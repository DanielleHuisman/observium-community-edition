-- ============================================================================
-- Copyright (C) 2017 by  HUAWEI TECHNOLOGIES. All rights reserved.
-- Description: This mib is used for autodiagnose
-- Reference: None
-- Version:   V1.02
-- ============================================================================

	HUAWEI-AUTODIAGNOSE-MIB DEFINITIONS ::= BEGIN
		IMPORTS   
			hwWlan			
				FROM HUAWEI-WLAN-MIB
			Integer32		
				FROM SNMPv2-SMI
			MacAddress, DateAndTime, RowStatus		
				FROM SNMPv2-TC 
			MODULE-COMPLIANCE, OBJECT-GROUP
        FROM SNMPv2-CONF
			IpAddress,MODULE-IDENTITY, OBJECT-TYPE
			  FROM SNMPv2-SMI;    
			    
		-- 1.3.6.1.4.1.2011.6.139.10	    
		hwAutodiag MODULE-IDENTITY	  
 
			LAST-UPDATED "201701171600Z"		-- May 4, 2014 at 16:00 GMT
			ORGANIZATION 
				"Huawei Technologies Co.,Ltd."
			CONTACT-INFO 
          "Huawei Industrial Base
				   Bantian, Longgang
				   Shenzhen 518129
				   People's Republic of China
				   Website: http://www.huawei.com
				   Email: support@huawei.com
				  "
			DESCRIPTION 
				"The MIB module include wids informations."
				
 			REVISION "201701171600Z"		-- May 08, 2012 at 00:00 GMT
			DESCRIPTION 
				"
				V1.02, Inital version.
				"

                               		REVISION "201512181600Z"		-- May 08, 2012 at 00:00 GMT
			DESCRIPTION 
				"
				V1.01, Inital version.
				"

			REVISION "201405041600Z"		-- May 08, 2012 at 00:00 GMT
			DESCRIPTION 
				"
				V1.00, Inital version.
				"
			::= { hwWlan 10}			    
--       
-- Node definitions
--
	
		-- 1.3.6.1.4.1.2011.6.139.10.1          
		hwAutoDiagnoseTable OBJECT-TYPE
			SYNTAX SEQUENCE OF HwAutoDiagnoseEntry
			MAX-ACCESS not-accessible
			STATUS current
			DESCRIPTION
			"Diagnostic task information table."
			::= { hwAutodiag 1 }

		
		-- 1.3.6.1.4.1.2011.6.139.10.1.1
		hwAutoDiagnoseEntry OBJECT-TYPE
			SYNTAX HwAutoDiagnoseEntry    
			MAX-ACCESS not-accessible
			STATUS current
			DESCRIPTION
			"Diagnostic task information table entry."
			INDEX { hwAutoDiagnoseTaskID }
			::= { hwAutoDiagnoseTable 1 }

		
		HwAutoDiagnoseEntry ::=
			SEQUENCE { 
				hwAutoDiagnoseIssueType
					INTEGER,
				hwAutoDiagnoseIssueID
					INTEGER,
				hwAutoDiagnoseObjetcMac
					MacAddress,
				hwAutoDiagnoseObjetcIP
					IpAddress,
				hwAutoDiagnoseObjetcIPv6
					OCTET STRING,
				hwAutoDiagnoseObjectName
					OCTET STRING,
				hwAutoDiagnoseObjetcGatewayIP
					IpAddress,
				hwAutoDiagnoseObjetcGatewayIPv6
					OCTET STRING,
				hwAutoDiagnoseStartTime
					DateAndTime,
				hwAutoDiagnoseTaskTimerangeStartTime
					DateAndTime,      				
				hwAutoDiagnoseTaskTimerangeEndTime
					DateAndTime,
				hwAutoDiagnoseTaskStatus
					INTEGER,
				hwAutoDiagnoseTaskType
					INTEGER,
				hwAutoDiagnoseTaskID
					Integer32,  
				hwAutoDiagnoseRowStatus
					RowStatus
			 }

		-- 1.3.6.1.4.1.2011.6.139.10.1.1.1
		hwAutoDiagnoseIssueType OBJECT-TYPE
			SYNTAX INTEGER
			  {
				 ac(1),
				 ap(2),
				 wirelessSta(3),
				 wiredSta(4),
				 switch(5)
				}
			MAX-ACCESS read-write
			STATUS current
			DESCRIPTION
			"Autodiagnose issue type,
       AC(1)
       AP(2)
       WIRELESS-STA(3)
       WIRED-STA(4) 
       SWITCH(5)"
			::= { hwAutoDiagnoseEntry 1 }

		
		-- 1.3.6.1.4.1.2011.6.139.10.1.1.2
		hwAutoDiagnoseIssueID OBJECT-TYPE
			SYNTAX INTEGER
			  {
			   allIssue(0),
				 staOnlineFail(1),
				 staOffline(2),
				 wiredlessStaUsageAbnormal(3),
				 apOfflineOrOnlineFail(4),
				 apDeviceException(5),
				 acDeviceException(6),
				 upgradeFail(7),
				 wiredStaUsageAbnormal(8),
				 switchDeviceException(9)
				}
			MAX-ACCESS read-write
			STATUS current
			DESCRIPTION
			"Autodiagnose issue ID.
			 all issue(0)
			 sta online fail (1)  
			 sta offline (2) 
			 wiredless-sta usage abnormal(3) 
			 ap offline or online fail(4) 
			 ap device exception(5)  
			 ac device exception(6) 
			 upgrade fail(7)  
			 wired-sta usage abnormal(8) 
			 switch device exception(9)
			 "
			::= { hwAutoDiagnoseEntry 2 }

		
		-- 1.3.6.1.4.1.2011.6.139.10.1.1.3
		hwAutoDiagnoseObjetcMac OBJECT-TYPE
			SYNTAX MacAddress
			MAX-ACCESS read-write
			STATUS current              
			DESCRIPTION
			"Appoint autodiagnose-object MAC address."
			::= { hwAutoDiagnoseEntry 3 }

		
		-- 1.3.6.1.4.1.2011.6.139.10.1.1.4
		hwAutoDiagnoseObjetcIP OBJECT-TYPE
			SYNTAX IpAddress
			MAX-ACCESS read-write
			STATUS current
			DESCRIPTION
			"Appoint autodiagnose-object IP address."
			::= { hwAutoDiagnoseEntry 4 }

		
		-- 1.3.6.1.4.1.2011.6.139.10.1.1.5
		hwAutoDiagnoseObjetcIPv6 OBJECT-TYPE
			SYNTAX OCTET STRING
			MAX-ACCESS read-write
			STATUS current
			DESCRIPTION
			"appoint autodiagnose-object IPv6 address."
			::= { hwAutoDiagnoseEntry 5 }

		
		-- 1.3.6.1.4.1.2011.6.139.10.1.1.6
		hwAutoDiagnoseObjectName OBJECT-TYPE
			SYNTAX OCTET STRING
			MAX-ACCESS read-write
			STATUS current
			DESCRIPTION
			"appoint autodiagnose-object name."
			::= { hwAutoDiagnoseEntry 6 }

		
		-- 1.3.6.1.4.1.2011.6.139.10.1.1.7
		hwAutoDiagnoseObjetcGatewayIP OBJECT-TYPE
			SYNTAX IpAddress
			MAX-ACCESS read-write
			STATUS current
			DESCRIPTION
			"appoint autodiagnose-object gateway IP address."
			::= { hwAutoDiagnoseEntry 7 }

		
		-- 1.3.6.1.4.1.2011.6.139.10.1.1.8
		hwAutoDiagnoseObjetcGatewayIPv6 OBJECT-TYPE
			SYNTAX OCTET STRING
			MAX-ACCESS read-write
			STATUS current
			DESCRIPTION
			"appoint autodiagnose-object gateway IPv6 address."
			::= { hwAutoDiagnoseEntry 8 }

		
		-- 1.3.6.1.4.1.2011.6.139.10.1.1.9
		hwAutoDiagnoseStartTime OBJECT-TYPE
			SYNTAX DateAndTime
			MAX-ACCESS read-write
			STATUS current
			DESCRIPTION
			"appoint autodiagnose-task start time."
			::= { hwAutoDiagnoseEntry 9 }

			
		-- 1.3.6.1.4.1.2011.6.139.10.1.1.10
		hwAutoDiagnoseTaskTimerangeStartTime OBJECT-TYPE
			SYNTAX DateAndTime
			MAX-ACCESS read-write
			STATUS current
			DESCRIPTION
			"Appoint autodiagnose-task time-range start time. The end time is later than start time."
			::= { hwAutoDiagnoseEntry 10 }
			
		-- 1.3.6.1.4.1.2011.6.139.10.1.1.11
		hwAutoDiagnoseTaskTimerangeEndTime OBJECT-TYPE
			SYNTAX DateAndTime
			MAX-ACCESS read-write
			STATUS current
			DESCRIPTION
			"Appoint task time-range end time. The end time is later than start time"
			::= { hwAutoDiagnoseEntry 11 }
		
		-- 1.3.6.1.4.1.2011.6.139.10.1.1.12
		hwAutoDiagnoseTaskStatus OBJECT-TYPE
			SYNTAX INTEGER
			  {
				 idle(1),
				 waiting(2),
				 ready(3),
				 running(4),
				 done(5),
				 dead(6),
				 timeout(7)
				}
			MAX-ACCESS read-only
			STATUS current
			DESCRIPTION
			"Appoint task status. 
			 IDLE(1) 
			 WAITTING(2) 
			 READY(3)
			 RUNNING(4) 
			 DONE(5) 
			 DEAD(6)
			 TIMEOUT(7)"
			::= { hwAutoDiagnoseEntry 12 }

		
		-- 1.3.6.1.4.1.2011.6.139.10.1.1.13
		hwAutoDiagnoseTaskType OBJECT-TYPE
			SYNTAX INTEGER
			  {
				 timerTask(1),
				 realTimeTask(2)
				}
			MAX-ACCESS read-only
			STATUS current
			DESCRIPTION
			"Appoint task type. 
			 Timer task(1) 
			 Real time task(2)"
			::= { hwAutoDiagnoseEntry 13 }

		
		-- 1.3.6.1.4.1.2011.6.139.10.1.1.14
		hwAutoDiagnoseTaskID OBJECT-TYPE
			SYNTAX Integer32
			MAX-ACCESS read-write
			STATUS current
			DESCRIPTION
			"Appoint task ID. ID 0 is real time task ID region <1-5> is timer task"
			::= { hwAutoDiagnoseEntry 14 }

					      
		-- 1.3.6.1.4.1.2011.6.139.10.1.1.15
		hwAutoDiagnoseRowStatus OBJECT-TYPE
			SYNTAX RowStatus
			MAX-ACCESS read-create
			STATUS current
			DESCRIPTION
			"Appoint create or delete task."
			::= { hwAutoDiagnoseEntry 15 }


		-- 1.3.6.1.4.1.2011.6.139.10.2
		hwAutoDiagnoseIssueResultTable OBJECT-TYPE
			SYNTAX SEQUENCE OF HwAutoDiagnoseIssueResultEntry
			MAX-ACCESS not-accessible
			STATUS current
			DESCRIPTION
			"Appoint task issue result table."
			::= { hwAutodiag 2 }

		
		-- 1.3.6.1.4.1.2011.6.139.10.2.1    
		hwAutoDiagnoseIssueResultEntry OBJECT-TYPE
			SYNTAX HwAutoDiagnoseIssueResultEntry
			MAX-ACCESS not-accessible
			STATUS current
			DESCRIPTION
			"Appoint task issue result table entry."
			INDEX { hwAutoDiagnoseTaskID,hwAutoDiagnoseIssueIndex }
			::= { hwAutoDiagnoseIssueResultTable 1 }

		
		HwAutoDiagnoseIssueResultEntry ::=
			SEQUENCE { 
				hwAutoDiagnoseIssueIndex
					Integer32,     
				hwAutoDiagnoseIssueIdNum
				  INTEGER,
				hwAutoDiagnoseIssueResult
					INTEGER,
				hwAutoDiagnoseIssueStatus
					INTEGER,
				hwAutoDiagnoseIssueSuggestion
					OCTET STRING,
				hwAutoDiagnoseIssueSuggestion
					OCTET STRING,
				hwAutoDiagnoseIssueSuggestionCh
					OCTET STRING	
					 }
		
		-- 1.3.6.1.4.1.2011.6.139.10.2.1.1
		hwAutoDiagnoseIssueIndex OBJECT-TYPE
			SYNTAX Integer32
			MAX-ACCESS read-write
			STATUS current
			DESCRIPTION
			"Appoint task issue index."
			::= { hwAutoDiagnoseIssueResultEntry 1 }     
			
		-- 1.3.6.1.4.1.2011.6.139.10.2.1.2
		hwAutoDiagnoseIssueIdNum OBJECT-TYPE
			SYNTAX INTEGER
			  {
				 staOnlineFail(1),
				 staOffline(2),
				 wiredlessStaUsageAbnormal(3),
				 apOfflineOrOnlineFail(4),
				 apDeviceException(5),
				 acDeviceException(6),
				 upgradeFail(7),
				 wiredStaUsageAbnormal(8),
				 switchDeviceException(9)
				}
			MAX-ACCESS read-only
			STATUS current
			DESCRIPTION
			"Appoint task issue ID.
			 sta online fail (1)  
			 sta offline (2) 
			 wireless-sta usage abnormal(3) 
			 ap offline or online fail(4) 
			 ap device exception(5)  
			 ac device exception(6) 
			 upgrade fail(7)  
			 wired-sta usage abnormal(8)
			 switch device exception(9)"
			::= { hwAutoDiagnoseIssueResultEntry 2 }


		                                                          
		-- 1.3.6.1.4.1.2011.6.139.10.2.1.3
		hwAutoDiagnoseIssueResult OBJECT-TYPE
			SYNTAX INTEGER
			  {
				 noProblem(1),
				 existProblem(2),
				 potentialProblem(3),
				 execFail(4)
				}
			MAX-ACCESS read-only
			STATUS current
			DESCRIPTION
			"Appoint task issue result. 
			no problem(1) 
			exist problem(2) 
			potential problem(3) 
			exec fail(4)"
			::= { hwAutoDiagnoseIssueResultEntry 3 }

		
		-- 1.3.6.1.4.1.2011.6.139.10.2.1.4
		hwAutoDiagnoseIssueStatus OBJECT-TYPE
			SYNTAX INTEGER
			  {
				 waiting(1),
				 running(2),
				 done(3)
				}
			MAX-ACCESS read-only
			STATUS current
			DESCRIPTION
			"Appoint autodiagnose-task issue execute status.waiting(1) running(2) done(3)"
			::= { hwAutoDiagnoseIssueResultEntry 4 }

		
		-- 1.3.6.1.4.1.2011.6.139.10.2.1.5
		hwAutoDiagnoseIssueSuggestion OBJECT-TYPE
			SYNTAX OCTET STRING
			MAX-ACCESS read-only
			STATUS current
			DESCRIPTION
			"Appoint autodiagnose-task issue execute suggestion."
			::= { hwAutoDiagnoseIssueResultEntry 5 }

		-- 1.3.6.1.4.1.2011.6.139.10.2.1.6
		hwAutoDiagnoseIssueSuggestionCh OBJECT-TYPE
			SYNTAX OCTET STRING
			MAX-ACCESS read-only
			STATUS current
			DESCRIPTION
			"Appoint autodiagnose-task issue execute chinese suggestion."
			::= { hwAutoDiagnoseIssueResultEntry 6 }
			
		-- 1.3.6.1.4.1.2011.6.139.10.3
		hwAutoDiagnoseSubIssueResultTable OBJECT-TYPE
			SYNTAX SEQUENCE OF HwAutoDiagnoseSubIssueResultEntry
			MAX-ACCESS not-accessible
			STATUS current
			DESCRIPTION
			"Appoint autodiagnose-task sub-issue execute result table. "
			::= { hwAutodiag 3 }

		
		-- 1.3.6.1.4.1.2011.6.139.10.3.1
		hwAutoDiagnoseSubIssueResultEntry OBJECT-TYPE
			SYNTAX HwAutoDiagnoseSubIssueResultEntry
			MAX-ACCESS not-accessible
			STATUS current
			DESCRIPTION
			"Appoint autodiagnose-task sub-issue execute result table."
			INDEX { hwAutoDiagnoseTaskID, hwAutoDiagnoseIssueIndex, hwAutoDiagnoseSubIssueIndex }
			::= { hwAutoDiagnoseSubIssueResultTable 1 }

		
		HwAutoDiagnoseSubIssueResultEntry ::=
			SEQUENCE { 
				hwAutoDiagnoseSubIssueIndex
					Integer32,
				hwAutoDiagnoseSubIssueId
					Integer32,
				hwAutoDiagnoseSubIssueStatus
					INTEGER,
				hwAutoDiagnoseSubIssueResult
					INTEGER,
				hwAutoDiagnoseSubIssueFaultReason
			                                      OCTET STRING,
			                      hwAutoDiagnoseSubIssueFaultDealSuggestion
			                                      OCTET STRING,
			                      hwAutoDiagnoseSubIssueName
			                                      OCTET STRING,
			                      hwAutoDiagnoseSubIssueFaultReasonCh
			                                      OCTET STRING,
			                      hwAutoDiagnoseSubIssueFaultDealSuggestionCh
                			                                      OCTET STRING
					 }     
					 
		-- 1.3.6.1.4.1.2011.6.139.10.3.1.1
		hwAutoDiagnoseSubIssueIndex OBJECT-TYPE
			SYNTAX Integer32
			MAX-ACCESS read-write
			STATUS current
			DESCRIPTION
			"Appoint autodiagnose-task sub-issue execute result table index."
			::= { hwAutoDiagnoseSubIssueResultEntry 1 }
			
		-- 1.3.6.1.4.1.2011.6.139.10.3.1.2 
		hwAutoDiagnoseSubIssueId OBJECT-TYPE
			SYNTAX Integer32
			MAX-ACCESS read-only
			STATUS current
			DESCRIPTION
			"Appoint task sub-issue ID."
			::= { hwAutoDiagnoseSubIssueResultEntry 2 }     
			
		-- 1.3.6.1.4.1.2011.6.139.10.3.1.3
		hwAutoDiagnoseSubIssueStatus OBJECT-TYPE
			SYNTAX INTEGER
				{
				waitting(1),
				running(2),
				done(3)
				}
			MAX-ACCESS read-only
			STATUS current
			DESCRIPTION
			"Describe sub-issue execute status.
			 waitting(1) 
			 running(2) 
			 done(3)"
			::= { hwAutoDiagnoseSubIssueResultEntry 3 }

		-- 1.3.6.1.4.1.2011.6.139.10.3.1.4
		hwAutoDiagnoseSubIssueResult OBJECT-TYPE
			SYNTAX INTEGER
			  {
				 noProblem(1),
				 existProblem(2),
				 potentialProblem(3),
				 execFail(4)
				}
			MAX-ACCESS read-only
			STATUS current
			DESCRIPTION
			"Describe sub-issue execute result.
			no problem(1) 
			exist problem(2) 
			potential problem(3) 
			exec fail(4)"
			::= { hwAutoDiagnoseSubIssueResultEntry 4 }

		-- 1.3.6.1.4.1.2011.6.139.10.3.1.5
		hwAutoDiagnoseSubIssueFaultReason OBJECT-TYPE
			SYNTAX OCTET STRING
			MAX-ACCESS read-only
			STATUS current
			DESCRIPTION
			"Describe the subissue fault reason."
			::= { hwAutoDiagnoseSubIssueResultEntry 5 }

		-- 1.3.6.1.4.1.2011.6.139.10.3.1.6
		hwAutoDiagnoseSubIssueFaultDealSuggestion OBJECT-TYPE
			SYNTAX OCTET STRING
			MAX-ACCESS read-only
			STATUS current
			DESCRIPTION
			"Describe the subissue suggestion."
			::= { hwAutoDiagnoseSubIssueResultEntry 6 }

		-- 1.3.6.1.4.1.2011.6.139.10.3.1.7
		hwAutoDiagnoseSubIssueName OBJECT-TYPE
			SYNTAX OCTET STRING
			MAX-ACCESS read-only
			STATUS current
			DESCRIPTION
			"Describe the subissue name."
			::= { hwAutoDiagnoseSubIssueResultEntry 7 }


		-- 1.3.6.1.4.1.2011.6.139.10.3.1.8
		hwAutoDiagnoseSubIssueFaultReasonCh OBJECT-TYPE
			SYNTAX OCTET STRING
			MAX-ACCESS read-only
			STATUS current
			DESCRIPTION
			"Describe the subissue fault chinese reason."
			::= { hwAutoDiagnoseSubIssueResultEntry 8 }

		-- 1.3.6.1.4.1.2011.6.139.10.3.1.9
		hwAutoDiagnoseSubIssueFaultDealSuggestionCh OBJECT-TYPE
			SYNTAX OCTET STRING
			MAX-ACCESS read-only
			STATUS current
			DESCRIPTION
			"Describe the subissue chinese suggestion."
			::= { hwAutoDiagnoseSubIssueResultEntry 9 }
		
		-- 1.3.6.1.4.1.2011.6.139.10.4
		hwAutoDiagnoseSubIssueDetailResultTable OBJECT-TYPE
			SYNTAX SEQUENCE OF HwAutoDiagnoseSubIssueDetailResultEntry
			MAX-ACCESS not-accessible
			STATUS current
			DESCRIPTION
			"Describe subissue-detail result table."
			::= { hwAutodiag 4 }

		-- 1.3.6.1.4.1.2011.6.139.10.4.1
		hwAutoDiagnoseSubIssueDetailResultEntry OBJECT-TYPE
			SYNTAX HwAutoDiagnoseSubIssueDetailResultEntry
			MAX-ACCESS not-accessible
			STATUS current
			DESCRIPTION
			"Describe subissue-detail result table-entry."
			INDEX { hwAutoDiagnoseTaskID,hwAutoDiagnoseIssueIndex, hwAutoDiagnoseSubIssueIndex, hwAutoDiagnoseSubIssueDetailIndex }
			::= { hwAutoDiagnoseSubIssueDetailResultTable 1 }

		HwAutoDiagnoseSubIssueDetailResultEntry ::=
			SEQUENCE { 
				hwAutoDiagnoseSubIssueDetailIndex
					Integer32,      
			                     hwAutoDiagnoseSubIssueDetailResult
					INTEGER,
				hwAutoDiagnoseSubIssueDetailFaultReason
					OCTET STRING,
				hwAutoDiagnoseSubIssueDetailFaultDealSuggestion
					OCTET STRING,
				hwAutoDiagnoseSubIssueDetailFaultReasonCh
					OCTET STRING,
				hwAutoDiagnoseSubIssueDetailFaultDealSuggestionCh
					OCTET STRING
					 }
					  
		-- 1.3.6.1.4.1.2011.6.139.10.4.1.1
		hwAutoDiagnoseSubIssueDetailIndex OBJECT-TYPE
			SYNTAX Integer32
			MAX-ACCESS read-write
			STATUS current
			DESCRIPTION
			"Subissue-detail result table index."
			::= { hwAutoDiagnoseSubIssueDetailResultEntry 1 }  
			
		-- 1.3.6.1.4.1.2011.6.139.10.4.1.2
		hwAutoDiagnoseSubIssueDetailResult OBJECT-TYPE
			SYNTAX INTEGER
			  {
				 noProblem(1),
				 existProblem(2),
				 potentialProblem(3),
				 execFail(4)
				}
			MAX-ACCESS read-only
			STATUS current
			DESCRIPTION
			"Subissue-detail result. 
			 no problem(1) 
			 exist problem(2) 
			 potential problem(3) 
			 exec fail(4)"
			::= { hwAutoDiagnoseSubIssueDetailResultEntry 2 }    
						      
		-- 1.3.6.1.4.1.2011.6.139.10.4.1.3
		hwAutoDiagnoseSubIssueDetailFaultReason OBJECT-TYPE
			SYNTAX OCTET STRING
			MAX-ACCESS read-only
			STATUS current
			DESCRIPTION
			"Subissue-detail result reason."
			::= { hwAutoDiagnoseSubIssueDetailResultEntry 3 }    

		-- 1.3.6.1.4.1.2011.6.139.10.4.1.4
		hwAutoDiagnoseSubIssueDetailFaultDealSuggestion OBJECT-TYPE
			SYNTAX OCTET STRING
			MAX-ACCESS read-only
			STATUS current
			DESCRIPTION
			"Subissue-detail result suggestion."
			::= { hwAutoDiagnoseSubIssueDetailResultEntry 4 }
			
		-- 1.3.6.1.4.1.2011.6.139.10.4.1.5
		hwAutoDiagnoseSubIssueDetailFaultReasonCh OBJECT-TYPE
			SYNTAX OCTET STRING
			MAX-ACCESS read-only
			STATUS current
			DESCRIPTION
			"Subissue-detail result chinese reason."
			::= { hwAutoDiagnoseSubIssueDetailResultEntry 5 }    

		-- 1.3.6.1.4.1.2011.6.139.10.4.1.6
		hwAutoDiagnoseSubIssueDetailFaultDealSuggestionCh OBJECT-TYPE
			SYNTAX OCTET STRING
			MAX-ACCESS read-only
			STATUS current
			DESCRIPTION
			"Subissue-detail result chinese suggestion."
			::= { hwAutoDiagnoseSubIssueDetailResultEntry 6 }

		-- 1.3.6.1.4.1.2011.6.139.10.5
		hwAutoDiagnoseConformance OBJECT IDENTIFIER ::= { hwAutodiag 5 }

		
		-- 1.3.6.1.4.1.2011.6.139.10.5.1
		hwAutoDiagnoseCompliances OBJECT IDENTIFIER ::= { hwAutoDiagnoseConformance 1 }

		
		-- 1.3.6.1.4.1.2011.6.139.10.5.1.1
		hwAutoDiagnoseCompliance MODULE-COMPLIANCE
			STATUS current
			DESCRIPTION 
			"Description."
      MODULE 
			::= { hwAutoDiagnoseCompliances 1 }

		
		-- 1.3.6.1.4.1.2011.6.139.10.5.2
		hwAutoDiagnoseObjectGroups OBJECT IDENTIFIER ::= { hwAutoDiagnoseConformance 2 }				
		
		-- 1.3.6.1.4.1.2011.6.139.10.5.2.1
		hwAutoDiagnosetGroups OBJECT-GROUP
			OBJECTS { hwAutoDiagnoseIssueType, hwAutoDiagnoseIssueID,hwAutoDiagnoseObjetcMac,hwAutoDiagnoseObjetcIP,
                      hwAutoDiagnoseObjetcIPv6, hwAutoDiagnoseObjectName, hwAutoDiagnoseObjetcGatewayIP,hwAutoDiagnoseObjetcGatewayIPv6,
                      hwAutoDiagnoseStartTime, hwAutoDiagnoseTaskTimerangeStartTime, hwAutoDiagnoseTaskTimerangeEndTime,
                      hwAutoDiagnoseTaskStatus, hwAutoDiagnoseTaskType,  hwAutoDiagnoseRowStatus
                     }
			STATUS current
			DESCRIPTION 
				"Description."
			::= { hwAutoDiagnoseObjectGroups 1 }

		-- 1.3.6.1.4.1.2011.6.139.10.5.2.2
		hwAutoDiagnosetIssueResultGroups OBJECT-GROUP
			OBJECTS { hwAutoDiagnoseIssueIndex, hwAutoDiagnoseIssueIdNum, hwAutoDiagnoseIssueResult, hwAutoDiagnoseIssueStatus,hwAutoDiagnoseIssueSuggestion,hwAutoDiagnoseIssueSuggestionCh }
			STATUS current
			DESCRIPTION 
				"Description."
			::= { hwAutoDiagnoseObjectGroups 2 }    
			 
		-- 1.3.6.1.4.1.2011.6.139.10.5.2.3
		hwAutoDiagnosetSubIssueResultGroups OBJECT-GROUP
			OBJECTS { hwAutoDiagnoseSubIssueId, hwAutoDiagnoseSubIssueStatus, hwAutoDiagnoseSubIssueName,
				      hwAutoDiagnoseSubIssueResult, hwAutoDiagnoseSubIssueFaultReason, hwAutoDiagnoseSubIssueFaultDealSuggestion,hwAutoDiagnoseSubIssueFaultReasonCh,hwAutoDiagnoseSubIssueFaultDealSuggestionCh
				    }
			STATUS current
			DESCRIPTION 
				"Description."
			::= { hwAutoDiagnoseObjectGroups 3 }         

		-- 1.3.6.1.4.1.2011.6.139.10.5.2.4
		hwAutoDiagnosetSubIssueDetailResultGroups OBJECT-GROUP
			OBJECTS { hwAutoDiagnoseSubIssueDetailResult, hwAutoDiagnoseSubIssueDetailFaultReason,
				      hwAutoDiagnoseSubIssueDetailFaultDealSuggestion,hwAutoDiagnoseSubIssueDetailFaultReasonCh,hwAutoDiagnoseSubIssueDetailFaultDealSuggestionCh
				    }
			STATUS current
			DESCRIPTION 
				"Description."
			::= { hwAutoDiagnoseObjectGroups 4 }					
	
	END
         
--
-- HUAWEI-AUTODIAGNOSE-MIB.mib
--

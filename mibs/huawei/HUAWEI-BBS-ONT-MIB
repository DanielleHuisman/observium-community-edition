-- =================================================================                                                  
-- Copyright (C) 2014 by HUAWEI TECHNOLOGIES. All rights reserved                                                   
-- Description:  The MIB is used for defining Huawei's BBS MIB objects for both profile-mode and distributing-mode.                                                             
-- Reference:                                                                                                 
-- Version: V1.02
-- ================================================================                    


    HUAWEI-BBS-ONT-MIB DEFINITIONS ::= BEGIN
        IMPORTS
            MODULE-IDENTITY, mib-2, OBJECT-TYPE, Counter32, Counter64,
            Unsigned32, Integer32, zeroDotZero, IpAddress, Gauge32, NOTIFICATION-TYPE
                FROM SNMPv2-SMI
            TruthValue, DateAndTime, RowStatus, MacAddress,TEXTUAL-CONVENTION
                FROM SNMPv2-TC
            ifIndex
                FROM IF-MIB
            MODULE-COMPLIANCE, OBJECT-GROUP
                FROM SNMPv2-CONF
            OwnerString, EntryStatus
                FROM RMON-MIB
            huaweiMgmt, huaweiUtility
                FROM HUAWEI-MIB;


        hwBbsOntMIB MODULE-IDENTITY
            LAST-UPDATED "201410240900Z"
            ORGANIZATION "Huawei Technologies Co.,Ltd."
            CONTACT-INFO                                        
                         "Huawei Industrial Base                
                          Bantian, Longgang                     
                          Shenzhen 518129                       
                          People's Republic of China            
                          Website: http://www.huawei.com        
                          Email: support@huawei.com             
                         "                                      
            DESCRIPTION  "The MIB is used for defining Huawei's BBS MIB objects for both profile-mode and distributing-mode.
            		 "

    --  Revision history
            REVISION     "201410240900Z"
            DESCRIPTION  "V1.02, changes in this revision:
                         - Modify the implied value of the leaf hwBbsCosQueueMapProfileNameIndex.
                         "
            
	    REVISION     "201406160900Z"           
            DESCRIPTION  "V1.01, changes in this revision:
                         - Modify the description of hwBbsOntCosQueueMapBindTable and hwBbsOntCosQueueMapBindEntry.
                         "   
    
            REVISION     "201109300900Z"
            DESCRIPTION  "V1.00, Initial version."
            ::= { huaweiUtility  173 }

        hwBbsObjectMIB OBJECT IDENTIFIER ::= { hwBbsOntMIB 1}

  --Table hwBbsCosQueueMapProfileTable
        hwBbsCosQueueMapProfileTable OBJECT-TYPE
            SYNTAX SEQUENCE OF HwBbsCosQueueMapProfileEntry
            MAX-ACCESS not-accessible
            STATUS     current
            DESCRIPTION
                "The hwBbsCosQueueMapProfileTable is used to config the ONT cos-queue-map profile.
                 The index of this table is hwBbsCosQueueMapProfileNameIndex.
                "
            ::= { hwBbsObjectMIB 1 }

        hwBbsCosQueueMapProfileEntry OBJECT-TYPE
            SYNTAX HwBbsCosQueueMapProfileEntry
            MAX-ACCESS not-accessible
            STATUS current
            DESCRIPTION
                "The hwBbsCosQueueMapProfileTable is used to config the ONT cos-queue-map profile.
                 The index of this entry is hwBbsCosQueueMapProfileNameIndex.
                "
            INDEX       { IMPLIED hwBbsCosQueueMapProfileNameIndex }
            ::= { hwBbsCosQueueMapProfileTable 1 }

        HwBbsCosQueueMapProfileEntry ::=
            SEQUENCE
                {
                hwBbsCosQueueMapProfileNameIndex        	OCTET STRING,
                hwBbsCosQueueMapProfileCos0QueueId              Integer32,
                hwBbsCosQueueMapProfileCos1QueueId		Integer32,
                hwBbsCosQueueMapProfileCos2QueueId          	Integer32,
                hwBbsCosQueueMapProfileCos3QueueId         	Integer32,
                hwBbsCosQueueMapProfileCos4QueueId        	Integer32,
                hwBbsCosQueueMapProfileCos5QueueId		Integer32,
                hwBbsCosQueueMapProfileCos6QueueId		Integer32,
                hwBbsCosQueueMapProfileCos7QueueId		Integer32,
                hwBbsCosQueueMapProfileBindNum	                Integer32,
                hwBbsCosQueueMapProfileRowStatus                RowStatus
                }

        hwBbsCosQueueMapProfileNameIndex  OBJECT-TYPE
            SYNTAX OCTET STRING (SIZE (1..32))
            MAX-ACCESS   not-accessible
            STATUS       current
            DESCRIPTION
                "This object indicates the ONT cos-queue-map profile name index.
                "
            ::= { hwBbsCosQueueMapProfileEntry 1 }

        hwBbsCosQueueMapProfileCos0QueueId OBJECT-TYPE
            SYNTAX Integer32 (0..7)
            MAX-ACCESS read-write
            STATUS current
            DESCRIPTION
                "This object indicates the queue ID of cos0.
                "
            ::= { hwBbsCosQueueMapProfileEntry 2 }

        hwBbsCosQueueMapProfileCos1QueueId OBJECT-TYPE
            SYNTAX Integer32 (0..7)
            MAX-ACCESS read-write
            STATUS current
            DESCRIPTION
                "This object indicates the queue ID of cos1.
                "
            ::= { hwBbsCosQueueMapProfileEntry 3 }
            
        hwBbsCosQueueMapProfileCos2QueueId OBJECT-TYPE
            SYNTAX Integer32 (0..7)
            MAX-ACCESS read-write
            STATUS current
            DESCRIPTION
                "This object indicates the queue ID of cos2.
                "
            ::= { hwBbsCosQueueMapProfileEntry 4 }
            
        hwBbsCosQueueMapProfileCos3QueueId OBJECT-TYPE
            SYNTAX Integer32 (0..7)
            MAX-ACCESS read-write
            STATUS current
            DESCRIPTION
                "This object indicates the queue ID of cos3.
                "
            ::= { hwBbsCosQueueMapProfileEntry 5 }
       
        hwBbsCosQueueMapProfileCos4QueueId OBJECT-TYPE
            SYNTAX Integer32 (0..7)
            MAX-ACCESS read-write
            STATUS current
            DESCRIPTION
                "This object indicates the queue ID of cos4.
                "
            ::= { hwBbsCosQueueMapProfileEntry 6 }
            
        hwBbsCosQueueMapProfileCos5QueueId OBJECT-TYPE
            SYNTAX Integer32 (0..7)
            MAX-ACCESS read-write
            STATUS current
            DESCRIPTION
                "This object indicates the queue ID of cos5.
                "   
            ::= { hwBbsCosQueueMapProfileEntry 7 }
            
        hwBbsCosQueueMapProfileCos6QueueId OBJECT-TYPE
            SYNTAX Integer32 (0..7)
            MAX-ACCESS read-write
            STATUS current
            DESCRIPTION
                "This object indicates the queue ID of cos6.
                "
            ::= { hwBbsCosQueueMapProfileEntry 8 }
            
        hwBbsCosQueueMapProfileCos7QueueId OBJECT-TYPE
            SYNTAX Integer32 (0..7)
            MAX-ACCESS read-write
            STATUS current
            DESCRIPTION
                "This object indicates the queue ID of cos7.
                "
            ::= { hwBbsCosQueueMapProfileEntry 9 }
        
        hwBbsCosQueueMapProfileBindNum OBJECT-TYPE
            SYNTAX Integer32
            MAX-ACCESS read-only
            STATUS current
            DESCRIPTION
                "This object indicates the number of ONT bound with cos-queue-map profile."
            ::= { hwBbsCosQueueMapProfileEntry 10 }
                
        hwBbsCosQueueMapProfileRowStatus OBJECT-TYPE
            SYNTAX RowStatus
            MAX-ACCESS read-create
            STATUS current
            DESCRIPTION
                "The hwBbsCosQueueMapProfileRowStatus is used to create a new row
                 or to modify or delete an existing row in this table.
                "
            ::= { hwBbsCosQueueMapProfileEntry 11 }
            
  --Table hwBbsCosQueueMapProfileTable   end
  
  --Table hwBbsOntCosQueueMapBindTable   
  	hwBbsOntCosQueueMapBindTable OBJECT-TYPE
            SYNTAX SEQUENCE OF HwBbsOntCosQueueMapBindEntry
            MAX-ACCESS not-accessible
            STATUS     current
            DESCRIPTION
                "The hwBbsOntCosQueueMapBindTable is used for ONT binding or unbinding cos-queue-map profile.
                 The index of this table is ifIndex and hwBbsOntIndex.
                "
            ::= { hwBbsObjectMIB 2 }
            
   	hwBbsOntCosQueueMapBindEntry OBJECT-TYPE
            SYNTAX HwBbsOntCosQueueMapBindEntry
            MAX-ACCESS not-accessible
            STATUS current
            DESCRIPTION
                "The hwBbsOntCosQueueMapBindTable is used for ONT binding or unbinding cos-queue-map profile.
                 The index of this entry is ifIndex and hwBbsOntIndex.
                "
            INDEX       { ifIndex, hwBbsOntIndex }
            ::= { hwBbsOntCosQueueMapBindTable 1 }

        HwBbsOntCosQueueMapBindEntry ::=
            SEQUENCE
                {
                hwBbsOntIndex                               Integer32,
		hwBbsOntBindUpCosQueueMapProfileName        OCTET STRING,
		hwBbsOntBindDownCosQueueMapProfileName      OCTET STRING
                }
                
        hwBbsOntIndex OBJECT-TYPE
	       SYNTAX   Integer32
	       MAX-ACCESS  not-accessible
	       STATUS   current
	       DESCRIPTION
	           "The index of the bound cos-queue-map profile ONT."
	       ::= { hwBbsOntCosQueueMapBindEntry 1 }
                
        hwBbsOntBindUpCosQueueMapProfileName   OBJECT-TYPE
            SYNTAX OCTET STRING (SIZE (0..32))
            MAX-ACCESS   read-write
            STATUS       current
            DESCRIPTION
                "The name of upstream cos-queue-map profile which used by the ONT.
                "
            ::= { hwBbsOntCosQueueMapBindEntry 2 }
            
        hwBbsOntBindDownCosQueueMapProfileName   OBJECT-TYPE
            SYNTAX OCTET STRING (SIZE (0..32))
            MAX-ACCESS   read-write
            STATUS       current
            DESCRIPTION
                "The name of downstream cos-queue-map profile which used by the ONT.
                "
            ::= { hwBbsOntCosQueueMapBindEntry 3 }
                
   --Table hwBbsOntCosQueueMapBindTable   end
   
        END

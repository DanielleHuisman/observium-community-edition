-- =================================================================
-- Copyright (C) 2013 by  HUAWEI TECHNOLOGIES. All rights reserved.
--
-- DESCRIPTION:  HUAWEI-DIE-MIB
-- Reference:  
-- Version: V1.00
-- History:
--         Created by g00141720  2012-12-18
-- =================================================================

    HUAWEI-DIE-MIB DEFINITIONS ::= BEGIN

        IMPORTS 
            huaweiMgmt, hwDatacomm         
                FROM HUAWEI-MIB            
            IpAddress, Unsigned32, Counter64, OBJECT-TYPE, MODULE-IDENTITY, 
            NOTIFICATION-TYPE,Integer32,Counter32     
                FROM SNMPv2-SMI        
           MODULE-COMPLIANCE,OBJECT-GROUP,NOTIFICATION-GROUP
                FROM SNMPv2-CONF	
    
            DisplayString, RowStatus, TruthValue, MacAddress, DateAndTime            
                FROM SNMPv2-TC;
                
        hwDIEmib MODULE-IDENTITY 
            LAST-UPDATED "201301101150Z"
            ORGANIZATION "Huawei Technologies Co.,Ltd."
            CONTACT-INFO 
                "Huawei Industrial Base
                  Bantian, Longgang
                   Shenzhen 518129
                   People's Republic of China
                   Website: http://www.huawei.com
                   Email: support@huawei.com"
            DESCRIPTION 
                "The MIB module for creating and deleting bulk files of
                SNMP data for file transfer."
            REVISION "201301101150Z"              -- January 11, 2013 at 11:50 GMT
            DESCRIPTION 
                "The MIB module for creating and deleting bulk files of
                SNMP data for file transfer."
            REVISION "201306291150Z"              -- JUNE 26, 2013 at 11:50 GMT
            DESCRIPTION 
                "The MIB module for creating and deleting bulk files of
                SNMP data for file transfer."
            REVISION "201310261150Z"              -- OCT 28, 2013 at 11:50 GMT

            DESCRIPTION
                "The MIB contains objects of module DIE."
            ::= { hwDatacomm 317 }

--
-- Node definitions
--

        hwDIEMibObjects OBJECT IDENTIFIER ::= { hwDIEmib 1 }

        hwDIETable OBJECT-TYPE
            SYNTAX SEQUENCE OF HwDIEEntry
            MAX-ACCESS not-accessible
            STATUS current
            DESCRIPTION
                "The DIE table."
            ::= { hwDIEMibObjects 1 }

        hwDIEEntry OBJECT-TYPE
            SYNTAX HwDIEEntry
            MAX-ACCESS not-accessible
            STATUS current
            DESCRIPTION
                "The DIE entry."
            INDEX { hwDIEDeviceProfileIndex }
            ::= { hwDIETable 1 }

        HwDIEEntry ::=
            SEQUENCE {
                hwDIEDeviceProfileIndex
                    Integer32,
                hwDIEDeviceProfileName
                    DisplayString,
                hwDIEDeviceProfileDevType
                    DisplayString,
                hwDIEDeviceProfileEnable    
                    INTEGER,
                hwDIEDeviceProfileRuleLogic
                    DisplayString,                    
                hwDIEDeviceProfileRowStatus
                    RowStatus
             }

        hwDIEDeviceProfileIndex OBJECT-TYPE
            SYNTAX      Integer32(0..128)
            MAX-ACCESS  read-only
            STATUS      current
            DESCRIPTION
                "DIE profile index."
            ::={ hwDIEEntry 1 }

       hwDIEDeviceProfileName OBJECT-TYPE
            SYNTAX DisplayString (SIZE (1..32))
            MAX-ACCESS read-create
            STATUS current
            DESCRIPTION
                "DIE profile name."
            ::= { hwDIEEntry 2 }
            
        hwDIEDeviceProfileDevType OBJECT-TYPE
            SYNTAX DisplayString (SIZE (0..32))
            MAX-ACCESS read-create
            STATUS current
            DESCRIPTION
                "DIE profile device type."
            ::= { hwDIEEntry 3 }
            
         hwDIEDeviceProfileEnable OBJECT-TYPE
            SYNTAX INTEGER
                {
                    disable(1),
                    enable(2)
                }
            MAX-ACCESS read-create
            STATUS current
            DESCRIPTION
                "Specify device profile enable Flag."
            ::= { hwDIEEntry 4 }  
            
         hwDIEDeviceProfileRuleLogic OBJECT-TYPE
            SYNTAX DisplayString (SIZE (0..80))
            MAX-ACCESS  read-create
            STATUS      current
            DESCRIPTION
                "Rule operation logic."
            ::={ hwDIEEntry 5 }            
            
         hwDIEDeviceProfileRowStatus OBJECT-TYPE
            SYNTAX      RowStatus
            MAX-ACCESS  read-create
            STATUS      current
            DESCRIPTION
                "RowStatus."
            ::={ hwDIEEntry 6 }    
				    
        hwDIERuleTable  OBJECT-TYPE
            SYNTAX SEQUENCE OF HwDIERuleEntry
            MAX-ACCESS not-accessible
            STATUS current
            DESCRIPTION
                "The DIE extend table."
            ::= { hwDIEMibObjects 2 }
                              
        hwDIERuleEntry OBJECT-TYPE
            SYNTAX HwDIERuleEntry
            MAX-ACCESS not-accessible
            STATUS current
            DESCRIPTION
                "The DIE extend entry."
            INDEX { hwDIEDeviceProfileIndex, hwDIERuleRuleIndex }
            ::= { hwDIERuleTable 1 }

        HwDIERuleEntry ::=
            SEQUENCE {
                hwDIERuleRuleIndex
                    Integer32,
                hwDIERuleMacAddress
                    MacAddress,
                hwDIERuleMacMask
                    Integer32,
                hwDIERuleDhcpOptionID    
                    Integer32,
                hwDIERuleDhcpOptionType
                    INTEGER,
                hwDIERuleDhcpOptionTextAscii
                    DisplayString,
                hwDIERuleDhcpOptionTextHex
                    DisplayString,
                hwDIERuleDhcpOptionMatch
                    INTEGER,
                hwDIERuleUserAgentText
                    DisplayString,
                hwDIERuleUserAgentMatch
                    INTEGER,
                hwDIERuleRowStatus
                    RowStatus
             }
             
         hwDIERuleRuleIndex OBJECT-TYPE
            SYNTAX      Integer32(0..7)
            MAX-ACCESS  read-only
            STATUS      current
            DESCRIPTION
                "Rule index."
            ::={ hwDIERuleEntry 1 }
				    
         hwDIERuleMacAddress OBJECT-TYPE
            SYNTAX MacAddress
            MAX-ACCESS read-create
            STATUS current
            DESCRIPTION
                "Mac address"
            ::={ hwDIERuleEntry 2 }	
            
         hwDIERuleMacMask OBJECT-TYPE
            SYNTAX      Integer32(0..48)
            MAX-ACCESS  read-create
            STATUS      current
            DESCRIPTION
                "Mac address mask."
            ::={ hwDIERuleEntry 3 }
				    
         hwDIERuleDhcpOptionID OBJECT-TYPE
            SYNTAX      Integer32(0..254)
            MAX-ACCESS  read-create
            STATUS      current
            DESCRIPTION
                "DHCP option id."
            ::={ hwDIERuleEntry 4 }
		
         hwDIERuleDhcpOptionType OBJECT-TYPE
            SYNTAX INTEGER
            {
                    invalid(0),
                    ascii(1),
                    hex(2)
            }
            MAX-ACCESS read-create
            STATUS current
            DESCRIPTION
                "The object means option type in DHCP option value
                The value means :
                ascii(1)- The option type is ascii string
                hex(2)  - The option type is hex number"
            ::= { hwDIERuleEntry 5 }
		    
         hwDIERuleDhcpOptionTextAscii OBJECT-TYPE
            SYNTAX DisplayString (SIZE (0..247))
            MAX-ACCESS read-create
            STATUS current
            DESCRIPTION
                "DHCP option content."
            ::= { hwDIERuleEntry 6 }
            
         hwDIERuleDhcpOptionTextHex OBJECT-TYPE
            SYNTAX DisplayString (SIZE (0..765))
            MAX-ACCESS read-create
            STATUS current
            DESCRIPTION
                "DHCP option content."
            ::= { hwDIERuleEntry 7 }	
            
         hwDIERuleDhcpOptionMatch OBJECT-TYPE
            SYNTAX INTEGER
                {
                    invalid(0),
                    subMatch(1),
                    allMatch(2)
                }
            MAX-ACCESS  read-create
            STATUS      current
            DESCRIPTION
                "DHCP option mask."
            ::={ hwDIERuleEntry 8 } 
				    
         hwDIERuleUserAgentText OBJECT-TYPE
            SYNTAX DisplayString (SIZE (0..247))
            MAX-ACCESS read-create
            STATUS current
            DESCRIPTION
                "User agent content."
            ::= { hwDIERuleEntry 9 }	
            
         hwDIERuleUserAgentMatch OBJECT-TYPE
            SYNTAX INTEGER
                {
                    invalid(0),
                    subMatch(1),
                    allMatch(2)
                }
            MAX-ACCESS  read-create
            STATUS      current
            DESCRIPTION
                "User agent mask."
            ::={ hwDIERuleEntry 10 }
            
         hwDIERuleRowStatus OBJECT-TYPE
            SYNTAX      RowStatus
            MAX-ACCESS  read-create
            STATUS      current
            DESCRIPTION
                "RowStatus."
            ::={ hwDIERuleEntry 11 } 	
			    				    
         hwDeviceSensorDhcpOption OBJECT-TYPE
            SYNTAX OCTET STRING (SIZE (0..32))
            MAX-ACCESS read-write
            STATUS current
            DESCRIPTION
               "Description."
            ::= { hwDIEMibObjects 3 }
				               
         hwDeviceSensorLLDPTlv OBJECT-TYPE                         
            SYNTAX OCTET STRING (SIZE (0..32))                     
            MAX-ACCESS read-write                                  
            STATUS current                                         
            DESCRIPTION                                            
                "Description."                                     
            ::= { hwDIEMibObjects 4 }    
            --  ============== conformance information ==============
        hwDIEConformance OBJECT IDENTIFIER ::= { hwDIEmib 3 }
        
        
        hwDIECompliances OBJECT IDENTIFIER ::= { hwDIEConformance 1 }
        hwDIECompliance MODULE-COMPLIANCE
               STATUS      current
               DESCRIPTION
                   "The compliance statement for systems supporting 
                this module."

               MODULE      -- this module
               MANDATORY-GROUPS    { hwDIEGroup, hwDIERuleGroup,hwDeviceSensorGroup}  
                                               
              ::= { hwDIECompliances 1 }
                                   
                --  ============== groups ==============  
        hwDIEObjectGroups OBJECT IDENTIFIER ::= { hwDIEConformance 2 } 
                                 
        hwDIEGroup OBJECT-GROUP
            OBJECTS {  hwDIEDeviceProfileIndex,hwDIEDeviceProfileName,
                       hwDIEDeviceProfileDevType,hwDIEDeviceProfileEnable,
                       hwDIEDeviceProfileRuleLogic,hwDIEDeviceProfileRowStatus }
            STATUS current       
            DESCRIPTION          
                "The DIE configuration."
            ::= { hwDIEObjectGroups 1 }

        hwDIERuleGroup OBJECT-GROUP
            OBJECTS {  hwDIERuleRuleIndex, hwDIERuleMacAddress, hwDIERuleMacMask,
                       hwDIERuleDhcpOptionID, hwDIERuleDhcpOptionType, hwDIERuleDhcpOptionTextAscii,
                       hwDIERuleDhcpOptionTextHex, hwDIERuleDhcpOptionMatch, hwDIERuleUserAgentText,
                       hwDIERuleUserAgentMatch, hwDIERuleRowStatus }
            STATUS current
            DESCRIPTION 
                "The DIE rule configuration."
            ::= { hwDIEObjectGroups 2 }
	hwDeviceSensorGroup OBJECT-GROUP
	   OBJECTS { hwDeviceSensorDhcpOption,hwDeviceSensorLLDPTlv }
	   STATUS current
           DESCRIPTION 
	        "The DIE sensor configuration."
	    ::= { hwDIEObjectGroups 3 }
         --  ============== conformance information define end ==============                         			    
    END

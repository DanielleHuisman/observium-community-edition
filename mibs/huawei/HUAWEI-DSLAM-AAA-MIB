-- =================================================================
-- Copyright (C) 2015 by  HUAWEI TECHNOLOGIES. All rights reserved.
-- Description:  The MIB file is for management of AAA module on DSLAM.
--               AAA, Authentication, Authorization and Accounting
--               is a network security mechanism, which provides a
--               framework for unified authentication, authorization
--               and accounting configurations.
-- Reference:  
-- Version:      V1.13
-- =================================================================

    HUAWEI-DSLAM-AAA-MIB DEFINITIONS ::= BEGIN

        IMPORTS
            huaweiMgmt
                FROM HUAWEI-MIB
            IpAddress, Unsigned32, Counter64, OBJECT-TYPE, MODULE-IDENTITY,
            NOTIFICATION-TYPE,Integer32
                FROM SNMPv2-SMI
            DisplayString, RowStatus, TruthValue, MacAddress, DateAndTime
                FROM SNMPv2-TC;

        hwDslamAaa MODULE-IDENTITY
            LAST-UPDATED "201511060000Z"
            ORGANIZATION "Huawei Technologies Co.,Ltd."
            CONTACT-INFO
                         "Huawei Industrial Base
                          Bantian, Longgang
                          Shenzhen 518129
                          People's Republic of China
                          Website: http://www.huawei.com
                          Email: support@huawei.com
                         "
            DESCRIPTION
                "The MIB file is for management of AAA module on DSLAM.
                 AAA, Authentication, Authorization and Accounting
                 is a network security mechanism, which provides a
                 framework for unified authentication, authorization
                 and accounting configurations.
                "

            -- Revision history
	        REVISION     "201511060000Z"
            DESCRIPTION  "V1.13, added the leaf node hwRadiusPrimaryAuthServerVpnName, hwRadiusSecondaryAuthServerVpnName1, 
			              hwRadiusPrimaryAcctServerVpnName, and hwRadiusSecondaryAcctServerVpnName1."
			
            REVISION     "201503190000Z"
            DESCRIPTION  "V1.12, modified the size list of hwRadiusServerKey node."
           
            REVISION     "201409090000Z"
            DESCRIPTION  "V1.11, modified the size list of hwRadiusServerKey node."

            REVISION     "201401180000Z"
            DESCRIPTION  "V1.10, modified the size list of hwRadiusServerKey node."
            
            REVISION     "201108160000Z"
            DESCRIPTION  "V1.09, modified the description and format."
            
            REVISION     "201107130000Z"
            DESCRIPTION  "V1.08, added leaf node hwRadiusSourceInterfaceIfType and hwRadiusSourceInterfaceIfNumber."
            
            REVISION     "201007210000Z"
            DESCRIPTION  "V1.07, modified the description and format."

            REVISION     "201006200900Z"
            DESCRIPTION  "V1.06, deleted the Chinese characters in this file."

            REVISION     "201001130900Z"
            DESCRIPTION  "V1.05, modified the description and format."

            REVISION     "200903070900Z"
            DESCRIPTION  "V1.01, changed the attitude of node hwRadiusGroupName as not-accessable.
                         Added notconfiged(6) enum to node hwAuthenMethod2,hwAuthenMethod3,
                         hwAuthenMethod4. "

            REVISION     "200901070900Z"
            DESCRIPTION  "V1.00, initial version."

            ::= { huaweiMgmt 109 }

        hwAAAMibObjects OBJECT IDENTIFIER ::= { hwDslamAaa 1 }

        hwAuthenSchemeTable OBJECT-TYPE
            SYNTAX SEQUENCE OF HwAuthenSchemeEntry
            MAX-ACCESS not-accessible
            STATUS current
            DESCRIPTION
                "Authentication scheme table. It is used to configure authentication scheme.
                 The index of this table is hwAuthenSchemeName."
            ::= { hwAAAMibObjects 1 }

        hwAuthenSchemeEntry OBJECT-TYPE
            SYNTAX HwAuthenSchemeEntry
            MAX-ACCESS not-accessible
            STATUS current
            DESCRIPTION
                "Authentication scheme table. It is used to configure authentication scheme.
                 The index of this entry is hwAuthenSchemeName.
                "
            INDEX { hwAuthenSchemeName }
            ::= { hwAuthenSchemeTable 1 }

        HwAuthenSchemeEntry ::=
            SEQUENCE {
                hwAuthenSchemeName
                    OCTET STRING,
                hwAuthenMethod1
                    INTEGER,
                hwAuthenRowStatus
                    RowStatus,
                hwAuthenFailPolicy
                    INTEGER,
                hwAuthenFailDomain
                    OCTET STRING,
                hwAuthenMethod2
                    INTEGER,
                hwAuthenMethod3
                    INTEGER,
                hwAuthenMethod4
                    INTEGER
             }

        hwAuthenSchemeName OBJECT-TYPE
            SYNTAX OCTET STRING (SIZE (1..32))
            MAX-ACCESS not-accessible
            STATUS current
            DESCRIPTION
                "The index of the hwAuthenSchemeTable.
                 This object indicates authentication scheme name."
            ::= { hwAuthenSchemeEntry 1 }

        hwAuthenMethod1 OBJECT-TYPE
            SYNTAX INTEGER
                {
                local(1),
                radius(2),
                tacacs(3)
                }
            MAX-ACCESS read-create
            STATUS current
            DESCRIPTION
                "The first priority of authentication mode.
                 Options:
                 1. local(1)  -Indicates that the system authenticates users through the local mode.
                 2. radius(2) -Indicates that the system authenticates users through the RADIUS protocol.
                 3. tacacs(3) -Indicates that the system authenticates users through the HWTACACS protocol.
                "
            ::= { hwAuthenSchemeEntry 2 }

        hwAuthenRowStatus OBJECT-TYPE
            SYNTAX RowStatus
            MAX-ACCESS read-create
            STATUS current
            DESCRIPTION
                "Row admin status, only support CreateAndGo(4),Destory(6),Active(1).
                 Options:
                 1. active(1)      -indicates query operation
                 2. createAndGo(4) -indicates creating operation
                 3. destroy(6)     -indicates deleting operation
                "
            ::= { hwAuthenSchemeEntry 3 }

        hwAuthenFailPolicy OBJECT-TYPE
            SYNTAX INTEGER
                {
                online(1),
                offline(2)
                }
            MAX-ACCESS read-create
            STATUS current
            DESCRIPTION
                "Authentication fail policy, it's not supported.
                 Options:
                 1. online(1)  -indicates that the user is online when the authorization fails.
                 2. offline(2) -indicates that the user is offline when the authorization fails.
                "
            ::= { hwAuthenSchemeEntry 4 }

        hwAuthenFailDomain OBJECT-TYPE
            SYNTAX OCTET STRING (SIZE (1..64))
            MAX-ACCESS read-create
            STATUS current
            DESCRIPTION
                "Authentication fail domain, it's not supported."
            ::= { hwAuthenSchemeEntry 5 }

        hwAuthenMethod2 OBJECT-TYPE
            SYNTAX INTEGER
                {
                local(1),
                radius(2),
                tacacs(3),
                none(4),
                notconfiged(6)
                }
            MAX-ACCESS read-create
            STATUS current
            DESCRIPTION
                "The second priority of authentication mode.
                 Options:
                 1. local(1)       -Indicates that the system authenticates users through the local mode.
                 2. radius(2)      -Indicates that the system authenticates users through the RADIUS protocol.
                 3. tacacs(3)      -Indicates that the system authenticates users through the HWTACACS protocol.
                 4. none(4)        -Indicates that authentication is not required.
                 5. notconfiged(6) -Indicates that authentication is not configured.
                "
            ::= { hwAuthenSchemeEntry 6 }

        hwAuthenMethod3 OBJECT-TYPE
            SYNTAX INTEGER
                {
                local(1),
                radius(2),
                tacacs(3),
                none(4),
                notconfiged(6)
                }
            MAX-ACCESS read-create
            STATUS current
            DESCRIPTION
                "The third priority of authentication mode.
                 Options:
                 1. local(1)       -Indicates that the system authenticates users through the local mode.
                 2. radius(2)      -Indicates that the system authenticates users through the RADIUS protocol.
                 3. tacacs(3)      -Indicates that the system authenticates users through the HWTACACS protocol.
                 4. none(4)        -Indicates that authentication is not required.
                 5. notconfiged(6) -Indicates that authentication is not configured.
                "
            ::= { hwAuthenSchemeEntry 7 }

            hwAuthenMethod4 OBJECT-TYPE
            SYNTAX INTEGER
                {
                local(1),
                radius(2),
                tacacs(3),
                none(4),
                notconfiged(6)
                }
            MAX-ACCESS read-create
            STATUS current
            DESCRIPTION
                "The fourth priority of authentication mode.
                 Options:
                 1. local(1)       -Indicates that the system authenticates users through the local mode.
                 2. radius(2)      -Indicates that the system authenticates users through the RADIUS protocol.
                 3. tacacs(3)      -Indicates that the system authenticates users through the HWTACACS protocol.
                 4. none(4)        -Indicates that authentication is not required.
                 5. notconfiged(6) -Indicates that authentication is not configured.
                "
            ::= { hwAuthenSchemeEntry 8 }

        hwAcctSchemeTable OBJECT-TYPE
            SYNTAX SEQUENCE OF HwAcctSchemeEntry
            MAX-ACCESS not-accessible
            STATUS current
            DESCRIPTION
                "Account scheme table.
                 The index of this table is hwAcctSchemeName.
                "
            ::= { hwAAAMibObjects 2 }

        hwAcctSchemeEntry OBJECT-TYPE
            SYNTAX HwAcctSchemeEntry
            MAX-ACCESS not-accessible
            STATUS current
            DESCRIPTION
                "Account scheme table.
                 The index of this entry is hwAcctSchemeName.
                "
            INDEX { hwAcctSchemeName }
            ::= { hwAcctSchemeTable 1 }

        HwAcctSchemeEntry ::=
            SEQUENCE {
                hwAcctSchemeName
                    OCTET STRING,
                hwAccMethod
                    INTEGER,
                hwAcctStartFail
                    INTEGER,
                hwAcctOnlineFail
                    INTEGER,
                hwAccRealTimeInter
                    Integer32,
                hwAcctRowStatus
                    RowStatus
             }

        hwAcctSchemeName OBJECT-TYPE
            SYNTAX OCTET STRING (SIZE (1..32))
            MAX-ACCESS not-accessible
            STATUS current
            DESCRIPTION
                "Account scheme name, The index of the hwAcctSchemeTable,
                 This object indicates accounting scheme name.
                "
            ::= { hwAcctSchemeEntry 1 }

        hwAccMethod OBJECT-TYPE
            SYNTAX INTEGER
                {
                noacct(2),
                radius(3),
                hwtacacs(5)
                }
            MAX-ACCESS read-create
            STATUS current
            DESCRIPTION
                "Accounting scheme mode.
                 Options:
                 1. noacct(2)   -Indicates that the accounting is not implemented. In such a case, accounting is not implemented for users.
                 2. radius(3)   -Uses the RADIUS protocol to implement the accounting for users.
                 3. hwtacacs(5) -Uses the HWTACACS protocol to implement the accounting for users.
                "
            ::= { hwAcctSchemeEntry 2 }

        hwAcctStartFail OBJECT-TYPE
            SYNTAX INTEGER
                {
                none(1),
                offline(2),
                radiusNone(3),
                radiusOfflline(4),
                localnone(5),
                localOffline(6)
                }
            MAX-ACCESS read-create
            STATUS current
            DESCRIPTION
                "The scheme would be used when accounting scheme starts failed.
                 Options:
                 1. none(1)            -ignoring the failure.
                 2. offline(2)         -forcing the user offline.
                 3. radiusNone(3)      -This value is not supported.
                 4. radiusOfflline(4)  -This value is not supported.
                 5. localnone(5)       -This value is not supported.
                 6. localOffline(6)    -This value is not supported.
                 It's not supported.
                "
            ::= { hwAcctSchemeEntry 3 }

        hwAcctOnlineFail OBJECT-TYPE
            SYNTAX INTEGER
                {
                none(1),
                offline(2),
                radiusNone(3),
                radiusOfflline(4),
                localnone(5),
                localOffline(6)
                }
            MAX-ACCESS read-create
            STATUS current
            DESCRIPTION
                "The scheme would be used when accounting realtime starts failed.
                 Options:
                 1. none(1)            -ignoring the failure.
                 2. offline(2)         -forcing the user offline.
                 3. radiusNone(3)      -This value is not supported.
                 4. radiusOfflline(4)  -This value is not supported.
                 5. localnone(5)       -This value is not supported.
                 6. localOffline(6)    -This value is not supported.
                 It's not supported.
                "
            ::= { hwAcctSchemeEntry 4 }

        hwAccRealTimeInter OBJECT-TYPE
            SYNTAX Integer32
            MAX-ACCESS read-create
            STATUS current
            DESCRIPTION
                "The interval of realtime account.
                "
            ::= { hwAcctSchemeEntry 5 }

        hwAcctRowStatus OBJECT-TYPE
            SYNTAX RowStatus
            MAX-ACCESS read-create
            STATUS current
            DESCRIPTION
                "Row admin status, only support CreateAndGo(4),Destory(6),Active(1).
                 Options:
                 1. active(1)      -indicates query operation.
                 2. createAndGo(4) -indicates creating operation.
                 3. destroy(6)     -indicates deleting operation.
                "
            ::= { hwAcctSchemeEntry 6 }

       hwDomainTable OBJECT-TYPE
            SYNTAX SEQUENCE OF HwDomainEntry
            MAX-ACCESS not-accessible
            STATUS current
            DESCRIPTION
                "It is used to configure the domain which belongs to users.
                 Base on a domain, every ISP can use different authentication-scheme,
                 accounting-scheme, and so on.
                 The index of this table is hwDomainName.
                "
            ::= { hwAAAMibObjects 4 }

        hwDomainEntry OBJECT-TYPE
            SYNTAX HwDomainEntry
            MAX-ACCESS not-accessible
            STATUS current
            DESCRIPTION
                "It is used to configure the domain which belongs to users.
                 Base on a domain, every ISP can use different authentication-scheme,
                 accounting-scheme, and so on.
                 The index of this entry is hwDomainName.
                "
            INDEX { hwDomainName }
            ::= { hwDomainTable 1 }

        HwDomainEntry ::=
            SEQUENCE {
                hwDomainName
                    OCTET STRING,
                hwDomainAuthenSchemeName
                    OCTET STRING,
                hwDomainAcctSchemeName
                    OCTET STRING,
                hwDomainRadiusGroupName
                    OCTET STRING,
                hwDomainRowStatus
                    RowStatus
                }

        hwDomainName OBJECT-TYPE
            SYNTAX OCTET STRING (SIZE (1..20))
            MAX-ACCESS not-accessible
            STATUS current
            DESCRIPTION
                "The index of the table, indicates the name of Domain.
                "
            ::= { hwDomainEntry 1 }

        hwDomainAuthenSchemeName OBJECT-TYPE
            SYNTAX OCTET STRING (SIZE (1..32))
            MAX-ACCESS read-create
            STATUS current
            DESCRIPTION
                "The name of authentication scheme.
                "
            ::= { hwDomainEntry 2 }

        hwDomainAcctSchemeName OBJECT-TYPE
            SYNTAX OCTET STRING (SIZE (1..32))
            MAX-ACCESS read-create
            STATUS current
            DESCRIPTION
                "The name of accounting Scheme.
                "
            ::= { hwDomainEntry 3 }

        hwDomainRadiusGroupName OBJECT-TYPE
            SYNTAX OCTET STRING (SIZE (0..32))
            MAX-ACCESS read-create
            STATUS current
            DESCRIPTION
                "Group name of hwRadiusGroupTable table.
                "
            ::= { hwDomainEntry 4 }

        hwDomainRowStatus OBJECT-TYPE
            SYNTAX RowStatus
            MAX-ACCESS read-create
            STATUS current
            DESCRIPTION
                "Row admin status, only support CreateAndGo(4),Destory(6),Active(1).
                 Options:
                 1. active(1)      -indicates query operation
                 2. createAndGo(4) -indicates creating operation
                 3. destroy(6)     -indicates deleting operation
                "
            ::= { hwDomainEntry 11 }

        hwDomainExtTable OBJECT-TYPE
            SYNTAX SEQUENCE OF HwDomainExtEntry
            MAX-ACCESS not-accessible
            STATUS current
            DESCRIPTION
                "The domain extend table which is an extended table of
                 hwDomainTable contains some new server properties haven't any standard.
                 The index of this table is hwDomainName.
                "
            ::= { hwAAAMibObjects 5 }

        hwDomainExtEntry OBJECT-TYPE
            SYNTAX HwDomainExtEntry
            MAX-ACCESS not-accessible
            STATUS current
            DESCRIPTION
                "The domain extend table which is an extended table of
                 hwDomainTable contains some new server properties haven't any standard.
                 The index of this entry is hwDomainName.
                "
            INDEX { hwDomainName }
            ::= { hwDomainExtTable 1 }

        HwDomainExtEntry ::=
            SEQUENCE {
                hwDot1xTemplate
                    Integer32,
                hwAdminUserPriority
                    Integer32
                }
        hwDot1xTemplate OBJECT-TYPE
            SYNTAX Integer32 (1..256)
            MAX-ACCESS read-write
            STATUS current
            DESCRIPTION
                "The 802.1x template of the domain, this node is not supported by MXU products.
                "
                 DEFVAL { 1 }
            ::= { hwDomainExtEntry 22 }

        hwAdminUserPriority OBJECT-TYPE
            SYNTAX Integer32 (-1..3)
            MAX-ACCESS read-write
            STATUS current
            DESCRIPTION
                "Priority of admin user, this node is not supported
                "
            ::= { hwDomainExtEntry 36 }

        hwDomainStatTable OBJECT-TYPE
            SYNTAX SEQUENCE OF HwDomainStatEntry
            MAX-ACCESS not-accessible
            STATUS current
            DESCRIPTION
                "Domain statistic table.
                 The index of this table is hwDomainName."
            ::= { hwAAAMibObjects 6 }

        hwDomainStatEntry OBJECT-TYPE
            SYNTAX HwDomainStatEntry
            MAX-ACCESS not-accessible
            STATUS current
            DESCRIPTION
                "Domain statistic table.
                 The index of this entry is hwDomainName.
                "
            INDEX { hwDomainName }
            ::= { hwDomainStatTable 1 }

            HwDomainStatEntry ::=
                SEQUENCE {
                    hwDomainAccessedNum
                        Integer32,
                    hwDomainOnlineNum
                        Integer32,
                    hwDomainOnlinePPPUser
                        Integer32,
                    hwDomainFlowDnByte
                        Counter64,
                    hwDomainFlowDnPkt
                        Counter64,
                    hwDomainFlowUpByte
                        Counter64,
                    hwDomainFlowUpPkt
                        Counter64,
                    hwDomainIPTotalNum
                        Integer32,
                    hwDomainIPUsedNum
                        Integer32,
                    hwDomainIPConflictNum
                        Integer32,
                    hwDomainIPExcludeNum
                        Integer32,
                    hwDomainIPIdleNum
                        Integer32
                    }

            hwDomainAccessedNum OBJECT-TYPE
                SYNTAX Integer32
                MAX-ACCESS read-only
                STATUS current
                DESCRIPTION
                    "Accessed Number"
                ::= { hwDomainStatEntry 1 }

            hwDomainOnlineNum OBJECT-TYPE
                SYNTAX Integer32
                MAX-ACCESS read-only
                STATUS current
                DESCRIPTION
                    "Online number"
                ::= { hwDomainStatEntry 2 }

            hwDomainOnlinePPPUser OBJECT-TYPE
                SYNTAX Integer32
                MAX-ACCESS read-only
                STATUS current
                DESCRIPTION
                    "Online PPP user number"
                ::= { hwDomainStatEntry 3 }

            hwDomainFlowDnByte OBJECT-TYPE
                SYNTAX Counter64
                MAX-ACCESS read-only
                STATUS current
                DESCRIPTION
                    "The byte number of a flow on down direction.
                    "
                ::= { hwDomainStatEntry 4 }

            hwDomainFlowDnPkt OBJECT-TYPE
                SYNTAX Counter64
                MAX-ACCESS read-only
                STATUS current
                DESCRIPTION
                    "The packet number of flow on down direction.
                    "
                ::= { hwDomainStatEntry 5 }

            hwDomainFlowUpByte OBJECT-TYPE
                SYNTAX Counter64
                MAX-ACCESS read-only
                STATUS current
                DESCRIPTION
                    "The byte number of flow on up direction.
                    "
                ::= { hwDomainStatEntry 6 }

            hwDomainFlowUpPkt OBJECT-TYPE
                SYNTAX Counter64
                MAX-ACCESS read-only
                STATUS current
                DESCRIPTION
                    "The packet number of flow on up direction.
                    "
                ::= { hwDomainStatEntry 7 }

            hwDomainIPTotalNum OBJECT-TYPE
                SYNTAX Integer32
                MAX-ACCESS read-only
                STATUS current
                DESCRIPTION
                    "Total IP addresses number configured in this domain.
                    "
                ::= { hwDomainStatEntry 8 }

            hwDomainIPUsedNum OBJECT-TYPE
                SYNTAX Integer32
                MAX-ACCESS read-only
                STATUS current
                DESCRIPTION
                    "Used IP addresses number.
                    "
                ::= { hwDomainStatEntry 9 }

            hwDomainIPConflictNum OBJECT-TYPE
                SYNTAX Integer32
                MAX-ACCESS read-only
                STATUS current
                DESCRIPTION
                    "Conflicted IP addresses number in this domain.
                    "
                ::= { hwDomainStatEntry 10 }

            hwDomainIPExcludeNum OBJECT-TYPE
                SYNTAX Integer32
                MAX-ACCESS read-only
                STATUS current
                DESCRIPTION
                    "Excluded IP addresses number in this domain.
                    "
                ::= { hwDomainStatEntry 11 }

            hwDomainIPIdleNum OBJECT-TYPE
                SYNTAX Integer32
                MAX-ACCESS read-only
                STATUS current
                DESCRIPTION
                    "Idle IP addresses number in this domain.
                    "
                ::= { hwDomainStatEntry 12 }

        hwRadiusGroupTable OBJECT-TYPE
            SYNTAX SEQUENCE OF HwRadiusGroupEntry
            MAX-ACCESS not-accessible
            STATUS current
            DESCRIPTION
                "The radius group table which contains some public information of
                 radius group is used to configure property of radius group.
                 The index of this table is hwRadiusGroupName.
                "
            ::= { hwAAAMibObjects 7 }

        hwRadiusGroupEntry OBJECT-TYPE
            SYNTAX HwRadiusGroupEntry
            MAX-ACCESS not-accessible
            STATUS current
            DESCRIPTION
                "The radius group table which contains some public information of
                 radius group is used to configure property of radius group.
                 The index of this entry is hwRadiusGroupName.
                "
            INDEX { hwRadiusGroupName }
            ::= { hwRadiusGroupTable 1 }

        HwRadiusGroupEntry ::=
            SEQUENCE {
                hwRadiusGroupName
                    OCTET STRING,
                hwRadiusServerKey
                    OCTET STRING,
                hwRadiusServerProtType
                    INTEGER,
                hwRadiusServerRetransmit
                    Integer32,
                hwRadiusServerTimeout
                    Integer32,
                hwRadiusGroupRowStatus
                    RowStatus
                }

        hwRadiusGroupName OBJECT-TYPE
            SYNTAX OCTET STRING (SIZE (1..32))
            MAX-ACCESS not-accessible
            STATUS current
            DESCRIPTION
                "The index of the table, indicates the name of radius group.
                "
            ::= { hwRadiusGroupEntry 1 }

        hwRadiusServerKey OBJECT-TYPE
            SYNTAX OCTET STRING (SIZE (0..128))
            MAX-ACCESS read-create
            STATUS current
            DESCRIPTION
                "The secret key shared between radius servers.
                "
            ::= { hwRadiusGroupEntry 2 }

        hwRadiusServerProtType OBJECT-TYPE
            SYNTAX INTEGER
                {
                radius(1),
                radiusPlus10(2),
                radiusPlus11(3)
                }
            MAX-ACCESS read-create
            STATUS current
            DESCRIPTION
                "This leaf node is not supported.
                 Options:
                 1. radius(1)        -indicates the standard RADIUS protocol
                 2. radiusPlus10(2)  -indicates the RADIUS+1.0 version
                 3. radiusPlus11(3)  -indicates the RADIUS+1.1 version
                "
            ::= { hwRadiusGroupEntry 4 }

        hwRadiusServerRetransmit OBJECT-TYPE
            SYNTAX Integer32
            MAX-ACCESS read-create
            STATUS current
            DESCRIPTION
                "The max number of radius packet retransmit.
                "
            ::= { hwRadiusGroupEntry 5 }

        hwRadiusServerTimeout OBJECT-TYPE
            SYNTAX Integer32
            MAX-ACCESS read-create
            STATUS current
            DESCRIPTION
                "Radius packet retransmit interval
                "
            ::= { hwRadiusGroupEntry 6 }

        hwRadiusGroupRowStatus OBJECT-TYPE
            SYNTAX RowStatus
            MAX-ACCESS read-create
            STATUS current
            DESCRIPTION
                "Row admin status, only support CreateAndGo(4),Destory(6),Active(1).
                 Options:
                 1. active(1)      -indicates query operation
                 2. createAndGo(4) -indicates creating operation
                 3. destroy(6)     -indicates deleting operation
                "
            ::= { hwRadiusGroupEntry 7 }

        hwLocalUserTable OBJECT-TYPE
            SYNTAX SEQUENCE OF HwLocalUserEntry
            MAX-ACCESS not-accessible
            STATUS current
            DESCRIPTION
                "Local user table. This table is used to configure local user information.
                 The index of this table is hwLocalUserName.
                "
            ::= { hwAAAMibObjects 10 }

        hwLocalUserEntry OBJECT-TYPE
            SYNTAX HwLocalUserEntry
            MAX-ACCESS not-accessible
            STATUS current
            DESCRIPTION
                "Local user table. This table is used to configure local user information.
                 The index of this entry is hwLocalUserName.
                "
            INDEX { hwLocalUserName }
            ::= { hwLocalUserTable 1 }

        HwLocalUserEntry ::=
            SEQUENCE {
                hwLocalUserName
                    OCTET STRING,
                hwLocalUserPassword
                    OCTET STRING,
                hwLocalUserAccessType
                    Integer32,
                hwLocalUserPriority
                    Integer32,
                hwftpdirction
                    OCTET STRING,
                hwLocalUserRowStatus
                    RowStatus
                }

        hwLocalUserName OBJECT-TYPE
            SYNTAX OCTET STRING (SIZE (1..65))
            MAX-ACCESS not-accessible
            STATUS current
            DESCRIPTION
                "Local user name
                "
            ::= { hwLocalUserEntry 1 }

        hwLocalUserPassword OBJECT-TYPE
            SYNTAX OCTET STRING (SIZE (0..16))
            MAX-ACCESS read-create
            STATUS current
            DESCRIPTION
                "local user's password
                "
            ::= { hwLocalUserEntry 2 }

        hwLocalUserAccessType OBJECT-TYPE
            SYNTAX Integer32
            MAX-ACCESS read-create
            STATUS current
            DESCRIPTION
                "Local user's type.
                "
            ::= { hwLocalUserEntry 3 }

        hwLocalUserPriority OBJECT-TYPE
            SYNTAX Integer32 (0..4)
            MAX-ACCESS read-create
            STATUS current
            DESCRIPTION
                "Local user's priority.
                "
            ::= { hwLocalUserEntry 4 }

        hwftpdirction OBJECT-TYPE
            SYNTAX OCTET STRING (SIZE (1..64))
            MAX-ACCESS read-create
            STATUS current
            DESCRIPTION
                "ftp directory.
                "
            ::= { hwLocalUserEntry 5 }

        hwLocalUserRowStatus OBJECT-TYPE
            SYNTAX RowStatus
            MAX-ACCESS read-create
            STATUS current
            DESCRIPTION
                "Row admin status, only support CreateAndGo(4),Destory(6),Active(1).
                 Options:
                 1. active(1)      -indicates query operation
                 2. createAndGo(4) -indicates creating operation
                 3. destroy(6)     -indicates deleting operation
                "
            ::= { hwLocalUserEntry 12 }

         hwAccessTable OBJECT-TYPE
            SYNTAX SEQUENCE OF HwAccessEntry
            MAX-ACCESS not-accessible
            STATUS current
            DESCRIPTION
                "Access user table.
                 The access table is used to query the property of online users.
                 Notice: Read operation is not allowed for all the items in this table.
                 1. The index of hwAccessTable also uses hwAccessIndex, get operation only
                    supports the standard get operation with hwAccessIndex as its index.
                 2. To prevent too much interaction, getnext operation does use the standard operation that uses hwAccessIndex as its index.
                 The index of this table is hwAccessIndex.
                "
            ::= { hwAAAMibObjects 15 }

        hwAccessEntry OBJECT-TYPE
            SYNTAX HwAccessEntry
            MAX-ACCESS not-accessible
            STATUS current
            DESCRIPTION
                "Access user table.
                 The access table is used to query the property of online users.
                 Notice: Read operation is not allowed for all the items in this table.
                 1. The index of hwAccessTable also uses hwAccessIndex, get operation only
                    supports the standard get operation with hwAccessIndex as its index.
                 2. To prevent too much interaction, getnext operation does use the standard operation that uses hwAccessIndex as its index.
                 The index of this entry is hwAccessIndex.
                "
            INDEX { hwAccessIndex }
            ::= { hwAccessTable 1 }

        HwAccessEntry ::=
            SEQUENCE {
                hwAccessIndex
                    Integer32,
                hwAccessUserName
                    OCTET STRING,
                hwAccessPortType
                    INTEGER,
                hwAccessPriority
                    Integer32,
                hwAccessSlotNo
                    Integer32,
                hwAccessSubSlotNo
                    Integer32,
                hwAccessPortNo
                    Integer32,
                hwAccessVLANID
                    Integer32,
                hwAccessPVC
                    Integer32,
                hwAccessAuthenMethod
                    INTEGER,
                hwAccessAcctMethod
                    INTEGER,
                hwAccessIPAddress
                    IpAddress,
                hwAccessMACAddress
                    MacAddress,
                hwAccessIfIdleCut
                    TruthValue,
                hwAccessIdleCutTime
                    Integer32,
                hwAccessIdleCutFlow
                    Integer32,
                hwAccessTimeLimit
                    Integer32,
                hwAccessTotalFlow64Limit
                    Counter64,
                hwAccessStartTime
                    DateAndTime,
                hwAccessCARIfUpActive
                    TruthValue,
                hwAccessCARUpPeakRate
                    Unsigned32,
                hwAccessCARUpAverageRate
                    Unsigned32,
                hwAccessCARIfDnActive
                    TruthValue,
                hwAccessCARDnPeakRate
                    Unsigned32,
                hwAccessCARDnAverageRate
                    Unsigned32,
                hwAccessUpFlow64
                    Counter64,
                hwAccessDnFlow64
                    Counter64,
                hwAccessUpPacket64
                    Counter64,
                hwAccessDnPacket64
                    Counter64
                }

        hwAccessIndex OBJECT-TYPE
            SYNTAX Integer32 (0..65535)
            MAX-ACCESS not-accessible
            STATUS current
            DESCRIPTION
                "unqualified index
                "
            ::= { hwAccessEntry 1 }

        hwAccessUserName OBJECT-TYPE
            SYNTAX OCTET STRING (SIZE (1..129))
            MAX-ACCESS read-only
            STATUS current
            DESCRIPTION
                "access user name"
            ::= { hwAccessEntry 3 }

        hwAccessPortType OBJECT-TYPE
            SYNTAX INTEGER
                {
                all(1),
                ppp(2),
                vlan(3),
                vlanweb(4),
                vlanportal(5),
                vlan8021x(6),
                telnet(7),
                ftp(8),
                ssh(9),
                igmp(10)
                }
            MAX-ACCESS read-only
            STATUS current
            DESCRIPTION
                "access port type
                 Options:
                 1. all(1)        -all access types allowed
                 2. ppp(2)        -PPP access
                 3. vlan(3)       -This value is not supported
                 4. vlanweb(4)    -Web access
                 5. vlanportal(5) -This value is not supported
                 6. vlan8021x(6)  -802.1X access
                 7. telnet(7)     -Telnet access
                 8. ftp(8)        -FTP access
                 9. ssh(9)        -SSH access
                 10.igmp(10)      -IGMP access
                "
            ::= { hwAccessEntry 5 }

        hwAccessPriority OBJECT-TYPE
            SYNTAX Integer32 (0..15|255)
            MAX-ACCESS read-only
            STATUS current
            DESCRIPTION
                "access pri
                "
            ::= { hwAccessEntry 6 }

        hwAccessSlotNo OBJECT-TYPE
            SYNTAX Integer32
            MAX-ACCESS read-only
            STATUS current
            DESCRIPTION
                "slot No
                "
            ::= { hwAccessEntry 8 }

        hwAccessSubSlotNo OBJECT-TYPE
            SYNTAX Integer32
            MAX-ACCESS read-only
            STATUS current
            DESCRIPTION
                "subslot No
                "
            ::= { hwAccessEntry 9 }

        hwAccessPortNo OBJECT-TYPE
            SYNTAX Integer32
            MAX-ACCESS read-only
            STATUS current
            DESCRIPTION
                "port No
                "
            ::= { hwAccessEntry 10 }

        hwAccessVLANID OBJECT-TYPE
            SYNTAX Integer32
            MAX-ACCESS read-only
            STATUS current
            DESCRIPTION
                "vlanid
                "
            ::= { hwAccessEntry 11 }

        hwAccessPVC OBJECT-TYPE
            SYNTAX Integer32
            MAX-ACCESS read-only
            STATUS current
            DESCRIPTION
                "vpi vpc
                "
            ::= { hwAccessEntry 12 }

        hwAccessAuthenMethod OBJECT-TYPE
            SYNTAX INTEGER
                {
                local(1),
                noauth(2),
                radius(3),
                localRadius(4),
                radiusLocal(5),
                radiusNoauth(6)
                }
            MAX-ACCESS read-only
            STATUS current
            DESCRIPTION
                "Authentication method.
                 Options:
                 1. local(1)        -local authentication
                 2. noauth(2)       -none authentication
                 3. radius(3)       -RADIUS authentication (default)
                 4. localRadius(4)  -local authentication, and then RADIUS authentication if local authentication fails
                 5. radiusLocal(5)  -RADIUS authentication, and then local authentication if RADIUS authentication fails
                 6. radiusNoauth(6) -RADIUS authentication, and then no authentication if RADIUS authentication fails
                "
            ::= { hwAccessEntry 13 }

        hwAccessAcctMethod OBJECT-TYPE
            SYNTAX INTEGER
                {
                local(1),
                radius(2),
                none(3),
                both(4)
                }
            MAX-ACCESS read-only
            STATUS current
            DESCRIPTION
                "Account method.
                 Options:
                 1. local(1)       -local accounting
                 2. radius(2)      -RADIUS accounting
                 3. none(3)        -no accounting
                 4. both(4)        -local and RADIUS accounting
                "
            ::= { hwAccessEntry 14 }

        hwAccessIPAddress OBJECT-TYPE
            SYNTAX IpAddress
            MAX-ACCESS read-only
            STATUS current
            DESCRIPTION
                "IP address.
                "
            ::= { hwAccessEntry 15 }

        hwAccessMACAddress OBJECT-TYPE
            SYNTAX MacAddress
            MAX-ACCESS read-only
            STATUS current
            DESCRIPTION
                "The MAC address of access user.
                "
            ::= { hwAccessEntry 17 }

        hwAccessIfIdleCut OBJECT-TYPE
            SYNTAX TruthValue
            MAX-ACCESS read-only
            STATUS current
            DESCRIPTION
                "if idle cut.
                "
            ::= { hwAccessEntry 18 }

        hwAccessIdleCutTime OBJECT-TYPE
            SYNTAX Integer32
            MAX-ACCESS read-only
            STATUS current
            DESCRIPTION
                "idle cut time.
                "
            ::= { hwAccessEntry 19 }

        hwAccessIdleCutFlow OBJECT-TYPE
            SYNTAX Integer32
            MAX-ACCESS read-only
            STATUS current
            DESCRIPTION
                "idle cut flow.
                "
            ::= { hwAccessEntry 20 }

        hwAccessTimeLimit OBJECT-TYPE
            SYNTAX Integer32
            MAX-ACCESS read-only
            STATUS current
            DESCRIPTION
                "session time
                "
            ::= { hwAccessEntry 21 }

        hwAccessTotalFlow64Limit OBJECT-TYPE
            SYNTAX Counter64
            MAX-ACCESS read-only
            STATUS current
            DESCRIPTION
                "remain flow(64bit)
                "
            ::= { hwAccessEntry 22 }

        hwAccessStartTime OBJECT-TYPE
            SYNTAX DateAndTime
            MAX-ACCESS read-only
            STATUS current
            DESCRIPTION
                "start time
                "
            ::= { hwAccessEntry 25 }

        hwAccessCARIfUpActive OBJECT-TYPE
            SYNTAX TruthValue
            MAX-ACCESS read-only
            STATUS current
            DESCRIPTION
                "up flow's control
                "
            ::= { hwAccessEntry 27 }

        hwAccessCARUpPeakRate OBJECT-TYPE
            SYNTAX Unsigned32 (64..1048576|4294967295)
            MAX-ACCESS read-only
            STATUS current
            DESCRIPTION
                "up peek rate(Kbps)
                "
            ::= { hwAccessEntry 28 }

        hwAccessCARUpAverageRate OBJECT-TYPE
            SYNTAX Unsigned32 (64..1048576|4294967295)
            MAX-ACCESS read-only
            STATUS current
            DESCRIPTION
                "up average rate(Kbps)
                "
            ::= { hwAccessEntry 29 }

        hwAccessCARIfDnActive OBJECT-TYPE
            SYNTAX TruthValue
            MAX-ACCESS read-only
            STATUS current
            DESCRIPTION
                "down flow's control
                "
            ::= { hwAccessEntry 31 }

        hwAccessCARDnPeakRate OBJECT-TYPE
            SYNTAX Unsigned32 (64..1048576|4294967295)
            MAX-ACCESS read-only
            STATUS current
            DESCRIPTION
                "down peek rate(Kbps)
                "
            ::= { hwAccessEntry 32 }

        hwAccessCARDnAverageRate OBJECT-TYPE
            SYNTAX Unsigned32 (64..1048576|4294967295)
            MAX-ACCESS read-only
            STATUS current
            DESCRIPTION
                "down average rate(Kbps)
                "
            ::= { hwAccessEntry 33 }

        hwAccessUpFlow64 OBJECT-TYPE
            SYNTAX Counter64
            MAX-ACCESS read-only
            STATUS current
            DESCRIPTION
                "up flow(64Byte)
                "
            ::= { hwAccessEntry 36 }

        hwAccessDnFlow64 OBJECT-TYPE
            SYNTAX Counter64
            MAX-ACCESS read-only
            STATUS current
            DESCRIPTION
                "down flow(64Byte)
                "
            ::= { hwAccessEntry 37 }

        hwAccessUpPacket64 OBJECT-TYPE
            SYNTAX Counter64
            MAX-ACCESS read-only
            STATUS current
            DESCRIPTION
                "up packet
                "
            ::= { hwAccessEntry 38 }

        hwAccessDnPacket64 OBJECT-TYPE
            SYNTAX Counter64
            MAX-ACCESS read-only
            STATUS current
            DESCRIPTION
                "down packet
                "
            ::= { hwAccessEntry 39 }

        hwAccessExtTable OBJECT-TYPE
            SYNTAX SEQUENCE OF HwAccessExtEntry
            MAX-ACCESS not-accessible
            STATUS current
            DESCRIPTION
                "Access user extended table.
                 The index of this table is hwAccessIndex.
                "
            ::= { hwAAAMibObjects 16 }

        hwAccessExtEntry OBJECT-TYPE
            SYNTAX HwAccessExtEntry
            MAX-ACCESS not-accessible
            STATUS current
            DESCRIPTION
                "Access user extended table.
                 The index of this entry is hwAccessIndex.
                "
            INDEX { hwAccessIndex }
            ::= { hwAccessExtTable 1 }

            HwAccessExtEntry ::=
                SEQUENCE {
                    hwAuthenticationState
                        Integer32,
                    hwAccountingState
                        Integer32,
                    hwAccessDomainName
                        OCTET STRING,
                    hwIdleTimeLength
                        Integer32,
                    hwAcctSessionID
                        OCTET STRING,
                    hwAccessStartAcctTime
                        DateAndTime,
                    hwAccessNormalServerGroup
                        OCTET STRING,
                    hwAccessDomainAcctCopySeverGroup
                        OCTET STRING,
                    hwAccessPVlanAcctCopyServerGroup
                        OCTET STRING,
                    hwAccessCurAuthenPlace
                        INTEGER,
                    hwAccessActionFlag
                        INTEGER,
                    hwAccessAuthtype
                        INTEGER,
                    hwAccessType
                        INTEGER
                    }

            hwAuthenticationState OBJECT-TYPE
                SYNTAX Integer32 (1..4)
                MAX-ACCESS read-only
                STATUS current
                DESCRIPTION
                    "Authentication state machine state"
                ::= { hwAccessExtEntry 4 }

            hwAccountingState OBJECT-TYPE
                SYNTAX Integer32 (1..7)
                MAX-ACCESS read-only
                STATUS current
                DESCRIPTION
                    "accounting state machine state"
                ::= { hwAccessExtEntry 6 }

            hwAccessDomainName OBJECT-TYPE
                SYNTAX OCTET STRING (SIZE (1..64))
                MAX-ACCESS read-only
                STATUS current
                DESCRIPTION
                    "the domain of the access"
                ::= { hwAccessExtEntry 7 }

            hwIdleTimeLength OBJECT-TYPE
                SYNTAX Integer32 (0..120)
                MAX-ACCESS read-only
                STATUS current
                DESCRIPTION
                    "idle-cut time"
                ::= { hwAccessExtEntry 8 }

            hwAcctSessionID OBJECT-TYPE
                SYNTAX OCTET STRING (SIZE (0..44))
                MAX-ACCESS read-only
                STATUS current
                DESCRIPTION
                    "AcctSessionID"
                ::= { hwAccessExtEntry 9 }

            hwAccessStartAcctTime OBJECT-TYPE
                SYNTAX DateAndTime
                MAX-ACCESS read-only
                STATUS current
                DESCRIPTION
                    "StartAcctTime"
                ::= { hwAccessExtEntry 10 }

            hwAccessNormalServerGroup OBJECT-TYPE
                SYNTAX OCTET STRING (SIZE (1..32))
                MAX-ACCESS read-only
                STATUS current
                DESCRIPTION
                    "AccessNormalServerGroup
                    "
                ::= { hwAccessExtEntry 11 }

            hwAccessDomainAcctCopySeverGroup OBJECT-TYPE
                SYNTAX OCTET STRING (SIZE (1..32))
                MAX-ACCESS read-only
                STATUS current
                DESCRIPTION
                    "AccessNormalServerGroup"
                ::= { hwAccessExtEntry 12 }

            hwAccessPVlanAcctCopyServerGroup OBJECT-TYPE
                SYNTAX OCTET STRING (SIZE (1..32))
                MAX-ACCESS read-only
                STATUS current
                DESCRIPTION
                    "AccessNormalServerGroup"
                ::= { hwAccessExtEntry 13 }

            hwAccessCurAuthenPlace OBJECT-TYPE
                SYNTAX INTEGER
                    {
                    none(0),
                    local(1),
                    remote(2)
                    }
                MAX-ACCESS read-only
                STATUS current
                DESCRIPTION
                    "AccessCurAuthenPlace.
                     Options:
                     1. none(0)        -none authentication
                     2. local(1)       -local authentication
                     3. remote(2)      -remote authentication
                    "
                ::= { hwAccessExtEntry 14 }

            hwAccessActionFlag OBJECT-TYPE
                SYNTAX INTEGER
                    {
                    idle(0),
                    newuserauth(1),
                    reauth(2),
                    login(3),
                    logout(4),
                    authmodify(5),
                    offline(6)
                    }
                MAX-ACCESS read-only
                STATUS current
                DESCRIPTION
                    "AccessActionFlag.
                     Options:
                     1. idle(0)        -idle
                     2. newuserauth(1) -new user authentication
                     3. reauth(2)      -reauthentication
                     4. login(3)       -login
                     5. logout(4)      -logout
                     6. authmodify(5)  -authorization modify
                     7. offline(6)     -user leaving
                    "
                ::= { hwAccessExtEntry 15 }

            hwAccessAuthtype OBJECT-TYPE
                SYNTAX INTEGER
                    {
                    none(0),
                    ppp(1),
                    dot1x(2),
                    web(3),
                    bind(4),
                    fast(5),
                    wlan(6),
                    admin(7)
                    }
                MAX-ACCESS read-only
                STATUS current
                DESCRIPTION
                    "Access user type.
                    Options:
                    1. none(0)         -all access types
                    2. ppp(1)          -PPP access
                    3. dot1x(2)        -802.1X access
                    4. web(3)          -Web access
                    5. bind(4)         -binding access
                    6. fast(5)         -fast access
                    7. wlan(6)         -wlan access
                    8. admin(7)        -admin access
                    "
                ::= { hwAccessExtEntry 16 }

            hwAccessType OBJECT-TYPE
                SYNTAX INTEGER
                    {
                    telnet(1),
                    terminal(2),
                    ssh(3),
                    ftp(4),
                    x25pad(5),
                    ppp(6),
                    pppoe(7),
                    pppoeovlan(8),
                    pppoa(9),
                    pppoeoa(10),
                    --NYLD2869
                    pppolns(11),
                    ordinaryvlan(12),
                    eap(13),
                    pnp(14),
                    ip(15),
                    staticvlan(16),
                    layer2leasedline(17),
                    layer2leasedlineuser(18),
                    layer3leasedline(19),
                    pppoeleasedline(20),
                    nmsleasedline(21),
                    proxyleasedline(22),
                    relayleasedline(23),
                    e1pos(24)
                    --NYLD2869
                    }
                MAX-ACCESS read-only
                STATUS current
                DESCRIPTION
                    "Access user type.
                     Options:
                     1.  telnet(1)                 -Telnet access
                     2.  terminal(2)               -terminal access
                     3.  ssh(3)                    -SSH access
                     4.  ftp(4)                    -FTP access
                     5.  x25pad(5)                 -x25-PAD access
                     6.  ppp(6)                    -PPP access
                     7.  pppoe(7)                  -PPPOE access
                     8.  pppoeovlan(8)             -pppoeovlan access     
                     9.  pppoa(9)                  -pppoa access
                     10. pppoeoa(10)               -pppoeoa access
                     11. pppolns(11)               -pppolns access
                     12. ordinaryvlan(12)          -ordinary vlanaccess
                     13. eap(13)                   -eap access
                     14. pnp(14)                   -pnp access
                     15. ip(15)                    -ip access
                     16. staticvlan(16)            -staticvlan access
                     17. layer2leasedline(17)      -layer2leasedline access
                     18. layer2leasedlineuser(18)  -layer2leasedlineuser access
                     19. layer3leasedline(19)      -layer3leasedline access
                     20. pppoeleasedline(20)       -pppoeleasedline access
                     21. nmsleasedline(21)         -nmsleasedline( access
                     22. proxyleasedline(22)       -proxyleasedline access
                     23. relayleasedline(23)       -relayleasedline access
                     24. e1pos(24)                 -e1pos access
                    "
                ::= { hwAccessExtEntry 17 }

         hwAcctSchemeExtTable OBJECT-TYPE
            SYNTAX SEQUENCE OF HwAcctSchemeExtEntry
            MAX-ACCESS not-accessible
            STATUS current
            DESCRIPTION
                "Access scheme extend table.
                 The index of this table is hwAcctSchemeName.
                "
            ::= { hwAAAMibObjects 19 }

        hwAcctSchemeExtEntry OBJECT-TYPE
            SYNTAX HwAcctSchemeExtEntry
            MAX-ACCESS not-accessible
            STATUS current
            DESCRIPTION
                "Access scheme extend table.
                 The index of this entry is hwAcctSchemeName.
                "
            INDEX { hwAcctSchemeName }
            ::= { hwAcctSchemeExtTable 1 }

        HwAcctSchemeExtEntry ::=
            SEQUENCE {
            hwIfRealtimeAcct
                TruthValue,
            hwRealtimeFailMaxnum
                Integer32
            }

        hwIfRealtimeAcct OBJECT-TYPE
            SYNTAX TruthValue
            MAX-ACCESS read-write
            STATUS current
            DESCRIPTION
            "if need realtime account"
            DEFVAL { yes }
            ::= { hwAcctSchemeExtEntry 1 }

        hwRealtimeFailMaxnum OBJECT-TYPE
            SYNTAX Integer32 (1..255)
            MAX-ACCESS read-write
            STATUS current
            DESCRIPTION
                "The permit time of realtime account failure"
            DEFVAL { 3 }
            ::= { hwAcctSchemeExtEntry 2 }

        hwRadiusGroupExtTable OBJECT-TYPE
            SYNTAX SEQUENCE OF HwRadiusGroupExtEntry
            MAX-ACCESS not-accessible
            STATUS current
            DESCRIPTION
                "The radius group configure table which is an extended table of
                 hwRadiusGroupTable is used to configure some extended parameters on radius group.
                 The index of this table is hwRadiusGroupName.
                "
            ::= { hwAAAMibObjects 20 }

        hwRadiusGroupExtEntry OBJECT-TYPE
            SYNTAX HwRadiusGroupExtEntry
            MAX-ACCESS not-accessible
            STATUS current
            DESCRIPTION
                "The radius group configure table which is an extended table of
                 hwRadiusGroupTable is used to configure some extended parameters on radius group.
                 The index of this entry is hwRadiusGroupName.
                "
            INDEX { hwRadiusGroupName }
            ::= { hwRadiusGroupExtTable 1 }

        HwRadiusGroupExtEntry ::=
            SEQUENCE {
                hwRadiusPrimaryAuthServerIP
                    IpAddress,
                hwRadiusPrimaryAuthServerPort
                    Integer32,
                hwRadiusSecondaryAuthServerIP1
                    IpAddress,
                hwRadiusSecondaryAuthServerPort1
                    Integer32,
                hwRadiusPrimaryAcctServerIP
                    IpAddress,
                hwRadiusPrimaryAcctServerPort
                    Integer32,
                hwRadiusSecondaryAcctServerIP1
                    IpAddress,
                hwRadiusSecondaryAcctServerPort1
                    Integer32,
                hwRadiusPacketUnit
                    INTEGER,
                hwRadiusDomainInclude
                    INTEGER,  
                hwRadiusPrimaryAuthServerVpnName
                    OCTET STRING,
                hwRadiusSecondaryAuthServerVpnName1
                    OCTET STRING,  
                hwRadiusPrimaryAcctServerVpnName
                    OCTET STRING,
                hwRadiusSecondaryAcctServerVpnName1
                    OCTET STRING
                }

        hwRadiusPrimaryAuthServerIP OBJECT-TYPE
            SYNTAX IpAddress
            MAX-ACCESS read-write
            STATUS current
            DESCRIPTION
                "The ip address of primary radius authentication server.
                "
            ::= { hwRadiusGroupExtEntry 1 }

        hwRadiusPrimaryAuthServerPort OBJECT-TYPE
            SYNTAX Integer32 (0..65535)
            MAX-ACCESS read-write
            STATUS current
            DESCRIPTION
                "The UDP port of primary radius authentication server.
                "
            ::= { hwRadiusGroupExtEntry 2 }

        hwRadiusSecondaryAuthServerIP1 OBJECT-TYPE
            SYNTAX IpAddress
            MAX-ACCESS read-write
            STATUS current
            DESCRIPTION
                "The ip address of secondary radius authentication server.
                "
            ::= { hwRadiusGroupExtEntry 3 }

        hwRadiusSecondaryAuthServerPort1 OBJECT-TYPE
            SYNTAX Integer32 (0..65535)
            MAX-ACCESS read-write
            STATUS current
            DESCRIPTION
                "The UDP port of secondary radius authentication server.
                "
            ::= { hwRadiusGroupExtEntry 4 }

        hwRadiusPrimaryAcctServerIP OBJECT-TYPE
            SYNTAX IpAddress
            MAX-ACCESS read-write
            STATUS current
            DESCRIPTION
                "The ip address of primary radius accounting server.
                "
            ::= { hwRadiusGroupExtEntry 17 }

        hwRadiusPrimaryAcctServerPort OBJECT-TYPE
            SYNTAX Integer32 (0..65535)
            MAX-ACCESS read-write
            STATUS current
            DESCRIPTION
                "The UDP port of primary radius accounting server.
                "
            DEFVAL { 1813 }
            ::= { hwRadiusGroupExtEntry 18 }

        hwRadiusSecondaryAcctServerIP1 OBJECT-TYPE
            SYNTAX IpAddress
            MAX-ACCESS read-write
            STATUS current
            DESCRIPTION
                "The ip address of secondary radius accounting server.
                "
            ::= { hwRadiusGroupExtEntry 19 }

        hwRadiusSecondaryAcctServerPort1 OBJECT-TYPE
            SYNTAX Integer32 (0..65535)
            MAX-ACCESS read-write
            STATUS current
            DESCRIPTION
                "The UDP port of secondary radius accounting server.
                "
            ::= { hwRadiusGroupExtEntry 20 }

        hwRadiusPacketUnit OBJECT-TYPE
            SYNTAX INTEGER
                {
                byte(1),
                kbyte(2),
                mbyte(3),
                gbyte(4)
                }
            MAX-ACCESS read-write
            STATUS current
            DESCRIPTION
                "The data unit of the flow info in the radius accounting packet.
                 Options:
                 1. byte(1)  -Indicates the byte as the traffic unit.
                 2. kbyte(2) -Indicates the kbyte as the traffic unit.
                 3. mbyte(3) -Indicates the megabyte as the traffic unit.
                 4. gbyte(4) -Indicates the Gbyte as the traffic unit.
                "
            DEFVAL { byte }
            ::= { hwRadiusGroupExtEntry 35 }

        hwRadiusDomainInclude OBJECT-TYPE
            SYNTAX INTEGER
                {
                includingdomain(1),
                notincludingdomain(2),
                original(3)
                }
            MAX-ACCESS read-write
            STATUS current
            DESCRIPTION
                "User name format in the radius packet.
                 Options:
                 1. includingdomain(1)    -Indicates that a user name contains a domain name.
                 2. notincludingdomain(2) -Indicates that a user name doesn't contain a domain name.
                 3. original(3)           -Indicates that a user name uses the original domain name.
                "
            DEFVAL { includingdomain }
            ::= { hwRadiusGroupExtEntry 36 }

        hwRadiusPrimaryAuthServerVpnName OBJECT-TYPE
            SYNTAX OCTET STRING(SIZE (0..31))
            MAX-ACCESS read-write
            STATUS current
            DESCRIPTION
                "VPN-instance of primary radius authentication server.
                "
            ::= { hwRadiusGroupExtEntry 41 } 
            
        hwRadiusSecondaryAuthServerVpnName1 OBJECT-TYPE
            SYNTAX OCTET STRING(SIZE (0..31))
            MAX-ACCESS read-write
            STATUS current
            DESCRIPTION
                "VPN-instance of secondary radius authentication server.
                "
            ::= { hwRadiusGroupExtEntry 42 } 
            
        hwRadiusPrimaryAcctServerVpnName OBJECT-TYPE
            SYNTAX OCTET STRING(SIZE (0..31))
            MAX-ACCESS read-write
            STATUS current
            DESCRIPTION
                "VPN-instance of primary radius accounting server.
                "
            ::= { hwRadiusGroupExtEntry 43 }     
            
        hwRadiusSecondaryAcctServerVpnName1 OBJECT-TYPE
            SYNTAX OCTET STRING(SIZE (0..31))
            MAX-ACCESS read-write
            STATUS current
            DESCRIPTION
                "VPN-instance of secondary radius accounting server.
                "
            ::= { hwRadiusGroupExtEntry 44 }
        
        hwAAAStatExtTable OBJECT IDENTIFIER ::= { hwAAAMibObjects 32}

        hwAAAStatExtEntry OBJECT IDENTIFIER ::= { hwAAAStatExtTable 1 }

        hwDomainNum OBJECT-TYPE
            SYNTAX Integer32 (0..255)
            MAX-ACCESS read-only
            STATUS current
            DESCRIPTION
                "The number of the domains which have been created."
            ::= { hwAAAStatExtEntry 1 }


        hwAuthenSchemeNum OBJECT-TYPE
            SYNTAX Integer32 (0..16)
            MAX-ACCESS read-only
            STATUS current
            DESCRIPTION
                "The number of the authenschems which have been created."
            ::= { hwAAAStatExtEntry 2 }

        hwAccSchemeNum OBJECT-TYPE
            SYNTAX Integer32 (0..128)
            MAX-ACCESS read-only
            STATUS current
            DESCRIPTION
                "The number of the acctSchemes which have been created."
            ::= { hwAAAStatExtEntry 3 }

        hwTotalAcessNum OBJECT-TYPE
            SYNTAX Integer32 (0..1152)
            MAX-ACCESS read-only
            STATUS current
            DESCRIPTION
                "The number of access all users."
            ::= { hwAAAStatExtEntry 4 }

        hwTotalOnlineNum OBJECT-TYPE
            SYNTAX Integer32 (0..1152)
            MAX-ACCESS read-only
            STATUS current
            DESCRIPTION
                "The number of access all ftp user."
            ::= { hwAAAStatExtEntry 5 }

        hwTotalOnlineAccoutNum OBJECT-TYPE
            SYNTAX Integer32 (0..1152)
            MAX-ACCESS read-only
            STATUS current
            DESCRIPTION
                "The number of access all ssh users."
            ::= { hwAAAStatExtEntry 6 }

       hwRadiusSourceInterfaceObject OBJECT IDENTIFIER ::= { hwAAAMibObjects 33 }
       hwRadiusSourceInterfaceIfType OBJECT-TYPE
           SYNTAX INTEGER
                  {
                      meth(1),
                      vlanif(2),
                      loopback(3),
                      notConfiged(4)
                  }
           MAX-ACCESS          read-write
           STATUS              current
           DESCRIPTION         "Indicates the interface type.
                         Options:
                         1. meth(1)        -indicates the MEth interface
                         2. vlanif(2)      -indicates the VLAN interface
                         3. loopback(3)    -indicates the loopback interface
                         4. notConfiged(4) -indicates that no source interface is configured
                            When this leaf is set to notConfiged(4), it means that no source
                             interface is configured in the case of the create operation, and
                             that the source interface is deleted in the case of the modify operation.
                            "
                ::= { hwRadiusSourceInterfaceObject 1}
       hwRadiusSourceInterfaceIfNumber OBJECT-TYPE
          SYNTAX              Integer32 (0..4093)
          MAX-ACCESS          read-write
          STATUS              current
          DESCRIPTION         "Indicates the interface ID.
                             Range: 0-4093
                             Range for the MEth interface: 0
                             Range for the VLAN interface: 1-4093
                             Range for the loopback interface: 0-31
                             The interface ID and interface type (hwRadiusSourceInterfaceIfType) together identify an interface.
                            "
                ::= { hwRadiusSourceInterfaceObject 2 }
     END

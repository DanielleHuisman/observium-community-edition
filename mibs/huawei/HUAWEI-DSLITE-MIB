--  ==================================================================
-- Copyright (C) 2018 by  HUAWEI TECHNOLOGIES. All rights reserved.
-- 
-- Description: HUAWEI Hierarchy Quality Of Service MIB
-- Reference:
-- Version: V2.32
-- History:
-- <author>,  <date>,  <contents>
-- jugaoming   2015-05-29   V5 to V8
-- ==================================================================
-- ==================================================================

--  HUAWEI-DSLITE-MIB.mib
-- Tuesday, March 06, 2012 at 17:50:32
-- 

	HUAWEI-DSLITE-MIB DEFINITIONS ::= BEGIN
 
		IMPORTS
 			hwDatacomm			
				FROM HUAWEI-MIB			
			Ipv6Address			
				FROM IPV6-TC			
			OBJECT-GROUP, MODULE-COMPLIANCE, NOTIFICATION-GROUP			
				FROM SNMPv2-CONF			
			TimeTicks, IpAddress, Integer32, Unsigned32, Counter64, 
            BITS, OBJECT-TYPE, MODULE-IDENTITY, NOTIFICATION-TYPE            
				FROM SNMPv2-SMI			
            DisplayString, TruthValue, TEXTUAL-CONVENTION            
				FROM SNMPv2-TC;
	
	
--  
-- 
-- 
-- 
-- 1.3.6.1.4.1.2011.5.25.240
-- June 28, 2010 at 15:12 GMT
		hwDsliteMIB MODULE-IDENTITY 
			LAST-UPDATED "201801131500Z"  --Janurary 13, 2018 at 15:00 GMT
			ORGANIZATION 
				 "Huawei Technologies Co.,Ltd."
			CONTACT-INFO 
				"Huawei Industrial Base
				  Bantian, Longgang
				   Shenzhen 518129
				   People's Republic of China
				   Website: http://www.huawei.com
				   Email: support@huawei.com
				 "
			DESCRIPTION 
				"HUAWEI-DSLITE-MIB is used to configure alarms.
				"
                    REVISION
                                                                                       "201801131500Z"  --Janurary 13, 2018 at 15:00 GMT
                                                                  DESCRIPTION 
                                                                                      "Modify the Discription."
                    REVISION
                                                                                       "201712131132Z" --December 13 2017 at 10:00 GMT
                                                                  DESCRIPTION
                                                                                      "Add hwVSMBoardNotSupportAlarm and hwVSMBoardNotSupportResume."


                    REVISION
                                                                                       "201711021132Z" --November 02 2017 at 11:32 GMT
                                                                  DESCRIPTION
                                                                                      "Add hwMAPBoardNotSupport and hwMAPBoardNotSupportResume."

                    REVISION
                                                                                       "201708291132Z" --August 29 2017 at 11:32 GMT
                                                                  DESCRIPTION
                                                                                      "Add hwCGNDAPUPCPConfigInconsistent and hwCGNDAPPoolSectionSyncFail. Modify hwCGNDAPBackupConfigInconsistent"

                    REVISION
                                                                                       "201708031000Z" --August 3, 2017 at 10:00 GMT
                                                                  DESCRIPTION
                                                                                      "Add hwCGNGlobalPoolReleaseFail and hwCGNDAPBackupConfigInconsisten"
			        REVISION
                                                                                       "201706241117Z" --June 24, 2017 at 11:17 GMT
                                                                  DESCRIPTION
                                                                                      "Add description"
			        REVISION
                                                                                       "201706151111Z" --June 15, 2017 at 11:11 GMT
                                                                  DESCRIPTION
                                                                                      "Add description"
                                                                  REVISION				
                                                                                       "201706052111Z" --June 05, 2017 at 21:11 GMT                                                                
                                                                  DESCRIPTION
                                                                                       "Add VSUServiceFaultResumeAlarm"                                               
                                                                  REVISION
                                                                                       "201703141945Z" -- March 14, 2017 at 19:45 GMT
                                                                  DESCRIPTION
                                                                                       "Add CGN server map alarm."
                                                                  REVISION
                                                                                        "201701101844Z" --Janurary 10, 2017
                                                                  DESCRIPTION
                                                                                        "Add hwVSUDevicePerformanceExhaustAlarm and hwVSUDevicePerformanceExhaustAlarm"
                                                                  REVISION
                                                                                        "201604271030Z" -- Apr 27, 2016 
                                                                  DESCRIPTION
                                                                                        "Modify DevicePerformance change CGN to VSU."
                                                                  REVISION
                                                                                        "201512161030Z" -- Dec 16, 2015
                                                                  DESCRIPTION
                                                                                        "Add hwCGNRadiusSpecificAddressUserNumFullAlarm and hwCGNRadiusSpecificAddressUserNumFullResumeAlarm."
                                                                  REVISION
                                                                                        "201512041230Z" -- Dec 4, 2015
                                                                  DESCRIPTION
                                                                                        "Modify hwCGNAlarmbpsRate name."
                                                                  REVISION
                                                                                        "201511171030Z" -- Nov 17, 2015
                                                                  DESCRIPTION
                                                                                        "Modify mutlti CPU Performance alarm."                                                                 
                                                                  REVISION
                                                                                        "201509282100Z" -- Sep 28, 2015
                                                                  DESCRIPTION
                                                                                        "Add mutlti CPU Performance alarm."	                                                                 

                                                                  REVISION
                                                                                        "201505291130Z" -- May 29, 2015
                                                                  DESCRIPTION
                                                                                        "Add mutlti board alarm."																						
                                                                  REVISION
                                                                                        "201502281600Z" -- Feb 28, 2015
                                                                  DESCRIPTION
                                                                                        "Add 'Session Spec Overload Alarm'."
				                                                  REVISION
                                                                                        "201412290000Z" -- Dec 29, 2014		
																  DESCRIPTION
                                                                                        "Rename dap traps."																						
				                                                  REVISION
                                                                                        "201412270000Z" -- Dec 27, 2014
                                                                  DESCRIPTION
                                                                                        "Add dap traps."
                                                                  REVISION
                                                                                        "201407010000Z" -- Jul 01, 2014
                                                                  DESCRIPTION
                                                                                        "Add 'Device Performance'."
                                                                  REVISION
                                                                                        "201403280000Z" -- Mar 28, 2014
                                                                  DESCRIPTION
                                                                                        "Add 'No Pat','Access list','User table'."
                                                                  REVISION
                                                                                        "201302050000Z" -- Feb 5, 2013
                                                                  DESCRIPTION
                                                                                        "Initial version."
			::= { hwDatacomm 240 }
		
	
--
-- Textual conventions
--
	
--  Textual conventions
-- 
		RowStatus ::= TEXTUAL-CONVENTION
			STATUS current
			DESCRIPTION 
				"The RowStatus textual convention is used to manage the
				creation and deletion of conceptual rows, and is used as the
				value of the SYNTAX clause for the status column of a
				conceptual row (as described in Section 7.7.1 of [2].)
				The status column has six defined values:
				
				     - `active', which indicates that the conceptual row is
				     available for use by the managed device;
				
				     - `notInService', which indicates that the conceptual
				     row exists in the agent, but is unavailable for use by
				     the managed device (see NOTE below); 'notInService' has
				     no implication regarding the internal consistency of
				     the row, availability of resources, or consistency with
				     the current state of the managed device;
				
				     - `notReady', which indicates that the conceptual row
				     exists in the agent, but is missing information
				     necessary in order to be available for use by the
				     managed device (i.e., one or more required columns in
				     the conceptual row have not been instanciated);
				
				     - `createAndGo', which is supplied by a management
				     station wishing to create a new instance of a
				     conceptual row and to have its status automatically set
				     to active, making it available for use by the managed
				     device;
				
				     - `createAndWait', which is supplied by a management
				     station wishing to create a new instance of a
				     conceptual row (but not make it available for use by
				     the managed device); and,
				
				     - `destroy', which is supplied by a management station
				     wishing to delete all of the instances associated with
				     an existing conceptual row.
				
				Whereas five of the six values (all except `notReady') may
				be specified in a management protocol set operation, only
				three values will be returned in response to a management
				protocol retrieval operation:  `notReady', `notInService' or
				`active'.  That is, when queried, an existing conceptual row
				has only three states:  it is either available for use by
				the managed device (the status column has value `active');
				it is not available for use by the managed device, though
				the agent has sufficient information to attempt to make it
				so (the status column has value `notInService'); or, it is
				not available for use by the managed device, and an attempt
				to make it so would fail because the agent has insufficient
				information (the state column has value `notReady').
				                         NOTE WELL
				
				     This textual convention may be used for a MIB table,
				     irrespective of whether the values of that table's
				     conceptual rows are able to be modified while it is
				     active, or whether its conceptual rows must be taken
				     out of service in order to be modified.  That is, it is
				     the responsibility of the DESCRIPTION clause of the
				     status column to specify whether the status column must
				     not be `active' in order for the value of some other
				     column of the same conceptual row to be modified.  If
				     such a specification is made, affected columns may be
				     changed by an SNMP set PDU if the RowStatus would not
				     be equal to `active' either immediately before or after
				     processing the PDU.  In other words, if the PDU also
				     contained a varbind that would change the RowStatus
				     value, the column in question may be changed if the
				     RowStatus was not equal to `active' as the PDU was
				     received, or if the varbind sets the status to a value
				     other than 'active'.
				
				
				Also note that whenever any elements of a row exist, the
				RowStatus column must also exist.
				To summarize the effect of having a conceptual row with a
				status column having a SYNTAX clause value of RowStatus,
				consider the following state diagram:
				
				
				                             STATE
				  +--------------+-----------+-------------+-------------
				  |      A       |     B     |      C      |      D
				  |              |status col.|status column|
				  |status column |    is     |      is     |status column
				ACTION    |does not exist|  notReady | notInService|  is active
				--------------+--------------+-----------+-------------+-------------
				set status    |noError    ->D|inconsist- |inconsistent-|inconsistent-
				column to     |       or     |   entValue|        Value|        Value
				createAndGo   |inconsistent- |           |             |
				  |         Value|           |             |
				--------------+--------------+-----------+-------------+-------------
				set status    |noError  see 1|inconsist- |inconsistent-|inconsistent-
				column to     |       or     |   entValue|        Value|        Value
				createAndWait |wrongValue    |           |             |
				--------------+--------------+-----------+-------------+-------------
				set status    |inconsistent- |inconsist- |noError      |noError
				column to     |         Value|   entValue|             |
				active        |              |           |             |
				  |              |     or    |             |
				  |              |           |             |
				  |              |see 2   ->D|see 8     ->D|          ->D
				--------------+--------------+-----------+-------------+-------------
				set status    |inconsistent- |inconsist- |noError      |noError   ->C
				column to     |         Value|   entValue|             |
				notInService  |              |           |             |
				  |              |     or    |             |      or
				  |              |           |             |
				  |              |see 3   ->C|          ->C|see 6
				--------------+--------------+-----------+-------------+-------------
				set status    |noError       |noError    |noError      |noError   ->A
				column to     |              |           |             |      or
				destroy       |           ->A|        ->A|          ->A|see 7
				--------------+--------------+-----------+-------------+-------------
				set any other |see 4         |noError    |noError      |see 5
				column to some|              |           |             |
				value         |              |      see 1|          ->C|          ->D
				--------------+--------------+-----------+-------------+-------------
				
				(1) goto B or C, depending on information available to the
				agent.
				
				(2) if other variable bindings included in the same PDU,
				provide values for all columns which are missing but
				required, and all columns have acceptable values, then
				return noError and goto D.
				
				(3) if other variable bindings included in the same PDU,
				provide legal values for all columns which are missing but
				required, then return noError and goto C.
				
				(4) at the discretion of the agent, the return value may be
				either:
				
				     inconsistentName:  because the agent does not choose to
				     create such an instance when the corresponding
				     RowStatus instance does not exist, or
				
				     inconsistentValue:  if the supplied value is
				     inconsistent with the state of some other MIB object's
				     value, or
				
				     noError: because the agent chooses to create the
				     instance.
				
				If noError is returned, then the instance of the status
				column must also be created, and the new state is B or C,
				depending on the information available to the agent.  If
				inconsistentName or inconsistentValue is returned, the row
				remains in state A.
				
				(5) depending on the MIB definition for the column/table,
				either noError or inconsistentValue may be returned.
				
				(6) the return value can indicate one of the following
				errors:
				
				     wrongValue: because the agent does not support
				     notInService (e.g., an agent which does not support
				     createAndWait), or
				
				     inconsistentValue: because the agent is unable to take
				     the row out of service at this time, perhaps because it
				     is in use and cannot be de-activated.
				
				(7) the return value can indicate the following error:
				
				     inconsistentValue: because the agent is unable to
				     remove the row at this time, perhaps because it is in
				     use and cannot be de-activated.
				(8) the transition to D can fail, e.g., if the values of the
				conceptual row are inconsistent, then the error code would
				be inconsistentValue.
				
				NOTE: Other processing of (this and other varbinds of) the
				set request may result in a response other than noError
				being returned, e.g., wrongValue, noCreation, etc.
				
				
				                  Conceptual Row Creation
				
				There are four potential interactions when creating a
				conceptual row:  selecting an instance-identifier which is
				not in use; creating the conceptual row; initializing any
				objects for which the agent does not supply a default; and,
				making the conceptual row available for use by the managed
				device.
				
				Interaction 1: Selecting an Instance-Identifier
				
				The algorithm used to select an instance-identifier varies
				for each conceptual row.  In some cases, the instance-
				identifier is semantically significant, e.g., the
				destination address of a route, and a management station
				selects the instance-identifier according to the semantics.
				
				In other cases, the instance-identifier is used solely to
				distinguish conceptual rows, and a management station
				without specific knowledge of the conceptual row might
				examine the instances present in order to determine an
				unused instance-identifier.  (This approach may be used, but
				it is often highly sub-optimal; however, it is also a
				questionable practice for a naive management station to
				attempt conceptual row creation.)
				
				Alternately, the MIB module which defines the conceptual row
				might provide one or more objects which provide assistance
				in determining an unused instance-identifier.  For example,
				if the conceptual row is indexed by an integer-value, then
				an object having an integer-valued SYNTAX clause might be
				defined for such a purpose, allowing a management station to
				issue a management protocol retrieval operation.  In order
				to avoid unnecessary collisions between competing management
				stations, `adjacent' retrievals of this object should be
				different.
				
				Finally, the management station could select a pseudo-random
				number to use as the index.  In the event that this index
				was already in use and an inconsistentValue was returned in
				response to the management protocol set operation, the
				management station should simply select a new pseudo-random
				number and retry the operation.
				
				A MIB designer should choose between the two latter
				algorithms based on the size of the table (and therefore the
				efficiency of each algorithm).  For tables in which a large
				number of entries are expected, it is recommended that a MIB
				object be defined that returns an acceptable index for
				creation.  For tables with small numbers of entries, it is
				recommended that the latter pseudo-random index mechanism be
				used.
				
				Interaction 2: Creating the Conceptual Row
				
				Once an unused instance-identifier has been selected, the
				management station determines if it wishes to create and
				activate the conceptual row in one transaction or in a
				negotiated set of interactions.
				
				Interaction 2a: Creating and Activating the Conceptual Row
				
				The management station must first determine the column
				requirements, i.e., it must determine those columns for
				which it must or must not provide values.  Depending on the
				complexity of the table and the management station's
				knowledge of the agent's capabilities, this determination
				can be made locally by the management station.  Alternately,
				the management station issues a management protocol get
				operation to examine all columns in the conceptual row that
				it wishes to create.  In response, for each column, there
				are three possible outcomes:
				
				     - a value is returned, indicating that some other
				     management station has already created this conceptual
				     row.  We return to interaction 1.
				
				     - the exception `noSuchInstance' is returned,
				     indicating that the agent implements the object-type
				     associated with this column, and that this column in at
				     least one conceptual row would be accessible in the MIB
				     view used by the retrieval were it to exist. For those
				     columns to which the agent provides read-create access,
				     the `noSuchInstance' exception tells the management
				     station that it should supply a value for this column
				     when the conceptual row is to be created.
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				Once the column requirements have been determined, a
				management protocol set operation is accordingly issued.
				This operation also sets the new instance of the status
				column to `createAndGo'.
				
				When the agent processes the set operation, it verifies that
				it has sufficient information to make the conceptual row
				available for use by the managed device.  The information
				available to the agent is provided by two sources:  the
				management protocol set operation which creates the
				conceptual row, and, implementation-specific defaults
				supplied by the agent (note that an agent must provide
				implementation-specific defaults for at least those objects
				which it implements as read-only).  If there is sufficient
				information available, then the conceptual row is created, a
				`noError' response is returned, the status column is set to
				`active', and no further interactions are necessary (i.e.,
				interactions 3 and 4 are skipped).  If there is insufficient
				information, then the conceptual row is not created, and the
				set operation fails with an error of `inconsistentValue'.
				On this error, the management station can issue a management
				protocol retrieval operation to determine if this was
				because it failed to specify a value for a required column,
				or, because the selected instance of the status column
				already existed.  In the latter case, we return to
				interaction 1.  In the former case, the management station
				can re-issue the set operation with the additional
				information, or begin interaction 2 again using
				`createAndWait' in order to negotiate creation of the
				conceptual row.
				                         NOTE WELL
				
				     Regardless of the method used to determine the column
				     requirements, it is possible that the management
				     station might deem a column necessary when, in fact,
				     the agent will not allow that particular columnar
				     instance to be created or written.  In this case, the
				     management protocol set operation will fail with an
				     error such as `noCreation' or `notWritable'.  In this
				     case, the management station decides whether it needs
				     to be able to set a value for that particular columnar
				     instance.  If not, the management station re-issues the
				     management protocol set operation, but without setting
				     a value for that particular columnar instance;
				     otherwise, the management station aborts the row
				     creation algorithm.
				
				Interaction 2b: Negotiating the Creation of the Conceptual
				Row
				
				The management station issues a management protocol set
				operation which sets the desired instance of the status
				column to `createAndWait'.  If the agent is unwilling to
				process a request of this sort, the set operation fails with
				an error of `wrongValue'.  (As a consequence, such an agent
				must be prepared to accept a single management protocol set
				operation, i.e., interaction 2a above, containing all of the
				columns indicated by its column requirements.)  Otherwise,
				the conceptual row is created, a `noError' response is
				returned, and the status column is immediately set to either
				`notInService' or `notReady', depending on whether it has
				sufficient information to (attempt to) make the conceptual
				row available for use by the managed device.  If there is
				sufficient information available, then the status column is
				set to `notInService'; otherwise, if there is insufficient
				information, then the status column is set to `notReady'.
				Regardless, we proceed to interaction 3.
				
				Interaction 3: Initializing non-defaulted Objects
				
				The management station must now determine the column
				requirements.  It issues a management protocol get operation
				to examine all columns in the created conceptual row.  In
				the response, for each column, there are three possible
				outcomes:
				     - a value is returned, indicating that the agent
				     implements the object-type associated with this column
				     and had sufficient information to provide a value.  For
				     those columns to which the agent provides read-create
				     access (and for which the agent allows their values to
				     be changed after their creation), a value return tells
				     the management station that it may issue additional
				     management protocol set operations, if it desires, in
				     order to change the value associated with this column.
				
				     - the exception `noSuchInstance' is returned,
				     indicating that the agent implements the object-type
				     associated with this column, and that this column in at
				     least one conceptual row would be accessible in the MIB
				     view used by the retrieval were it to exist. However,
				     the agent does not have sufficient information to
				     provide a value, and until a value is provided, the
				     conceptual row may not be made available for use by the
				     managed device.  For those columns to which the agent
				     provides read-create access, the `noSuchInstance'
				     exception tells the management station that it must
				     issue additional management protocol set operations, in
				     order to provide a value associated with this column.
				
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				If the value associated with the status column is
				`notReady', then the management station must first deal with
				all `noSuchInstance' columns, if any.  Having done so, the
				value of the status column becomes `notInService', and we
				proceed to interaction 4.
				Interaction 4: Making the Conceptual Row Available
				
				Once the management station is satisfied with the values
				associated with the columns of the conceptual row, it issues
				a management protocol set operation to set the status column
				to `active'.  If the agent has sufficient information to
				make the conceptual row available for use by the managed
				device, the management protocol set operation succeeds (a
				`noError' response is returned).  Otherwise, the management
				protocol set operation fails with an error of
				`inconsistentValue'.
				
				                         NOTE WELL
				
				     A conceptual row having a status column with value
				     `notInService' or `notReady' is unavailable to the
				     managed device.  As such, it is possible for the
				     managed device to create its own instances during the
				     time between the management protocol set operation
				     which sets the status column to `createAndWait' and the
				     management protocol set operation which sets the status
				     column to `active'.  In this case, when the management
				     protocol set operation is issued to set the status
				     column to `active', the values held in the agent
				     supersede those used by the managed device.
				
				If the management station is prevented from setting the
				status column to `active' (e.g., due to management station
				or network failure) the conceptual row will be left in the
				`notInService' or `notReady' state, consuming resources
				indefinitely.  The agent must detect conceptual rows that
				have been in either state for an abnormally long period of
				time and remove them.  It is the responsibility of the
				DESCRIPTION clause of the status column to indicate what an
				abnormally long period of time would be.  This period of
				time should be long enough to allow for human response time
				(including `think time') between the creation of the
				conceptual row and the setting of the status to `active'.
				In the absence of such information in the DESCRIPTION
				clause, it is suggested that this period be approximately 5
				minutes in length.  This removal action applies not only to
				newly-created rows, but also to previously active rows which
				are set to, and left in, the notInService state for a
				prolonged period exceeding that which is considered normal
				for such a conceptual row.
				                 Conceptual Row Suspension
				
				When a conceptual row is `active', the management station
				may issue a management protocol set operation which sets the
				instance of the status column to `notInService'.  If the
				agent is unwilling to do so, the set operation fails with an
				error of `wrongValue' or `inconsistentValue'.  Otherwise,
				the conceptual row is taken out of service, and a `noError'
				response is returned.  It is the responsibility of the
				DESCRIPTION clause of the status column to indicate under
				what circumstances the status column should be taken out of
				service (e.g., in order for the value of some other column
				of the same conceptual row to be modified).
				
				
				                  Conceptual Row Deletion
				
				For deletion of conceptual rows, a management protocol set
				operation is issued which sets the instance of the status
				column to `destroy'.  This request may be made regardless of
				the current value of the status column (e.g., it is possible
				to delete conceptual rows which are either `notReady',
				`notInService' or `active'.)  If the operation succeeds,
				then all instances associated with the conceptual row are
				immediately removed."
			SYNTAX INTEGER
				{
				active(1),
				notInService(2),
				notReady(3),
				createAndGo(4),
				createAndWait(5),
				destroy(6)
				}
			
	
--
-- Node definitions
--
	
--  Node definitions
-- 
-- 1.3.6.1.4.1.2011.5.25.240.1
		hwDsliteObjects OBJECT IDENTIFIER ::= { hwDsliteMIB 1 }
		
        
		-- 1.3.6.1.4.1.2011.5.25.240.1.1
		hwDsliteScalar OBJECT IDENTIFIER ::= { hwDsliteObjects 1 }
		
        
		-- 1.3.6.1.4.1.2011.5.25.240.1.1.1
		hwDslitePathmtuEnable OBJECT-TYPE
			SYNTAX TruthValue
			MAX-ACCESS read-write
			STATUS current
			DESCRIPTION
				"Enable or Disable DS-Lite tunnel PMTU detection."
			::= { hwDsliteScalar 1 }
		
        
		-- 1.3.6.1.4.1.2011.5.25.240.1.1.2
		hwDslitePathmtuDetectTimeout OBJECT-TYPE
			SYNTAX Integer32 (60..300)
			MAX-ACCESS read-write
			STATUS current
			DESCRIPTION
				"Timeout value of DS-Lite tunnel PMTU detection."
			::= { hwDsliteScalar 2 }
		
        
		-- 1.3.6.1.4.1.2011.5.25.240.1.1.3
		hwDslitePathmtuDuration OBJECT-TYPE
			SYNTAX Integer32 (600..6000)
			MAX-ACCESS read-write
			STATUS current
			DESCRIPTION
				"Duration of DS-Lite tunnel PMTU detection."
			::= { hwDsliteScalar 3 }
		
        
		-- 1.3.6.1.4.1.2011.5.25.240.1.1.4
		hwDsliteTcpMss OBJECT-TYPE
			SYNTAX Integer32 (536..1461)
			MAX-ACCESS read-write
			STATUS current
			DESCRIPTION
				"DS-Lite will modify TCP SYNC packet'MSS to this value. 
				Valid range : 536~1460. 1461 means do not modify MSS."
			::= { hwDsliteScalar 4 }
		
        
		-- 1.3.6.1.4.1.2011.5.25.240.1.1.6
		hwDsliteCGNAlarmRoutingTable OBJECT-TYPE
			SYNTAX Integer32 (60..90)
			MAX-ACCESS read-write
			STATUS current
			DESCRIPTION
				"Threshold of routing table alarm."
			::= { hwDsliteScalar 6 }
		
        
		-- 1.3.6.1.4.1.2011.5.25.240.1.1.7
		hwDsliteCGNAlarmConnectNumber OBJECT-TYPE
			SYNTAX Integer32 (60..90)
			MAX-ACCESS read-write
			STATUS current
			DESCRIPTION
				"Threshold of DS-Lite connections alarm."
			::= { hwDsliteScalar 7 }
		
        
		-- 1.3.6.1.4.1.2011.5.25.240.1.1.8
		hwDslitePathmtuAgingTime OBJECT-TYPE
			SYNTAX Integer32 (600..6000)
			MAX-ACCESS read-write
			STATUS current
			DESCRIPTION
				"Aging time of DS-Lite tunnel PMTU items."
			::= { hwDsliteScalar 8 }
		
        
		-- 1.3.6.1.4.1.2011.5.25.240.1.1.9
		hwDsliteSessionAgingTimeType OBJECT-TYPE
			SYNTAX INTEGER
				{
				tcp(1),
				udp(2),
				icmp(3),
				fragment(4),
				syn(5),
				fin(6),
				tunnel(8)
				}
			MAX-ACCESS read-write
			STATUS current
			DESCRIPTION
				"Indicate which type of aging time is to configure by hwDsliteSessionAgingTime."
			::= { hwDsliteScalar 9 }
		
        
		-- 1.3.6.1.4.1.2011.5.25.240.1.1.10
		hwDsliteSessionAgingTime OBJECT-TYPE
			SYNTAX Integer32 (1..40000)
			MAX-ACCESS read-write
			STATUS current
			DESCRIPTION
				"Aging time value of type hwDsliteSessionAgingTimeType.
				(fragment :millisecond ,other : second)"
			::= { hwDsliteScalar 10 }
		
        
		-- 1.3.6.1.4.1.2011.5.25.240.1.2
		hwCGNAlarmScalar OBJECT IDENTIFIER ::= { hwDsliteObjects 2 }
		
        
		-- 1.3.6.1.4.1.2011.5.25.240.1.2.1
		hwCGNAlarmIpVersion OBJECT-TYPE
			SYNTAX INTEGER
				{
				ipv4(4),
				ipv6(6)
				}
			MAX-ACCESS accessible-for-notify
			STATUS current
			DESCRIPTION
				"Indicate which type the routing table alarm is . 
				4 for ipv4 routing table alarm,6 for ipv6 routing table alarm."
			::= { hwCGNAlarmScalar 1 }
		
        
		-- 1.3.6.1.4.1.2011.5.25.240.1.2.2
		hwCGNAlarmInstanceType OBJECT-TYPE
			SYNTAX DisplayString
			MAX-ACCESS accessible-for-notify
			STATUS current
			DESCRIPTION
				"The object indicates the type of instance in which port usage reaches a threshold."
			::= { hwCGNAlarmScalar 2 }
		
        
		-- 1.3.6.1.4.1.2011.5.25.240.1.2.3
		hwCGNAlarmCpeIpAddr OBJECT-TYPE
			SYNTAX DisplayString
			MAX-ACCESS accessible-for-notify
			STATUS current
			DESCRIPTION
				"The object indicates the user CPE IP address in an instance in which port usage reaches a threshold."
			::= { hwCGNAlarmScalar 3 }
		
        
		-- 1.3.6.1.4.1.2011.5.25.240.1.2.4
		hwCGNAlarmProtocolType OBJECT-TYPE
			SYNTAX DisplayString
			MAX-ACCESS accessible-for-notify
			STATUS current
			DESCRIPTION
				"The object indicates the protocol type of an instance in which port usage reaches a threshold. The value can be TCP, UDP, ICMP, or TOTAL."
			::= { hwCGNAlarmScalar 4 }
		
        
		-- 1.3.6.1.4.1.2011.5.25.240.1.2.5
		hwCGNAlarmAddrGroupName OBJECT-TYPE
			SYNTAX DisplayString
			MAX-ACCESS accessible-for-notify
			STATUS current
			DESCRIPTION
				"The object indicates the name of an address pool of an instance in which port usage reaches a threshold."
			::= { hwCGNAlarmScalar 5 }
		
        
		-- 1.3.6.1.4.1.2011.5.25.240.1.2.6
		hwCGNAlarmSpecificIP OBJECT-TYPE
			SYNTAX DisplayString
			MAX-ACCESS accessible-for-notify
			STATUS current
			DESCRIPTION
				"Indicate the IP address whose port usage reach threshold "
			::= { hwCGNAlarmScalar 6 }
		
        
		-- 1.3.6.1.4.1.2011.5.25.240.1.2.7
		hwCGNAlarmInstanceName OBJECT-TYPE
			SYNTAX DisplayString
			MAX-ACCESS accessible-for-notify
			STATUS current
			DESCRIPTION
				"The object indicates the name of an instance in which user- or address pool-based port usage reaches a threshold."
			::= { hwCGNAlarmScalar 7 }
		
        
		-- 1.3.6.1.4.1.2011.5.25.240.1.2.8
		hwVSUAlarmThreshold OBJECT-TYPE
			SYNTAX Integer32
			MAX-ACCESS accessible-for-notify
			STATUS current
			DESCRIPTION
				"The object indicates the alarm threshold of user- or public address pool-based port usage."
			::= { hwCGNAlarmScalar 8 }
		
        
		-- 1.3.6.1.4.1.2011.5.25.240.1.2.9
		hwCGNAlarmPortNum OBJECT-TYPE
			SYNTAX Integer32
			MAX-ACCESS accessible-for-notify
			STATUS current
			DESCRIPTION
				"The value of this object specifies the number of ports used when user- or public address pool-based port usage reaches an alarm threshold."
			::= { hwCGNAlarmScalar 9 }
		
        
		-- 1.3.6.1.4.1.2011.5.25.240.1.2.10
		hwVSUAlarmSlot OBJECT-TYPE
			SYNTAX Integer32
			MAX-ACCESS accessible-for-notify
			STATUS current
			DESCRIPTION
				"The object indicates the slot ID of a board on which user- or public address pool-based port usage reaches an alarm threshold."
			::= { hwCGNAlarmScalar 10 }
		
        
		-- 1.3.6.1.4.1.2011.5.25.240.1.2.11
		hwVSUAlarmCpu OBJECT-TYPE
			SYNTAX Integer32               
			MAX-ACCESS accessible-for-notify
			STATUS current
			DESCRIPTION
				"The object indicates the CPU ID of a board on which user- or public address pool-based port usage reaches an alarm threshold."
			::= { hwCGNAlarmScalar 11 }
		
        
		-- 1.3.6.1.4.1.2011.5.25.240.1.2.12
		hwCGNAlarmSessionNum OBJECT-TYPE
			SYNTAX Integer32
			MAX-ACCESS accessible-for-notify
			STATUS current
			DESCRIPTION
				"The value of this object specifies the number of IPv4 sessions when port usage reaches an alarm threshold."
			::= { hwCGNAlarmScalar 12 }
		
        
		-- 1.3.6.1.4.1.2011.5.25.240.1.2.13
		hwCGNAlarmCid OBJECT-TYPE
			SYNTAX Integer32
			MAX-ACCESS accessible-for-notify
			STATUS current
			DESCRIPTION
				"The object indicates the user ID used when port usage reaches an alarm threshold."
			::= { hwCGNAlarmScalar 13 }
		
        
		-- 1.3.6.1.4.1.2011.5.25.240.1.2.14
		hwCGNAlarmDeviceThreshold OBJECT-TYPE
			SYNTAX Integer32
			MAX-ACCESS read-write
			STATUS current
			DESCRIPTION
				"Indicate the threshold of the chassis"
			::= { hwCGNAlarmScalar 14 }
		
		-- 1.3.6.1.4.1.2011.5.25.240.1.2.15
		hwCGNAlarmTotalSessionNum OBJECT-TYPE
			SYNTAX Integer32
			MAX-ACCESS read-write
			STATUS current
			DESCRIPTION
				"Indicate the total session of the chassis"
			::= { hwCGNAlarmScalar 15 }
		
		-- 1.3.6.1.4.1.2011.5.25.240.1.2.16
		hwCGNAlarmIPNum OBJECT-TYPE
			SYNTAX Integer32
			MAX-ACCESS accessible-for-notify
			STATUS current
			DESCRIPTION
				"The value of this object specifies the number of IP addresses used in an address pool when port usage reaches an alarm threshold."
			::= { hwCGNAlarmScalar 16 }

		-- 1.3.6.1.4.1.2011.5.25.240.1.2.17
		hwCGNAlarmAccessUserNum OBJECT-TYPE
			SYNTAX Integer32
			MAX-ACCESS accessible-for-notify
			STATUS current
			DESCRIPTION
				"Access user number "
			::= { hwCGNAlarmScalar 17 }

		-- 1.3.6.1.4.1.2011.5.25.240.1.2.18
		hwCGNAlarmUserTableNum OBJECT-TYPE
			SYNTAX Integer32
			MAX-ACCESS accessible-for-notify
			STATUS current
			DESCRIPTION
				"The value of this object specifies the number of user tables."
			::= { hwCGNAlarmScalar 18 }

		-- 1.3.6.1.4.1.2011.5.25.240.1.2.19
		hwVSUAlarmbpsRateInUse OBJECT-TYPE
			SYNTAX Integer32
			MAX-ACCESS accessible-for-notify
			STATUS current
			DESCRIPTION
				"The object indicates the usage of the rate at bit/s."
			::= { hwCGNAlarmScalar 19 }
		
		-- 1.3.6.1.4.1.2011.5.25.240.1.2.20
		hwVSUAlarmMbpsRate OBJECT-TYPE
			SYNTAX Integer32
			MAX-ACCESS accessible-for-notify
			STATUS current
			DESCRIPTION
				"The object indicates the usage of the rate at Mbit/s."
			::= { hwCGNAlarmScalar 20 }
		
		-- 1.3.6.1.4.1.2011.5.25.240.1.2.21
		hwVSUAlarmppsRate OBJECT-TYPE
			SYNTAX Integer32
			MAX-ACCESS accessible-for-notify
			STATUS current
			DESCRIPTION
				"The object indicates the usage of the rate at pps."
			::= { hwCGNAlarmScalar 21 }
		
		-- 1.3.6.1.4.1.2011.5.25.240.1.2.22
		hwVSUAlarmCpuUsage OBJECT-TYPE
			SYNTAX Integer32
			MAX-ACCESS accessible-for-notify
			STATUS current
			DESCRIPTION
				"The object indicates CPU usage."
			::= { hwCGNAlarmScalar 22 }

		-- 1.3.6.1.4.1.2011.5.25.240.1.2.23
		hwCGNAlarmUsedIPNum OBJECT-TYPE
			SYNTAX Integer32
			MAX-ACCESS accessible-for-notify
			STATUS current
			DESCRIPTION
				"The value of this object specifies the number of used addresses in a global static address pool."
			::= { hwCGNAlarmScalar 23 }
						
		-- 1.3.6.1.4.1.2011.5.25.240.1.2.24
		hwCGNAlarmPoolName OBJECT-TYPE
			SYNTAX DisplayString
			MAX-ACCESS accessible-for-notify
			STATUS current
			DESCRIPTION
				"The object indicates the name of a global static address pool."
			::= { hwCGNAlarmScalar 24 }
			
		-- 1.3.6.1.4.1.2011.5.25.240.1.2.25
		hwCGNAlarmReason OBJECT-TYPE
			SYNTAX DisplayString
			MAX-ACCESS accessible-for-notify
			STATUS current
			DESCRIPTION
				"Indicate the alarm reason"
			::= { hwCGNAlarmScalar 25 }
			
		-- 1.3.6.1.4.1.2011.5.25.240.1.2.26
		hwCGNAlarmSubnet OBJECT-TYPE
			SYNTAX DisplayString
			MAX-ACCESS accessible-for-notify
			STATUS current
			DESCRIPTION
				"The object indicates the sub-mask of a global static address pool."
			::= { hwCGNAlarmScalar 26 }
			
		-- 1.3.6.1.4.1.2011.5.25.240.1.2.27
		hwCGNAlarmMask OBJECT-TYPE
			SYNTAX DisplayString
			MAX-ACCESS accessible-for-notify
			STATUS current
			DESCRIPTION
				"The object indicates the mask of a global static address pool."
			::= { hwCGNAlarmScalar 27 }
		-- 1.3.6.1.4.1.2011.5.25.240.1.2.28
		hwVSUAlarmBoardName OBJECT-TYPE
			SYNTAX DisplayString
			MAX-ACCESS accessible-for-notify
			STATUS current
			DESCRIPTION
				"The object indicates the name of the VSUF-80/VSUF-160 board on which user- or public address pool-based port usage reaches an alarm threshold."
			::= { hwCGNAlarmScalar 28 }

		-- 1.3.6.1.4.1.2011.5.25.240.1.2.29
		hwCGNAlarmServerMapUsage OBJECT-TYPE
			SYNTAX Integer32
			MAX-ACCESS accessible-for-notify
			STATUS current
			DESCRIPTION
				"The value of this object specifies the number of server-map entries."
			::= { hwCGNAlarmScalar 29 }
		
		-- 1.3.6.1.4.1.2011.5.25.240.1.2.30
		hwVSUServiceFaultCode OBJECT-TYPE
			SYNTAX Integer32
			MAX-ACCESS accessible-for-notify
			STATUS current
			DESCRIPTION
				"The object indicates the VSU service error code."
			::= { hwCGNAlarmScalar 30 }
		
		-- 1.3.6.1.4.1.2011.5.25.240.1.2.31
		hwVSUServiceFaultKey OBJECT-TYPE
			SYNTAX DisplayString
			MAX-ACCESS accessible-for-notify
			STATUS current
			DESCRIPTION
				"The object indicates the VSU service fault keywords."
			::= { hwCGNAlarmScalar 31 }
		
		-- 1.3.6.1.4.1.2011.5.25.240.1.2.32
		hwVSUReasonDescription OBJECT-TYPE
			SYNTAX DisplayString
			MAX-ACCESS accessible-for-notify
			STATUS current
			DESCRIPTION
				"The object indicates the description of a VSU service fault cause."
			::= { hwCGNAlarmScalar 32 }
			
		-- 1.3.6.1.4.1.2011.5.25.240.1.2.33
		hwMAPFrameId OBJECT-TYPE
			SYNTAX Integer32               
			MAX-ACCESS accessible-for-notify
			STATUS current
			DESCRIPTION
				"Indicate the LPU board's frame number"
			::= { hwCGNAlarmScalar 33 }			

		-- 1.3.6.1.4.1.2011.5.25.240.1.2.34
		hwMAPSlotId OBJECT-TYPE
			SYNTAX Integer32               
			MAX-ACCESS accessible-for-notify
			STATUS current
			DESCRIPTION
				"Indicate the LPU board's slot number"
			::= { hwCGNAlarmScalar 34 }

		-- 1.3.6.1.4.1.2011.5.25.240.1.2.35
		hwFuncationName OBJECT-TYPE
			SYNTAX DisplayString
			MAX-ACCESS accessible-for-notify
			STATUS current
			DESCRIPTION
				"Indicate the function's name."
			::= { hwCGNAlarmScalar 35 }			

		-- 1.3.6.1.4.1.2011.5.25.240.1.2.36
		hwLPUAlarmBoardName  OBJECT-TYPE
			SYNTAX DisplayString
			MAX-ACCESS accessible-for-notify
			STATUS current
			DESCRIPTION
				"Indicate the LPU board's name."
			::= { hwCGNAlarmScalar 36 }

		
--  1.3.6.1.4.1.2011.5.25.240.1.3
		hwDsliteInstanceTable OBJECT-TYPE
			SYNTAX SEQUENCE OF HwDsliteInstanceEntry
			MAX-ACCESS not-accessible
			STATUS current
			DESCRIPTION
				"This table is used to configure DS-Lite instance."
			::= { hwDsliteObjects 3 }
		
--  1.3.6.1.4.1.2011.5.25.240.1.3.1
		hwDsliteInstanceEntry OBJECT-TYPE
			SYNTAX HwDsliteInstanceEntry
			MAX-ACCESS not-accessible
			STATUS current
			DESCRIPTION
				"This table is used to configure DS-Lite instance."
			INDEX { hwInstanceName }
			::= { hwDsliteInstanceTable 1 }
		
		HwDsliteInstanceEntry ::=
			SEQUENCE { 
				hwInstanceName
					DisplayString,
				hwInstanceModeFullCone
					TruthValue,
				hwInstanceLocalIp
					Ipv6Address,
				hwInstanceMtu
					Integer32,
				hwInstanceLogSessionEnable
					TruthValue,
				hwInstanceSessionLimitEnable
					TruthValue,
				hwInstancePortLimitEnable
					TruthValue,
				hwInstanceTrafficClass
					Integer32,
				hwInstanceDscpCopyEnable
					TruthValue,
				hwInstanceLocalIpPrefixLength
					Integer32,
				hwInstanceCGNAlarmNatPortNumber
					Integer32,
				hwInstanceDetectALGMask
					Unsigned32,
				hwInstanceRowStatus
					RowStatus
			 }

--  1.3.6.1.4.1.2011.5.25.240.1.3.1.1
		hwInstanceName OBJECT-TYPE
			SYNTAX DisplayString (SIZE (1..31))
			MAX-ACCESS read-only
			STATUS current
			DESCRIPTION
				"Instance name."
			::= { hwDsliteInstanceEntry 1 }
		
--  1.3.6.1.4.1.2011.5.25.240.1.3.1.2
		hwInstanceModeFullCone OBJECT-TYPE
			SYNTAX TruthValue
			MAX-ACCESS read-create
			STATUS current
			DESCRIPTION
				"Indicates whether address groups of this instance use full-cone mode."
			::= { hwDsliteInstanceEntry 2 }
		
--  1.3.6.1.4.1.2011.5.25.240.1.3.1.3
		hwInstanceLocalIp OBJECT-TYPE
			SYNTAX Ipv6Address
			MAX-ACCESS read-create
			STATUS current
			DESCRIPTION
				"Local ip of this instance."
			::= { hwDsliteInstanceEntry 3 }
		
--  1.3.6.1.4.1.2011.5.25.240.1.3.1.4
		hwInstanceMtu OBJECT-TYPE
			SYNTAX Integer32 (1280..9600)
			MAX-ACCESS read-create
			STATUS current
			DESCRIPTION
				"Mtu of this instance."
			DEFVAL { 1500 }
			::= { hwDsliteInstanceEntry 4 }
		
--  1.3.6.1.4.1.2011.5.25.240.1.3.1.5
		hwInstanceLogSessionEnable OBJECT-TYPE
			SYNTAX TruthValue
			MAX-ACCESS read-create
			STATUS current
			DESCRIPTION
				"Whether log of this instance is enabled."
			::= { hwDsliteInstanceEntry 5 }
		
--  1.3.6.1.4.1.2011.5.25.240.1.3.1.7
		hwInstanceSessionLimitEnable OBJECT-TYPE
			SYNTAX TruthValue
			MAX-ACCESS read-create
			STATUS current
			DESCRIPTION
				"Whether Portlimit of this instance is enabled."
            ::= { hwDsliteInstanceEntry 7 }
		
--  1.3.6.1.4.1.2011.5.25.240.1.3.1.8
		hwInstancePortLimitEnable OBJECT-TYPE
			SYNTAX TruthValue
			MAX-ACCESS read-create
			STATUS current
			DESCRIPTION
				"Whether Portlimit of this instance is enabled."
            ::= { hwDsliteInstanceEntry 8 }
		
--  0 - 255 : set traffic class value
-- 256 : undo set traffic class
-- 1.3.6.1.4.1.2011.5.25.240.1.3.1.9
		hwInstanceTrafficClass OBJECT-TYPE
			SYNTAX Integer32 (0..256)
			MAX-ACCESS read-create
			STATUS current
			DESCRIPTION
				"Traffic class value of IPv6 packets when entering DS-Lite tunnel."
			DEFVAL { 256 }
            ::= { hwDsliteInstanceEntry 9 }
		
--  1.3.6.1.4.1.2011.5.25.240.1.3.1.10
		hwInstanceDscpCopyEnable OBJECT-TYPE
			SYNTAX TruthValue
			MAX-ACCESS read-create
			STATUS current
			DESCRIPTION
				"Whether to copy IPv6 packet'DSCP to IPv4 packet."
            ::= { hwDsliteInstanceEntry 10 }
		
--  1.3.6.1.4.1.2011.5.25.240.1.3.1.12
		hwInstanceLocalIpPrefixLength OBJECT-TYPE
			SYNTAX Integer32 (0..128)
			MAX-ACCESS read-create
			STATUS current
			DESCRIPTION
				"IPv6 prefix length of local ip."
            ::= { hwDsliteInstanceEntry 12 }
		
--  1.3.6.1.4.1.2011.5.25.240.1.3.1.13
		hwInstanceCGNAlarmNatPortNumber OBJECT-TYPE
			SYNTAX Integer32 (60..90)
			MAX-ACCESS read-create
			STATUS current
			DESCRIPTION
				"Threshold of used NAT port number when alarm."
            ::= { hwDsliteInstanceEntry 13 }
		
--  1.3.6.1.4.1.2011.5.25.240.1.3.1.14
		hwInstanceDetectALGMask OBJECT-TYPE
			SYNTAX Unsigned32
			MAX-ACCESS read-create
			STATUS current
			DESCRIPTION
				"Indicates the application protocols that need DS-Lite to process at NAT transform."
            ::= { hwDsliteInstanceEntry 14 }
		
--  1.3.6.1.4.1.2011.5.25.240.1.3.1.51
		hwInstanceRowStatus OBJECT-TYPE
			SYNTAX RowStatus
			MAX-ACCESS read-create
			STATUS current
			DESCRIPTION
				"Create or delete table row."
            ::= { hwDsliteInstanceEntry 51 }
		
--  1.3.6.1.4.1.2011.5.25.240.1.4
		hwDsliteInstanceSlotTable OBJECT-TYPE
			SYNTAX SEQUENCE OF HwDsliteInstanceSlotEntry
			MAX-ACCESS not-accessible
			STATUS current
			DESCRIPTION
				"This table is used to configure processing board for a DS-Lite instance."
			::= { hwDsliteObjects 4 }
		
--  1.3.6.1.4.1.2011.5.25.240.1.4.1
		hwDsliteInstanceSlotEntry OBJECT-TYPE
			SYNTAX HwDsliteInstanceSlotEntry
			MAX-ACCESS not-accessible
			STATUS current
			DESCRIPTION
				"Description."
			INDEX { hwSlotInstanceName, hwSlotSlotId }
			::= { hwDsliteInstanceSlotTable 1 }
		
		HwDsliteInstanceSlotEntry ::=
			SEQUENCE { 
				hwSlotInstanceName
					DisplayString,
				hwSlotSlotId
					Integer32,
				hwSlotIsMaster
					TruthValue,
				hwSlotRowStatus
					RowStatus
			 }

--  1.3.6.1.4.1.2011.5.25.240.1.4.1.1
		hwSlotInstanceName OBJECT-TYPE
			SYNTAX DisplayString (SIZE (1..31))
			MAX-ACCESS read-only
			STATUS current
			DESCRIPTION
				"Instance name the slot(board) belongs to."
			::= { hwDsliteInstanceSlotEntry 1 }
		
--  1.3.6.1.4.1.2011.5.25.240.1.4.1.2
		hwSlotSlotId OBJECT-TYPE
			SYNTAX Integer32 (1..16)
			MAX-ACCESS read-only
			STATUS current
			DESCRIPTION
				"Indicates which slot the instance uses."
			::= { hwDsliteInstanceSlotEntry 2 }
		
--  1.3.6.1.4.1.2011.5.25.240.1.4.1.3
		hwSlotIsMaster OBJECT-TYPE
			SYNTAX TruthValue
			MAX-ACCESS read-create
			STATUS current
			DESCRIPTION
				"Indicates the instance uses the board as a master or slave one."
			::= { hwDsliteInstanceSlotEntry 3 }
		
--  1.3.6.1.4.1.2011.5.25.240.1.4.1.51
		hwSlotRowStatus OBJECT-TYPE
			SYNTAX RowStatus
			MAX-ACCESS read-create
			STATUS current
			DESCRIPTION
				"Create or delete table row."
            ::= { hwDsliteInstanceSlotEntry 51 }
		
--  1.3.6.1.4.1.2011.5.25.240.1.5
		hwDsliteInstanceAddressGroupTable OBJECT-TYPE
			SYNTAX SEQUENCE OF HwDsliteInstanceAddressGroupEntry
			MAX-ACCESS not-accessible
			STATUS current
			DESCRIPTION
				"This table is used to configure the address groups of a DS-Lite instance."
			::= { hwDsliteObjects 5 }
		
--  1.3.6.1.4.1.2011.5.25.240.1.5.1
		hwDsliteInstanceAddressGroupEntry OBJECT-TYPE
			SYNTAX HwDsliteInstanceAddressGroupEntry
			MAX-ACCESS not-accessible
			STATUS current
			DESCRIPTION
				"Description."
			INDEX { hwAddressGroupInstanceName, hwAddressGroupName }
			::= { hwDsliteInstanceAddressGroupTable 1 }
		
		HwDsliteInstanceAddressGroupEntry ::=
			SEQUENCE { 
				hwAddressGroupInstanceName
					DisplayString,
				hwAddressGroupName
					DisplayString,
				hwAddressGroupStartAddress
					IpAddress,
				hwAddressGroupEndAddress
					IpAddress,
				hwAddressGroupFullCone
					TruthValue,
				hwAddressGroupRowStatus
					RowStatus
			 }

--  1.3.6.1.4.1.2011.5.25.240.1.5.1.1
		hwAddressGroupInstanceName OBJECT-TYPE
			SYNTAX DisplayString (SIZE (1..31))
			MAX-ACCESS read-only
			STATUS current
			DESCRIPTION
				"Instance name the address group belongs to."
			::= { hwDsliteInstanceAddressGroupEntry 1 }
		
--  1.3.6.1.4.1.2011.5.25.240.1.5.1.2
		hwAddressGroupName OBJECT-TYPE
			SYNTAX DisplayString (SIZE (1..31))
			MAX-ACCESS read-only
			STATUS current
			DESCRIPTION
				"Address group name."
			::= { hwDsliteInstanceAddressGroupEntry 2 }
		
--  1.3.6.1.4.1.2011.5.25.240.1.5.1.3
		hwAddressGroupStartAddress OBJECT-TYPE
			SYNTAX IpAddress
			MAX-ACCESS read-create
			STATUS current
			DESCRIPTION
				"Start address of address group."
			::= { hwDsliteInstanceAddressGroupEntry 3 }
		
--  1.3.6.1.4.1.2011.5.25.240.1.5.1.4
		hwAddressGroupEndAddress OBJECT-TYPE
			SYNTAX IpAddress
			MAX-ACCESS read-create
			STATUS current
			DESCRIPTION
				"End address of address group."
			::= { hwDsliteInstanceAddressGroupEntry 4 }
		
--  1.3.6.1.4.1.2011.5.25.240.1.5.1.5
		hwAddressGroupFullCone OBJECT-TYPE
			SYNTAX TruthValue
			MAX-ACCESS read-create
			STATUS current
			DESCRIPTION
				"Indicates whether the address groups use full-cone mode."
			::= { hwDsliteInstanceAddressGroupEntry 5 }
		
--  1.3.6.1.4.1.2011.5.25.240.1.5.1.51
		hwAddressGroupRowStatus OBJECT-TYPE
			SYNTAX RowStatus
			MAX-ACCESS read-create
			STATUS current
			DESCRIPTION
				"Create or delete table row."
            ::= { hwDsliteInstanceAddressGroupEntry 51 }
		
--  1.3.6.1.4.1.2011.5.25.240.1.6
		hwDsliteInstanceRemoteIpTable OBJECT-TYPE
			SYNTAX SEQUENCE OF HwDsliteInstanceRemoteIpEntry
			MAX-ACCESS not-accessible
			STATUS current
			DESCRIPTION
				"This table is used to configure the remote IP of a DS-Lite instance."
			::= { hwDsliteObjects 6 }
		
--  1.3.6.1.4.1.2011.5.25.240.1.6.1
		hwDsliteInstanceRemoteIpEntry OBJECT-TYPE
			SYNTAX HwDsliteInstanceRemoteIpEntry
			MAX-ACCESS not-accessible
			STATUS current
			DESCRIPTION
				"Description."
			INDEX { hwRemoteIpInstanceName, hwRemoteIpv6Addr, hwRemoteIpIpv6AddrPrefixLength }
			::= { hwDsliteInstanceRemoteIpTable 1 }
		
		HwDsliteInstanceRemoteIpEntry ::=
			SEQUENCE { 
				hwRemoteIpInstanceName
					DisplayString,
				hwRemoteIpv6Addr
					Ipv6Address,
				hwRemoteIpIpv6AddrPrefixLength
					Integer32,
				hwRemoteIpRowStatus
					RowStatus
			 }

--  1.3.6.1.4.1.2011.5.25.240.1.6.1.1
		hwRemoteIpInstanceName OBJECT-TYPE
			SYNTAX DisplayString (SIZE (1..31))
			MAX-ACCESS read-only
			STATUS current
			DESCRIPTION
				"Instance name the remote ip belongs to."
			::= { hwDsliteInstanceRemoteIpEntry 1 }
		
--  1.3.6.1.4.1.2011.5.25.240.1.6.1.2
		hwRemoteIpv6Addr OBJECT-TYPE
			SYNTAX Ipv6Address
			MAX-ACCESS read-only
			STATUS current
			DESCRIPTION
				"Remote IPv6 address."
			::= { hwDsliteInstanceRemoteIpEntry 2 }
		
--  1.3.6.1.4.1.2011.5.25.240.1.6.1.3
		hwRemoteIpIpv6AddrPrefixLength OBJECT-TYPE
			SYNTAX Integer32 (0..128)
			MAX-ACCESS read-only
			STATUS current
			DESCRIPTION
				"Remote IPv6 address prefix length."
			::= { hwDsliteInstanceRemoteIpEntry 3 }
		
--  1.3.6.1.4.1.2011.5.25.240.1.6.1.51
		hwRemoteIpRowStatus OBJECT-TYPE
			SYNTAX RowStatus
			MAX-ACCESS read-create
			STATUS current
			DESCRIPTION
				"Create or delete table row."
            ::= { hwDsliteInstanceRemoteIpEntry 51 }
		
--  1.3.6.1.4.1.2011.5.25.240.1.7
		hwDsliteInstanceOutboundTable OBJECT-TYPE
			SYNTAX SEQUENCE OF HwDsliteInstanceOutboundEntry
			MAX-ACCESS not-accessible
			STATUS current
			DESCRIPTION
				"This table is used to configure a outbound for a DS-Lite instance."
			::= { hwDsliteObjects 7 }
		
--  1.3.6.1.4.1.2011.5.25.240.1.7.1
		hwDsliteInstanceOutboundEntry OBJECT-TYPE
			SYNTAX HwDsliteInstanceOutboundEntry
			MAX-ACCESS not-accessible
			STATUS current
			DESCRIPTION
				"Description."
			INDEX { hwOutboundInstanceName, hwOutboundAcl6Number }
			::= { hwDsliteInstanceOutboundTable 1 }
		
		HwDsliteInstanceOutboundEntry ::=
			SEQUENCE { 
				hwOutboundInstanceName
					DisplayString,
				hwOutboundAcl6Number
					Integer32,
				hwOutboundAddressGroupName
					DisplayString,
				hwOutboundRowStatus
					RowStatus
			 }

--  1.3.6.1.4.1.2011.5.25.240.1.7.1.1
		hwOutboundInstanceName OBJECT-TYPE
			SYNTAX DisplayString (SIZE (1..31))
			MAX-ACCESS read-only
			STATUS current
			DESCRIPTION
				"Instance name the outbound belongs to."
			::= { hwDsliteInstanceOutboundEntry 1 }
		
--  1.3.6.1.4.1.2011.5.25.240.1.7.1.2
		hwOutboundAcl6Number OBJECT-TYPE
			SYNTAX Integer32 (2000..3999)
			MAX-ACCESS read-only
			STATUS current
			DESCRIPTION
				"Acl6 number of the outbound."
			::= { hwDsliteInstanceOutboundEntry 2 }
		
--  1.3.6.1.4.1.2011.5.25.240.1.7.1.3
		hwOutboundAddressGroupName OBJECT-TYPE
			SYNTAX DisplayString (SIZE (1..31))
			MAX-ACCESS read-create
			STATUS current
			DESCRIPTION
				"Address group name of the outbound."
			::= { hwDsliteInstanceOutboundEntry 3 }
		
--  1.3.6.1.4.1.2011.5.25.240.1.7.1.51
		hwOutboundRowStatus OBJECT-TYPE
			SYNTAX RowStatus
			MAX-ACCESS read-create
			STATUS current
			DESCRIPTION
				"Create or delete table row."
            ::= { hwDsliteInstanceOutboundEntry 51 }
		
--  1.3.6.1.4.1.2011.5.25.240.1.8
		hwDsliteInstanceLogSessionHostTable OBJECT-TYPE
			SYNTAX SEQUENCE OF HwDsliteInstanceLogSessionHostEntry
			MAX-ACCESS not-accessible
			STATUS current
			DESCRIPTION
				"This table is used to configure log hosts for a DS-Lite instance."
			::= { hwDsliteObjects 8 }
		
--  1.3.6.1.4.1.2011.5.25.240.1.8.1
		hwDsliteInstanceLogSessionHostEntry OBJECT-TYPE
			SYNTAX HwDsliteInstanceLogSessionHostEntry
			MAX-ACCESS not-accessible
			STATUS current
			DESCRIPTION
				"Description."
			INDEX { hwSessionLogInstanceName, hwSessionLogHostIp }
			::= { hwDsliteInstanceLogSessionHostTable 1 }
		
		HwDsliteInstanceLogSessionHostEntry ::=
			SEQUENCE { 
				hwSessionLogInstanceName
					DisplayString,
				hwSessionLogSourceIp
					IpAddress,
				hwSessionLogSourcePort
					Integer32,
				hwSessionLogHostIp
					IpAddress,
				hwSessionLogHostPort
					Integer32,
				hwSessionLogRowStatus
					RowStatus
			 }

--  1.3.6.1.4.1.2011.5.25.240.1.8.1.1
		hwSessionLogInstanceName OBJECT-TYPE
			SYNTAX DisplayString (SIZE (1..31))
			MAX-ACCESS read-only
			STATUS current
			DESCRIPTION
				"Instance name the log host belongs to."
			::= { hwDsliteInstanceLogSessionHostEntry 1 }
		
--  1.3.6.1.4.1.2011.5.25.240.1.8.1.2
		hwSessionLogSourceIp OBJECT-TYPE
			SYNTAX IpAddress
			MAX-ACCESS read-create
			STATUS current
			DESCRIPTION
				"Source ip of log host."
			::= { hwDsliteInstanceLogSessionHostEntry 2 }
		
--  1.3.6.1.4.1.2011.5.25.240.1.8.1.3
		hwSessionLogSourcePort OBJECT-TYPE
			SYNTAX Integer32 (0..65535)
			MAX-ACCESS read-create
			STATUS current
			DESCRIPTION
				"Source port of log host."
			::= { hwDsliteInstanceLogSessionHostEntry 3 }
		
--  1.3.6.1.4.1.2011.5.25.240.1.8.1.4
		hwSessionLogHostIp OBJECT-TYPE
			SYNTAX IpAddress
			MAX-ACCESS read-only
			STATUS current
			DESCRIPTION
				"Host ip of log host."
			::= { hwDsliteInstanceLogSessionHostEntry 4 }
		
--  1.3.6.1.4.1.2011.5.25.240.1.8.1.5
		hwSessionLogHostPort OBJECT-TYPE
			SYNTAX Integer32 (0..65535)
			MAX-ACCESS read-create
			STATUS current
			DESCRIPTION
				"Host port of log host."
			::= { hwDsliteInstanceLogSessionHostEntry 5 }
		
--  1.3.6.1.4.1.2011.5.25.240.1.8.1.51
		hwSessionLogRowStatus OBJECT-TYPE
			SYNTAX RowStatus
			MAX-ACCESS read-create
			STATUS current
			DESCRIPTION
				"Create or delete table row."
            ::= { hwDsliteInstanceLogSessionHostEntry 51 }
		
--  1.3.6.1.4.1.2011.5.25.240.1.9
		hwDsliteInstanceServerTable OBJECT-TYPE
			SYNTAX SEQUENCE OF HwDsliteInstanceServerEntry
			MAX-ACCESS not-accessible
			STATUS current
			DESCRIPTION
				"This table is used to configure servers in a DS-Lite instance."
			::= { hwDsliteObjects 9 }
		
--  1.3.6.1.4.1.2011.5.25.240.1.9.1
		hwDsliteInstanceServerEntry OBJECT-TYPE
			SYNTAX HwDsliteInstanceServerEntry
			MAX-ACCESS not-accessible
			STATUS current
			DESCRIPTION
				"Description."
			INDEX { hwServerInstanceName, hwServerInsideAddress, hwServerInsidePort, hwServerCPE }
			::= { hwDsliteInstanceServerTable 1 }
		
		HwDsliteInstanceServerEntry ::=
			SEQUENCE { 
				hwServerInstanceName
					DisplayString,
				hwServerProtocol
					INTEGER,
				hwServerGlobalAddress
					IpAddress,
				hwServerGlobalPort
					Integer32,
				hwServerInsideAddress
					IpAddress,
				hwServerInsidePort
					Integer32,
				hwServerCPE
					Ipv6Address,
				hwServerRowStatus
					RowStatus
			 }

--  1.3.6.1.4.1.2011.5.25.240.1.9.1.1
		hwServerInstanceName OBJECT-TYPE
			SYNTAX DisplayString (SIZE (1..31))
			MAX-ACCESS read-only
			STATUS current
			DESCRIPTION
				"Instance name the server is configured in."
			::= { hwDsliteInstanceServerEntry 1 }
		
--  1.3.6.1.4.1.2011.5.25.240.1.9.1.2
		hwServerProtocol OBJECT-TYPE
			SYNTAX INTEGER
				{
				any(0),
				tcp(6),
				udp(17)
				}
			MAX-ACCESS read-create
			STATUS current
			DESCRIPTION
				"Server protocol."
			::= { hwDsliteInstanceServerEntry 2 }
		
--  1.3.6.1.4.1.2011.5.25.240.1.9.1.3
		hwServerGlobalAddress OBJECT-TYPE
			SYNTAX IpAddress
			MAX-ACCESS read-create
			STATUS current
			DESCRIPTION
				"Published public ip address of this server ."
			::= { hwDsliteInstanceServerEntry 3 }
		
--  1.3.6.1.4.1.2011.5.25.240.1.9.1.4
		hwServerGlobalPort OBJECT-TYPE
			SYNTAX Integer32 (0..65535)
			MAX-ACCESS read-create
			STATUS current
			DESCRIPTION
				"Published public port of this server ."
			::= { hwDsliteInstanceServerEntry 4 }
		
--  1.3.6.1.4.1.2011.5.25.240.1.9.1.5
		hwServerInsideAddress OBJECT-TYPE
			SYNTAX IpAddress
			MAX-ACCESS read-only
			STATUS current
			DESCRIPTION
				"Inside ip address of this server ."
			::= { hwDsliteInstanceServerEntry 5 }
		
--  1.3.6.1.4.1.2011.5.25.240.1.9.1.6
		hwServerInsidePort OBJECT-TYPE
			SYNTAX Integer32 (0..65535)
			MAX-ACCESS read-only
			STATUS current
			DESCRIPTION
				"Inside port of this server ."
			::= { hwDsliteInstanceServerEntry 6 }
		
--  1.3.6.1.4.1.2011.5.25.240.1.9.1.7
		hwServerCPE OBJECT-TYPE
			SYNTAX Ipv6Address
			MAX-ACCESS read-only
			STATUS current
			DESCRIPTION
				"CPE which the server is from."
			::= { hwDsliteInstanceServerEntry 7 }
		
--  1.3.6.1.4.1.2011.5.25.240.1.9.1.51
		hwServerRowStatus OBJECT-TYPE
			SYNTAX RowStatus
			MAX-ACCESS read-create
			STATUS current
			DESCRIPTION
				"Create or delete table row."
            ::= { hwDsliteInstanceServerEntry 51 }
		
--  1.3.6.1.4.1.2011.5.25.240.1.10
		hwDsliteInstanceSessionLimitTable OBJECT-TYPE
			SYNTAX SEQUENCE OF HwDsliteInstanceSessionLimitEntry
			MAX-ACCESS not-accessible
			STATUS current
			DESCRIPTION
				"This table is used to configure session limits for a DS-Lite instance."
			::= { hwDsliteObjects 10 }
		
--  1.3.6.1.4.1.2011.5.25.240.1.10.1
		hwDsliteInstanceSessionLimitEntry OBJECT-TYPE
			SYNTAX HwDsliteInstanceSessionLimitEntry
			MAX-ACCESS not-accessible
			STATUS current
			DESCRIPTION
				"Description."
			INDEX { hwSessionLimitInstanceName, hwSessionLimitType }
			::= { hwDsliteInstanceSessionLimitTable 1 }
		
		HwDsliteInstanceSessionLimitEntry ::=
			SEQUENCE { 
				hwSessionLimitInstanceName
					DisplayString,
				hwSessionLimitType
					INTEGER,
				hwSessionLimitNumber
					Integer32,
				hwSessionLimitRowStatus
					RowStatus
			 }

--  1.3.6.1.4.1.2011.5.25.240.1.10.1.1
		hwSessionLimitInstanceName OBJECT-TYPE
			SYNTAX DisplayString (SIZE (1..31))
			MAX-ACCESS read-only
			STATUS current
			DESCRIPTION
				"Instance name that is limited."
			::= { hwDsliteInstanceSessionLimitEntry 1 }
		
--  1.3.6.1.4.1.2011.5.25.240.1.10.1.2
		hwSessionLimitType OBJECT-TYPE
			SYNTAX INTEGER
				{
				tcp(0),
				udp(1),
				icmp(2),
				total(3)
				}
			MAX-ACCESS read-only
			STATUS current
			DESCRIPTION
				"Session limit type : tcp or udp or totally."
			::= { hwDsliteInstanceSessionLimitEntry 2 }
		
--  1.3.6.1.4.1.2011.5.25.240.1.10.1.3
		hwSessionLimitNumber OBJECT-TYPE
			SYNTAX Integer32 (1..65535)
			MAX-ACCESS read-create
			STATUS current
			DESCRIPTION
				"The limit number."
			::= { hwDsliteInstanceSessionLimitEntry 3 }
		
--  1.3.6.1.4.1.2011.5.25.240.1.10.1.51
		hwSessionLimitRowStatus OBJECT-TYPE
			SYNTAX RowStatus
			MAX-ACCESS read-create
			STATUS current
			DESCRIPTION
				"Create or delete table row."
            ::= { hwDsliteInstanceSessionLimitEntry 51 }
		
--  1.3.6.1.4.1.2011.5.25.240.1.11
		hwDsliteInstancePortLimitTable OBJECT-TYPE
			SYNTAX SEQUENCE OF HwDsliteInstancePortLimitEntry
			MAX-ACCESS not-accessible
			STATUS current
			DESCRIPTION
				"This table is used to configure port limits for a DS-Lite instance."
			::= { hwDsliteObjects 11 }
		
--  1.3.6.1.4.1.2011.5.25.240.1.11.1
		hwDsliteInstancePortLimitEntry OBJECT-TYPE
			SYNTAX HwDsliteInstancePortLimitEntry
			MAX-ACCESS not-accessible
			STATUS current
			DESCRIPTION
				"Description."
			INDEX { hwPortLimitInstanceName, hwPortLimitType }
			::= { hwDsliteInstancePortLimitTable 1 }
		
		HwDsliteInstancePortLimitEntry ::=
			SEQUENCE { 
				hwPortLimitInstanceName
					DisplayString,
				hwPortLimitType
					INTEGER,
				hwPortLimitNumber
					Integer32,
				hwPortLimitRowStatus
					RowStatus
			 }

--  1.3.6.1.4.1.2011.5.25.240.1.11.1.1
		hwPortLimitInstanceName OBJECT-TYPE
			SYNTAX DisplayString (SIZE (1..31))
			MAX-ACCESS read-only
			STATUS current
			DESCRIPTION
				"Instance name that is limited."
			::= { hwDsliteInstancePortLimitEntry 1 }
		
--  1.3.6.1.4.1.2011.5.25.240.1.11.1.2
		hwPortLimitType OBJECT-TYPE
			SYNTAX INTEGER
				{
				tcp(0),
				udp(1),
				icmp(2),
				total(3)
				}
			MAX-ACCESS read-only
			STATUS current
			DESCRIPTION
				"Port limit type: tcp or udp or totally."
			::= { hwDsliteInstancePortLimitEntry 2 }
		
--  1.3.6.1.4.1.2011.5.25.240.1.11.1.3
		hwPortLimitNumber OBJECT-TYPE
			SYNTAX Integer32 (1..300000)
			MAX-ACCESS read-create
			STATUS current
			DESCRIPTION
				"The limit number."
			::= { hwDsliteInstancePortLimitEntry 3 }
		
--  1.3.6.1.4.1.2011.5.25.240.1.11.1.51
		hwPortLimitRowStatus OBJECT-TYPE
			SYNTAX RowStatus
			MAX-ACCESS read-create
			STATUS current
			DESCRIPTION
				"Create or delete table row."
            ::= { hwDsliteInstancePortLimitEntry 51 }
		
--  1.3.6.1.4.1.2011.5.25.240.1.12
        hwDsliteStatisticTable OBJECT-TYPE
            SYNTAX SEQUENCE OF HwDsliteStatisticEntry
			MAX-ACCESS not-accessible
			STATUS current
			DESCRIPTION
				"This table provides statistical information of DS-Lite ."
			::= { hwDsliteObjects 12 }
		
--  1.3.6.1.4.1.2011.5.25.240.1.12.1
        hwDsliteStatisticEntry OBJECT-TYPE
            SYNTAX HwDsliteStatisticEntry
			MAX-ACCESS not-accessible
			STATUS current
			DESCRIPTION
				"Description."
            INDEX { hwDsliteStatisticSlotId, hwDsliteStatisticCpuId }
            ::= { hwDsliteStatisticTable 1 }
		
        HwDsliteStatisticEntry ::=
			SEQUENCE { 
                hwDsliteStatisticSlotId
                    Integer32,
                hwDsliteStatisticCpuId
                    Integer32,
                hwDsliteStatisticDiscard
					Counter64,
                hwDsliteStatisticReceived
					Counter64,
                hwDsliteStatisticTransmitted
					Counter64,
                hwDsliteStatisticIpv4Session
					Counter64,
                hwDsliteStatisticIpv6Session
                    Counter64,
                hwDsliteStatisticRowStatus
                    RowStatus
			 }

--  1.3.6.1.4.1.2011.5.25.240.1.12.1.1
        hwDsliteStatisticSlotId OBJECT-TYPE
            SYNTAX Integer32 (1..16)
			MAX-ACCESS read-only
			STATUS current
			DESCRIPTION
				"Indicate the information is from which slot(board)."
            ::= { hwDsliteStatisticEntry 1 }
		
--  1.3.6.1.4.1.2011.5.25.240.1.12.1.2
        hwDsliteStatisticCpuId OBJECT-TYPE
            SYNTAX Integer32 (0..3)
            MAX-ACCESS read-only
            STATUS current
            DESCRIPTION
                "Indicate the information is from which cpu of the board."
            ::= { hwDsliteStatisticEntry 2 }
        -- 1.3.6.1.4.1.2011.5.25.240.1.12.1.3
        hwDsliteStatisticDiscard OBJECT-TYPE
			SYNTAX Counter64
			MAX-ACCESS read-only
			STATUS current
			DESCRIPTION
				"Discarded packet count."
            ::= { hwDsliteStatisticEntry 3 }
		
        -- 1.3.6.1.4.1.2011.5.25.240.1.12.1.4
        hwDsliteStatisticReceived OBJECT-TYPE
			SYNTAX Counter64
			MAX-ACCESS read-only
			STATUS current
			DESCRIPTION
				"Received packet count."
            ::= { hwDsliteStatisticEntry 4 }
		
        -- 1.3.6.1.4.1.2011.5.25.240.1.12.1.5
        hwDsliteStatisticTransmitted OBJECT-TYPE
			SYNTAX Counter64
			MAX-ACCESS read-only
			STATUS current
			DESCRIPTION
				"Transmitted packet count."
            ::= { hwDsliteStatisticEntry 5 }
		
        -- 1.3.6.1.4.1.2011.5.25.240.1.12.1.6
        hwDsliteStatisticIpv4Session OBJECT-TYPE
			SYNTAX Counter64
			MAX-ACCESS read-only
			STATUS current
			DESCRIPTION
				"Current IPv4 Session number."
            ::= { hwDsliteStatisticEntry 6 }
		
        -- 1.3.6.1.4.1.2011.5.25.240.1.12.1.7
        hwDsliteStatisticIpv6Session OBJECT-TYPE
			SYNTAX Counter64
			MAX-ACCESS read-only
			STATUS current
			DESCRIPTION
				"Current IPv6 Session number."
            ::= { hwDsliteStatisticEntry 7 }
		
        -- 1.3.6.1.4.1.2011.5.25.240.1.12.1.8
        hwDsliteStatisticRowStatus OBJECT-TYPE
            SYNTAX RowStatus
            MAX-ACCESS read-create
            STATUS current
            DESCRIPTION
                "Create or delete table row."
            ::= { hwDsliteStatisticEntry 8 }
--  1.3.6.1.4.1.2011.5.25.240.1.13
		hwDslitePortUsageTable OBJECT-TYPE
			SYNTAX SEQUENCE OF HwDslitePortUsageEntry
			MAX-ACCESS not-accessible
			STATUS current
			DESCRIPTION
				"This table is used to configure the address groups of a DS-Lite instance."
			::= { hwDsliteObjects 13 }
		
--  1.3.6.1.4.1.2011.5.25.240.1.13.1
		hwDslitePortUsageEntry OBJECT-TYPE
			SYNTAX HwDslitePortUsageEntry
			MAX-ACCESS not-accessible
			STATUS current
			DESCRIPTION
				"Description."
			INDEX { hwPortUsageInstanceName, hwPortUsageAddrGroupName, hwPortUsageSlotID, hwPortUsageCpuID, hwPortUsageIP
				 }
			::= { hwDslitePortUsageTable 1 }
		
		HwDslitePortUsageEntry ::=
			SEQUENCE { 
				hwPortUsageInstanceName
					DisplayString,
				hwPortUsageAddrGroupName
					DisplayString,
				hwPortUsageSlotID
					Integer32,
				hwPortUsageCpuID
					Integer32,
				hwPortUsageIP
					IpAddress,
				hwPortUsageOfFullGroup
					OCTET STRING,
				hwPortUsageOfPortRange
					OCTET STRING,
				hwPortUsageOfPortforwarding
					OCTET STRING,
				hwPortUsageOfSpecificIP
					OCTET STRING,
				hwPortUsageRowStatus
					RowStatus
			 }

--  1.3.6.1.4.1.2011.5.25.240.1.13.1.1
		hwPortUsageInstanceName OBJECT-TYPE
			SYNTAX DisplayString (SIZE (1..31))
			MAX-ACCESS read-only
			STATUS current
			DESCRIPTION
				"Instance name the address group belongs to."
			::= { hwDslitePortUsageEntry 1 }
		
--  1.3.6.1.4.1.2011.5.25.240.1.13.1.2
		hwPortUsageAddrGroupName OBJECT-TYPE
			SYNTAX DisplayString (SIZE (1..31))
			MAX-ACCESS read-only
			STATUS current
			DESCRIPTION
				"Address group name."
			::= { hwDslitePortUsageEntry 2 }
		
--  1.3.6.1.4.1.2011.5.25.240.1.13.1.3
		hwPortUsageSlotID OBJECT-TYPE
			SYNTAX Integer32 (1..16)
			MAX-ACCESS read-only
			STATUS current
			DESCRIPTION
				"The slot ID of NAT board,1..16"
			::= { hwDslitePortUsageEntry 3 }
		
--  1.3.6.1.4.1.2011.5.25.240.1.13.1.4
		hwPortUsageCpuID OBJECT-TYPE
			SYNTAX Integer32 (0..3)
			MAX-ACCESS read-only
			STATUS current
			DESCRIPTION
				"The ID of CPU,0..3"
			::= { hwDslitePortUsageEntry 4 }
		
--  1.3.6.1.4.1.2011.5.25.240.1.13.1.5
		hwPortUsageIP OBJECT-TYPE
			SYNTAX IpAddress
			MAX-ACCESS read-only
			STATUS current
			DESCRIPTION
				"Port usage of specific IP address"
			::= { hwDslitePortUsageEntry 5 }
		
--  1.3.6.1.4.1.2011.5.25.240.1.13.1.6
		hwPortUsageOfFullGroup OBJECT-TYPE
			SYNTAX OCTET STRING (SIZE (1..256))
			MAX-ACCESS read-create
			STATUS current
			DESCRIPTION
				"Port usage of full address group"
			::= { hwDslitePortUsageEntry 6 }
		
--  1.3.6.1.4.1.2011.5.25.240.1.13.1.7
		hwPortUsageOfPortRange OBJECT-TYPE
			SYNTAX OCTET STRING (SIZE (1..256))
			MAX-ACCESS read-create
			STATUS current
			DESCRIPTION
				"Port usage of port-range"
			::= { hwDslitePortUsageEntry 7 }
		
--  1.3.6.1.4.1.2011.5.25.240.1.13.1.8
		hwPortUsageOfPortforwarding OBJECT-TYPE
			SYNTAX OCTET STRING (SIZE (1..256))
			MAX-ACCESS read-create
			STATUS current
			DESCRIPTION
				"Port usage of portforwarding"
			::= { hwDslitePortUsageEntry 8 }
		
--  1.3.6.1.4.1.2011.5.25.240.1.13.1.9
		hwPortUsageOfSpecificIP OBJECT-TYPE
			SYNTAX OCTET STRING (SIZE (1..256))
			MAX-ACCESS read-create
			STATUS current
			DESCRIPTION
				"Port usage of specific IP address"
			::= { hwDslitePortUsageEntry 9 }
		
--  1.3.6.1.4.1.2011.5.25.240.1.13.1.10
		hwPortUsageRowStatus OBJECT-TYPE
			SYNTAX RowStatus
			MAX-ACCESS read-create
			STATUS current
			DESCRIPTION
				"Create or delete table row."
			::= { hwDslitePortUsageEntry 10 }
		
--  1.3.6.1.4.1.2011.5.25.240.1.14
		hwSMCopyTable OBJECT-TYPE
			SYNTAX SEQUENCE OF HwSMCopyEntry
			MAX-ACCESS not-accessible
			STATUS current
			DESCRIPTION
				"Description."
			::= { hwDsliteObjects 14 }
		
--  1.3.6.1.4.1.2011.5.25.240.1.14.1
		hwSMCopyEntry OBJECT-TYPE
			SYNTAX HwSMCopyEntry
			MAX-ACCESS not-accessible
			STATUS current
			DESCRIPTION
				"Description."
			INDEX { hwSMCopyIndex }
			::= { hwSMCopyTable 1 }
		
		HwSMCopyEntry ::=
			SEQUENCE { 
				hwSMCopyIndex
					Integer32,
				hwSMCopyProtocol
					OCTET STRING,
				hwSMCopySrcFileType
					Integer32,
				hwSMCopyDstFileType
					Integer32,
				hwSMCopyFtpServer
					IpAddress,
				hwSMCopySrcFileName
					OCTET STRING,
				hwSMCopyDstFileName
					OCTET STRING,
				hwSMCopyUserName
					OCTET STRING,
				hwSMCopyUserPwd
					OCTET STRING,
				hwSMCopyRowStatus
					RowStatus
			 }

--  1.3.6.1.4.1.2011.5.25.240.1.14.1.1
		hwSMCopyIndex OBJECT-TYPE
			SYNTAX Integer32 (1)
			MAX-ACCESS read-only
			STATUS current
			DESCRIPTION
				"Description."
			::= { hwSMCopyEntry 1 }
		
--  1.3.6.1.4.1.2011.5.25.240.1.14.1.2
		hwSMCopyProtocol OBJECT-TYPE
			SYNTAX OCTET STRING (SIZE (0..5))
			MAX-ACCESS read-create
			STATUS current
			DESCRIPTION
				"Description."
			::= { hwSMCopyEntry 2 }
		
--  1.3.6.1.4.1.2011.5.25.240.1.14.1.3
		hwSMCopySrcFileType OBJECT-TYPE
			SYNTAX Integer32 (1..10)
			MAX-ACCESS read-create
			STATUS current
			DESCRIPTION
				"Description."
			DEFVAL { 1 }
			::= { hwSMCopyEntry 3 }
		
--  1.3.6.1.4.1.2011.5.25.240.1.14.1.4
		hwSMCopyDstFileType OBJECT-TYPE
			SYNTAX Integer32 (1..10)
			MAX-ACCESS read-create
			STATUS current
			DESCRIPTION
				"Description."
			DEFVAL { 4 }
			::= { hwSMCopyEntry 4 }
		
--  1.3.6.1.4.1.2011.5.25.240.1.14.1.5
		hwSMCopyFtpServer OBJECT-TYPE
			SYNTAX IpAddress
			MAX-ACCESS read-create
			STATUS current
			DESCRIPTION
				"Description."
			::= { hwSMCopyEntry 5 }
		
--  1.3.6.1.4.1.2011.5.25.240.1.14.1.6
		hwSMCopySrcFileName OBJECT-TYPE
			SYNTAX OCTET STRING (SIZE (0..80))
			MAX-ACCESS read-create
			STATUS current
			DESCRIPTION
				"Description."
			::= { hwSMCopyEntry 6 }
		
--  1.3.6.1.4.1.2011.5.25.240.1.14.1.7
		hwSMCopyDstFileName OBJECT-TYPE
			SYNTAX OCTET STRING (SIZE (0..80))
			MAX-ACCESS read-create
			STATUS current
			DESCRIPTION
				"Description."
			::= { hwSMCopyEntry 7 }
		
--  1.3.6.1.4.1.2011.5.25.240.1.14.1.8
		hwSMCopyUserName OBJECT-TYPE
			SYNTAX OCTET STRING (SIZE (0..80))
			MAX-ACCESS read-create
			STATUS current
			DESCRIPTION
				"Description."
			::= { hwSMCopyEntry 8 }
		
--  1.3.6.1.4.1.2011.5.25.240.1.14.1.9
		hwSMCopyUserPwd OBJECT-TYPE
			SYNTAX OCTET STRING (SIZE (0..80))
			MAX-ACCESS read-create
			STATUS current
			DESCRIPTION
				"Description."
			::= { hwSMCopyEntry 9 }
		
--  1.3.6.1.4.1.2011.5.25.240.1.14.1.10
		hwSMCopyRowStatus OBJECT-TYPE
			SYNTAX RowStatus
			MAX-ACCESS read-create
			STATUS current
			DESCRIPTION
				"Description."
			::= { hwSMCopyEntry 10 }
		
--  1.3.6.1.4.1.2011.5.25.240.1.15
		hwSMReadTable OBJECT-TYPE
			SYNTAX SEQUENCE OF HwSMReadEntry
			MAX-ACCESS not-accessible
			STATUS current
			DESCRIPTION
				"Description."
			::= { hwDsliteObjects 15 }
		
--  1.3.6.1.4.1.2011.5.25.240.1.15.1
		hwSMReadEntry OBJECT-TYPE
			SYNTAX HwSMReadEntry
			MAX-ACCESS not-accessible
			STATUS current
			DESCRIPTION
				"Description."
			INDEX { hwSMReadIndex }
			::= { hwSMReadTable 1 }
		
		HwSMReadEntry ::=
			SEQUENCE { 
				hwSMReadIndex
					Integer32,
				hwSMReadFileType
					Integer32,
				hwSMReadFileName
					OCTET STRING,
				hwSMReadRowStatus
					RowStatus
			 }

--  1.3.6.1.4.1.2011.5.25.240.1.15.1.1
		hwSMReadIndex OBJECT-TYPE
			SYNTAX Integer32 (1)
			MAX-ACCESS read-only
			STATUS current
			DESCRIPTION
				"Description."
			::= { hwSMReadEntry 1 }
		
--  1.3.6.1.4.1.2011.5.25.240.1.15.1.2
		hwSMReadFileType OBJECT-TYPE
			SYNTAX Integer32 (1..10)
			MAX-ACCESS read-create
			STATUS current
			DESCRIPTION
				"Description."
			::= { hwSMReadEntry 2 }
		
--  1.3.6.1.4.1.2011.5.25.240.1.15.1.3
		hwSMReadFileName OBJECT-TYPE
			SYNTAX OCTET STRING (SIZE (0..80))
			MAX-ACCESS read-create
			STATUS current
			DESCRIPTION
				"Description."
			::= { hwSMReadEntry 3 }
		
--  1.3.6.1.4.1.2011.5.25.240.1.15.1.4
		hwSMReadRowStatus OBJECT-TYPE
			SYNTAX RowStatus
			MAX-ACCESS read-create
			STATUS current
			DESCRIPTION
				"Description."
			::= { hwSMReadEntry 4 }
		
--  1.3.6.1.4.1.2011.5.25.240.1.16
		hwCopyConfigScalar OBJECT IDENTIFIER ::= { hwDsliteObjects 16 }
		
--  1.3.6.1.4.1.2011.5.25.240.1.16.1
		hwSMCopyState OBJECT-TYPE
			SYNTAX Integer32
			MAX-ACCESS read-only
			STATUS current
			DESCRIPTION
				"Description."
			::= { hwCopyConfigScalar 1 }
		
--  1.3.6.1.4.1.2011.5.25.240.1.16.2
		hwSMCopyTimeStarted OBJECT-TYPE
			SYNTAX TimeTicks
			MAX-ACCESS read-only
			STATUS current
			DESCRIPTION
				"Description."
			::= { hwCopyConfigScalar 2 }
		
--  1.3.6.1.4.1.2011.5.25.240.1.16.3
		hwSMCopyTimeCompleted OBJECT-TYPE
			SYNTAX TimeTicks
			MAX-ACCESS read-only
			STATUS current
			DESCRIPTION
				"Description."
			::= { hwCopyConfigScalar 3 }
		
--  1.3.6.1.4.1.2011.5.25.240.1.16.4
		hwSMCopyFailCause OBJECT-TYPE
			SYNTAX OCTET STRING
			MAX-ACCESS read-only
			STATUS current
			DESCRIPTION
				"Description."
			::= { hwCopyConfigScalar 4 }
		
--  1.3.6.1.4.1.2011.5.25.240.1.17
		hwReadConfigScalar OBJECT IDENTIFIER ::= { hwDsliteObjects 17 }
		
--  1.3.6.1.4.1.2011.5.25.240.1.17.1
		hwSMReadState OBJECT-TYPE
			SYNTAX Integer32
			MAX-ACCESS read-only
			STATUS current
			DESCRIPTION
				"Description."
			::= { hwReadConfigScalar 1 }
		
--  1.3.6.1.4.1.2011.5.25.240.1.17.2
		hwSMReadResultFileName OBJECT-TYPE
			SYNTAX OCTET STRING
			MAX-ACCESS read-only
			STATUS current
			DESCRIPTION
				"Description."
			::= { hwReadConfigScalar 2 }
		
--  1.3.6.1.4.1.2011.5.25.240.1.17.3
		hwSMReadResultCode OBJECT-TYPE
			SYNTAX Integer32
			MAX-ACCESS read-only
			STATUS current
			DESCRIPTION
				"Description."
			::= { hwReadConfigScalar 3 }
		
--  1.3.6.1.4.1.2011.5.25.240.1.17.4
		hwSMReadResultDescription OBJECT-TYPE
			SYNTAX OCTET STRING
			MAX-ACCESS read-only
			STATUS current
			DESCRIPTION
				"Description."
			::= { hwReadConfigScalar 4 }
		
        
		-- 1.3.6.1.4.1.2011.5.25.240.2
		hwDsliteTraps OBJECT IDENTIFIER ::= { hwDsliteMIB 2 }
		
        
		-- 1.3.6.1.4.1.2011.5.25.240.2.1
		hwCGNRoutingTableAlarm NOTIFICATION-TYPE
			OBJECTS { hwCGNAlarmIpVersion }
			STATUS current
			DESCRIPTION 
				"Description."
			::= { hwDsliteTraps 1 }
		
--  Notification, triggered when routing table items reach the threshold.
        
		-- 1.3.6.1.4.1.2011.5.25.240.2.2
		hwCGNGloablV4SessionNumAlarm NOTIFICATION-TYPE
			OBJECTS { hwCGNAlarmSessionNum, hwVSUAlarmThreshold, hwVSUAlarmSlot, hwVSUAlarmCpu }
			STATUS current
			DESCRIPTION 
				"The object indicates the alarm generated when the total number of session connections exceeds a specified threshold."
			::= { hwDsliteTraps 2 }
		
--  Notification, triggered when DS-Lite connections reach the threshold.
        
		-- 1.3.6.1.4.1.2011.5.25.240.2.3
		hwCGNUserSessionNumAlarm NOTIFICATION-TYPE
			OBJECTS { hwCGNAlarmProtocolType, hwCGNAlarmInstanceType, hwCGNAlarmInstanceName, hwCGNAlarmCpeIpAddr }
			STATUS current
			DESCRIPTION 
				"Description."
			::= { hwDsliteTraps 3 }
		
--  Notification, triggered when sessions of user reach the threshold.
        
		-- 1.3.6.1.4.1.2011.5.25.240.2.4
		hwCGNUserPortNumAlarm NOTIFICATION-TYPE
			OBJECTS { hwCGNAlarmProtocolType, hwCGNAlarmCpeIpAddr, hwCGNAlarmInstanceType, hwCGNAlarmInstanceName, hwCGNAlarmAddrGroupName, 
				hwVSUAlarmThreshold, hwCGNAlarmPortNum, hwVSUAlarmSlot, hwVSUAlarmCpu, hwCGNAlarmCid
				 }
			STATUS current
			DESCRIPTION 
				"The object indicates the alarm generated when user port usage exceeds a specified threshold."
			::= { hwDsliteTraps 4 }
		
--  Notification, triggered when used NAT ports of user reach the threshold.
        
		-- 1.3.6.1.4.1.2011.5.25.240.2.5
		hwCGNPortforwardingAlarm NOTIFICATION-TYPE
			OBJECTS { hwCGNAlarmInstanceType, hwCGNAlarmInstanceName, hwCGNAlarmAddrGroupName, hwCGNAlarmProtocolType }
			STATUS current
			DESCRIPTION 
				"Description."
			::= { hwDsliteTraps 5 }
		
--  Notification, triggered when Portforwarding reach the threshold.
        
		-- 1.3.6.1.4.1.2011.5.25.240.2.6
		hwCGNDsliteTunnelNumAlarm NOTIFICATION-TYPE
			STATUS current
			DESCRIPTION 
				"Description."
			::= { hwDsliteTraps 6 }
		
--  Notification, triggered when dslite tunnel reach the threshold.
        
		-- 1.3.6.1.4.1.2011.5.25.240.2.7
		hwCGNPortUsageOfAddrGroupAlarm NOTIFICATION-TYPE
			OBJECTS { hwCGNAlarmInstanceType, hwCGNAlarmInstanceName, hwCGNAlarmAddrGroupName }
			STATUS current
			DESCRIPTION 
				"Description."
			::= { hwDsliteTraps 7 }
		
--  Notification, triggered when dslite tunnel reach the threshold.
        
		-- 1.3.6.1.4.1.2011.5.25.240.2.8
		hwCGNPortUsageOfSpecificIpAlarm NOTIFICATION-TYPE
			OBJECTS { hwCGNAlarmAddrGroupName, hwCGNAlarmSpecificIP, hwCGNAlarmInstanceType, hwCGNAlarmInstanceName, hwVSUAlarmThreshold, 
				hwCGNAlarmPortNum, hwVSUAlarmSlot, hwVSUAlarmCpu }
			STATUS current
			DESCRIPTION 
				"Description."
			::= { hwDsliteTraps 8 }
		
--  Notification, triggered when used NAT ports of address group reach the threshold.
        
		-- 1.3.6.1.4.1.2011.5.25.240.2.9
		hwCGNUserDiscardNumAlarm NOTIFICATION-TYPE
			OBJECTS { hwCGNAlarmInstanceType, hwCGNAlarmInstanceName, hwCGNAlarmCpeIpAddr }
			STATUS current
			DESCRIPTION 
				"Description."
			::= { hwDsliteTraps 9 }
		
--  Notification, triggered when used NAT ports of address group reach the threshold.
        
		-- 1.3.6.1.4.1.2011.5.25.240.2.10
		hwCGNInstanceDiscardNumAlarm NOTIFICATION-TYPE
			OBJECTS { hwCGNAlarmInstanceType, hwCGNAlarmInstanceName }
			STATUS current
			DESCRIPTION 
				"Description."
			::= { hwDsliteTraps 10 }
		
--  Notification, triggered when used NAT ports of address group reach the threshold.
        
		-- 1.3.6.1.4.1.2011.5.25.240.2.11
		hwCGNGloablV4SessionNumResumeAlarm NOTIFICATION-TYPE
			OBJECTS { hwCGNAlarmSessionNum, hwVSUAlarmThreshold, hwVSUAlarmSlot, hwVSUAlarmCpu }
			STATUS current
			DESCRIPTION 
				"The object indicates the alarm generated when the number of IPV4 sessions exceeds a specified threshold on a NAT/DS-Lite/NAT64 board."
			::= { hwDsliteTraps 11 }
		
        
		-- 1.3.6.1.4.1.2011.5.25.240.2.12
		hwCGNUserPortNumResumeAlarm NOTIFICATION-TYPE
			OBJECTS { hwCGNAlarmProtocolType, hwCGNAlarmCpeIpAddr, hwCGNAlarmInstanceType, hwCGNAlarmInstanceName, hwCGNAlarmAddrGroupName, 
				hwVSUAlarmThreshold, hwCGNAlarmPortNum, hwVSUAlarmSlot, hwVSUAlarmCpu, hwCGNAlarmCid
				 }
			STATUS current
			DESCRIPTION 
				"The object indicates the clear alarm generated when CGN user port usage falls to a normal range."
			::= { hwDsliteTraps 12 }
		
        
		-- 1.3.6.1.4.1.2011.5.25.240.2.13
		hwCGNPortUsageOfSpecificIpResumeAlarm NOTIFICATION-TYPE
			OBJECTS { hwCGNAlarmAddrGroupName, hwCGNAlarmSpecificIP, hwCGNAlarmInstanceType, hwCGNAlarmInstanceName, hwVSUAlarmThreshold, 
				hwCGNAlarmPortNum, hwVSUAlarmSlot, hwVSUAlarmCpu }
			STATUS current
			DESCRIPTION 
				"Description."
			::= { hwDsliteTraps 13 }
		
--  Notification, triggered when used NAT ports of address group reach the threshold.
        
		-- 1.3.6.1.4.1.2011.5.25.240.2.14
		hwCGNPortUsageOfSpecificIpPreAlarm NOTIFICATION-TYPE
			OBJECTS { hwCGNAlarmAddrGroupName, hwCGNAlarmInstanceType, hwCGNAlarmInstanceName, hwVSUAlarmThreshold, hwCGNAlarmPortNum, 
				hwVSUAlarmSlot, hwVSUAlarmCpu }
			STATUS current
			DESCRIPTION 
				"The object indicates the alarm generated when the number of pre-allocated ports based on a public network address pool reaches a specified threshold."
			::= { hwDsliteTraps 14 }
		
--  Notification, triggered when used NAT ports of address group reach the threshold.
        
		-- 1.3.6.1.4.1.2011.5.25.240.2.15
		hwCGNPortUsageOfSpecificIpPreResumeAlarm NOTIFICATION-TYPE
			OBJECTS { hwCGNAlarmAddrGroupName, hwCGNAlarmInstanceType, hwCGNAlarmInstanceName, hwVSUAlarmThreshold, hwCGNAlarmPortNum, 
				hwVSUAlarmSlot, hwVSUAlarmCpu }
			STATUS current
			DESCRIPTION 
				"The object indicates the clear alarm generated when the number pre-allocated ports based on a public network address pool falls to a normal range."
			::= { hwDsliteTraps 15 }
		
--  Notification, triggered when used NAT ports of address group reach the threshold.
        
		-- 1.3.6.1.4.1.2011.5.25.240.2.16
		hwCGNStaticMappingCopyConfigEvent NOTIFICATION-TYPE
			OBJECTS { hwSMCopyFtpServer, hwSMCopySrcFileName, hwSMCopyState, hwSMCopyTimeStarted, hwSMCopyTimeCompleted, 
				hwSMCopyFailCause }
			STATUS current
			DESCRIPTION 
				"Description."
			::= { hwDsliteTraps 16 }
		
        
		-- 1.3.6.1.4.1.2011.5.25.240.2.17
		hwCGNStaticMappingReadConfigEvent NOTIFICATION-TYPE
			OBJECTS { hwSMReadResultFileName, hwSMReadResultCode, hwSMReadResultDescription }
			STATUS current
			DESCRIPTION 
				"Description."
			::= { hwDsliteTraps 17 }
		
        
		-- 1.3.6.1.4.1.2011.5.25.240.2.18
		hwCGNDeviceSessionNumAlarm NOTIFICATION-TYPE
			OBJECTS { hwCGNAlarmDeviceThreshold, hwCGNAlarmTotalSessionNum }
			STATUS current
			DESCRIPTION 
				"Description."
			::= { hwDsliteTraps 18 }
		
        
		-- 1.3.6.1.4.1.2011.5.25.240.2.19
		hwCGNDeviceSessionNumResumeAlarm NOTIFICATION-TYPE
			OBJECTS { hwCGNAlarmDeviceThreshold, hwCGNAlarmTotalSessionNum }
			STATUS current
			DESCRIPTION 
				"Description."
			::= { hwDsliteTraps 19 }
		
--  1.3.6.1.4.1.2011.5.25.240.2.20
		-- 1.3.6.1.4.1.2011.5.25.240.2.20
		hwCGNUserPortExhaustAlarm NOTIFICATION-TYPE
			OBJECTS { hwCGNAlarmAddrGroupName, hwCGNAlarmInstanceType, hwCGNAlarmInstanceName, hwCGNAlarmPortNum, hwVSUAlarmSlot, 
				hwVSUAlarmCpu }
			STATUS current
			DESCRIPTION 
				"User port exhaust alarm."
			::= { hwDsliteTraps 20 }
		
--  1.3.6.1.4.1.2011.5.25.240.2.21
		-- 1.3.6.1.4.1.2011.5.25.240.2.21
		hwCGNUserPortExhaustResumeAlarm NOTIFICATION-TYPE
			OBJECTS { hwCGNAlarmAddrGroupName, hwCGNAlarmInstanceType, hwCGNAlarmInstanceName, hwCGNAlarmPortNum, hwVSUAlarmSlot, 
				hwVSUAlarmCpu }
			STATUS current
			DESCRIPTION 
				"User port exhaust resume alarm."
			::= { hwDsliteTraps 21 }
		
--  1.3.6.1.4.1.2011.5.25.240.2.22
		-- 1.3.6.1.4.1.2011.5.25.240.2.22
		hwCGNSessionExhaustAlarm NOTIFICATION-TYPE
			OBJECTS { hwCGNAlarmSessionNum, hwVSUAlarmSlot, hwVSUAlarmCpu }
			STATUS current
			DESCRIPTION 
				"The object indicates the alarm generated when system session connections are used up."
			::= { hwDsliteTraps 22 }
		
--  1.3.6.1.4.1.2011.5.25.240.2.23	
		-- 1.3.6.1.4.1.2011.5.25.240.2.23
		hwCGNSessionExhaustResumeAlarm NOTIFICATION-TYPE
			OBJECTS { hwCGNAlarmSessionNum, hwVSUAlarmSlot, hwVSUAlarmCpu }
			STATUS current
			DESCRIPTION 
				"The object indicates the alarm generated when the session connections become available again."
			::= { hwDsliteTraps 23 }
		
--  1.3.6.1.4.1.2011.5.25.240.2.24	
		-- 1.3.6.1.4.1.2011.5.25.240.2.24
		hwCGNSpecificIpExhaustAlarm NOTIFICATION-TYPE
			OBJECTS { hwCGNAlarmAddrGroupName, hwCGNAlarmInstanceType, hwCGNAlarmInstanceName, hwCGNAlarmPortNum, hwVSUAlarmSlot, 
				hwVSUAlarmCpu }
			STATUS current
			DESCRIPTION 
				"The object indicates the alarm generated when ports in a public address pool are used up."
			::= { hwDsliteTraps 24 }
		
--  1.3.6.1.4.1.2011.5.25.240.2.25							
		-- 1.3.6.1.4.1.2011.5.25.240.2.25
		hwCGNSpecificIpExhaustResumeAlarm NOTIFICATION-TYPE
			OBJECTS { hwCGNAlarmAddrGroupName, hwCGNAlarmInstanceType, hwCGNAlarmInstanceName, hwCGNAlarmPortNum, hwVSUAlarmSlot, 
				hwVSUAlarmCpu }
			STATUS current
			DESCRIPTION 
				"The object indicates the clear alarm generated when the ports in a public address pool become available again."
			::= { hwDsliteTraps 25 }
		
		-- 1.3.6.1.4.1.2011.5.25.240.2.26
		hwCGNUserIPNumAlarm NOTIFICATION-TYPE
			OBJECTS { hwCGNAlarmAddrGroupName, hwCGNAlarmInstanceType, hwCGNAlarmInstanceName, hwVSUAlarmThreshold, hwCGNAlarmIPNum, 
				hwVSUAlarmSlot, hwVSUAlarmCpu }
			STATUS current
			DESCRIPTION 
				"The object indicates the alarm generated when usage of the NAT64 no-PAT address pool reaches a specified threshold."
			::= { hwDsliteTraps 26 }
		
		-- 1.3.6.1.4.1.2011.5.25.240.2.27
		hwCGNUserIPNumResumeAlarm NOTIFICATION-TYPE
			OBJECTS { hwCGNAlarmAddrGroupName, hwCGNAlarmInstanceType, hwCGNAlarmInstanceName, hwVSUAlarmThreshold, hwCGNAlarmIPNum, 
				hwVSUAlarmSlot, hwVSUAlarmCpu }
			STATUS current
			DESCRIPTION 
				"The object indicates the clear alarm generated when usage of the NAT64 no-PAT address pool falls to a normal range."
			::= { hwDsliteTraps 27 }  
			
		-- 1.3.6.1.4.1.2011.5.25.240.2.28
		hwCGNNoPatAddrGroupExhaustAlarm NOTIFICATION-TYPE
			OBJECTS { hwCGNAlarmAddrGroupName, hwCGNAlarmInstanceType, hwCGNAlarmInstanceName, hwCGNAlarmIPNum, 
				hwVSUAlarmSlot, hwVSUAlarmCpu }
			STATUS current
			DESCRIPTION 
				"The object indicates the alarm generated when addresses in a no-PAT address pool are used up."
			::= { hwDsliteTraps 28 }  
			
		-- 1.3.6.1.4.1.2011.5.25.240.2.29
		hwCGNNoPatAddrGroupExhaustResumeAlarm NOTIFICATION-TYPE
			OBJECTS { hwCGNAlarmAddrGroupName, hwCGNAlarmInstanceType, hwCGNAlarmInstanceName, hwCGNAlarmIPNum, 
				hwVSUAlarmSlot, hwVSUAlarmCpu }
			STATUS current
			DESCRIPTION 
				"The object indicates the clear alarm generated when addresses in a no-PAT address pool become available again."
			::= { hwDsliteTraps 29 } 
                                        
       	-- 1.3.6.1.4.1.2011.5.25.240.2.30
		hwCGNNoPatAddrGroupThresholdAlarm NOTIFICATION-TYPE
			OBJECTS { hwCGNAlarmAddrGroupName, hwCGNAlarmInstanceType, hwCGNAlarmInstanceName, hwCGNAlarmIPNum, 
				hwVSUAlarmThreshold,hwVSUAlarmSlot, hwVSUAlarmCpu }
			STATUS current
			DESCRIPTION 
				"The object indicates the alarm generated when address usage of the no-PAT address pool reaches a specified alarm threshold."
			::= { hwDsliteTraps 30 }     
			
		  	-- 1.3.6.1.4.1.2011.5.25.240.2.31
		 hwCGNNoPatAddrGroupThresholdResumeAlarm NOTIFICATION-TYPE
			OBJECTS { hwCGNAlarmAddrGroupName, hwCGNAlarmInstanceType, hwCGNAlarmInstanceName, hwCGNAlarmIPNum, 
				hwVSUAlarmThreshold, hwVSUAlarmSlot, hwVSUAlarmCpu }
			STATUS current
			DESCRIPTION 
				"The object indicates the clear alarm generated when no-PAT of IP addresses in the address pool usage reaches a specified threshold is cleared."
			::= { hwDsliteTraps 31 } 


		-- 1.3.6.1.4.1.2011.5.25.240.2.32
		hwCGNAccessLimitThresholdAlarm NOTIFICATION-TYPE
			OBJECTS {hwCGNAlarmAddrGroupName,hwCGNAlarmInstanceType, hwCGNAlarmInstanceName,hwVSUAlarmThreshold,hwCGNAlarmAccessUserNum,
				hwVSUAlarmSlot, hwVSUAlarmCpu }
			STATUS current
			DESCRIPTION 
				"The number of access-users reach the threshold"
			::= { hwDsliteTraps 32 }


		-- 1.3.6.1.4.1.2011.5.25.240.2.33
		hwCGNAccessLimitThresholdResumeAlarm NOTIFICATION-TYPE
			OBJECTS {hwCGNAlarmAddrGroupName,hwCGNAlarmInstanceType, hwCGNAlarmInstanceName,hwVSUAlarmThreshold,hwCGNAlarmAccessUserNum,
				hwVSUAlarmSlot, hwVSUAlarmCpu }
			STATUS current
			DESCRIPTION 
				"The number of access-users within normal range"
			::= { hwDsliteTraps 33 }


		-- 1.3.6.1.4.1.2011.5.25.240.2.34
		hwCGNAccessLimitExhaustAlarm NOTIFICATION-TYPE
			OBJECTS {hwCGNAlarmAddrGroupName,hwCGNAlarmInstanceType, hwCGNAlarmInstanceName,hwCGNAlarmAccessUserNum ,
				hwVSUAlarmSlot, hwVSUAlarmCpu }
			STATUS current
			DESCRIPTION 
				"The access-users exhaust alarm"
			::= { hwDsliteTraps 34 }

		-- 1.3.6.1.4.1.2011.5.25.240.2.35
		hwCGNAccessLimitExhaustResumeAlarm NOTIFICATION-TYPE
			OBJECTS {hwCGNAlarmAddrGroupName,hwCGNAlarmInstanceType, hwCGNAlarmInstanceName,hwCGNAlarmAccessUserNum ,
				hwVSUAlarmSlot, hwVSUAlarmCpu }
			STATUS current
			DESCRIPTION 
				"The access-users exhaust resume alarm"
			::= { hwDsliteTraps 35 }

		-- 1.3.6.1.4.1.2011.5.25.240.2.36
		hwCGNUserTableExhaustAlarm NOTIFICATION-TYPE
			OBJECTS { hwCGNAlarmUserTableNum, hwVSUAlarmSlot, hwVSUAlarmCpu }
			STATUS current
			DESCRIPTION 
				"The object indicates the alarm generated when user tables are used up."
			::= { hwDsliteTraps 36 }  
			
		-- 1.3.6.1.4.1.2011.5.25.240.2.37
		hwCGNUserTableExhaustResumeAlarm NOTIFICATION-TYPE
			OBJECTS { hwCGNAlarmUserTableNum, hwVSUAlarmSlot, hwVSUAlarmCpu }
			STATUS current
			DESCRIPTION 
				"The object indicates the clear alarm generated when user tables become available again."
			::= { hwDsliteTraps 37 } 
                                        
       	-- 1.3.6.1.4.1.2011.5.25.240.2.38
		hwCGNUserTableThresholdAlarm NOTIFICATION-TYPE
			OBJECTS { hwCGNAlarmUserTableNum, hwVSUAlarmThreshold, hwVSUAlarmSlot, hwVSUAlarmCpu }
			STATUS current
			DESCRIPTION 
				"The object indicates the alarm generated when the number of created user tables reaches a specified threshold."
			::= { hwDsliteTraps 38 }     
			
		  	-- 1.3.6.1.4.1.2011.5.25.240.2.39
		 hwCGNUserTableThresholdResumeAlarm NOTIFICATION-TYPE
			OBJECTS { hwCGNAlarmUserTableNum, hwVSUAlarmThreshold, hwVSUAlarmSlot, hwVSUAlarmCpu }
			STATUS current
			DESCRIPTION 
				"The object indicates the clear alarm generated when the number of user tables falls to a normal range."
			::= { hwDsliteTraps 39 } 

		-- 1.3.6.1.4.1.2011.5.25.240.2.40
		hwVSUDevicePerformanceAlarm NOTIFICATION-TYPE
			OBJECTS { hwVSUAlarmThreshold, hwVSUAlarmbpsRateInUse, hwVSUAlarmMbpsRate, hwVSUAlarmppsRate, hwVSUAlarmCpuUsage, 
				hwVSUAlarmSlot, hwVSUAlarmCpu }
			STATUS current
			DESCRIPTION 
				"The object indicates the alarm generated when CPU forwarding performance exceeds a specified threshold."
			::= { hwDsliteTraps 40 }
		
		-- 1.3.6.1.4.1.2011.5.25.240.2.41
		hwVSUDevicePerformanceResumeAlarm NOTIFICATION-TYPE
			OBJECTS { hwVSUAlarmThreshold, hwVSUAlarmbpsRateInUse, hwVSUAlarmMbpsRate, hwVSUAlarmppsRate, hwVSUAlarmCpuUsage, 
				hwVSUAlarmSlot, hwVSUAlarmCpu }
			STATUS current
			DESCRIPTION 
				"The object indicates the clear alarm generated when CPU performance is restored."
			::= { hwDsliteTraps 41 }

		-- 1.3.6.1.4.1.2011.5.25.240.2.42
		hwCGNGlobalPoolPreAlarm NOTIFICATION-TYPE
			OBJECTS { hwCGNAlarmAddrGroupName, hwVSUAlarmThreshold, hwCGNAlarmUsedIPNum }
			STATUS current
			DESCRIPTION 
				"The object indicates the alarm generated when IP address usage of the global public IP address pool reaches a specified threshold."
			::= { hwDsliteTraps 42 }
			
		-- 1.3.6.1.4.1.2011.5.25.240.2.43
		hwCGNGlobalPoolPreResumeAlarm NOTIFICATION-TYPE
			OBJECTS { hwCGNAlarmAddrGroupName, hwVSUAlarmThreshold, hwCGNAlarmUsedIPNum }
			STATUS current
			DESCRIPTION 
				"The object indicates the clear alarm generated when IP address usage of the global public IP address pool falls to a normal range."
			::= { hwDsliteTraps 43 }
			
		-- 1.3.6.1.4.1.2011.5.25.240.2.44
		hwCGNGlobalPoolExhaustAlarm NOTIFICATION-TYPE
			OBJECTS { hwCGNAlarmAddrGroupName, hwCGNAlarmUsedIPNum }
			STATUS current
			DESCRIPTION 
				"The object indicates the alarm generated when IP addresses in the global public network address pool are used up."
			::= { hwDsliteTraps 44 }
			
		-- 1.3.6.1.4.1.2011.5.25.240.2.45
		hwCGNGlobalPoolExhaustResumeAlarm NOTIFICATION-TYPE
			OBJECTS { hwCGNAlarmAddrGroupName, hwCGNAlarmUsedIPNum }
			STATUS current
			DESCRIPTION 
				"The object indicates the clear alarm generated when IP addresses in the global public network address pool become available."
			::= { hwDsliteTraps 45 }			
			
		-- 1.3.6.1.4.1.2011.5.25.240.2.46
		hwCGNDAPPoolApplyFail NOTIFICATION-TYPE
			OBJECTS { hwCGNAlarmPoolName, hwCGNAlarmSubnet, hwCGNAlarmMask, hwCGNAlarmReason }
			STATUS current
			DESCRIPTION 
				"Fail to apply for the subnet."
			::= { hwDsliteTraps 46 }		
			
		-- 1.3.6.1.4.1.2011.5.25.240.2.47
		hwCGNDAPPoolReleaseFail NOTIFICATION-TYPE
			OBJECTS { hwCGNAlarmPoolName, hwCGNAlarmSubnet, hwCGNAlarmMask, hwCGNAlarmReason }
			STATUS current
			DESCRIPTION 
				"Fail to release the subnet."
			::= { hwDsliteTraps 47 }
			
		-- 1.3.6.1.4.1.2011.5.25.240.2.48
		hwCGNDAPPoolSubnetFull NOTIFICATION-TYPE
			OBJECTS { hwCGNAlarmPoolName }
			STATUS current
			DESCRIPTION 
				"The number of subnet in the IP global pool is exhausted."
			::= { hwDsliteTraps 48 }			
			
		-- 1.3.6.1.4.1.2011.5.25.240.2.49
		hwCGNDAPDeviceSubnetFull NOTIFICATION-TYPE
			STATUS current
			DESCRIPTION 
				"The number of subnet in the device is exhausted."
			::= { hwDsliteTraps 49 }			
			
		-- 1.3.6.1.4.1.2011.5.25.240.2.50
		hwCGNInstanceDAPPoolApplyFail NOTIFICATION-TYPE
			OBJECTS { hwCGNAlarmPoolName, hwCGNAlarmInstanceType, hwCGNAlarmInstanceName, hwCGNAlarmSubnet, hwCGNAlarmMask }
			STATUS current
			DESCRIPTION 
				"The object indicates the alarm generated when an attempt to apply for an address range in a global address pool fails."
			::= { hwDsliteTraps 50 }
			
		-- 1.3.6.1.4.1.2011.5.25.240.2.51
		hwCGNInstanceDAPPoolSubnetFull NOTIFICATION-TYPE
			OBJECTS { hwCGNAlarmPoolName, hwCGNAlarmInstanceType, hwCGNAlarmInstanceName }
			STATUS current
			DESCRIPTION 
				"The number of subnet in the IP pool is exhausted."
			::= { hwDsliteTraps 51 }	
			
		-- 1.3.6.1.4.1.2011.5.25.240.2.52
		hwCGNSessionSpecOverloadAlarm NOTIFICATION-TYPE
			OBJECTS { hwVSUAlarmSlot, hwVSUAlarmCpu, hwCGNAlarmSessionNum }
			STATUS current
			DESCRIPTION 
				"Session spec overload alarm."
			::= { hwDsliteTraps 52 }
		
		-- 1.3.6.1.4.1.2011.5.25.240.2.53
		hwCGNSessionSpecOverloadResumeAlarm NOTIFICATION-TYPE
			OBJECTS { hwVSUAlarmSlot, hwVSUAlarmCpu, hwCGNAlarmSessionNum }
			STATUS current
			DESCRIPTION 
				"Session spec overload resume alarm."
			::= { hwDsliteTraps 53 }	
			
		-- 1.3.6.1.4.1.2011.5.25.240.2.54
		hwCGNGloablV4SessionNumBoardAlarm NOTIFICATION-TYPE
			OBJECTS { hwCGNAlarmSessionNum, hwVSUAlarmThreshold, hwVSUAlarmBoardName, hwVSUAlarmCpu }
			STATUS current
			DESCRIPTION 
				"The object indicates the alarm generated when the total number of session connections exceeds a specified threshold."
			::= { hwDsliteTraps 54 }
			
		-- 1.3.6.1.4.1.2011.5.25.240.2.55
		hwCGNGloablV4SessionNumBoardResumeAlarm NOTIFICATION-TYPE
			OBJECTS { hwCGNAlarmSessionNum, hwVSUAlarmThreshold, hwVSUAlarmBoardName, hwVSUAlarmCpu }
			STATUS current
			DESCRIPTION 
				"The object indicates the clear alarm generated when the total number of session connections is restored."
			::= { hwDsliteTraps 55 }	
			
		-- 1.3.6.1.4.1.2011.5.25.240.2.56
		hwCGNSessionExhaustBoardAlarm NOTIFICATION-TYPE
			OBJECTS { hwCGNAlarmSessionNum, hwVSUAlarmBoardName, hwVSUAlarmCpu }
			STATUS current
			DESCRIPTION 
				"The object indicates the alarm generated when system session connections are used up."
			::= { hwDsliteTraps 56 }	
			
		-- 1.3.6.1.4.1.2011.5.25.240.2.57
		hwCGNSessionExhaustBoardResumeAlarm NOTIFICATION-TYPE
			OBJECTS { hwCGNAlarmSessionNum, hwVSUAlarmBoardName, hwVSUAlarmCpu }
			STATUS current
			DESCRIPTION 
				"The object indicates the alarm generated when the session connections become available again."
			::= { hwDsliteTraps 57 }			
			
		-- 1.3.6.1.4.1.2011.5.25.240.2.58
		hwCGNNoPatAddrGroupExhaustBoardAlarm NOTIFICATION-TYPE
			OBJECTS { hwCGNAlarmAddrGroupName, hwCGNAlarmInstanceType, hwCGNAlarmInstanceName, hwCGNAlarmIPNum, 
				hwVSUAlarmBoardName, hwVSUAlarmCpu }
			STATUS current
			DESCRIPTION 
				"The object indicates the alarm generated when addresses in a no-PAT address pool are used up."
			::= { hwDsliteTraps 58 } 	

		-- 1.3.6.1.4.1.2011.5.25.240.2.59
		hwCGNNoPatAddrGroupExhaustBoardResumeAlarm NOTIFICATION-TYPE
			OBJECTS { hwCGNAlarmAddrGroupName, hwCGNAlarmInstanceType, hwCGNAlarmInstanceName, hwCGNAlarmIPNum, 
				hwVSUAlarmBoardName, hwVSUAlarmCpu }
			STATUS current
			DESCRIPTION 
				"Addresses in the no-pat public address pool became available"
			::= { hwDsliteTraps 59 } 	

       	-- 1.3.6.1.4.1.2011.5.25.240.2.60
		hwCGNNoPatAddrGroupThresholdBoardAlarm NOTIFICATION-TYPE
			OBJECTS { hwCGNAlarmAddrGroupName, hwCGNAlarmInstanceType, hwCGNAlarmInstanceName, hwCGNAlarmIPNum, 
				hwVSUAlarmThreshold,hwVSUAlarmBoardName, hwVSUAlarmCpu }
			STATUS current
			DESCRIPTION 
				"The object indicates the clear alarm generated when addresses in a no-PAT address pool become available again."
			::= { hwDsliteTraps 60 }  

		-- 1.3.6.1.4.1.2011.5.25.240.2.61
		 hwCGNNoPatAddrGroupThresholdBoardResumeAlarm NOTIFICATION-TYPE
			OBJECTS { hwCGNAlarmAddrGroupName, hwCGNAlarmInstanceType, hwCGNAlarmInstanceName, hwCGNAlarmIPNum, 
				hwVSUAlarmThreshold, hwVSUAlarmBoardName, hwVSUAlarmCpu }
			STATUS current
			DESCRIPTION 
				"The object indicates the clear alarm generated when no-PAT of IP addresses in the address pool usage reaches a specified threshold is cleared."
			::= { hwDsliteTraps 61 }  		

		-- 1.3.6.1.4.1.2011.5.25.240.2.62
		hwCGNPortUsageOfSpecificIpPreBoardAlarm NOTIFICATION-TYPE
			OBJECTS { hwCGNAlarmAddrGroupName, hwCGNAlarmInstanceType, hwCGNAlarmInstanceName, hwVSUAlarmThreshold, hwCGNAlarmPortNum, 
				hwVSUAlarmBoardName, hwVSUAlarmCpu }
			STATUS current
			DESCRIPTION 
				"The object indicates the alarm generated when the number of pre-allocated ports based on a public network address pool reaches a specified threshold."
			::= { hwDsliteTraps 62 }	

		-- 1.3.6.1.4.1.2011.5.25.240.2.63
		hwCGNPortUsageOfSpecificIpPreBoardResumeAlarm NOTIFICATION-TYPE
			OBJECTS { hwCGNAlarmAddrGroupName, hwCGNAlarmInstanceType, hwCGNAlarmInstanceName, hwVSUAlarmThreshold, hwCGNAlarmPortNum, 
				hwVSUAlarmBoardName, hwVSUAlarmCpu }
			STATUS current
			DESCRIPTION 
				"The object indicates the clear alarm generated when the number pre-allocated ports based on a public network address pool falls to a normal range."
			::= { hwDsliteTraps 63 }	

		-- 1.3.6.1.4.1.2011.5.25.240.2.64
		hwCGNSpecificIpExhaustBoardAlarm NOTIFICATION-TYPE
			OBJECTS { hwCGNAlarmAddrGroupName, hwCGNAlarmInstanceType, hwCGNAlarmInstanceName, hwCGNAlarmPortNum, hwVSUAlarmBoardName, 
				hwVSUAlarmCpu }
			STATUS current
			DESCRIPTION 
				"The object indicates the alarm generated when ports in a public address pool are used up."
			::= { hwDsliteTraps 64 }			
			
		-- 1.3.6.1.4.1.2011.5.25.240.2.65
		hwCGNSpecificIpExhaustBoardResumeAlarm NOTIFICATION-TYPE
			OBJECTS { hwCGNAlarmAddrGroupName, hwCGNAlarmInstanceType, hwCGNAlarmInstanceName, hwCGNAlarmPortNum, hwVSUAlarmBoardName, 
				hwVSUAlarmCpu }
			STATUS current
			DESCRIPTION 
				"The object indicates the clear alarm generated when the ports in a public address pool become available again."
			::= { hwDsliteTraps 65 }
			
		-- 1.3.6.1.4.1.2011.5.25.240.2.66
		hwCGNUserPortNumBoardAlarm NOTIFICATION-TYPE
			OBJECTS { hwCGNAlarmProtocolType, hwCGNAlarmCpeIpAddr, hwCGNAlarmInstanceType, hwCGNAlarmInstanceName, hwCGNAlarmAddrGroupName, 
				hwVSUAlarmThreshold, hwCGNAlarmPortNum, hwVSUAlarmBoardName, hwVSUAlarmCpu, hwCGNAlarmCid
				 }
			STATUS current
			DESCRIPTION 
				"The object indicates the alarm generated when port usage of CGN users exceeds a specified threshold."
			::= { hwDsliteTraps 66 }		

		-- 1.3.6.1.4.1.2011.5.25.240.2.67
		hwCGNUserPortNumBoardResumeAlarm NOTIFICATION-TYPE
			OBJECTS { hwCGNAlarmProtocolType, hwCGNAlarmCpeIpAddr, hwCGNAlarmInstanceType, hwCGNAlarmInstanceName, hwCGNAlarmAddrGroupName, 
				hwVSUAlarmThreshold, hwCGNAlarmPortNum, hwVSUAlarmBoardName, hwVSUAlarmCpu, hwCGNAlarmCid
				 }
			STATUS current
			DESCRIPTION 
				"The object indicates the clear alarm generated when CGN user port usage falls to a normal range."
			::= { hwDsliteTraps 67 }	

		-- 1.3.6.1.4.1.2011.5.25.240.2.68
		hwCGNUserTableExhaustBoardAlarm NOTIFICATION-TYPE
			OBJECTS { hwCGNAlarmUserTableNum, hwVSUAlarmBoardName, hwVSUAlarmCpu }
			STATUS current
			DESCRIPTION 
				"The object indicates the alarm generated when user tables are used up."
			::= { hwDsliteTraps 68 }  

		-- 1.3.6.1.4.1.2011.5.25.240.2.69
		hwCGNUserTableExhaustBoardResumeAlarm NOTIFICATION-TYPE
			OBJECTS { hwCGNAlarmUserTableNum, hwVSUAlarmBoardName, hwVSUAlarmCpu }
			STATUS current
			DESCRIPTION 
				"The object indicates the clear alarm generated when user tables become available again."
			::= { hwDsliteTraps 69 } 

       	-- 1.3.6.1.4.1.2011.5.25.240.2.70
		hwCGNUserTableThresholdBoardAlarm NOTIFICATION-TYPE
			OBJECTS { hwCGNAlarmUserTableNum, hwVSUAlarmThreshold, hwVSUAlarmBoardName, hwVSUAlarmCpu }
			STATUS current
			DESCRIPTION 
				"The object indicates the alarm generated when the number of created user tables reaches a specified threshold."
			::= { hwDsliteTraps 70 } 

		  	-- 1.3.6.1.4.1.2011.5.25.240.2.71
		 hwCGNUserTableThresholdBoardResumeAlarm NOTIFICATION-TYPE
			OBJECTS { hwCGNAlarmUserTableNum, hwVSUAlarmThreshold, hwVSUAlarmBoardName, hwVSUAlarmCpu }
			STATUS current
			DESCRIPTION 
				"The object indicates the clear alarm generated when the number of user tables falls to a normal range."
			::= { hwDsliteTraps 71 } 	

            -- 1.3.6.1.4.1.2011.5.25.240.2.72
		hwVSUDevicePerformanceBoardAlarm NOTIFICATION-TYPE
			OBJECTS { hwVSUAlarmThreshold, hwVSUAlarmbpsRateInUse, hwVSUAlarmMbpsRate, hwVSUAlarmppsRate, hwVSUAlarmCpuUsage, 
				hwVSUAlarmBoardName, hwVSUAlarmCpu }
			STATUS current
			DESCRIPTION 
				"The object indicates the alarm generated when CPU forwarding performance exceeds a specified threshold."
			::= { hwDsliteTraps 72 }
		          
			          
			-- 1.3.6.1.4.1.2011.5.25.240.2.73
		hwVSUDevicePerformanceBoardResumeAlarm NOTIFICATION-TYPE
			OBJECTS { hwVSUAlarmThreshold, hwVSUAlarmbpsRateInUse, hwVSUAlarmMbpsRate, hwVSUAlarmppsRate, hwVSUAlarmCpuUsage, 
				hwVSUAlarmBoardName, hwVSUAlarmCpu }
			STATUS current
			DESCRIPTION 
				"The object indicates the clear alarm generated when CPU performance is restored."
			::= { hwDsliteTraps 73 }	

			-- 1.3.6.1.4.1.2011.5.25.240.2.76
		hwCGNRadiusSpecificAddressUserNumFullAlarm NOTIFICATION-TYPE
			OBJECTS { hwCGNAlarmIPNum }
			STATUS current
			DESCRIPTION 
				" The number of radius-specific-address users reaches the upper limit."
			::= { hwDsliteTraps 76 }

			-- 1.3.6.1.4.1.2011.5.25.240.2.77
		hwCGNRadiusSpecificAddressUserNumFullResumeAlarm NOTIFICATION-TYPE
			OBJECTS { hwCGNAlarmIPNum }
			STATUS current
			DESCRIPTION 
				"The number of radius-specific-address users is lower than the upper limit."
			::= { hwDsliteTraps 77 }	
	
		-- 1.3.6.1.4.1.2011.5.25.240.2.78
		hwVSUDevicePerformanceExhaustAlarm NOTIFICATION-TYPE
			OBJECTS { hwVSUAlarmbpsRateInUse, hwVSUAlarmMbpsRate, hwVSUAlarmppsRate, hwVSUAlarmCpuUsage, hwVSUAlarmBoardName, hwVSUAlarmCpu }
			STATUS current
			DESCRIPTION 
				"The object indicates the alarm generated when CPU forwarding performance is used up."
			::= { hwDsliteTraps 78 }

		
		-- 1.3.6.1.4.1.2011.5.25.240.2.79
		hwVSUDevicePerformanceExhaustResumeAlarm NOTIFICATION-TYPE
			OBJECTS { hwVSUAlarmbpsRateInUse, hwVSUAlarmMbpsRate, hwVSUAlarmppsRate, hwVSUAlarmCpuUsage, hwVSUAlarmBoardName, hwVSUAlarmCpu }
			STATUS current
			DESCRIPTION 
				"The object indicates the clear alarm generated when CPU forwarding performance becomes available."
			::= { hwDsliteTraps 79 }
            
		-- 1.3.6.1.4.1.2011.5.25.240.2.80
		hwCGNUserIPNumBoardAlarm NOTIFICATION-TYPE
			OBJECTS { hwCGNAlarmAddrGroupName, hwCGNAlarmInstanceType, hwCGNAlarmInstanceName, hwVSUAlarmThreshold, hwCGNAlarmIPNum, 
				hwVSUAlarmBoardName, hwVSUAlarmCpu }
			STATUS current
			DESCRIPTION 
				"The object indicates the alarm generated when address usage of NAT64 no-PAT address pool reaches a specified threshold in a virtual cluster scenario."
			::= { hwDsliteTraps 80 }
		
		-- 1.3.6.1.4.1.2011.5.25.240.2.81
		hwCGNUserIPNumBoardResumeAlarm NOTIFICATION-TYPE
			OBJECTS { hwCGNAlarmAddrGroupName, hwCGNAlarmInstanceType, hwCGNAlarmInstanceName, hwCGNAlarmIPNum, hwVSUAlarmThreshold, 
				hwVSUAlarmBoardName, hwVSUAlarmCpu }
			STATUS current
			DESCRIPTION 
				"The object indicates the clear alarm generated when address usage of NAT64 no-PAT address pool falls to a normal range in a virtual cluster scenario."
			::= { hwDsliteTraps 81 }
		
		-- 1.3.6.1.4.1.2011.5.25.240.2.82
		hwCGNServerMapNumThresholdAlarm NOTIFICATION-TYPE
			OBJECTS { hwCGNAlarmServerMapUsage, hwVSUAlarmThreshold, hwVSUAlarmBoardName, hwVSUAlarmCpu }
			STATUS current
			DESCRIPTION 
				"The object indicates the alarm generated when server-map usage reaches a specified threshold."
			::= { hwDsliteTraps 82 }
		
		-- 1.3.6.1.4.1.2011.5.25.240.2.83
		hwCGNServerMapNumThresholdResumeAlarm NOTIFICATION-TYPE
			OBJECTS { hwCGNAlarmServerMapUsage, hwVSUAlarmThreshold, hwVSUAlarmBoardName, hwVSUAlarmCpu }
			STATUS current
			DESCRIPTION 
				"The object indicates the clear alarm generated when server-map usage falls to a normal range."
			::= { hwDsliteTraps 83 }
		
		-- 1.3.6.1.4.1.2011.5.25.240.2.84
		hwCGNServerMapNumExhaustAlarm NOTIFICATION-TYPE
			OBJECTS { hwCGNAlarmServerMapUsage, hwVSUAlarmBoardName, hwVSUAlarmCpu }
			STATUS current
			DESCRIPTION 
				"The object indicates the alarm generated when server-map entries are used up."
			::= { hwDsliteTraps 84 }
		
		-- 1.3.6.1.4.1.2011.5.25.240.2.85
		hwCGNServerMapNumExhaustResumeAlarm NOTIFICATION-TYPE
			OBJECTS { hwCGNAlarmServerMapUsage, hwVSUAlarmBoardName, hwVSUAlarmCpu }
			STATUS current
			DESCRIPTION 
				"The object indicates the clear alarm generated when server-map entries become available again."
			::= { hwDsliteTraps 85 }
		
		-- 1.3.6.1.4.1.2011.5.25.240.2.86
		hwVSUServiceFaultAlarm NOTIFICATION-TYPE
			OBJECTS { hwVSUServiceFaultCode, hwVSUServiceFaultKey, hwVSUReasonDescription, hwVSUAlarmBoardName, hwVSUAlarmCpu }
			STATUS current
			DESCRIPTION 
				"The object indicates the alarm generated when a VSU service fails."
			::= { hwDsliteTraps 86 }
		
		-- 1.3.6.1.4.1.2011.5.25.240.2.87
		hwVSUServiceFaultResumeAlarm NOTIFICATION-TYPE
			OBJECTS { hwVSUServiceFaultCode, hwVSUServiceFaultKey, hwVSUReasonDescription, hwVSUAlarmBoardName, hwVSUAlarmCpu }
			STATUS current
			DESCRIPTION 
				"The object indicates the clear alarm generated when a VSU service becomes available again."
			::= { hwDsliteTraps 87 }
        
        -- 1.3.6.1.4.1.2011.5.25.240.2.88
		hwCGNGlobalPoolReleaseFail NOTIFICATION-TYPE
			OBJECTS { hwCGNAlarmPoolName, hwCGNAlarmSubnet, hwCGNAlarmMask, hwCGNAlarmReason }
			STATUS current
			DESCRIPTION 
				"Fail to release the subnet."
			::= { hwDsliteTraps 88 }
            
        -- 1.3.6.1.4.1.2011.5.25.240.2.89
		hwCGNDAPBackupConfigInconsistent NOTIFICATION-TYPE
			OBJECTS { hwCGNAlarmPoolName, hwCGNAlarmReason }
			STATUS current
			DESCRIPTION 
				"The global address pool configurations of the master and backup devices are inconsistent."
			::= { hwDsliteTraps 89 }

        -- 1.3.6.1.4.1.2011.5.25.240.2.90
		hwCGNDAPUPCPConfigInconsistent NOTIFICATION-TYPE
			OBJECTS { hwCGNAlarmPoolName }
			STATUS current
			DESCRIPTION 
				"The configuration of the local-up-id of the global address pool is inconsistent with the effective UPID on the CP."
			::= { hwDsliteTraps 90 }

        -- 1.3.6.1.4.1.2011.5.25.240.2.91
		hwCGNDAPPoolSectionSyncFail NOTIFICATION-TYPE
			OBJECTS { hwCGNAlarmPoolName, hwCGNAlarmSubnet, hwCGNAlarmMask, hwCGNAlarmReason }
			STATUS current
			DESCRIPTION 
				"The peer processing failed during the synchronization of address sections of the global address pool."
			::= { hwDsliteTraps 91 }

        -- 1.3.6.1.4.1.2011.5.25.240.2.92
		hwMAPBoardNotSupportAlarm NOTIFICATION-TYPE
			OBJECTS { hwMAPFrameId, hwMAPSlotId  }
			STATUS current
			DESCRIPTION 
				"The board does not support MAP."
			::= { hwDsliteTraps 92 }
			
        -- 1.3.6.1.4.1.2011.5.25.240.2.93
		hwMAPBoardNotSupportResume NOTIFICATION-TYPE
			OBJECTS { hwMAPFrameId, hwMAPSlotId  }
			STATUS current
			DESCRIPTION 
				"The alarm was cleared because the board that does not support MAP was removed or the MAP configuration was deleted from the board."
			::= { hwDsliteTraps 93 }

        -- 1.3.6.1.4.1.2011.5.25.240.2.94
		hwVSMBoardNotSupportAlarm NOTIFICATION-TYPE
			OBJECTS { hwFuncationName , hwLPUAlarmBoardName }
			STATUS current
			DESCRIPTION 
				"The board does not support this function."
			::= { hwDsliteTraps 94 }
			
        -- 1.3.6.1.4.1.2011.5.25.240.2.95
		hwVSMBoardNotSupportResume NOTIFICATION-TYPE
			OBJECTS { hwFuncationName , hwLPUAlarmBoardName }
			STATUS current
			DESCRIPTION 
				"The alarm was cleared because the board that does not support this function was removed or this function configuration was deleted from the board."
			::= { hwDsliteTraps 95 }

		
--  1.3.6.1.4.1.2011.5.25.240.3
        hwDsliteConformance OBJECT IDENTIFIER ::= { hwDsliteMIB 3 }
		
--  1.3.6.1.4.1.2011.5.25.240.3.1
		hwDsliteCompliances OBJECT IDENTIFIER ::= { hwDsliteConformance 1 }
		
--  1.3.6.1.4.1.2011.5.25.240.3.1.1
		hwDsliteCompliance MODULE-COMPLIANCE
			STATUS current
			DESCRIPTION 
				"Description."
			MODULE -- this module
				MANDATORY-GROUPS { hwDsliteInstanceGroup, hwDsliteInstanceSlotGroup, hwDsliteInstanceAddressGroupGroup, hwDsliteInstanceRemoteIpGroup, hwDsliteInstanceOutboundGroup, 
					hwDsliteScalarPathmtuGroup }
			::= { hwDsliteCompliances 1 }
		
--  1.3.6.1.4.1.2011.5.25.240.3.2
		hwDsliteGroups OBJECT IDENTIFIER ::= { hwDsliteConformance 2 }
		
--  1.3.6.1.4.1.2011.5.25.240.3.2.1
		hwDsliteScalarPathmtuGroup OBJECT-GROUP
			OBJECTS { hwDslitePathmtuEnable, hwDslitePathmtuDetectTimeout, hwDslitePathmtuDuration, hwDslitePathmtuAgingTime }
			STATUS current
			DESCRIPTION 
				"Description."
			::= { hwDsliteGroups 1 }
		
--  1.3.6.1.4.1.2011.5.25.240.3.2.2
		hwDsliteScalarTcpMssGroup OBJECT-GROUP
			OBJECTS { hwDsliteTcpMss }
			STATUS current
			DESCRIPTION 
				"Description."
			::= { hwDsliteGroups 2 }
		
--  1.3.6.1.4.1.2011.5.25.240.3.2.3
		hwDsliteScalarCGNAlarmGroup OBJECT-GROUP
			OBJECTS { hwDsliteCGNAlarmRoutingTable, hwDsliteCGNAlarmConnectNumber, hwCGNAlarmInstanceType, hwCGNAlarmCpeIpAddr, hwCGNAlarmAddrGroupName, 
				hwCGNAlarmSpecificIP, hwCGNAlarmIpVersion, hwVSUAlarmThreshold, hwVSUAlarmCpu, hwVSUAlarmSlot, 
				hwCGNAlarmPortNum, hwCGNAlarmSessionNum, hwCGNAlarmCid, hwCGNAlarmInstanceName, hwCGNAlarmProtocolType, 
				hwCGNAlarmServerMapUsage, hwCGNAlarmTotalSessionNum, hwCGNAlarmDeviceThreshold, hwCGNAlarmIPNum, hwCGNAlarmAccessUserNum, 
				hwCGNAlarmUserTableNum, hwVSUAlarmbpsRateInUse, hwVSUAlarmMbpsRate, hwVSUAlarmppsRate, hwVSUAlarmCpuUsage, 
				hwCGNAlarmUsedIPNum, hwCGNAlarmPoolName, hwCGNAlarmReason, hwCGNAlarmSubnet, hwCGNAlarmMask, 
				hwVSUAlarmBoardName, hwVSUServiceFaultCode, hwVSUServiceFaultKey, hwVSUReasonDescription }
			STATUS current
			DESCRIPTION 
				"Description."
			::= { hwDsliteGroups 3 }
		
--  1.3.6.1.4.1.2011.5.25.240.3.2.4
		hwDsliteInstanceGroup OBJECT-GROUP
			OBJECTS { hwInstanceName, hwInstanceModeFullCone, hwInstanceLocalIp, hwInstanceMtu, hwInstanceLogSessionEnable, 
				hwInstanceSessionLimitEnable, hwInstancePortLimitEnable, hwInstanceTrafficClass, hwInstanceDscpCopyEnable, hwInstanceRowStatus, 
				hwInstanceLocalIpPrefixLength, hwInstanceCGNAlarmNatPortNumber, hwInstanceDetectALGMask }
			STATUS current
			DESCRIPTION 
				"Description."
			::= { hwDsliteGroups 4 }
		
--  1.3.6.1.4.1.2011.5.25.240.3.2.5
		hwDsliteInstanceSlotGroup OBJECT-GROUP
			OBJECTS { hwSlotInstanceName, hwSlotSlotId, hwSlotIsMaster, hwSlotRowStatus }
			STATUS current
			DESCRIPTION 
				"Description."
			::= { hwDsliteGroups 5 }
		
--  1.3.6.1.4.1.2011.5.25.240.3.2.6
		hwDsliteInstanceAddressGroupGroup OBJECT-GROUP
			OBJECTS { hwAddressGroupInstanceName, hwAddressGroupName, hwAddressGroupStartAddress, hwAddressGroupEndAddress, hwAddressGroupFullCone, 
				hwAddressGroupRowStatus }
			STATUS current
			DESCRIPTION 
				"Description."
			::= { hwDsliteGroups 6 }
		
--  1.3.6.1.4.1.2011.5.25.240.3.2.7
		hwDsliteInstanceRemoteIpGroup OBJECT-GROUP
			OBJECTS { hwRemoteIpInstanceName, hwRemoteIpv6Addr, hwRemoteIpIpv6AddrPrefixLength, hwRemoteIpRowStatus }
			STATUS current
			DESCRIPTION 
				"Description."
			::= { hwDsliteGroups 7 }
		
--  1.3.6.1.4.1.2011.5.25.240.3.2.8
		hwDsliteInstanceOutboundGroup OBJECT-GROUP
			OBJECTS { hwOutboundInstanceName, hwOutboundAcl6Number, hwOutboundAddressGroupName, hwOutboundRowStatus }
			STATUS current
			DESCRIPTION 
				"Description."
			::= { hwDsliteGroups 8 }
		
--  1.3.6.1.4.1.2011.5.25.240.3.2.9
		hwDsliteInstanceLogSessionHostGroup OBJECT-GROUP
			OBJECTS { hwSessionLogInstanceName, hwSessionLogSourceIp, hwSessionLogSourcePort, hwSessionLogHostIp, hwSessionLogHostPort, 
				hwSessionLogRowStatus }
			STATUS current
			DESCRIPTION 
				"Description."
			::= { hwDsliteGroups 9 }
		
--  1.3.6.1.4.1.2011.5.25.240.3.2.10
		hwDsliteInstanceServerGroup OBJECT-GROUP
			OBJECTS { hwServerInstanceName, hwServerProtocol, hwServerGlobalAddress, hwServerGlobalPort, hwServerInsideAddress, 
				hwServerInsidePort, hwServerCPE, hwServerRowStatus }
			STATUS current
			DESCRIPTION 
				"Description."
			::= { hwDsliteGroups 10 }
		
--  1.3.6.1.4.1.2011.5.25.240.3.2.11
		hwDsliteInstanceSessionLimitGroup OBJECT-GROUP
			OBJECTS { hwSessionLimitInstanceName, hwSessionLimitType, hwSessionLimitNumber, hwSessionLimitRowStatus }
			STATUS current
			DESCRIPTION 
				"Description."
			::= { hwDsliteGroups 11 }
		
--  1.3.6.1.4.1.2011.5.25.240.3.2.12
		hwDsliteInstancePortLimitGroup OBJECT-GROUP
			OBJECTS { hwPortLimitInstanceName, hwPortLimitType, hwPortLimitNumber, hwPortLimitRowStatus }
			STATUS current
			DESCRIPTION 
				"Description."
			::= { hwDsliteGroups 12 }
		
--  1.3.6.1.4.1.2011.5.25.240.3.2.13
        hwDsliteStatisticGroup OBJECT-GROUP
            OBJECTS { hwDsliteStatisticSlotId, hwDsliteStatisticCpuId, hwDsliteStatisticDiscard, hwDsliteStatisticReceived, hwDsliteStatisticTransmitted, 
                hwDsliteStatisticIpv4Session, hwDsliteStatisticIpv6Session, hwDsliteStatisticRowStatus }
			STATUS current
			DESCRIPTION 
				"Description."
			::= { hwDsliteGroups 13 }
		
--  1.3.6.1.4.1.2011.5.25.240.3.2.14
		hwDsliteTrapsGroup NOTIFICATION-GROUP
		NOTIFICATIONS { hwCGNRoutingTableAlarm, hwCGNGloablV4SessionNumAlarm, hwCGNUserSessionNumAlarm, hwCGNUserPortNumAlarm, hwCGNPortforwardingAlarm, 
		hwCGNDsliteTunnelNumAlarm, hwCGNPortUsageOfAddrGroupAlarm, hwCGNPortUsageOfSpecificIpAlarm, hwCGNUserDiscardNumAlarm, hwCGNInstanceDiscardNumAlarm, 
				hwCGNGloablV4SessionNumResumeAlarm, hwCGNUserPortNumResumeAlarm, hwCGNStaticMappingCopyConfigEvent, hwCGNUserIPNumBoardAlarm, hwCGNUserIPNumBoardResumeAlarm, 
				hwCGNServerMapNumThresholdAlarm, hwCGNServerMapNumThresholdResumeAlarm, hwCGNServerMapNumExhaustAlarm, hwCGNServerMapNumExhaustResumeAlarm, hwCGNPortUsageOfSpecificIpPreAlarm, 
				hwCGNPortUsageOfSpecificIpResumeAlarm, hwCGNPortUsageOfSpecificIpPreResumeAlarm, hwCGNStaticMappingReadConfigEvent, hwCGNDeviceSessionNumAlarm, hwCGNDeviceSessionNumResumeAlarm, 
				hwCGNUserPortExhaustAlarm, hwCGNUserPortExhaustResumeAlarm, hwCGNSessionExhaustAlarm, hwCGNSessionExhaustResumeAlarm, hwCGNSpecificIpExhaustAlarm, 
				hwCGNSpecificIpExhaustResumeAlarm, hwCGNUserIPNumAlarm, hwCGNUserIPNumResumeAlarm, hwCGNNoPatAddrGroupExhaustAlarm, hwCGNNoPatAddrGroupExhaustResumeAlarm, 
				hwCGNNoPatAddrGroupThresholdAlarm, hwCGNNoPatAddrGroupThresholdResumeAlarm, hwCGNAccessLimitThresholdAlarm, hwCGNAccessLimitThresholdResumeAlarm, hwCGNAccessLimitExhaustAlarm, 
				hwCGNAccessLimitExhaustResumeAlarm, hwCGNUserTableExhaustAlarm, hwCGNUserTableExhaustResumeAlarm, hwCGNUserTableThresholdAlarm, hwCGNUserTableThresholdResumeAlarm, 
				hwVSUDevicePerformanceAlarm, hwVSUDevicePerformanceResumeAlarm, hwCGNGlobalPoolPreAlarm, hwCGNGlobalPoolPreResumeAlarm, hwCGNGlobalPoolExhaustAlarm, 
				hwCGNGlobalPoolExhaustResumeAlarm, hwCGNDAPPoolApplyFail, hwCGNDAPPoolReleaseFail, hwCGNDAPPoolSubnetFull, hwCGNDAPDeviceSubnetFull, 
				hwCGNInstanceDAPPoolApplyFail, hwCGNInstanceDAPPoolSubnetFull, hwCGNSessionSpecOverloadAlarm, hwCGNSessionSpecOverloadResumeAlarm, hwCGNGloablV4SessionNumBoardAlarm, 
				hwCGNGloablV4SessionNumBoardResumeAlarm, hwCGNSessionExhaustBoardAlarm, hwCGNSessionExhaustBoardResumeAlarm, hwCGNNoPatAddrGroupExhaustBoardAlarm, hwCGNNoPatAddrGroupExhaustBoardResumeAlarm, 
				hwCGNNoPatAddrGroupThresholdBoardAlarm, hwCGNNoPatAddrGroupThresholdBoardResumeAlarm, hwCGNPortUsageOfSpecificIpPreBoardAlarm, hwCGNPortUsageOfSpecificIpPreBoardResumeAlarm, hwCGNSpecificIpExhaustBoardAlarm, 
				hwCGNSpecificIpExhaustBoardResumeAlarm, hwCGNUserPortNumBoardAlarm, hwCGNUserPortNumBoardResumeAlarm, hwCGNUserTableExhaustBoardAlarm, hwCGNUserTableExhaustBoardResumeAlarm, 
				hwCGNUserTableThresholdBoardAlarm, hwCGNUserTableThresholdBoardResumeAlarm, hwVSUDevicePerformanceBoardAlarm, hwVSUDevicePerformanceBoardResumeAlarm, hwVSUDevicePerformanceExhaustAlarm, 
				hwVSUDevicePerformanceExhaustResumeAlarm, hwVSUServiceFaultAlarm, hwVSUServiceFaultResumeAlarm, 
                hwCGNGlobalPoolReleaseFail, hwCGNDAPBackupConfigInconsistent,  hwCGNDAPUPCPConfigInconsistent, hwCGNDAPPoolSectionSyncFail, hwMAPBoardNotSupportAlarm, hwMAPBoardNotSupportResume,hwVSMBoardNotSupportAlarm, hwVSMBoardNotSupportResume }
			STATUS current
			DESCRIPTION 
				"Description."
			::= { hwDsliteGroups 14 }
		
--  1.3.6.1.4.1.2011.5.25.240.3.2.15
		hwDsliteScalarSessionAgingTimeGroup OBJECT-GROUP
			OBJECTS { hwDsliteSessionAgingTimeType, hwDsliteSessionAgingTime }
			STATUS current
			DESCRIPTION 
				"Description."
			::= { hwDsliteGroups 15 }
		
--  1.3.6.1.4.1.2011.5.25.240.3.2.16
		hwDslitePortUsageGroup OBJECT-GROUP
			OBJECTS { hwPortUsageInstanceName, hwPortUsageAddrGroupName, hwPortUsageSlotID, hwPortUsageCpuID, hwPortUsageOfFullGroup, 
				hwPortUsageOfPortRange, hwPortUsageOfPortforwarding, hwPortUsageOfSpecificIP, hwPortUsageRowStatus, hwPortUsageIP
				 }
			STATUS current
			DESCRIPTION 
				"Description."
			::= { hwDsliteGroups 16 }
		
--  1.3.6.1.4.1.2011.5.25.240.3.2.17
		hwDsliteScalarSMCopyGroup OBJECT-GROUP
			OBJECTS { hwSMCopyState, hwSMCopyTimeStarted, hwSMCopyTimeCompleted, hwSMCopyFailCause }
			STATUS current
			DESCRIPTION 
				"Description."
			::= { hwDsliteGroups 17 }
		
--  1.3.6.1.4.1.2011.5.25.240.3.2.18
		hwDsliteScalarSMReadGroup OBJECT-GROUP
			OBJECTS { hwSMReadState, hwSMReadResultFileName, hwSMReadResultCode, hwSMReadResultDescription }
			STATUS current
			DESCRIPTION 
				"Description."
			::= { hwDsliteGroups 18 }
		
--  1.3.6.1.4.1.2011.5.25.240.3.2.19
		hwDsliteCopyGroup OBJECT-GROUP
			OBJECTS { hwSMCopyIndex, hwSMCopyProtocol, hwSMCopySrcFileType, hwSMCopyDstFileType, hwSMCopyFtpServer, 
				hwSMCopySrcFileName, hwSMCopyDstFileName, hwSMCopyUserName, hwSMCopyUserPwd, hwSMCopyRowStatus
				 }
			STATUS current
			DESCRIPTION 
				"Description."
			::= { hwDsliteGroups 19 }
		
--  1.3.6.1.4.1.2011.5.25.240.3.2.20
		hwDsliteReadGroup OBJECT-GROUP
			OBJECTS { hwSMReadIndex, hwSMReadFileType, hwSMReadFileName, hwSMReadRowStatus }
			STATUS current
			DESCRIPTION 
				"Description."
			::= { hwDsliteGroups 20 }
		
	
	END

--
-- HUAWEI-DSLITE-MIB.mib
--

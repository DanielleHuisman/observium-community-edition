-- ============================================================================
-- Copyright (C) 2014 by  HUAWEI TECHNOLOGIES. All rights reserved.
-- Description: The mib is used for defining the MIB objects of electronic switch.
-- Reference:  
-- Version: V1.08
-- ============================================================================

    HUAWEI-ELECTRO-SWITCH-MIB DEFINITIONS ::= BEGIN
 
        IMPORTS
            huaweiMgmt           
                FROM HUAWEI-MIB  
            OBJECT-TYPE, MODULE-IDENTITY, OBJECT-IDENTITY, Integer32            
                FROM SNMPv2-SMI;  

        hwEthernetPort MODULE-IDENTITY
            LAST-UPDATED "201406300000Z"                              
            ORGANIZATION "Huawei Technologies Co.,Ltd."                
            CONTACT-INFO                                            
                         "Huawei Industrial Base         
                          Bantian, Longgang                    
                          Shenzhen 518129                       
                          People's Republic of China            
                          Website: http://www.huawei.com        
                          Email: support@huawei.com             
                         "                                                                                 
            DESCRIPTION
                "
                The mib is used for defining the MIB objects of electronic switch.               
                " 
                
--  Revision history
            REVISION    "201406300000Z"
            DESCRIPTION "V1.08, 1. modified module name 'hwEthernet' to 'hwEthernetPort'.
                                2. removed all hyphens (-) from enumerated values of hwElectroSwitchLocation."

            REVISION    "201011100000Z"
            DESCRIPTION "V1.07,Modified the description of hwElectroSwitchEntry."
            
            REVISION    "201008250000Z"
            DESCRIPTION "V1.06, modified the contact-info and the revision history. Modified the description of leaves."

            REVISION    "201006170000Z"
            DESCRIPTION "V1.05, added the description of the MIB header file; added the revision history; 
                         modified the object description in hwElectroSwitchTable." 

            REVISION    "200701300000Z"
            DESCRIPTION "V1.00, completed the draft."
                ::= { huaweiMgmt 14 }
--          
-- hwElectroSwitch
--    
    hwElectroSwitchTable OBJECT-TYPE
            SYNTAX SEQUENCE OF HwElectroSwitchEntry
            MAX-ACCESS not-accessible
            STATUS current
            DESCRIPTION
                "
                Electronic switch table.
                This table is used for querying and setting the electronic function. By setting 
                the electronic function, the user can select the port on the control board or 
                the upstream interface board for upstream transmission.
                The index of this table is hwElectroSwitchIndex.
                "
            ::= { hwEthernetPort 15 }
            
        hwElectroSwitchEntry OBJECT-TYPE
        SYNTAX HwElectroSwitchEntry
            MAX-ACCESS not-accessible
            STATUS current
            DESCRIPTION
                "   
                Electronic switch table.
                This table is used for querying and setting the electronic function. By setting 
                the electronic function, the user can select the port on the control board or 
                the upstream interface board for upstream transmission.                
                The index of this entry is hwElectroSwitchIndex.
                "
            INDEX { hwElectroSwitchIndex }
            ::= { hwElectroSwitchTable 1 }
            
        HwElectroSwitchEntry ::=
        SEQUENCE{ 
                hwElectroSwitchIndex
                    Integer32,
                hwElectroSwitchLocation
                    INTEGER,
                hwElectroSwitchLocation0Info
                    OCTET STRING,
                hwElectroSwitchLocation1Info
                    OCTET STRING                
                }
             
        hwElectroSwitchIndex OBJECT-TYPE
            SYNTAX Integer32 (1..8)
            MAX-ACCESS not-accessible
            STATUS current
            DESCRIPTION
                "
                Index of this table.
                "
            ::= { hwElectroSwitchEntry 1 }
            
        hwElectroSwitchLocation OBJECT-TYPE
            SYNTAX INTEGER 
                {
                    location0(1),
                    location1(2)
                }
            MAX-ACCESS read-write
            STATUS current
            DESCRIPTION
                "
                The switch location of electronic switch.
                Options:
                1. location0(1) -The electronic switch points to the ports of mainboard.
                2. location1(2) -The electronic switch points to the ports of upstream interface board.
                "
            ::= { hwElectroSwitchEntry 2 }
            
        hwElectroSwitchLocation0Info OBJECT-TYPE        
            SYNTAX OCTET STRING (SIZE (0..96))                                    
            MAX-ACCESS read-only                              
            STATUS current                                    
            DESCRIPTION                                       
                "
                The available port description when electronic switch location is 
                location-0, including frame index, slot index and port index. 
                If the operation granularity is board-class, no port index is  
                given. If the port is VOIP port, the description is VOIP.           
                "                   
            ::= { hwElectroSwitchEntry 3 }
            
        hwElectroSwitchLocation1Info OBJECT-TYPE        
            SYNTAX OCTET STRING (SIZE (0..96))                                    
            MAX-ACCESS read-only                              
            STATUS current                                    
            DESCRIPTION                                       
                "
                The available port description when electronic switch location is 
                location-1, including frame index, slot index and port index. 
                If the operation granularity is board-class, no port index is given.          
                "                                    
            ::= { hwElectroSwitchEntry 4 }                  
                    
    END

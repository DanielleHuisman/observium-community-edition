-- ============================================================================
-- Copyright (C) 2016 by HUAWEI TECHNOLOGIES. All rights reserved.
--
-- Description:
-- Reference:
-- Version: V1.01
-- History:
-- ============================================================================

HUAWEI-ENT-VOICE-PUBLIC-MIB DEFINITIONS ::= BEGIN
    IMPORTS
        MODULE-IDENTITY, OBJECT-TYPE, NOTIFICATION-TYPE, private, Integer32, Unsigned32
            FROM SNMPv2-SMI
        MODULE-COMPLIANCE, OBJECT-GROUP, NOTIFICATION-GROUP
            FROM SNMPv2-CONF
        TEXTUAL-CONVENTION
            FROM SNMPv2-TC
        IpAddress, TimeTicks, Counter32
            FROM SNMPv2-SMI
        RowStatus, DisplayString
            FROM SNMPv2-TC
        hwDatacomm
            FROM HUAWEI-MIB;

hwEntVoicePublicMIB MODULE-IDENTITY
    LAST-UPDATED "201602240000Z"
      ORGANIZATION 
                "Huawei Technologies Co.,Ltd."
      CONTACT-INFO 
              "Huawei Industrial Base                
              Bantian, Longgang                     
              Shenzhen 518129                       
              People's Republic of China            
              Website: http://www.huawei.com        
              Email: support@huawei.com             
              "   
    DESCRIPTION
        "Huawei VOICE PUBLIC mib."

-- Revision history

    REVISION     "201602240000Z"
    DESCRIPTION  "V1.01, add hwEntPbxStateSipipTrkGrpMaxCr."

    REVISION     "201107010000Z"
    DESCRIPTION  "V1.0, create this file."

::= { hwDatacomm 249 }


-- hwEntSysParaConfigTable

hwEntSysParaConfigTable OBJECT IDENTIFIER  ::= { hwEntVoicePublicMIB 1 }

    hwEntSysParaCountry OBJECT-TYPE
        SYNTAX INTEGER {
            chinaMainland(1),
            chinaHongkong(2),
            brazil(3),
            egypt(4),
            singapore(5),
            thailand(6),
            france(7),
            britainMsfuk(8),
            britainEtsi(9),
            bulgaria(10) }
        MAX-ACCESS read-write
        STATUS current
        DESCRIPTION
            "System parameter of country.
            Options:
            chinaMainland(1) - China mainland
            chinaHongkong(2) - China Hongkong
            brazil(3) - Brazil
            egypt(4) - Egypt
            singapore(5) - Singapore
            thailand(6) - Thailand
            france(7) - France
            britainMsfuk(8) - Britain msfuk
            britainEtsi(9) - Britain etsi
            bulgaria(10) - Bulgaria
            Default: chinaMainland(1)"
        ::= { hwEntSysParaConfigTable 1 }

    hwEntSysParaStopInitialRing OBJECT-TYPE
        SYNTAX INTEGER { enable(1), disable(2) }
        MAX-ACCESS read-write
        STATUS current
        DESCRIPTION
            "System parameter of stop initial ring switch.
            Options:
            enable(1) - enable
            disable(2) - disable
            Default: enable(1)"
    ::= { hwEntSysParaConfigTable 2 }

    hwEntSysParaMwiMode OBJECT-TYPE
        SYNTAX INTEGER { highVoltage(1), fskWithRing(2), fskWithoutRing(3) }
        MAX-ACCESS read-write
        STATUS current
        DESCRIPTION
            "System parameter of mwi mode.
            Options:
            highVoltage(1) - high voltage
            fskWithRing(2) - fsk with ring
            fskWithoutRing(3) - fsk without ring
            Default: fskWithRing(2)"
    ::= { hwEntSysParaConfigTable 3 }

    hwEntSysParaFlashHookUpper OBJECT-TYPE
        SYNTAX Integer32 (50..1400)
        MAX-ACCESS read-write
        STATUS current
        DESCRIPTION
            "System parameter of hooking upper threshold. (Unit: ms)
            Default: 350"
    ::= { hwEntSysParaConfigTable 4 }

    hwEntSysParaFlashHookLower OBJECT-TYPE
        SYNTAX Integer32 (50..1400)
        MAX-ACCESS read-write
        STATUS current
        DESCRIPTION
            "System parameter of hooking lower threshold. (Unit: ms)
            Default: 100"
    ::= { hwEntSysParaConfigTable 5 }

    hwEntSysParaParkFeed OBJECT-TYPE
        SYNTAX INTEGER { enable(1), disable(2) }
        MAX-ACCESS read-write
        STATUS current
        DESCRIPTION
            "System parameter of park feed switch.
            Options:
            enable(1) - enable
            disable(2) - disable
            Default: disable(2)"
    ::= { hwEntSysParaConfigTable 6 }

    hwEntSysParaPcm OBJECT-TYPE
        SYNTAX INTEGER {aLaw(1),uLaw(2)}
        MAX-ACCESS read-write
        STATUS current
        DESCRIPTION
            "System parameter of PCM.
            Options:
            aLaw(1) - a law
            uLaw(2) - u law
            Default: aLaw(1)"
    ::= { hwEntSysParaConfigTable 7 }

    hwEntSysParaRingFrequency OBJECT-TYPE
        SYNTAX INTEGER {frequency16HZ(1),frequency25HZ(2),frequency50HZ(3)}
        MAX-ACCESS read-write
        STATUS current
        DESCRIPTION
            "System parameter of ring frequency.
            Options:
            frequency16HZ(1) - 16HZ
            frequency25HZ(2) - 25HZ
            frequency50HZ(3) - 50HZ
            Default: frequency25HZ(2)"
    ::= { hwEntSysParaConfigTable 8 }

    hwEntSysParaRingAcAmplitude OBJECT-TYPE
        SYNTAX INTEGER { ac65Vrms(1), ac50Vrms(2) }
        MAX-ACCESS read-write
        STATUS current
        DESCRIPTION
            "System parameter of ring ac-amplitude.
            Options:
            ac65Vrms(1) - 65Vrms
            ac50Vrms(2) - 50Vrms
            Default: ac50Vrms(2)"
    ::= { hwEntSysParaConfigTable 9 }

    hwEntSysParaGlobalDigitmap OBJECT-TYPE
        SYNTAX INTEGER { enable(1), disable(2) }
        MAX-ACCESS read-write
        STATUS current
        DESCRIPTION
            "System parameter of global digitmap.
            Options:
            enable(1) - enable
            disable(2) - disable
            Default: enable(1)"
    ::= { hwEntSysParaConfigTable 10 }

    hwEntSysParaSctpSendChecksum OBJECT-TYPE
        SYNTAX INTEGER { enable(1), disable(2) }
        MAX-ACCESS read-write
        STATUS current
        DESCRIPTION
            "System parameter of sctp send checksum.
            Options:
            enable(1) - enable
            disable(2) - disable
            Default: enable(1)"
    ::= { hwEntSysParaConfigTable 11 }

    hwEntSysParaSctpReceiveChecksum OBJECT-TYPE
        SYNTAX INTEGER { enable(1), disable(2) }
        MAX-ACCESS read-write
        STATUS current
        DESCRIPTION
            "System parameter of sctp receive checksum.
            Options:
            enable(1) - enable
            disable(2) - disable
            Default: enable(1)"
    ::= { hwEntSysParaConfigTable 12 }

    hwEntSysParaVoipVpnInstance OBJECT-TYPE
        SYNTAX DisplayString (SIZE (1..31))
        MAX-ACCESS read-write
        STATUS current
        DESCRIPTION
            "System parameter of voip vpn instance."
    ::= { hwEntSysParaConfigTable 13 }

-- IP address configuration table

hwEntVoipAddressTable OBJECT-TYPE
    SYNTAX SEQUENCE OF HwEntVoipAddressEntry
    MAX-ACCESS not-accessible
    STATUS current
    DESCRIPTION
        "VOIP multiply IP table.
        The index of this table is hwEntVoipAddressIndex"
::= { hwEntVoicePublicMIB 2 }

    hwEntVoipAddressEntry OBJECT-TYPE
        SYNTAX HwEntVoipAddressEntry
        MAX-ACCESS not-accessible
        STATUS current
        DESCRIPTION
            "VOIP multiply IP table.
            The index of this entry is hwEntVoipAddressIndex"
        INDEX { hwEntVoipAddressIndex }
    ::= { hwEntVoipAddressTable 1 }

    HwEntVoipAddressEntry ::=
        SEQUENCE {
            hwEntVoipAddressIndex            Integer32,
            hwEntVoipAddressType             INTEGER,
            hwEntVoipInterfaceType           DisplayString,
            hwEntVoipInterfaceId             DisplayString,
            hwEntVoipMethod                  INTEGER,
            hwEntVoipIPAddress               IpAddress,
            hwEntVoipAddressRowStatus        RowStatus
        }

        hwEntVoipAddressIndex OBJECT-TYPE
            SYNTAX Integer32 (0..15)
            MAX-ACCESS not-accessible
            STATUS current
            DESCRIPTION
                "The index of VOIP address"
        ::= { hwEntVoipAddressEntry 1 }

        hwEntVoipAddressType OBJECT-TYPE
            SYNTAX INTEGER { signalling(1), media(2) }
            MAX-ACCESS read-create
            STATUS current
            DESCRIPTION
                "The type of VOIP address.
                Options:
                signalling(1) - indicates that the type of VOIP IP is signaling.
                media(2)      - indicates that the type of VOIP IP is media."
        ::= { hwEntVoipAddressEntry 2 }

        hwEntVoipInterfaceType OBJECT-TYPE
            SYNTAX DisplayString(SIZE (0..32))
            MAX-ACCESS read-create
            STATUS current
            DESCRIPTION
                "The interface type of VOIP address."
        ::= { hwEntVoipAddressEntry  3 }

        hwEntVoipInterfaceId OBJECT-TYPE
            SYNTAX DisplayString(SIZE (0..32))
            MAX-ACCESS read-create
            STATUS current
            DESCRIPTION
                "The interface ID of VOIP address."
        ::= { hwEntVoipAddressEntry  4 }

        hwEntVoipMethod OBJECT-TYPE
            SYNTAX INTEGER { static(1), dynamic(2)}
            MAX-ACCESS read-create
            STATUS current
            DESCRIPTION
                "Static IP address or dynamic IP address name.
                Options:
                static(1) - the IP address is configured statically.
                dynamic(2) - the IP address is obtained dynamically."
        ::= { hwEntVoipAddressEntry  5 }

        hwEntVoipIPAddress OBJECT-TYPE
            SYNTAX IpAddress
            MAX-ACCESS read-create
            STATUS current
            DESCRIPTION
                "IP address."
        ::= { hwEntVoipAddressEntry 6 }

        hwEntVoipAddressRowStatus OBJECT-TYPE
            SYNTAX  RowStatus
            MAX-ACCESS  read-create
            STATUS  current
            DESCRIPTION
                "Indicates the status of this conceptual row.
                Options:
                active(1)
                createAndGo(4)
                destroy(6)"
        ::= { hwEntVoipAddressEntry 7 }

   --==
   
    hwEntPbxStateTable OBJECT IDENTIFIER  ::= { hwEntVoicePublicMIB 3 }
  
    hwEntPbxStatePotsUserNum OBJECT-TYPE
        SYNTAX Integer32
        MAX-ACCESS read-only
        STATUS current
        DESCRIPTION
            "Indicates the number of pots users."
    ::= { hwEntPbxStateTable 1 }
       
    hwEntPbxStateBraUserNum OBJECT-TYPE
        SYNTAX Integer32
        MAX-ACCESS read-only
        STATUS current
        DESCRIPTION
            "Indicates the number of bra users."
    ::= { hwEntPbxStateTable 2 }
    

    hwEntPbxStateSipueUserNum OBJECT-TYPE
        SYNTAX Integer32
        MAX-ACCESS read-only
        STATUS current
        DESCRIPTION
            "Indicates the number of sipue users."
    ::= { hwEntPbxStateTable 3 }
    
    hwEntPbxAt0TrkNum OBJECT-TYPE
        SYNTAX Integer32
        MAX-ACCESS read-only
        STATUS current
        DESCRIPTION
            "Indicates the number of at0 trunk."
    ::= { hwEntPbxStateTable 4 }
    
    hwEntPbxPraTrkNum OBJECT-TYPE
        SYNTAX Integer32
        MAX-ACCESS read-only
        STATUS current
        DESCRIPTION
            "Indicates the number of pra trunk."
    ::= { hwEntPbxStateTable 5 }
    
    hwEntPbxR2TrkNum OBJECT-TYPE
        SYNTAX Integer32
        MAX-ACCESS read-only
        STATUS current
        DESCRIPTION
            "Indicates the number of r2 trunk."
    ::= { hwEntPbxStateTable 6 }
    
    hwEntPbxSipat0TrkNum OBJECT-TYPE
        SYNTAX Integer32
        MAX-ACCESS read-only
        STATUS current
        DESCRIPTION
            "Indicates the number of sipat0 trunk."
    ::= { hwEntPbxStateTable 7 }
    
    hwEntPbxSipTrkGrpNum OBJECT-TYPE
        SYNTAX Integer32
        MAX-ACCESS read-only
        STATUS current
        DESCRIPTION
            "Indicates the number of sip trunk group."
    ::= { hwEntPbxStateTable 8 }
    
    hwEntPbxStateOnlineUserNum OBJECT-TYPE
        SYNTAX Integer32
        MAX-ACCESS read-only
        STATUS current
        DESCRIPTION
            "Indicates the number of online users."
    ::= { hwEntPbxStateTable 9 }
    
    hwEntPbxStateMaxCallNum OBJECT-TYPE
        SYNTAX Integer32
        MAX-ACCESS read-only
        STATUS current
        DESCRIPTION
            "Indicates the max number of calls."
    ::= { hwEntPbxStateTable 10 }     
       
    hwEntPbxStateSipipTrkGrpMaxCr OBJECT-TYPE
        SYNTAX Integer32
        MAX-ACCESS read-only
        STATUS current
        DESCRIPTION
            "Indicates the remaining max cr number of sipip trunk group."
    ::= { hwEntPbxStateTable 11 }
                                      
    hwEntPbxStateSippraTrkGrpMaxCr OBJECT-TYPE
        SYNTAX Integer32
        MAX-ACCESS read-only
        STATUS current
        DESCRIPTION
            "Indicates the remaining max cr number of sippra trunk group."
    ::= { hwEntPbxStateTable 12 }
    
    hwEntPbxStateSipat0TrkGrpMaxCr OBJECT-TYPE
        SYNTAX Integer32
        MAX-ACCESS read-only
        STATUS current
        DESCRIPTION
            "Indicates the remaining max cr number of sipat0 trunk group."
    ::= { hwEntPbxStateTable 13 }

    
    hwEntSipagStateTable OBJECT IDENTIFIER  ::= { hwEntVoicePublicMIB 4 }
        
    hwEntSipagStatePotsUserNum OBJECT-TYPE
        SYNTAX Integer32
        MAX-ACCESS read-only
        STATUS current
        DESCRIPTION
            "Indicates the number of pots ports."
    ::= { hwEntSipagStateTable 1 }
        
    hwEntSipagStateBraUserNum OBJECT-TYPE
        SYNTAX Integer32
        MAX-ACCESS read-only
        STATUS current
        DESCRIPTION
            "Indicates the number of bra users."
    ::= { hwEntSipagStateTable 2 }
       
    hwEntSipagStatePraUserNum OBJECT-TYPE
        SYNTAX Integer32
        MAX-ACCESS read-only
        STATUS current
        DESCRIPTION
            "Indicates the number of pra users."
    ::= { hwEntSipagStateTable 3 }
    
    hwEntSipagStateSipagNum OBJECT-TYPE
        SYNTAX Integer32
        MAX-ACCESS read-only
        STATUS current
        DESCRIPTION
            "Indicates the number of sipag."
    ::= { hwEntSipagStateTable 4 }
    
    hwEntSipagStateOnlineNum OBJECT-TYPE
        SYNTAX Integer32
        MAX-ACCESS read-only
        STATUS current
        DESCRIPTION
            "Indicates the number of online users."
    ::= { hwEntSipagStateTable 5 }
    
    hwEntSipagStateMaxCallNum OBJECT-TYPE
        SYNTAX Integer32
        MAX-ACCESS read-only
        STATUS current
        DESCRIPTION
            "Indicates the max number of calls."
    ::= { hwEntSipagStateTable 6 }
    
    hwEntSipagStateBestFlag OBJECT-TYPE
        SYNTAX INTEGER { running(1), shutdown(2)}
        MAX-ACCESS read-only
        STATUS current
        DESCRIPTION
            "Indicates the best flag."
    ::= { hwEntSipagStateTable 7 }
    
    hwEntCallStaticsTable OBJECT IDENTIFIER  ::= { hwEntVoicePublicMIB 5 }
 
    hwEntCallStaticsAttemptCall OBJECT-TYPE
        SYNTAX Integer32
        MAX-ACCESS read-only
        STATUS current
        DESCRIPTION
            "Indicates the attempt call number."
    ::= { hwEntCallStaticsTable 1 }
    
    hwEntCallStaticsAlertingCall OBJECT-TYPE
        SYNTAX Integer32
        MAX-ACCESS read-only
        STATUS current
        DESCRIPTION
            "Indicates the alerting call number."
    ::= { hwEntCallStaticsTable 2 }
    
    hwEntCallStaticsAnswerCall OBJECT-TYPE
        SYNTAX Integer32
        MAX-ACCESS read-only
        STATUS current
        DESCRIPTION
            "Indicates the answer call number."
    ::= { hwEntCallStaticsTable 3 }
    
    hwEntCallStaticTotalCallTime OBJECT-TYPE
        SYNTAX Integer32
        MAX-ACCESS read-only
        STATUS current
        DESCRIPTION
            "Indicates the total call timer."
    ::= { hwEntCallStaticsTable 4 }
        
    hwEntPbxTrunkCallStaticsTable OBJECT-TYPE
    SYNTAX SEQUENCE OF HwEntPbxTrunkCallStaticsEntry
    MAX-ACCESS not-accessible
    STATUS current
    DESCRIPTION
        "Indicates the trunk call statics"
        ::= { hwEntVoicePublicMIB 6 }
   
    hwEntPbxTrunkCallStaticsEntry OBJECT-TYPE
        SYNTAX HwEntPbxTrunkCallStaticsEntry
        MAX-ACCESS not-accessible
        STATUS current
        DESCRIPTION
            "Indicates the trunk call statics"
        INDEX { 
                 hwEntPbxTrunkCallStaticsTrkGrpName,
                 hwEntPbxTrunkCallStaticsCallType
              }
    ::= { hwEntPbxTrunkCallStaticsTable 1 }

    HwEntPbxTrunkCallStaticsEntry ::=
        SEQUENCE {
            hwEntPbxTrunkCallStaticsTrkGrpName           DisplayString,
            hwEntPbxTrunkCallStaticsCallType             INTEGER,
            hwEntPbxTrunkCallStaticsTrkGrpType           INTEGER,
            hwEntPbxTrunkCallStaticsAttemptCall          Integer32,
            hwEntPbxTrunkCallStaticsAlertingCall         Integer32,
            hwEntPbxTrunkCallStaticsAnswerCall           Integer32,
            hwEntPbxTrunkCallStaticsTotalCallTime        Integer32,
            hwEntPbxTrunkCallStaticsTrunkNum             Integer32, 
            hwEntPbxTrunkCallStaticsTrunkOccupyPer       Integer32
        }
    
    hwEntPbxTrunkCallStaticsTrkGrpName OBJECT-TYPE
        SYNTAX DisplayString(SIZE (1..32))
        MAX-ACCESS not-accessible
        STATUS current
        DESCRIPTION
            "Indicates the trunk group name."
    ::= { hwEntPbxTrunkCallStaticsEntry 1 }
    
    hwEntPbxTrunkCallStaticsCallType OBJECT-TYPE
        SYNTAX INTEGER {inCall(1), outCall(2), all(3)}
        MAX-ACCESS not-accessible
        STATUS current
        DESCRIPTION
            "Indicates the call type."
    ::= { hwEntPbxTrunkCallStaticsEntry 2 }
    
    hwEntPbxTrunkCallStaticsTrkGrpType OBJECT-TYPE
        SYNTAX INTEGER {at0(1), sip(2), pra(3), r2(4)}
        MAX-ACCESS read-only
        STATUS current
        DESCRIPTION
            "Indicates the trunk type."
    ::= { hwEntPbxTrunkCallStaticsEntry 3 }
    
    hwEntPbxTrunkCallStaticsAttemptCall OBJECT-TYPE
        SYNTAX Integer32
        MAX-ACCESS read-only
        STATUS current
        DESCRIPTION
            "Indicates the attempt call number."
    ::= { hwEntPbxTrunkCallStaticsEntry 4 }
    
    hwEntPbxTrunkCallStaticsAlertingCall OBJECT-TYPE
        SYNTAX Integer32
        MAX-ACCESS read-only
        STATUS current
        DESCRIPTION
            "Indicates the aletring call number."
    ::= { hwEntPbxTrunkCallStaticsEntry 5 }
    
    hwEntPbxTrunkCallStaticsAnswerCall OBJECT-TYPE
        SYNTAX Integer32
        MAX-ACCESS read-only
        STATUS current
        DESCRIPTION
            "Indicates the answer call number."
    ::= { hwEntPbxTrunkCallStaticsEntry 6 }
    
    hwEntPbxTrunkCallStaticsTotalCallTime OBJECT-TYPE
        SYNTAX Integer32
        MAX-ACCESS read-only
        STATUS current
        DESCRIPTION
            "Indicates the total call time."
    ::= { hwEntPbxTrunkCallStaticsEntry 7 }
    
    hwEntPbxTrunkCallStaticsTrunkNum OBJECT-TYPE
        SYNTAX Integer32
        MAX-ACCESS read-only
        STATUS current
        DESCRIPTION
            "Indicates the trunk number."
    ::= { hwEntPbxTrunkCallStaticsEntry 8 }
    
    hwEntPbxTrunkCallStaticsTrunkOccupyPer OBJECT-TYPE
        SYNTAX Integer32
        MAX-ACCESS read-only
        STATUS current
        DESCRIPTION
            "Indicates the busy trunk number."
    ::= { hwEntPbxTrunkCallStaticsEntry 9 }     
    
    -- ========== tone configuration table ===============================

    hwEntToneTable OBJECT-TYPE
        SYNTAX SEQUENCE OF HwEntToneEntry
        MAX-ACCESS not-accessible
        STATUS current
        DESCRIPTION
            "Voice tone table.
            The index of this table is hwEntToneToneIndex"
    ::= { hwEntVoicePublicMIB 8 }

    hwEntToneEntry OBJECT-TYPE
        SYNTAX HwEntToneEntry
        MAX-ACCESS not-accessible
        STATUS current
        DESCRIPTION
            "VOIP multiply IP table.
            The index of this entry is hwEntToneToneIndex"
        INDEX { hwEntToneToneIndex }
    ::= { hwEntToneTable 1 }

    HwEntToneEntry ::=
        SEQUENCE {
            hwEntToneToneIndex               Integer32,
			hwEntToneRowStatus               RowStatus,
            hwEntToneFrequency1Freq          Integer32,
            hwEntToneFrequency1Ampl          Integer32, 
            hwEntToneFrequency2Freq          Integer32,
            hwEntToneFrequency2Ampl          Integer32, 
            hwEntToneFrequency3Freq          Integer32,
            hwEntToneFrequency3Ampl          Integer32, 
            hwEntToneFrequency4Freq          Integer32,
            hwEntToneFrequency4Ampl          Integer32,
            hwEntToneCadenceSeq1OnTime       Integer32,
            hwEntToneCadenceSeq1OffTime      Integer32,
            hwEntToneCadenceSeq1BFreqFlag    Integer32,
            hwEntToneCadenceSeq2OnTime       Integer32,
            hwEntToneCadenceSeq2OffTime      Integer32,
            hwEntToneCadenceSeq2BFreqFlag    Integer32,
            hwEntToneCadenceSeq3OnTime       Integer32,
            hwEntToneCadenceSeq3OffTime      Integer32,
            hwEntToneCadenceSeq3BFreqFlag    Integer32,
            hwEntToneCadenceSeq4OnTime       Integer32,
            hwEntToneCadenceSeq4OffTime      Integer32,
            hwEntToneCadenceSeq4BFreqFlag    Integer32			
        }

        hwEntToneToneIndex OBJECT-TYPE
            SYNTAX Integer32 (1..11)
            MAX-ACCESS not-accessible
            STATUS current
            DESCRIPTION
                "The index of tone"
        ::= { hwEntToneEntry 1 }

		hwEntToneRowStatus OBJECT-TYPE
            SYNTAX  RowStatus
            MAX-ACCESS  read-create
            STATUS  current
            DESCRIPTION
                "Indicates the status of this conceptual row.
                Options:
                active(1)
                createAndGo(4)
                destroy(6)"
        ::= { hwEntToneEntry 2 }
		
        hwEntToneFrequency1Freq OBJECT-TYPE
            SYNTAX Integer32 (0..4000)
            MAX-ACCESS read-create
            STATUS current
            DESCRIPTION
                "The Frequency value(Hz) of Frequency1."
        ::= { hwEntToneEntry 3 }

        hwEntToneFrequency1Ampl OBJECT-TYPE
            SYNTAX Integer32(0..100)
            MAX-ACCESS read-create
            STATUS current
            DESCRIPTION
                "The amplitude value(0.1dbm) of Frequency1."
        ::= { hwEntToneEntry  4 }

		hwEntToneFrequency2Freq OBJECT-TYPE
            SYNTAX Integer32 (0..4000)
            MAX-ACCESS read-create
            STATUS current
            DESCRIPTION
                "The Frequency value(Hz) of Frequency2."
        ::= { hwEntToneEntry 5 }

        hwEntToneFrequency2Ampl OBJECT-TYPE
            SYNTAX Integer32(0..100)
            MAX-ACCESS read-create
            STATUS current
            DESCRIPTION
                "The amplitude value(0.1dbm) of Frequency2."
        ::= { hwEntToneEntry  6 }
		
		hwEntToneFrequency3Freq OBJECT-TYPE
            SYNTAX Integer32(0..4000)
            MAX-ACCESS read-create
            STATUS current
            DESCRIPTION
                "The Frequency value(Hz) of Frequency3."
        ::= { hwEntToneEntry 7 }

        hwEntToneFrequency3Ampl OBJECT-TYPE
            SYNTAX Integer32(0..100)
            MAX-ACCESS read-create
            STATUS current
            DESCRIPTION
                "The amplitude value(0.1dbm) of Frequency3."
        ::= { hwEntToneEntry  8 }
		
		hwEntToneFrequency4Freq OBJECT-TYPE
            SYNTAX Integer32(0..4000)
            MAX-ACCESS read-create
            STATUS current
            DESCRIPTION
                "The Frequency value(Hz) of Frequency4."
        ::= { hwEntToneEntry 9 }

        hwEntToneFrequency4Ampl OBJECT-TYPE
            SYNTAX Integer32(0..100)
            MAX-ACCESS read-create
            STATUS current
            DESCRIPTION
                "The amplitude value(0.1dbm) of Frequency4."
        ::= { hwEntToneEntry  10 }
 
        hwEntToneCadenceSeq1OnTime OBJECT-TYPE
            SYNTAX Integer32 (0..65535)
            MAX-ACCESS read-create
            STATUS current
            DESCRIPTION
                "The on time value(ms) of sequence1."
        ::= { hwEntToneEntry 11 }

        hwEntToneCadenceSeq1OffTime OBJECT-TYPE
            SYNTAX Integer32(0..65535)
            MAX-ACCESS read-create
            STATUS current
            DESCRIPTION
                "The off time value(ms) of sequence1."
        ::= { hwEntToneEntry  12 }
		
		hwEntToneCadenceSeq1BFreqFlag OBJECT-TYPE
            SYNTAX Integer32(0..12)
            MAX-ACCESS read-create
            STATUS current
            DESCRIPTION
                "The base-frequency-flag of sequence1."
        ::= { hwEntToneEntry  13 }
		
		hwEntToneCadenceSeq2OnTime OBJECT-TYPE
            SYNTAX Integer32 (0..65535)
            MAX-ACCESS read-create
            STATUS current
            DESCRIPTION
                "The on time value(ms) of sequence2."
        ::= { hwEntToneEntry 14 }

        hwEntToneCadenceSeq2OffTime OBJECT-TYPE
            SYNTAX Integer32(0..65535)
            MAX-ACCESS read-create
            STATUS current
            DESCRIPTION
                "The off time value(ms) of sequence2."
        ::= { hwEntToneEntry  15 }

        hwEntToneCadenceSeq2BFreqFlag OBJECT-TYPE
            SYNTAX Integer32(0..12)
            MAX-ACCESS read-create
            STATUS current
            DESCRIPTION
                "The base-frequency-flag of sequence2."
        ::= { hwEntToneEntry  16 }

        hwEntToneCadenceSeq3OnTime OBJECT-TYPE
            SYNTAX Integer32 (0..65535)
            MAX-ACCESS read-create
            STATUS current
            DESCRIPTION
                "The on time value(ms) of sequence3."
        ::= { hwEntToneEntry 17 }

        hwEntToneCadenceSeq3OffTime OBJECT-TYPE
            SYNTAX Integer32(0..65535)
            MAX-ACCESS read-create
            STATUS current
            DESCRIPTION
                "The off time value(ms) of sequence3."
        ::= { hwEntToneEntry  18 }

        hwEntToneCadenceSeq3BFreqFlag OBJECT-TYPE
            SYNTAX Integer32(0..12)
            MAX-ACCESS read-create
            STATUS current
            DESCRIPTION
                "The base-frequency-flag of sequence3."
        ::= { hwEntToneEntry  19 }
		
		hwEntToneCadenceSeq4OnTime OBJECT-TYPE
            SYNTAX Integer32 (0..65535)
            MAX-ACCESS read-create
            STATUS current
            DESCRIPTION
                "The on time value(ms) of sequence4."
        ::= { hwEntToneEntry 20 }

        hwEntToneCadenceSeq4OffTime OBJECT-TYPE
            SYNTAX Integer32(0..65535)
            MAX-ACCESS read-create
            STATUS current
            DESCRIPTION
                "The off time value(ms) of sequence4."
        ::= { hwEntToneEntry  21 }

        hwEntToneCadenceSeq4BFreqFlag OBJECT-TYPE
            SYNTAX Integer32(0..12)
            MAX-ACCESS read-create
            STATUS current
            DESCRIPTION
                "The base-frequency-flag of sequence4."
        ::= { hwEntToneEntry  22 }
		
		
    --  ============== conformance information ==============
        hwEntVoicePublicConformance OBJECT IDENTIFIER ::= { hwEntVoicePublicMIB 7 }
        
        
        hwEntVoicePublicCompliances OBJECT IDENTIFIER ::= { hwEntVoicePublicConformance 1 }
        hwEntVoicePublicCompliance MODULE-COMPLIANCE
               STATUS      current
               DESCRIPTION
                   "The compliance statement for systems supporting 
                the this module."

               MODULE      -- this module
               MANDATORY-GROUPS    {hwEntSysParaConfigGroup, hwEntVoipAddressGroup, hwEntPbxStateGroup, 
               			hwEntSipagStateGroup, hwEntCallStaticsGroup, hwEntPbxTrunkCallStaticsGroup}  
                                               
              ::= { hwEntVoicePublicCompliances 1 }  
              
          
        --  ============== groups ==============  
        hwEntVoicePublicGroups OBJECT IDENTIFIER ::= { hwEntVoicePublicConformance 2 } 
        
	   hwEntSysParaConfigGroup OBJECT-GROUP
	     OBJECTS
	     {
	       	hwEntSysParaCountry,
		hwEntSysParaStopInitialRing,
		hwEntSysParaMwiMode,
		hwEntSysParaFlashHookUpper,
		hwEntSysParaFlashHookLower,
		hwEntSysParaParkFeed,
		hwEntSysParaPcm,
		hwEntSysParaRingFrequency,
		hwEntSysParaRingAcAmplitude,
		hwEntSysParaGlobalDigitmap,
		hwEntSysParaSctpSendChecksum,
		hwEntSysParaSctpReceiveChecksum,
		hwEntSysParaVoipVpnInstance
	     }
	    STATUS current
            DESCRIPTION 
                "The hwEntSysParaConfig group."
            ::= { hwEntVoicePublicGroups 1 }
 
 	hwEntVoipAddressGroup OBJECT-GROUP
	     OBJECTS
	     {
		hwEntVoipAddressType,
		hwEntVoipInterfaceType,
		hwEntVoipInterfaceId,
		hwEntVoipMethod,
		hwEntVoipIPAddress,
		hwEntVoipAddressRowStatus
	     }
	    STATUS current
            DESCRIPTION 
                "The HwEntVoipAddress group."
            ::= { hwEntVoicePublicGroups 2 }           

 	hwEntPbxStateGroup OBJECT-GROUP
	     OBJECTS
	     {
	       	hwEntPbxStatePotsUserNum,
		hwEntPbxStateBraUserNum,
		hwEntPbxStateSipueUserNum,
		hwEntPbxAt0TrkNum,
		hwEntPbxPraTrkNum,
		hwEntPbxR2TrkNum,
		hwEntPbxSipat0TrkNum,
		hwEntPbxSipTrkGrpNum,
		hwEntPbxStateOnlineUserNum,
		hwEntPbxStateMaxCallNum,
		hwEntPbxStateSipipTrkGrpMaxCr,
		hwEntPbxStateSippraTrkGrpMaxCr,
		hwEntPbxStateSipat0TrkGrpMaxCr
	     }
	    STATUS current
            DESCRIPTION 
                "The hwEntPbxState group."
            ::= { hwEntVoicePublicGroups 3 }      
            
 	hwEntSipagStateGroup OBJECT-GROUP
	     OBJECTS
	     {
	       	hwEntSipagStatePotsUserNum,
		hwEntSipagStateBraUserNum,
		hwEntSipagStatePraUserNum,
		hwEntSipagStateSipagNum,
		hwEntSipagStateOnlineNum,
		hwEntSipagStateMaxCallNum,
		hwEntSipagStateBestFlag
	     }
	    STATUS current
            DESCRIPTION 
                "The hwEntSipagState group."
            ::= { hwEntVoicePublicGroups 4 }      

 	hwEntCallStaticsGroup OBJECT-GROUP
	     OBJECTS
	     {
	       	hwEntCallStaticsAttemptCall,
		hwEntCallStaticsAlertingCall,
		hwEntCallStaticsAnswerCall,
		hwEntCallStaticTotalCallTime
	     }
	    STATUS current
            DESCRIPTION 
                "The hwEntCallStatics group."
            ::= { hwEntVoicePublicGroups 5 }      
            
 	hwEntPbxTrunkCallStaticsGroup OBJECT-GROUP
	     OBJECTS
	     {
		hwEntPbxTrunkCallStaticsTrkGrpType,
		hwEntPbxTrunkCallStaticsAttemptCall,
		hwEntPbxTrunkCallStaticsAlertingCall,
		hwEntPbxTrunkCallStaticsAnswerCall,
		hwEntPbxTrunkCallStaticsTotalCallTime,
		hwEntPbxTrunkCallStaticsTrunkNum, 
		hwEntPbxTrunkCallStaticsTrunkOccupyPer
	     }
	    STATUS current
            DESCRIPTION 
                "The hwEntPbxTrunkCallStaticsGroup group."
            ::= { hwEntVoicePublicGroups 6 }          
    
END

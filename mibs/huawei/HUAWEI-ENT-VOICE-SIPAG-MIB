-- ============================================================================
-- Copyright (C) 2011 by HUAWEI TECHNOLOGIES. All rights reserved.
--
-- Description: This mib is used for defining huawei's SIP MIB objects, which provides SIP management.
-- Reference:
-- Version: V1.0
-- History:
-- ============================================================================

HUAWEI-ENT-VOICE-SIPAG-MIB DEFINITIONS ::= BEGIN
	IMPORTS
		MODULE-IDENTITY, OBJECT-TYPE, NOTIFICATION-TYPE, private
			FROM SNMPv2-SMI
		MODULE-COMPLIANCE, OBJECT-GROUP, NOTIFICATION-GROUP
			FROM SNMPv2-CONF
		TEXTUAL-CONVENTION
			FROM SNMPv2-TC
		IpAddress, TimeTicks, Counter32, Integer32, Unsigned32
			FROM SNMPv2-SMI
		RowStatus, DisplayString
			FROM SNMPv2-TC
		hwDatacomm
			FROM HUAWEI-MIB;

hwEntVoiceSipagMIB MODULE-IDENTITY
	LAST-UPDATED "201107010000Z"
      ORGANIZATION 
                "Huawei Technologies Co.,Ltd."
      CONTACT-INFO 
              "Huawei Industrial Base                
              Bantian, Longgang                     
              Shenzhen 518129                       
              People's Republic of China            
              Website: http://www.huawei.com        
              Email: support@huawei.com             
              "   
	DESCRIPTION
		"This mib is used for defining huawei's SIP MIB objects, which provides SIP management."

	-- Revision history

	REVISION	 "201107010000Z"
	DESCRIPTION  "V1.0, create this file."

::= { hwDatacomm 250 }

  --========================================================================

  hwEntSipAgConfigTable OBJECT-TYPE
     SYNTAX      SEQUENCE OF HwEntSipAgConfigEntry
     MAX-ACCESS  not-accessible
     STATUS      current
     DESCRIPTION
       "
       This table is used to config the parameters of SipAg.
       The index of this table is hwEntSipAgId.
       "
     ::= { hwEntVoiceSipagMIB 1 }

   hwEntSipAgConfigEntry OBJECT-TYPE
     SYNTAX      HwEntSipAgConfigEntry
     MAX-ACCESS  not-accessible
     STATUS      current
     DESCRIPTION
       "
       This table is used to config the parameters of SipAg.
       The index of this entry is hwEntSipAgId.
       "
     INDEX    {
                hwEntSipAgId
              }
     ::= { hwEntSipAgConfigTable 1 }

   HwEntSipAgConfigEntry ::=
     SEQUENCE
     {
       hwEntSipAgId                         Integer32,
       hwEntSipAgMediaIPAddress             IpAddress,
       hwEntSipAgSignallingIPAddress        IpAddress,
       hwEntSipAgSignallingPort             Integer32,
       hwEntSipAgMediaAddrName              DisplayString,
       hwEntSipAgSignallingAddrName         DisplayString,
       hwEntSipAgTransMode                  INTEGER,
       hwEntSipAgDomainName                 DisplayString,
       hwEntSipAgHomeDomainName             DisplayString,
       hwEntSipAgRegisterUri                DisplayString,
       hwEntSipAgConferenceFactoryUri       DisplayString,
       hwEntSipAgDesc                       DisplayString,
       hwEntSipAgPhoneContext               DisplayString,
       hwEntSipAgAdminStatus                INTEGER,
       hwEntSipAgRowStatus                  RowStatus,
       hwEntSipAgProfileIndex               Integer32,
       hwEntSipAgProfileName                DisplayString,
       hwEntSipAgSrvLogicIndex              Integer32,
       hwEntSipAgSrvLogicName               DisplayString,
       hwEntSipAgServerDhcpOption           INTEGER,
       hwEntSipAgSwitchoverDestination      Integer32,
       hwEntSipAgAuthMode                   INTEGER,
       hwEntSipAgAuthPasswordMode           INTEGER,
       hwEntSipAgAuthUserName               DisplayString,
       hwEntSipAgAuthPassword               DisplayString,
       hwEntSipAgAuthHA1                    DisplayString,
       hwEntSipAgSubUAProfile               INTEGER,
       hwEntSipAgSubRegState                INTEGER,
       hwEntSipAgSubMwi                     INTEGER,
       hwEntSipAgSdpNegoMode                INTEGER,
       hwEntSipAgProxyDualHome              INTEGER,
       hwEntSipAgProxyDetectMode            INTEGER,
       hwEntSipAgProxyRefreshMode           INTEGER
    }

   hwEntSipAgId OBJECT-TYPE
     SYNTAX      Integer32(0..16777215)
     MAX-ACCESS  not-accessible
     STATUS      current
     DESCRIPTION
         "
         Sipag ID.
         "
     ::= { hwEntSipAgConfigEntry 1 }

   hwEntSipAgMediaIPAddress OBJECT-TYPE
     SYNTAX      IpAddress
     MAX-ACCESS  read-create
     STATUS      current
     DESCRIPTION
         "
         Indicates the media IP address.
         "
     ::= { hwEntSipAgConfigEntry 2 }

   hwEntSipAgSignallingIPAddress OBJECT-TYPE
     SYNTAX      IpAddress
     MAX-ACCESS  read-create
     STATUS      current
     DESCRIPTION
         "
         Indicates the signalling IP address.
         "
     ::= { hwEntSipAgConfigEntry 3 }

   hwEntSipAgSignallingPort OBJECT-TYPE
     SYNTAX      Integer32(5000..5999)
     MAX-ACCESS  read-create
     STATUS      current
     DESCRIPTION
         "
         Indicates the signalling port.
         "
     ::= { hwEntSipAgConfigEntry 4 }

   hwEntSipAgMediaAddrName OBJECT-TYPE
     SYNTAX      DisplayString(SIZE (0..64))
     MAX-ACCESS  read-create
     STATUS      current
     DESCRIPTION
         "
         Indicates the dynamic media IP name.
         "
     ::= { hwEntSipAgConfigEntry 5 }

   hwEntSipAgSignallingAddrName OBJECT-TYPE
     SYNTAX      DisplayString(SIZE (0..64))
     MAX-ACCESS  read-create
     STATUS      current
     DESCRIPTION
         "
         Indicates the dynamic signalliing IP name.
         "
     ::= { hwEntSipAgConfigEntry 6 }

    hwEntSipAgTransMode OBJECT-TYPE
     SYNTAX      INTEGER{tcp(1),udp(2),sctp(3)}
     MAX-ACCESS  read-create
     STATUS      current
     DESCRIPTION
         "
         Indicates the transfer mode.
         Options:
         tcp(1)    -TCP
         udp(2)    -UDP
         sctp(3)   -SCTP
         Default: udp(2)
         "
     ::= { hwEntSipAgConfigEntry 7 }

   hwEntSipAgDomainName OBJECT-TYPE
     SYNTAX      DisplayString(SIZE (0..64))
     MAX-ACCESS  read-create
     STATUS      current
     DESCRIPTION
         "
         Indicates the domain name of sipag.
         "
     ::= { hwEntSipAgConfigEntry 8 }

   hwEntSipAgHomeDomainName OBJECT-TYPE
     SYNTAX      DisplayString(SIZE (0..64))
     MAX-ACCESS  read-create
     STATUS      current
     DESCRIPTION
         "
         Indicates the home domain name.
         "
     ::= { hwEntSipAgConfigEntry 9 }

   hwEntSipAgRegisterUri OBJECT-TYPE
     SYNTAX      DisplayString(SIZE (0..64))
     MAX-ACCESS  read-create
     STATUS      current
     DESCRIPTION
         "
         Indicates the Register-URI.
         "
     ::= { hwEntSipAgConfigEntry 10 }

   hwEntSipAgConferenceFactoryUri OBJECT-TYPE
     SYNTAX      DisplayString(SIZE (0..64))
     MAX-ACCESS  read-create
     STATUS      current
     DESCRIPTION
         "
         Indicates the ConferenceFactory-URI.
         "
     ::= { hwEntSipAgConfigEntry 11 }

   hwEntSipAgDesc OBJECT-TYPE
     SYNTAX      DisplayString(SIZE (0..32))
     MAX-ACCESS  read-create
     STATUS      current
     DESCRIPTION
         "
         Indicates the Description.
         "
     ::= { hwEntSipAgConfigEntry 12 }

   hwEntSipAgPhoneContext OBJECT-TYPE
     SYNTAX      DisplayString(SIZE (0..32))
     MAX-ACCESS  read-create
     STATUS      current
     DESCRIPTION
         "
         Indicates the Phone Context.
         "
     ::= { hwEntSipAgConfigEntry 13 }

   hwEntSipAgRowStatus OBJECT-TYPE
     SYNTAX      RowStatus
     MAX-ACCESS  read-create
     STATUS      current
     DESCRIPTION
         "
         This is used to create new rows in this table, modify existing rows, and delete existing rows.
         "
     ::= { hwEntSipAgConfigEntry 14 }

   hwEntSipAgAdminStatus OBJECT-TYPE
     SYNTAX      INTEGER{reset(1),switchover(2)}
     MAX-ACCESS  read-create
     STATUS      current
     DESCRIPTION
         "
         Indicates the AdminStatus.
         Options:
         reset(1)       -reset
         switchover(2)  -switchover
         "
     ::= { hwEntSipAgConfigEntry 15 }

   hwEntSipAgSwitchoverDestination OBJECT-TYPE
     SYNTAX      Integer32(0..1)
     MAX-ACCESS  read-create
     STATUS      current
     DESCRIPTION
         "
         Indicates the target proxy of switchover.
         Options:
         0: primary proxy
         1: secondary proxy
         "
     ::= { hwEntSipAgConfigEntry 16 }

   hwEntSipAgProfileIndex OBJECT-TYPE
     SYNTAX      Integer32(0..3)
     MAX-ACCESS  read-create
     STATUS      current
     DESCRIPTION
         "
         Indicates the ProfileIndex.
         Default: 1
         "
     ::= { hwEntSipAgConfigEntry 17 }

   hwEntSipAgProfileName OBJECT-TYPE
     SYNTAX      DisplayString(SIZE (0..32))
     MAX-ACCESS  read-only
     STATUS      current
     DESCRIPTION
         "
         Indicates the ProfileName.
         "
     ::= { hwEntSipAgConfigEntry 18 }

   hwEntSipAgSrvLogicIndex OBJECT-TYPE
     SYNTAX      Integer32(0..9)
     MAX-ACCESS  read-create
     STATUS      current
     DESCRIPTION
         "
         Indicates the servelogic index.
         Default: 0
         "
     ::= { hwEntSipAgConfigEntry 19 }

   hwEntSipAgSrvLogicName OBJECT-TYPE
     SYNTAX      DisplayString(SIZE (0..32))
     MAX-ACCESS  read-only
     STATUS      current
     DESCRIPTION
         "
         Indicates the servelogic name.
         "
     ::= { hwEntSipAgConfigEntry 20 }

   hwEntSipAgServerDhcpOption OBJECT-TYPE
     SYNTAX      INTEGER{none(1),option120(2),option21(3)}
     MAX-ACCESS  read-create
     STATUS      current
     DESCRIPTION
         "
         Indicates the DHCP option.
         Options:
         none(1)        -none
         option120(2)   -option120
         option21(3)    -option21
         Default: none(1)
         "
     ::= { hwEntSipAgConfigEntry 21 }

    hwEntSipAgAuthMode OBJECT-TYPE
      SYNTAX      INTEGER{interface(1) ,user(2)}
      MAX-ACCESS  read-create
      STATUS      current
      DESCRIPTION
          "
          Indicates the user authentication mode.
          Options:
          interface(1)     -interface
          user(2)          -single user
          Default: user(2)
          "
      ::= { hwEntSipAgConfigEntry 22 }

   hwEntSipAgAuthUserName OBJECT-TYPE
     SYNTAX      DisplayString(SIZE (0..64))
     MAX-ACCESS  read-create
     STATUS      current
     DESCRIPTION
         "
         Indicates the auth username.
         "
     ::= { hwEntSipAgConfigEntry 23 }

   hwEntSipAgAuthPasswordMode OBJECT-TYPE
     SYNTAX      INTEGER{password(1),ha1(2)}
     MAX-ACCESS  read-create
     STATUS      current
     DESCRIPTION
         "
         Indicates the auth password mode.
         Options:
         password(1)   -auth by password
         ha1(2)        -auth by ha1
         Default: password(1)
         "
     ::= { hwEntSipAgConfigEntry 24 }

    hwEntSipAgAuthPassword OBJECT-TYPE
     SYNTAX      DisplayString(SIZE (0..64))
     MAX-ACCESS  read-create
     STATUS      current
     DESCRIPTION
         "
         Indicates the auth password.
         "
     ::= { hwEntSipAgConfigEntry 25 }

   hwEntSipAgAuthHA1 OBJECT-TYPE
     SYNTAX      DisplayString(SIZE (0..32))
     MAX-ACCESS  read-create
     STATUS      current
     DESCRIPTION
         "
         Indicates the auth ha1 password.
         "
     ::= { hwEntSipAgConfigEntry 26 }

    hwEntSipAgSubUAProfile OBJECT-TYPE
    SYNTAX      INTEGER{enable(1), disable(2)}
    MAX-ACCESS  read-create
    STATUS      current
    DESCRIPTION
     "
     Indicates the flag to subscribe to UA-Profile.
     Options:
     enable(1)
     disable(2)
     Default: enable(1)
     "
    ::= { hwEntSipAgConfigEntry 27 }

    hwEntSipAgSubRegState OBJECT-TYPE
    SYNTAX      INTEGER{enable(1), disable(2)}
    MAX-ACCESS  read-create
    STATUS      current
    DESCRIPTION
     "
     Indicates the flag to subscribe to REG-STATE.
     Options:
     enable(1)
     disable(2)
     Default: disable(2)
     "
    ::= { hwEntSipAgConfigEntry 28 }

    hwEntSipAgSubMwi OBJECT-TYPE
    SYNTAX      INTEGER{enable(1), disable(2)}
    MAX-ACCESS  read-create
    STATUS      current
    DESCRIPTION
     "
     Indicates the flag to subscribe to MWI.
     Options:
     enable(1)
     disable(2)
     Default: disable(2)
     "
    ::= { hwEntSipAgConfigEntry 29 }

    hwEntSipAgSdpNegoMode OBJECT-TYPE
    SYNTAX      INTEGER{local(1), remote(2)}
    MAX-ACCESS  read-create
    STATUS      current
    DESCRIPTION
     "
     Indicates the SDP negotiation mode.
     Options:
     local(1)    -Local end takes priority when codec negotiation
     remote(2)   -Remote end takes priority when codec negotiation
     Default: remote(2)
     "
    ::= { hwEntSipAgConfigEntry 30 }

    hwEntSipAgProxyDualHome OBJECT-TYPE
    SYNTAX      INTEGER{ no(1), dualhome(2), autoswitchover(3)}
    MAX-ACCESS  read-create
    STATUS      current
    DESCRIPTION
     "
     Indicates the mode of supporting proxy dual-homing.
     Options:
     no(1)             -not support proxy dual-homing
     dualhome(2)       -support proxy dual-homing, but not support auto switchover
     autoswitchover(3) -support proxy dual-homing and auto switchover
     Default: dualhome(2)
     "
    ::= { hwEntSipAgConfigEntry 31 }

    hwEntSipAgProxyDetectMode OBJECT-TYPE
    SYNTAX      INTEGER{ option(1) , probe(2), register(3)}
    MAX-ACCESS  read-create
    STATUS      current
    DESCRIPTION
     "
     Indicate the proxy detection mode.
     Options:
     option(1)    -detect proxy by option message
     probe(2)     -detect proxy by probe mode
     register(3)  -detect proxy by register message
     Default: probe(2)
     "
    ::= { hwEntSipAgConfigEntry 32 }

    hwEntSipAgProxyRefreshMode OBJECT-TYPE
    SYNTAX      INTEGER { immediate(1), defer(2), noswitch(3), null(255) }
    MAX-ACCESS  read-create
    STATUS      current
    DESCRIPTION
     "
     Indicate Proxy address refresh mode.
     Options:
     immediate(1)     -immediate switch
     defer(2)         -switch in no calls cases
     no-switch(3)     -no switch
     null(255)        -invalid value
     "
    ::= { hwEntSipAgConfigEntry 33 }

  --========================================================================

  hwEntSipAgRunningTable OBJECT-TYPE
     SYNTAX      SEQUENCE OF HwEntSipAgRunningEntry
     MAX-ACCESS  not-accessible
     STATUS      current
     DESCRIPTION
       "
       This table is used to query the running parameters.
       The index of this table is hwEntSipAgId.
       "
     ::= { hwEntVoiceSipagMIB 2 }

   hwEntSipAgRunningEntry OBJECT-TYPE
     SYNTAX      HwEntSipAgRunningEntry
     MAX-ACCESS  not-accessible
     STATUS      current
     DESCRIPTION
       "
       This table is used to query the running parameters.
       The index of this entry is hwEntSipAgId.
       "
     INDEX    {
                hwEntSipAgRunningId
              }
     ::= { hwEntSipAgRunningTable 1 }

   HwEntSipAgRunningEntry ::=
     SEQUENCE
     {
       hwEntSipAgRunningId                        Integer32,
       hwEntSipAgRunningMediaIPAddress            IpAddress,
       hwEntSipAgRunningSignallingIPAddress       IpAddress,
       hwEntSipAgRunningSignallingPort            Integer32,
       hwEntSipAgRunningMediaAddrName             DisplayString,
       hwEntSipAgRunningSignallingAddrName        DisplayString,
       hwEntSipAgRunningTransMode                 INTEGER,
       hwEntSipAgRunningDomainName                DisplayString,
       hwEntSipAgRunningHomeDomainName            DisplayString,
       hwEntSipAgRunningRegisterUri               DisplayString,
       hwEntSipAgRunningConferenceFactoryUri      DisplayString,
       hwEntSipAgRunningDesc                      DisplayString,
       hwEntSipAgRunningPhoneContext              DisplayString,
       hwEntSipAgRunningProfileIndex              Integer32,
       hwEntSipAgRunningProfileName               DisplayString,
       hwEntSipAgRunningSrvLogicIndex             Integer32,
       hwEntSipAgRunningSrvLogicName              DisplayString,
       hwEntSipAgRunningServerDhcpOption          INTEGER,
       hwEntSipAgRunningAuthMode                  INTEGER,
       hwEntSipAgRunningAuthUserName              DisplayString,
       hwEntSipAgRunningAuthPasswordMode          INTEGER,
       hwEntSipAgRunningAuthPassword              DisplayString,
       hwEntSipAgRunningAuthHA1                   DisplayString,
       hwEntSipAgRunningSubUAProfile              INTEGER,
       hwEntSipAgRunningSubRegState               INTEGER,
       hwEntSipAgRunningSubMwi                    INTEGER,
       hwEntSipAgRunningSdpNegoMode               INTEGER,
       hwEntSipAgRunningProxyDualHome             INTEGER,
       hwEntSipAgRunningProxyDetectMode           INTEGER,
       hwEntSipAgRunningProxyRefreshMode          INTEGER,
       hwEntSipAgRunningState                     INTEGER
     }

    hwEntSipAgRunningId OBJECT-TYPE
     SYNTAX      Integer32(0..16777215)
     MAX-ACCESS  not-accessible
     STATUS      current
     DESCRIPTION
         "
         Sipag ID.
         "
     ::= { hwEntSipAgRunningEntry 1 }
    
    hwEntSipAgRunningMediaIPAddress OBJECT-TYPE
     SYNTAX      IpAddress
     MAX-ACCESS  read-only
     STATUS      current
     DESCRIPTION
         "
         Indicates the media ip address.
         "
     ::= { hwEntSipAgRunningEntry 2 }

    hwEntSipAgRunningSignallingIPAddress OBJECT-TYPE
     SYNTAX      IpAddress
     MAX-ACCESS  read-only
     STATUS      current
     DESCRIPTION
         "
         Indicates the signalling ip address.
         "
     ::= { hwEntSipAgRunningEntry 3 }

    hwEntSipAgRunningSignallingPort OBJECT-TYPE
     SYNTAX      Integer32(5000..5999)
     MAX-ACCESS  read-only
     STATUS      current
     DESCRIPTION
         "
         Indicates the Signalling Port.
         "
     ::= { hwEntSipAgRunningEntry 4 }

   hwEntSipAgRunningMediaAddrName OBJECT-TYPE
     SYNTAX      DisplayString(SIZE (0..64))
     MAX-ACCESS  read-only
     STATUS      current
     DESCRIPTION
         "
         Indicates the current dynamic media IP name.
         "
     ::= { hwEntSipAgRunningEntry 5 }

   hwEntSipAgRunningSignallingAddrName OBJECT-TYPE
     SYNTAX      DisplayString(SIZE (0..64))
     MAX-ACCESS  read-only
     STATUS      current
     DESCRIPTION
         "
         Indicates the current dynamic signalling IP name.
         "
     ::= { hwEntSipAgRunningEntry 6 }

    hwEntSipAgRunningTransMode OBJECT-TYPE
     SYNTAX      INTEGER{tcp(1),udp(2),sctp(3),null(255)}
     MAX-ACCESS  read-only
     STATUS      current
     DESCRIPTION
         "
         Indicates the Transfer Mode. null(255) means the interface is not started.
         Options:
         tcp(1)     -TCP
         udp(2)     -UDP
         sctp(3)    -SCTP
         null(255)  -interface is not started
         "
     ::= { hwEntSipAgRunningEntry 7 }

   hwEntSipAgRunningDomainName OBJECT-TYPE
     SYNTAX     DisplayString(SIZE (0..64))
     MAX-ACCESS  read-only
     STATUS      current
     DESCRIPTION
         "
         Indicates the domain name of sipag.
         "
     ::= { hwEntSipAgRunningEntry 8 }

   hwEntSipAgRunningHomeDomainName OBJECT-TYPE
     SYNTAX      DisplayString(SIZE (0..64))
     MAX-ACCESS  read-only
     STATUS      current
     DESCRIPTION
         "
         Indicates the home domain name.
         "
     ::= { hwEntSipAgRunningEntry 9 }

   hwEntSipAgRunningRegisterUri OBJECT-TYPE
     SYNTAX      DisplayString(SIZE (0..64))
     MAX-ACCESS  read-only
     STATUS      current
     DESCRIPTION
         "
         Indicates the register-URI.
         "
     ::= { hwEntSipAgRunningEntry 10 }

   hwEntSipAgRunningConferenceFactoryUri OBJECT-TYPE
     SYNTAX      DisplayString(SIZE (0..64))
     MAX-ACCESS  read-only
     STATUS      current
     DESCRIPTION
         "
         Indicates the conferencefactory-URI.
         "
     ::= { hwEntSipAgRunningEntry 11 }

   hwEntSipAgRunningDesc OBJECT-TYPE
     SYNTAX      DisplayString(SIZE (0..32))
     MAX-ACCESS  read-only
     STATUS      current
     DESCRIPTION
         "
         Indicates the description of sipag.
         "
     ::= { hwEntSipAgRunningEntry 12 }

   hwEntSipAgRunningPhoneContext OBJECT-TYPE
     SYNTAX      DisplayString(SIZE (0..32))
     MAX-ACCESS  read-only
     STATUS      current
     DESCRIPTION
         "
         Indicates the phone context.
         "
     ::= { hwEntSipAgRunningEntry 13 }

   hwEntSipAgRunningProfileIndex OBJECT-TYPE
     SYNTAX      Integer32(0..3)
     MAX-ACCESS  read-only
     STATUS      current
     DESCRIPTION
         "
         Indicates the profile index.
         "
     ::= { hwEntSipAgRunningEntry 14 }

   hwEntSipAgRunningProfileName OBJECT-TYPE
     SYNTAX      DisplayString(SIZE (0..32))
     MAX-ACCESS  read-only
     STATUS      current
     DESCRIPTION
         "
         Indicates the ProfileName.
         "
     ::= { hwEntSipAgRunningEntry 15 }

   hwEntSipAgRunningSrvLogicIndex OBJECT-TYPE
     SYNTAX      Integer32(0..9)
     MAX-ACCESS  read-only
     STATUS      current
     DESCRIPTION
         "
         Indicates the servelogic index.
         "
     ::= { hwEntSipAgRunningEntry 16 }

   hwEntSipAgRunningSrvLogicName OBJECT-TYPE
     SYNTAX      DisplayString(SIZE (0..32))
     MAX-ACCESS  read-only
     STATUS      current
     DESCRIPTION
         "
         Indicates the servelogic name.
         "
     ::= { hwEntSipAgRunningEntry 17 }

   hwEntSipAgRunningServerDhcpOption OBJECT-TYPE
     SYNTAX      INTEGER{none(1),option120(2),option21(3)}
     MAX-ACCESS  read-only
     STATUS      current
     DESCRIPTION
         "
         Indicates the DHCP option.
         Options:
         none(1)       -none
         option120(2)  -option120
         option21(3)   -option21
         "

     ::= { hwEntSipAgRunningEntry 18 }

   hwEntSipAgRunningAuthMode OBJECT-TYPE
     SYNTAX      INTEGER{interface(1), user(2)}
     MAX-ACCESS  read-only
     STATUS      current
     DESCRIPTION
         "
         Indicates user authentication mode.
         Options:
         interface(1)    -interface
         user(2)   -single user
         "
     ::= { hwEntSipAgRunningEntry 19 }

   hwEntSipAgRunningAuthUserName OBJECT-TYPE
     SYNTAX      DisplayString(SIZE (0..64))
     MAX-ACCESS  read-only
     STATUS      current
     DESCRIPTION
         "
         Indicates the auth username.
         "
     ::= { hwEntSipAgRunningEntry 20 }

   hwEntSipAgRunningAuthPasswordMode OBJECT-TYPE
     SYNTAX      INTEGER{password(1),ha1(2)}
     MAX-ACCESS  read-only
     STATUS      current
     DESCRIPTION
         "
         Indicates the auth password mode.
         Options:
         password(1)   -password
         ha1(2)        -HA1
         "
     ::= { hwEntSipAgRunningEntry 21 }

    hwEntSipAgRunningAuthPassword OBJECT-TYPE
     SYNTAX      DisplayString(SIZE (0..64))
     MAX-ACCESS  read-only
     STATUS      current
     DESCRIPTION
         "
         Indicates the auth password.
         "
     ::= { hwEntSipAgRunningEntry 22 }

  hwEntSipAgRunningAuthHA1 OBJECT-TYPE
     SYNTAX      DisplayString(SIZE (0..32))
     MAX-ACCESS  read-only
     STATUS      current
     DESCRIPTION
         "
         Indicates the auth ha1 password.
         "
     ::= { hwEntSipAgRunningEntry 23 }

     hwEntSipAgRunningSubUAProfile OBJECT-TYPE
     SYNTAX      INTEGER{enable(1), disable(2)}
     MAX-ACCESS  read-only
     STATUS      current
     DESCRIPTION
         "
         Indicates the flag to subscribe to UA-Profile.
         Options:
         enable(1)
         disable(2)
         "
     ::= { hwEntSipAgRunningEntry 24 }

     hwEntSipAgRunningSubRegState OBJECT-TYPE
     SYNTAX      INTEGER{enable(1), disable(2)}
     MAX-ACCESS  read-only
     STATUS      current
     DESCRIPTION
         "
         Indicates the flag to subscribe to REG-STATE.
         Options:
         enable(1)
         disable(2)
         "
     ::= { hwEntSipAgRunningEntry 25 }

     hwEntSipAgRunningSubMwi OBJECT-TYPE
     SYNTAX      INTEGER{enable(1), disable(2)}
     MAX-ACCESS  read-only
     STATUS      current
     DESCRIPTION
         "
         Indicates the flag to subscribe to MWI.
         Options:
         enable(1)
         disable(2)
         "
     ::= { hwEntSipAgRunningEntry 26 }

    hwEntSipAgRunningSdpNegoMode OBJECT-TYPE
    SYNTAX      INTEGER{local(1), remote (2)}
    MAX-ACCESS  read-only
    STATUS      current
    DESCRIPTION
        "
        Indicates the SDP negotiation mode.
        Options:
        local(1)    -local first
        remote(2)   -remote first
        "
       ::= { hwEntSipAgRunningEntry 27 }

    hwEntSipAgRunningProxyDualHome OBJECT-TYPE
    SYNTAX      INTEGER{ no(1), dualhome(2), autoswitchover(3)}
    MAX-ACCESS  read-only
    STATUS      current
    DESCRIPTION
        "
        Indicate the mode of supporting proxy dual-homing.
        Options:
        no(1)              -not support proxy dual-homing
        dualhome(2)        -support proxy dual-homing, but not support auto switchover
        autoswitchover(3)  -support proxy dual-homing and auto switchover
        "
       ::= { hwEntSipAgRunningEntry 28 }

    hwEntSipAgRunningProxyDetectMode OBJECT-TYPE
    SYNTAX      INTEGER{ option(1) , probe(2), register(3)}
    MAX-ACCESS  read-only
    STATUS      current
    DESCRIPTION
     "
     Indicates the proxy detection mode.
     Options:
     option(1)     -detection proxy by option message
     probe(2)      -detection proxy by probe mode
     register(3)   -detection proxy by register message
     "
    ::= { hwEntSipAgRunningEntry 29 }

    hwEntSipAgRunningProxyRefreshMode OBJECT-TYPE
    SYNTAX      INTEGER { immediate(1), defer(2), noswitch(3) }
    MAX-ACCESS  read-only
    STATUS      current
    DESCRIPTION
     "
     Indicate Proxy address refresh mode.
     Options:
     immediate(1)    -immediate switch
     defer(2)        -switch in no calls cases
     no-switch(3)    -no switch
     "
    ::= { hwEntSipAgRunningEntry 30 }

  hwEntSipAgRunningState OBJECT-TYPE
    SYNTAX      INTEGER{ notStart(1) , fault(2), normal(3) }
    MAX-ACCESS  read-only
    STATUS      current
    DESCRIPTION
     "
     Indicate the sipag state.
     Options:
     notStart(1)
     fault(2)
     normal(3)
     "       
    ::= { hwEntSipAgRunningEntry 31 }  
    
  --========================================================================

  hwEntSipAgProxyTable OBJECT-TYPE
     SYNTAX      SEQUENCE OF HwEntSipAgProxyEntry
     MAX-ACCESS  not-accessible
     STATUS      current
     DESCRIPTION
       "
       This table is used to config the parameters of sipag proxy.
       The indexes of this table are hwEntSipAgId, hwSipAgProxyIndex.
       "
     ::= { hwEntVoiceSipagMIB 3 }

   hwEntSipAgProxyEntry OBJECT-TYPE
     SYNTAX      HwEntSipAgProxyEntry
     MAX-ACCESS  not-accessible
     STATUS      current
     DESCRIPTION
       "
       This table is used to config the parameters of sipag proxy.
       The indexes of this entry are hwEntSipAgId, hwSipAgProxyIndex.
       "
     INDEX    {
                hwEntSipAgProxyId,
                hwSipAgProxyIndex
              }
     ::= { hwEntSipAgProxyTable 1 }

   HwEntSipAgProxyEntry ::=
     SEQUENCE
     {
       hwEntSipAgProxyId          Integer32,
       hwSipAgProxyIndex          Integer32,
       hwSipAgProxyIPAddress1     IpAddress,
       hwSipAgProxyIPAddress2     IpAddress,
       hwSipAgProxyPort           Integer32,
       hwSipAgProxyDomainName     DisplayString,
       hwSipAgProxyAddressMode    INTEGER
    }

    hwEntSipAgProxyId OBJECT-TYPE
     SYNTAX      Integer32(0..16777215)
     MAX-ACCESS  not-accessible
     STATUS      current
     DESCRIPTION
         "
         Sipag ID.
         "
     ::= { hwEntSipAgProxyEntry 1 }
     
    hwSipAgProxyIndex OBJECT-TYPE
     SYNTAX      Integer32(0..1)
     MAX-ACCESS  not-accessible
     STATUS      current
     DESCRIPTION
         "
         proxy index.
         0: main
         1: standby
         "
     ::= { hwEntSipAgProxyEntry 2 }

    hwSipAgProxyIPAddress1 OBJECT-TYPE
     SYNTAX      IpAddress
     MAX-ACCESS  read-write
     STATUS      current
     DESCRIPTION
         "
         Indicates the proxy IP address1.
         "
     ::= { hwEntSipAgProxyEntry 3 }
     
    hwSipAgProxyIPAddress2 OBJECT-TYPE
     SYNTAX      IpAddress
     MAX-ACCESS  read-write
     STATUS      current
     DESCRIPTION
         "
         Indicates the proxy IP address2.
         "
     ::= { hwEntSipAgProxyEntry 4 }

    hwSipAgProxyPort OBJECT-TYPE
     SYNTAX      Integer32(1..65535)
     MAX-ACCESS  read-write
     STATUS      current
     DESCRIPTION
         "
         Indicates the proxy port.
         "
     ::= { hwEntSipAgProxyEntry 5 }

    hwSipAgProxyDomainName OBJECT-TYPE
     SYNTAX      DisplayString(SIZE (0..64))
     MAX-ACCESS  read-write
     STATUS      current
     DESCRIPTION
         "
         Indicates the proxy domain name.
         "
     ::= { hwEntSipAgProxyEntry 6 }

   hwSipAgProxyAddressMode OBJECT-TYPE
     SYNTAX      INTEGER { ip(1), dnsA(2), dnsSrv(3), dnsNaptr(4)}
     MAX-ACCESS  read-write
     STATUS      current
     DESCRIPTION
         "
         The proxy address mode.
         ip(1)
         dnsA(2)
         dnsSrv(3)
         dnsNaptr(4)
         "
     ::= { hwEntSipAgProxyEntry 7 }

  --========================================================================

  hwEntSipAgProxyRunningTable OBJECT-TYPE
     SYNTAX      SEQUENCE OF HwEntSipAgProxyRunningEntry
     MAX-ACCESS  not-accessible
     STATUS      current
     DESCRIPTION
       "
       This table is used to query the running parameters of sipag proxy.
       The indexes of this table are hwEntSipAgId, hwSipAgProxyIndex.
       "
     ::= { hwEntVoiceSipagMIB 4 }

   hwEntSipAgProxyRunningEntry OBJECT-TYPE
     SYNTAX      HwEntSipAgProxyRunningEntry
     MAX-ACCESS  not-accessible
     STATUS      current
     DESCRIPTION
       "
       This table is used to query the running parameters sipag proxy.
       The indexes of this entry are hwEntSipAgId, hwSipAgProxyIndex.
       "
     INDEX    {
                hwEntSipAgProxyRunningId,
                hwSipAgProxyRunningIndex
              }
     ::= { hwEntSipAgProxyRunningTable 1 }

   HwEntSipAgProxyRunningEntry ::=
     SEQUENCE
     {
       hwEntSipAgProxyRunningId        Integer32,
       hwSipAgProxyRunningIndex        Integer32,
       hwSipAgProxyRunningIPAddress1   IpAddress,
       hwSipAgProxyRunningIPAddress2   IpAddress,
       hwSipAgProxyRunningPort         Integer32,
       hwSipAgProxyRunningDomainName   DisplayString,
       hwSipAgProxyRunningAddressMode  INTEGER,
       hwSipAgProxyRunningState        INTEGER
    }
   
   hwEntSipAgProxyRunningId OBJECT-TYPE
     SYNTAX      Integer32(0..16777215)
     MAX-ACCESS  not-accessible
     STATUS      current
     DESCRIPTION
         "
         Sipag ID.
         "
     ::= { hwEntSipAgProxyRunningEntry 1 }
     
   hwSipAgProxyRunningIndex OBJECT-TYPE
     SYNTAX      Integer32(0..1)
     MAX-ACCESS  not-accessible
     STATUS      current
     DESCRIPTION
         "
         proxy index.
         0: main
         1: standby
         "
     ::= { hwEntSipAgProxyRunningEntry 2 }  
   
   hwSipAgProxyRunningIPAddress1 OBJECT-TYPE
     SYNTAX      IpAddress
     MAX-ACCESS  read-only
     STATUS      current
     DESCRIPTION
         "
         Indicates the proxy IP address1.
         "
     ::= { hwEntSipAgProxyRunningEntry 3 }

   hwSipAgProxyRunningIPAddress2 OBJECT-TYPE
     SYNTAX      IpAddress
     MAX-ACCESS  read-only
     STATUS      current
     DESCRIPTION
         "
         Indicates the proxy IP address2.
         "
     ::= { hwEntSipAgProxyRunningEntry 4 }

   hwSipAgProxyRunningPort OBJECT-TYPE
     SYNTAX      Integer32(1..65535)
     MAX-ACCESS  read-only
     STATUS      current
     DESCRIPTION
         "
         Indicates the Proxy Port.
         "
     ::= { hwEntSipAgProxyRunningEntry 5 }

   hwSipAgProxyRunningDomainName OBJECT-TYPE
     SYNTAX      DisplayString(SIZE (0..64))
     MAX-ACCESS  read-only
     STATUS      current
     DESCRIPTION
         "
         Indicates the proxy domain name.
         "
     ::= { hwEntSipAgProxyRunningEntry 6 }

   hwSipAgProxyRunningAddressMode OBJECT-TYPE
     SYNTAX      INTEGER {ip(1),dnsA(2),dnsSrv(3),dnsNaptr(4)}
     MAX-ACCESS  read-only
     STATUS      current
     DESCRIPTION
         "
         The proxy address mode.
         ip(1)
         dnsA(2)
         dnsSrv(3)
         dnsNaptr(4)
         "
     ::= { hwEntSipAgProxyRunningEntry 7 }

   hwSipAgProxyRunningState OBJECT-TYPE
     SYNTAX      INTEGER {unknown(1), down(2), up(3) }
     MAX-ACCESS  read-only
     STATUS      current
     DESCRIPTION
         "
         The proxy state.
         unknown(1)
         down(2)
         up(3)
         "
     ::= { hwEntSipAgProxyRunningEntry 8 }

  --========================================================================

   hwEntSipProfileTable OBJECT-TYPE
     SYNTAX      SEQUENCE OF HwEntSipProfileEntry
     MAX-ACCESS  not-accessible
     STATUS      current
     DESCRIPTION
       "
       This table is used to query the sipag profile.
       The index of this table is hwEntSipProfileIndex.
       "
    ::= { hwEntVoiceSipagMIB 5 }

   hwEntSipProfileEntry OBJECT-TYPE
     SYNTAX      HwEntSipProfileEntry
     MAX-ACCESS  not-accessible
     STATUS      current
     DESCRIPTION
       "
       This table is used to config the Sip Profile.
       The index of this entry is hwEntSipProfileIndex.
       "
     INDEX    {
                hwEntSipProfileIndex
              }
    ::= { hwEntSipProfileTable 1 }

   HwEntSipProfileEntry ::=
     SEQUENCE
     {
       hwEntSipProfileIndex       Integer32,
       hwEntSipProfileName        DisplayString
     }

   hwEntSipProfileIndex OBJECT-TYPE
     SYNTAX      Integer32(0..3)
     MAX-ACCESS  not-accessible
     STATUS      current
     DESCRIPTION
         "
         Indicates the index of sipprofile.
         "
    ::= { hwEntSipProfileEntry 1 }

   hwEntSipProfileName OBJECT-TYPE
     SYNTAX      DisplayString(SIZE (0..32))
     MAX-ACCESS  read-only
     STATUS      current
     DESCRIPTION
         "
         Indicates the name of sipprofile.
         "
    ::= { hwEntSipProfileEntry 2 }

  --========================================================================

   hwEntSipSrvLogicTable OBJECT-TYPE
     SYNTAX      SEQUENCE OF HwEntSipSrvLogicEntry
     MAX-ACCESS  not-accessible
     STATUS      current
     DESCRIPTION
       "
       This table is used to config the Sip Serve-Logic list.
       The index of this table is hwEntSipSrvLogicIndex.
       "
    ::= { hwEntVoiceSipagMIB 6 }

   hwEntSipSrvLogicEntry OBJECT-TYPE
     SYNTAX      HwEntSipSrvLogicEntry
     MAX-ACCESS  not-accessible
     STATUS      current
     DESCRIPTION
       "
       This table is used to config the sip serve-logic list.
       The index of this entry is hwEntSipSrvLogicIndex.
       "
     INDEX    {
                hwEntSipSrvLogicIndex
              }
    ::= { hwEntSipSrvLogicTable 1 }

   HwEntSipSrvLogicEntry ::=
     SEQUENCE
     {
       hwEntSipSrvLogicIndex       Integer32,
       hwEntSipSrvLogicName        DisplayString
     }

   hwEntSipSrvLogicIndex OBJECT-TYPE
     SYNTAX      Integer32(0..9)
     MAX-ACCESS  not-accessible
     STATUS      current
     DESCRIPTION
         "
         Indicates the index of serve-logic.
         "
    ::= { hwEntSipSrvLogicEntry 1 }

   hwEntSipSrvLogicName OBJECT-TYPE
     SYNTAX      DisplayString(SIZE (0..32))
     MAX-ACCESS  read-only
     STATUS      current
     DESCRIPTION
         "
         Indicates the name of serve-logic.
         "
    ::= { hwEntSipSrvLogicEntry 2 }

  --========================================================================

  hwEntSipAgDmmParaTable OBJECT-TYPE
     SYNTAX      SEQUENCE OF HwEntSipAgDmmParaEntry
     MAX-ACCESS  not-accessible
     STATUS      current
     DESCRIPTION
       "
       This table is used to config the digitmap.
       The index of this table is hwEntSipAgId.
       "
     ::= { hwEntVoiceSipagMIB 7 }

  hwEntSipAgDmmParaEntry OBJECT-TYPE
     SYNTAX      HwEntSipAgDmmParaEntry
     MAX-ACCESS  not-accessible
     STATUS      current
     DESCRIPTION
       "
       This table is used to config the digitmap.
       The index of this entry is hwEntSipAgId.
       "
     INDEX    {
               hwEntSipAgDmmParaId
              }
     ::= { hwEntSipAgDmmParaTable 1 }

  HwEntSipAgDmmParaEntry ::=
     SEQUENCE
     {
       hwEntSipAgDmmParaId         Integer32,
       hwEntSipAgDmmParaStartTimer Integer32,
       hwEntSipAgDmmParaShortTimer Integer32,
       hwEntSipAgDmmParaLongTimer  Integer32
     }

  hwEntSipAgDmmParaId OBJECT-TYPE
     SYNTAX      Integer32(0..16777215)
     MAX-ACCESS  not-accessible
     STATUS      current
     DESCRIPTION
         "
         Sipag ID.
         "
     ::= { hwEntSipAgDmmParaEntry 1 }
     
  hwEntSipAgDmmParaStartTimer OBJECT-TYPE
     SYNTAX      Integer32(0..99)
     MAX-ACCESS  read-write
     STATUS      current
     DESCRIPTION
         "
         Indicates the length of the DMM start timer.
         Default: 20
         Unit: second
         "
     ::= { hwEntSipAgDmmParaEntry 2 }

  hwEntSipAgDmmParaShortTimer OBJECT-TYPE
     SYNTAX      Integer32(1..99)
     MAX-ACCESS  read-write
     STATUS      current
     DESCRIPTION
         "
         Indicates the length of the DMM short timer.
         Default: 4
         Unit: second
         "
     ::= { hwEntSipAgDmmParaEntry 3 }

  hwEntSipAgDmmParaLongTimer OBJECT-TYPE
     SYNTAX      Integer32(1..99)
     MAX-ACCESS  read-write
     STATUS      current
     DESCRIPTION
         "
         Indicates the length of the DMM long timer.
         Default: 20
         Unit: second
         "
     ::= { hwEntSipAgDmmParaEntry 4 }

  --========================================================================

  hwEntSipAgUserGroupTable OBJECT-TYPE
     SYNTAX      SEQUENCE OF HwEntSipAgUserGroupEntry
     MAX-ACCESS  not-accessible
     STATUS      current
     DESCRIPTION
       "
       This table is used to config the parameters of sip user group.
       The index of this table is hwEntSipAgUserGroupName.
       "
     ::= { hwEntVoiceSipagMIB 8 }

   hwEntSipAgUserGroupEntry OBJECT-TYPE
     SYNTAX      HwEntSipAgUserGroupEntry
     MAX-ACCESS  not-accessible
     STATUS      current
     DESCRIPTION
       "
       This table is used to config the parameters of sip user group.
       The index of this entry is hwEntSipAgUserGroupName.
       "
     INDEX    {
                hwEntSipAgUserGroupSipAgId,
                hwEntSipAgUserGroupId
              }
     ::= { hwEntSipAgUserGroupTable 1 }

   HwEntSipAgUserGroupEntry ::=
     SEQUENCE
     {
       hwEntSipAgUserGroupSipAgId	           Integer32,
       hwEntSipAgUserGroupId                       Integer32,
       hwEntSipAgUserGroupRegisterUriMode          INTEGER,
       hwEntSipAgUserGroupUri                      DisplayString,
       hwEntSipAgUserGroupGrpName                  DisplayString,
       hwEntSipAgUserGroupAuthUserName             DisplayString,
       hwEntSipAgUserGroupAuthPassWordMode         INTEGER,
       hwEntSipAgUserGroupAuthPassword             DisplayString,
       hwEntSipAgUserGroupAuthHA1                  DisplayString,
       hwEntSipAgUserGroupPrecinctMode             INTEGER,
       hwEntSipAgUserGroupSubUaProfile             INTEGER,
       hwEntSipAgUserGroupRowStatus                RowStatus,
       hwEntSipAgUserGroupAdminStatus              INTEGER,
       hwEntSipAgUserGroupRunningState             INTEGER
    }

    hwEntSipAgUserGroupSipAgId OBJECT-TYPE
     SYNTAX      Integer32(0..16777215)
     MAX-ACCESS  not-accessible
     STATUS      current
     DESCRIPTION
         "
         Sipag ID.
         "
     ::= { hwEntSipAgUserGroupEntry 1 }


    hwEntSipAgUserGroupId OBJECT-TYPE
     SYNTAX      Integer32(0..65535)
     MAX-ACCESS  not-accessible
     STATUS      current
     DESCRIPTION
         "
         User Group ID.
         "
     ::= { hwEntSipAgUserGroupEntry 2 }

   hwEntSipAgUserGroupRegisterUriMode OBJECT-TYPE
     SYNTAX      INTEGER{inneruser(1),alone(2)}
     MAX-ACCESS  read-create
     STATUS      current
     DESCRIPTION
         "
         Indicates the user group register URI mode.
         Options:
         inneruser(1)   -inner user
         alone(2)       -alone
         "
     ::= { hwEntSipAgUserGroupEntry 3 }

    hwEntSipAgUserGroupUri OBJECT-TYPE
     SYNTAX      DisplayString(SIZE (0..64))
     MAX-ACCESS  read-create
     STATUS      current
     DESCRIPTION
         "
         Indicates the Register-URI of the sip user group without the domain.
         "
     ::= { hwEntSipAgUserGroupEntry 4 }

    hwEntSipAgUserGroupGrpName OBJECT-TYPE
     SYNTAX      DisplayString(SIZE (0..64))
     MAX-ACCESS  read-create
     STATUS      current
     DESCRIPTION
         "
         Indicates the sip user group Name.
         "
     ::= { hwEntSipAgUserGroupEntry 5 }

    hwEntSipAgUserGroupAuthUserName OBJECT-TYPE
     SYNTAX      DisplayString(SIZE (0..64))
     MAX-ACCESS  read-create
     STATUS      current
     DESCRIPTION
         "
         Indicates the Auth Username of the sip user group.
         "
     ::= { hwEntSipAgUserGroupEntry 6 }

   hwEntSipAgUserGroupAuthPassWordMode OBJECT-TYPE
     SYNTAX      INTEGER{password(1),ha1(2)}
     MAX-ACCESS  read-create
     STATUS      current
     DESCRIPTION
         "
         Indicates the Auth PasswordMode of the sip user group.
         Options:
         password(1)   -auth by password
         ha1(2)        -auth by HA1
         Default: password(1)
         "
     ::= { hwEntSipAgUserGroupEntry 7 }

    hwEntSipAgUserGroupAuthPassword OBJECT-TYPE
     SYNTAX      DisplayString(SIZE (0..64))
     MAX-ACCESS  read-create
     STATUS      current
     DESCRIPTION
         "
         Indicates the Auth Password of the sip user group.
         "
     ::= { hwEntSipAgUserGroupEntry 8 }

    hwEntSipAgUserGroupAuthHA1 OBJECT-TYPE
     SYNTAX      DisplayString(SIZE (0..32))
     MAX-ACCESS  read-create
     STATUS      current
     DESCRIPTION
         "
         Indicates the Auth HA1 value of the sip user group.
         "
     ::= { hwEntSipAgUserGroupEntry 9 }

   hwEntSipAgUserGroupPrecinctMode OBJECT-TYPE
     SYNTAX      INTEGER{local(1), remote(2)}
     MAX-ACCESS  read-create
     STATUS      current
     DESCRIPTION
         "
         Indicates the user PrecinctMode in the sip user group.
         Options:
         local(1)
         remote(2)
         Default: local(1)
         "
     ::= { hwEntSipAgUserGroupEntry 10 }

   hwEntSipAgUserGroupSubUaProfile OBJECT-TYPE
     SYNTAX      INTEGER{enable(1),disable(2)}
     MAX-ACCESS  read-create
     STATUS      current
     DESCRIPTION
         "
         Indicates the flag of the user group with the same UA Profile privilege.
         Options:
         enable(1)
         disable(2)
         Default: enable(1)
         "
     ::= { hwEntSipAgUserGroupEntry 11 }

   hwEntSipAgUserGroupRowStatus OBJECT-TYPE
     SYNTAX      RowStatus
     MAX-ACCESS  read-create
     STATUS      current
     DESCRIPTION
         "
         This is used to create new rows in this table, modify existing rows, and to delete existing rows.
         "
     ::= { hwEntSipAgUserGroupEntry 12 }

   hwEntSipAgUserGroupAdminStatus OBJECT-TYPE
     SYNTAX      INTEGER{startservice(1), endservice(2)}
     MAX-ACCESS  read-create
     STATUS      current
     DESCRIPTION
         "
         Indicates the admin operation of the sip user group.
         Options:
         startservice(1)   -start service
         endservice(2)     -end service
         "
     ::= { hwEntSipAgUserGroupEntry 13 }

   hwEntSipAgUserGroupRunningState OBJECT-TYPE
     SYNTAX      INTEGER{startSvc(1),rBlock(2),lBlock(3)}
     MAX-ACCESS  read-only
     STATUS      current
     DESCRIPTION
         "
         Indicates the service state of user group.
         Options:
         startSvc(1)   -start service
         rBlock(2)     -remote block
         lBlock(3)     -local block
         "
     ::= { hwEntSipAgUserGroupEntry 14 }

  --========================================================================

   hwEntSipAgSoftNumberParaTable OBJECT-TYPE
     SYNTAX      SEQUENCE OF HwEntSipAgSoftNumberParaEntry
     MAX-ACCESS  not-accessible
     STATUS      current
     DESCRIPTION
       "
       This table is used to config the soft number parameters of sipag.
       The indexes of this table are hwEntSipAgId, hwEntSipAgSoftNumberParaNo.
       "
    ::= { hwEntVoiceSipagMIB 9 }

   hwEntSipAgSoftNumberParaEntry OBJECT-TYPE
     SYNTAX      HwEntSipAgSoftNumberParaEntry
     MAX-ACCESS  not-accessible
     STATUS      current
     DESCRIPTION
       "
       This table is used to config the soft number parameters of sipag.
       The indexes of this entry are hwEntSipAgId, hwEntSipAgSoftNumberParaNo.
       "
     INDEX    {
                hwEntSipAgSoftNumberParaId,
                hwEntSipAgSoftNumberParaNo
              }
    ::= { hwEntSipAgSoftNumberParaTable 1 }

   HwEntSipAgSoftNumberParaEntry ::=
     SEQUENCE
     {
       hwEntSipAgSoftNumberParaId        Integer32,
       hwEntSipAgSoftNumberParaNo        Integer32,
       hwEntSipAgSoftNumberParaValue     Integer32
     }

   hwEntSipAgSoftNumberParaId OBJECT-TYPE
     SYNTAX      Integer32(0..16777215)
     MAX-ACCESS  not-accessible
     STATUS      current
     DESCRIPTION
         "
         Sipag ID.
         "
     ::= { hwEntSipAgSoftNumberParaEntry 1 }

   hwEntSipAgSoftNumberParaNo OBJECT-TYPE
     SYNTAX      Integer32
     MAX-ACCESS  not-accessible
     STATUS      current
     DESCRIPTION
         "
         The number of sip mg soft number parameter.
         "
     ::= { hwEntSipAgSoftNumberParaEntry 2 }

   hwEntSipAgSoftNumberParaValue OBJECT-TYPE
     SYNTAX      Integer32
     MAX-ACCESS  read-write
     STATUS      current
     DESCRIPTION
         "
         The value of sip mg soft number parameter.
         "
     ::= { hwEntSipAgSoftNumberParaEntry 3 }

  --========================================================================

     hwEntSipAgSoftStringParaTable OBJECT-TYPE
     SYNTAX      SEQUENCE OF HwEntSipAgSoftStringParaEntry
     MAX-ACCESS  not-accessible
     STATUS      current
     DESCRIPTION
       "
       This table is used to config the soft string Parameters of SIP interface.
       The indexes of this table are hwEntSipAgId, hwEntSipAgSoftStringParaNo.
       "
    ::= { hwEntVoiceSipagMIB 10 }

   hwEntSipAgSoftStringParaEntry OBJECT-TYPE
     SYNTAX      HwEntSipAgSoftStringParaEntry
     MAX-ACCESS  not-accessible
     STATUS      current
     DESCRIPTION
       "
       This table is used to config the soft string parameters of sipag.
       The indexes of this entry are hwEntSipAgId, hwEntSipAgSoftStringParaNo.
       "
     INDEX    {
                hwEntSipAgSoftStringParaId,
                hwEntSipAgSoftStringParaNo
              }
    ::= { hwEntSipAgSoftStringParaTable 1 }

   HwEntSipAgSoftStringParaEntry ::=
     SEQUENCE
     {
       hwEntSipAgSoftStringParaId               Integer32,
       hwEntSipAgSoftStringParaNo               Integer32,
       hwEntSipAgSoftStringParaValue            DisplayString
     }

     hwEntSipAgSoftStringParaId OBJECT-TYPE
     SYNTAX      Integer32(0..16777215)
     MAX-ACCESS  not-accessible
     STATUS      current
     DESCRIPTION
         "
         Sipag ID.
         "
     ::= { hwEntSipAgSoftStringParaEntry 1 }

     hwEntSipAgSoftStringParaNo OBJECT-TYPE
     SYNTAX      Integer32
     MAX-ACCESS  not-accessible
     STATUS      current
     DESCRIPTION
         "
         The number of sip mg soft string parameter.
         "
     ::= { hwEntSipAgSoftStringParaEntry 2 }

     hwEntSipAgSoftStringParaValue OBJECT-TYPE
     SYNTAX      DisplayString(SIZE (0..64))
     MAX-ACCESS  read-write
     STATUS      current
     DESCRIPTION
         "
         The value of sip mg soft string parameter.
         "
     ::= { hwEntSipAgSoftStringParaEntry 3 }


--==

     hwEntSipAgSoftStringParaRunningTable OBJECT-TYPE
     SYNTAX      SEQUENCE OF HwEntSipAgSoftStringParaRunningEntry
     MAX-ACCESS  not-accessible
     STATUS      current
     DESCRIPTION
       "
       This table is used to query the running soft string parameters of sipag.
       The indexes of this table are hwEntSipAgId, hwEntSipAgSoftStringParaNo.
       "
    ::= { hwEntVoiceSipagMIB 11 }

   hwEntSipAgSoftStringParaRunningEntry OBJECT-TYPE
     SYNTAX      HwEntSipAgSoftStringParaRunningEntry
     MAX-ACCESS  not-accessible
     STATUS      current
     DESCRIPTION
       "
       This table is used to query the running soft string parameters of sipag.
       The indexes of this entry are hwEntSipAgId, hwEntSipAgSoftStringParaNo.
       "
     INDEX    {
                hwEntSipAgSoftStringParaRunningId,
                hwEntSipAgSoftStringParaRunningNo
              }
    ::= { hwEntSipAgSoftStringParaRunningTable 1 }

   HwEntSipAgSoftStringParaRunningEntry ::=
     SEQUENCE
     {
       hwEntSipAgSoftStringParaRunningId        Integer32,
       hwEntSipAgSoftStringParaRunningNo        Integer32,
       hwEntSipAgSoftStringParaRunningValue     DisplayString
     }
     
     hwEntSipAgSoftStringParaRunningId OBJECT-TYPE
     SYNTAX      Integer32(0..16777215)
     MAX-ACCESS  not-accessible
     STATUS      current
     DESCRIPTION
         "
         Sipag ID.
         "
     ::= { hwEntSipAgSoftStringParaRunningEntry 1 }
     
     hwEntSipAgSoftStringParaRunningNo OBJECT-TYPE
     SYNTAX      Integer32
     MAX-ACCESS  not-accessible
     STATUS      current
     DESCRIPTION
         "
         The number of sip mg soft string parameter.
         "
     ::= { hwEntSipAgSoftStringParaRunningEntry 2 }
     
     hwEntSipAgSoftStringParaRunningValue OBJECT-TYPE
     SYNTAX      DisplayString(SIZE (0..64))
     MAX-ACCESS  read-only
     STATUS      current
     DESCRIPTION
         "
         The value of sip mg soft string parameter.
         "
     ::= { hwEntSipAgSoftStringParaRunningEntry 3 }
     
--==

  hwEntFaxModemParaTable OBJECT-TYPE
     SYNTAX      SEQUENCE OF HwEntFaxModemParaEntry
     MAX-ACCESS  not-accessible
     STATUS      current
     DESCRIPTION
         "
         This table is used to config the fax and modem parameters of sipag.
         The index of this table is hwEntSipAgId.
         "
     ::= { hwEntVoiceSipagMIB 12 }
 
   hwEntFaxModemParaEntry OBJECT-TYPE
     SYNTAX      HwEntFaxModemParaEntry
     MAX-ACCESS  not-accessible
     STATUS      current
     DESCRIPTION
         "
         This table is used to config the fax parameter.
         The index of this entry is hwEntSipAgId.
         "
     INDEX    {  
                hwEntFaxSipAgId
              }
     ::= { hwEntFaxModemParaTable 1 }
 
   HwEntFaxModemParaEntry ::=
     SEQUENCE
     {
       hwEntFaxSipAgId                  Integer32,
       hwEntFaxTransMode                INTEGER,
       hwEntModemTransMode              INTEGER,
       hwEntFaxModemNegoMode            INTEGER,
       hwEntFaxModemParaVbdCodec        INTEGER,
       hwEntFaxModemParaVbdPtType 	    INTEGER, 
       hwEntFaxModemVbdAttributeType    INTEGER,
       hwEntFaxModemRtpInterval         INTEGER
     }
         
   hwEntFaxSipAgId OBJECT-TYPE
     SYNTAX      Integer32(0..16777215)
     MAX-ACCESS  not-accessible
     STATUS      current
     DESCRIPTION
         "
         Sipag ID.
         "
     ::= { hwEntFaxModemParaEntry 1 }
         
   hwEntFaxTransMode OBJECT-TYPE
     SYNTAX      INTEGER{thoroughly(1), t38(2)}            
     MAX-ACCESS  read-write
     STATUS      current
     DESCRIPTION
         "
         Indicates the fax transmission mode.
         Options:
         thoroughly(1)  -use voice codec
         t38(2)         -use T.38 codec
         Default: thoroughly(1)
         " 
     ::= { hwEntFaxModemParaEntry 2 } 
    
   hwEntModemTransMode OBJECT-TYPE
     SYNTAX      INTEGER{thoroughly(1), relay(2)}            
     MAX-ACCESS  read-write
     STATUS      current
     DESCRIPTION
         "
         Indicates the modem transmission mode.
         Options:
         thoroughly(1)  -Thoroughly transmission
         relay(2)       -Relay mode
         Default: thoroughly(1)
         "
     ::= { hwEntFaxModemParaEntry 3 } 
          
    hwEntFaxModemNegoMode OBJECT-TYPE
     SYNTAX      INTEGER{negotiate(1), selfswitch(2)}
     MAX-ACCESS  read-write
     STATUS      current
     DESCRIPTION
         "
         Indicates the negotiate mode.
         Options:
         negotiate(1)   -negotiate 
         selfswitch(2)  -do not negotiate
         Default: negotiate(1)
         "
     ::= { hwEntFaxModemParaEntry 4 }
     
     hwEntFaxModemParaVbdCodec OBJECT-TYPE
     SYNTAX      INTEGER{g711a(1), g711u(2)}            
     MAX-ACCESS  read-write
     STATUS      current
     DESCRIPTION
         " 
         Indicates the codec of VBD.
         Options:
         g711a(1)   -G.711A
         g711u(2)   -G.711U
         Default: g711a(1)
         "
     ::= { hwEntFaxModemParaEntry 5 }
     
     hwEntFaxModemParaVbdPtType OBJECT-TYPE
     SYNTAX      INTEGER{static(1), dynamic(2)}            
     MAX-ACCESS  read-write
     STATUS      current
     DESCRIPTION
         " 
         Indicates the payload type of VBD.
         Options:
         static(1)   -static payload type
         dynamic(2)  -dynamic payload type
         Default: static(1)
         "
     ::= { hwEntFaxModemParaEntry 6 }     
     
     hwEntFaxModemVbdAttributeType OBJECT-TYPE
     SYNTAX      INTEGER{v152(1), chinatelecom(2), chinatelecomext(3), ietf(4)}            
     MAX-ACCESS  read-write
     STATUS      current
     DESCRIPTION
         " 
         Indicate the format of session attribute lines when starting fax VBD negotiation.
         Options:
         v152(1)              -v.152 format
         chinatelecom(2)      -chinatelecom format
         chinatelecomext(3)   -chinatelecom ext format
         ietf(4)              -ietf format
         Default: v152(1)
         "
     ::= { hwEntFaxModemParaEntry 7 }
     
     hwEntFaxModemRtpInterval OBJECT-TYPE
     SYNTAX      INTEGER{pt5ms(1), pt10ms(2), pt20ms(3), pt30ms(4)}            
     MAX-ACCESS  read-write
     STATUS      current
     DESCRIPTION
         " 
         Indicates the default RTP packet time of DSP channel.
         Options:
         pt5ms(1) 
         pt10ms(2)
         pt20ms(3)
         pt30ms(4)
         Default: pt10ms(2)
       "
     ::= { hwEntFaxModemParaEntry 8 }
     
--==

     hwEntDtmfParaTable OBJECT-TYPE
     SYNTAX      SEQUENCE OF HwEntDtmfParaEntry
     MAX-ACCESS  not-accessible
     STATUS      current
     DESCRIPTION
         "
         This table is used to config the DTMF parameter of sipag.
         The index of this table is hwEntSipAgId.
         "
     ::= { hwEntVoiceSipagMIB 13 }
 
   hwEntDtmfParaEntry OBJECT-TYPE
     SYNTAX      HwEntDtmfParaEntry
     MAX-ACCESS  not-accessible
     STATUS      current
     DESCRIPTION
         "
         This table is used to config the DTMF parameter of sipag.
         The index of this entry is hwEntSipAgId.
         "
     INDEX    {  
                hwEntDtmfSipAgId
              }
     ::= { hwEntDtmfParaTable 1 }
 
   HwEntDtmfParaEntry ::=
     SEQUENCE
     {
       hwEntDtmfSipAgId           Integer32,
       hwEntDtmfTransMode         INTEGER
     }
     
     hwEntDtmfSipAgId OBJECT-TYPE
     SYNTAX      Integer32(0..16777215)
     MAX-ACCESS  not-accessible
     STATUS      current
     DESCRIPTION
         "
         Sipag ID.
         "
     ::= { hwEntDtmfParaEntry 1 }
     
     hwEntDtmfTransMode OBJECT-TYPE
     SYNTAX      INTEGER{thoroughly(1), erase(2)}            
     MAX-ACCESS  read-write
     STATUS      current
     DESCRIPTION
         " 
         Indicates the transmission mode of DTMF. 
         Options:
         thoroughly(1)  -transparent transmission
         erase(2)       -erase DTMF
         Default: thoroughly(1)
       "
     ::= { hwEntDtmfParaEntry 2 }
     
--== 

   hwEntNteTable OBJECT-TYPE
     SYNTAX      SEQUENCE OF HwEntNteEntry
     MAX-ACCESS  not-accessible
     STATUS      current
     DESCRIPTION
         "
         This table is used to config the nte parameter of sipag.
         The index of this table is hwEntSipAgId.
         "
     ::= { hwEntVoiceSipagMIB 14 }
 
   hwEntNteEntry OBJECT-TYPE
     SYNTAX      HwEntNteEntry
     MAX-ACCESS  not-accessible
     STATUS      current
     DESCRIPTION
         "
         This table is used to config the nte parameter of sipag.
         The index of this entry is hwEntSipAgId..
         "
     INDEX    {  
                hwEntNteSipAgId
              }
     ::= { hwEntNteTable 1 }
 
   HwEntNteEntry ::=
     SEQUENCE
     {
       hwEntNteSipAgId     Integer32,
       hwEntNteNegoMode    INTEGER,
       hwEntNteFaxModem    INTEGER,
       hwEntNteFlashHook   INTEGER,
       hwEntNteDtmf        INTEGER
     } 
     
     hwEntNteSipAgId OBJECT-TYPE
     SYNTAX      Integer32(0..16777215)
     MAX-ACCESS  not-accessible
     STATUS      current
     DESCRIPTION
         "
         Sipag ID.
         "
     ::= { hwEntNteEntry 1 }
     
     hwEntNteNegoMode OBJECT-TYPE
     SYNTAX      INTEGER{negoStart(1), fixedStart(2), noInitiativeStart(3)}            
     MAX-ACCESS  read-write
     STATUS      current
     DESCRIPTION
         " 
         Indicates the start mode of NTE.
         Options:
         negoStart(1)          -negotiate start
         fixedStart(2)         -fixed start
         noInitiativeStart(3)  -no initiative start
         Default: noInitiativeStart(3)
         "
     ::= { hwEntNteEntry 2 }    

     hwEntNteFaxModem OBJECT-TYPE
     SYNTAX      INTEGER{enable(1),disable(2)} 
     MAX-ACCESS  read-write
     STATUS      current
     DESCRIPTION
         "
         Indicates the flag of fax and modem event using nte parameter.
         Options:
         enable(1)
         disable(2)
         Default: enable(1)
         "
     ::= { hwEntNteEntry 3 }      

     hwEntNteFlashHook OBJECT-TYPE
     SYNTAX      INTEGER{enable(1),disable(2)} 
     MAX-ACCESS  read-write
     STATUS      current
     DESCRIPTION
         "
         Indicates the enabled flag of flash hook event using nte parameter.
         Options:
         enable(1)
         disable(2)
         Default: disable(2)
         "
     ::= { hwEntNteEntry 4 }
     
     hwEntNteDtmf OBJECT-TYPE
     SYNTAX      INTEGER{enable(1),disable(2)} 
     MAX-ACCESS  read-write
     STATUS      current
     DESCRIPTION
         "
         Indicates the enabled flag of dtmf using nte parameter.
         Options:
         enable(1)
         disable(2)
         Default: enable(1)
         "
     ::= { hwEntNteEntry 5 }     
     
--==

    hwEntRedundancyTable OBJECT-TYPE
     SYNTAX      SEQUENCE OF HwEntRedundancyEntry
     MAX-ACCESS  not-accessible
     STATUS      current
     DESCRIPTION
         "
         This table is used to config the redundancy parameter.
         The index of this table is hwEntSipAgId.
         "
     ::= { hwEntVoiceSipagMIB 15 }
 
   hwEntRedundancyEntry OBJECT-TYPE
     SYNTAX      HwEntRedundancyEntry
     MAX-ACCESS  not-accessible
     STATUS      current
     DESCRIPTION
         "
         This table is used to config the redundancy parameter of sipag.
         The index of this entry is hwEntSipAgId.
         "
     INDEX    {  
                hwEntRedundancySipAgId
              }
     ::= { hwEntRedundancyTable 1 }
 
   HwEntRedundancyEntry ::=
     SEQUENCE
     {
       hwEntRedundancySipAgId         Integer32,
       hwEntRedundancyNegoMode        INTEGER,
       hwEntRedundancyStartMode       INTEGER,
       hwEntRedundancyNte             INTEGER,
       hwEntRedundancyVbd             INTEGER, 
       hwEntRedundancyVoice           INTEGER
     }
     
     hwEntRedundancySipAgId OBJECT-TYPE
     SYNTAX      Integer32(0..16777215)
     MAX-ACCESS  not-accessible
     STATUS      current
     DESCRIPTION
         "
         Sipag ID.
         "
     ::= { hwEntRedundancyEntry 1 }
     
     hwEntRedundancyNegoMode OBJECT-TYPE
     SYNTAX      INTEGER{negoStart(1), fixedStart(2), noInitiativeStart(3)}            
     MAX-ACCESS  read-write
     STATUS      current
     DESCRIPTION
         " 
         Indicates the start mode of the redundancy.
         Options:
         negoStart(1)          -negotiate start
         fixedStart(2)         -fixed start
         noInitiativeStart(3)  -no initiative start
         Default: noInitiativeStart(3)
         "
     ::= { hwEntRedundancyEntry 2 }    

     hwEntRedundancyStartMode OBJECT-TYPE
     SYNTAX      INTEGER{smartRedundancy(1), ordinaryRedundancy(2)} 
     MAX-ACCESS  read-write
     STATUS      current
     DESCRIPTION
         "
         Indicates the start mode of the redundancy.
         Options:
         smartRedundancy(1)     -smart start redundancy
         ordinaryRedundancy(2)  -start redundancy ordinary
         Default: ordinaryRedundancy(2)
         "
     ::= { hwEntRedundancyEntry 3 }      

     hwEntRedundancyNte OBJECT-TYPE
     SYNTAX      INTEGER{enable(1), disable(2)} 
     MAX-ACCESS  read-write
     STATUS      current
     DESCRIPTION
         "
         Indicates the enabled flag of NTE with using redundancy.
         Options:
         enable(1)
         disable(2)
         Default: disable(2)
         "
     ::= { hwEntRedundancyEntry 4 }      

     hwEntRedundancyVbd OBJECT-TYPE
     SYNTAX      INTEGER{enable(1), disable(2)} 
     MAX-ACCESS  read-write
     STATUS      current
     DESCRIPTION
         "
         Indicates the enabled flag of the VBD using redundancy.
         Options:
         enable(1)
         disable(2)
         Default: enable(1)
         "
     ::= { hwEntRedundancyEntry 5 }      

     hwEntRedundancyVoice OBJECT-TYPE
     SYNTAX      INTEGER{enable(1), disable(2)} 
     MAX-ACCESS  read-write
     STATUS      current
     DESCRIPTION
         "
         Indicates the enabled flag of voice using redundancy.
         Options:
         1. enable(1)
         2. disable(2)
         Default: disable(2)
         "
     ::= { hwEntRedundancyEntry 6 }      
 
    
    --  ============== conformance information ==============
        hwEntVoiceSipagConformance OBJECT IDENTIFIER ::= { hwEntVoiceSipagMIB 16 }
        
        
        hwEntVoiceSipagCompliances OBJECT IDENTIFIER ::= { hwEntVoiceSipagConformance 1 }
        hwEntVoiceSipagCompliance MODULE-COMPLIANCE
               STATUS      current
               DESCRIPTION
                   "The compliance statement for systems supporting 
                the this module."

               MODULE      -- this module
               MANDATORY-GROUPS    {hwEntSipAgConfigGroup, hwEntSipAgRunningGroup, hwEntSipAgProxyGroup, 
                		hwEntSipAgProxyRunningGroup, hwEntSipProfileGroup, hwEntSipSrvLogicGroup,
                		hwEntSipAgDmmParaGroup}  
                                               
              ::= { hwEntVoiceSipagCompliances 1 }  
              
          
        --  ============== groups ==============  
        hwEntVoiceSipagGroups OBJECT IDENTIFIER ::= { hwEntVoiceSipagConformance 2 } 
        
	   hwEntSipAgConfigGroup OBJECT-GROUP
	     OBJECTS
	     {
	       	hwEntSipAgId  ,
		hwEntSipAgMediaIPAddress,
		hwEntSipAgSignallingIPAddress,
		hwEntSipAgSignallingPort,
		hwEntSipAgMediaAddrName,
		hwEntSipAgSignallingAddrName,
		hwEntSipAgTransMode,
		hwEntSipAgDomainName ,
		hwEntSipAgHomeDomainName,
		hwEntSipAgRegisterUri,
		hwEntSipAgConferenceFactoryUri,
		hwEntSipAgDesc,
		hwEntSipAgPhoneContext,
		hwEntSipAgAdminStatus,
		hwEntSipAgRowStatus,
		hwEntSipAgProfileIndex,
		hwEntSipAgProfileName,
		hwEntSipAgSrvLogicIndex,
		hwEntSipAgSrvLogicName,
		hwEntSipAgServerDhcpOption,
		hwEntSipAgSwitchoverDestination,
		hwEntSipAgAuthMode,
		hwEntSipAgAuthPasswordMode,
		hwEntSipAgAuthUserName,
		hwEntSipAgAuthPassword,
		hwEntSipAgAuthHA1,
		hwEntSipAgSubUAProfile,
		hwEntSipAgSubRegState,
		hwEntSipAgSubMwi,
		hwEntSipAgSdpNegoMode,
		hwEntSipAgProxyDualHome,
		hwEntSipAgProxyDetectMode,
		hwEntSipAgProxyRefreshMode
	     }
	    STATUS current
            DESCRIPTION 
                "The hwEntSipAgConfig group."
            ::= { hwEntVoiceSipagGroups 1 }
 
 	hwEntSipAgRunningGroup OBJECT-GROUP
	     OBJECTS
	     {
	       	hwEntSipAgRunningId ,
		hwEntSipAgRunningMediaIPAddress,
		hwEntSipAgRunningSignallingIPAddress,
		hwEntSipAgRunningSignallingPort,
		hwEntSipAgRunningMediaAddrName,
		hwEntSipAgRunningSignallingAddrName,
		hwEntSipAgRunningTransMode,
		hwEntSipAgRunningDomainName,
		hwEntSipAgRunningHomeDomainName,
		hwEntSipAgRunningRegisterUri,
		hwEntSipAgRunningConferenceFactoryUri,
		hwEntSipAgRunningDesc,
		hwEntSipAgRunningPhoneContext,
		hwEntSipAgRunningProfileIndex,
		hwEntSipAgRunningProfileName,
		hwEntSipAgRunningSrvLogicIndex,
		hwEntSipAgRunningSrvLogicName,
		hwEntSipAgRunningServerDhcpOption,
		hwEntSipAgRunningAuthMode,
		hwEntSipAgRunningAuthUserName,
		hwEntSipAgRunningAuthPasswordMode,
		hwEntSipAgRunningAuthPassword,
		hwEntSipAgRunningAuthHA1,
		hwEntSipAgRunningSubUAProfile,
		hwEntSipAgRunningSubRegState,
		hwEntSipAgRunningSubMwi,
		hwEntSipAgRunningSdpNegoMode,
		hwEntSipAgRunningProxyDualHome,
		hwEntSipAgRunningProxyDetectMode,
		hwEntSipAgRunningProxyRefreshMode,
		hwEntSipAgRunningState 
	     }
	    STATUS current
            DESCRIPTION 
                "The hwEntSipAgRunning group."
            ::= { hwEntVoiceSipagGroups 2 }           

 	hwEntSipAgProxyGroup OBJECT-GROUP
	     OBJECTS
	     {
	       	hwEntSipAgProxyId,
		hwSipAgProxyIndex,
		hwSipAgProxyIPAddress1,
		hwSipAgProxyIPAddress2,
		hwSipAgProxyPort,
		hwSipAgProxyDomainName,
		hwSipAgProxyAddressMode
	     }
	    STATUS current
            DESCRIPTION 
                "The hwEntSipAgProxy group."
            ::= { hwEntVoiceSipagGroups 3 }      
            
 	hwEntSipAgProxyRunningGroup OBJECT-GROUP
	     OBJECTS
	     {
	       	hwEntSipAgProxyRunningId,
		hwSipAgProxyRunningIndex,
		hwSipAgProxyRunningIPAddress1,
		hwSipAgProxyRunningIPAddress2,
		hwSipAgProxyRunningPort,
		hwSipAgProxyRunningDomainName,
		hwSipAgProxyRunningAddressMode,
		hwSipAgProxyRunningState
	     }
	    STATUS current
            DESCRIPTION 
                "The hwEntSipAgProxyRunning group."
            ::= { hwEntVoiceSipagGroups 4 }      

 	hwEntSipProfileGroup OBJECT-GROUP
	     OBJECTS
	     {
	       	hwEntSipProfileIndex,
		hwEntSipProfileName 
	     }
	    STATUS current
            DESCRIPTION 
                "The hwEntSipProfile group."
            ::= { hwEntVoiceSipagGroups 5 }      
            
 	hwEntSipSrvLogicGroup OBJECT-GROUP
	     OBJECTS
	     {
	       	hwEntSipSrvLogicIndex,
		hwEntSipSrvLogicName  
	     }
	    STATUS current
            DESCRIPTION 
                "The hwEntSipSrvLogic group."
            ::= { hwEntVoiceSipagGroups 6 }  
            
	hwEntSipAgDmmParaGroup OBJECT-GROUP
	     OBJECTS
	     {
	       	hwEntSipAgDmmParaId,
		hwEntSipAgDmmParaStartTimer,
		hwEntSipAgDmmParaShortTimer,
		hwEntSipAgDmmParaLongTimer  
	     }
	    STATUS current
            DESCRIPTION 
                "The hwEntSipAgDmmPara group."
            ::= { hwEntVoiceSipagGroups 7 }  
            
 	hwEntSipAgUserGroupGroup OBJECT-GROUP
	     OBJECTS
	     {
	       	hwEntSipAgUserGroupSipAgId,
		hwEntSipAgUserGroupId,
		hwEntSipAgUserGroupRegisterUriMode,
		hwEntSipAgUserGroupUri,
		hwEntSipAgUserGroupGrpName,
		hwEntSipAgUserGroupAuthUserName,
		hwEntSipAgUserGroupAuthPassWordMode,
		hwEntSipAgUserGroupAuthPassword,
		hwEntSipAgUserGroupAuthHA1,
		hwEntSipAgUserGroupPrecinctMode,
		hwEntSipAgUserGroupSubUaProfile,
		hwEntSipAgUserGroupRowStatus,
		hwEntSipAgUserGroupAdminStatus,
		hwEntSipAgUserGroupRunningState  
	     }
	    STATUS current
            DESCRIPTION 
                "The hwEntSipAgUserGroup group."
            ::= { hwEntVoiceSipagGroups 8 }  
            
	hwEntSipAgSoftNumberParaGroup OBJECT-GROUP
	     OBJECTS
	     {
	       	hwEntSipAgSoftNumberParaId,
		hwEntSipAgSoftNumberParaNo,
		hwEntSipAgSoftNumberParaValue  
	     }
	    STATUS current
            DESCRIPTION 
                "The hwEntSipAgSoftNumberPara group."
            ::= { hwEntVoiceSipagGroups 9 }
            
 	hwEntSipAgSoftStringParaGroup OBJECT-GROUP
	     OBJECTS
	     {
	       	hwEntSipAgSoftStringParaId,
		hwEntSipAgSoftStringParaNo,
		hwEntSipAgSoftStringParaValue  
	     }
	    STATUS current
            DESCRIPTION 
                "The hwEntSipAgSoftStringPara group."
            ::= { hwEntVoiceSipagGroups 10 }  
            
	hwEntSipAgSoftStringParaRunningGroup OBJECT-GROUP
	     OBJECTS
	     {
	       	hwEntSipAgSoftStringParaRunningId,
		hwEntSipAgSoftStringParaRunningNo,
		hwEntSipAgSoftStringParaRunningValue  
	     }
	    STATUS current
            DESCRIPTION 
                "The hwEntSipAgSoftStringParaRunningGroup group."
            ::= { hwEntVoiceSipagGroups 11 }
            
 	hwEntFaxModemParaGroup OBJECT-GROUP
	     OBJECTS
	     {
	       	hwEntFaxSipAgId,
		hwEntFaxTransMode,
		hwEntModemTransMode,
		hwEntFaxModemNegoMode,
		hwEntFaxModemParaVbdCodec,
		hwEntFaxModemParaVbdPtType, 
		hwEntFaxModemVbdAttributeType,
		hwEntFaxModemRtpInterval  
	     }
	    STATUS current
            DESCRIPTION 
                "The hwEntFaxModemPara group."
            ::= { hwEntVoiceSipagGroups 12 }  
            
	hwEntDtmfParaGroup OBJECT-GROUP
	     OBJECTS
	     {
	       	hwEntDtmfSipAgId,
		hwEntDtmfTransMode 
	     }
	    STATUS current
            DESCRIPTION 
                "The hwEntDtmfPara group."
            ::= { hwEntVoiceSipagGroups 13 }
            
 	hwEntNteGroup OBJECT-GROUP
	     OBJECTS
	     {
	       	hwEntNteSipAgId,
		hwEntNteNegoMode,
		hwEntNteFaxModem,
		hwEntNteFlashHook,
		hwEntNteDtmf 
	     }
	    STATUS current
            DESCRIPTION 
                "The hwEntNte group."
            ::= { hwEntVoiceSipagGroups 14 }  
            
	hwEntRedundancyGroup OBJECT-GROUP
	     OBJECTS
	     {
	       	hwEntRedundancySipAgId,
		hwEntRedundancyNegoMode,
		hwEntRedundancyStartMode,
		hwEntRedundancyNte,
		hwEntRedundancyVbd, 
		hwEntRedundancyVoice  
	     }
	    STATUS current
            DESCRIPTION 
                "The hwEntRedundancy group."
            ::= { hwEntVoiceSipagGroups 15 }
            
 	                                                 

 END

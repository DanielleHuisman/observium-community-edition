-- ============================================================================
-- Copyright (C) 2019 by  HUAWEI TECHNOLOGIES. All rights reserved.
-- Description: The MIB module defines OIDs for Huawei components
--              used by the ENTITY-MIB.
-- Reference:
-- Version:     V1.84
-- ============================================================================
    HUAWEI-ENTITY-VENDORTYPE-MIB DEFINITIONS ::= BEGIN
        IMPORTS
            Integer32,IpAddress, OBJECT-TYPE, MODULE-IDENTITY,
            NOTIFICATION-TYPE
                FROM SNMPv2-SMI
            TEXTUAL-CONVENTION,DateAndTime,MacAddress
                FROM SNMPv2-TC
            huaweiUtility
                FROM HUAWEI-MIB;

        hwEntityVendorType MODULE-IDENTITY
            LAST-UPDATED "201909251000Z"
            ORGANIZATION "Huawei Technologies Co.,Ltd."
            CONTACT-INFO
                         "Huawei Industrial Base
                          Bantian, Longgang
                          Shenzhen 518129
                          People's Republic of China
                          Website: http://www.huawei.com
                          Email: support@huawei.com
                         "
            DESCRIPTION
                "The MIB module defines OIDs for Huawei components used by the ENTITY-MIB."

--  Revision history

         REVISION     "201909251000Z"
         DESCRIPTION  "V1.84,
                      added hwPhysicalBoardModuleH903CGHD(148678),         --  8*XG/G combo board of MA5800.
                      added hwPhysicalBoardModuleH903CSHD(148679),         --  8*XGS/G combo board of MA5800.
                      added hwPhysicalBoardModuleH902OXEG(148680),         --  24*10GE board of MA5800.
                      added hwPhysicalBoardModuleH903CGUD(148681),         --  8*XGS/G combo board of MA5800.
                      added hwPhysicalBoardModuleH902FLEF(148682),         --  16*flex-PON board of MA5800.
                      added hwPhysicalBoardModuleH902XGLF(148683),         --  16*XG GPON board of MA5800.	
                      "

         REVISION     "201909051000Z"
         DESCRIPTION  "V1.83,
                       added hwPhysicalBoardModuleH803X2CK(146080),    --- 10GE synchronized Ethernet interface board.
                       "

         REVISION     "201907191000Z"
         DESCRIPTION  "V1.82,
                      added hwPhysicalBoardModuleH902XSHFE(148672),    --- 16*10G XGS-PON board of EA5800. 
                      added hwPhysicalBoardModuleH902EPHFE(148673),    --- 16 port EPON board of EA5800.		
                      added hwPhysicalBoardModuleH902EPHF(148674),     --- 16 port EPON board of MA5800.
                      added hwPhysicalBoardModuleH901MPSAE(148676),    --- control board of EA5800-X2.
                      "

         REVISION     "201907031000Z"
         DESCRIPTION  "V1.81,
                     added hwPhysicalBoardModuleH903MPLAE(148670),    --- control board of EA5800.
                     added hwPhysicalBoardModuleH902OGHK(148671),     --- 48 P2P board of MA5800.
                     added hwPhysicalBoardModuleH902PISB(148675),     --- AC Power board of MA5800-X2.					  
                      "
					  
         REVISION     "201905071000Z"
         DESCRIPTION  "V1.80,
                      added hwPhysicalBoardModuleH902FLHFE(148669),    --- 16*flex-PON board of EA5800.  
                      "
		      
         REVISION     "201904301100Z"
         DESCRIPTION  "V1.79,
                      added hwPhysicalBoardModuleH902GPSF(148662),     --- 16*GPON board of MA5800.
                      added hwPhysicalBoardModuleH902GPHFE(148668),    --- 16*GPON board of MA5800."
         REVISION     "201904121100Z"
         DESCRIPTION  "V1.78,
                      added hwPhysicalBoardModuleH902XSHF(148664),    --- 16*10G XGS-PON board of MA5800. 
					  added hwPhysicalBoardModuleH902FLHF(148665),    --- 16*flex-PON board of MA5800. 
					  added hwPhysicalBoardModuleH902CGUF(148666),    --- 16*XG GPON and GPON combo board of MA5800.
					  added hwPhysicalBoardModuleH902OXHD(148667),    --- 8*10GE P2P board of MA5800. 
                      "

         REVISION     "201903061100Z"
         DESCRIPTION  "V1.77,
                      added hwPhysicalPortNdfChannel(3009),
                      added hwPhysicalPortNdrChannel(3010),
                      "

         REVISION     "201901281000Z"
         DESCRIPTION  "V1.76,
                      added hwPhysicalBoardModuleH902GPUF(148659),    --- 16*GPON board of MA5800.
                      added hwPhysicalBoardModuleH902GPLF(148660),    --- 16*GPON board of MA5800.
                      added hwPhysicalBoardModuleH902XELD(148661),    --- 8*10G EPON board of MA5800.
                      "
         REVISION     "201812121000Z"
         DESCRIPTION  "V1.75,
                      added hwPhysicalChassisH805MABC(147540)
                      added hwPhysicalChassisH805MABO(147541) 
                      added hwPhysicalBoardModuleH805SCUP(156057)          
                      added hwPhysicalBoardModuleH805SCUQ(156061) 
                      added hwPhysicalBoardModuleH803OPGE(156087)          
                      added hwPhysicalBoardModuleH803EDTB(156088)   
                      "
                
         REVISION     "201811061000Z"
         DESCRIPTION  "V1.74,
                      added hwPhysicalBoardModuleH902CGHF(148658),    --- 16*XG/G GPON board of MA5800.     
                      "
					  
         REVISION     "201808061000Z"
         DESCRIPTION  "V1.73,
	 	      		  added hwPhysicalBoardModuleH901GPHH(148656),    --- 32*G-PON board of MA5800.                     
	 	      		  added hwPhysicalBoardModuleH901MPLE(148657),    --- control board of MA5800.                     
	 	      		  added hwPhysicalSubBoardModuleH902CKUB(148515),    --- CLock subboard of MA5800.                     
	 	      		  added hwPhysicalSubBoardModuleH902CKUA(148516),    --- CLock subboard of MA5800.                     
                     "		 
         
         REVISION     "201807301000Z"
         DESCRIPTION  "V1.72,
	 	      		  added hwPhysicalBoardModuleH801SCUP(156082),    --- control board of of MA5600T.
                      added hwPhysicalBoardModuleH801SCUQ(156083),    --- control board of of MA5600T.
                     "
					 
         REVISION     "201806201000Z"
         DESCRIPTION  "V1.71,
	 	      		  added hwPhysicalBoardModuleH806GPFD(146157),    --- 16*G-PON board of MA5600T.
                      added hwPhysicalBoardModuleH902NXED(148649),    --- 8*Port ETH board of MA5800.
 	 	      		  added hwPhysicalBoardModuleH903MPLA(148650),    --- control board of MA5800.
                      added hwPhysicalBoardModuleH902MPLB(148651),    --- control board of MA5800.
	 	      		  added hwPhysicalBoardModuleH902CIUA(148652),    --- GPIO board of MA5800.
                      added hwPhysicalBoardModuleH902PILA(148653),    --- Power board of MA5800.
					  added hwPhysicalBoardModuleH901NCEB(148655),    --- 2*100G service board of MA5800.
                     "
	 REVISION     "201805311000Z"
         DESCRIPTION  "V1.70,
                          added hwPhysicalBoardModuleH901FLHF(148645),    --- 16*flex-PON board of MA5800.       
                          added hwPhysicalBoardModuleH902CSHF(148646),    --- 16*10G GPON board of MA5800.
                          added hwPhysicalBoardModuleH902GPHF(148647),    --- 16*10G GPON board of MA5800.
                          added hwPhysicalBoardModuleH902XEHD(148648),    --- 8*10G GPON board of MA5800.
						  added hwPhysicalBoardModuleH901GPUF(148654),    --- 16*GPON board of MA5800.
                      "
         REVISION     "201805121000Z"
         DESCRIPTION  "V1.69,
                      added hwPhysicalBoardModuleH902XSHD(148644),    --- 8*10G GPON board of MA5800.
                      added hwPhysicalBoardModuleH902TWHD(148643),    --- 8*10G GPON board of MA5800.
                      "

         REVISION     "201804081000Z"
         DESCRIPTION  "V1.68,
                      added hwPhysicalBoardModuleH901CGUD(148641),     ---  8*GE and 10GE combo board of MA5800.
                      added hwPhysicalBoardModuleH901CGUF(148642),     ---  16*XG GPON and GPON combo board of MA5800.
                      "

         REVISION     "201804021000Z"
         DESCRIPTION  "V1.67,
                      added hwPhysicalBoardModuleH801XSBD(146156),     ---  8-port 10G EPON interface board of MA5600T.
                      "

         REVISION     "201802231000Z"
         DESCRIPTION  "V1.66,                       
                      added hwPhysicalBoardModuleH921MPCA(148510),     --- control board of MA5801-GP08.
                      added hwPhysicalBoardModuleH921MPCAE(148511),    --- control board of EA5801-GP08.
                      added hwPhysicalBoardModuleH921GPHD(148540),     --- 8*GPON board of MA5801-GP08.
                      added hwPhysicalBoardModuleH921NXHC(148541),     --- 4*10GE board of MA5801-GP08.
                      added hwPhysicalBoardModuleH921GPHDE(148542),    --- 8*GPON board of EA5801-GP08.
                      added hwPhysicalBoardModuleH921PICA(148543),     --- DC Power board of MA5801-GP08.
                      added hwPhysicalBoardModuleME170-12A(148544),    --- AC Power board of MA5801-GP08.
                      added hwPhysicalBoardModuleH921CIUA(148545),     --- GPIO board of MA5801-GP08.
                      added hwPhysicalBoardModuleH921CGHC(148546),     --- 4*GE and 10GE combo board of MA5801-CG04.
                      added hwPhysicalBoardModuleH921CGHCE(148547),    --- 4*GE and 10GE combo board of EA5801-CG04.
                      added hwPhysicalBoardModuleH921NXHCE(148548),    --- 4*10GE board of EA5801-GP08.
                      added hwPhysicalBoardModuleH902CRED(148638),     --- IP backhaul board of MA5800.
                      added hwPhysicalBoardModuleH901CSHDE(148639),    --- 8*XGS GPON and GPON combo board of EA5800.
                      added hwPhysicalBoardModuleH901CSHFE(148640),    --- 16*XGS GPON and GPON combo board of EA5800.
                      "

         REVISION     "201711231000Z"
         DESCRIPTION  "V1.65,
                      added hwPhysicalBoardModuleH901CSHD(148632),     --- 8*XGS GPON and GPON combo board of MA5800.
                      added hwPhysicalBoardModuleH901CGHF(148633),     --- 16*XG GPON and GPON combo board of MA5800.
                      added hwPhysicalBoardModuleH901CSHF(148634),     --- 16*XGS GPON and GPON combo board of MA5800.
                      added hwPhysicalBoardModuleH901XEHF(148635),     --- 16*10G EPON board of MA5800.
                      added hwPhysicalBoardModuleH902CGHD(148636),     --- 8*XGS GPON and GPON combo board of MA5800.
                      added hwPhysicalBoardModuleH902CSHD(148637),     --- 8*XG GPON and GPON combo board of MA5800.					  
                      added hwPhysicalBoardModuleH911MPCA(148510),     --- control board of MA5801-GP08.
                      added hwPhysicalBoardModuleH911MPCAE(148511),    --- control board of EA5801-GP08.
                      added hwPhysicalBoardModuleH911GPHD(148540),     --- 8*GE GPON board of MA5801-GP08.
                      added hwPhysicalBoardModuleH911NXHC(148541),     --- 4 P2P board of MA5801-GP08.
                      added hwPhysicalBoardModuleH911GPHDE(148542),    --- 8*GE GPON board of EA5801-GP08.
                      added hwPhysicalBoardModuleH911PICA(148543),     --- DC Power board of MA5801-GP08.
                      added hwPhysicalBoardModuleME17012A(148544),    --- AC Power board of MA5801-GP08.
                      added hwPhysicalBoardModuleH911CIUA(148545),     --- GPIO board of MA5801-GP08.
		      "
		      
	 REVISION     "201711171000Z"
         DESCRIPTION  "V1.64,
                      added hwPhysicalBoardModuleH801CGBD(146151),     --- 8-port 10G GPON and GPON combo interface board of MA5600T.
                      added hwPhysicalBoardModuleH802CGBD(146152),     --- 8-port 10G GPON and GPON combo interface board of MA5600T.
                      added hwPhysicalBoardModuleH801CSBD(146153),     --- 8-port 10GS-PON and GPON combo interface board of MA5600T.
                      added hwPhysicalBoardModuleH802CSBD(146154),     --- 8-port 10GS-PON and GPON combo interface board of MA5600T.
                      added hwPhysicalBoardModuleH801XSBD(146155),     --- 8-port 10GS-PON interface board of MA5600T.
                      "

         REVISION     "201710241000Z"
         DESCRIPTION  "V1.63,
                      added hwPhysicalBoardModuleH802GICK(146079),     --- GE synchronized Ethernet interface board.
                      "

         REVISION     "201709271800Z"
         DESCRIPTION  "V1.62,
                      added hwPhysicalBoardModuleH901TWEDE(148628),    --- 8*10G GPON board of MA5800.
                      added hwPhysicalBoardModuleH902TWED(148629),     --- 8*10G Flex-PON  board of MA5800 support TWDM-PON XGS-PON.
                      added hwPhysicalBoardModuleH903XSHD(148630),     --- 8*10G GPON board of MA5800.
                      added hwPhysicalBoardModuleH901XSHF(148631),     --- 16*10G XGS-PON board of MA5800.
                      "
         REVISION     "201708211800Z"
         DESCRIPTION  "V1.61,
                      added hwPhysicalBoardModuleH809VPED(156070),
                      "

         REVISION     "201707201800Z"
         DESCRIPTION  "V1.60,
                      added hwPhysicalPortOptic10GEponPR30PLUS,
                      added hwPhysicalPortOpticXGponComboD1,
                      added hwPhysicalPortOpticXGSponComboD2,
                      "

         REVISION     "201706241800Z"
         DESCRIPTION  "V1.59,
                      added hwPhysicalBoardModuleH80DCSPE(155960),
                      "

         REVISION     "201706120930Z"
         DESCRIPTION  "V1.58,
                      added hwPhysicalChassisH901BPLD,                --- 400G backplane for MA5800-X17
                      added hwPhysicalChassisH802MABR.
                      "

         REVISION     "201705090930Z"
         DESCRIPTION  "V1.57,
                      added hwPhysicalBoardModuleH902XSED(148623),    --- 8*10G GPON board of MA5800.
                      added hwPhysicalBoardModuleH901DSHD(148624),    --- 8*GE and 10GE combo board of MA5800
                      added hwPhysicalBoardModuleH901OGHF(148625),    --- 16 P2P board of MA5800.
                      added hwPhysicalBoardModuleH901OXHG(148626),    --- 24*10GE board of MA5800.
                      added hwPhysicalBoardModuleH901NXLC(148627),    --- 4*10GE board of MA5800.
                      "

         REVISION     "201703290930Z"
         DESCRIPTION  "V1.56,
                      added hwPhysicalBoardModuleH902MPLAE(148619),
                      added hwPhysicalBoardModuleH901MPSCE(148620),
                      added hwPhysicalBoardModuleH901GPSFE(148621),
                      added hwPhysicalBoardModuleH901XGHDE(148622),
                      "

         REVISION     "201703221000Z"
         DESCRIPTION  "V1.55,
                      added hwPhysicalBoardModuleH901GPLF(148615),
                      added hwPhysicalBoardModuleH901XGLD(148616),
                      added hwPhysicalBoardModuleH901XGLF(148617),
                      added hwPhysicalBoardModuleH901XELD(148618),
                      "

         REVISION     "201702211000Z"
         DESCRIPTION  "V1.54,
                      added hwPhysicalSubBoardModuleH901TPUA(148601),     --- TPM SubBoard of H902MPLA.
                      added hwPhysicalBoardModuleH801XP1A(155958),     --- 1-port XG-PON/XGS-PON interface board.
                      "

         REVISION     "201702141000Z"
         DESCRIPTION  "V1.53,
                      added hwPhysicalBoardModuleH802X2CS(148015),     --- 10GE synchronized Ethernet interface board.
                      added hwPhysicalBoardModuleH801GPND(148016),     --- 8GPON board of MA5600T.
                      "

	 REVISION     "201609241000Z"
         DESCRIPTION  "V1.52,
                      added hwPhysicalPortDocsisPort ,
	              added hwPhysicalPortDocsis30UpstreamChannel ,
	              added hwPhysicalPortDocsis30DownstreamChannel ,
                      added hwPhysicalPortDocsis31UpstreamChannel ,
	              added hwPhysicalPortDocsis31DownstreamChannel ,
	              added hwPhysicalPortEqamChannel .
                      "

         REVISION     "201609211000Z"
         DESCRIPTION  "V1.51,
                      added hwPhysicalBoardModuleH901PIMA(148614),    --- DC Power board of MA5800-X7.
                      "

         REVISION     "201607301700Z"
         DESCRIPTION  "V1.50,
                      added hwPhysicalBoardModuleH901CGID(148613),    --- 8*GE and 10GE combo board of MA5800.
		      added hwPhysicalBoardModuleH901MPLC(148507),    --- control board of MA5800.
                      added hwPhysicalBoardModuleH901MPLD(148508),    --- control board of MA5800.
                      added hwPhysicalBoardModuleH902MPLC(148509),    --- control board of MA5800.
                      "

         REVISION     "201606081700Z"
         DESCRIPTION  "V1.49,
                      added hwPhysicalBoardModuleH901CVEC(148539),    --- support vector board of MA5800.
                      "

         REVISION     "201605121700Z"
         DESCRIPTION  "V1.48,
                      added hwPhysicalBoardModuleH80XVPS(148014),     --- support vector board of MA5600T.
                      added hwPhysicalBoardModuleH901MPSC(148505),    --- control board of MA5800-X2.
                      added hwPhysicalBoardModuleH901MPSD(148506),    --- control board of MA5800-X2.
                      added hwPhysicalBoardModuleH901CGCD(148608),    --- 8*GE and 10GE combo board of MA5800.
                      added hwPhysicalBoardModuleH901XGSF(148609),    --- 16*10GE board of MA5800.
                      added hwPhysicalBoardModuleH901PISA(148610),    --- DC Power board of MA5800-X2
                      added hwPhysicalBoardModuleH901PISB(148611),    --- AC Power board of MA5800-X2
                      added hwPhysicalBoardModuleH901PISC(148612),    --- DC Power board of MA5800-X2
                      added hwPhysicalSubBoardModuleH901CPCB(148513), --- Clock subboard of MA5800-X2 H901MPSC
                      added hwPhysicalSubBoardModuleH901CPCC(148514), --- Clock subboard of MA5800-X2 H901MPSD
                      "

         REVISION     "201603211700Z"
         DESCRIPTION  "V1.47,
                      added hwPhysicalBoardModuleH901TWED(148607),     --- 8*10G GPON board of MA5800
                      "

         REVISION     "201602201600Z"
         DESCRIPTION  "V1.46,
                      added hwPhysicalBoardModuleH901XSED(148604),     --- 8*10G GPON board of MA5800
	 	      added hwPhysicalBoardModuleH901GPHD(148605),     --- 8*GPON board of MA5800.
                      added hwPhysicalBoardModuleH901GPSD(148606).     --- 8*GPON board of MA5800.
                      "

         REVISION    "201512281600Z"
         DESCRIPTION "V1.45,
                     Add: hwPhysicalChassisH901BPSB(148513),     -- Backplane of the MA5800-X2.
                     Add: hwPhysicalBoardModuleH901MPSA(148503)
                     Add: hwPhysicalBoardModuleH902MPLA(148504)
                     Add: hwPhysicalSubBoardModuleH901CPCA(148512)
                     Add: hwPhysicalBoardModuleH901MPWD(148601)
                     Add: hwPhysicalBoardModuleH901MPWE(148602)
                     Add: hwPhysicalBoardModuleH901MPWC(148603)
                     "

         REVISION     "201512070900Z"
         DESCRIPTION  "V1.44,
                      added hwPhysicalChassisH901BPIB. --- 19inch, 200G backplane for MA5800-X15"

         REVISION     "201512030900Z"
         DESCRIPTION  "V1.43,
                      added hwPhysicalBoardModuleH901OXEG,
                      added hwPhysicalChassisH901BPLE."

         REVISION     "201509110900Z"
         DESCRIPTION  "V1.42,
                      added hwPhysicalBoardModuleH80XATR,
                      added hwPhysicalBoardModuleH901CRED."

         REVISION     "201508271100Z"
         DESCRIPTION  "V1.41,
                      added hwPhysicalSubBoardModuleH831UP2E,
                      added  hwPhysicalSubBoardModuleH831UP2F,
                      added hwPhysicalSubBoardModuleHS21PWBB,
                      added hwPhysicalSubBoardModuleHS21MIXB"

         REVISION     "201508051500Z"
         DESCRIPTION  "V1.40,
                      added hwPhysicalBoardModuleH901PILB."

         REVISION     "201506241800Z"
         DESCRIPTION  "V1.39,
                      added hwPhysicalSubBoardModuleH901CKUB,
                      added hwPhysicalBoardModuleH80XSDM,
                      added hwPhysicalBoardModuleH80XSDP."

         REVISION     "201506231200Z"
         DESCRIPTION  "V1.38,
                      added hwPhysicalChassisRemoteReserve30~hwPhysicalChassisRemoteReserve39,
                      added hwPhysicalChassisMA5800Reserve11~hwPhysicalChassisMA5800Reserve40,
                      added hwPhysicalBoardModuleMA5800CBReserve03~hwPhysicalBoardModuleMA5800CBReserve10,
                      added hwPhysicalBoardModuleMA5800Reserve00~hwPhysicalBoardModuleMA5800Reserve99,
                      added hwPhysicalBoardModuleRemoteReserve10~hwPhysicalBoardModuleRemoteReserve29,
                      added hwPhysicalSubBoardModuleReserve11~hwPhysicalSubBoardModuleReserve25."

         REVISION     "201504081200Z"
         DESCRIPTION  "V1.37,
                      added hwPhysicalBoardModuleH901EDSH."

--  Revision history

         REVISION     "201503311200Z"
         DESCRIPTION  "V1.36,
                      added hwPhysicalChassisH802MABH,
                      added hwPhysicalChassisH803MABC."

         REVISION     "201412011200Z"
         DESCRIPTION  "V1.35,
                      added hwPhysicalBoardModuleH809EPBD,
                      added hwPhysicalBoardModuleH801TOPB,
                      added hwPhysicalBoardModuleH80DCCPE."

         REVISION     "201411201200Z"
         DESCRIPTION  "V1.34,
                      added hwPhysicalChassisH901BPMB,
                      added hwPhysicalBoardModuleH901XEHD,
                      added hwPhysicalBoardModuleH901GPSF,
                      added hwPhysicalBoardModuleH901EPHF."

         REVISION     "201408281200Z"
         DESCRIPTION  "V1.33,
                      added hwPhysicalChassisH831MABCA(DT)
		      added hwPhysicalSubBoardModuleH831UP2C
		      added hwPhysicalPortOptic100MBASEFXType
                      added hwPhysicalPortOptic100MBASELXType."

         REVISION     "201406231200Z"
         DESCRIPTION  "V1.32, Correct the ORGANIZATION information"
         REVISION     "201406121200Z"
         DESCRIPTION  "V1.31,
                      added hwPhysicalBoardModuleH801X2CK."

         REVISION     "201406061200Z"
         DESCRIPTION  "V1.30,
                      added hwPhysicalBoardModuleH802SCUB
                      added hwPhysicalBoardModuleH806CAME."

         REVISION     "201406041200Z"
         DESCRIPTION  "V1.29,
                      added hwPhysicalChassisH901BPLB,
                      added hwPhysicalBoardModuleH901MPLA,
                      added hwPhysicalBoardModuleH901MPLB,
                      added hwPhysicalBoardModuleH901XGHD,
                      added hwPhysicalBoardModuleH901GPHF,
                      added hwPhysicalBoardModuleH901OGHK,
                      added hwPhysicalBoardModuleH901NXED,
                      added hwPhysicalBoardModuleH901OXHD,
                      added hwPhysicalBoardModuleH901PILA,
                      added hwPhysicalBoardModuleH901CIUA,
                      added hwPhysicalSubBoardModuleH901CKUA,
                      added hwPhysicalEmuH901VESCType.
"

         REVISION     "201405271200Z"
         DESCRIPTION  "V1.28,
                      added hwPhysicalBoardModuleH801MPWE."

         REVISION     "201404091200Z"
         DESCRIPTION  "V1.27,
                      added hwPhysicalStackMxUType,
                      added hwPhysicalContainerMxUSlot,
                      added hwPhysicalContainerMxUSubSlot,
		      added hwPhysicalBoardModuleH831MABC,
		      added hwPhysicalBoardModuleH82DVCMM,
                      added hwPhysicalSubBoardModuleHS2DVCMM."
         REVISION     "201310161200Z"
         DESCRIPTION  "V1.26,
                      added hwPhysicalBoardModuleH80XVPG,
                      added hwPhysicalBoardModuleH806CCPE,
                      added hwPhysicalBoardModuleH807GPBD,
                      added hwPhysicalBoardModuleH807GPBH,
                      added hwPhysicalBoardModuleH801XGBD,
                      added hwPhysicalBoardModuleH803XEBD,
                      added hwPhysicalBoardModuleH805EPFD,
                      added hwPhysicalBoardModuleH802GPMD,
                      added hwPhysicalBoardModuleH805GPFD,
                      added hwPhysicalBoardModuleH802XEBD,
                      added hwPhysicalBoardModuleH803EPFD,
                      added hwPhysicalBoardModuleH802SCUH,
                      added hwPhysicalBoardModuleH802SCUV."

         REVISION     "201309221200Z"
         DESCRIPTION  "V1.25,
                      added hwPhysicalPortOpticGPONCLASSCPLUSPLUSType
                      added hwPhysicalPortOpticEPONPX20PLUSPLUSType."

	 REVISION     "201309011200Z"
         DESCRIPTION  "V1.24,
                      added hwPhysicalBoardModuleH802EPFD."

         REVISION     "201307091200Z"
	 DESCRIPTION  "V1.23,
	 	      added hwPhysicalPortOpticGponClassBPlus
                      added hwPhysicalPortOpticGponClassCPlus
                      added hwPhysicalPortOpticGponClassB
                      added hwPhysicalPortOpticEponPX20
                      added hwPhysicalPortOpticEponPX20Plus
                      added hwPhysicalPortOptic10GEponPR30
                      added hwPhysicalPortOptic10GEponPR20
                      added hwPhysicalPortOptic10GEponPRX30
                      added hwPhysicalPortOptic10GEponPRX20
                      added hwPhysicalPortOpticXGponN2A
                      added hwPhysicalPortOpticXGponN2B
                      added hwPhysicalPortOpticXGponN1."

         REVISION     "201307041200Z"
         DESCRIPTION  "V1.22,
                      added hwPhysicalChassisH802MABC."

         REVISION     "201306081200Z"
         DESCRIPTION  "V1.21,
                      added hwPhysicalChassisH801SPUC,
                      added hwPhysicalSubBoardModuleH801CKMD,
                      added hwPhysicalBoardModuleSHG,
                      added hwPhysicalChassisH802OPGE."

         REVISION     "201305271200Z"
         DESCRIPTION  "V1.20,
                      added hwPhysicalBoardModuleH806GPBD,
                      added hwPhysicalBoardModuleH806GPBH."

         REVISION     "201304281200Z"
         DESCRIPTION  "V1.19,
                      added hwPhysicalChassisMA5633,
                      added hwPhysicalBoardModuleH822CCKRA,
                            hwPhysicalBoardModuleHS33CDAA."

         REVISION     "201303221400Z"
         DESCRIPTION  "V1.18,
                      added hwPhysicalBoardModuleH801SCUK,
                      added hwPhysicalBoardModuleH801MCUE,
                      added hwPhysicalBoardModuleH801SCUV,
                      added hwPhysicalBoardModuleH801GPMD,
                      added hwPhysicalSubBoardModuleH801CPCC."

         REVISION     "201301061400Z"
         DESCRIPTION  "V1.17,
                      added hwPhysicalBoardModuleH801XESD."

         REVISION     "201211161400Z"
         DESCRIPTION  "V1.16,
                      added hwPhysicalBoardModuleH801MCUD1."

         REVISION     "201210301400Z"
         DESCRIPTION  "V1.15,
                      added hwPhysicalBoardModuleH80xVCP,
                      added hwPhysicalBoardModuleH801SPUF,
                      added hwPhysicalBoardModuleH801MPWD."


         REVISION     "201208011600Z"
         DESCRIPTION  "V1.14,
                      added hwPhysicalEmuType,
                      added hwPhysicalPowerFrameType,
                      added hwPhysicalPowerModuleType,
                      added hwPhysicalBatteryType."

         REVISION     "201208011200Z"
         DESCRIPTION  "V1.13,
                      added hwPhysicalBoardModuleH802SCUN,
                      added hwPhysicalBoardModuleH801SPUH."

         REVISION     "201207301600Z"
         DESCRIPTION  "V1.12,
                      added hwPhysicalChassisMA5623AR,
                      added hwPhysicalBoardModuleHS22CCVW,
                            hwPhysicalBoardModuleHS3BVCMM."

         REVISION     "201206201600Z"
         DESCRIPTION  "V1.11,
                      added hwPhysicalBoardModuleH80XVDQ,
                      added hwPhysicalBoardModuleH802XGBC."

         REVISION     "201206192001Z"
         DESCRIPTION  "V1.10,
                      added hwPhysicalChassisH801MABR,
                            hwPhysicalBoardModuleH801MCUD,
                            hwPhysicalBoardModuleH801MPWC,
                            hwPhysicalSubBoardModuleH801CPCA,
                            hwPhysicalSubBoardModuleH801CPCB."

         REVISION     "201206041700Z"
         DESCRIPTION  "V1.09,
                      added hwPhysicalBoardModuleH801XEBD."

         REVISION     "201202022001Z"
         DESCRIPTION  "V1.08,
                      added hwPhysicalBoardModuleH80XVDP,
                            hwPhysicalBoardModuleH805GPBD,
                            hwPhysicalBoardModuleH805EPBD,
                            hwPhysicalBoardModuleH808EPSD,
                            hwPhysicalBoardModuleH801GPFD,
                            hwPhysicalBoardModuleH80XVPE,
                            hwPhysicalBoardModuleH80XVCM,
                            hwPhysicalBoardModuleH80BCVME,
                            hwPhysicalBoardModuleH801XGBC,
                            hwPhysicalBoardModuleH801SCUH,
                            hwPhysicalChassisH802MABO."

         REVISION     "201201302001Z"
         DESCRIPTION  "V1.07,Modified the description of the mib file."

         REVISION     "201201102001Z"
         DESCRIPTION
                     "
                     V1.06, add iODN products' types:
                     added hwPhysicalStackMPU3101BAC1U,
                           hwPhysicalStackMPU3101CAC1U,
                           hwPhysicalStackMPU3101DAC1U,
                           hwPhysicalStackMPU3101BDC1U,
                           hwPhysicalStackMPU3101CDC1U,
                           hwPhysicalStackMPU3101DDC1U,
                           hwPhysicalStackAF11FPUA,
                           hwPhysicalStackAF11FPUAT,
                           hwPhysicalStackGPX147iMODF6U,
                           hwPhysicalStackAF11FATA,
                           hwPhysicalStackAF11IFBA,
                           hwPhysicalStackAF11FATC,
                           hwPhysicalStackAF11FATB to hwPhysicalStackType,
                     added hwPhysicalChassisGPX147iODF3101,
                           hwPhysicalChassisGXF147iFDT3101,
                           hwPhysicalChassisGXF147iFDT3101D864,
                           hwPhysicalChassisGXF147FDT2107D864,
                           hwPhysicalChassisGPX147iFAT3101,
                           hwPhysicalChassisGPX147iFAT310212,
                           hwPhysicalChassisGPX147iFAT3102,
                           hwPhysicalChassisGPX147ODF5101CH21200mm,
                           hwPhysicalChassisGPX147ODF5101FH21200mm,
                           hwPhysicalChassisGPX147ODF5101CH2900mm,
                           hwPhysicalChassisGPX147ODF5101FH2900mm,
                           hwPhysicalChassisGPX147ODF5101CH9,
                           hwPhysicalChassisGPX147ODF5101FH9,
                           hwPhysicalChassisGXF147iFDT3101D864A,
                           hwPhysicalChassisGXF147iFDT3103D432,
                           hwPhysicalChassisGPX147ODF5101CH2A,
                           hwPhysicalChassisGPX147ODF5101FH2A,
                           hwPhysicalChassisGPX147iFAT3103T16,
                           hwPhysicalChassisGPX147iFAT3103T24,
                           hwPhysicalChassisGPX147iFAT3105T32,
                           hwPhysicalChassisGPX147iFAT3105T36,
                           hwPhysicalChassisGPX147iFAT3101TD32,
                           hwPhysicalChassisGPX147iFAT3101TD36,
                           hwPhysicalChassisGPX147iFAT3103TD96F,
                           hwPhysicalChassisGPX147iFAT3103TD96P to hwPhysicalChassisType,
                     added hwPhysicalContainerGPX147SR51015U,
                           hwPhysicalContainerGPX147SR51015U2,
                           hwPhysicalContainerGPX147SR51025U,
                           hwPhysicalContainerGXF147FAT5201T to hwPhysicalContainerType.
                     added hwPhysicalBoardModuleAF11TMSA,
                           hwPhysicalBoardModuleAF11TMUA,
                           hwPhysicalBoardModuleAF11TMLA,
                           hwPhysicalBoardModuleAF11TMPA,
                           hwPhysicalBoardModuleAF11STSA,
                           hwPhysicalBoardModuleAF11STUA,
                           hwPhysicalBoardModuleAF11STLA,
                           hwPhysicalBoardModuleAF11STPA,
                           hwPhysicalBoardModuleAF11SPSIA,
                           hwPhysicalBoardModuleAF11SPUIA,
                           hwPhysicalBoardModuleAF11SPLIA,
                           hwPhysicalBoardModuleAF11SPPIA,
                           hwPhysicalBoardModuleAF11SPSHA,
                           hwPhysicalBoardModuleAF11SPUHA,
                           hwPhysicalBoardModuleAF11SPLHA,
                           hwPhysicalBoardModuleAF11SPPHA,
                           hwPhysicalBoardModuleAF11SPSOA,
                           hwPhysicalBoardModuleAF11SPUOA,
                           hwPhysicalBoardModuleAF11SPLOA,
                           hwPhysicalBoardModuleAF11SPPOA,
                           hwPhysicalBoardModuleAF11SPSPA,
                           hwPhysicalBoardModuleAF11SPUPA,
                           hwPhysicalBoardModuleAF11SPLPA,
                           hwPhysicalBoardModuleAF11SPPPA,
                           hwPhysicalBoardModuleAF11SPSJA,
                           hwPhysicalBoardModuleAF11SPUJA,
                           hwPhysicalBoardModuleAF11SPLJA,
                           hwPhysicalBoardModuleAF11SPPJA,
                           hwPhysicalBoardModuleAF11SPSQA,
                           hwPhysicalBoardModuleAF11SPUQA,
                           hwPhysicalBoardModuleAF11SPLQA,
                           hwPhysicalBoardModuleAF11SPPQA,
                           hwPhysicalBoardModuleAF11SPSKA,
                           hwPhysicalBoardModuleAF11SPUKA,
                           hwPhysicalBoardModuleAF11SPLKA,
                           hwPhysicalBoardModuleAF11SPPKA,
                           hwPhysicalBoardModuleAF11SPSRA,
                           hwPhysicalBoardModuleAF11SPURA,
                           hwPhysicalBoardModuleAF11SPLRA,
                           hwPhysicalBoardModuleAF11SPPRA,
                           hwPhysicalBoardModuleAF11SPSLA,
                           hwPhysicalBoardModuleAF11SPULA,
                           hwPhysicalBoardModuleAF11SPLLA,
                           hwPhysicalBoardModuleAF11SPPLA,
                           hwPhysicalBoardModuleAF11SPSSA,
                           hwPhysicalBoardModuleAF11SPUSA,
                           hwPhysicalBoardModuleAF11SPLSA,
                           hwPhysicalBoardModuleAF11SPPSA,
                           hwPhysicalBoardModuleAF11SPSMA,
                           hwPhysicalBoardModuleAF11SPUMA,
                           hwPhysicalBoardModuleAF11SPLMA,
                           hwPhysicalBoardModuleAF11SPPMA,
                           hwPhysicalBoardModuleAF11SPSTA,
                           hwPhysicalBoardModuleAF11SPUTA,
                           hwPhysicalBoardModuleAF11SPLTA,
                           hwPhysicalBoardModuleAF11SPPTA,
                           hwPhysicalBoardModuleAF11STUB,
                           hwPhysicalBoardModuleAF11STSB,
                           hwPhysicalBoardModuleAF11STLB,
                           hwPhysicalBoardModuleAF11STPB,
                           hwPhysicalBoardModuleAF11STUC,
                           hwPhysicalBoardModuleAF11STSC,
                           hwPhysicalBoardModuleAF11STLC,
                           hwPhysicalBoardModuleAF11STPC,
                           hwPhysicalBoardModuleAF11TMUB,
                           hwPhysicalBoardModuleAF11TMSB,
                           hwPhysicalBoardModuleAF11TMLB,
                           hwPhysicalBoardModuleAF11TMPB,
                           hwPhysicalBoardModuleAF11TMUC,
                           hwPhysicalBoardModuleAF11TMSC,
                           hwPhysicalBoardModuleAF11TMLC,
                           hwPhysicalBoardModuleAF11TMPC to hwPhysicalBoardModuleType,
                     added hwPhysicalSubBoardModuleAF11AMCX1,
                           hwPhysicalSubBoardModuleAF11AMCB1,
                           hwPhysicalSubBoardModuleAF11AMCC1,
                           hwPhysicalSubBoardModuleAF11AMCD1,
                           hwPhysicalSubBoardModuleAF11AMCX2,
                           hwPhysicalSubBoardModuleAF11AMCB2,
                           hwPhysicalSubBoardModuleAF11AMCC2,
                           hwPhysicalSubBoardModuleAF11AMCD2 to hwPhysicalSubBoardModuleType.
                     "

        REVISION     "201105090000Z"
        DESCRIPTION  "V1.05,added hwPhysicalBoardModuleH85BCVME,hwPhysicalBoardModuleH801VRGA and hwPhysicalBoardModuleH806EPBD."

        REVISION     "201012280000Z"
        DESCRIPTION  "V1.04,added hwPhysicalBoardModuleH803TPBA and hwPhysicalBoardModuleH803TPBC."

        REVISION     "201011100000Z"
        DESCRIPTION  "V1.03,Modified the description of the mib file."

        REVISION     "201011080900Z"
        DESCRIPTION  "V1.02,added device information of hwPhysicalBoardModuleType and hwPhysicalSubBoardModuleType."

        REVISION     "201008260900Z"
        DESCRIPTION  "V1.01,added hwPhysicalSubBoardModuleH801BITSB, hwPhysicalSubBoardModuleH801O4GS and hwPhysicalBoardModuleH801ETHA."

        REVISION     "201008140900Z"
        DESCRIPTION  "V1.00,Initial version."

            ::= { huaweiUtility 162 }


        hwEntityMIBObjects             OBJECT IDENTIFIER ::= { hwEntityVendorType 1 }


        hwPhysicalStackType            OBJECT IDENTIFIER ::= { hwEntityMIBObjects 1 }
            hwPhysicalStackP300Type   OBJECT IDENTIFIER ::= { hwPhysicalStackType 1 }

            hwPhysicalStackMPU3101BAC1U     OBJECT IDENTIFIER ::= { hwPhysicalStackType 2 }
            hwPhysicalStackMPU3101CAC1U     OBJECT IDENTIFIER ::= { hwPhysicalStackType 3 }
            hwPhysicalStackMPU3101DAC1U     OBJECT IDENTIFIER ::= { hwPhysicalStackType 4 }
            hwPhysicalStackMPU3101BDC1U     OBJECT IDENTIFIER ::= { hwPhysicalStackType 5 }
            hwPhysicalStackMPU3101CDC1U     OBJECT IDENTIFIER ::= { hwPhysicalStackType 6 }
            hwPhysicalStackMPU3101DDC1U     OBJECT IDENTIFIER ::= { hwPhysicalStackType 7 }
            hwPhysicalStackMxUType     	      OBJECT IDENTIFIER ::= { hwPhysicalStackType 100 }
            hwPhysicalStackAF11FPUA           OBJECT IDENTIFIER ::= { hwPhysicalStackType 257 }
            hwPhysicalStackAF11FPUAT          OBJECT IDENTIFIER ::= { hwPhysicalStackType 258 }
            hwPhysicalStackGPX147iMODF6U    OBJECT IDENTIFIER ::= { hwPhysicalStackType 259 }
            hwPhysicalStackAF11FATA           OBJECT IDENTIFIER ::= { hwPhysicalStackType 260 }
            hwPhysicalStackAF11IFBA           OBJECT IDENTIFIER ::= { hwPhysicalStackType 261 }
            hwPhysicalStackAF11FATC           OBJECT IDENTIFIER ::= { hwPhysicalStackType 513 }
            hwPhysicalStackAF11FATB           OBJECT IDENTIFIER ::= { hwPhysicalStackType 514 }

        hwPhysicalChassisType          OBJECT IDENTIFIER ::= { hwEntityMIBObjects 2 }
            hwPhysicalChassisGPX147iODF3101            OBJECT IDENTIFIER ::= { hwPhysicalChassisType 8193 }
            hwPhysicalChassisGXF147iFDT3101            OBJECT IDENTIFIER ::= { hwPhysicalChassisType 8194 }
            hwPhysicalChassisGXF147iFDT3101D864       OBJECT IDENTIFIER ::= { hwPhysicalChassisType 8195 }
            hwPhysicalChassisGXF147FDT2107D864        OBJECT IDENTIFIER ::= { hwPhysicalChassisType 8196 }
            hwPhysicalChassisGPX147iFAT3101            OBJECT IDENTIFIER ::= { hwPhysicalChassisType 8197 }
            hwPhysicalChassisGPX147iFAT310212         OBJECT IDENTIFIER ::= { hwPhysicalChassisType 8198 }
            hwPhysicalChassisGPX147iFAT3102            OBJECT IDENTIFIER ::= { hwPhysicalChassisType 8199 }
            hwPhysicalChassisGPX147ODF5101CH21200mm  OBJECT IDENTIFIER ::= { hwPhysicalChassisType 8200 }
            hwPhysicalChassisGPX147ODF5101FH21200mm  OBJECT IDENTIFIER ::= { hwPhysicalChassisType 8201 }
            hwPhysicalChassisGPX147ODF5101CH2900mm   OBJECT IDENTIFIER ::= { hwPhysicalChassisType 8202 }
            hwPhysicalChassisGPX147ODF5101FH2900mm   OBJECT IDENTIFIER ::= { hwPhysicalChassisType 8203 }
            hwPhysicalChassisGPX147ODF5101CH9         OBJECT IDENTIFIER ::= { hwPhysicalChassisType 8204 }
            hwPhysicalChassisGPX147ODF5101FH9         OBJECT IDENTIFIER ::= { hwPhysicalChassisType 8205 }
            hwPhysicalChassisGXF147iFDT3101D864A     OBJECT IDENTIFIER ::= { hwPhysicalChassisType 8206 }
            hwPhysicalChassisGXF147iFDT3103D432       OBJECT IDENTIFIER ::= { hwPhysicalChassisType 8208 }
            hwPhysicalChassisGPX147ODF5101CH2A        OBJECT IDENTIFIER ::= { hwPhysicalChassisType 8209 }
            hwPhysicalChassisGPX147ODF5101FH2A        OBJECT IDENTIFIER ::= { hwPhysicalChassisType 8210 }
            hwPhysicalChassisGPX147iFAT3103T16        OBJECT IDENTIFIER ::= { hwPhysicalChassisType 8449 }
            hwPhysicalChassisGPX147iFAT3103T24        OBJECT IDENTIFIER ::= { hwPhysicalChassisType 8450 }
            hwPhysicalChassisGPX147iFAT3105T32        OBJECT IDENTIFIER ::= { hwPhysicalChassisType 8451 }
            hwPhysicalChassisGPX147iFAT3105T36        OBJECT IDENTIFIER ::= { hwPhysicalChassisType 8452 }
            hwPhysicalChassisGPX147iFAT3101TD32       OBJECT IDENTIFIER ::= { hwPhysicalChassisType 8453 }
            hwPhysicalChassisGPX147iFAT3101TD36       OBJECT IDENTIFIER ::= { hwPhysicalChassisType 8454 }
            hwPhysicalChassisGPX147iFAT3103TD96F     OBJECT IDENTIFIER ::= { hwPhysicalChassisType 8455 }
            hwPhysicalChassisGPX147iFAT3103TD96P     OBJECT IDENTIFIER ::= { hwPhysicalChassisType 8456 }

            hwPhysicalChassisH801MABC   OBJECT IDENTIFIER ::= { hwPhysicalChassisType 145949 }
            hwPhysicalChassisH801MABH   OBJECT IDENTIFIER ::= { hwPhysicalChassisType 143362 }
            hwPhysicalChassisH801MABO   OBJECT IDENTIFIER ::= { hwPhysicalChassisType 143370 }
            hwPhysicalChassisH831MABCA   OBJECT IDENTIFIER ::= { hwPhysicalChassisType 143377 }
            hwPhysicalChassisH801Mabv   OBJECT IDENTIFIER ::= { hwPhysicalChassisType 143359 }
            hwPhysicalChassisH801Maba   OBJECT IDENTIFIER ::= { hwPhysicalChassisType 143360 }
            hwPhysicalChassisH801Spba   OBJECT IDENTIFIER ::= { hwPhysicalChassisType 143361 }
            hwPhysicalChassisH801Mabd   OBJECT IDENTIFIER ::= { hwPhysicalChassisType 145950 }
            hwPhysicalChassisH801Mabi   OBJECT IDENTIFIER ::= { hwPhysicalChassisType 145951 }
            hwPhysicalChassisH802MABC   OBJECT IDENTIFIER ::= { hwPhysicalChassisType 145952 }
            hwPhysicalChassisH802MABO   OBJECT IDENTIFIER ::= { hwPhysicalChassisType 147523 }
            hwPhysicalChassisH801MABR   OBJECT IDENTIFIER ::= { hwPhysicalChassisType 147525 }
            hwPhysicalChassisMA5623AR   OBJECT IDENTIFIER ::= { hwPhysicalChassisType 147526 }
            hwPhysicalChassisMA5633     OBJECT IDENTIFIER ::= { hwPhysicalChassisType 147527 }
            hwPhysicalChassisH803MABC   OBJECT IDENTIFIER ::= { hwPhysicalChassisType 147529 }
            hwPhysicalChassisRemoteReserve30   OBJECT IDENTIFIER ::= { hwPhysicalChassisType 147530 }
            hwPhysicalChassisRemoteReserve31   OBJECT IDENTIFIER ::= { hwPhysicalChassisType 147531 }
            hwPhysicalChassisRemoteReserve32   OBJECT IDENTIFIER ::= { hwPhysicalChassisType 147532 }
            hwPhysicalChassisRemoteReserve33   OBJECT IDENTIFIER ::= { hwPhysicalChassisType 147533 }
            hwPhysicalChassisRemoteReserve34   OBJECT IDENTIFIER ::= { hwPhysicalChassisType 147534 }
            hwPhysicalChassisRemoteReserve35   OBJECT IDENTIFIER ::= { hwPhysicalChassisType 147535 }
            hwPhysicalChassisRemoteReserve36   OBJECT IDENTIFIER ::= { hwPhysicalChassisType 147536 }
            hwPhysicalChassisRemoteReserve37   OBJECT IDENTIFIER ::= { hwPhysicalChassisType 147537 }
            hwPhysicalChassisRemoteReserve38   OBJECT IDENTIFIER ::= { hwPhysicalChassisType 147538 }
            hwPhysicalChassisRemoteReserve39   OBJECT IDENTIFIER ::= { hwPhysicalChassisType 147539 }
	    hwPhysicalChassisH805MABC    OBJECT IDENTIFIER ::= { hwPhysicalChassisType 147540 }    
	    hwPhysicalChassisH805MABO    OBJECT IDENTIFIER ::= { hwPhysicalChassisType 147541 }    
            hwPhysicalChassisH802MABH   OBJECT IDENTIFIER ::= { hwPhysicalChassisType 147571 }
            hwPhysicalChassisH802MABR   OBJECT IDENTIFIER ::= { hwPhysicalChassisType 147572 }
            hwPhysicalChassisH901BPLB   OBJECT IDENTIFIER ::= { hwPhysicalChassisType 148501 }
            hwPhysicalChassisH901BPMB   OBJECT IDENTIFIER ::= { hwPhysicalChassisType 148502 }
            hwPhysicalChassisH901BPLE   OBJECT IDENTIFIER ::= { hwPhysicalChassisType 148511 }
            hwPhysicalChassisH901BPIB   OBJECT IDENTIFIER ::= { hwPhysicalChassisType 148512 }
            hwPhysicalChassisH901BPSB   OBJECT IDENTIFIER ::= { hwPhysicalChassisType 148513 }
            hwPhysicalChassisH901BPLD   OBJECT IDENTIFIER ::= { hwPhysicalChassisType 148514 }
            hwPhysicalChassisMA5800Reserve15   OBJECT IDENTIFIER ::= { hwPhysicalChassisType 148515 }
            hwPhysicalChassisMA5800Reserve16   OBJECT IDENTIFIER ::= { hwPhysicalChassisType 148516 }
            hwPhysicalChassisMA5800Reserve17   OBJECT IDENTIFIER ::= { hwPhysicalChassisType 148517 }
            hwPhysicalChassisMA5800Reserve18   OBJECT IDENTIFIER ::= { hwPhysicalChassisType 148518 }
            hwPhysicalChassisMA5800Reserve19   OBJECT IDENTIFIER ::= { hwPhysicalChassisType 148519 }
            hwPhysicalChassisMA5800Reserve20   OBJECT IDENTIFIER ::= { hwPhysicalChassisType 148520 }
            hwPhysicalChassisMA5800Reserve21   OBJECT IDENTIFIER ::= { hwPhysicalChassisType 148521 }
            hwPhysicalChassisMA5800Reserve22   OBJECT IDENTIFIER ::= { hwPhysicalChassisType 148522 }
            hwPhysicalChassisMA5800Reserve23   OBJECT IDENTIFIER ::= { hwPhysicalChassisType 148523 }
            hwPhysicalChassisMA5800Reserve24   OBJECT IDENTIFIER ::= { hwPhysicalChassisType 148524 }
            hwPhysicalChassisMA5800Reserve25   OBJECT IDENTIFIER ::= { hwPhysicalChassisType 148525 }
            hwPhysicalChassisMA5800Reserve26   OBJECT IDENTIFIER ::= { hwPhysicalChassisType 148526 }
            hwPhysicalChassisMA5800Reserve27   OBJECT IDENTIFIER ::= { hwPhysicalChassisType 148527 }
            hwPhysicalChassisMA5800Reserve28   OBJECT IDENTIFIER ::= { hwPhysicalChassisType 148528 }
            hwPhysicalChassisMA5800Reserve29   OBJECT IDENTIFIER ::= { hwPhysicalChassisType 148529 }
            hwPhysicalChassisMA5800Reserve30   OBJECT IDENTIFIER ::= { hwPhysicalChassisType 148530 }
            hwPhysicalChassisMA5800Reserve31   OBJECT IDENTIFIER ::= { hwPhysicalChassisType 148531 }
            hwPhysicalChassisMA5800Reserve32   OBJECT IDENTIFIER ::= { hwPhysicalChassisType 148532 }
            hwPhysicalChassisMA5800Reserve33   OBJECT IDENTIFIER ::= { hwPhysicalChassisType 148533 }
            hwPhysicalChassisMA5800Reserve34   OBJECT IDENTIFIER ::= { hwPhysicalChassisType 148534 }
            hwPhysicalChassisMA5800Reserve35   OBJECT IDENTIFIER ::= { hwPhysicalChassisType 148535 }
            hwPhysicalChassisMA5800Reserve36   OBJECT IDENTIFIER ::= { hwPhysicalChassisType 148536 }
            hwPhysicalChassisMA5800Reserve37   OBJECT IDENTIFIER ::= { hwPhysicalChassisType 148537 }
            hwPhysicalChassisMA5800Reserve38   OBJECT IDENTIFIER ::= { hwPhysicalChassisType 148538 }
            hwPhysicalChassisMA5800Reserve39   OBJECT IDENTIFIER ::= { hwPhysicalChassisType 148539 }
            hwPhysicalChassisMA5800Reserve40   OBJECT IDENTIFIER ::= { hwPhysicalChassisType 148540 }      
	     
           
            hwPhysicalChassisH831MABC   OBJECT IDENTIFIER ::= { hwPhysicalChassisType 561193 }

        hwPhysicalContainerType        OBJECT IDENTIFIER ::= { hwEntityMIBObjects 3 }
            hwPhysicalContainerP300Slot      OBJECT IDENTIFIER ::= { hwPhysicalContainerType 1 }
            hwPhysicalContainerP300SubSlot   OBJECT IDENTIFIER ::= { hwPhysicalContainerType 2 }
            hwPhysicalContainerMxUSlot       OBJECT IDENTIFIER ::= { hwPhysicalContainerType 3 }
            hwPhysicalContainerMxUSubSlot    OBJECT IDENTIFIER ::= { hwPhysicalContainerType 4 }
            hwPhysicalContainerGPX147SR51015U              OBJECT IDENTIFIER ::= { hwPhysicalContainerType 16385 }
            hwPhysicalContainerGPX147SR51015U2            OBJECT IDENTIFIER ::= { hwPhysicalContainerType 16386 }
            hwPhysicalContainerGPX147SR51025U              OBJECT IDENTIFIER ::= { hwPhysicalContainerType 16387 }
            hwPhysicalContainerGXF147FAT5201T               OBJECT IDENTIFIER ::= { hwPhysicalContainerType 16388 }

        hwPhysicalBoardModuleType      OBJECT IDENTIFIER ::= { hwEntityMIBObjects 4 }
            hwPhysicalBoardModuleAF11TMSA          OBJECT IDENTIFIER ::= { hwPhysicalBoardModuleType 24577 }
            hwPhysicalBoardModuleAF11TMUA          OBJECT IDENTIFIER ::= { hwPhysicalBoardModuleType 24578 }
            hwPhysicalBoardModuleAF11TMLA          OBJECT IDENTIFIER ::= { hwPhysicalBoardModuleType 24579 }
            hwPhysicalBoardModuleAF11TMPA          OBJECT IDENTIFIER ::= { hwPhysicalBoardModuleType 24580 }
            hwPhysicalBoardModuleAF11STSA          OBJECT IDENTIFIER ::= { hwPhysicalBoardModuleType 24581 }
            hwPhysicalBoardModuleAF11STUA          OBJECT IDENTIFIER ::= { hwPhysicalBoardModuleType 24582 }
            hwPhysicalBoardModuleAF11STLA          OBJECT IDENTIFIER ::= { hwPhysicalBoardModuleType 24583 }
            hwPhysicalBoardModuleAF11STPA          OBJECT IDENTIFIER ::= { hwPhysicalBoardModuleType 24584 }
            hwPhysicalBoardModuleAF11SPSIA         OBJECT IDENTIFIER ::= { hwPhysicalBoardModuleType 24585 }
            hwPhysicalBoardModuleAF11SPUIA         OBJECT IDENTIFIER ::= { hwPhysicalBoardModuleType 24586 }
            hwPhysicalBoardModuleAF11SPLIA         OBJECT IDENTIFIER ::= { hwPhysicalBoardModuleType 24587 }
            hwPhysicalBoardModuleAF11SPPIA         OBJECT IDENTIFIER ::= { hwPhysicalBoardModuleType 24588 }
            hwPhysicalBoardModuleAF11SPSHA         OBJECT IDENTIFIER ::= { hwPhysicalBoardModuleType 24589 }
            hwPhysicalBoardModuleAF11SPUHA         OBJECT IDENTIFIER ::= { hwPhysicalBoardModuleType 24590 }
            hwPhysicalBoardModuleAF11SPLHA         OBJECT IDENTIFIER ::= { hwPhysicalBoardModuleType 24591 }
            hwPhysicalBoardModuleAF11SPPHA         OBJECT IDENTIFIER ::= { hwPhysicalBoardModuleType 24592 }
            hwPhysicalBoardModuleAF11SPSOA         OBJECT IDENTIFIER ::= { hwPhysicalBoardModuleType 24593 }
            hwPhysicalBoardModuleAF11SPUOA         OBJECT IDENTIFIER ::= { hwPhysicalBoardModuleType 24594 }
            hwPhysicalBoardModuleAF11SPLOA         OBJECT IDENTIFIER ::= { hwPhysicalBoardModuleType 24595 }
            hwPhysicalBoardModuleAF11SPPOA         OBJECT IDENTIFIER ::= { hwPhysicalBoardModuleType 24596 }
            hwPhysicalBoardModuleAF11SPSPA         OBJECT IDENTIFIER ::= { hwPhysicalBoardModuleType 24597 }
            hwPhysicalBoardModuleAF11SPUPA         OBJECT IDENTIFIER ::= { hwPhysicalBoardModuleType 24598 }
            hwPhysicalBoardModuleAF11SPLPA         OBJECT IDENTIFIER ::= { hwPhysicalBoardModuleType 24599 }
            hwPhysicalBoardModuleAF11SPPPA         OBJECT IDENTIFIER ::= { hwPhysicalBoardModuleType 24600 }
            hwPhysicalBoardModuleAF11SPSJA         OBJECT IDENTIFIER ::= { hwPhysicalBoardModuleType 24601 }
            hwPhysicalBoardModuleAF11SPUJA         OBJECT IDENTIFIER ::= { hwPhysicalBoardModuleType 24602 }
            hwPhysicalBoardModuleAF11SPLJA         OBJECT IDENTIFIER ::= { hwPhysicalBoardModuleType 24603 }
            hwPhysicalBoardModuleAF11SPPJA         OBJECT IDENTIFIER ::= { hwPhysicalBoardModuleType 24604 }
            hwPhysicalBoardModuleAF11SPSQA         OBJECT IDENTIFIER ::= { hwPhysicalBoardModuleType 24605 }
            hwPhysicalBoardModuleAF11SPUQA         OBJECT IDENTIFIER ::= { hwPhysicalBoardModuleType 24606 }
            hwPhysicalBoardModuleAF11SPLQA         OBJECT IDENTIFIER ::= { hwPhysicalBoardModuleType 24607 }
            hwPhysicalBoardModuleAF11SPPQA         OBJECT IDENTIFIER ::= { hwPhysicalBoardModuleType 24608 }
            hwPhysicalBoardModuleAF11SPSKA         OBJECT IDENTIFIER ::= { hwPhysicalBoardModuleType 24833 }
            hwPhysicalBoardModuleAF11SPUKA         OBJECT IDENTIFIER ::= { hwPhysicalBoardModuleType 24834 }
            hwPhysicalBoardModuleAF11SPLKA         OBJECT IDENTIFIER ::= { hwPhysicalBoardModuleType 24835 }
            hwPhysicalBoardModuleAF11SPPKA         OBJECT IDENTIFIER ::= { hwPhysicalBoardModuleType 24836 }
            hwPhysicalBoardModuleAF11SPSRA         OBJECT IDENTIFIER ::= { hwPhysicalBoardModuleType 24837 }
            hwPhysicalBoardModuleAF11SPURA         OBJECT IDENTIFIER ::= { hwPhysicalBoardModuleType 24838 }
            hwPhysicalBoardModuleAF11SPLRA         OBJECT IDENTIFIER ::= { hwPhysicalBoardModuleType 24839 }
            hwPhysicalBoardModuleAF11SPPRA         OBJECT IDENTIFIER ::= { hwPhysicalBoardModuleType 24840 }
            hwPhysicalBoardModuleAF11SPSLA         OBJECT IDENTIFIER ::= { hwPhysicalBoardModuleType 24841 }
            hwPhysicalBoardModuleAF11SPULA         OBJECT IDENTIFIER ::= { hwPhysicalBoardModuleType 24842 }
            hwPhysicalBoardModuleAF11SPLLA         OBJECT IDENTIFIER ::= { hwPhysicalBoardModuleType 24843 }
            hwPhysicalBoardModuleAF11SPPLA         OBJECT IDENTIFIER ::= { hwPhysicalBoardModuleType 24844 }
            hwPhysicalBoardModuleAF11SPSSA         OBJECT IDENTIFIER ::= { hwPhysicalBoardModuleType 24845 }
            hwPhysicalBoardModuleAF11SPUSA         OBJECT IDENTIFIER ::= { hwPhysicalBoardModuleType 24846 }
            hwPhysicalBoardModuleAF11SPLSA         OBJECT IDENTIFIER ::= { hwPhysicalBoardModuleType 24847 }
            hwPhysicalBoardModuleAF11SPPSA         OBJECT IDENTIFIER ::= { hwPhysicalBoardModuleType 24848 }
            hwPhysicalBoardModuleAF11SPSMA         OBJECT IDENTIFIER ::= { hwPhysicalBoardModuleType 24849 }
            hwPhysicalBoardModuleAF11SPUMA         OBJECT IDENTIFIER ::= { hwPhysicalBoardModuleType 24850 }
            hwPhysicalBoardModuleAF11SPLMA         OBJECT IDENTIFIER ::= { hwPhysicalBoardModuleType 24851 }
            hwPhysicalBoardModuleAF11SPPMA         OBJECT IDENTIFIER ::= { hwPhysicalBoardModuleType 24852 }
            hwPhysicalBoardModuleAF11SPSTA         OBJECT IDENTIFIER ::= { hwPhysicalBoardModuleType 24853 }
            hwPhysicalBoardModuleAF11SPUTA         OBJECT IDENTIFIER ::= { hwPhysicalBoardModuleType 24854 }
            hwPhysicalBoardModuleAF11SPLTA         OBJECT IDENTIFIER ::= { hwPhysicalBoardModuleType 24855 }
            hwPhysicalBoardModuleAF11SPPTA         OBJECT IDENTIFIER ::= { hwPhysicalBoardModuleType 24856 }
            hwPhysicalBoardModuleAF11STUB          OBJECT IDENTIFIER ::= { hwPhysicalBoardModuleType 25089 }
            hwPhysicalBoardModuleAF11STSB          OBJECT IDENTIFIER ::= { hwPhysicalBoardModuleType 25090 }
            hwPhysicalBoardModuleAF11STLB          OBJECT IDENTIFIER ::= { hwPhysicalBoardModuleType 25091 }
            hwPhysicalBoardModuleAF11STPB          OBJECT IDENTIFIER ::= { hwPhysicalBoardModuleType 25092 }
            hwPhysicalBoardModuleAF11STUC          OBJECT IDENTIFIER ::= { hwPhysicalBoardModuleType 25093 }
            hwPhysicalBoardModuleAF11STSC          OBJECT IDENTIFIER ::= { hwPhysicalBoardModuleType 25094 }
            hwPhysicalBoardModuleAF11STLC          OBJECT IDENTIFIER ::= { hwPhysicalBoardModuleType 25095 }
            hwPhysicalBoardModuleAF11STPC          OBJECT IDENTIFIER ::= { hwPhysicalBoardModuleType 25096 }
            hwPhysicalBoardModuleAF11TMUB          OBJECT IDENTIFIER ::= { hwPhysicalBoardModuleType 25097 }
            hwPhysicalBoardModuleAF11TMSB          OBJECT IDENTIFIER ::= { hwPhysicalBoardModuleType 25098 }
            hwPhysicalBoardModuleAF11TMLB          OBJECT IDENTIFIER ::= { hwPhysicalBoardModuleType 25099 }
            hwPhysicalBoardModuleAF11TMPB          OBJECT IDENTIFIER ::= { hwPhysicalBoardModuleType 25100 }
            hwPhysicalBoardModuleAF11TMUC          OBJECT IDENTIFIER ::= { hwPhysicalBoardModuleType 25101 }
            hwPhysicalBoardModuleAF11TMSC          OBJECT IDENTIFIER ::= { hwPhysicalBoardModuleType 25102 }
            hwPhysicalBoardModuleAF11TMLC          OBJECT IDENTIFIER ::= { hwPhysicalBoardModuleType 25103 }
            hwPhysicalBoardModuleAF11TMPC          OBJECT IDENTIFIER ::= { hwPhysicalBoardModuleType 25104 }

            hwPhysicalBoardModuleH801SCUN    OBJECT IDENTIFIER ::= { hwPhysicalBoardModuleType 146037 }
            hwPhysicalBoardModuleH801PRTE    OBJECT IDENTIFIER ::= { hwPhysicalBoardModuleType 146040 }
            hwPhysicalBoardModuleH801SPUB    OBJECT IDENTIFIER ::= { hwPhysicalBoardModuleType 146058 }
            hwPhysicalBoardModuleH801X2CS    OBJECT IDENTIFIER ::= { hwPhysicalBoardModuleType 146038 }
            hwPhysicalBoardModuleH801GICK    OBJECT IDENTIFIER ::= { hwPhysicalBoardModuleType 146056 }
            hwPhysicalBoardModuleH801GPBC    OBJECT IDENTIFIER ::= { hwPhysicalBoardModuleType 145977 }
            hwPhysicalBoardModuleH802GPBD    OBJECT IDENTIFIER ::= { hwPhysicalBoardModuleType 146054 }
            hwPhysicalBoardModuleH801SCUL    OBJECT IDENTIFIER ::= { hwPhysicalBoardModuleType 145978 }
            hwPhysicalBoardModuleH801X2CA    OBJECT IDENTIFIER ::= { hwPhysicalBoardModuleType 145979 }
            hwPhysicalBoardModuleH801GICF    OBJECT IDENTIFIER ::= { hwPhysicalBoardModuleType 145980 }
            hwPhysicalBoardModuleH801GICG    OBJECT IDENTIFIER ::= { hwPhysicalBoardModuleType 145981 }
            hwPhysicalBoardModuleH801CITC    OBJECT IDENTIFIER ::= { hwPhysicalBoardModuleType 145982 }
            hwPhysicalBoardModuleH801PIUA    OBJECT IDENTIFIER ::= { hwPhysicalBoardModuleType 145983 }
            hwPhysicalBoardModuleH821MCUA    OBJECT IDENTIFIER ::= { hwPhysicalBoardModuleType 145984 }
            hwPhysicalBoardModuleH82XVDJ     OBJECT IDENTIFIER ::= { hwPhysicalBoardModuleType 145985 }
            hwPhysicalBoardModuleH82XVDJA    OBJECT IDENTIFIER ::= { hwPhysicalBoardModuleType 145986 }
            hwPhysicalBoardModuleH82XVDJB    OBJECT IDENTIFIER ::= { hwPhysicalBoardModuleType 145987 }
            hwPhysicalBoardModuleH82XVDJC    OBJECT IDENTIFIER ::= { hwPhysicalBoardModuleType 145988 }
            hwPhysicalBoardModuleH82XVDJD    OBJECT IDENTIFIER ::= { hwPhysicalBoardModuleType 145989 }
            hwPhysicalBoardModuleH82XVDJE    OBJECT IDENTIFIER ::= { hwPhysicalBoardModuleType 145990 }
            hwPhysicalBoardModuleH82XVDJF    OBJECT IDENTIFIER ::= { hwPhysicalBoardModuleType 145991 }
            hwPhysicalBoardModuleH82XVDJG    OBJECT IDENTIFIER ::= { hwPhysicalBoardModuleType 145992 }
            hwPhysicalBoardModuleH82XVDJH    OBJECT IDENTIFIER ::= { hwPhysicalBoardModuleType 145993 }
            hwPhysicalBoardModuleH82XVDJI    OBJECT IDENTIFIER ::= { hwPhysicalBoardModuleType 145994 }
            hwPhysicalBoardModuleH82XVDJJ    OBJECT IDENTIFIER ::= { hwPhysicalBoardModuleType 145995 }
            hwPhysicalBoardModuleH82XVDJK    OBJECT IDENTIFIER ::= { hwPhysicalBoardModuleType 145996 }
            hwPhysicalBoardModuleH82XVDJL    OBJECT IDENTIFIER ::= { hwPhysicalBoardModuleType 145997 }
            hwPhysicalBoardModuleH82XVDJM    OBJECT IDENTIFIER ::= { hwPhysicalBoardModuleType 145998 }
            hwPhysicalBoardModuleH82XVDJN    OBJECT IDENTIFIER ::= { hwPhysicalBoardModuleType 145999 }
            hwPhysicalBoardModuleH82XVDJO    OBJECT IDENTIFIER ::= { hwPhysicalBoardModuleType 146000 }
            hwPhysicalBoardModuleH82XVDJP    OBJECT IDENTIFIER ::= { hwPhysicalBoardModuleType 146001 }
            hwPhysicalBoardModuleH82XVDJQ    OBJECT IDENTIFIER ::= { hwPhysicalBoardModuleType 146002 }
            hwPhysicalBoardModuleH82XVDJR    OBJECT IDENTIFIER ::= { hwPhysicalBoardModuleType 146003 }
            hwPhysicalBoardModuleH82XVDJS    OBJECT IDENTIFIER ::= { hwPhysicalBoardModuleType 146004 }
            hwPhysicalBoardModuleH82XVDJT    OBJECT IDENTIFIER ::= { hwPhysicalBoardModuleType 146005 }
            hwPhysicalBoardModuleH82XVDJU    OBJECT IDENTIFIER ::= { hwPhysicalBoardModuleType 146006 }
            hwPhysicalBoardModuleH82XVDJV    OBJECT IDENTIFIER ::= { hwPhysicalBoardModuleType 146007 }
            hwPhysicalBoardModuleH82XVDJW    OBJECT IDENTIFIER ::= { hwPhysicalBoardModuleType 146008 }
            hwPhysicalBoardModuleH82XVDJX    OBJECT IDENTIFIER ::= { hwPhysicalBoardModuleType 146009 }
            hwPhysicalBoardModuleH82XVDJY    OBJECT IDENTIFIER ::= { hwPhysicalBoardModuleType 146010 }
            hwPhysicalBoardModuleH82XVDJZ    OBJECT IDENTIFIER ::= { hwPhysicalBoardModuleType 146011 }
            hwPhysicalBoardModuleH801SCUB    OBJECT IDENTIFIER ::= { hwPhysicalBoardModuleType 146018 }
            hwPhysicalBoardModuleH801ASRB    OBJECT IDENTIFIER ::= { hwPhysicalBoardModuleType 146019 }
            hwPhysicalBoardModuleH801PMIA    OBJECT IDENTIFIER ::= { hwPhysicalBoardModuleType 146020 }
            hwPhysicalBoardModuleH561SCUB    OBJECT IDENTIFIER ::= { hwPhysicalBoardModuleType 146021 }
            hwPhysicalBoardModuleH802SHLB    OBJECT IDENTIFIER ::= { hwPhysicalBoardModuleType 146022 }
            hwPhysicalBoardModuleH801EPBA    OBJECT IDENTIFIER ::= { hwPhysicalBoardModuleType 146023 }
            hwPhysicalBoardModuleH801TOPA    OBJECT IDENTIFIER ::= { hwPhysicalBoardModuleType 146025 }
            hwPhysicalBoardModuleH569SHEB    OBJECT IDENTIFIER ::= { hwPhysicalBoardModuleType 146026 }
            hwPhysicalBoardModuleH801SCUF    OBJECT IDENTIFIER ::= { hwPhysicalBoardModuleType 146027 }
            hwPhysicalBoardModuleADP         OBJECT IDENTIFIER ::= { hwPhysicalBoardModuleType 146028 }
            hwPhysicalBoardModuleADQ         OBJECT IDENTIFIER ::= { hwPhysicalBoardModuleType 146029 }
            hwPhysicalBoardModuleASP         OBJECT IDENTIFIER ::= { hwPhysicalBoardModuleType 146030 }
            hwPhysicalBoardModuleH801EDTB    OBJECT IDENTIFIER ::= { hwPhysicalBoardModuleType 146031 }
            hwPhysicalBoardModuleH80xVDM     OBJECT IDENTIFIER ::= { hwPhysicalBoardModuleType 146032 }
            hwPhysicalBoardModuleH80xVDN     OBJECT IDENTIFIER ::= { hwPhysicalBoardModuleType 146033 }
            hwPhysicalBoardModuleH801GSCA    OBJECT IDENTIFIER ::= { hwPhysicalBoardModuleType 146034 }
            hwPhysicalBoardModuleH802EPBD    OBJECT IDENTIFIER ::= { hwPhysicalBoardModuleType 146039 }
            hwPhysicalBoardModuleH801X4CS    OBJECT IDENTIFIER ::= { hwPhysicalBoardModuleType 146041 }
            hwPhysicalBoardModuleH801GPBD    OBJECT IDENTIFIER ::= { hwPhysicalBoardModuleType 146042 }
            hwPhysicalBoardModuleH801OPGA    OBJECT IDENTIFIER ::= { hwPhysicalBoardModuleType 146043 }
            hwPhysicalBoardModuleH801CITB    OBJECT IDENTIFIER ::= { hwPhysicalBoardModuleType 146047 }
            hwPhysicalBoardModuleH855VDMF    OBJECT IDENTIFIER ::= { hwPhysicalBoardModuleType 146048 }
            hwPhysicalBoardModuleH801PAIB    OBJECT IDENTIFIER ::= { hwPhysicalBoardModuleType 146049 }
            hwPhysicalBoardModuleH851VSNKE   OBJECT IDENTIFIER ::= { hwPhysicalBoardModuleType 146050 }
            hwPhysicalBoardModuleH851VSNLE   OBJECT IDENTIFIER ::= { hwPhysicalBoardModuleType 146051 }
            hwPhysicalBoardModuleH801GPJC    OBJECT IDENTIFIER ::= { hwPhysicalBoardModuleType 146052 }
            hwPhysicalBoardModuleH801CSPA    OBJECT IDENTIFIER ::= { hwPhysicalBoardModuleType 146055 }
            hwPhysicalBoardModuleH801SPUA    OBJECT IDENTIFIER ::= { hwPhysicalBoardModuleType 146057 }
            hwPhysicalBoardModuleH801EPBC    OBJECT IDENTIFIER ::= { hwPhysicalBoardModuleType 146059 }
            hwPhysicalBoardModuleH801BIUB    OBJECT IDENTIFIER ::= { hwPhysicalBoardModuleType 146060 }
            hwPhysicalBoardModuleH801PRTG    OBJECT IDENTIFIER ::= { hwPhysicalBoardModuleType 146061 }
            hwPhysicalBoardModuleH802OPGD    OBJECT IDENTIFIER ::= { hwPhysicalBoardModuleType 146062 }
            hwPhysicalBoardModuleH85BVDMD    OBJECT IDENTIFIER ::= { hwPhysicalBoardModuleType 146063 }
            hwPhysicalBoardModuleH802EDTB    OBJECT IDENTIFIER ::= { hwPhysicalBoardModuleType 146064 }
            hwPhysicalBoardModuleH802P2CA    OBJECT IDENTIFIER ::= { hwPhysicalBoardModuleType 146065 }
            hwPhysicalBoardModuleH802OPGE    OBJECT IDENTIFIER ::= { hwPhysicalBoardModuleType 146075 }
            hwPhysicalBoardModuleH801MPWE    OBJECT IDENTIFIER ::= { hwPhysicalBoardModuleType 146076 }
            hwPhysicalBoardModuleH806CAME    OBJECT IDENTIFIER ::= { hwPhysicalBoardModuleType 146077 }
            hwPhysicalBoardModuleH801X2CK    OBJECT IDENTIFIER ::= { hwPhysicalBoardModuleType 146078 }
            hwPhysicalBoardModuleH802GICK    OBJECT IDENTIFIER ::= { hwPhysicalBoardModuleType 146079 }
            hwPhysicalBoardModuleH808ASPB    OBJECT IDENTIFIER ::= { hwPhysicalBoardModuleType 146081 }
            hwPhysicalBoardModuleH801SCUA    OBJECT IDENTIFIER ::= { hwPhysicalBoardModuleType 143360 }
            hwPhysicalBoardModuleH801SPLK    OBJECT IDENTIFIER ::= { hwPhysicalBoardModuleType 143361 }
            hwPhysicalBoardModuleH801SPMA    OBJECT IDENTIFIER ::= { hwPhysicalBoardModuleType 143362 }
            hwPhysicalBoardModuleH805ADLL    OBJECT IDENTIFIER ::= { hwPhysicalBoardModuleType 143363 }
            hwPhysicalBoardModuleH802SHLA    OBJECT IDENTIFIER ::= { hwPhysicalBoardModuleType 143364 }
            hwPhysicalBoardModuleH801AIUG    OBJECT IDENTIFIER ::= { hwPhysicalBoardModuleType 143365 }
            hwPhysicalBoardModuleADI         OBJECT IDENTIFIER ::= { hwPhysicalBoardModuleType 143366 }
            hwPhysicalBoardModuleADIA        OBJECT IDENTIFIER ::= { hwPhysicalBoardModuleType 143367 }
            hwPhysicalBoardModuleADIB        OBJECT IDENTIFIER ::= { hwPhysicalBoardModuleType 143368 }
            hwPhysicalBoardModuleADIC        OBJECT IDENTIFIER ::= { hwPhysicalBoardModuleType 143369 }
            hwPhysicalBoardModuleADID        OBJECT IDENTIFIER ::= { hwPhysicalBoardModuleType 143370 }
            hwPhysicalBoardModuleADIE        OBJECT IDENTIFIER ::= { hwPhysicalBoardModuleType 143371 }
            hwPhysicalBoardModuleADIF        OBJECT IDENTIFIER ::= { hwPhysicalBoardModuleType 143372 }
            hwPhysicalBoardModuleADIG        OBJECT IDENTIFIER ::= { hwPhysicalBoardModuleType 143373 }
            hwPhysicalBoardModuleADIH        OBJECT IDENTIFIER ::= { hwPhysicalBoardModuleType 143374 }
            hwPhysicalBoardModuleADII        OBJECT IDENTIFIER ::= { hwPhysicalBoardModuleType 143375 }
            hwPhysicalBoardModuleADIJ        OBJECT IDENTIFIER ::= { hwPhysicalBoardModuleType 143376 }
            hwPhysicalBoardModuleADIK        OBJECT IDENTIFIER ::= { hwPhysicalBoardModuleType 143377 }
            hwPhysicalBoardModuleADIM        OBJECT IDENTIFIER ::= { hwPhysicalBoardModuleType 143378 }
            hwPhysicalBoardModuleADIN        OBJECT IDENTIFIER ::= { hwPhysicalBoardModuleType 143379 }
            hwPhysicalBoardModuleADIL        OBJECT IDENTIFIER ::= { hwPhysicalBoardModuleType 143380 }
            hwPhysicalBoardModuleADIO        OBJECT IDENTIFIER ::= { hwPhysicalBoardModuleType 143381 }
            hwPhysicalBoardModuleADIP        OBJECT IDENTIFIER ::= { hwPhysicalBoardModuleType 143382 }
            hwPhysicalBoardModuleADIQ        OBJECT IDENTIFIER ::= { hwPhysicalBoardModuleType 143383 }
            hwPhysicalBoardModuleADIR        OBJECT IDENTIFIER ::= { hwPhysicalBoardModuleType 143384 }
            hwPhysicalBoardModuleADIS        OBJECT IDENTIFIER ::= { hwPhysicalBoardModuleType 143385 }
            hwPhysicalBoardModuleADIT        OBJECT IDENTIFIER ::= { hwPhysicalBoardModuleType 143386 }
            hwPhysicalBoardModuleADIU        OBJECT IDENTIFIER ::= { hwPhysicalBoardModuleType 143387 }
            hwPhysicalBoardModuleADIV        OBJECT IDENTIFIER ::= { hwPhysicalBoardModuleType 143388 }
            hwPhysicalBoardModuleADIW        OBJECT IDENTIFIER ::= { hwPhysicalBoardModuleType 143389 }
            hwPhysicalBoardModuleADIX        OBJECT IDENTIFIER ::= { hwPhysicalBoardModuleType 143390 }
            hwPhysicalBoardModuleADIY        OBJECT IDENTIFIER ::= { hwPhysicalBoardModuleType 143391 }
            hwPhysicalBoardModuleADIZ        OBJECT IDENTIFIER ::= { hwPhysicalBoardModuleType 143392 }
            hwPhysicalBoardModuleADL         OBJECT IDENTIFIER ::= { hwPhysicalBoardModuleType 143393 }
            hwPhysicalBoardModuleADLA        OBJECT IDENTIFIER ::= { hwPhysicalBoardModuleType 143394 }
            hwPhysicalBoardModuleADLB        OBJECT IDENTIFIER ::= { hwPhysicalBoardModuleType 143395 }
            hwPhysicalBoardModuleADLC        OBJECT IDENTIFIER ::= { hwPhysicalBoardModuleType 143396 }
            hwPhysicalBoardModuleADLD        OBJECT IDENTIFIER ::= { hwPhysicalBoardModuleType 143397 }
            hwPhysicalBoardModuleADLE        OBJECT IDENTIFIER ::= { hwPhysicalBoardModuleType 143398 }
            hwPhysicalBoardModuleADLF        OBJECT IDENTIFIER ::= { hwPhysicalBoardModuleType 143399 }
            hwPhysicalBoardModuleADLG        OBJECT IDENTIFIER ::= { hwPhysicalBoardModuleType 143400 }
            hwPhysicalBoardModuleADLH        OBJECT IDENTIFIER ::= { hwPhysicalBoardModuleType 143401 }
            hwPhysicalBoardModuleADLI        OBJECT IDENTIFIER ::= { hwPhysicalBoardModuleType 143402 }
            hwPhysicalBoardModuleADLJ        OBJECT IDENTIFIER ::= { hwPhysicalBoardModuleType 143403 }
            hwPhysicalBoardModuleADLK        OBJECT IDENTIFIER ::= { hwPhysicalBoardModuleType 143404 }
            hwPhysicalBoardModuleADLM        OBJECT IDENTIFIER ::= { hwPhysicalBoardModuleType 143405 }
            hwPhysicalBoardModuleADLN        OBJECT IDENTIFIER ::= { hwPhysicalBoardModuleType 143406 }
            hwPhysicalBoardModuleADLO        OBJECT IDENTIFIER ::= { hwPhysicalBoardModuleType 143407 }
            hwPhysicalBoardModuleADLP        OBJECT IDENTIFIER ::= { hwPhysicalBoardModuleType 143408 }
            hwPhysicalBoardModuleADLQ        OBJECT IDENTIFIER ::= { hwPhysicalBoardModuleType 143409 }
            hwPhysicalBoardModuleADLR        OBJECT IDENTIFIER ::= { hwPhysicalBoardModuleType 143410 }
            hwPhysicalBoardModuleADLS        OBJECT IDENTIFIER ::= { hwPhysicalBoardModuleType 143411 }
            hwPhysicalBoardModuleADLT        OBJECT IDENTIFIER ::= { hwPhysicalBoardModuleType 143412 }
            hwPhysicalBoardModuleADLU        OBJECT IDENTIFIER ::= { hwPhysicalBoardModuleType 143413 }
            hwPhysicalBoardModuleADLV        OBJECT IDENTIFIER ::= { hwPhysicalBoardModuleType 143414 }
            hwPhysicalBoardModuleADLW        OBJECT IDENTIFIER ::= { hwPhysicalBoardModuleType 143415 }
            hwPhysicalBoardModuleADLX        OBJECT IDENTIFIER ::= { hwPhysicalBoardModuleType 143416 }
            hwPhysicalBoardModuleADLY        OBJECT IDENTIFIER ::= { hwPhysicalBoardModuleType 143417 }
            hwPhysicalBoardModuleADLZ        OBJECT IDENTIFIER ::= { hwPhysicalBoardModuleType 143418 }
            hwPhysicalBoardModuleSHD         OBJECT IDENTIFIER ::= { hwPhysicalBoardModuleType 143419 }
            hwPhysicalBoardModuleSHDA        OBJECT IDENTIFIER ::= { hwPhysicalBoardModuleType 143420 }
            hwPhysicalBoardModuleSHDB        OBJECT IDENTIFIER ::= { hwPhysicalBoardModuleType 143421 }
            hwPhysicalBoardModuleSHDC        OBJECT IDENTIFIER ::= { hwPhysicalBoardModuleType 143422 }
            hwPhysicalBoardModuleSHDD        OBJECT IDENTIFIER ::= { hwPhysicalBoardModuleType 143423 }
            hwPhysicalBoardModuleSHDE        OBJECT IDENTIFIER ::= { hwPhysicalBoardModuleType 143424 }
            hwPhysicalBoardModuleSHDF        OBJECT IDENTIFIER ::= { hwPhysicalBoardModuleType 143425 }
            hwPhysicalBoardModuleSHDG        OBJECT IDENTIFIER ::= { hwPhysicalBoardModuleType 143426 }
            hwPhysicalBoardModuleSHDH        OBJECT IDENTIFIER ::= { hwPhysicalBoardModuleType 143427 }
            hwPhysicalBoardModuleSHDI        OBJECT IDENTIFIER ::= { hwPhysicalBoardModuleType 143428 }
            hwPhysicalBoardModuleSHDJ        OBJECT IDENTIFIER ::= { hwPhysicalBoardModuleType 143429 }
            hwPhysicalBoardModuleSHDK        OBJECT IDENTIFIER ::= { hwPhysicalBoardModuleType 143430 }
            hwPhysicalBoardModuleSHDL        OBJECT IDENTIFIER ::= { hwPhysicalBoardModuleType 143431 }
            hwPhysicalBoardModuleSHDM        OBJECT IDENTIFIER ::= { hwPhysicalBoardModuleType 143432 }
            hwPhysicalBoardModuleSHDN        OBJECT IDENTIFIER ::= { hwPhysicalBoardModuleType 143433 }
            hwPhysicalBoardModuleSHDO        OBJECT IDENTIFIER ::= { hwPhysicalBoardModuleType 143434 }
            hwPhysicalBoardModuleSHDP        OBJECT IDENTIFIER ::= { hwPhysicalBoardModuleType 143435 }
            hwPhysicalBoardModuleSHDQ        OBJECT IDENTIFIER ::= { hwPhysicalBoardModuleType 143436 }
            hwPhysicalBoardModuleSHDR        OBJECT IDENTIFIER ::= { hwPhysicalBoardModuleType 143437 }
            hwPhysicalBoardModuleSHDS        OBJECT IDENTIFIER ::= { hwPhysicalBoardModuleType 143438 }
            hwPhysicalBoardModuleSHDT        OBJECT IDENTIFIER ::= { hwPhysicalBoardModuleType 143439 }
            hwPhysicalBoardModuleSHDU        OBJECT IDENTIFIER ::= { hwPhysicalBoardModuleType 143440 }
            hwPhysicalBoardModuleSHDV        OBJECT IDENTIFIER ::= { hwPhysicalBoardModuleType 143441 }
            hwPhysicalBoardModuleSHDW        OBJECT IDENTIFIER ::= { hwPhysicalBoardModuleType 143442 }
            hwPhysicalBoardModuleSHDX        OBJECT IDENTIFIER ::= { hwPhysicalBoardModuleType 143443 }
            hwPhysicalBoardModuleSHDY        OBJECT IDENTIFIER ::= { hwPhysicalBoardModuleType 143444 }
            hwPhysicalBoardModuleSHDZ        OBJECT IDENTIFIER ::= { hwPhysicalBoardModuleType 143445 }
            hwPhysicalBoardModuleH80ASHLM    OBJECT IDENTIFIER ::= { hwPhysicalBoardModuleType 143446 }
            hwPhysicalBoardModuleSHG         OBJECT IDENTIFIER ::= { hwPhysicalBoardModuleType 143447 }
            hwPhysicalBoardModuleADK         OBJECT IDENTIFIER ::= { hwPhysicalBoardModuleType 143500 }
            hwPhysicalBoardModuleH521mcca    OBJECT IDENTIFIER ::= { hwPhysicalBoardModuleType 143600 }
            hwPhysicalBoardModuleH801SPLG1   OBJECT IDENTIFIER ::= { hwPhysicalBoardModuleType 143700 }
            hwPhysicalBoardModuleH801SPLG2   OBJECT IDENTIFIER ::= { hwPhysicalBoardModuleType 143701 }
            hwPhysicalBoardModuleH801BSPA    OBJECT IDENTIFIER ::= { hwPhysicalBoardModuleType 143702 }
            hwPhysicalBoardModuleVDL         OBJECT IDENTIFIER ::= { hwPhysicalBoardModuleType 143703 }
            hwPhysicalBoardModuleVDLA        OBJECT IDENTIFIER ::= { hwPhysicalBoardModuleType 143704 }
            hwPhysicalBoardModuleVDLB        OBJECT IDENTIFIER ::= { hwPhysicalBoardModuleType 143705 }
            hwPhysicalBoardModuleVDLC        OBJECT IDENTIFIER ::= { hwPhysicalBoardModuleType 143706 }
            hwPhysicalBoardModuleVDLD        OBJECT IDENTIFIER ::= { hwPhysicalBoardModuleType 143707 }
            hwPhysicalBoardModuleVDLE        OBJECT IDENTIFIER ::= { hwPhysicalBoardModuleType 143708 }
            hwPhysicalBoardModuleVDLF        OBJECT IDENTIFIER ::= { hwPhysicalBoardModuleType 143709 }
            hwPhysicalBoardModuleVDLG        OBJECT IDENTIFIER ::= { hwPhysicalBoardModuleType 143710 }
            hwPhysicalBoardModuleVDLH        OBJECT IDENTIFIER ::= { hwPhysicalBoardModuleType 143711 }
            hwPhysicalBoardModuleVDLI        OBJECT IDENTIFIER ::= { hwPhysicalBoardModuleType 143712 }
            hwPhysicalBoardModuleVDLJ        OBJECT IDENTIFIER ::= { hwPhysicalBoardModuleType 143713 }
            hwPhysicalBoardModuleVDLK        OBJECT IDENTIFIER ::= { hwPhysicalBoardModuleType 143714 }
            hwPhysicalBoardModuleVDLL        OBJECT IDENTIFIER ::= { hwPhysicalBoardModuleType 143715 }
            hwPhysicalBoardModuleVDLM        OBJECT IDENTIFIER ::= { hwPhysicalBoardModuleType 143716 }
            hwPhysicalBoardModuleVDLN        OBJECT IDENTIFIER ::= { hwPhysicalBoardModuleType 143717 }
            hwPhysicalBoardModuleVDLO        OBJECT IDENTIFIER ::= { hwPhysicalBoardModuleType 143718 }
            hwPhysicalBoardModuleVDLP        OBJECT IDENTIFIER ::= { hwPhysicalBoardModuleType 143719 }
            hwPhysicalBoardModuleVDLQ        OBJECT IDENTIFIER ::= { hwPhysicalBoardModuleType 143720 }
            hwPhysicalBoardModuleVDLR        OBJECT IDENTIFIER ::= { hwPhysicalBoardModuleType 143721 }
            hwPhysicalBoardModuleVDLS        OBJECT IDENTIFIER ::= { hwPhysicalBoardModuleType 143722 }
            hwPhysicalBoardModuleVDLT        OBJECT IDENTIFIER ::= { hwPhysicalBoardModuleType 143723 }
            hwPhysicalBoardModuleVDLU        OBJECT IDENTIFIER ::= { hwPhysicalBoardModuleType 143724 }
            hwPhysicalBoardModuleVDLV        OBJECT IDENTIFIER ::= { hwPhysicalBoardModuleType 143725 }
            hwPhysicalBoardModuleVDLW        OBJECT IDENTIFIER ::= { hwPhysicalBoardModuleType 143726 }
            hwPhysicalBoardModuleVDLX        OBJECT IDENTIFIER ::= { hwPhysicalBoardModuleType 143727 }
            hwPhysicalBoardModuleVDLY        OBJECT IDENTIFIER ::= { hwPhysicalBoardModuleType 143728 }
            hwPhysicalBoardModuleVDLZ        OBJECT IDENTIFIER ::= { hwPhysicalBoardModuleType 143729 }
            hwPhysicalBoardModuleH803CVD     OBJECT IDENTIFIER ::= { hwPhysicalBoardModuleType 143730 }
            hwPhysicalBoardModuleH803CVDA    OBJECT IDENTIFIER ::= { hwPhysicalBoardModuleType 143731 }
            hwPhysicalBoardModuleH803CVDB    OBJECT IDENTIFIER ::= { hwPhysicalBoardModuleType 143732 }
            hwPhysicalBoardModuleH803CVDC    OBJECT IDENTIFIER ::= { hwPhysicalBoardModuleType 143733 }
            hwPhysicalBoardModuleH803CVDD    OBJECT IDENTIFIER ::= { hwPhysicalBoardModuleType 143734 }
            hwPhysicalBoardModuleH803CVDE    OBJECT IDENTIFIER ::= { hwPhysicalBoardModuleType 143735 }
            hwPhysicalBoardModuleH803CVDF    OBJECT IDENTIFIER ::= { hwPhysicalBoardModuleType 143736 }
            hwPhysicalBoardModuleH803CVDG    OBJECT IDENTIFIER ::= { hwPhysicalBoardModuleType 143737 }
            hwPhysicalBoardModuleH803CVDH    OBJECT IDENTIFIER ::= { hwPhysicalBoardModuleType 143738 }
            hwPhysicalBoardModuleH803CVDI    OBJECT IDENTIFIER ::= { hwPhysicalBoardModuleType 143739 }
            hwPhysicalBoardModuleH803CVDJ    OBJECT IDENTIFIER ::= { hwPhysicalBoardModuleType 143740 }
            hwPhysicalBoardModuleH803CVDK    OBJECT IDENTIFIER ::= { hwPhysicalBoardModuleType 143741 }
            hwPhysicalBoardModuleH803CVDL    OBJECT IDENTIFIER ::= { hwPhysicalBoardModuleType 143742 }
            hwPhysicalBoardModuleH803CVDM    OBJECT IDENTIFIER ::= { hwPhysicalBoardModuleType 143743 }
            hwPhysicalBoardModuleH803CVDN    OBJECT IDENTIFIER ::= { hwPhysicalBoardModuleType 143744 }
            hwPhysicalBoardModuleH803CVDO    OBJECT IDENTIFIER ::= { hwPhysicalBoardModuleType 143745 }
            hwPhysicalBoardModuleH803CVDP    OBJECT IDENTIFIER ::= { hwPhysicalBoardModuleType 143746 }
            hwPhysicalBoardModuleH803CVDQ    OBJECT IDENTIFIER ::= { hwPhysicalBoardModuleType 143747 }
            hwPhysicalBoardModuleH803CVDR    OBJECT IDENTIFIER ::= { hwPhysicalBoardModuleType 143748 }
            hwPhysicalBoardModuleH803CVDS    OBJECT IDENTIFIER ::= { hwPhysicalBoardModuleType 143749 }
            hwPhysicalBoardModuleH803CVDT    OBJECT IDENTIFIER ::= { hwPhysicalBoardModuleType 143750 }
            hwPhysicalBoardModuleH803CVDU    OBJECT IDENTIFIER ::= { hwPhysicalBoardModuleType 143751 }
            hwPhysicalBoardModuleH803CVDV    OBJECT IDENTIFIER ::= { hwPhysicalBoardModuleType 143752 }
            hwPhysicalBoardModuleH803CVDW    OBJECT IDENTIFIER ::= { hwPhysicalBoardModuleType 143753 }
            hwPhysicalBoardModuleH803CVDX    OBJECT IDENTIFIER ::= { hwPhysicalBoardModuleType 143754 }
            hwPhysicalBoardModuleH803CVDY    OBJECT IDENTIFIER ::= { hwPhysicalBoardModuleType 143755 }
            hwPhysicalBoardModuleH803CVDZ    OBJECT IDENTIFIER ::= { hwPhysicalBoardModuleType 143756 }
            hwPhysicalBoardModuleH805CAN     OBJECT IDENTIFIER ::= { hwPhysicalBoardModuleType 143757 }
            hwPhysicalBoardModuleH805CANA    OBJECT IDENTIFIER ::= { hwPhysicalBoardModuleType 143758 }
            hwPhysicalBoardModuleH805CANB    OBJECT IDENTIFIER ::= { hwPhysicalBoardModuleType 143759 }
            hwPhysicalBoardModuleH805CANC    OBJECT IDENTIFIER ::= { hwPhysicalBoardModuleType 143760 }
            hwPhysicalBoardModuleH805CAND    OBJECT IDENTIFIER ::= { hwPhysicalBoardModuleType 143761 }
            hwPhysicalBoardModuleH805CANE    OBJECT IDENTIFIER ::= { hwPhysicalBoardModuleType 143762 }
            hwPhysicalBoardModuleH805CANF    OBJECT IDENTIFIER ::= { hwPhysicalBoardModuleType 143763 }
            hwPhysicalBoardModuleH805CANG    OBJECT IDENTIFIER ::= { hwPhysicalBoardModuleType 143764 }
            hwPhysicalBoardModuleH805CANH    OBJECT IDENTIFIER ::= { hwPhysicalBoardModuleType 143765 }
            hwPhysicalBoardModuleH805CANI    OBJECT IDENTIFIER ::= { hwPhysicalBoardModuleType 143766 }
            hwPhysicalBoardModuleH805CANJ    OBJECT IDENTIFIER ::= { hwPhysicalBoardModuleType 143767 }
            hwPhysicalBoardModuleH805CANK    OBJECT IDENTIFIER ::= { hwPhysicalBoardModuleType 143768 }
            hwPhysicalBoardModuleH805CANL    OBJECT IDENTIFIER ::= { hwPhysicalBoardModuleType 143769 }
            hwPhysicalBoardModuleH805CANM    OBJECT IDENTIFIER ::= { hwPhysicalBoardModuleType 143770 }
            hwPhysicalBoardModuleH805CANN    OBJECT IDENTIFIER ::= { hwPhysicalBoardModuleType 143771 }
            hwPhysicalBoardModuleH805CANO    OBJECT IDENTIFIER ::= { hwPhysicalBoardModuleType 143772 }
            hwPhysicalBoardModuleH805CANP    OBJECT IDENTIFIER ::= { hwPhysicalBoardModuleType 143773 }
            hwPhysicalBoardModuleH805CANQ    OBJECT IDENTIFIER ::= { hwPhysicalBoardModuleType 143774 }
            hwPhysicalBoardModuleH805CANR    OBJECT IDENTIFIER ::= { hwPhysicalBoardModuleType 143775 }
            hwPhysicalBoardModuleH805CANS    OBJECT IDENTIFIER ::= { hwPhysicalBoardModuleType 143776 }
            hwPhysicalBoardModuleH805CANT    OBJECT IDENTIFIER ::= { hwPhysicalBoardModuleType 143777 }
            hwPhysicalBoardModuleH805CANU    OBJECT IDENTIFIER ::= { hwPhysicalBoardModuleType 143778 }
            hwPhysicalBoardModuleH805CANV    OBJECT IDENTIFIER ::= { hwPhysicalBoardModuleType 143779 }
            hwPhysicalBoardModuleH805CANW    OBJECT IDENTIFIER ::= { hwPhysicalBoardModuleType 143780 }
            hwPhysicalBoardModuleH805CANX    OBJECT IDENTIFIER ::= { hwPhysicalBoardModuleType 143781 }
            hwPhysicalBoardModuleH805CANY    OBJECT IDENTIFIER ::= { hwPhysicalBoardModuleType 143782 }
            hwPhysicalBoardModuleH805CANZ    OBJECT IDENTIFIER ::= { hwPhysicalBoardModuleType 143783 }
            hwPhysicalBoardModuleH805CAL     OBJECT IDENTIFIER ::= { hwPhysicalBoardModuleType 143784 }
            hwPhysicalBoardModuleH805CALA    OBJECT IDENTIFIER ::= { hwPhysicalBoardModuleType 143785 }
            hwPhysicalBoardModuleH805CALB    OBJECT IDENTIFIER ::= { hwPhysicalBoardModuleType 143786 }
            hwPhysicalBoardModuleH805CALC    OBJECT IDENTIFIER ::= { hwPhysicalBoardModuleType 143787 }
            hwPhysicalBoardModuleH805CALD    OBJECT IDENTIFIER ::= { hwPhysicalBoardModuleType 143788 }
            hwPhysicalBoardModuleH805CALE    OBJECT IDENTIFIER ::= { hwPhysicalBoardModuleType 143789 }
            hwPhysicalBoardModuleH805CALF    OBJECT IDENTIFIER ::= { hwPhysicalBoardModuleType 143790 }
            hwPhysicalBoardModuleH805CALG    OBJECT IDENTIFIER ::= { hwPhysicalBoardModuleType 143791 }
            hwPhysicalBoardModuleH805CALH    OBJECT IDENTIFIER ::= { hwPhysicalBoardModuleType 143792 }
            hwPhysicalBoardModuleH805CALI    OBJECT IDENTIFIER ::= { hwPhysicalBoardModuleType 143793 }
            hwPhysicalBoardModuleH805CALJ    OBJECT IDENTIFIER ::= { hwPhysicalBoardModuleType 143794 }
            hwPhysicalBoardModuleH805CALK    OBJECT IDENTIFIER ::= { hwPhysicalBoardModuleType 143795 }
            hwPhysicalBoardModuleH805CALL    OBJECT IDENTIFIER ::= { hwPhysicalBoardModuleType 143796 }
            hwPhysicalBoardModuleH805CALM    OBJECT IDENTIFIER ::= { hwPhysicalBoardModuleType 143797 }
            hwPhysicalBoardModuleH805CALN    OBJECT IDENTIFIER ::= { hwPhysicalBoardModuleType 143798 }
            hwPhysicalBoardModuleH805CALO    OBJECT IDENTIFIER ::= { hwPhysicalBoardModuleType 143799 }
            hwPhysicalBoardModuleH805CALP    OBJECT IDENTIFIER ::= { hwPhysicalBoardModuleType 143800 }
            hwPhysicalBoardModuleH805CALQ    OBJECT IDENTIFIER ::= { hwPhysicalBoardModuleType 143801 }
            hwPhysicalBoardModuleH805CALR    OBJECT IDENTIFIER ::= { hwPhysicalBoardModuleType 143802 }
            hwPhysicalBoardModuleH805CALS    OBJECT IDENTIFIER ::= { hwPhysicalBoardModuleType 143803 }
            hwPhysicalBoardModuleH805CALT    OBJECT IDENTIFIER ::= { hwPhysicalBoardModuleType 143804 }
            hwPhysicalBoardModuleH805CALU    OBJECT IDENTIFIER ::= { hwPhysicalBoardModuleType 143805 }
            hwPhysicalBoardModuleH805CALV    OBJECT IDENTIFIER ::= { hwPhysicalBoardModuleType 143806 }
            hwPhysicalBoardModuleH805CALW    OBJECT IDENTIFIER ::= { hwPhysicalBoardModuleType 143807 }
            hwPhysicalBoardModuleH805CALX    OBJECT IDENTIFIER ::= { hwPhysicalBoardModuleType 143808 }
            hwPhysicalBoardModuleH805CALY    OBJECT IDENTIFIER ::= { hwPhysicalBoardModuleType 143809 }
            hwPhysicalBoardModuleH805CALZ    OBJECT IDENTIFIER ::= { hwPhysicalBoardModuleType 143810 }
            hwPhysicalBoardModuleH801GICA    OBJECT IDENTIFIER ::= { hwPhysicalBoardModuleType 143811 }
            hwPhysicalBoardModuleH801GICB    OBJECT IDENTIFIER ::= { hwPhysicalBoardModuleType 143812 }
            hwPhysicalBoardModuleH801FICA    OBJECT IDENTIFIER ::= { hwPhysicalBoardModuleType 143813 }
            hwPhysicalBoardModuleH801PRTA    OBJECT IDENTIFIER ::= { hwPhysicalBoardModuleType 143814 }
            hwPhysicalBoardModuleH801CITA    OBJECT IDENTIFIER ::= { hwPhysicalBoardModuleType 143815 }
            hwPhysicalBoardModuleH801PRTS    OBJECT IDENTIFIER ::= { hwPhysicalBoardModuleType 143816 }
            hwPhysicalBoardModuleH801CITS    OBJECT IDENTIFIER ::= { hwPhysicalBoardModuleType 143817 }
            hwPhysicalBoardModuleH80xVDS     OBJECT IDENTIFIER ::= { hwPhysicalBoardModuleType 143818 }
            hwPhysicalBoardModuleH80xVDSA    OBJECT IDENTIFIER ::= { hwPhysicalBoardModuleType 143819 }
            hwPhysicalBoardModuleH80xVDSB    OBJECT IDENTIFIER ::= { hwPhysicalBoardModuleType 143820 }
            hwPhysicalBoardModuleH80xVDSC    OBJECT IDENTIFIER ::= { hwPhysicalBoardModuleType 143821 }
            hwPhysicalBoardModuleH80xVDSD    OBJECT IDENTIFIER ::= { hwPhysicalBoardModuleType 143822 }
            hwPhysicalBoardModuleH80xVDSE    OBJECT IDENTIFIER ::= { hwPhysicalBoardModuleType 143823 }
            hwPhysicalBoardModuleH80xVDSF    OBJECT IDENTIFIER ::= { hwPhysicalBoardModuleType 143824 }
            hwPhysicalBoardModuleH80xVDSG    OBJECT IDENTIFIER ::= { hwPhysicalBoardModuleType 143825 }
            hwPhysicalBoardModuleH80xVDSH    OBJECT IDENTIFIER ::= { hwPhysicalBoardModuleType 143826 }
            hwPhysicalBoardModuleH80xVDSI    OBJECT IDENTIFIER ::= { hwPhysicalBoardModuleType 143827 }
            hwPhysicalBoardModuleH80xVDSJ    OBJECT IDENTIFIER ::= { hwPhysicalBoardModuleType 143828 }
            hwPhysicalBoardModuleH80xVDSK    OBJECT IDENTIFIER ::= { hwPhysicalBoardModuleType 143829 }
            hwPhysicalBoardModuleH80xVDSL    OBJECT IDENTIFIER ::= { hwPhysicalBoardModuleType 143830 }
            hwPhysicalBoardModuleH80xVDSM    OBJECT IDENTIFIER ::= { hwPhysicalBoardModuleType 143831 }
            hwPhysicalBoardModuleH80xVDSN    OBJECT IDENTIFIER ::= { hwPhysicalBoardModuleType 143832 }
            hwPhysicalBoardModuleH80xVDSO    OBJECT IDENTIFIER ::= { hwPhysicalBoardModuleType 143833 }
            hwPhysicalBoardModuleH80xVDSP    OBJECT IDENTIFIER ::= { hwPhysicalBoardModuleType 143834 }
            hwPhysicalBoardModuleH80xVDSQ    OBJECT IDENTIFIER ::= { hwPhysicalBoardModuleType 143835 }
            hwPhysicalBoardModuleH80xVDSR    OBJECT IDENTIFIER ::= { hwPhysicalBoardModuleType 143836 }
            hwPhysicalBoardModuleH80xVDSS    OBJECT IDENTIFIER ::= { hwPhysicalBoardModuleType 143837 }
            hwPhysicalBoardModuleH80xVDST    OBJECT IDENTIFIER ::= { hwPhysicalBoardModuleType 143838 }
            hwPhysicalBoardModuleH80xVDSU    OBJECT IDENTIFIER ::= { hwPhysicalBoardModuleType 143839 }
            hwPhysicalBoardModuleH80xVDSV    OBJECT IDENTIFIER ::= { hwPhysicalBoardModuleType 143840 }
            hwPhysicalBoardModuleH80xVDSW    OBJECT IDENTIFIER ::= { hwPhysicalBoardModuleType 143841 }
            hwPhysicalBoardModuleH80xVDSX    OBJECT IDENTIFIER ::= { hwPhysicalBoardModuleType 143842 }
            hwPhysicalBoardModuleH80xVDSY    OBJECT IDENTIFIER ::= { hwPhysicalBoardModuleType 143843 }
            hwPhysicalBoardModuleH80xVDSZ    OBJECT IDENTIFIER ::= { hwPhysicalBoardModuleType 143844 }
            hwPhysicalBoardModuleH80xVDT     OBJECT IDENTIFIER ::= { hwPhysicalBoardModuleType 143845 }
            hwPhysicalBoardModuleH80xVDTA    OBJECT IDENTIFIER ::= { hwPhysicalBoardModuleType 143846 }
            hwPhysicalBoardModuleH80xVDTB    OBJECT IDENTIFIER ::= { hwPhysicalBoardModuleType 143847 }
            hwPhysicalBoardModuleH80xVDTC    OBJECT IDENTIFIER ::= { hwPhysicalBoardModuleType 143848 }
            hwPhysicalBoardModuleH80xVDTD    OBJECT IDENTIFIER ::= { hwPhysicalBoardModuleType 143849 }
            hwPhysicalBoardModuleH80xVDTE    OBJECT IDENTIFIER ::= { hwPhysicalBoardModuleType 143850 }
            hwPhysicalBoardModuleH80xVDTF    OBJECT IDENTIFIER ::= { hwPhysicalBoardModuleType 143851 }
            hwPhysicalBoardModuleH80xVDTG    OBJECT IDENTIFIER ::= { hwPhysicalBoardModuleType 143852 }
            hwPhysicalBoardModuleH80xVDTH    OBJECT IDENTIFIER ::= { hwPhysicalBoardModuleType 143853 }
            hwPhysicalBoardModuleH80xVDTI    OBJECT IDENTIFIER ::= { hwPhysicalBoardModuleType 143854 }
            hwPhysicalBoardModuleH80xVDTJ    OBJECT IDENTIFIER ::= { hwPhysicalBoardModuleType 143855 }
            hwPhysicalBoardModuleH80xVDTK    OBJECT IDENTIFIER ::= { hwPhysicalBoardModuleType 143856 }
            hwPhysicalBoardModuleH80xVDTL    OBJECT IDENTIFIER ::= { hwPhysicalBoardModuleType 143857 }
            hwPhysicalBoardModuleH80xVDTM    OBJECT IDENTIFIER ::= { hwPhysicalBoardModuleType 143858 }
            hwPhysicalBoardModuleH80xVDTN    OBJECT IDENTIFIER ::= { hwPhysicalBoardModuleType 143859 }
            hwPhysicalBoardModuleH80xVDTO    OBJECT IDENTIFIER ::= { hwPhysicalBoardModuleType 143860 }
            hwPhysicalBoardModuleH80xVDTP    OBJECT IDENTIFIER ::= { hwPhysicalBoardModuleType 143861 }
            hwPhysicalBoardModuleH80xVDTQ    OBJECT IDENTIFIER ::= { hwPhysicalBoardModuleType 143862 }
            hwPhysicalBoardModuleH80xVDTR    OBJECT IDENTIFIER ::= { hwPhysicalBoardModuleType 143863 }
            hwPhysicalBoardModuleH80xVDTS    OBJECT IDENTIFIER ::= { hwPhysicalBoardModuleType 143864 }
            hwPhysicalBoardModuleH80xVDTT    OBJECT IDENTIFIER ::= { hwPhysicalBoardModuleType 143865 }
            hwPhysicalBoardModuleH80xVDTU    OBJECT IDENTIFIER ::= { hwPhysicalBoardModuleType 143866 }
            hwPhysicalBoardModuleH80xVDTV    OBJECT IDENTIFIER ::= { hwPhysicalBoardModuleType 143867 }
            hwPhysicalBoardModuleH80xVDTW    OBJECT IDENTIFIER ::= { hwPhysicalBoardModuleType 143868 }
            hwPhysicalBoardModuleH80xVDTX    OBJECT IDENTIFIER ::= { hwPhysicalBoardModuleType 143869 }
            hwPhysicalBoardModuleH80xVDTY    OBJECT IDENTIFIER ::= { hwPhysicalBoardModuleType 143870 }
            hwPhysicalBoardModuleH80xVDTZ    OBJECT IDENTIFIER ::= { hwPhysicalBoardModuleType 143871 }
            hwPhysicalBoardModuleH801OPFA    OBJECT IDENTIFIER ::= { hwPhysicalBoardModuleType 143872 }
            hwPhysicalBoardModuleH801GICD    OBJECT IDENTIFIER ::= { hwPhysicalBoardModuleType 143873 }
            hwPhysicalBoardModuleH801GICE    OBJECT IDENTIFIER ::= { hwPhysicalBoardModuleType 143874 }
            hwPhysicalBoardModuleH801FICB    OBJECT IDENTIFIER ::= { hwPhysicalBoardModuleType 143875 }
            hwPhysicalBoardModuleH801HWTF    OBJECT IDENTIFIER ::= { hwPhysicalBoardModuleType 143876 }
            hwPhysicalBoardModuleH801MCUA    OBJECT IDENTIFIER ::= { hwPhysicalBoardModuleType 143877 }
            hwPhysicalBoardModuleH801MPWA    OBJECT IDENTIFIER ::= { hwPhysicalBoardModuleType 143878 }
            hwPhysicalBoardModuleH801ETHA    OBJECT IDENTIFIER ::= { hwPhysicalBoardModuleType 143879 }
            hwPhysicalBoardModuleH801MFGA    OBJECT IDENTIFIER ::= { hwPhysicalBoardModuleType 143880 }
            hwPhysicalBoardModuleH801SPLE    OBJECT IDENTIFIER ::= { hwPhysicalBoardModuleType 143881 }
            hwPhysicalBoardModuleH801SPLE1   OBJECT IDENTIFIER ::= { hwPhysicalBoardModuleType 143882 }
            hwPhysicalBoardModuleH801SPLE2   OBJECT IDENTIFIER ::= { hwPhysicalBoardModuleType 143883 }
            hwPhysicalBoardModuleH801SPLE3   OBJECT IDENTIFIER ::= { hwPhysicalBoardModuleType 143884 }
            hwPhysicalBoardModuleH801SPLE4   OBJECT IDENTIFIER ::= { hwPhysicalBoardModuleType 143885 }
            hwPhysicalBoardModuleH801MCUB    OBJECT IDENTIFIER ::= { hwPhysicalBoardModuleType 143886 }
            hwPhysicalBoardModuleH801BIUA    OBJECT IDENTIFIER ::= { hwPhysicalBoardModuleType 143887 }
            hwPhysicalBoardModuleH802DSRE    OBJECT IDENTIFIER ::= { hwPhysicalBoardModuleType 143888 }
            hwPhysicalBoardModuleH802DSRD    OBJECT IDENTIFIER ::= { hwPhysicalBoardModuleType 143889 }
            hwPhysicalBoardModuleH80XVDR     OBJECT IDENTIFIER ::= { hwPhysicalBoardModuleType 143890 }
            hwPhysicalBoardModuleH801ETHB    OBJECT IDENTIFIER ::= { hwPhysicalBoardModuleType 143891 }
            hwPhysicalBoardModuleH80XVDJ     OBJECT IDENTIFIER ::= { hwPhysicalBoardModuleType 143892 }
            hwPhysicalBoardModuleH561EPBA    OBJECT IDENTIFIER ::= { hwPhysicalBoardModuleType 145920 }
            hwPhysicalBoardModuleH565VDE     OBJECT IDENTIFIER ::= { hwPhysicalBoardModuleType 145921 }
            hwPhysicalBoardModuleH565VDEA    OBJECT IDENTIFIER ::= { hwPhysicalBoardModuleType 145922 }
            hwPhysicalBoardModuleH565VDEC    OBJECT IDENTIFIER ::= { hwPhysicalBoardModuleType 145924 }
            hwPhysicalBoardModuleH565VDED    OBJECT IDENTIFIER ::= { hwPhysicalBoardModuleType 145925 }
            hwPhysicalBoardModuleH565VDEE    OBJECT IDENTIFIER ::= { hwPhysicalBoardModuleType 145926 }
            hwPhysicalBoardModuleH565VDEF    OBJECT IDENTIFIER ::= { hwPhysicalBoardModuleType 145927 }
            hwPhysicalBoardModuleH565VDEG    OBJECT IDENTIFIER ::= { hwPhysicalBoardModuleType 145928 }
            hwPhysicalBoardModuleH565VDEH    OBJECT IDENTIFIER ::= { hwPhysicalBoardModuleType 145929 }
            hwPhysicalBoardModuleH565VDEI    OBJECT IDENTIFIER ::= { hwPhysicalBoardModuleType 145930 }
            hwPhysicalBoardModuleH565VDEJ    OBJECT IDENTIFIER ::= { hwPhysicalBoardModuleType 145931 }
            hwPhysicalBoardModuleH565VDEK    OBJECT IDENTIFIER ::= { hwPhysicalBoardModuleType 145932 }
            hwPhysicalBoardModuleH565VDEL    OBJECT IDENTIFIER ::= { hwPhysicalBoardModuleType 145933 }
            hwPhysicalBoardModuleH565VDEM    OBJECT IDENTIFIER ::= { hwPhysicalBoardModuleType 145934 }
            hwPhysicalBoardModuleH565VDEN    OBJECT IDENTIFIER ::= { hwPhysicalBoardModuleType 145935 }
            hwPhysicalBoardModuleH565VDEO    OBJECT IDENTIFIER ::= { hwPhysicalBoardModuleType 145936 }
            hwPhysicalBoardModuleH565VDEP    OBJECT IDENTIFIER ::= { hwPhysicalBoardModuleType 145937 }
            hwPhysicalBoardModuleH565VDEQ    OBJECT IDENTIFIER ::= { hwPhysicalBoardModuleType 145938 }
            hwPhysicalBoardModuleH565VDER    OBJECT IDENTIFIER ::= { hwPhysicalBoardModuleType 145939 }
            hwPhysicalBoardModuleH565VDES    OBJECT IDENTIFIER ::= { hwPhysicalBoardModuleType 145940 }
            hwPhysicalBoardModuleH565VDET    OBJECT IDENTIFIER ::= { hwPhysicalBoardModuleType 145941 }
            hwPhysicalBoardModuleH565VDEU    OBJECT IDENTIFIER ::= { hwPhysicalBoardModuleType 145942 }
            hwPhysicalBoardModuleH565VDEV    OBJECT IDENTIFIER ::= { hwPhysicalBoardModuleType 145943 }
            hwPhysicalBoardModuleH565VDEW    OBJECT IDENTIFIER ::= { hwPhysicalBoardModuleType 145944 }
            hwPhysicalBoardModuleH565VDEX    OBJECT IDENTIFIER ::= { hwPhysicalBoardModuleType 145945 }
            hwPhysicalBoardModuleH565VDEY    OBJECT IDENTIFIER ::= { hwPhysicalBoardModuleType 145946 }
            hwPhysicalBoardModuleH565VDEZ    OBJECT IDENTIFIER ::= { hwPhysicalBoardModuleType 145947 }
            hwPhysicalBoardModuleH561ETHA    OBJECT IDENTIFIER ::= { hwPhysicalBoardModuleType 145948 }
            hwPhysicalBoardModuleH801CITD    OBJECT IDENTIFIER ::= { hwPhysicalBoardModuleType 145949 }
            hwPhysicalBoardModuleH801PRTB    OBJECT IDENTIFIER ::= { hwPhysicalBoardModuleType 145950 }
            hwPhysicalBoardModuleH801MCUC    OBJECT IDENTIFIER ::= { hwPhysicalBoardModuleType 146035 }
            hwPhysicalBoardModuleH801MPWB    OBJECT IDENTIFIER ::= { hwPhysicalBoardModuleType 146036 }
            hwPhysicalBoardModuleH801MPWZ    OBJECT IDENTIFIER ::= { hwPhysicalBoardModuleType 146053 }
            hwPhysicalBoardModuleH85BCVME    OBJECT IDENTIFIER ::= { hwPhysicalBoardModuleType 146070 }
            hwPhysicalBoardModuleH801VRGA    OBJECT IDENTIFIER ::= { hwPhysicalBoardModuleType 146071 }
            hwPhysicalBoardModuleH806EPBD    OBJECT IDENTIFIER ::= { hwPhysicalBoardModuleType 146072 }
            hwPhysicalBoardModuleH801SPUF    OBJECT IDENTIFIER ::= { hwPhysicalBoardModuleType 146073 }
            hwPhysicalBoardModuleH801MPWD    OBJECT IDENTIFIER ::= { hwPhysicalBoardModuleType 146074 }
            hwPhysicalBoardModuleH803X2CK    OBJECT IDENTIFIER ::= { hwPhysicalBoardModuleType 146080 }
            hwPhysicalBoardModuleH803TPBA    OBJECT IDENTIFIER ::= { hwPhysicalBoardModuleType 146083 }
            hwPhysicalBoardModuleH803TPBC    OBJECT IDENTIFIER ::= { hwPhysicalBoardModuleType 146084 }
            hwPhysicalBoardModuleH80XVDP     OBJECT IDENTIFIER ::= { hwPhysicalBoardModuleType 146066 }
            hwPhysicalBoardModuleH805GPBD    OBJECT IDENTIFIER ::= { hwPhysicalBoardModuleType 146085 }
            hwPhysicalBoardModuleH805EPBD    OBJECT IDENTIFIER ::= { hwPhysicalBoardModuleType 146086 }
            hwPhysicalBoardModuleH808EPSD    OBJECT IDENTIFIER ::= { hwPhysicalBoardModuleType 146087 }
            hwPhysicalBoardModuleH806GPBD    OBJECT IDENTIFIER ::= { hwPhysicalBoardModuleType 146092 }
            hwPhysicalBoardModuleH807GPBD    OBJECT IDENTIFIER ::= { hwPhysicalBoardModuleType 146093 }
            hwPhysicalBoardModuleH801GPFD    OBJECT IDENTIFIER ::= { hwPhysicalBoardModuleType 146095 }
            hwPhysicalBoardModuleH80XVPE     OBJECT IDENTIFIER ::= { hwPhysicalBoardModuleType 146097 }
            hwPhysicalBoardModuleH80XVCM     OBJECT IDENTIFIER ::= { hwPhysicalBoardModuleType 146098 }
            hwPhysicalBoardModuleH80BCVME    OBJECT IDENTIFIER ::= { hwPhysicalBoardModuleType 146099 }
            hwPhysicalBoardModuleH801XGBC    OBJECT IDENTIFIER ::= { hwPhysicalBoardModuleType 146100 }
            hwPhysicalBoardModuleH801SCUH    OBJECT IDENTIFIER ::= { hwPhysicalBoardModuleType 146101 }
            hwPhysicalBoardModuleH801MCUD    OBJECT IDENTIFIER ::= { hwPhysicalBoardModuleType 146102 }
            hwPhysicalBoardModuleH801MPWC    OBJECT IDENTIFIER ::= { hwPhysicalBoardModuleType 146103 }
            hwPhysicalBoardModuleH801XEBD    OBJECT IDENTIFIER ::= { hwPhysicalBoardModuleType 146104 }
            hwPhysicalBoardModuleH80XVDQ     OBJECT IDENTIFIER ::= { hwPhysicalBoardModuleType 146105 }
            hwPhysicalBoardModuleH80xVCP     OBJECT IDENTIFIER ::= { hwPhysicalBoardModuleType 146106 }
            hwPhysicalBoardModuleH802XGBC    OBJECT IDENTIFIER ::= { hwPhysicalBoardModuleType 146107 }
            hwPhysicalBoardModuleH802EPFD    OBJECT IDENTIFIER ::= { hwPhysicalBoardModuleType 146114 }
            hwPhysicalBoardModuleH803EPFD    OBJECT IDENTIFIER ::= { hwPhysicalBoardModuleType 146115 }
            hwPhysicalBoardModuleH806GPBH    OBJECT IDENTIFIER ::= { hwPhysicalBoardModuleType 146119 }
            hwPhysicalBoardModuleH807GPBH    OBJECT IDENTIFIER ::= { hwPhysicalBoardModuleType 146120 }
            hwPhysicalBoardModuleH801XESD    OBJECT IDENTIFIER ::= { hwPhysicalBoardModuleType 146137 }
            hwPhysicalBoardModuleH80XVPG     OBJECT IDENTIFIER ::= { hwPhysicalBoardModuleType 146138 }
            hwPhysicalBoardModuleH806CCPE    OBJECT IDENTIFIER ::= { hwPhysicalBoardModuleType 146139 }
            hwPhysicalBoardModuleH801XGBD    OBJECT IDENTIFIER ::= { hwPhysicalBoardModuleType 146141 }
            hwPhysicalBoardModuleH803XEBD    OBJECT IDENTIFIER ::= { hwPhysicalBoardModuleType 146142 }
            hwPhysicalBoardModuleH805EPFD    OBJECT IDENTIFIER ::= { hwPhysicalBoardModuleType 146143 }
            hwPhysicalBoardModuleH802GPMD    OBJECT IDENTIFIER ::= { hwPhysicalBoardModuleType 146144 }
            hwPhysicalBoardModuleH805GPFD    OBJECT IDENTIFIER ::= { hwPhysicalBoardModuleType 146145 }
            hwPhysicalBoardModuleH802XEBD    OBJECT IDENTIFIER ::= { hwPhysicalBoardModuleType 146146 }
            hwPhysicalBoardModuleH809EPBD    OBJECT IDENTIFIER ::= { hwPhysicalBoardModuleType 146147 }
            hwPhysicalBoardModuleH801TOPB    OBJECT IDENTIFIER ::= { hwPhysicalBoardModuleType 146148 }
            hwPhysicalBoardModuleH80DCCPE    OBJECT IDENTIFIER ::= { hwPhysicalBoardModuleType 146149 }
            hwPhysicalBoardModuleH80XATR     OBJECT IDENTIFIER ::= { hwPhysicalBoardModuleType 146150 }
            hwPhysicalBoardModuleH801CGBD    OBJECT IDENTIFIER ::= { hwPhysicalBoardModuleType 146151 }
            hwPhysicalBoardModuleH802CGBD    OBJECT IDENTIFIER ::= { hwPhysicalBoardModuleType 146152 }
            hwPhysicalBoardModuleH801CSBD    OBJECT IDENTIFIER ::= { hwPhysicalBoardModuleType 146153 }
            hwPhysicalBoardModuleH802CSBD    OBJECT IDENTIFIER ::= { hwPhysicalBoardModuleType 146154 }
            hwPhysicalBoardModuleH801XSBD    OBJECT IDENTIFIER ::= { hwPhysicalBoardModuleType 146155 }
            hwPhysicalBoardModuleH801XEUD    OBJECT IDENTIFIER ::= { hwPhysicalBoardModuleType 146156 }
	    hwPhysicalBoardModuleH806GPFD    OBJECT IDENTIFIER ::= { hwPhysicalBoardModuleType 146157 }     
            hwPhysicalBoardModuleH802SCUN    OBJECT IDENTIFIER ::= { hwPhysicalBoardModuleType 148001 }
            hwPhysicalBoardModuleH801SPUH    OBJECT IDENTIFIER ::= { hwPhysicalBoardModuleType 148002 }
            hwPhysicalBoardModuleH801SCUK    OBJECT IDENTIFIER ::= { hwPhysicalBoardModuleType 148003 }
            hwPhysicalBoardModuleH801MCUD1   OBJECT IDENTIFIER ::= { hwPhysicalBoardModuleType 148005 }
            hwPhysicalBoardModuleH801MCUE    OBJECT IDENTIFIER ::= { hwPhysicalBoardModuleType 148006 }
            hwPhysicalBoardModuleH801GPMD    OBJECT IDENTIFIER ::= { hwPhysicalBoardModuleType 148007 }
            hwPhysicalBoardModuleH801SCUV    OBJECT IDENTIFIER ::= { hwPhysicalBoardModuleType 148008 }
            hwPhysicalBoardModuleH802SCUH    OBJECT IDENTIFIER ::= { hwPhysicalBoardModuleType 148009 }
            hwPhysicalBoardModuleH802SCUV    OBJECT IDENTIFIER ::= { hwPhysicalBoardModuleType 148010 }
            hwPhysicalBoardModuleH802SCUB    OBJECT IDENTIFIER ::= { hwPhysicalBoardModuleType 148011 }
            hwPhysicalBoardModuleH80XSDM     OBJECT IDENTIFIER ::= { hwPhysicalBoardModuleType 148012 }
            hwPhysicalBoardModuleH80XSDP     OBJECT IDENTIFIER ::= { hwPhysicalBoardModuleType 148013 }
            hwPhysicalBoardModuleH80XVPS     OBJECT IDENTIFIER ::= { hwPhysicalBoardModuleType 148014 }
            hwPhysicalBoardModuleH802X2CS    OBJECT IDENTIFIER ::= { hwPhysicalBoardModuleType 148015 }
            hwPhysicalBoardModuleH801XP1A    OBJECT IDENTIFIER ::= { hwPhysicalBoardModuleType 155958}
            hwPhysicalBoardModuleH801GPND    OBJECT IDENTIFIER ::= { hwPhysicalBoardModuleType 148016 }
            hwPhysicalBoardModuleH901MPLA    OBJECT IDENTIFIER ::= { hwPhysicalBoardModuleType 148501 }
            hwPhysicalBoardModuleH901MPLB    OBJECT IDENTIFIER ::= { hwPhysicalBoardModuleType 148502 }
            hwPhysicalBoardModuleH901MPSA    OBJECT IDENTIFIER ::= { hwPhysicalBoardModuleType 148503 }
            hwPhysicalBoardModuleH902MPLA    OBJECT IDENTIFIER ::= { hwPhysicalBoardModuleType 148504 }
            hwPhysicalBoardModuleH901MPSC    OBJECT IDENTIFIER ::= { hwPhysicalBoardModuleType 148505 }
            hwPhysicalBoardModuleH901MPSD    OBJECT IDENTIFIER ::= { hwPhysicalBoardModuleType 148506 }
            hwPhysicalBoardModuleH901MPLC    OBJECT IDENTIFIER ::= { hwPhysicalBoardModuleType 148507 }
            hwPhysicalBoardModuleH901MPLD    OBJECT IDENTIFIER ::= { hwPhysicalBoardModuleType 148508 }
            hwPhysicalBoardModuleH902MPLC    OBJECT IDENTIFIER ::= { hwPhysicalBoardModuleType 148509 }
            hwPhysicalBoardModuleH921MPCA    OBJECT IDENTIFIER ::= { hwPhysicalBoardModuleType 148510 }
            hwPhysicalBoardModuleH921MPCAE   OBJECT IDENTIFIER ::= { hwPhysicalBoardModuleType 148511 }
            hwPhysicalBoardModuleH901XGHD    OBJECT IDENTIFIER ::= { hwPhysicalBoardModuleType 148521 }
            hwPhysicalBoardModuleH901GPHF    OBJECT IDENTIFIER ::= { hwPhysicalBoardModuleType 148522 }
            hwPhysicalBoardModuleH901OGHK    OBJECT IDENTIFIER ::= { hwPhysicalBoardModuleType 148523 }
            hwPhysicalBoardModuleH901NXED    OBJECT IDENTIFIER ::= { hwPhysicalBoardModuleType 148524 }
            hwPhysicalBoardModuleH901OXHD    OBJECT IDENTIFIER ::= { hwPhysicalBoardModuleType 148525 }
            hwPhysicalBoardModuleH901PILA    OBJECT IDENTIFIER ::= { hwPhysicalBoardModuleType 148526 }
            hwPhysicalBoardModuleH901CIUA    OBJECT IDENTIFIER ::= { hwPhysicalBoardModuleType 148527 }
            hwPhysicalBoardModuleH901GPSF    OBJECT IDENTIFIER ::= { hwPhysicalBoardModuleType 148529 }
            hwPhysicalBoardModuleH901EPHF    OBJECT IDENTIFIER ::= { hwPhysicalBoardModuleType 148530 }
            hwPhysicalBoardModuleH901XEHD    OBJECT IDENTIFIER ::= { hwPhysicalBoardModuleType 148531 }
            hwPhysicalBoardModuleH901EDSH    OBJECT IDENTIFIER ::= { hwPhysicalBoardModuleType 148536 }
            hwPhysicalBoardModuleH901PILB    OBJECT IDENTIFIER ::= { hwPhysicalBoardModuleType 148537 }
            hwPhysicalBoardModuleH901CRED    OBJECT IDENTIFIER ::= { hwPhysicalBoardModuleType 148538 }
            hwPhysicalBoardModuleH901CVEC    OBJECT IDENTIFIER ::= { hwPhysicalBoardModuleType 148539 }
            hwPhysicalBoardModuleH921GPHD    OBJECT IDENTIFIER ::= { hwPhysicalBoardModuleType 148540 }
            hwPhysicalBoardModuleH921NXHC    OBJECT IDENTIFIER ::= { hwPhysicalBoardModuleType 148541 }
            hwPhysicalBoardModuleH921GPHDE   OBJECT IDENTIFIER ::= { hwPhysicalBoardModuleType 148542 }
            hwPhysicalBoardModuleH921PICA    OBJECT IDENTIFIER ::= { hwPhysicalBoardModuleType 148543 }
            hwPhysicalBoardModuleME17012A   OBJECT IDENTIFIER ::= { hwPhysicalBoardModuleType 148544 }
            hwPhysicalBoardModuleH921CIUA    OBJECT IDENTIFIER ::= { hwPhysicalBoardModuleType 148545 }
            hwPhysicalBoardModuleH921CGHC    OBJECT IDENTIFIER ::= { hwPhysicalBoardModuleType 148546 }
            hwPhysicalBoardModuleH921CGHCE   OBJECT IDENTIFIER ::= { hwPhysicalBoardModuleType 148547 }
            hwPhysicalBoardModuleH921NXHCE   OBJECT IDENTIFIER ::= { hwPhysicalBoardModuleType 148548 }
            hwPhysicalBoardModuleH901OXEG    OBJECT IDENTIFIER ::= { hwPhysicalBoardModuleType 148600 }
            hwPhysicalBoardModuleH901MPWD    OBJECT IDENTIFIER ::= { hwPhysicalBoardModuleType 148601 }
            hwPhysicalBoardModuleH901MPWE    OBJECT IDENTIFIER ::= { hwPhysicalBoardModuleType 148602 }
            hwPhysicalBoardModuleH901MPWC    OBJECT IDENTIFIER ::= { hwPhysicalBoardModuleType 148603 }
            hwPhysicalBoardModuleH901XSED    OBJECT IDENTIFIER ::= { hwPhysicalBoardModuleType 148604 }
            hwPhysicalBoardModuleH901GPHD    OBJECT IDENTIFIER ::= { hwPhysicalBoardModuleType 148605 }
            hwPhysicalBoardModuleH901GPSD    OBJECT IDENTIFIER ::= { hwPhysicalBoardModuleType 148606 }
            hwPhysicalBoardModuleH901TWED    OBJECT IDENTIFIER ::= { hwPhysicalBoardModuleType 148607 }
            hwPhysicalBoardModuleH901CGCD    OBJECT IDENTIFIER ::= { hwPhysicalBoardModuleType 148608 }
            hwPhysicalBoardModuleH901XGSF    OBJECT IDENTIFIER ::= { hwPhysicalBoardModuleType 148609}
            hwPhysicalBoardModuleH901PISA    OBJECT IDENTIFIER ::= { hwPhysicalBoardModuleType 148610}
            hwPhysicalBoardModuleH901PISB    OBJECT IDENTIFIER ::= { hwPhysicalBoardModuleType 148611}
            hwPhysicalBoardModuleH901PISC    OBJECT IDENTIFIER ::= { hwPhysicalBoardModuleType 148612}
            hwPhysicalBoardModuleH901CGID    OBJECT IDENTIFIER ::= { hwPhysicalBoardModuleType 148613}
            hwPhysicalBoardModuleH901PIMA    OBJECT IDENTIFIER ::= { hwPhysicalBoardModuleType 148614}
            hwPhysicalBoardModuleH901GPLF    OBJECT IDENTIFIER ::= { hwPhysicalBoardModuleType 148615}
            hwPhysicalBoardModuleH901XGLD    OBJECT IDENTIFIER ::= { hwPhysicalBoardModuleType 148616}
            hwPhysicalBoardModuleH901XGLF    OBJECT IDENTIFIER ::= { hwPhysicalBoardModuleType 148617}
            hwPhysicalBoardModuleH901XELD    OBJECT IDENTIFIER ::= { hwPhysicalBoardModuleType 148618}
            hwPhysicalBoardModuleH902MPLAE   OBJECT IDENTIFIER ::= { hwPhysicalBoardModuleType 148619}
            hwPhysicalBoardModuleH901MPSCE   OBJECT IDENTIFIER ::= { hwPhysicalBoardModuleType 148620}
            hwPhysicalBoardModuleH901GPSFE   OBJECT IDENTIFIER ::= { hwPhysicalBoardModuleType 148621}
            hwPhysicalBoardModuleH901XGHDE   OBJECT IDENTIFIER ::= { hwPhysicalBoardModuleType 148622}
            hwPhysicalBoardModuleH902XSED    OBJECT IDENTIFIER ::= { hwPhysicalBoardModuleType 148623}
            hwPhysicalBoardModuleH901DSHD    OBJECT IDENTIFIER ::= { hwPhysicalBoardModuleType 148624}
            hwPhysicalBoardModuleH901OGHF    OBJECT IDENTIFIER ::= { hwPhysicalBoardModuleType 148625}
            hwPhysicalBoardModuleH901OXHG    OBJECT IDENTIFIER ::= { hwPhysicalBoardModuleType 148626}
            hwPhysicalBoardModuleH901NXLC    OBJECT IDENTIFIER ::= { hwPhysicalBoardModuleType 148627}
            hwPhysicalBoardModuleH901TWEDE   OBJECT IDENTIFIER ::= { hwPhysicalBoardModuleType 148628}
            hwPhysicalBoardModuleH902TWED    OBJECT IDENTIFIER ::= { hwPhysicalBoardModuleType 148629}
            hwPhysicalBoardModuleH903XSHD    OBJECT IDENTIFIER ::= { hwPhysicalBoardModuleType 148630}
            hwPhysicalBoardModuleH901XSHF    OBJECT IDENTIFIER ::= { hwPhysicalBoardModuleType 148631}
            hwPhysicalBoardModuleH901CSHD    OBJECT IDENTIFIER ::= { hwPhysicalBoardModuleType 148632}
            hwPhysicalBoardModuleH901CGHF    OBJECT IDENTIFIER ::= { hwPhysicalBoardModuleType 148633}
            hwPhysicalBoardModuleH901CSHF    OBJECT IDENTIFIER ::= { hwPhysicalBoardModuleType 148634}
            hwPhysicalBoardModuleH901XEHF    OBJECT IDENTIFIER ::= { hwPhysicalBoardModuleType 148635}
            hwPhysicalBoardModuleH902CGHD    OBJECT IDENTIFIER ::= { hwPhysicalBoardModuleType 148636}
            hwPhysicalBoardModuleH902CSHD    OBJECT IDENTIFIER ::= { hwPhysicalBoardModuleType 148637}
            hwPhysicalBoardModuleH902CRED    OBJECT IDENTIFIER ::= { hwPhysicalBoardModuleType 148638}
            hwPhysicalBoardModuleH901CSHDE   OBJECT IDENTIFIER ::= { hwPhysicalBoardModuleType 148639}
            hwPhysicalBoardModuleH901CSHFE   OBJECT IDENTIFIER ::= { hwPhysicalBoardModuleType 148640}
            hwPhysicalBoardModuleH901CGUD    OBJECT IDENTIFIER ::= { hwPhysicalBoardModuleType 148641}
            hwPhysicalBoardModuleH901CGUF    OBJECT IDENTIFIER ::= { hwPhysicalBoardModuleType 148642}
            hwPhysicalBoardModuleH902TWHD    OBJECT IDENTIFIER ::= { hwPhysicalBoardModuleType 148643}
            hwPhysicalBoardModuleH902XSHD    OBJECT IDENTIFIER ::= { hwPhysicalBoardModuleType 148644}
            hwPhysicalBoardModuleH901FLHF    OBJECT IDENTIFIER ::= { hwPhysicalBoardModuleType 148645}
            hwPhysicalBoardModuleH902CSHF    OBJECT IDENTIFIER ::= { hwPhysicalBoardModuleType 148646}
            hwPhysicalBoardModuleH902GPHF    OBJECT IDENTIFIER ::= { hwPhysicalBoardModuleType 148647}
            hwPhysicalBoardModuleH902XEHD    OBJECT IDENTIFIER ::= { hwPhysicalBoardModuleType 148648}
            hwPhysicalBoardModuleH902NXED    OBJECT IDENTIFIER ::= { hwPhysicalBoardModuleType 148649}
            hwPhysicalBoardModuleH903MPLA    OBJECT IDENTIFIER ::= { hwPhysicalBoardModuleType 148650}
            hwPhysicalBoardModuleH902MPLB    OBJECT IDENTIFIER ::= { hwPhysicalBoardModuleType 148651}
            hwPhysicalBoardModuleH902CIUA    OBJECT IDENTIFIER ::= { hwPhysicalBoardModuleType 148652}
            hwPhysicalBoardModuleH902PILA    OBJECT IDENTIFIER ::= { hwPhysicalBoardModuleType 148653}
            hwPhysicalBoardModuleH901GPUF    OBJECT IDENTIFIER ::= { hwPhysicalBoardModuleType 148654}
            hwPhysicalBoardModuleH901NCEB    OBJECT IDENTIFIER ::= { hwPhysicalBoardModuleType 148655}
            hwPhysicalBoardModuleH901GPHH    OBJECT IDENTIFIER ::= { hwPhysicalBoardModuleType 148656}
            hwPhysicalBoardModuleH901MPLE    OBJECT IDENTIFIER ::= { hwPhysicalBoardModuleType 148657}
            hwPhysicalBoardModuleH902CGHF    OBJECT IDENTIFIER ::= { hwPhysicalBoardModuleType 148658}
            hwPhysicalBoardModuleH902GPUF    OBJECT IDENTIFIER ::= { hwPhysicalBoardModuleType 148659}
            hwPhysicalBoardModuleH902GPLF    OBJECT IDENTIFIER ::= { hwPhysicalBoardModuleType 148660}
            hwPhysicalBoardModuleH902XELD    OBJECT IDENTIFIER ::= { hwPhysicalBoardModuleType 148661}
            hwPhysicalBoardModuleH902GPSF    OBJECT IDENTIFIER ::= { hwPhysicalBoardModuleType 148662}
            hwPhysicalBoardModuleMA5800Reserve63    OBJECT IDENTIFIER ::= { hwPhysicalBoardModuleType 148663}
            hwPhysicalBoardModuleH902XSHF    OBJECT IDENTIFIER ::= { hwPhysicalBoardModuleType 148664}
            hwPhysicalBoardModuleH902FLHF    OBJECT IDENTIFIER ::= { hwPhysicalBoardModuleType 148665}
            hwPhysicalBoardModuleH902CGUF    OBJECT IDENTIFIER ::= { hwPhysicalBoardModuleType 148666}
            hwPhysicalBoardModuleH902OXHD    OBJECT IDENTIFIER ::= { hwPhysicalBoardModuleType 148667}
            hwPhysicalBoardModuleH902GPHFE    OBJECT IDENTIFIER ::= { hwPhysicalBoardModuleType 148668}
            hwPhysicalBoardModuleH902FLHFE    OBJECT IDENTIFIER ::= { hwPhysicalBoardModuleType 148669}
            hwPhysicalBoardModuleH903MPLAE    OBJECT IDENTIFIER ::= { hwPhysicalBoardModuleType 148670}
            hwPhysicalBoardModuleH902OGHK     OBJECT IDENTIFIER ::= { hwPhysicalBoardModuleType 148671}
            hwPhysicalBoardModuleH902XSHFE    OBJECT IDENTIFIER ::= { hwPhysicalBoardModuleType 148672}
            hwPhysicalBoardModuleH902EPHFE    OBJECT IDENTIFIER ::= { hwPhysicalBoardModuleType 148673}
            hwPhysicalBoardModuleH902EPHF     OBJECT IDENTIFIER ::= { hwPhysicalBoardModuleType 148674}
            hwPhysicalBoardModuleH902PISB     OBJECT IDENTIFIER ::= { hwPhysicalBoardModuleType 148675}
            hwPhysicalBoardModuleH901MPSAE    OBJECT IDENTIFIER ::= { hwPhysicalBoardModuleType 148676}
            hwPhysicalBoardModuleMA5800Reserve77    OBJECT IDENTIFIER ::= { hwPhysicalBoardModuleType 148677}
            hwPhysicalBoardModuleH903CGHD     OBJECT IDENTIFIER ::= { hwPhysicalBoardModuleType 148678}
            hwPhysicalBoardModuleH903CSHD     OBJECT IDENTIFIER ::= { hwPhysicalBoardModuleType 148679}
            hwPhysicalBoardModuleH902OXEG     OBJECT IDENTIFIER ::= { hwPhysicalBoardModuleType 148680}
            hwPhysicalBoardModuleH903CGUD     OBJECT IDENTIFIER ::= { hwPhysicalBoardModuleType 148681}
            hwPhysicalBoardModuleH902FLEF     OBJECT IDENTIFIER ::= { hwPhysicalBoardModuleType 148682}
            hwPhysicalBoardModuleH902XGLF     OBJECT IDENTIFIER ::= { hwPhysicalBoardModuleType 148683}
            hwPhysicalBoardModuleMA5800Reserve84    OBJECT IDENTIFIER ::= { hwPhysicalBoardModuleType 148684}
            hwPhysicalBoardModuleMA5800Reserve85    OBJECT IDENTIFIER ::= { hwPhysicalBoardModuleType 148685}
            hwPhysicalBoardModuleMA5800Reserve86    OBJECT IDENTIFIER ::= { hwPhysicalBoardModuleType 148686}
            hwPhysicalBoardModuleMA5800Reserve87    OBJECT IDENTIFIER ::= { hwPhysicalBoardModuleType 148687}
            hwPhysicalBoardModuleMA5800Reserve88    OBJECT IDENTIFIER ::= { hwPhysicalBoardModuleType 148688}
            hwPhysicalBoardModuleMA5800Reserve89    OBJECT IDENTIFIER ::= { hwPhysicalBoardModuleType 148689}
            hwPhysicalBoardModuleMA5800Reserve90    OBJECT IDENTIFIER ::= { hwPhysicalBoardModuleType 148690}
            hwPhysicalBoardModuleMA5800Reserve91    OBJECT IDENTIFIER ::= { hwPhysicalBoardModuleType 148691}
            hwPhysicalBoardModuleMA5800Reserve92    OBJECT IDENTIFIER ::= { hwPhysicalBoardModuleType 148692}
            hwPhysicalBoardModuleMA5800Reserve93    OBJECT IDENTIFIER ::= { hwPhysicalBoardModuleType 148693}
            hwPhysicalBoardModuleMA5800Reserve94    OBJECT IDENTIFIER ::= { hwPhysicalBoardModuleType 148694}
            hwPhysicalBoardModuleMA5800Reserve95    OBJECT IDENTIFIER ::= { hwPhysicalBoardModuleType 148695}
            hwPhysicalBoardModuleMA5800Reserve96    OBJECT IDENTIFIER ::= { hwPhysicalBoardModuleType 148696}
            hwPhysicalBoardModuleMA5800Reserve97    OBJECT IDENTIFIER ::= { hwPhysicalBoardModuleType 148697}
            hwPhysicalBoardModuleMA5800Reserve98    OBJECT IDENTIFIER ::= { hwPhysicalBoardModuleType 148698}
            hwPhysicalBoardModuleMA5800Reserve99    OBJECT IDENTIFIER ::= { hwPhysicalBoardModuleType 148699}
            hwPhysicalBoardModuleHS22CCVW    OBJECT IDENTIFIER ::= { hwPhysicalBoardModuleType 155928 }
            hwPhysicalBoardModuleHS3BVCMM    OBJECT IDENTIFIER ::= { hwPhysicalBoardModuleType 155929 }
            hwPhysicalBoardModuleH822CCKRA   OBJECT IDENTIFIER ::= { hwPhysicalBoardModuleType 155930 }
            hwPhysicalBoardModuleHS33CDAA    OBJECT IDENTIFIER ::= { hwPhysicalBoardModuleType 155931 }
            hwPhysicalBoardModuleH82DVCMM    OBJECT IDENTIFIER ::= { hwPhysicalBoardModuleType 155949 }
            hwPhysicalBoardModuleH801SPUC    OBJECT IDENTIFIER ::= { hwPhysicalBoardModuleType 155955 }
            hwPhysicalBoardModuleH80DCSPE    OBJECT IDENTIFIER ::= { hwPhysicalBoardModuleType 155960 }
            hwPhysicalBoardModuleHS2DVCMM    OBJECT IDENTIFIER ::= { hwPhysicalBoardModuleType 155962 }
            hwPhysicalBoardModuleH806VPED    OBJECT IDENTIFIER ::= { hwPhysicalBoardModuleType 156070 }
            hwPhysicalBoardModuleRemoteReserve10    OBJECT IDENTIFIER ::= { hwPhysicalBoardModuleType 156010 }
            hwPhysicalBoardModuleRemoteReserve11    OBJECT IDENTIFIER ::= { hwPhysicalBoardModuleType 156011 }
            hwPhysicalBoardModuleRemoteReserve12    OBJECT IDENTIFIER ::= { hwPhysicalBoardModuleType 156012 }
            hwPhysicalBoardModuleRemoteReserve13    OBJECT IDENTIFIER ::= { hwPhysicalBoardModuleType 156013 }
            hwPhysicalBoardModuleRemoteReserve14    OBJECT IDENTIFIER ::= { hwPhysicalBoardModuleType 156014 }
            hwPhysicalBoardModuleRemoteReserve15    OBJECT IDENTIFIER ::= { hwPhysicalBoardModuleType 156015 }
            hwPhysicalBoardModuleRemoteReserve16    OBJECT IDENTIFIER ::= { hwPhysicalBoardModuleType 156016 }
            hwPhysicalBoardModuleRemoteReserve17    OBJECT IDENTIFIER ::= { hwPhysicalBoardModuleType 156017 }
            hwPhysicalBoardModuleRemoteReserve18    OBJECT IDENTIFIER ::= { hwPhysicalBoardModuleType 156018 }
            hwPhysicalBoardModuleRemoteReserve19    OBJECT IDENTIFIER ::= { hwPhysicalBoardModuleType 156019 }
            hwPhysicalBoardModuleRemoteReserve20    OBJECT IDENTIFIER ::= { hwPhysicalBoardModuleType 156020 }
            hwPhysicalBoardModuleRemoteReserve21    OBJECT IDENTIFIER ::= { hwPhysicalBoardModuleType 156021 }
            hwPhysicalBoardModuleRemoteReserve22    OBJECT IDENTIFIER ::= { hwPhysicalBoardModuleType 156022 }
            hwPhysicalBoardModuleRemoteReserve23    OBJECT IDENTIFIER ::= { hwPhysicalBoardModuleType 156023 }
            hwPhysicalBoardModuleRemoteReserve24    OBJECT IDENTIFIER ::= { hwPhysicalBoardModuleType 156024 }
            hwPhysicalBoardModuleRemoteReserve25    OBJECT IDENTIFIER ::= { hwPhysicalBoardModuleType 156025 }
            hwPhysicalBoardModuleRemoteReserve26    OBJECT IDENTIFIER ::= { hwPhysicalBoardModuleType 156026 }
            hwPhysicalBoardModuleRemoteReserve27    OBJECT IDENTIFIER ::= { hwPhysicalBoardModuleType 156027 }
            hwPhysicalBoardModuleRemoteReserve28    OBJECT IDENTIFIER ::= { hwPhysicalBoardModuleType 156028 }
            hwPhysicalBoardModuleRemoteReserve29    OBJECT IDENTIFIER ::= { hwPhysicalBoardModuleType 156029 }
	    hwPhysicalBoardModuleH805SCUP           OBJECT IDENTIFIER ::= { hwPhysicalBoardModuleType 156057 }           
            hwPhysicalBoardModuleH805SCUQ           OBJECT IDENTIFIER ::= { hwPhysicalBoardModuleType 156061 } 
            hwPhysicalBoardModuleH801SCUP           OBJECT IDENTIFIER ::= { hwPhysicalBoardModuleType 156082 }
            hwPhysicalBoardModuleH801SCUQ           OBJECT IDENTIFIER ::= { hwPhysicalBoardModuleType 156083 }   
            hwPhysicalBoardModuleH803OPGE           OBJECT IDENTIFIER ::= { hwPhysicalBoardModuleType 156087 }           
            hwPhysicalBoardModuleH803EDTB           OBJECT IDENTIFIER ::= { hwPhysicalBoardModuleType 156088 } 
			
        hwPhysicalSubBoardModuleType   OBJECT IDENTIFIER ::= { hwEntityMIBObjects 5 }
            hwPhysicalSubBoardModuleAF11AMCX1     OBJECT IDENTIFIER ::= { hwPhysicalSubBoardModuleType 33025 }
            hwPhysicalSubBoardModuleAF11AMCB1     OBJECT IDENTIFIER ::= { hwPhysicalSubBoardModuleType 33026 }
            hwPhysicalSubBoardModuleAF11AMCC1     OBJECT IDENTIFIER ::= { hwPhysicalSubBoardModuleType 33027 }
            hwPhysicalSubBoardModuleAF11AMCD1     OBJECT IDENTIFIER ::= { hwPhysicalSubBoardModuleType 33028 }
            hwPhysicalSubBoardModuleAF11AMCX2     OBJECT IDENTIFIER ::= { hwPhysicalSubBoardModuleType 33029 }
            hwPhysicalSubBoardModuleAF11AMCB2     OBJECT IDENTIFIER ::= { hwPhysicalSubBoardModuleType 33030 }
            hwPhysicalSubBoardModuleAF11AMCC2     OBJECT IDENTIFIER ::= { hwPhysicalSubBoardModuleType 33031 }
            hwPhysicalSubBoardModuleAF11AMCD2     OBJECT IDENTIFIER ::= { hwPhysicalSubBoardModuleType 33032 }

            hwPhysicalSubBoardModuleH801BITSB  OBJECT IDENTIFIER ::= { hwPhysicalSubBoardModuleType 146038 }
            hwPhysicalSubBoardModuleH801O4GS   OBJECT IDENTIFIER ::= { hwPhysicalSubBoardModuleType 143361 }
            hwPhysicalSubBoardModuleH801CKMC   OBJECT IDENTIFIER ::= { hwPhysicalSubBoardModuleType 146024 }
            hwPhysicalSubBoardModuleH801O2GS   OBJECT IDENTIFIER ::= { hwPhysicalSubBoardModuleType 143360 }
            hwPhysicalSubBoardModuleH801O4FS   OBJECT IDENTIFIER ::= { hwPhysicalSubBoardModuleType 143362 }
            hwPhysicalSubBoardModuleH801E2GA   OBJECT IDENTIFIER ::= { hwPhysicalSubBoardModuleType 143363 }
            hwPhysicalSubBoardModuleH801O2CS   OBJECT IDENTIFIER ::= { hwPhysicalSubBoardModuleType 143364 }
            hwPhysicalSubBoardModuleH801E4GA   OBJECT IDENTIFIER ::= { hwPhysicalSubBoardModuleType 143365 }
            hwPhysicalSubBoardModuleH801D4GA   OBJECT IDENTIFIER ::= { hwPhysicalSubBoardModuleType 143366 }
            hwPhysicalSubBoardModuleH801O2FN   OBJECT IDENTIFIER ::= { hwPhysicalSubBoardModuleType 143367 }
            hwPhysicalSubBoardModuleH801O2GN   OBJECT IDENTIFIER ::= { hwPhysicalSubBoardModuleType 143368 }
            hwPhysicalSubBoardModuleH801EP1A   OBJECT IDENTIFIER ::= { hwPhysicalSubBoardModuleType 143371 }
            hwPhysicalSubBoardModuleH801GP1A   OBJECT IDENTIFIER ::= { hwPhysicalSubBoardModuleType 143372 }
            hwPhysicalSubBoardModuleH561EP1A   OBJECT IDENTIFIER ::= { hwPhysicalSubBoardModuleType 145920 }
            hwPhysicalSubBoardModuleH561EP2A   OBJECT IDENTIFIER ::= { hwPhysicalSubBoardModuleType 145921 }
            hwPhysicalSubBoardModuleH561EP4A   OBJECT IDENTIFIER ::= { hwPhysicalSubBoardModuleType 145922 }
            hwPhysicalSubBoardModuleH531O4GS   OBJECT IDENTIFIER ::= { hwPhysicalSubBoardModuleType 145923 }
            hwPhysicalSubBoardModuleH561BITS   OBJECT IDENTIFIER ::= { hwPhysicalSubBoardModuleType 145924 }
            hwPhysicalSubBoardModuleH822EP1A   OBJECT IDENTIFIER ::= { hwPhysicalSubBoardModuleType 145925 }
            hwPhysicalSubBoardModuleH801FLBA   OBJECT IDENTIFIER ::= { hwPhysicalSubBoardModuleType 145938 }
            hwPhysicalSubBoardModuleH801NH1A   OBJECT IDENTIFIER ::= { hwPhysicalSubBoardModuleType 145940 }
            hwPhysicalSubBoardModuleH801CSSA   OBJECT IDENTIFIER ::= { hwPhysicalSubBoardModuleType 146017 }
            hwPhysicalSubBoardModuleH801O2CE   OBJECT IDENTIFIER ::= { hwPhysicalSubBoardModuleType 146021 }
            hwPhysicalSubBoardModuleH802GP1A   OBJECT IDENTIFIER ::= { hwPhysicalSubBoardModuleType 146022 }
            hwPhysicalSubBoardModuleH801X1HA   OBJECT IDENTIFIER ::= { hwPhysicalSubBoardModuleType 146023 }
            hwPhysicalSubBoardModuleH801M2XA   OBJECT IDENTIFIER ::= { hwPhysicalSubBoardModuleType 146025 }
            hwPhysicalSubBoardModuleH901CKUA   OBJECT IDENTIFIER ::= { hwPhysicalSubBoardModuleType 148501 }
            hwPhysicalSubBoardModuleH901CKUB   OBJECT IDENTIFIER ::= { hwPhysicalSubBoardModuleType 148502 }
            hwPhysicalSubBoardModuleReserve11   OBJECT IDENTIFIER ::= { hwPhysicalSubBoardModuleType 148511 }
            hwPhysicalSubBoardModuleH901CPCA   OBJECT IDENTIFIER ::= { hwPhysicalSubBoardModuleType 148512 }
            hwPhysicalSubBoardModuleH901CPCB   OBJECT IDENTIFIER ::= { hwPhysicalSubBoardModuleType 148513 }
            hwPhysicalSubBoardModuleH901CPCC   OBJECT IDENTIFIER ::= { hwPhysicalSubBoardModuleType 148514 }
            hwPhysicalSubBoardModuleH902CKUB   OBJECT IDENTIFIER ::= { hwPhysicalSubBoardModuleType 148515 }
            hwPhysicalSubBoardModuleH902CKUA   OBJECT IDENTIFIER ::= { hwPhysicalSubBoardModuleType 148516 }
            hwPhysicalSubBoardModuleReserve17   OBJECT IDENTIFIER ::= { hwPhysicalSubBoardModuleType 148517 }
            hwPhysicalSubBoardModuleReserve18   OBJECT IDENTIFIER ::= { hwPhysicalSubBoardModuleType 148518 }
            hwPhysicalSubBoardModuleReserve19   OBJECT IDENTIFIER ::= { hwPhysicalSubBoardModuleType 148519 }
            hwPhysicalSubBoardModuleReserve20   OBJECT IDENTIFIER ::= { hwPhysicalSubBoardModuleType 148520 }
            hwPhysicalSubBoardModuleReserve21   OBJECT IDENTIFIER ::= { hwPhysicalSubBoardModuleType 148521 }
            hwPhysicalSubBoardModuleReserve22   OBJECT IDENTIFIER ::= { hwPhysicalSubBoardModuleType 148522 }
            hwPhysicalSubBoardModuleReserve23   OBJECT IDENTIFIER ::= { hwPhysicalSubBoardModuleType 148523 }
            hwPhysicalSubBoardModuleReserve24   OBJECT IDENTIFIER ::= { hwPhysicalSubBoardModuleType 148524 }
            hwPhysicalSubBoardModuleReserve25   OBJECT IDENTIFIER ::= { hwPhysicalSubBoardModuleType 148525 }
            hwPhysicalSubBoardModuleH901TPUA   OBJECT IDENTIFIER ::= { hwPhysicalSubBoardModuleType 148601 }
            hwPhysicalSubBoardModuleH831UP2C   OBJECT IDENTIFIER ::= { hwPhysicalSubBoardModuleType 155659 }
            hwPhysicalSubBoardModuleH831UP2E   OBJECT IDENTIFIER ::= { hwPhysicalSubBoardModuleType 155952 }
            hwPhysicalSubBoardModuleH831UP2F   OBJECT IDENTIFIER ::= { hwPhysicalSubBoardModuleType 155953 }
            hwPhysicalSubBoardModuleHS21PWBB   OBJECT IDENTIFIER ::= { hwPhysicalSubBoardModuleType 155954 }
            hwPhysicalSubBoardModuleHS21MIXB   OBJECT IDENTIFIER ::= { hwPhysicalSubBoardModuleType 155955 }
            hwPhysicalSubBoardModuleH801CPCA   OBJECT IDENTIFIER ::= { hwPhysicalSubBoardModuleType 204923 }
            hwPhysicalSubBoardModuleH801CPCB   OBJECT IDENTIFIER ::= { hwPhysicalSubBoardModuleType 204933 }
            hwPhysicalSubBoardModuleH801CPCC   OBJECT IDENTIFIER ::= { hwPhysicalSubBoardModuleType 204934 }
            hwPhysicalSubBoardModuleH801CKMD   OBJECT IDENTIFIER ::= { hwPhysicalSubBoardModuleType 888891 }
            

        hwPhysicalPortType             OBJECT IDENTIFIER ::= { hwEntityMIBObjects 6 }
            hwPhysicalPortOptic100MOC3MSType            OBJECT IDENTIFIER ::= { hwPhysicalPortType 1 }
            hwPhysicalPortOptic100MOC3SMIType           OBJECT IDENTIFIER ::= { hwPhysicalPortType 2 }
            hwPhysicalPortOptic100MOC3SMLType           OBJECT IDENTIFIER ::= { hwPhysicalPortType 3 }
            hwPhysicalPortOptic100MOC12MMSType          OBJECT IDENTIFIER ::= { hwPhysicalPortType 4 }
            hwPhysicalPortOptic100MOC12SMIType          OBJECT IDENTIFIER ::= { hwPhysicalPortType 5 }
            hwPhysicalPortOptic100MOC12SMLType          OBJECT IDENTIFIER ::= { hwPhysicalPortType 6 }
            hwPhysicalPortOptic1000MBASETType           OBJECT IDENTIFIER ::= { hwPhysicalPortType 7 }
            hwPhysicalPortOptic1000MBASECXType          OBJECT IDENTIFIER ::= { hwPhysicalPortType 8 }
            hwPhysicalPortOptic1000MBASELXType          OBJECT IDENTIFIER ::= { hwPhysicalPortType 9 }
            hwPhysicalPortOptic1000MBASESXType          OBJECT IDENTIFIER ::= { hwPhysicalPortType 10 }
            hwPhysicalPortOpticOC48SType                OBJECT IDENTIFIER ::= { hwPhysicalPortType 11 }
            hwPhysicalPortOpticOC48IType                OBJECT IDENTIFIER ::= { hwPhysicalPortType 12 }
            hwPhysicalPortOpticOC48LType                OBJECT IDENTIFIER ::= { hwPhysicalPortType 13 }
            hwPhysicalPortOptic10GBASESRType            OBJECT IDENTIFIER ::= { hwPhysicalPortType 16 }
            hwPhysicalPortOptic10GBASELRType            OBJECT IDENTIFIER ::= { hwPhysicalPortType 17 }
            hwPhysicalPortOptic10GBASEERType            OBJECT IDENTIFIER ::= { hwPhysicalPortType 18 }
            hwPhysicalPortOptic10GBASELRMType           OBJECT IDENTIFIER ::= { hwPhysicalPortType 19 }
            hwPhysicalPortOptic10GBASESWType            OBJECT IDENTIFIER ::= { hwPhysicalPortType 20 }
            hwPhysicalPortOptic10GBASELWType            OBJECT IDENTIFIER ::= { hwPhysicalPortType 21 }
            hwPhysicalPortOptic10GBASEEWType            OBJECT IDENTIFIER ::= { hwPhysicalPortType 22 }
            hwPhysicalPortOptic10GBASESRWType           OBJECT IDENTIFIER ::= { hwPhysicalPortType 23 }
            hwPhysicalPortOptic10GBASELRWType           OBJECT IDENTIFIER ::= { hwPhysicalPortType 24 }
            hwPhysicalPortOptic10GBASEERWType           OBJECT IDENTIFIER ::= { hwPhysicalPortType 25 }
            hwPhysicalPortOptic1200MXSNIType            OBJECT IDENTIFIER ::= { hwPhysicalPortType 26 }
            hwPhysicalPortOptic1200SMLLLType            OBJECT IDENTIFIER ::= { hwPhysicalPortType 27 }
            hwPhysicalPortOpticEXTENDED1550NMType       OBJECT IDENTIFIER ::= { hwPhysicalPortType 28 }
            hwPhysicalPortOpticINTERMEDIATE1300NMType   OBJECT IDENTIFIER ::= { hwPhysicalPortType 29 }
            hwPhysicalPortOptic2XFCMMFType              OBJECT IDENTIFIER ::= { hwPhysicalPortType 30 }
            hwPhysicalPortOptic2XFCSMFType              OBJECT IDENTIFIER ::= { hwPhysicalPortType 31 }
            hwPhysicalPortOptic1000M100MBASELXType      OBJECT IDENTIFIER ::= { hwPhysicalPortType 32 }
            hwPhysicalPortOptic1000MBX10Type            OBJECT IDENTIFIER ::= { hwPhysicalPortType 33 }
            hwPhysicalPortOptic1000MBASEBXType          OBJECT IDENTIFIER ::= { hwPhysicalPortType 34 }
            hwPhysicalPortOpticSFPPLUSType              OBJECT IDENTIFIER ::= { hwPhysicalPortType 35 }
            hwPhysicalPortOptic100MBASEBXType           OBJECT IDENTIFIER ::= { hwPhysicalPortType 36 }
            hwPhysicalPortOptic100MBASEFXType           OBJECT IDENTIFIER ::= { hwPhysicalPortType 37 }
            hwPhysicalPortOptic100MBASELXType           OBJECT IDENTIFIER ::= { hwPhysicalPortType 38 }

            hwPhysicalPortOpticGponClassBPlus           OBJECT IDENTIFIER ::= { hwPhysicalPortType 2001 }
            hwPhysicalPortOpticGponClassCPlus           OBJECT IDENTIFIER ::= { hwPhysicalPortType 2002 }
            hwPhysicalPortOpticGponClassB               OBJECT IDENTIFIER ::= { hwPhysicalPortType 2003 }
            hwPhysicalPortOpticEponPX20                 OBJECT IDENTIFIER ::= { hwPhysicalPortType 2004 }
            hwPhysicalPortOpticEponPX20Plus             OBJECT IDENTIFIER ::= { hwPhysicalPortType 2005 }
            hwPhysicalPortOptic10GEponPR30              OBJECT IDENTIFIER ::= { hwPhysicalPortType 2010 }
            hwPhysicalPortOptic10GEponPR20              OBJECT IDENTIFIER ::= { hwPhysicalPortType 2011 }
            hwPhysicalPortOptic10GEponPRX30             OBJECT IDENTIFIER ::= { hwPhysicalPortType 2012 }
            hwPhysicalPortOptic10GEponPRX20             OBJECT IDENTIFIER ::= { hwPhysicalPortType 2013 }
            hwPhysicalPortOpticXGponN2A                 OBJECT IDENTIFIER ::= { hwPhysicalPortType 2014 }
            hwPhysicalPortOpticXGponN2B                 OBJECT IDENTIFIER ::= { hwPhysicalPortType 2015 }
            hwPhysicalPortOpticXGponN1                  OBJECT IDENTIFIER ::= { hwPhysicalPortType 2016 }
            hwPhysicalPortOpticGPONCLASSCPLUSPLUSType   OBJECT IDENTIFIER ::= { hwPhysicalPortType 2017 }
            hwPhysicalPortOpticEPONPX20PLUSPLUSType     OBJECT IDENTIFIER ::= { hwPhysicalPortType 2018 }

            hwPhysicalPortDocsisPort                    OBJECT IDENTIFIER ::= { hwPhysicalPortType 3000 }
            hwPhysicalPortDocsis30UpstreamChannel       OBJECT IDENTIFIER ::= { hwPhysicalPortType 3001 }
            hwPhysicalPortDocsis30DownstreamChannel     OBJECT IDENTIFIER ::= { hwPhysicalPortType 3002 }
            hwPhysicalPortDocsis31UpstreamChannel       OBJECT IDENTIFIER ::= { hwPhysicalPortType 3003 }
            hwPhysicalPortDocsis31DownstreamChannel     OBJECT IDENTIFIER ::= { hwPhysicalPortType 3004 }
            hwPhysicalPortEqamChannel                   OBJECT IDENTIFIER ::= { hwPhysicalPortType 3005 }
            hwPhysicalPortOptic10GEponPR30PLUS          OBJECT IDENTIFIER ::= { hwPhysicalPortType 3006 }
            hwPhysicalPortOpticXGponComboD1             OBJECT IDENTIFIER ::= { hwPhysicalPortType 3007 }
            hwPhysicalPortOpticXGSponComboD2            OBJECT IDENTIFIER ::= { hwPhysicalPortType 3008 }
            hwPhysicalPortNdfChannel                    OBJECT IDENTIFIER ::= { hwPhysicalPortType 3009 }
            hwPhysicalPortNdrChannel                    OBJECT IDENTIFIER ::= { hwPhysicalPortType 3010 }

        hwPhysicalEmuType                OBJECT IDENTIFIER ::= { hwEntityMIBObjects 7 }
            hwPhysicalEmuFanType                OBJECT IDENTIFIER ::= { hwPhysicalEmuType 3 }
            hwPhysicalEmuPower4845Type          OBJECT IDENTIFIER ::= { hwPhysicalEmuType 4 }
            hwPhysicalEmuH801EscType            OBJECT IDENTIFIER ::= { hwPhysicalEmuType 7 }
            hwPhysicalEmuMiniEscType            OBJECT IDENTIFIER ::= { hwPhysicalEmuType 9 }
            hwPhysicalEmuPower4830Type          OBJECT IDENTIFIER ::= { hwPhysicalEmuType 10 }
            hwPhysicalEmuPower4875LType         OBJECT IDENTIFIER ::= { hwPhysicalEmuType 11 }
            hwPhysicalEmuH801CITDType           OBJECT IDENTIFIER ::= { hwPhysicalEmuType 12 }
            hwPhysicalEmuH801CITXType           OBJECT IDENTIFIER ::= { hwPhysicalEmuType 13 }
            hwPhysicalEmuTCUType                OBJECT IDENTIFIER ::= { hwPhysicalEmuType 14 }
            hwPhysicalEmuPower3000Type          OBJECT IDENTIFIER ::= { hwPhysicalEmuType 15 }
            hwPhysicalEmuSMUType                OBJECT IDENTIFIER ::= { hwPhysicalEmuType 16 }
            hwPhysicalEmuVPEAType               OBJECT IDENTIFIER ::= { hwPhysicalEmuType 17 }
            hwPhysicalEmuH801VESCType           OBJECT IDENTIFIER ::= { hwPhysicalEmuType 18 }
            hwPhysicalEmuH901VESCType           OBJECT IDENTIFIER ::= { hwPhysicalEmuType 19 }

        hwPhysicalPowerFrameType          OBJECT IDENTIFIER ::= { hwEntityMIBObjects 8 }
            hwPhysicalSmuPowerFrameType         OBJECT IDENTIFIER ::= { hwPhysicalPowerFrameType 1 }

        hwPhysicalPowerModuleType         OBJECT IDENTIFIER ::= { hwEntityMIBObjects 9 }
            hwPhysicalSmuPowerModuleType        OBJECT IDENTIFIER ::= { hwPhysicalPowerModuleType 1 }

        hwPhysicalBatteryType             OBJECT IDENTIFIER ::= { hwEntityMIBObjects 10 }
            hwPhysicalCommonBatteryType         OBJECT IDENTIFIER ::= { hwPhysicalBatteryType 1 }


END

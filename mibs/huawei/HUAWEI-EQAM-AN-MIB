-- =================================================================
-- Copyright (C) 2018 by HUAWEI TECHNOLOGIES. All rights reserved.
-- Description:  The MIB is used for defining Huawei's EQAM attribute.
-- Reference:    None
-- Version:      V1.37
-- =================================================================

HUAWEI-EQAM-AN-MIB DEFINITIONS ::= BEGIN

        IMPORTS
            huaweiUtility
                FROM HUAWEI-MIB
            EnabledStatus
                FROM P-BRIDGE-MIB
            VlanId
                FROM Q-BRIDGE-MIB
            OBJECT-GROUP, NOTIFICATION-GROUP
                FROM SNMPv2-CONF
            ifIndex, InterfaceIndex, InterfaceIndexOrZero
                FROM IF-MIB
            Integer32, Unsigned32, OBJECT-TYPE, MODULE-IDENTITY, OBJECT-IDENTITY,
            NOTIFICATION-TYPE, TimeTicks, Counter32, Counter64
                FROM SNMPv2-SMI
            RowStatus,DisplayString, TruthValue, TEXTUAL-CONVENTION, DateAndTime
                FROM SNMPv2-TC
            ChannelList                                             
                FROM DOCS-IF3-MIB
            InetAddressType, InetAddress, InetPortNumber
                FROM INET-ADDRESS-MIB
            hwFrameIndex, hwSlotIndex, hwPortIndex
                FROM HUAWEI-DEVICE-MIB;

        hwEqamAn MODULE-IDENTITY
            LAST-UPDATED "201812200000Z"
            ORGANIZATION "Huawei Technologies Co.,Ltd."
            CONTACT-INFO
                         "Huawei Industrial Base
                         Bantian, Longgang
                         Shenzhen 518129
                         People's Republic of China
                         Website: http://www.huawei.com
                         Email: support@huawei.com
                         "
        DESCRIPTION
            "The MIB is used for defining Huawei's EQAM attribute.
            "

        --  Revision history
            REVISION     "201812200000Z"
            DESCRIPTION  "V1.37, Added hwDocsQamVideoDomainLocalInterfaceLoopbackNumber to hwDocsQamVideoDomainTable.
                   "
				   
            REVISION     "201810250000Z"
            DESCRIPTION  "V1.36,  Added value invalid(255) to hwDocsQamScsEisProtocolVersion and hwDocsQamScsEcmgProtocolVersion.
                   Modified the description of hwDocsQamVideoStreamESSrambleStateList.
                   Added hwDocsQamVideoStreamOutputESSrambleStateList to hwDocsQamVideoStreamTable.
                   "
				   
            REVISION     "201809190000Z"
            DESCRIPTION  "V1.35,  Added value ver2(3) to hwDocsQamScsEisProtocolVersion.
                   Modified the description of hwDocsQamScsEcmgEcmTable.
                   Modified the index of hwDocsQamScsEcmgEcmEntry from hwDocsQamScsEcmgECMID to hwDocsQamScsEcmgStreamID.
                   Modified the value range of hwDocsQamScsEcmgStreamID from (0..65535 | 4294967295) to (0..4294967295).
                   "

            REVISION     "201808290000Z"
            DESCRIPTION  "V1.34,  Modified the description of hwDocsQamInputTSPIDList.
                   Modified the description of hwDocsQamInputTSPIDStateMask.
                   Modified the description of hwDocsQamOutputTSPIDList.
                   Modified the description of hwDocsQamOutputTSPIDStateMask.
                   "
				   
            REVISION     "201808220000Z"
            DESCRIPTION  "V1.33, Modified the value range of hwDocsQamEISProfileCPDuration from (10..300) to (10..3600).
                   Modified the value range of hwDocsQamInputTSPIDNumber from (0..256) to (0..512).
                   Modified the value range of hwDocsQamOutputTSPIDNumber from (0..256) to (0..512).
                   Modified the value range of hwDocsQamInputTSPIDList from (0..512) to (0..1024).
                   Modified the value range of hwDocsQamInputTSPIDStateMask from (0..512) to (0..1024).
                   Modified the value range of hwDocsQamOutputTSPIDList from (0..512) to (0..1024).
                   Modified the value range of hwDocsQamOutputTSPIDStateMask from (0..512) to (0..1024).
                   Added hwDocsQamEISProfileProtocol to hwDocsQamEISProfileTable.
                   Added hwDocsQamScsEisNominalCPDuration,  hwDocsQamScsEisMinAcDelayStart, hwDocsQamScsEisCpDurationConfigMode to hwDocsQamEISProfileTable.
                   Modified the description of hwDocsQamVideoDomainReservedPID, hwDocsQamChannelProfileRate, hwDocsQamChannelSCSName, hwDocsQamEISProfileTcpPort,
                   hwDocsQamECMGCASubSystemId, hwDocsQamECMGTcpPort, hwDocsQamSCSEISProfileName, hwDocsQamScsEisScgOriginalNetworkID, hwDocsQamScsEisScgReferenceID, 
                   hwDocsQamScsEisScgActivationTime, hwDocsQamScsEisScgRecommendedCPDuration, hwDocsQamScsEisScgEcmACTransferMode.
                   "
		
            REVISION     "201805310000Z"
            DESCRIPTION  "V1.32, added hwDocsQamVODProcessFrameSlot, hwDocsQamVideoDomainReservedPID, hwDocsQamChannelProfileRate, hwDocsQamVODProcessGroupTable 
                   and hwDocsQamEISProfileTable, hwDocsQamECMGTable, hwDocsQamECMGChannelTable,hwDocsQamSCSTable, hwDocsQamSCSECMGTable.             
                   "  
                                   
            REVISION     "201803270000Z"
            DESCRIPTION  "V1.31, Modified the description of hwEqamExtendLicenseDVBPortLockFlg .
                   Modified the description of hwEqamExtendLicenseVODChannelLockFlg.
                   Modified the description of hwDocsQamInputTSETR290MonitoringType.
                   Modified the description of hwDocsQamInputTSETR290MonitoringState.
                   Modified the description of hwDocsQamInputTSETR290MonitoringLastErrorIndication.
                   Modified the description of hwDocsQamInputPIDETR290MonitoringState.
                   Modified the description of hwDocsQamInputPIDETR290MonitoringLastErrorIndication.
                   Modified the description of hwDocsQamNotificationPSIType.
                   "
                   
                REVISION     "201803220000Z"
            DESCRIPTION  "V1.30, Modified the default value of hwEqamExtendLicenseDVBPortLockFlg from unlocked(2) to locked(1).
                   Modified the default value of hwEqamExtendLicenseVODChannelLockFlg from unlocked(2) to locked(1).
                   Modified the description of hwDocsQamDVBPATErrorTrap.
                   Modified the description of hwDocsQamDVBPATMissingTrap.
                   Modified the description of hwDocsQamDVBPMTErrorTrap.
                   Modified the description of hwDocsQamDVBPMTMissingTrap.
                   Modified the description of hwDocsQamDVBContinutyCounterErrorTrap.
                   Modified the description of hwDocsQamETR290MonitoringAlarmTsSyncLossTrap.
                   Modified the description of hwDocsQamETR290MonitoringAlarmSyncByteErrorTrap.
                   Modified the description of hwDocsQamETR290MonitoringAlarmPATErrorTrap.
                   Modified the description of hwDocsQamETR290MonitoringAlarmContinuitycountErrorTrap.
                   Modified the description of hwDocsQamETR290MonitoringAlarmPMTErrorTrap.
                   Modified the description of hwDocsQamETR290MonitoringAlarmPIDErrorTrap.
                   Modified the description of hwDocsQamETR290MonitoringAlarmTransportErrorTrap.
                   Modified the description of hwDocsQamETR290MonitoringAlarmCRCErrorTrap.
                   Modified the description of hwDocsQamETR290MonitoringAlarmPCRErrorTrap.
                   Modified the description of hwDocsQamETR290MonitoringAlarmPCRAccuracyErrorTrap.
                   Modified the description of hwDocsQamETR290MonitoringAlarmCATErrorTrap.
                   "
                 
            REVISION     "201802280000Z"
            DESCRIPTION  "V1.29, added hwEqamLicControlObjects.
                   "
            REVISION     "201802130000Z"
            DESCRIPTION  "V1.28, added hwDocsQamVideoFrequncyOffsetCorrectionFactor to hwDocsQamVideoGlobalConfigObject.
                   "           
            REVISION     "201801120000Z"
            DESCRIPTION  "V1.27, added hwDocsQamVODLocalIpHashConflictTrap.
                   Added hwFrameIndex, hwSlotIndex, hwPortIndex to HUAWEI-EQAM-AN-MIB DEFINITIONS.
                   "
            REVISION     "201710120000Z"
            DESCRIPTION  "V1.26, added hwDocsQamDVBInputTsTimeOut to hwDocsQamVideoGlobalConfigObject.
                   Added hwDocsQamDVBPrimaryInputTSLossTrap, hwDocsQamDVBPrimaryInputTSRecoveryTrap, hwDocsQamDVBSecondaryInputTSLossTrap, hwDocsQamDVBSecondaryInputTSRecoveryTrap.
                   " 
            REVISION     "201708100000Z"
            DESCRIPTION  "V1.25, added hwDocsQamInputTSSeamlessPrimaryPacketSpacing, hwDocsQamInputTSSeamlessSecondaryPacketSpacing, hwDocsQamInputTSSeamlessPrimaryPacketSpacingMax and hwDocsQamInputTSSeamlessSecondaryPacketSpacingMax to hwDocsQamDVBInputTSStatisticsTable.
                   Modified the description of hwDocsQamInputTSETR290MonitoringLastErrorOccurTime.
                   Modified the description of hwDocsQamInputPIDETR290MonitoringLastErrorOccurTime.
                   "
            REVISION     "201707280000Z"
            DESCRIPTION  "V1.24,  Modified the value range of hwDocsQamInputPIDETR290MonitoringPCRDiscontinuity from (1..500) to (0..4294967295).
                   Modified the value range of hwDocsQamInputPIDETR290MonitoringPCRDiscontinuityMax from (1..500) to (0..4294967295).
                   Modified the value range of hwDocsQamInputPIDETR290MonitoringPCRAccuracyJitter from (500..1000) to (0..4294967295).
                   Modified the value range of hwDocsQamInputPIDETR290MonitoringPCRAccuracyJitterMax from (500..1000) to (0..4294967295).
                   "
            REVISION     "201707050000Z"
            DESCRIPTION  "V1.23, added hwDocsQamETR290MonitoringObj, hwDocsQamETR290MonitoringProfileTable, hwDocsQamETR290MonitoringInputTSTable, hwDocsQamInputTSETR290DetailsTable 
                   and hwDocsQamInputPIDETR290DetailsTable.  
                   Added hwDocsQamNotificationProgramName, hwDocsQamNotificationPSIType, hwDocsQamETR290MonitoringAlarmTsSyncLossTrap, hwDocsQamETR290MonitoringAlarmSyncByteErrorTrap,  
                   hwDocsQamETR290MonitoringAlarmPATErrorTrap, hwDocsQamETR290MonitoringAlarmContinuitycountErrorTrap, hwDocsQamETR290MonitoringAlarmPMTErrorTrap, 
                   hwDocsQamETR290MonitoringAlarmPIDErrorTrap, hwDocsQamETR290MonitoringAlarmTransportErrorTrap, hwDocsQamETR290MonitoringAlarmCRCErrorTrap,
                   hwDocsQamETR290MonitoringAlarmPCRErrorTrap, hwDocsQamETR290MonitoringAlarmPCRAccuracyErrorTrap, hwDocsQamETR290MonitoringAlarmCATErrorTrap.             
                   "  
            REVISION     "201706290000Z"
            DESCRIPTION  "V1.22,  Modified the value range of hwDocsQamLocationID from (1..4096|4294967295) to (0..4294967295).
                      Delete BITS from HUAWEI-EQAM-AN-MIB DEFINITIONS.
                   "
            REVISION     "201705230000Z"
            DESCRIPTION  "V1.21, added hwDocsQamOutputTSStatisticsOperMode to hwDocsQamOutputTSTable. 
                           Added hwDocsQamVideoProgramNumberTotalGlobal, hwDocsQamVideoProgramNumberOnlineGlobal and hwDocsQamDVBChannelMonitoringProbeDuration to hwDocsQamVideoGlobalConfigObject. 
                   Added hwDocsQamVideoStreamSrambled and hwDocsQamVideoStreamESSrambleStateList to hwDocsQamVideoStreamTable.
                   Added hwDocsQamVODSummaryTable, hwDocsQamDVBChannelMonitoringControlTable, hwDocsQamDVBChannelMonitoringTable and hwDocsQamDVBChannelPidMonitoringTable.
                   " 
                    
            REVISION     "201705150000Z"
            DESCRIPTION  "V1.20, added hwDocsQamVideoMapPIDKeepOriginal to hwDocsQamVideoMapTable. 
                         "
                                           
            REVISION     "201702200000Z"
            DESCRIPTION  "V1.19, added hwDocsQamInputTSStateSwitchoverReason to hwDocsQamInputTSStateTable.
                   Added hwDocsQamInputTSRedundancyTriggers and hwDocsQamInputTSRedundancyTriggersDefault to hwDocsQamInputTSTable. 
                   Added hwDocsQamInputTSDefaultSwitchoverTriggers and hwDocsQamInputTSStatisticsClearAll to hwDocsQamVideoGlobalConfigObject.
                   Added hwDocsQamInputTSStatisticsLastCleared to hwDocsQamDVBInputTSStatisticsTable.
                   Modified the description of hwDocsQamFmRDSRealTimeClock.
                   "
            
            REVISION     "201612300000Z"
            DESCRIPTION  "V1.18, added hwDocsQamInputTSMode and hwDocsQamInputTSTransportStreamID to hwDocsQamInputTSTable.
                   Added hwDocsQamInputTSProgramState, hwDocsQamInputTSProgramRate, hwDocsQamInputTSProgramMaxRate, hwDocsQamInputTSProgramMinRate,
                   hwDocsQamInputTSProgramCaNumber, hwDocsQamInputTSProgramCaPIDList and hwDocsQamInputTSProgramCaSystemIDList to hwDocsQamInputTSProgramTable. 
                   Added hwDocsQamOutputTSProgramState, hwDocsQamOutputTSProgramRate, hwDocsQamOutputTSProgramMaxRate, hwDocsQamOutputTSProgramMinRate, 
                   hwDocsQamOutputTSProgramCaNumber, hwDocsQamOutputTSProgramCaPIDList, hwDocsQamOutputTSProgramCaSystemIDList to hwDocsQamOutputTSProgramTable.
                   Added hwDocsQamVideoMapEnable to hwDocsQamVideoMapTable. 
                   Added hwDocsQamDVBDomainChannelOutputEnable to hwDocsQamDVBDomainChannelTable.
                   Added hwDocsQamInputTSProgramEsTable, hwDocsQamOutputTSTable, hwDocsQamOutputTSProgramEsTable, hwDocsQamOutputPIDInfoTable, hwDocsQamOutputTSPIDTable and hwDocsQamEPGTable.
                   " 
            
            REVISION     "201612190000Z"
            DESCRIPTION  "V1.17, added hwDocsQamLocationIDInsertionConfigObject and hwDocsQamLocationIDConfigTable.
                   Added hwDocsQamDVBInputTSSeamlessAverageDelay,hwDocsQamDVBInputTSSeamlessMaxDelay,hwDocsQamDVBInputTSSeamlessMinDelay,
                   hwDocsQamDVBInputTSOriginalPrimaryRTPSequenceErrorCounter and hwDocsQamDVBInputTSOriginalSecondaryRTPSequenceErrorCounter to hwDocsQamDVBInputTSStatisticsTable.
                   "
                    
            REVISION     "201611080000Z"
            DESCRIPTION  "V1.16, modified hwDocsQamInputTSUdpPort and hwDocsQamInputTSSecondaryUdpPort to hwDocsQamInputTSTable.
                   "
                   
            REVISION     "201610220000Z"
            DESCRIPTION  "V1.15, Modified the hwDocsQamFmRDSRadioTest to hwDocsQamFmRDSRadioText.
                   "
                    
            REVISION     "201609270000Z"
            DESCRIPTION  "V1.14, Modified the description of hwDocsQamFmRDSProgramType.
                   "
                                           
            REVISION     "201609180000Z"
            DESCRIPTION  "V1.13, deleted hwDocsQamFmRDSCountryCode of hwDocsQamFmRDSTable.
                   Added hwDocsQamFmRDSMode, hwDocsQamFmRDSCTDef, hwDocsQamFmRDSCountryCodeValue, hwDocsQamFmRDSTATP, hwDocsQamFmRDSDI, hwDocsQamFmRDSMS, hwDocsQamFmRDSCT and hwDocsQamFmRDSRealTimeClock to hwDocsQamFmRDSTable.
                   "        
                            
            REVISION     "201608310000Z"
            DESCRIPTION  "V1.12, added hwDocsQamDVBDomainDefChannelOutputRate to hwDocsQamDVBDomainTable.
                   Added hwDocsQamDVBDomainChannelOutputRate to hwDocsQamDVBDomainChannelTable.
                   "
                        
            REVISION     "201608180000Z"
            DESCRIPTION  "V1.11, added hwDocsQamVideoMapProgramName to hwDocsQamVideoMapTable.                                          
                   Added hwDocsQamDVBDomainChannelOriginalNetworkID to hwDocsQamDVBDomainChannelTable.
                   Added hwDocsQamDVBInputTSPATErrors, hwDocsQamDVBInputTSPATMissings, hwDocsQamDVBInputTSPMTErrors, hwDocsQamDVBInputTSPMTMissings to hwDocsQamDVBInputTSStatisticsTable.
                   Added hwDocsQamInputPIDInfoTable, hwDocsQamInputTSPIDTable.
                   "                               
  
            REVISION     "201606280000Z"
            DESCRIPTION  "V1.10, added hwDocsQamInputTSEPGInput, hwDocsQamInputTSJitter and hwDocsQamInputTSRTPSequenceErrorCounter to hwDocsQamInputTSTable.              
                   Added hwDocsQamDVBDomainPSISIDefModeSDTA, hwDocsQamDVBDomainPSISIDefModeSDTO, hwDocsQamDVBDomainPSISIDefModeEITpfA,
                   hwDocsQamDVBDomainPSISIDefModeEITpfO, hwDocsQamDVBDomainPSISIDefModeEITsFirstA, hwDocsQamDVBDomainPSISIDefModeEITsFirstO,
                   hwDocsQamDVBDomainPSISIDefModeEITsSecondA, hwDocsQamDVBDomainPSISIDefModeEITsSecondO, hwDocsQamDVBDomainPSISIDefIntervalSDTA,
                   hwDocsQamDVBDomainPSISIDefIntervalSDTO, hwDocsQamDVBDomainPSISIDefIntervalPAT, hwDocsQamDVBDomainPSISIDefIntervalPMT,
                   hwDocsQamDVBDomainPSISIDefIntervalEITpfA, hwDocsQamDVBDomainPSISIDefIntervalEITpfO, hwDocsQamDVBDomainPSISIDefIntervalEITsFirstA,
                   hwDocsQamDVBDomainPSISIDefIntervalEITsFirstO, hwDocsQamDVBDomainPSISIDefIntervalEITsSecondA, hwDocsQamDVBDomainPSISIDefIntervalEITsSecondO,
                   and hwDocsQamDVBDomainPSISIDefSpeedEIT to hwDocsQamDVBDomainTable.
                   Added hwDocsQamInputTSProgramName to hwDocsQamInputTSProgramTable.
                   Added hwDocsQamOutputTSProgramName to hwDocsQamOutputTSProgramTable.
                   Added hwDocsQamDVBInputTSDiscontinuityCounter to hwDocsQamDVBInputTSStatisticsTable.
                   Added hwDocsQamDVBDomainChannelTable, hwDocsQamFMDomainTable, hwDocsQamFmMapTable, hwDocsQamFMPortConfigTable,
                   hwDocsQamFmRDSTable, hwDocsQamDVBPIDMappingTable.
                   Added three enumerated values remap(2), remapfirst(3) and remapall(4) in hwDocsQamVideoMapMode leaf node.
                   Modified description of hwDocsQamDVBInputTSStatisticsTable and hwDocsQamDVBInputTSStatisticsEntry.   
                   Added hwDocsQamInputTSRedundancyMode to hwDocsQamInputTSTable.              
                   Added hwDocsQamDVBProcessFrameSlot to hwDocsQamVideoGlobalConfigObject. 
                   Added hwDocsQamDVBProcessGroupTable.  
                   "
        
            REVISION     "201603150000Z"
            DESCRIPTION  "V1.09, added hwDocsQamNGODEdgeDevicelocalIfType and hwDocsQamNGODEdgeDevicelocalIfNumbe to hwDocsQamNGODEdgeDeviceTable.              
                         Added hwDocsQamGratuitousArpPeriodSendMode to hwDocsQamVideoGlobalConfigObject.             
                     "
    
            REVISION     "201602240000Z"
            DESCRIPTION  "V1.08, Modified description of hwDocsQamInputTSIndex.
                     Modified  description of hwDocsQamDVBDomainRowStatus.
                     Modified description of hwDocsQamVODPortConfigRowStatus.
                     Modified description of hwDocsQamDVBPortConfigRowStatus.              
                     "  
    
            REVISION     "201601280000Z"
            DESCRIPTION  "V1.07, Modified oid of hwDocsQamMulticastVlanId and hwDocsQamSecondaryMulticastVlanId.
                     Modified oid of hwDocsQamVideoMapMode, hwDocsQamVideoMapNITRemap, hwDocsQamVideoMapFilterPIDList and hwDocsQamVideoMapInputTsIndex.
                     Modified oid of hwDocsQamVideoDomainUDPPortStep and hwDocsQamVideoDomainBindVideoProfile.
                     Modified oid of hwDocsQamVideoStreamSourceIpAddressType, hwDocsQamVideoStreamSourceIpAddress and hwDocsQamVideoStreamDiscontinuityCounter.              
                     "
        
            REVISION     "201601040000Z"
            DESCRIPTION  "V1.06, deleted hwDocsQamAutoConfigMulticastVlanId of hwDocsQamVideoGlobalConfigObject, 
                     added hwDocsQamMulticastVlanId and hwDocsQamSecondaryMulticastVlanId to hwDocsQamVideoGlobalConfigObject.
             Deleted hwDocsQamVideoDomainMulticastVlanID of hwDocsQamVideoDomainTable, 
             added hwDocsQamVideoDomainBindVideoProfile and hwDocsQamVideoDomainUDPPortStep to hwDocsQamVideoDomainTable.
             Deleted hwDocsQamVideoMapMulticastIPAddrType and hwDocsQamVideoMapMulticastIPAddr of HwDocsQamVideoMapEntry, 
             added hwDocsQamVideoMapInputTsIndex to HwDocsQamVideoMapEntry.
             Deleted hwDocsQamVideoDomainBindTable.
             Deleted hwDocsQamVideoStreamConfigState, hwDocsQamVideoStreamMapMode, hwDocsQamVideoStreamProgramNum, 
             hwDocsQamVideoStreamNITRemap and hwDocsQamVideoStreamFilterPIDList of HwDocsQamVideoStreamEntry, 
             added hwDocsQamVideoStreamSourceIpAddressType, hwDocsQamVideoStreamSourceIpAddress and 
             hwDocsQamVideoStreamDiscontinuityCounter to HwDocsQamVideoStreamEntry.
             Modified name of hwDocsQamVideoInputStreamCountOfJitterOverrun to hwDocsQamVideoInputStreamCountOfJitterOverflow,
             Modified name of hwDocsQamVideoInputStreamCountOfJitterUnderrun to hwDocsQamVideoInputStreamCountOfJitterUnderflow.
             added hwDocsQamVideoInputTSDiscontinuityCounter to HwDocsQamVideoInputStreamStatisticsEntry.
                         Added hwDocsQamDVBDomainTable, hwDocsQamInputTSTable, hwDocsQamVODPortConfigTable, hwDocsQamDVBPortConfigTable, 
             hwDocsQamInputTSStateTable, hwDocsQamInputTSProgramTable, hwDocsQamOutputTSProgramTable, hwDocsQamDVBInputTSStatisticsTable,
             hwDocsQamNotificationObject, hwDocsQamDVBPATErrorTrap, hwDocsQamDVBPATMissingTrap, hwDocsQamDVBPMTErrorTrap,
             hwDocsQamDVBPMTMissingTrap and hwDocsQamDVBContinutyCounterErrorTrap.                         
                     "
                     
            REVISION     "201507070000Z"
            DESCRIPTION  "V1.05, added hwDocsQamAutoConfigMulticastVlanId to hwDocsQamVideoGlobalConfigObject.
                         Added hwDocsQamVideoMapMulticastIPAddrType, hwDocsQamVideoMapMulticastIPAddr, hwDocsQamVideoMapMode,
                         hwDocsQamVideoMapNITRemap and hwDocsQamVideoMapFilterPIDList to hwDocsQamVideoMapTable.
                         Modified description of hwDocsQamVideoMapUdpPort and hwDocsQamVideoMapPmtPid to hwDocsQamVideoMapTable.
                         Added hwDocsQamVideoDomainMulticastVlanID to hwDocsQamVideoDomainTable.
                         Added hwDocsQamVideoStreamConfigState, hwDocsQamVideoStreamMapMode, hwDocsQamVideoStreamProgramNum,
                         hwDocsQamVideoStreamNITRemap and hwDocsQamVideoStreamFilterPIDList to hwDocsQamVideoStreamTable.
                         Modified description of hwDocsQamVideoStreamDestinationUdpPort to hwDocsQamVideoStreamTable.
                         Added hwDocsQamVideoStreamMPTSProgramTable.
                     "
        
            REVISION     "201505270000Z"
            DESCRIPTION  "V1.04, Modified the SYNTAX of hwDocsQamNGODEdgeDeviceEdgeInputIfindex from InterfaceIndexOrZero to Unsigned32.
                     "
        
            REVISION     "201502170000Z"
            DESCRIPTION  "V1.03, added hwDocsQamNGODEdgeDeviceRecvNotificationErrPkts to hwDocsQamNGODEdgeDeviceStatisticsTable.
                     "
        
            REVISION     "201501220000Z"                                      
        DESCRIPTION  "V1.02, Added hwDocsQamNGODEdgeDeviceTable, hwDocsQamNGODEdgeDeviceEdgeInputTable, hwDocsQamNGODEdgeDeviceStatisticsTable and hwDocsQamChannelTable"
        
        REVISION     "201405280000Z"                                      
        DESCRIPTION  "V1.01, add the node hwDocsQamVideoStreamTraffic."
                
            REVISION     "201310100000Z"
            DESCRIPTION  "V1.00, initial version."         
        ::= { huaweiUtility 187 }
        
-- Textual Conventions

HwEqamPsiPolicyDvbDomain ::= TEXTUAL-CONVENTION
     STATUS      current
     DESCRIPTION
         "PSI/SI output policy for DVB domain.
          'stop' indicates PSI/SI output is disabled.
          'play' indicates PSI/SI will be enabled for playout.
         "
     SYNTAX      INTEGER 
           {
           stop(1),
           play(2)
           }
           
HwEqamPsiPolicyChannnel ::= TEXTUAL-CONVENTION
      STATUS      current
      DESCRIPTION
         "PSI/SI output policy for channel.
          'stop' indicates PSI/SI output is disabled.
          'play' indicates PSI/SI will be enabled for playout.
          'default' indicates the output policy inherits from the DVB domain.
         "
     SYNTAX      INTEGER 
           {
           stop(1),
           play(2),
           default(3)
           }  
                      
HwEqamInputPIDType ::= TEXTUAL-CONVENTION
     STATUS      current
     DESCRIPTION
         "Indicates the input PID type. 
         Options:
         pat(1)      --Program Association Table
         pmt(2)      --Program Map Table
         cat(3)      --Conditional Access Table
         nit(4)      --Network Information Table
         sdt(5)      --Service Description Table
         eit(6)      --Event Information Table
         tdttot(7)   --Time and Date Table/Time Offset Table
         ecm(8)      --Entitlement Control Message
         emm(9)      --Entitlement Management Message
         pcr(10)     --Program Clock Reference
         null(11)    --NULL
         media(12)   --Media
         unknown(255)--Unkonwn
         "                              
     SYNTAX      INTEGER 
           {
           pat(1),      
           pmt(2),               
           cat(3),      
           nit(4),      
           sdt(5),      
           eit(6),      
           tdttot(7),   
           ecm(8),      
           emm(9),      
           pcr(10),     
           null(11),    
           media(12),   
           unknown(255)
           }                  
--  Node definitions

        -- 1.3.6.1.4.1.2011.6.187.1
        hwDocsQamVideoGlobalConfigObject   OBJECT IDENTIFIER ::= { hwEqamAn 1 }
        
        -- 1.3.6.1.4.1.2011.6.187.1.1
        hwDocsQamVideoTimeOutInterval  OBJECT-TYPE
            SYNTAX      Integer32 (1..6000)
            UNITS       "second"
            MAX-ACCESS  read-write
            STATUS      current
            DESCRIPTION
                "Indicates the video timeout interval.
                 Default: 60
                "
            ::= { hwDocsQamVideoGlobalConfigObject 1 }

        -- 1.3.6.1.4.1.2011.6.187.1.2
        hwDocsQamAutoConfigIppoolAddressType  OBJECT-TYPE
            SYNTAX      InetAddressType
            MAX-ACCESS  read-write
            STATUS      current
            DESCRIPTION
                "Indicates the address type of the address pool. Only IPv4 addresses are supported.
                "
            ::= { hwDocsQamVideoGlobalConfigObject 2 }
                  
        -- 1.3.6.1.4.1.2011.6.187.1.3
        hwDocsQamAutoConfigIppoolStartAddress  OBJECT-TYPE
            SYNTAX      InetAddress
            MAX-ACCESS  read-write
            STATUS      current
            DESCRIPTION
                "Indicates the start address of the address pool. 
                 To delete an IP address pool, bind hwDocsQamAutoConfigIppoolStartAddress and hwDocsQamAutoConfigIppoolEndAddress together and set their values to 0xff 0xff 0xff 0xff.
                 The value of hwDocsQamAutoConfigIppoolStartAddress or hwDocsQamAutoConfigIppoolEndAddress must be set to a valid unicast IP address in other scenarios.
                "
            ::= { hwDocsQamVideoGlobalConfigObject 3 }
      
        -- 1.3.6.1.4.1.2011.6.187.1.4
        hwDocsQamAutoConfigIppoolEndAddress  OBJECT-TYPE
            SYNTAX      InetAddress
            MAX-ACCESS  read-write
            STATUS      current
            DESCRIPTION
                "Indicates the end address of the address pool.
                 To delete an IP address pool, bind hwDocsQamAutoConfigIppoolStartAddress and hwDocsQamAutoConfigIppoolEndAddress together and set their values to 0xff 0xff 0xff 0xff.
                 The value of hwDocsQamAutoConfigIppoolStartAddress or hwDocsQamAutoConfigIppoolEndAddress must be set to a valid unicast IP address in other scenarios.
                "
            ::= { hwDocsQamVideoGlobalConfigObject 4 }
      
        -- 1.3.6.1.4.1.2011.6.187.1.5
        hwDocsQamAutoConfigIppoolVlanId  OBJECT-TYPE
            SYNTAX      Integer32 (-1|1..4093)
            MAX-ACCESS  read-write
            STATUS      current
            DESCRIPTION
                "Indicates the VLAN ID of the video domain. The default value is -1, indicating that the VLAN ID is invalid.
                "
            ::= { hwDocsQamVideoGlobalConfigObject 5 }
      
        -- 1.3.6.1.4.1.2011.6.187.1.6
        hwDocsQamAutoConfigVideoProfile  OBJECT-TYPE
            SYNTAX      OCTET STRING (SIZE (0..15))
            MAX-ACCESS  read-write
            STATUS      current
            DESCRIPTION
                "Automatically pre-configures the name of the video profile.
                "
            ::= { hwDocsQamVideoGlobalConfigObject 6 }
            
        -- 1.3.6.1.4.1.2011.6.187.1.8
        hwDocsQamMulticastVlanId  OBJECT-TYPE
            SYNTAX      Integer32 (-1|1..4093)
            MAX-ACCESS  read-write
            STATUS      current
            DESCRIPTION
                "Indicates the multicast VLAN ID of the video service. The default value is -1, indicating that the multicast VLAN ID is invalid.
                "
            ::= { hwDocsQamVideoGlobalConfigObject 8 }
            
        -- 1.3.6.1.4.1.2011.6.187.1.9
        hwDocsQamSecondaryMulticastVlanId  OBJECT-TYPE
            SYNTAX      Integer32 (-1|1..4093)
            MAX-ACCESS  read-write
            STATUS      current
            DESCRIPTION
                "Indicates the secondary multicast VLAN ID. The default value is -1, indicating that the multicast VLAN ID is invalid.
                "
            ::= { hwDocsQamVideoGlobalConfigObject 9 }
            
        -- 1.3.6.1.4.1.2011.6.187.1.10
        hwDocsQamGratuitousArpPeriodSendMode  OBJECT-TYPE
            SYNTAX      INTEGER
                  {
                  enabled(1),
                  disabled(2)
                  }
            MAX-ACCESS  read-write
            STATUS      current
            DESCRIPTION
                "Indicates the gratuitous ARP period send mode, the default value is disabled(2).
                 Options: 
                 1. enabled(1)      -indicates the gratuitous ARP period send mode is enabled
                 2. disabled(2)     -indicates the gratuitous ARP period send mode is disabled
                "
            ::= { hwDocsQamVideoGlobalConfigObject 10 }  
            
         -- 1.3.6.1.4.1.2011.6.187.1.11
         hwDocsQamDVBProcessFrameSlot             OBJECT-TYPE
            SYNTAX       Unsigned32 (0..4294967295)
            MAX-ACCESS   read-write
            STATUS       current
            DESCRIPTION
              "Indicates the frame ID and slot ID of the DVB service processing board. 
               The most significant 16 bits indicate the frame ID while the least significant 16 bits indicate the slot ID. 
               The default value is 0xFFFFFFFF, indicating that no DVB service processing board is configured. 
              "
             ::= { hwDocsQamVideoGlobalConfigObject 11 } 
                         
         -- 1.3.6.1.4.1.2011.6.187.1.12
         hwDocsQamInputTSDefaultSwitchoverTriggers             OBJECT-TYPE
             SYNTAX     BITS
                  {
                  nobitrate(0),
                  nosignal(1),
                  patmissing(2),
                  pmtmissing(3)
                  }            
            MAX-ACCESS  read-write
            STATUS      current
            DESCRIPTION
                "Indicates the default trigger conditions for protection switching on input TSs. The format is 4 bits. 
                 A bit of this attribute is set to 1 if the parameter indicated by the comment was present in the protection switching, and to 0 otherwise. 
                 None of the trigger bit is set by default.
                 Bit 0 -indicates that the trigger condition is no-bitrate.
                 Bit 1 -indicates that the trigger condition is no-signal. 
                 Bit 2 -indicates that the trigger condition is pat-missing.
                 Bit 3 -indicates that the trigger condition is pmt-missing.
                "
             ::= { hwDocsQamVideoGlobalConfigObject 12 }  
             
             
         -- 1.3.6.1.4.1.2011.6.187.1.13
         hwDocsQamInputTSStatisticsClearAll             OBJECT-TYPE
             SYNTAX     INTEGER
                  {
                  clearStatistic(1)
                  }            
            MAX-ACCESS  read-write
            STATUS      current
            DESCRIPTION
                "Clears all the input TS statistics.
                 Options: 
                 1. clearStatistic(1)  -Clears all the input TS statistics
                 The default value is clearStatistic(1). 
                "
             ::= { hwDocsQamVideoGlobalConfigObject 13 }  
         
             -- 1.3.6.1.4.1.2011.6.187.1.14
         hwDocsQamVideoProgramNumberTotalGlobal         OBJECT-TYPE
             SYNTAX      Unsigned32(0..4294967295)      
             MAX-ACCESS  read-only
             STATUS      current
             DESCRIPTION
                "Indicates the number of global VOD programs. 
                "
             ::= { hwDocsQamVideoGlobalConfigObject 14 }  
             
         -- 1.3.6.1.4.1.2011.6.187.1.15
         hwDocsQamVideoProgramNumberOnlineGlobal         OBJECT-TYPE
             SYNTAX      Unsigned32(0..4294967295)      
             MAX-ACCESS  read-only
             STATUS      current
             DESCRIPTION
                "Indicates the number of global online VOD programs. 
                "
             ::= { hwDocsQamVideoGlobalConfigObject 15 }   
                            
         -- 1.3.6.1.4.1.2011.6.187.1.16
         hwDocsQamDVBChannelMonitoringProbeDuration             OBJECT-TYPE
            SYNTAX     Unsigned32 (60..120)     
            UNITS       "second"       
            MAX-ACCESS  read-write
            STATUS      current
            DESCRIPTION
                "Indicates the duration of DVB channel monitoring.
                 The default value is 60. 
                "
             ::= { hwDocsQamVideoGlobalConfigObject 16 } 
             
         -- 1.3.6.1.4.1.2011.6.187.1.17
         hwDocsQamDVBInputTsTimeOut             OBJECT-TYPE
            SYNTAX     Unsigned32 (5..60)     
            UNITS       "second"       
            MAX-ACCESS  read-write
            STATUS      current
            DESCRIPTION
                "Indicates the timeout interval of input TSs .
                 The default value is 5. 
                "
             ::= { hwDocsQamVideoGlobalConfigObject 17 }
             
        -- 1.3.6.1.4.1.2011.6.187.1.18
         hwDocsQamVideoFrequncyOffsetCorrectionFactor             OBJECT-TYPE
            SYNTAX     Integer32 (1..10)          
            MAX-ACCESS  read-write
            STATUS      current
            DESCRIPTION
                "Indicates the frequency offset correction factor.
                 The default value is 2. 
                "
             ::= { hwDocsQamVideoGlobalConfigObject 18 }  
                         
        -- 1.3.6.1.4.1.2011.6.187.1.19
         hwDocsQamVODProcessFrameSlot             OBJECT-TYPE
            SYNTAX       Unsigned32 (0..4294967295)
            MAX-ACCESS   read-write
            STATUS       current
            DESCRIPTION
              "Indicates the frame ID and slot ID of the VOD service processing board. 
               The most significant 16 bits indicate the frame ID while the least significant 16 bits indicate the slot ID. 
               The default value is 0xFFFFFFFF, indicating that no VOD service processing board is configured. 
              "
             ::= { hwDocsQamVideoGlobalConfigObject 19 } 
    
        -- 1.3.6.1.4.1.2011.6.187.2
        hwDocsQamVideoProfileTable    OBJECT-TYPE
            SYNTAX          SEQUENCE OF HwDocsQamVideoProfileEntry
            MAX-ACCESS      not-accessible
            STATUS          current
            DESCRIPTION
                "Indicates the video profile table used to manage information including video mapping.
                 The index of this table is hwDocsQamVideoProfileName.
                "
            ::= { hwEqamAn 2 }
    
        -- 1.3.6.1.4.1.2011.6.187.2.1
        hwDocsQamVideoProfileEntry    OBJECT-TYPE
            SYNTAX          HwDocsQamVideoProfileEntry
            MAX-ACCESS      not-accessible
            STATUS          current
            DESCRIPTION
                "Indicates the video profile table used to manage information including video mapping.
                 The index of this entry is hwDocsQamVideoProfileName.
                "
            INDEX   
                { 
                hwDocsQamVideoProfileName
                }
            ::= { hwDocsQamVideoProfileTable  1 }
        
        HwDocsQamVideoProfileEntry ::=
            SEQUENCE 
                { 
                hwDocsQamVideoProfileName
                  OCTET STRING,
                hwDocsQamVideoProfileRowStatus
                  RowStatus   
                }
        
        -- 1.3.6.1.4.1.2011.6.187.2.1.1   
        hwDocsQamVideoProfileName        OBJECT-TYPE
            SYNTAX       OCTET STRING (SIZE (1..15))
            MAX-ACCESS   not-accessible
            STATUS       current
            DESCRIPTION
              "Indicates the video profile name. 
              "
            ::= { hwDocsQamVideoProfileEntry 1}
          
        -- 1.3.6.1.4.1.2011.6.187.2.1.2 
        hwDocsQamVideoProfileRowStatus        OBJECT-TYPE
            SYNTAX       RowStatus
            MAX-ACCESS   read-create
            STATUS       current
            DESCRIPTION
                "Row status, used to query, create, modify, and delete a video profile table. 
                 It supports the active(1), createAndGo(4), and destroy(6) operations.
                 During query, the value of this leaf is always active(1).
                 During deletion, specify the value of this leaf to destroy(6).
                 During creation, specify the value of this leaf to createAndGo(4).
                 To modify the parameters of a video profile table, this leaf need not be issued together.
                 Options:
                 1. active(1)      -indicates the query operation
                 2. createAndGo(4) -indicates the creating operation
                 3. destroy(6)     -indicates the deleting operation
                "
            ::= { hwDocsQamVideoProfileEntry 2}
          
        -- 1.3.6.1.4.1.2011.6.187.3
        hwDocsQamVideoMapTable    OBJECT-TYPE
            SYNTAX          SEQUENCE OF HwDocsQamVideoMapEntry
            MAX-ACCESS      not-accessible
            STATUS          current
            DESCRIPTION
                "Indicates the video mapping table used to configure the mapping between video streams and cable channels.
                 The indexes of this table are hwDocsQamVideoProfileName and hwDocsQamVideoMapIndex.
                "
            ::= { hwEqamAn 3 }
    
        -- 1.3.6.1.4.1.2011.6.187.3.1
        hwDocsQamVideoMapEntry    OBJECT-TYPE
            SYNTAX          HwDocsQamVideoMapEntry
            MAX-ACCESS      not-accessible
            STATUS          current
            DESCRIPTION
                "Indicates the video mapping table used to configure the mapping between video streams and cable channels.
                 The indexes of this entry are hwDocsQamVideoProfileName and hwDocsQamVideoMapIndex.
                "
            INDEX   
                { 
                hwDocsQamVideoProfileName,
                hwDocsQamVideoMapIndex
                }
            ::= { hwDocsQamVideoMapTable  1 }
        
        HwDocsQamVideoMapEntry ::=
            SEQUENCE 
                { 
                hwDocsQamVideoMapIndex
                  Unsigned32,
                hwDocsQamVideoMapUdpPort
                  InetPortNumber,
                hwDocsQamVideoMapStreamType
                  INTEGER,
                hwDocsQamVideoMapInputProgram
                  Integer32,
                hwDocsQamVideoMapOutputProgram
                  Integer32,
                hwDocsQamVideoMapJitter
                  Integer32,
                hwDocsQamVideoMapPmtPid
                  Integer32,
                hwDocsQamVideoMapChannelList
                  ChannelList,
                hwDocsQamVideoMapRowStatus
                  RowStatus,
                hwDocsQamVideoMapMode
                  INTEGER,
                hwDocsQamVideoMapNITRemap
                  Integer32,
                hwDocsQamVideoMapFilterPIDList
                  OCTET STRING,
                hwDocsQamVideoMapInputTsIndex
                  Integer32, 
                hwDocsQamVideoMapProgramName
                  OCTET STRING,
                hwDocsQamVideoMapEnable
                  TruthValue,
                hwDocsQamVideoMapPIDKeepOriginal
                  TruthValue,
                hwDocsQamVideoMapScramblingRule
                  BITS
                }
        
        -- 1.3.6.1.4.1.2011.6.187.3.1.1   
        hwDocsQamVideoMapIndex        OBJECT-TYPE
            SYNTAX      Unsigned32 (1..65535|4294967295)
            MAX-ACCESS  not-accessible
            STATUS      current
            DESCRIPTION
                "Indicates the index of a video mapping table. 
                 You can also fill 4294967295 and the system will automatically allocate an index.
                "
            ::= { hwDocsQamVideoMapEntry 1 }
          
        -- 1.3.6.1.4.1.2011.6.187.3.1.2   
        hwDocsQamVideoMapUdpPort        OBJECT-TYPE
            SYNTAX      InetPortNumber
            MAX-ACCESS  read-create
            STATUS      current
            DESCRIPTION
                "Indicates the UDP port number. The default value is 0, indicating that the UDP port number is invalid.
                 Range: 0-65535
                "
            ::= { hwDocsQamVideoMapEntry 2 }
          
        -- 1.3.6.1.4.1.2011.6.187.3.1.3   
        hwDocsQamVideoMapStreamType        OBJECT-TYPE
            SYNTAX      INTEGER
                  {
                  data(1),
                  spts(2),
                  mpts(3),
                  plant(4)
                  }
            MAX-ACCESS  read-create
            STATUS      current
            DESCRIPTION
                "Indicates the program stream type.
                 Options: 
                 1. data(1)   -indicates the data type
                 2. spts(2)   -indicates the spts type
                 3. mpts(3)   -indicates the mpts type
                 4. plant(4)  -indicates the plant type
                "
            ::= { hwDocsQamVideoMapEntry 3 }
          
        -- 1.3.6.1.4.1.2011.6.187.3.1.4   
        hwDocsQamVideoMapInputProgram        OBJECT-TYPE
            SYNTAX      Integer32 (-1|1..65535)
            MAX-ACCESS  read-create
            STATUS      current
            DESCRIPTION
                "Indicates the program ID of the input stream. The default value is -1, indicating that the program ID is ignored.
                "
            ::= { hwDocsQamVideoMapEntry 4 }
          
        -- 1.3.6.1.4.1.2011.6.187.3.1.5   
        hwDocsQamVideoMapOutputProgram        OBJECT-TYPE
            SYNTAX      Integer32 (-1|1..65535)
            MAX-ACCESS  read-create
            STATUS      current
            DESCRIPTION
                "Indicates the program ID of the output stream. The default value is -1, indicating that the program ID is ignored.
                "
            ::= { hwDocsQamVideoMapEntry 5 }
          
        -- 1.3.6.1.4.1.2011.6.187.3.1.6   
        hwDocsQamVideoMapJitter        OBJECT-TYPE
            SYNTAX      Integer32 (-1|0..250)
            UNITS       "millisecond"
            MAX-ACCESS  read-create
            STATUS      current
            DESCRIPTION
                "Indicates the network jitter allowed. 
                 If hwDocsQamVideoMapStreamType is data or mpts, the default value is -1, indicating that network jitter is ignored.
                 If hwDocsQamVideoMapStreamType is spts, the default value is 100.
                "
            ::= { hwDocsQamVideoMapEntry 6 }
          
        -- 1.3.6.1.4.1.2011.6.187.3.1.7   
        hwDocsQamVideoMapPmtPid        OBJECT-TYPE
            SYNTAX      Integer32 (-1|32..8190)
            MAX-ACCESS  read-create
            STATUS      current
            DESCRIPTION
                "Indicates the PMT PID of the output program.
                 If hwDocsQamVideoMapStreamType is data or hwDocsQamVideoMapStreamType is mpts and hwDocsQamVideoMapMode is passthrough, 
                 the default value is -1, indicating that output programs' PMT PIDs are ignored;
                 if hwDocsQamVideoMapStreamType is spts or hwDocsQamVideoMapStreamType is mpts and hwDocsQamVideoMapMode is not passthrough,
                 when the user does not specify the pmt pid, the system will automatically allocate one.
                "
            ::= { hwDocsQamVideoMapEntry 7 }
          
        -- 1.3.6.1.4.1.2011.6.187.3.1.8   
        hwDocsQamVideoMapChannelList        OBJECT-TYPE
            SYNTAX      ChannelList
            MAX-ACCESS  read-create
            STATUS      current
            DESCRIPTION
                "Indicates the channel list for output videos.
                "
            ::= { hwDocsQamVideoMapEntry 8 }
            
        -- 1.3.6.1.4.1.2011.6.187.3.1.9
        hwDocsQamVideoMapRowStatus        OBJECT-TYPE
            SYNTAX       RowStatus
            MAX-ACCESS   read-create
            STATUS       current
            DESCRIPTION
                "Row status, used to query, create, modify, and delete a video mapping table. 
                 It supports the active(1), createAndGo(4), and destroy(6) operations.
                 During query, the value of this leaf is always active(1).
                 During deletion, specify the value of this leaf to destroy(6).
                 During creation, specify the value of this leaf to createAndGo(4).
                 To modify the parameters of a video mapping table, this leaf need not be issued together.
                 Options:
                 1. active(1)      -indicates the query operation
                 2. createAndGo(4) -indicates the creating operation
                 3. destroy(6)     -indicates the deleting operation
                "
            ::= { hwDocsQamVideoMapEntry 9}
            
        -- 1.3.6.1.4.1.2011.6.187.3.1.12  
        hwDocsQamVideoMapMode        OBJECT-TYPE
            SYNTAX      INTEGER
                  {
                  passthrough(1),
                  remap(2),
                  remapfirst(3),
                  remapall(4),
                  invalid(255)
                  }
            MAX-ACCESS  read-create
            STATUS      current
            DESCRIPTION
                "Indicates the video stream map mode, the default value is invalid(255).
                 Options: 
                 1. passthrough(1) -indicates the MPTS video stream mode is passthrough. When video stream is configured to this mode, 
                                    all programs from the input TS will transparently forward to the output without any modifications.
                 2. remap(2)       -indicates the MPTS video stream mode is remap. When video stream configured to this mode, 
                                    only one specified program from the input TS will be remap to the output with the specified program id and program name.
                 3. remapfirst(3)  -indicates the MPTS video stream mode is remapfirst. When video stream configured to this mode,
                                    only the first learned program from the input TS will be remap to the output automatically
                                    without any modifications of program id or program name.
                 4. remapall(4)    -indicates the MPTS video stream mode is remapall. When video stream configured to this mode,
                                    all learned programs from the input TS will be remap to the output automatically 
                                    without any modifications of program id or program name.
                 5. invalid(255)   -indicates the video stream mode is ignored if hwDocsQamVideoMapStreamType is not mpts.                 "
            ::= { hwDocsQamVideoMapEntry 12 }
            
        -- 1.3.6.1.4.1.2011.6.187.3.1.13   
        hwDocsQamVideoMapNITRemap        OBJECT-TYPE
            SYNTAX      Integer32 (-1 | 16 | 32..8190)
            MAX-ACCESS  read-create
            STATUS      current
            DESCRIPTION
                "Indicates the output NIT PID which the input NIT PID mapped to. 
                 If hwDocsQamVideoMapStreamType is not mpts, the default value is always -1, indicating that the NIT remap PID is ignored.
                 If hwDocsQamVideoMapStreamType is mpts, vlaue -1 means cancel the NIT remap.
                "
            ::= { hwDocsQamVideoMapEntry 13 }
            
        -- 1.3.6.1.4.1.2011.6.187.3.1.14   
        hwDocsQamVideoMapFilterPIDList        OBJECT-TYPE
            SYNTAX      OCTET STRING (SIZE (0..64))
            MAX-ACCESS  read-create
            STATUS      current
            DESCRIPTION
                "Indicates the filter PID list which are not allowed to forward.
                 Filter PID consists of two bytes and no greater than 8190. 
                 Max of 32 filter PIDs can be configured for each video mapping.
                 If hwDocsQamVideoMapStreamType is not mpts, the default value is always null string, indicating that the filter PID is ignored. 
                 If hwDocsQamVideoMapStreamType is mpts, the default value null string means cancel the PID filter.
                "
            ::= { hwDocsQamVideoMapEntry 14 }

        -- 1.3.6.1.4.1.2011.6.187.3.1.15
        hwDocsQamVideoMapInputTsIndex   OBJECT-TYPE
            SYNTAX       Integer32 (-1|1..65535)
            MAX-ACCESS   read-create
            STATUS       current
            DESCRIPTION
                "Indicates the index of the transport stream, the default value is -1, indicating that the index of the transport stream is ignored.
                "
            ::= { hwDocsQamVideoMapEntry 15}
                        
        -- 1.3.6.1.4.1.2011.6.187.3.1.16
        hwDocsQamVideoMapProgramName   OBJECT-TYPE
            SYNTAX       OCTET STRING (SIZE (0..63))
            MAX-ACCESS   read-create
            STATUS       current
            DESCRIPTION
                "Indicates the name of an output program in video mapping. 
                The default value is a null string, which indicates that the name of the input program is inherited.
                "
            ::= { hwDocsQamVideoMapEntry 16} 
            
        -- 1.3.6.1.4.1.2011.6.187.3.1.17
        hwDocsQamVideoMapEnable   OBJECT-TYPE
            SYNTAX       TruthValue
            MAX-ACCESS   read-create
            STATUS       current
            DESCRIPTION
                "Indicates the enabling status of video mapping. If hwDocsQamVideoMapStreamType is mpts, this value can be set to true or false; 
                if hwDocsQamVideoMapStreamType is not mpts, this value can be set to only true.
                The default value is true(1)."
            ::= { hwDocsQamVideoMapEntry 17} 
             
         -- 1.3.6.1.4.1.2011.6.187.3.1.18
         hwDocsQamVideoMapPIDKeepOriginal   OBJECT-TYPE
            SYNTAX       TruthValue
            MAX-ACCESS   read-create
            STATUS       current
            DESCRIPTION
                "Indicates the keeping program PID original of video mapping. If hwDocsQamVideoMapMode is remap, this value can be set to true or false; 
                if hwDocsQamVideoMapMode is not remap, this value can be set to only false.
                The default value is false(2)."
            ::= { hwDocsQamVideoMapEntry 18}
                        
         -- 1.3.6.1.4.1.2011.6.187.3.1.19
         hwDocsQamVideoMapScramblingRule        OBJECT-TYPE
            SYNTAX      BITS
                  {
                  reserved(0),
                  other(1),
                  video(2),
                  audio(3)
                  }            
            MAX-ACCESS  read-create
            STATUS      current
            DESCRIPTION
                "Indicates the scrambling rule of video mapping.
                 reserved 0 - reserved.
                 other 1 - other scrambling rule. 
                 video 2 - video scrambling rule. 
                 audio 3 - audio scrambling rule. 
                "
            ::= { hwDocsQamVideoMapEntry 19 }                    
  
        -- 1.3.6.1.4.1.2011.6.187.4
        hwDocsQamVideoDomainTable    OBJECT-TYPE
            SYNTAX          SEQUENCE OF HwDocsQamVideoDomainEntry
            MAX-ACCESS      not-accessible
            STATUS          current
            DESCRIPTION
                "Indicates the video domain table used to manage information, such as EQAM's IP address.
                 The index of this table is hwDocsQamVideoDomainName.
                "
            ::= { hwEqamAn 4 }
        
        -- 1.3.6.1.4.1.2011.6.187.4.1
        hwDocsQamVideoDomainEntry    OBJECT-TYPE
            SYNTAX          HwDocsQamVideoDomainEntry
            MAX-ACCESS      not-accessible
            STATUS          current
            DESCRIPTION
                "Indicates the video domain table used to manage information, such as EQAM's IP address.
                 The index of this entry is hwDocsQamVideoDomainName.
                "
            INDEX   
                { 
                hwDocsQamVideoDomainName
                }
            ::= { hwDocsQamVideoDomainTable  1 }
            
        HwDocsQamVideoDomainEntry ::=
            SEQUENCE 
                { 
                hwDocsQamVideoDomainName
                  OCTET STRING,
                hwDocsQamVideoDomainLocalIpAddress
                  InetAddress,
                hwDocsQamVideoDomainLocalIpAddressType
                  InetAddressType,
                hwDocsQamVideoDomainLocalVlanID
                  Integer32,
                hwDocsQamVideoDomainRowStatus
                  RowStatus,
                hwDocsQamVideoDomainUDPPortStep
                  Unsigned32,
                hwDocsQamVideoDomainBindVideoProfile
                  OCTET STRING,
                hwDocsQamVideoDomainReservedPID
                  OCTET STRING,
                hwDocsQamVideoDomainLocalInterfaceLoopbackNumber
                  Unsigned32
                }
            
        -- 1.3.6.1.4.1.2011.6.187.4.1.1   
        hwDocsQamVideoDomainName        OBJECT-TYPE
            SYNTAX       OCTET STRING (SIZE (1..15))
            MAX-ACCESS   not-accessible
            STATUS       current
            DESCRIPTION
              "Indicates the video domain name.
              "
            ::= { hwDocsQamVideoDomainEntry 1 }
          
        -- 1.3.6.1.4.1.2011.6.187.4.1.2   
        hwDocsQamVideoDomainLocalIpAddress        OBJECT-TYPE
            SYNTAX       InetAddress
            MAX-ACCESS   read-create
            STATUS       current
            DESCRIPTION
              "Indicates the local IP address of the video domain.
              "
            ::= { hwDocsQamVideoDomainEntry 2 }
          
        -- 1.3.6.1.4.1.2011.6.187.4.1.3   
        hwDocsQamVideoDomainLocalIpAddressType        OBJECT-TYPE
            SYNTAX       InetAddressType
            MAX-ACCESS   read-create
            STATUS       current
            DESCRIPTION
              "Indicates the local IP address type of the local end.
              "
            ::= { hwDocsQamVideoDomainEntry 3 }
          
        -- 1.3.6.1.4.1.2011.6.187.4.1.4   
        hwDocsQamVideoDomainLocalVlanID        OBJECT-TYPE
            SYNTAX       Integer32 (-1|1..4093)
            MAX-ACCESS   read-create
            STATUS       current
            DESCRIPTION
              "Indicates the local VLAN ID of the video domain. The default value is -1, indicating that the local VLAN ID is invalid.
              "
            ::= { hwDocsQamVideoDomainEntry 4 }
          
        -- 1.3.6.1.4.1.2011.6.187.4.1.5 
        hwDocsQamVideoDomainRowStatus        OBJECT-TYPE
            SYNTAX       RowStatus
            MAX-ACCESS   read-create
            STATUS       current
            DESCRIPTION
                "Row status, used to query, create, modify, and delete a video domain table. 
                 It supports the active(1), createAndGo(4), and destroy(6) operations.
                 During query, the value of this leaf is always active(1).
                 During deletion, specify the value of this leaf to destroy(6).
                 During creation, specify the value of this leaf to createAndGo(4).
                 To modify the parameters of a video domain table, this leaf need not be issued together.
                 Options:
                 1. active(1)      -indicates the query operation
                 2. createAndGo(4) -indicates the creating operation
                 3. destroy(6)     -indicates the deleting operation
                "
            ::= { hwDocsQamVideoDomainEntry 5 }
            
        -- 1.3.6.1.4.1.2011.6.187.4.1.7   
        hwDocsQamVideoDomainUDPPortStep        OBJECT-TYPE
            SYNTAX       Unsigned32(1..10000)
            MAX-ACCESS   read-create
            STATUS       current
            DESCRIPTION
              "Indicates the step of udp port. The default value is 512.
              "
            ::= { hwDocsQamVideoDomainEntry 7 }

        -- 1.3.6.1.4.1.2011.6.187.4.1.8   
        hwDocsQamVideoDomainBindVideoProfile        OBJECT-TYPE
            SYNTAX       OCTET STRING (SIZE (0..15))
            MAX-ACCESS   read-create
            STATUS       current
            DESCRIPTION
              "Indicates the bind video profile name.
              "
            ::= { hwDocsQamVideoDomainEntry 8 }
                        
        -- 1.3.6.1.4.1.2011.6.187.4.1.9   
        hwDocsQamVideoDomainReservedPID        OBJECT-TYPE
            SYNTAX       OCTET STRING (SIZE (0..8))
            MAX-ACCESS   read-create
            STATUS       current
            DESCRIPTION
              "Indicates the reserved pid of video domain.
			  For the reserved PID, you can enter 1 or 2 ranges, and specify a 2-byte minimum value and a 2-byte maximum value for each range.
			  For example, value 0x00 0x20 0x00 0x30 0x00 0x90 0x00 0xF0 indicates that 2 ranges ( range 32-48 and range 144-240 ) are configured.
			  For another example, value 0x01 0x10 0x01 0x20 indicates that the reserved PID range is configured as 272-288.
			  The default value is a null string, indicating that the reserved PID is not configured.
			  "
            ::= { hwDocsQamVideoDomainEntry 9 }
			
        -- 1.3.6.1.4.1.2011.6.187.4.1.10
        hwDocsQamVideoDomainLocalInterfaceLoopbackNumber        OBJECT-TYPE
            SYNTAX      Unsigned32 (0..31|4294967295)
            MAX-ACCESS  read-create
            STATUS      current
            DESCRIPTION
                "Indicates the local Loopback Interface of the video domain. The default value is 4294967295.
                "
            DEFVAL { 4294967295 }
            ::= { hwDocsQamVideoDomainEntry 10 }
            
        -- 1.3.6.1.4.1.2011.6.187.6
        hwDocsQamChannelProfileTable    OBJECT-TYPE
            SYNTAX          SEQUENCE OF HwDocsQamChannelProfileEntry
            MAX-ACCESS      not-accessible
            STATUS          current
            DESCRIPTION
                "Indicates the EQAM channel profile table used for managing parameters related to channels.
                 The index of this table is hwDocsQamChannelProfileName.
                "
            ::= { hwEqamAn 6 }
    
        -- 1.3.6.1.4.1.2011.6.187.6.1
        hwDocsQamChannelProfileEntry    OBJECT-TYPE
            SYNTAX          HwDocsQamChannelProfileEntry
            MAX-ACCESS      not-accessible
            STATUS          current
            DESCRIPTION
                "Indicates the EQAM channel profile table used for managing parameters related to channels.
                 The index of this entry is hwDocsQamChannelProfileName.
                "
            INDEX   
                { 
                hwDocsQamChannelProfileName
                }
            ::= { hwDocsQamChannelProfileTable  1 }
        
        HwDocsQamChannelProfileEntry ::=
            SEQUENCE 
                { 
                hwDocsQamChannelProfileName
                  OCTET STRING,
                hwDocsQamChannelProfileTransportStreamID
                  Integer32,
                hwDocsQamChannelProfilePATSendPeriod
                  Integer32,
                hwDocsQamChannelProfilePMTSendPeriod
                  Integer32,
                hwDocsQamChannelProfileRowStatus
                  RowStatus,
                hwDocsQamChannelProfileRate
                  Unsigned32  
                }
        
        -- 1.3.6.1.4.1.2011.6.187.6.1.1   
        hwDocsQamChannelProfileName        OBJECT-TYPE
            SYNTAX       OCTET STRING (SIZE (1..15))
            MAX-ACCESS   not-accessible
            STATUS       current
            DESCRIPTION
              "Indicates the name of the channel profile table.
              "
            ::= { hwDocsQamChannelProfileEntry 1 }
      
        -- 1.3.6.1.4.1.2011.6.187.6.1.2
        hwDocsQamChannelProfileTransportStreamID        OBJECT-TYPE
            SYNTAX      Integer32 (0..65535)
            MAX-ACCESS  read-create
            STATUS      current
            DESCRIPTION
                "Indicates the transport stream ID.
                "
            DEFVAL { 0 }
            ::= { hwDocsQamChannelProfileEntry 2 }
          
        -- 1.3.6.1.4.1.2011.6.187.6.1.3
        hwDocsQamChannelProfilePATSendPeriod        OBJECT-TYPE
            SYNTAX      Integer32 (30..1000)
            UNITS       "millisecond"
            MAX-ACCESS  read-create
            STATUS      current
            DESCRIPTION
                "Indicates the PAT send interval.
                "
            DEFVAL { 100 }
            ::= { hwDocsQamChannelProfileEntry 3 }
      
        -- 1.3.6.1.4.1.2011.6.187.6.1.4
        hwDocsQamChannelProfilePMTSendPeriod        OBJECT-TYPE
            SYNTAX      Integer32 (30..1000)
            UNITS       "millisecond"
            MAX-ACCESS  read-create
            STATUS      current
            DESCRIPTION
                "Indicates the PMT send interval.
                "
            DEFVAL { 100 }
            ::= { hwDocsQamChannelProfileEntry 4 }
      
        -- 1.3.6.1.4.1.2011.6.187.6.1.5 
        hwDocsQamChannelProfileRowStatus        OBJECT-TYPE
            SYNTAX       RowStatus
            MAX-ACCESS   read-create
            STATUS       current
            DESCRIPTION
                "Row status, used to query, create, modify, and delete a channel profile table. 
                 It supports the active(1), createAndGo(4), and destroy(6) operations.
                 During query, the value of this leaf is always active(1).
                 During deletion, specify the value of this leaf to destroy(6).
                 During creation, specify the value of this leaf to createAndGo(4).
                 To modify the parameters of a channel profile table, this leaf need not be issued together.
                 Options:
                 1. active(1)      -indicates the query operation
                 2. createAndGo(4) -indicates the creating operation
                 3. destroy(6)     -indicates the deleting operation
                "
            ::= { hwDocsQamChannelProfileEntry 5 }
                        
        -- 1.3.6.1.4.1.2011.6.187.6.1.6
        hwDocsQamChannelProfileRate        OBJECT-TYPE
            SYNTAX       Unsigned32(0..10000000)
            MAX-ACCESS   read-create
            STATUS       current
            DESCRIPTION
              "Indicates the rate of channel. The default value is 38015kbps.
              "
            DEFVAL { 38015 }
            ::= { hwDocsQamChannelProfileEntry 6 }
      
        -- 1.3.6.1.4.1.2011.6.187.7
        hwDocsQamDChannelBindTable    OBJECT-TYPE
            SYNTAX          SEQUENCE OF HwDocsQamDChannelBindEntry
            MAX-ACCESS      not-accessible
            STATUS          current
            DESCRIPTION
                "Indicates the EQAM channel binding table used for managing binding relationships between channel profiles and channel IDs.
                 The index of this table is ifIndex.
                "
            ::= { hwEqamAn 7 }
    
        -- 1.3.6.1.4.1.2011.6.187.7.1
        hwDocsQamDChannelBindEntry    OBJECT-TYPE
            SYNTAX          HwDocsQamDChannelBindEntry
            MAX-ACCESS      not-accessible
            STATUS          current
            DESCRIPTION
                "Indicates the EQAM channel binding table used for managing binding relationships between channel profiles and channel IDs.
                 The index of this entry is ifIndex.
                "
            INDEX   
                { 
                ifIndex
                }
            ::= { hwDocsQamDChannelBindTable  1 }
        
        HwDocsQamDChannelBindEntry ::=
            SEQUENCE 
                { 
                hwDocsQamDChannelBindProfileName
                  OCTET STRING
                }
        
        -- 1.3.6.1.4.1.2011.6.187.7.1.1   
        hwDocsQamDChannelBindProfileName        OBJECT-TYPE
            SYNTAX       OCTET STRING (SIZE (0..15))
            MAX-ACCESS   read-create
            STATUS       current
            DESCRIPTION
              "Indicates the channel profile name. hwDocsQamChannelProfileTable is a reference for setting parameters in the profile.
              "
            ::= { hwDocsQamDChannelBindEntry 1 }
                
        -- 1.3.6.1.4.1.2011.6.187.8
        hwDocsQamVideoStreamTable    OBJECT-TYPE
            SYNTAX          SEQUENCE OF HwDocsQamVideoStreamEntry
            MAX-ACCESS      not-accessible
            STATUS          current
            DESCRIPTION
                "Indicates the dynamic video stream information table used for obtaining dynamic video stream information.
                 The indexes of this table are ifIndex and hwDocsQamVideoStreamIndex.
                "
            ::= { hwEqamAn 8 }
    
        -- 1.3.6.1.4.1.2011.6.187.8.1
        hwDocsQamVideoStreamEntry    OBJECT-TYPE
            SYNTAX          HwDocsQamVideoStreamEntry
            MAX-ACCESS      not-accessible
            STATUS          current
            DESCRIPTION
                "Indicates the dynamic video stream information table used for obtaining dynamic video stream information.
                 The indexes of this entry are ifIndex and hwDocsQamVideoStreamIndex.
                "
            INDEX
                { 
                ifIndex,
                hwDocsQamVideoStreamIndex
                }
            ::= { hwDocsQamVideoStreamTable  1 }
        
        HwDocsQamVideoStreamEntry ::=
            SEQUENCE 
                { 
                hwDocsQamVideoStreamIndex
                  Unsigned32,
                hwDocsQamVideoStreamDestinationIpAddress
                  InetAddress,
                hwDocsQamVideoStreamDestinationIpAddressType
                  InetAddressType,
                hwDocsQamVideoStreamDestinationUdpPort
                  InetPortNumber,
                hwDocsQamVideoStreamType
                  INTEGER,
                hwDocsQamVideoStreamJitter
                  Integer32,
                hwDocsQamVideoStreamState
                  INTEGER,
                hwDocsQamVideoStreamInputStreamID
                  Integer32,
                hwDocsQamVideoStreamInputProgram
                  Integer32,
                hwDocsQamVideoStreamInputPMTPID
                  Integer32,
                hwDocsQamVideoStreamInputPCRPID
                  Integer32,
                hwDocsQamVideoStreamOutputStreamID
                  Integer32,
                hwDocsQamVideoStreamOutputProgram
                  Integer32,
                hwDocsQamVideoStreamOutputPMTPID
                  Integer32,
                hwDocsQamVideoStreamOutputPCRPID
                  Integer32,
                hwDocsQamVideoStreamInputESPIDList
                  OCTET STRING,
                hwDocsQamVideoStreamOutputESPIDList
                  OCTET STRING,
                hwDocsQamVideoStreamESTypeList
                  OCTET STRING,
                hwDocsQamVideoStreamChannelList
                  ChannelList,
                hwDocsQamVideoStreamTraffic
                  Unsigned32,   
                hwDocsQamVideoStreamSourceIpAddressType
                  InetAddressType,
                hwDocsQamVideoStreamSourceIpAddress
                  InetAddress,
                hwDocsQamVideoStreamDiscontinuityCounter
                  Counter64,
                hwDocsQamVideoStreamSrambled
                  TruthValue,
                hwDocsQamVideoStreamESSrambleStateList
                  OCTET STRING,
				hwDocsQamVideoStreamOutputESSrambleStateList
                  OCTET STRING
                }
        
        -- 1.3.6.1.4.1.2011.6.187.8.1.1   
        hwDocsQamVideoStreamIndex        OBJECT-TYPE
            SYNTAX      Unsigned32 (1..65535)
            MAX-ACCESS  not-accessible
            STATUS      current
            DESCRIPTION
                "Indicates the index of a dynamic video stream information table.
                "
            ::= { hwDocsQamVideoStreamEntry 1 }
          
        -- 1.3.6.1.4.1.2011.6.187.8.1.2   
        hwDocsQamVideoStreamDestinationIpAddress        OBJECT-TYPE
            SYNTAX      InetAddress
            MAX-ACCESS  read-only
            STATUS      current
            DESCRIPTION
                "Indicates the destination IP address.
                "
            ::= { hwDocsQamVideoStreamEntry 2 }
          
        -- 1.3.6.1.4.1.2011.6.187.8.1.3   
        hwDocsQamVideoStreamDestinationIpAddressType        OBJECT-TYPE
            SYNTAX      InetAddressType
            MAX-ACCESS  read-only
            STATUS      current
            DESCRIPTION
                "Indicates the destination IP address type.
                "
            ::= { hwDocsQamVideoStreamEntry 3 }
          
        -- 1.3.6.1.4.1.2011.6.187.8.1.4   
        hwDocsQamVideoStreamDestinationUdpPort        OBJECT-TYPE
            SYNTAX      InetPortNumber
            MAX-ACCESS  read-only
            STATUS      current
            DESCRIPTION
                "Indicates the destination UDP port number. The default value is 0, indicating that the UDP port number is invalid.
                 Range: 0-65535
                "
            ::= { hwDocsQamVideoStreamEntry 4 }
          
        -- 1.3.6.1.4.1.2011.6.187.8.1.5   
        hwDocsQamVideoStreamType        OBJECT-TYPE
            SYNTAX      INTEGER
                  {
                  data(1),
                  spts(2),
                  mpts(3),
                  plant(4)
                  }
            MAX-ACCESS  read-only
            STATUS      current
            DESCRIPTION
                "Indicates the data flow type.
                 Options: 
                 1. data(1)   -indicates the data type
                 2. spts(2)   -indicates the spts type
                 3. mpts(3)   -indicates the mpts type
                 4. plant(4)  -indicates the plant type
                "
            ::= { hwDocsQamVideoStreamEntry 5 }
          
        -- 1.3.6.1.4.1.2011.6.187.8.1.6   
        hwDocsQamVideoStreamJitter        OBJECT-TYPE
            SYNTAX      Integer32 (-1|0..250)
            UNITS       "millisecond"
            MAX-ACCESS  read-only
            STATUS      current
            DESCRIPTION
                "Indicates the network jitter allowed.
                 If the current video stream is not supported, -1 is returned.
                "
            ::= { hwDocsQamVideoStreamEntry 6 }
          
        -- 1.3.6.1.4.1.2011.6.187.8.1.7   
        hwDocsQamVideoStreamState        OBJECT-TYPE
            SYNTAX      INTEGER
                  {
                  offline(1),
                  online(2),
                  unknown(3)
                  }
            MAX-ACCESS  read-only
            STATUS      current
            DESCRIPTION
                "Indicates the video stream status.
                 Options: 
                 1. offline(1)   -indicates the offline state
                 2. online(2)    -indicates the online state
                 3. unknown(3)   -indicates the unknown state
                "
            ::= { hwDocsQamVideoStreamEntry 7 }
          
        -- 1.3.6.1.4.1.2011.6.187.8.1.8   
        hwDocsQamVideoStreamInputStreamID        OBJECT-TYPE
            SYNTAX      Integer32 (-1|0..65535)
            MAX-ACCESS  read-only
            STATUS      current
            DESCRIPTION
                "Indicates the input transport stream ID, the value -1 indicates that the input transport stream ID is invalid.
                "
            ::= { hwDocsQamVideoStreamEntry 8 }
          
        -- 1.3.6.1.4.1.2011.6.187.8.1.9   
        hwDocsQamVideoStreamInputProgram        OBJECT-TYPE
            SYNTAX      Integer32 (-1|0..65535)
            MAX-ACCESS  read-only
            STATUS      current
            DESCRIPTION
                "Indicates the input program ID, the value -1 indicates that the input program ID is invalid.
                "
            ::= { hwDocsQamVideoStreamEntry 9 }
          
        -- 1.3.6.1.4.1.2011.6.187.8.1.10    
        hwDocsQamVideoStreamInputPMTPID        OBJECT-TYPE
            SYNTAX      Integer32 (-1|0..8191)
            MAX-ACCESS  read-only
            STATUS      current
            DESCRIPTION
                "Indicates the input PMT PID, the value -1 indicates that the input PMT PID is invalid.
                "
            ::= { hwDocsQamVideoStreamEntry 10 }
          
        -- 1.3.6.1.4.1.2011.6.187.8.1.11    
        hwDocsQamVideoStreamInputPCRPID        OBJECT-TYPE
            SYNTAX      Integer32 (-1|0..8191)
            MAX-ACCESS  read-only
            STATUS      current
            DESCRIPTION
                "Indicates the input PCR PID, the value -1 indicates that the input PCR PID is invalid.
                "
            ::= { hwDocsQamVideoStreamEntry 11 }
          
        -- 1.3.6.1.4.1.2011.6.187.8.1.12    
        hwDocsQamVideoStreamOutputStreamID        OBJECT-TYPE
            SYNTAX      Integer32 (-1|0..65535)
            MAX-ACCESS  read-only
            STATUS      current
            DESCRIPTION
                "Indicates the output transport stream ID, the value -1 indicates that the output transport stream ID is invalid.
                "
            ::= { hwDocsQamVideoStreamEntry 12 }
          
        -- 1.3.6.1.4.1.2011.6.187.8.1.13    
        hwDocsQamVideoStreamOutputProgram        OBJECT-TYPE
            SYNTAX      Integer32 (-1|0..65535)
            MAX-ACCESS  read-only
            STATUS      current
            DESCRIPTION
                "Indicates the program ID of the output stream, the value -1 indicates that the program ID of the output stream is invalid.
                "
            ::= { hwDocsQamVideoStreamEntry 13 }
            
        -- 1.3.6.1.4.1.2011.6.187.8.1.14    
        hwDocsQamVideoStreamOutputPMTPID        OBJECT-TYPE
            SYNTAX      Integer32 (-1|0..8191)
            MAX-ACCESS  read-only
            STATUS      current
            DESCRIPTION
                "Indicates the PMT PID of the output stream, the value -1 indicates that the PMT PID of the output stream is invalid.
                "
            ::= { hwDocsQamVideoStreamEntry 14 }
          
        -- 1.3.6.1.4.1.2011.6.187.8.1.15    
        hwDocsQamVideoStreamOutputPCRPID        OBJECT-TYPE
            SYNTAX      Integer32 (-1|0..8191)
            MAX-ACCESS  read-only
            STATUS      current
            DESCRIPTION
                "Indicates the PCR PID of the output stream, the value -1 indicates that the PCR PID of the output stream is invalid.
                "
            ::= { hwDocsQamVideoStreamEntry 15 }
          
        -- 1.3.6.1.4.1.2011.6.187.8.1.16
        hwDocsQamVideoStreamInputESPIDList        OBJECT-TYPE
            SYNTAX       OCTET STRING (SIZE (0..128))
            MAX-ACCESS   read-only
            STATUS       current
            DESCRIPTION
              "Indicates the ESPID list for input streams. PID consists of two bytes and must be in one-to-one mapping with ESTypeList.
              "
            ::= { hwDocsQamVideoStreamEntry 16 }
          
        -- 1.3.6.1.4.1.2011.6.187.8.1.17
        hwDocsQamVideoStreamOutputESPIDList        OBJECT-TYPE
            SYNTAX       OCTET STRING (SIZE (0..128))
            MAX-ACCESS   read-only
            STATUS       current
            DESCRIPTION
              "Indicates the ESPID list for output streams. PID consists of two bytes and must be in one-to-one mapping with ESTypeList.
              "
            ::= { hwDocsQamVideoStreamEntry 17 }
          
        -- 1.3.6.1.4.1.2011.6.187.8.1.18
        hwDocsQamVideoStreamESTypeList        OBJECT-TYPE
            SYNTAX       OCTET STRING (SIZE (0..64))
            MAX-ACCESS   read-only
            STATUS       current
            DESCRIPTION
              "Indicate the ES type list. One byte indicates a type, which must be in one-to-one mapping with the ESPID list for input or output streams.
              "
            ::= { hwDocsQamVideoStreamEntry 18 }
        
        -- 1.3.6.1.4.1.2011.6.187.8.1.19
        hwDocsQamVideoStreamChannelList        OBJECT-TYPE
            SYNTAX       ChannelList
            MAX-ACCESS   read-only
            STATUS       current
            DESCRIPTION
              "Indicates the output channel list.
              "
            ::= { hwDocsQamVideoStreamEntry 19 }

        -- 1.3.6.1.4.1.2011.6.187.8.1.20
        hwDocsQamVideoStreamTraffic        OBJECT-TYPE
            SYNTAX       Unsigned32
            UNITS        "kbps"
            MAX-ACCESS   read-only
            STATUS       current
            DESCRIPTION
              "Indicates the video stream traffic.
              "
            ::= { hwDocsQamVideoStreamEntry 20 }  
            
        -- 1.3.6.1.4.1.2011.6.187.8.1.26
        hwDocsQamVideoStreamSourceIpAddressType  OBJECT-TYPE
            SYNTAX      InetAddressType
            MAX-ACCESS  read-create
            STATUS      current
            DESCRIPTION
                "Indicates the address type of the source IP address in video stream. Only IPv4 addresses are supported.
                "
            ::= { hwDocsQamVideoStreamEntry 26 }    
            
        -- 1.3.6.1.4.1.2011.6.187.8.1.27   
        hwDocsQamVideoStreamSourceIpAddress        OBJECT-TYPE
            SYNTAX       InetAddress
            MAX-ACCESS   read-create
            STATUS       current
            DESCRIPTION
                "Indicates the source IP address of the video stream.
                "
            ::= { hwDocsQamVideoStreamEntry 27 }               
            
        -- 1.3.6.1.4.1.2011.6.187.8.1.28
        hwDocsQamVideoStreamDiscontinuityCounter        OBJECT-TYPE  
            SYNTAX      Counter64
            MAX-ACCESS  read-only
            STATUS      current
            DESCRIPTION
                "Indicates the discontinuity counter of video stream.
                 Default: 0
                "
            ::= { hwDocsQamVideoStreamEntry 28 }
            
        -- 1.3.6.1.4.1.2011.6.187.8.1.29
        hwDocsQamVideoStreamSrambled        OBJECT-TYPE  
            SYNTAX       TruthValue
            MAX-ACCESS   read-only
            STATUS       current
            DESCRIPTION
                "Indicates whether a VOD program is scrambled. If one ES is scrambled, the entire program is scrambled.     
                Default: false(2). 
                "
            ::= { hwDocsQamVideoStreamEntry 29 }
            
        -- 1.3.6.1.4.1.2011.6.187.8.1.30
        hwDocsQamVideoStreamESSrambleStateList        OBJECT-TYPE  
            SYNTAX       OCTET STRING(SIZE (0..128))
            MAX-ACCESS   read-only
            STATUS       current
            DESCRIPTION
                "Indicates the sramble type mask of the video input stream ES. The default value is an empty character string, indicating no sramble type list mask.
                 Format: 2 bytes in network byte order, which indicates a sramble type list mask. A maximum of 64 sramble type list masks are supported. 
                     a 2-byte bit-field value defined as follows:
                     Bit 0:notScambled
                     Bit 1:evenScambled
                     Bit 2:oddScambled
                "
            ::= { hwDocsQamVideoStreamEntry 30 } 
			        
		-- 1.3.6.1.4.1.2011.6.187.8.1.31
        hwDocsQamVideoStreamOutputESSrambleStateList        OBJECT-TYPE  
            SYNTAX       OCTET STRING(SIZE (0..128))
            MAX-ACCESS   read-only
            STATUS       current
            DESCRIPTION
                "Indicates the sramble type mask of the video output stream ES. The default value is an empty character string, indicating no sramble type list mask.
                 Format: 2 bytes in network byte order, which indicates a sramble type list mask. A maximum of 64 sramble type list masks are supported. 
                     a 2-byte bit-field value defined as follows:
                     Bit 0:notScambled
                     Bit 1:evenScambled
                     Bit 2:oddScambled
                "
            ::= { hwDocsQamVideoStreamEntry 31 } 
   
        -- 1.3.6.1.4.1.2011.6.187.9
        hwDocsQamVideoInputStreamStatisticsTable    OBJECT-TYPE
            SYNTAX          SEQUENCE OF HwDocsQamVideoInputStreamStatisticsEntry
            MAX-ACCESS      not-accessible
            STATUS          current
            DESCRIPTION
                "Indicates the input statistics table for dynamic video streams.
                 The indexes of this table are ifIndex and hwDocsQamVideoInputStreamStatisticsIndex.
                "
            ::= { hwEqamAn 9 }
    
        -- 1.3.6.1.4.1.2011.6.187.9.1
        hwDocsQamVideoInputStreamStatisticsEntry    OBJECT-TYPE
            SYNTAX          HwDocsQamVideoInputStreamStatisticsEntry
            MAX-ACCESS      not-accessible
            STATUS          current
            DESCRIPTION
                "Indicates the input statistics table for dynamic video streams.
                 The indexes of this entry are ifIndex and hwDocsQamVideoInputStreamStatisticsIndex.
                "
            INDEX   
                { 
                ifIndex,
                hwDocsQamVideoInputStreamStatisticsIndex
                }
            ::= { hwDocsQamVideoInputStreamStatisticsTable  1 }
        
        HwDocsQamVideoInputStreamStatisticsEntry ::=
            SEQUENCE 
                { 
                hwDocsQamVideoInputStreamStatisticsIndex
                  Unsigned32,
                hwDocsQamVideoInputStreamOperMode
                  INTEGER,
                hwDocsQamVideoInputStreamPackets
                  Counter64,
                hwDocsQamVideoInputStreamCountOfJitterOverflow
                  Counter64,
                hwDocsQamVideoInputStreamCountOfJitterUnderflow
                  Counter64,
                hwDocsQamVideoInputTSDiscontinuityCounter
                  Counter64  
                }
        
        -- 1.3.6.1.4.1.2011.6.187.9.1.1   
        hwDocsQamVideoInputStreamStatisticsIndex        OBJECT-TYPE
            SYNTAX      Unsigned32 (1..65535)
            MAX-ACCESS  not-accessible
            STATUS      current
            DESCRIPTION
                "Indicates the index of input statistics table for dynamic video streams.
                "
            ::= { hwDocsQamVideoInputStreamStatisticsEntry 1 }
          
        -- 1.3.6.1.4.1.2011.6.187.9.1.2   
        hwDocsQamVideoInputStreamOperMode        OBJECT-TYPE
            SYNTAX      INTEGER
            {
              clearStatistic(1),
              invalid(-1)
            }
            MAX-ACCESS  read-write
            STATUS      current
            DESCRIPTION
                "Indicates the operation mode. The set operation can clear input statistics for dynamic video streams. 
                 Options: 
                 1. clearStatistic(1) -indicates clearing input statistics for dynamic video streams
                 2. invalid(-1)       -indicates invalid
                "
            ::= { hwDocsQamVideoInputStreamStatisticsEntry 2 }
          
        -- 1.3.6.1.4.1.2011.6.187.9.1.3   
        hwDocsQamVideoInputStreamPackets        OBJECT-TYPE
            SYNTAX      Counter64
            MAX-ACCESS  read-only
            STATUS      current
            DESCRIPTION
                "Indicates packet statistics for input streams.
                "
            ::= { hwDocsQamVideoInputStreamStatisticsEntry 3 }

        -- 1.3.6.1.4.1.2011.6.187.9.1.4   
        hwDocsQamVideoInputStreamCountOfJitterOverflow        OBJECT-TYPE
            SYNTAX      Counter64
            MAX-ACCESS  read-only
            STATUS      current
            DESCRIPTION
                "Indicates the jitter overflow statistics.
                "
            ::= { hwDocsQamVideoInputStreamStatisticsEntry 4 }
          
        -- 1.3.6.1.4.1.2011.6.187.9.1.5   
        hwDocsQamVideoInputStreamCountOfJitterUnderflow        OBJECT-TYPE
            SYNTAX      Counter64
            MAX-ACCESS  read-only
            STATUS      current
            DESCRIPTION
                "Indicates the jitter underflow statistics.
                "
            ::= { hwDocsQamVideoInputStreamStatisticsEntry 5 }
            
        -- 1.3.6.1.4.1.2011.6.187.9.1.6  
        hwDocsQamVideoInputTSDiscontinuityCounter        OBJECT-TYPE
            SYNTAX      Counter64
            MAX-ACCESS  read-only
            STATUS      current
            DESCRIPTION
                "Indicates the discontinuity counter of input streams.
                "
            ::= { hwDocsQamVideoInputStreamStatisticsEntry 6 }            
      
        -- 1.3.6.1.4.1.2011.6.187.10
        hwDocsQamVideoOutputDChannelStatisticsTable    OBJECT-TYPE
            SYNTAX          SEQUENCE OF HwDocsQamVideoOutputDChannelStatisticsEntry
            MAX-ACCESS      not-accessible
            STATUS          current
            DESCRIPTION
                "Indicates the output channel statistics table for dynamic video streams.
                 The index of this table is ifIndex.
                "
            ::= { hwEqamAn 10 }
    
        -- 1.3.6.1.4.1.2011.6.187.10.1
        hwDocsQamVideoOutputDChannelStatisticsEntry    OBJECT-TYPE
            SYNTAX          HwDocsQamVideoOutputDChannelStatisticsEntry
            MAX-ACCESS      not-accessible
            STATUS          current
            DESCRIPTION
                "Indicates the output channel statistics table for dynamic video streams.
                 The index of this entry is ifIndex.
                "
            INDEX   
                { 
                ifIndex
                }
            ::= { hwDocsQamVideoOutputDChannelStatisticsTable  1 }
        
        HwDocsQamVideoOutputDChannelStatisticsEntry ::=
            SEQUENCE 
                { 
                hwDocsQamVideoOutputDChannelOperMode
                  INTEGER,
                hwDocsQamVideoOutputDChannelPackets
                  Counter64,
                hwDocsQamVideoOutputDChannelDiscardPackets
                  Counter64,
                hwDocsQamVideoOutputDChannelPATNumber
                  Counter64,
                hwDocsQamVideoOutputDChannelPMTNumber
                  Counter64,
                hwDocsQamVideoOutputDChannelCATNumber
                  Counter64  
                }
        
        -- 1.3.6.1.4.1.2011.6.187.10.1.1    
        hwDocsQamVideoOutputDChannelOperMode        OBJECT-TYPE
            SYNTAX      INTEGER
            {
              clearStatistic(1),
              invalid(-1)
            }
            MAX-ACCESS  read-write
            STATUS      current
            DESCRIPTION
                "Indicates the operation mode. The set operation can clear output channel statistics for dynamic video streams. 
                 Options: 
                 1. clearStatistic(1) -indicates clearing output channel statistics for dynamic video streams
                 2. invalid(-1)       -indicates invalid
                "
            ::= { hwDocsQamVideoOutputDChannelStatisticsEntry 1 }
          
        -- 1.3.6.1.4.1.2011.6.187.10.1.2    
        hwDocsQamVideoOutputDChannelPackets        OBJECT-TYPE
            SYNTAX      Counter64
            MAX-ACCESS  read-only
            STATUS      current
            DESCRIPTION
                "Indicates the packet statistics for output channels.
                "
            ::= { hwDocsQamVideoOutputDChannelStatisticsEntry 2 }
          
        -- 1.3.6.1.4.1.2011.6.187.10.1.3    
        hwDocsQamVideoOutputDChannelDiscardPackets        OBJECT-TYPE
            SYNTAX      Counter64
            MAX-ACCESS  read-only
            STATUS      current
            DESCRIPTION
                "Indicates the packet loss statistics for output channels.
                "
            ::= { hwDocsQamVideoOutputDChannelStatisticsEntry 3 }
          
        -- 1.3.6.1.4.1.2011.6.187.10.1.4    
        hwDocsQamVideoOutputDChannelPATNumber        OBJECT-TYPE
            SYNTAX      Counter64
            MAX-ACCESS  read-only
            STATUS      current
            DESCRIPTION
                "Indicates the PAT statistics for output channels.
                "
            ::= { hwDocsQamVideoOutputDChannelStatisticsEntry 4 }
       
        -- 1.3.6.1.4.1.2011.6.187.10.1.5    
        hwDocsQamVideoOutputDChannelPMTNumber        OBJECT-TYPE
            SYNTAX      Counter64
            MAX-ACCESS  read-only
            STATUS      current
            DESCRIPTION
                "Indicates the PMT statistics for output channels.
                "
            ::= { hwDocsQamVideoOutputDChannelStatisticsEntry 5 }
          
        -- 1.3.6.1.4.1.2011.6.187.10.1.6    
        hwDocsQamVideoOutputDChannelCATNumber        OBJECT-TYPE
            SYNTAX      Counter64
            MAX-ACCESS  read-only
            STATUS      current
            DESCRIPTION
                "Indicates the CAT statistics for output channels.
                "
            ::= { hwDocsQamVideoOutputDChannelStatisticsEntry 6 }

-- 1.3.6.1.4.1.2011.6.187.11
        hwDocsQamNGODEdgeDeviceTable    OBJECT-TYPE
            SYNTAX          SEQUENCE OF HwDocsQamNGODEdgeDeviceEntry
            MAX-ACCESS      not-accessible
            STATUS          current
            DESCRIPTION
                "Indicates the edge device table.
                 The index of this table is hwDocsQamNGODEdgeDeviceName.
                "
            ::= { hwEqamAn 11 }
    
        -- 1.3.6.1.4.1.2011.6.187.11.1
        hwDocsQamNGODEdgeDeviceEntry    OBJECT-TYPE
            SYNTAX          HwDocsQamNGODEdgeDeviceEntry
            MAX-ACCESS      not-accessible
            STATUS          current
            DESCRIPTION
                "Indicates the edge device table.
                 The index of this entry is hwDocsQamNGODEdgeDeviceName.
                "
            INDEX   
                { 
                hwDocsQamNGODEdgeDeviceName
                }
            ::= { hwDocsQamNGODEdgeDeviceTable  1 }
        
        HwDocsQamNGODEdgeDeviceEntry ::=
            SEQUENCE 
                { 
                hwDocsQamNGODEdgeDeviceName
                  OCTET STRING,
                hwDocsQamNGODEdgeDeviceStreamingZone
                  OCTET STRING,
                hwDocsQamNGODEdgeDevicePeerAddressType
                  InetAddressType,
                hwDocsQamNGODEdgeDevicePeerAddress
                  InetAddress,
                hwDocsQamNGODEdgeDevicePeerPort
                  InetPortNumber,
                hwDocsQamNGODEdgeDeviceLocalAddressType
                  InetAddressType,
                hwDocsQamNGODEdgeDeviceLocalAddress
                  InetAddress,
                hwDocsQamNGODEdgeDeviceVREPIDMode
                  INTEGER,
                hwDocsQamNGODEdgeDeviceVREPID
                  Unsigned32,
                hwDocsQamNGODEdgeDeviceHoldTime
                  Unsigned32,
                hwDocsQamNGODEdgeDeviceConnectRetry
                  Unsigned32,
                hwDocsQamNGODEdgeDeviceActive
                  TruthValue,
                hwDocsQamNGODEdgeDeviceState
                  INTEGER,
                hwDocsQamNGODEdgeDeviceNegotiatedHoldTime
                  Unsigned32,
                hwDocsQamNGODEdgeDeviceEstablishedPeerAddressType
                  InetAddressType,
                hwDocsQamNGODEdgeDeviceEstablishedPeerAddress
                  InetAddress,
                hwDocsQamNGODEdgeDeviceEstablishedPeerPort
                  InetPortNumber,
                hwDocsQamNGODEdgeDeviceEstablishedLocalAddressType
                  InetAddressType,
                hwDocsQamNGODEdgeDeviceEstablishedLocalAddress
                  InetAddress,
                hwDocsQamNGODEdgeDeviceEstablishedLocalPort
                  InetPortNumber,
                hwDocsQamNGODEdgeDeviceCost
                  Unsigned32,
                hwDocsQamNGODEdgeDevicelocalIfType
                  INTEGER,
                hwDocsQamNGODEdgeDevicelocalIfNumber  
                  Integer32,
                hwDocsQamNGODEdgeDeviceRowStatus
                  RowStatus   
                }
        
        -- 1.3.6.1.4.1.2011.6.187.11.1.1   
        hwDocsQamNGODEdgeDeviceName        OBJECT-TYPE
            SYNTAX       OCTET STRING (SIZE (1..31))
            MAX-ACCESS   not-accessible
            STATUS       current
            DESCRIPTION
              " This attribute is the key that identifies the instance of the edge device.
              Suggested format <RegionName>.<localname>.
              "
            REFERENCE "Comcast-SP-NGOD-GEN-SDR-I03-100731"
            ::= { hwDocsQamNGODEdgeDeviceEntry 1}
          
        -- 1.3.6.1.4.1.2011.6.187.11.1.2 
        hwDocsQamNGODEdgeDeviceStreamingZone        OBJECT-TYPE
            SYNTAX       OCTET STRING (SIZE (0..31))
            MAX-ACCESS   read-create
            STATUS       current
            DESCRIPTION
              "This attribute identifies the streaming zone name which the edge device belongs to.
              Suggested format <RegionName>.<localname>.
              Null string means that the edge device does not belong to any streaming zone.
              "
            REFERENCE "Comcast-SP-NGOD-GEN-SDR-I03-100731"
            ::= { hwDocsQamNGODEdgeDeviceEntry 2}
            
        -- 1.3.6.1.4.1.2011.6.187.11.1.3 
        hwDocsQamNGODEdgeDevicePeerAddressType  OBJECT-TYPE
            SYNTAX      InetAddressType
            MAX-ACCESS  read-create
            STATUS      current
            DESCRIPTION
                "This attribute identifies the IP address type of ERM peer which the edge device setting up VREP session with.
                "
            ::= { hwDocsQamNGODEdgeDeviceEntry 3 }
            
        -- 1.3.6.1.4.1.2011.6.187.11.1.4 
        hwDocsQamNGODEdgeDevicePeerAddress  OBJECT-TYPE
            SYNTAX      InetAddress
            MAX-ACCESS  read-create
            STATUS      current
            DESCRIPTION
                "This attribute identifies the IP address of ERM peer which the edge device setting up VREP session with.
                "
            ::= { hwDocsQamNGODEdgeDeviceEntry 4 }
            
        -- 1.3.6.1.4.1.2011.6.187.11.1.5  
        hwDocsQamNGODEdgeDevicePeerPort        OBJECT-TYPE
            SYNTAX      InetPortNumber
            MAX-ACCESS  read-create
            STATUS      current
            DESCRIPTION
                "This attribute identifies the TCP port number of ERM peer which the edge device setting up VREP session with.
                The default port number is 6069.
                "
            ::= { hwDocsQamNGODEdgeDeviceEntry 5 }
            
        -- 1.3.6.1.4.1.2011.6.187.11.1.6 
        hwDocsQamNGODEdgeDeviceLocalAddressType  OBJECT-TYPE
            SYNTAX      InetAddressType
            MAX-ACCESS  read-create
            STATUS      current
            DESCRIPTION
                "This attribute identifies the IP address type of the edge device to setup VREP session.
                "
            ::= { hwDocsQamNGODEdgeDeviceEntry 6 }
            
        -- 1.3.6.1.4.1.2011.6.187.11.1.7 
        hwDocsQamNGODEdgeDeviceLocalAddress  OBJECT-TYPE
            SYNTAX      InetAddress
            MAX-ACCESS  read-create
            STATUS      current
            DESCRIPTION
                "This attribute identifies the IP address of the edge device to setup VREP session.
                "
            ::= { hwDocsQamNGODEdgeDeviceEntry 7 }
            
        -- 1.3.6.1.4.1.2011.6.187.11.1.8   
        hwDocsQamNGODEdgeDeviceVREPIDMode        OBJECT-TYPE
            SYNTAX      INTEGER
                  {
                  localip(1),
                  integer(2)
                  }
            MAX-ACCESS  read-create
            STATUS      current
            DESCRIPTION
                "This attribute identifies the IP address type of the edge device to setup VREP session.. 
                 The default value is localip(1).
                 Options: 
                 1. localip(1)   -indicates the localip mode. In this mode, edge device uses the hwDocsQamNGODEdgeDeviceLocalAddress
                 as the VREPID in the VREP OPEN message.
                 2. integer(2)   -indicates the integer mode. In this mode, edge device uses the manual configured VREPID 
                 which can be configured through hwDocsQamNGODEdgeDeviceVREPID as the VREPID in the VREP OPEN message.
                 
                "
            ::= { hwDocsQamNGODEdgeDeviceEntry 8 }
            
        -- 1.3.6.1.4.1.2011.6.187.11.1.9    
        hwDocsQamNGODEdgeDeviceVREPID        OBJECT-TYPE
            SYNTAX      Unsigned32 (0..4294967295)
            MAX-ACCESS  read-create
            STATUS      current
            DESCRIPTION
                "This attribute identifies the VREPID value of the edge device.
                The VREP Identifier MUST uniquely identify this speaker/listener within its Streaming Zone. A 
                given node MAY set the value of its VREP Identifier to an IPv4 address assigned to that 
                device. The value of the VREP Identifier is determined on startup and MUST be the 
                same for all peer connections. When comparing two VREP identifiers, the VREP 
                Identifier is to be interpreted as a numerical 4-octet unsigned integer.
                It is recommended that NGOD components set the VREP identifier to their IPv4 address
                when no identifier is configured in the Nx interface
                When hwDocsQamNGODEdgeDeviceVREPIDMode is localip(1), this attribute can't be modified and the value is the same with hwDocsQamNGODEdgeDeviceLocalAddress. 
                When hwDocsQamNGODEdgeDeviceVREPIDMode is integer(2), this atrribute can be configured to any integer as the VREPID.
                The default value is 0.
                "
            REFERENCE "Comcast-SP-NGOD-GEN-SDR-I03-100731"
            ::= { hwDocsQamNGODEdgeDeviceEntry 9 }
            
        -- 1.3.6.1.4.1.2011.6.187.11.1.10   
        hwDocsQamNGODEdgeDeviceHoldTime        OBJECT-TYPE
            SYNTAX      Unsigned32 (0 | 3..3600)
            MAX-ACCESS  read-create
            STATUS      current
            DESCRIPTION
                "This attribute identifies the number of seconds that the edge device proposes
                 for the value of the Hold Timer. Upon receipt of an OPEN message, a VREP speaker or
                 listener MUST calculate the value of the Hold Timer by using the smaller of its
                 configured Hold Time and the Hold Time received in the OPEN message. The Hold
                 Time MUST be either zero or at least three seconds. The calculated value indicates the maximum
                 number of seconds that may elapse between the receipt of successive KEEPALIVE and/or UPDATE messages by the sender.
                 If the Hold Timer is zero, then no procedures are necessary for keeping a peering session alive.
                The default value is 240. 
                Unit: s.
                "
            REFERENCE "Comcast-SP-NGOD-GEN-SDR-I03-100731"
            ::= { hwDocsQamNGODEdgeDeviceEntry 10 }
            
        -- 1.3.6.1.4.1.2011.6.187.11.1.11   
        hwDocsQamNGODEdgeDeviceConnectRetry        OBJECT-TYPE
            SYNTAX      Unsigned32 (60..3600)
            MAX-ACCESS  read-create
            STATUS      current
            DESCRIPTION
                "This attribute identifies the expire time for the edge device to setup an TCP connection. 
                The exact value of the ConnectRetry timer is a local matter, but should be sufficiently large to allow TCP initialization.
                The default value is 120 second.
                Unit: s.
                "
            REFERENCE "Comcast-SP-NGOD-GEN-SDR-I03-100731"
            ::= { hwDocsQamNGODEdgeDeviceEntry 11 }
            
        -- 1.3.6.1.4.1.2011.6.187.11.1.12 
        hwDocsQamNGODEdgeDeviceActive        OBJECT-TYPE
            SYNTAX       TruthValue
            MAX-ACCESS   read-write
            STATUS       current
            DESCRIPTION
                "This attribute identifies the state of the edge device. 
                Set ture to active the edge device and false to deactive.
                The default value is false.
                "
            ::= { hwDocsQamNGODEdgeDeviceEntry 12 }   
            
        -- 1.3.6.1.4.1.2011.6.187.11.1.13   
        hwDocsQamNGODEdgeDeviceState        OBJECT-TYPE
            SYNTAX      INTEGER
                  {
                  idle(1),
                  connect(2),
                  active(3),
                  opensent(4),
                  openconfirm(5),
                  established(6)
                  }
            MAX-ACCESS  read-only
            STATUS      current
            DESCRIPTION
                "Indicates the state of the edge device VREP FSM. 
                 Options: 
                 1. idle(1)        -Initially VREP is in the Idle state for each peer
                 2. connect(2)     -In this state, an edge device is waiting for a transport protocol connection 
                                    to be completed to the peer, and is listening for inbound transport connections from the peer
                 3. active(3)      -In this state, an edge device is listening for an inbound connection from the peer, 
                                    but is not in the process of initiating a connection to the peer
                 4. opensent(4)    -In this state, an edge device has sent an OPEN message to its peer and is
                                    waiting for an OPEN message from its peer
                 5. openconfirm(5) -In this state, an edge device has sent an OPEN to its peer, received an OPEN
                                    from its peer, and sent a KEEPALIVE in response to the OPEN
                 6. established(6) -In the Established state, an LS can exchange UPDATE, NOTIFICATION, and KEEPALIVE messages with its peer
                "
            REFERENCE "Comcast-SP-NGOD-GEN-SDR-I03-100731"
            ::= { hwDocsQamNGODEdgeDeviceEntry 13 }
            
        -- 1.3.6.1.4.1.2011.6.187.11.1.14   
        hwDocsQamNGODEdgeDeviceNegotiatedHoldTime        OBJECT-TYPE
            SYNTAX      Unsigned32 (0 | 3..3600)
            MAX-ACCESS  read-only
            STATUS      current
            DESCRIPTION
                "This attribute identifies the negotiated number of seconds that the edge device proposes
                 for the value of the Hold Timer. See hwDocsQamNGODEdgeDeviceHoldTime decription.
                The default value is 0.
                Unit: s.
                "
            REFERENCE "Comcast-SP-NGOD-GEN-SDR-I03-100731"
            ::= { hwDocsQamNGODEdgeDeviceEntry 14 }
            
        -- 1.3.6.1.4.1.2011.6.187.11.1.15 
        hwDocsQamNGODEdgeDeviceEstablishedPeerAddressType  OBJECT-TYPE
            SYNTAX      InetAddressType
            MAX-ACCESS  read-only
            STATUS      current
            DESCRIPTION
                "This attribute identifies the IP address type of ERM peer which the edge device established a VREP session with. 
                "
            ::= { hwDocsQamNGODEdgeDeviceEntry 15 }
            
        -- 1.3.6.1.4.1.2011.6.187.11.1.16 
        hwDocsQamNGODEdgeDeviceEstablishedPeerAddress  OBJECT-TYPE
            SYNTAX      InetAddress
            MAX-ACCESS  read-only
            STATUS      current
            DESCRIPTION
                "This attribute identifies the IP address of ERM peer which the edge device established a VREP session with. 
                When VREP session is not in established state, this value is 0.
                The default value is 0.
                "
            ::= { hwDocsQamNGODEdgeDeviceEntry 16 }
            
        -- 1.3.6.1.4.1.2011.6.187.11.1.17  
        hwDocsQamNGODEdgeDeviceEstablishedPeerPort        OBJECT-TYPE
            SYNTAX      InetPortNumber
            MAX-ACCESS  read-only
            STATUS      current
            DESCRIPTION
                "This attribute identifies the TCP port number of ERM peer which the edge device established a VREP session with.
                When VREP session is not in established state, this value is 0.
                The default value is 0.
                "
            ::= { hwDocsQamNGODEdgeDeviceEntry 17 }
            
        -- 1.3.6.1.4.1.2011.6.187.11.1.18 
        hwDocsQamNGODEdgeDeviceEstablishedLocalAddressType  OBJECT-TYPE
            SYNTAX      InetAddressType
            MAX-ACCESS  read-only
            STATUS      current
            DESCRIPTION
                "This attribute identifies the IP address type of the edge device established a VREP session. 
                "
            ::= { hwDocsQamNGODEdgeDeviceEntry 18 }
            
        -- 1.3.6.1.4.1.2011.6.187.11.1.19 
        hwDocsQamNGODEdgeDeviceEstablishedLocalAddress  OBJECT-TYPE
            SYNTAX      InetAddress
            MAX-ACCESS  read-only
            STATUS      current
            DESCRIPTION
                "This attribute identifies the IP address of the edge device established a VREP session.
                 When VREP session is not in established state, this value is 0.
                The default value is 0.
                "
            ::= { hwDocsQamNGODEdgeDeviceEntry 19 }
            
        -- 1.3.6.1.4.1.2011.6.187.11.1.20  
        hwDocsQamNGODEdgeDeviceEstablishedLocalPort        OBJECT-TYPE
            SYNTAX      InetPortNumber
            MAX-ACCESS  read-only
            STATUS      current
            DESCRIPTION
                "This attribute identifies the TCP port number of the edge device established a VREP session.
                When VREP session is not in established state, this value is 0.
                The default value is 0.
                "
            ::= { hwDocsQamNGODEdgeDeviceEntry 20 }
            
        -- 1.3.6.1.4.1.2011.6.187.11.1.21   
        hwDocsQamNGODEdgeDeviceCost        OBJECT-TYPE
            SYNTAX      Unsigned32 (0..255)
            MAX-ACCESS  read-create
            STATUS      current
            DESCRIPTION
                "This attribute identifies the cost of the edge devie. 
                The cost attribute is a topology independent attribute. 
                It represents the relative cost associated with the resources from a resource manager or of a data plane component.
                The default value is 0.
                "
            REFERENCE "Comcast-SP-NGOD-GEN-SDR-I03-100731"
            ::= { hwDocsQamNGODEdgeDeviceEntry 21 }
            
        -- 1.3.6.1.4.1.2011.6.187.11.1.22   
        hwDocsQamNGODEdgeDevicelocalIfType        OBJECT-TYPE
            SYNTAX      INTEGER
                  {
                  inloopback(1),
                  null(2),
                  meth(3),
                  vlanif(4),
                  loopback(5),
                  tunnel(6),
                  notconfigured(255)
                  }
            MAX-ACCESS  read-write
            STATUS      current
            DESCRIPTION
                "Indicates the interface type.
                 Options:
                 1. inloopback(1) -the system inner loopback interface
                 2. null(2)       -the NULL interface
                 3. meth(3)       -the ethernet interface for management
                 4. vlanif(4)     -the VLAN interface
                 5. loopback(5)   -the loopback interface
                 6. tunnel(6)     -the tunnel interface
                 7. notconfigured(255) -not configiured
                 The interface number (hwDocsQamNGODEdgeDevicelocalIfNumber)and interface type together identify an interface.
                 The default value is notConfigured(255), it indicates that no interface is configured.
                 It only supports vlanif(4) and loopback(5).
                "                
            ::= { hwDocsQamNGODEdgeDeviceEntry 22 }

        -- 1.3.6.1.4.1.2011.6.187.11.1.23   
        hwDocsQamNGODEdgeDevicelocalIfNumber        OBJECT-TYPE
            SYNTAX      Integer32 (-1|0..4093)
            MAX-ACCESS  read-write
            STATUS      current
            DESCRIPTION
                "Indicates the interface number.
                 Range: 0-4093
                 Range for the inloopback interface: 0
                 Range for the NULL interface: 0
                 Range for the MEth interface: 0
                 Range for the VLAN interface: 1-4093
                 Range for the loopback interface: 0-31
                 Range for the tunnel interface: 1-64                 
                 The interface number and interface type (hwDocsQamNGODEdgeDevicelocalIfType) together identify an interface.
                 The default value is -1, it indicates that no interface is configured.
                "
            ::= { hwDocsQamNGODEdgeDeviceEntry 23 }  

        -- 1.3.6.1.4.1.2011.6.187.11.1.255 
        hwDocsQamNGODEdgeDeviceRowStatus        OBJECT-TYPE
            SYNTAX       RowStatus
            MAX-ACCESS   read-create
            STATUS       current
            DESCRIPTION
                "Row status, used to query, create, modify, and delete a edge device. 
                 It supports the active(1), createAndGo(4), and destroy(6) operations.
                 During query, the value of this leaf is always active(1).
                 During deletion, specify the value of this leaf to destroy(6).
                 During creation, specify the value of this leaf to createAndGo(4).
                 To modify the parameters of a edge device table, this leaf need not be issued together.
                 Options:
                 1. active(1)      -indicates the query operation
                 2. createAndGo(4) -indicates the creating operation
                 3. destroy(6)     -indicates the deleting operation
                "
            ::= { hwDocsQamNGODEdgeDeviceEntry 255}
            
-- 1.3.6.1.4.1.2011.6.187.12
        hwDocsQamNGODEdgeDeviceEdgeInputTable    OBJECT-TYPE
            SYNTAX          SEQUENCE OF HwDocsQamNGODEdgeDeviceEdgeInputEntry
            MAX-ACCESS      not-accessible
            STATUS          current
            DESCRIPTION
                "Indicates the edge device input table.
                 The index of this table is hwDocsQamNGODEdgeDeviceName and hwDocsQamNGODEdgeDeviceEdgeInputIndex.
                "
            ::= { hwEqamAn 12 }
    
        -- 1.3.6.1.4.1.2011.6.187.12.1
        hwDocsQamNGODEdgeDeviceEdgeInputEntry    OBJECT-TYPE
            SYNTAX          HwDocsQamNGODEdgeDeviceEdgeInputEntry
            MAX-ACCESS      not-accessible
            STATUS          current
            DESCRIPTION
                "Indicates the edge device input table.
                 The index of this entry is hwDocsQamNGODEdgeDeviceName and hwDocsQamNGODEdgeDeviceEdgeInputIndex.
                "
            INDEX 
                { 
                hwDocsQamNGODEdgeDeviceName,
                hwDocsQamNGODEdgeDeviceEdgeInputIndex
                }
            ::= { hwDocsQamNGODEdgeDeviceEdgeInputTable  1 }
        
        HwDocsQamNGODEdgeDeviceEdgeInputEntry ::=
            SEQUENCE 
                { 
                hwDocsQamNGODEdgeDeviceEdgeInputIndex
                  Unsigned32,
                hwDocsQamNGODEdgeDeviceEdgeInputAddressType
                  InetAddressType,
                hwDocsQamNGODEdgeDeviceEdgeInputAddress
                  InetAddress,
                hwDocsQamNGODEdgeDeviceEdgeInputAddressMask
                  InetAddress,
                hwDocsQamNGODEdgeDeviceEdgeInputIfindex
                  Unsigned32,
                hwDocsQamNGODEdgeDeviceEdgeInputMaxBandwidth
                  Unsigned32,
                hwDocsQamNGODEdgeDeviceEdgeInputGroupName
                  OCTET STRING,
                hwDocsQamNGODEdgeDeviceEdgeInputRowStatus
                  RowStatus   
                }
        
        -- 1.3.6.1.4.1.2011.6.187.12.1.1   
        hwDocsQamNGODEdgeDeviceEdgeInputIndex        OBJECT-TYPE
            SYNTAX      Unsigned32 (1..4|4294967295)
            MAX-ACCESS  not-accessible
            STATUS      current
            DESCRIPTION
                "Indicates the index of the edge device input table.
                when set to 4294967295, the system automatically allocates an index for the instance.
                "      
            ::= { hwDocsQamNGODEdgeDeviceEdgeInputEntry 1 }
             
        -- 1.3.6.1.4.1.2011.6.187.12.1.2 
        hwDocsQamNGODEdgeDeviceEdgeInputAddressType  OBJECT-TYPE
            SYNTAX      InetAddressType
            MAX-ACCESS  read-create
            STATUS      current
            DESCRIPTION
                "This attribute identifies the IP address type of the edge device input host adress.
                "
            ::= { hwDocsQamNGODEdgeDeviceEdgeInputEntry 2 }
            
        -- 1.3.6.1.4.1.2011.6.187.12.1.3
        hwDocsQamNGODEdgeDeviceEdgeInputAddress  OBJECT-TYPE
            SYNTAX      InetAddress
            MAX-ACCESS  read-create
            STATUS      current
            DESCRIPTION
                "This attribute identifies the IP address of the edge device input host adress.
                "
            REFERENCE "Comcast-SP-NGOD-GEN-SDR-I03-100731"
            ::= { hwDocsQamNGODEdgeDeviceEdgeInputEntry 3 }
            
        -- 1.3.6.1.4.1.2011.6.187.12.1.4
        hwDocsQamNGODEdgeDeviceEdgeInputAddressMask  OBJECT-TYPE
            SYNTAX      InetAddress
            MAX-ACCESS  read-create
            STATUS      current
            DESCRIPTION
                "This attribute identifies the IP address mask of the edge device input host adress.
                "
            REFERENCE "Comcast-SP-NGOD-GEN-SDR-I03-100731"
            ::= { hwDocsQamNGODEdgeDeviceEdgeInputEntry 4 }
            
        -- 1.3.6.1.4.1.2011.6.187.12.1.5
        hwDocsQamNGODEdgeDeviceEdgeInputIfindex  OBJECT-TYPE
            SYNTAX      Unsigned32 (0..4294967295)
            MAX-ACCESS  read-create
            STATUS      current
            DESCRIPTION
                "This attribute identifies the input ifindex of the edge device input port.
                The ifIndex is an ifType of docsCableMaclayer(127).
                "
            REFERENCE "Comcast-SP-NGOD-GEN-SDR-I03-100731"
            ::= { hwDocsQamNGODEdgeDeviceEdgeInputEntry 5 }

        -- 1.3.6.1.4.1.2011.6.187.12.1.6   
        hwDocsQamNGODEdgeDeviceEdgeInputMaxBandwidth        OBJECT-TYPE
            SYNTAX      Unsigned32 (0..4294967295)
            MAX-ACCESS  read-create
            STATUS      current
            DESCRIPTION
                "This attribute identifies the max bandwidth of the edge device input port.
                 The default value is 0.
                 Unit: kbps.
                "
            REFERENCE "Comcast-SP-NGOD-GEN-SDR-I03-100731"
            ::= { hwDocsQamNGODEdgeDeviceEdgeInputEntry 6 }
            
        -- 1.3.6.1.4.1.2011.6.187.12.1.7   
        hwDocsQamNGODEdgeDeviceEdgeInputGroupName        OBJECT-TYPE
            SYNTAX       OCTET STRING (SIZE (0..31))
            MAX-ACCESS   read-create
            STATUS       current
            DESCRIPTION
              "This attribute identifies the group name of the edge device input belongs to. 
              The default value is null string.
              "
            REFERENCE "Comcast-SP-NGOD-GEN-SDR-I03-100731"
            ::= { hwDocsQamNGODEdgeDeviceEdgeInputEntry 7}
            
        -- 1.3.6.1.4.1.2011.6.187.12.1.255 
        hwDocsQamNGODEdgeDeviceEdgeInputRowStatus        OBJECT-TYPE
            SYNTAX       RowStatus
            MAX-ACCESS   read-create
            STATUS       current
            DESCRIPTION
                "Row status, used to query, create, modify, and delete a edge device input. 
                 It supports the active(1), createAndGo(4), and destroy(6) operations.
                 During query, the value of this leaf is always active(1).
                 During deletion, specify the value of this leaf to destroy(6).
                 During creation, specify the value of this leaf to createAndGo(4).
                 To modify the parameters of a device input table, this leaf need not be issued together.
                 Options:
                 1. active(1)      -indicates the query operation
                 2. createAndGo(4) -indicates the creating operation
                 3. destroy(6)     -indicates the deleting operation
                "
            ::= { hwDocsQamNGODEdgeDeviceEdgeInputEntry 255}
            
        -- 1.3.6.1.4.1.2011.6.187.13
        hwDocsQamNGODEdgeDeviceStatisticsTable    OBJECT-TYPE
            SYNTAX          SEQUENCE OF HwDocsQamNGODEdgeDeviceStatisticsEntry
            MAX-ACCESS      not-accessible
            STATUS          current
            DESCRIPTION
                "Indicates the edge device statistics table.
                 The index of this table is hwDocsQamNGODEdgeDeviceName.
                "
            ::= { hwEqamAn 13 }
    
        -- 1.3.6.1.4.1.2011.6.187.13.1
        hwDocsQamNGODEdgeDeviceStatisticsEntry    OBJECT-TYPE
            SYNTAX          HwDocsQamNGODEdgeDeviceStatisticsEntry
            MAX-ACCESS      not-accessible
            STATUS          current
            DESCRIPTION
                "Indicates the edge device statistics table.
                 The index of this entry is hwDocsQamNGODEdgeDeviceName.
                "
            INDEX 
                { 
                hwDocsQamNGODEdgeDeviceName
                }
            ::= { hwDocsQamNGODEdgeDeviceStatisticsTable  1 }
        
        HwDocsQamNGODEdgeDeviceStatisticsEntry ::=
            SEQUENCE 
                { 
                hwDocsQamNGODEdgeDeviceRecvOpenPkts
                  Counter32,
                hwDocsQamNGODEdgeDeviceSentOpenPkts
                  Counter32,
                hwDocsQamNGODEdgeDeviceRecvKeepalivePkts
                  Counter32,
                hwDocsQamNGODEdgeDeviceSentKeepalivePkts
                  Counter32,
                hwDocsQamNGODEdgeDeviceRecvNotificationPkts
                  Counter32,
                hwDocsQamNGODEdgeDeviceSentNotificationPkts
                  Counter32,
                hwDocsQamNGODEdgeDeviceSentUpdatePkts
                  Counter32,
                hwDocsQamNGODEdgeDeviceRecvErrPkts
                  Counter32,
                hwDocsQamNGODEdgeDeviceRecvMsgHeaderErrPkts
                  Counter32,
                hwDocsQamNGODEdgeDeviceRecvMsgHeaderBadLengthErrPkts
                  Counter32,
                hwDocsQamNGODEdgeDeviceRecvMsgHeaderBadTypeErrPkts
                  Counter32,
                hwDocsQamNGODEdgeDeviceRecvOpenMsgErrPkts
                  Counter32,
                hwDocsQamNGODEdgeDeviceRecvOpenMsgUnsupportedVersionErrPkts
                  Counter32,
                hwDocsQamNGODEdgeDeviceRecvOpenMsgBadPeerAddressDomainErrPkts
                  Counter32,
                hwDocsQamNGODEdgeDeviceRecvOpenMsgBadVREPIDErrPkts
                  Counter32,
                hwDocsQamNGODEdgeDeviceRecvOpenMsgUnsupportedOptionParaErrPkts
                  Counter32,
                hwDocsQamNGODEdgeDeviceRecvOpenMsgUnacceptableHoldTimeErrPkts
                  Counter32,
                hwDocsQamNGODEdgeDeviceRecvOpenMsgUnsupportedCapabilityErrPkts
                  Counter32,
                hwDocsQamNGODEdgeDeviceRecvOpenMsgCapabilityMissmatchErrPkts
                  Counter32,
                hwDocsQamNGODEdgeDeviceStatisticsReset
                  INTEGER, 
                hwDocsQamNGODEdgeDeviceRecvNotificationErrPkts
                  Counter32
                }
        
        -- 1.3.6.1.4.1.2011.6.187.13.1.1   
        hwDocsQamNGODEdgeDeviceRecvOpenPkts    OBJECT-TYPE   
            SYNTAX   Counter32 
            MAX-ACCESS   read-only
            STATUS       current
            DESCRIPTION
                "Indicates the number of OPEN packets received.
                "
            REFERENCE "Comcast-SP-NGOD-GEN-SDR-I03-100731"
            ::= { hwDocsQamNGODEdgeDeviceStatisticsEntry 1 }   
            
        -- 1.3.6.1.4.1.2011.6.187.13.1.2   
        hwDocsQamNGODEdgeDeviceSentOpenPkts    OBJECT-TYPE   
            SYNTAX   Counter32 
            MAX-ACCESS   read-only
            STATUS       current
            DESCRIPTION
                "Indicates the number of OPEN packets sent.
                "
            REFERENCE "Comcast-SP-NGOD-GEN-SDR-I03-100731"
            ::= { hwDocsQamNGODEdgeDeviceStatisticsEntry 2 } 
        
        -- 1.3.6.1.4.1.2011.6.187.13.1.3   
        hwDocsQamNGODEdgeDeviceRecvKeepalivePkts    OBJECT-TYPE   
            SYNTAX   Counter32 
            MAX-ACCESS   read-only
            STATUS       current
            DESCRIPTION
                "Indicates the number of KEEPALIVE packets received .
                "
            REFERENCE "Comcast-SP-NGOD-GEN-SDR-I03-100731"
            ::= { hwDocsQamNGODEdgeDeviceStatisticsEntry 3 }  
        
        -- 1.3.6.1.4.1.2011.6.187.13.1.4   
        hwDocsQamNGODEdgeDeviceSentKeepalivePkts    OBJECT-TYPE   
            SYNTAX   Counter32 
            MAX-ACCESS   read-only
            STATUS       current
            DESCRIPTION
                "Indicates the number of KEEPALIVE packets sent.
                "
            REFERENCE "Comcast-SP-NGOD-GEN-SDR-I03-100731"
            ::= { hwDocsQamNGODEdgeDeviceStatisticsEntry 4 }   
            
        -- 1.3.6.1.4.1.2011.6.187.13.1.5   
        hwDocsQamNGODEdgeDeviceRecvNotificationPkts    OBJECT-TYPE   
            SYNTAX   Counter32 
            MAX-ACCESS   read-only
            STATUS       current
            DESCRIPTION
                "Indicates the number of NOTIFICATION packets received .
                "
            REFERENCE "Comcast-SP-NGOD-GEN-SDR-I03-100731"
            ::= { hwDocsQamNGODEdgeDeviceStatisticsEntry 5 }  
            
        -- 1.3.6.1.4.1.2011.6.187.13.1.6   
        hwDocsQamNGODEdgeDeviceSentNotificationPkts    OBJECT-TYPE   
            SYNTAX   Counter32 
            MAX-ACCESS   read-only
            STATUS       current
            DESCRIPTION
                "Indicates the number of NOTIFICATION packets sent.
                "
            REFERENCE "Comcast-SP-NGOD-GEN-SDR-I03-100731"
            ::= { hwDocsQamNGODEdgeDeviceStatisticsEntry 6 }     
            
        -- 1.3.6.1.4.1.2011.6.187.13.1.7   
        hwDocsQamNGODEdgeDeviceSentUpdatePkts    OBJECT-TYPE   
            SYNTAX   Counter32 
            MAX-ACCESS   read-only
            STATUS       current
            DESCRIPTION
                "Indicates the number of UPDATE packets sent.
                "
            REFERENCE "Comcast-SP-NGOD-GEN-SDR-I03-100731"
            ::= { hwDocsQamNGODEdgeDeviceStatisticsEntry 7 }  
            
        -- 1.3.6.1.4.1.2011.6.187.13.1.8   
        hwDocsQamNGODEdgeDeviceRecvErrPkts    OBJECT-TYPE   
            SYNTAX   Counter32 
            MAX-ACCESS   read-only
            STATUS       current
            DESCRIPTION
                "Indicates the number of ERROR packets received.
                "
            REFERENCE "Comcast-SP-NGOD-GEN-SDR-I03-100731"
            ::= { hwDocsQamNGODEdgeDeviceStatisticsEntry 8 }     
            
        -- 1.3.6.1.4.1.2011.6.187.13.1.9   
        hwDocsQamNGODEdgeDeviceRecvMsgHeaderErrPkts    OBJECT-TYPE   
            SYNTAX   Counter32 
            MAX-ACCESS   read-only
            STATUS       current
            DESCRIPTION
                "Indicates the number of message header error packets received.
                "
            REFERENCE "Comcast-SP-NGOD-GEN-SDR-I03-100731"
            ::= { hwDocsQamNGODEdgeDeviceStatisticsEntry 9 }  
            
        -- 1.3.6.1.4.1.2011.6.187.13.1.10   
        hwDocsQamNGODEdgeDeviceRecvMsgHeaderBadLengthErrPkts    OBJECT-TYPE   
            SYNTAX   Counter32 
            MAX-ACCESS   read-only
            STATUS       current
            DESCRIPTION
                "Indicates the number of message header bad length packets received.
                "
            REFERENCE "Comcast-SP-NGOD-GEN-SDR-I03-100731"
            ::= { hwDocsQamNGODEdgeDeviceStatisticsEntry 10 } 
            
        -- 1.3.6.1.4.1.2011.6.187.13.1.11   
        hwDocsQamNGODEdgeDeviceRecvMsgHeaderBadTypeErrPkts    OBJECT-TYPE   
            SYNTAX   Counter32 
            MAX-ACCESS   read-only
            STATUS       current
            DESCRIPTION
                "Indicates the number of message header bad type packets received.
                "
            REFERENCE "Comcast-SP-NGOD-GEN-SDR-I03-100731"
            ::= { hwDocsQamNGODEdgeDeviceStatisticsEntry 11 }     
            
        -- 1.3.6.1.4.1.2011.6.187.13.1.12   
        hwDocsQamNGODEdgeDeviceRecvOpenMsgErrPkts    OBJECT-TYPE   
            SYNTAX   Counter32 
            MAX-ACCESS   read-only
            STATUS       current
            DESCRIPTION
                "Indicates the number of OPEN message error packets received.
                "
            REFERENCE "Comcast-SP-NGOD-GEN-SDR-I03-100731"
            ::= { hwDocsQamNGODEdgeDeviceStatisticsEntry 12 }  
            
        -- 1.3.6.1.4.1.2011.6.187.13.1.13   
        hwDocsQamNGODEdgeDeviceRecvOpenMsgUnsupportedVersionErrPkts    OBJECT-TYPE   
            SYNTAX   Counter32 
            MAX-ACCESS   read-only
            STATUS       current
            DESCRIPTION
                "Indicates the number of OPEN message unsupported versionError error packets received.
                "
            REFERENCE "Comcast-SP-NGOD-GEN-SDR-I03-100731"
            ::= { hwDocsQamNGODEdgeDeviceStatisticsEntry 13 }     
            
        -- 1.3.6.1.4.1.2011.6.187.13.1.14   
        hwDocsQamNGODEdgeDeviceRecvOpenMsgBadPeerAddressDomainErrPkts    OBJECT-TYPE   
            SYNTAX   Counter32 
            MAX-ACCESS   read-only
            STATUS       current
            DESCRIPTION
                "Indicates the number of OPEN message bad peer address domain error packets received.
                "
            REFERENCE "Comcast-SP-NGOD-GEN-SDR-I03-100731"
            ::= { hwDocsQamNGODEdgeDeviceStatisticsEntry 14 }     
            
        -- 1.3.6.1.4.1.2011.6.187.13.1.15   
        hwDocsQamNGODEdgeDeviceRecvOpenMsgBadVREPIDErrPkts    OBJECT-TYPE   
            SYNTAX   Counter32 
            MAX-ACCESS   read-only
            STATUS       current
            DESCRIPTION
                "Indicates the number of OPEN message VREPID error packets received.
                "
            REFERENCE "Comcast-SP-NGOD-GEN-SDR-I03-100731"
            ::= { hwDocsQamNGODEdgeDeviceStatisticsEntry 15 } 
            
        -- 1.3.6.1.4.1.2011.6.187.13.1.16   
        hwDocsQamNGODEdgeDeviceRecvOpenMsgUnsupportedOptionParaErrPkts    OBJECT-TYPE   
            SYNTAX   Counter32 
            MAX-ACCESS   read-only
            STATUS       current
            DESCRIPTION
                "Indicates the number of OPEN message unsupported Option parameter error packets received.
                "
            REFERENCE "Comcast-SP-NGOD-GEN-SDR-I03-100731"
            ::= { hwDocsQamNGODEdgeDeviceStatisticsEntry 16 }
            
        -- 1.3.6.1.4.1.2011.6.187.13.1.17   
        hwDocsQamNGODEdgeDeviceRecvOpenMsgUnacceptableHoldTimeErrPkts    OBJECT-TYPE   
            SYNTAX   Counter32 
            MAX-ACCESS   read-only
            STATUS       current
            DESCRIPTION
                "Indicates the number of OPEN message unacceptable hold time error packets received.
                "
            REFERENCE "Comcast-SP-NGOD-GEN-SDR-I03-100731"
            ::= { hwDocsQamNGODEdgeDeviceStatisticsEntry 17 } 
            
        -- 1.3.6.1.4.1.2011.6.187.13.1.18   
        hwDocsQamNGODEdgeDeviceRecvOpenMsgUnsupportedCapabilityErrPkts    OBJECT-TYPE   
            SYNTAX   Counter32 
            MAX-ACCESS   read-only
            STATUS       current
            DESCRIPTION
                "Indicates the number of OPEN message unsupported capability error packets received.
                "
            REFERENCE "Comcast-SP-NGOD-GEN-SDR-I03-100731"
            ::= { hwDocsQamNGODEdgeDeviceStatisticsEntry 18 } 
            
        -- 1.3.6.1.4.1.2011.6.187.13.1.19   
        hwDocsQamNGODEdgeDeviceRecvOpenMsgCapabilityMissmatchErrPkts    OBJECT-TYPE   
            SYNTAX   Counter32 
            MAX-ACCESS   read-only
            STATUS       current
            DESCRIPTION
                "Indicates the number of OPEN message capability missmatch error packets received.
                "
            REFERENCE "Comcast-SP-NGOD-GEN-SDR-I03-100731"
            ::= { hwDocsQamNGODEdgeDeviceStatisticsEntry 19 }
            
        -- 1.3.6.1.4.1.2011.6.187.13.1.20   
        hwDocsQamNGODEdgeDeviceStatisticsReset   OBJECT-TYPE
            SYNTAX   INTEGER{
                              clear(1)
                            }
            MAX-ACCESS   read-write
            STATUS       current
            DESCRIPTION
                "Rest the statistics of edge device.
                 Options:
                 1. clear(1)   -indicates resetingthe statistics of edge device
                "
            REFERENCE "Comcast-SP-NGOD-GEN-SDR-I03-100731"
            ::= { hwDocsQamNGODEdgeDeviceStatisticsEntry 20 }
            
        -- 1.3.6.1.4.1.2011.6.187.13.1.21   
        hwDocsQamNGODEdgeDeviceRecvNotificationErrPkts    OBJECT-TYPE   
            SYNTAX   Counter32 
            MAX-ACCESS   read-only
            STATUS       current
            DESCRIPTION
                "Indicates the number of NOTIFICATION error packets received.
                "
            REFERENCE "Comcast-SP-NGOD-GEN-SDR-I03-100731"
            ::= { hwDocsQamNGODEdgeDeviceStatisticsEntry 21 }
            
        -- 1.3.6.1.4.1.2011.6.187.14
        hwDocsQamChannelTable    OBJECT-TYPE
            SYNTAX          SEQUENCE OF HwDocsQamChannelEntry
            MAX-ACCESS      not-accessible
            STATUS          current
            DESCRIPTION
                "Indicates the qam channel table.
                 The index of this table is ifindex.
                "           
            ::= { hwEqamAn 14 }
    
        -- 1.3.6.1.4.1.2011.6.187.14.1
        hwDocsQamChannelEntry    OBJECT-TYPE
            SYNTAX          HwDocsQamChannelEntry
            MAX-ACCESS      not-accessible
            STATUS          current
            DESCRIPTION
                "Indicates the qam channel table.
                 The index of this entry is ifindex.
                "
            INDEX 
                { 
                ifIndex
                }
            ::= { hwDocsQamChannelTable  1 }
        
        HwDocsQamChannelEntry ::=
            SEQUENCE 
                { 
                hwDocsQamChannelStreamID
                  Unsigned32,
                hwDocsQamChannelServiceGroupName
                  OCTET STRING,
                hwDocsQamChannelEdgeDeviceName
                  OCTET STRING,
                hwDocsQamChannelSCSName
                  OCTET STRING
                }
        
        -- 1.3.6.1.4.1.2011.6.187.14.1.1   
        hwDocsQamChannelStreamID        OBJECT-TYPE
            SYNTAX      Unsigned32 (0..65535 | 4294967295)
            MAX-ACCESS  read-write
            STATUS      current
            DESCRIPTION
                "This attribute identifies the TSID of the EQAM channel.
                The default value is 4294967295.
                "
            ::= { hwDocsQamChannelEntry 1 }
            
        -- 1.3.6.1.4.1.2011.6.187.14.1.2   
        hwDocsQamChannelServiceGroupName        OBJECT-TYPE
            SYNTAX       OCTET STRING (SIZE (0..31))
            MAX-ACCESS   read-write
            STATUS       current
            DESCRIPTION
              "This attribute identifies the service group of the EQAM channel belongs to.
              Suggested format <RegionName>.<localname>. 
              The default value is null string.
              "
            REFERENCE "Comcast-SP-NGOD-GEN-SDR-I03-100731"
            ::= { hwDocsQamChannelEntry 2}
            
        -- 1.3.6.1.4.1.2011.6.187.14.1.3   
        hwDocsQamChannelEdgeDeviceName        OBJECT-TYPE
            SYNTAX       OCTET STRING (SIZE (0..31))
            MAX-ACCESS   read-write
            STATUS       current
            DESCRIPTION
              "This attribute identifies the egdge device of the EQAM channel belongs to. 
              The default value is null string.
              "
            REFERENCE "Comcast-SP-NGOD-GEN-SDR-I03-100731"
            ::= { hwDocsQamChannelEntry 3}
                        
        -- 1.3.6.1.4.1.2011.6.187.14.1.4  
        hwDocsQamChannelSCSName        OBJECT-TYPE
            SYNTAX       OCTET STRING (SIZE (0..31))
            MAX-ACCESS   read-write
            STATUS       current
            DESCRIPTION
              "Indicates the name of the SCS table.
               The default value is null string. If the node value is set to a null string, the SCS used by the channel will be deleted.
              "
            ::= { hwDocsQamChannelEntry 4 }  
            
        -- 1.3.6.1.4.1.2011.6.187.15
        hwDocsQamVideoStreamMPTSProgramTable    OBJECT-TYPE
            SYNTAX          SEQUENCE OF HwDocsQamVideoStreamMPTSProgramEntry
            MAX-ACCESS      not-accessible
            STATUS          current
            DESCRIPTION
                "Indicates the dynamic program information table for mpts video stream.
                 The indexes of this table are ifIndex, hwDocsQamVideoStreamIndex and hwDocsQamVideoStreamMultiProgramIndex.
                "
            ::= { hwEqamAn 15 }
    
        -- 1.3.6.1.4.1.2011.6.187.15.1
        hwDocsQamVideoStreamMPTSProgramEntry    OBJECT-TYPE
            SYNTAX          HwDocsQamVideoStreamMPTSProgramEntry
            MAX-ACCESS      not-accessible
            STATUS          current
            DESCRIPTION
                "Indicates the dynamic program information table for mpts video stream.
                 The indexes of this entry are ifIndex, hwDocsQamVideoStreamIndex and hwDocsQamVideoStreamMultiProgramIndex.
                "
            INDEX
                { 
                ifIndex,
                hwDocsQamVideoStreamIndex,
                hwDocsQamVideoStreamMPTSProgramIndex
                }
            ::= { hwDocsQamVideoStreamMPTSProgramTable  1 }
        
        HwDocsQamVideoStreamMPTSProgramEntry ::=
            SEQUENCE 
                { 
                hwDocsQamVideoStreamMPTSProgramIndex
                  Unsigned32,
                hwDocsQamVideoStreamMPTSInputProgram
                  Integer32,
                hwDocsQamVideoStreamMPTSInputPMTPID
                  Integer32,
                hwDocsQamVideoStreamMPTSInputPCRPID
                  Integer32,
                hwDocsQamVideoStreamMPTSOutputProgram
                  Integer32,
                hwDocsQamVideoStreamMPTSOutputPMTPID
                  Integer32,
                hwDocsQamVideoStreamMPTSOutputPCRPID
                  Integer32,
                hwDocsQamVideoStreamMPTSInputESPIDList
                  OCTET STRING,
                hwDocsQamVideoStreamMPTSOutputESPIDList
                  OCTET STRING,
                hwDocsQamVideoStreamMPTSESTypeList
                  OCTET STRING
                }
        
        -- 1.3.6.1.4.1.2011.6.187.8.15.1   
        hwDocsQamVideoStreamMPTSProgramIndex        OBJECT-TYPE
            SYNTAX      Unsigned32 (1..65535)
            MAX-ACCESS  not-accessible
            STATUS      current
            DESCRIPTION
                "Indicates the program index of a MPTS video stream.
                "
            ::= { hwDocsQamVideoStreamMPTSProgramEntry 1 }
          
        -- 1.3.6.1.4.1.2011.6.187.8.15.2   
        hwDocsQamVideoStreamMPTSInputProgram        OBJECT-TYPE
            SYNTAX      Integer32 (-1 | 0..65535)
            MAX-ACCESS  read-only
            STATUS      current
            DESCRIPTION
                "Indicates the input program ID, the value -1 indicates that the input program ID is invalid.
                "
            ::= { hwDocsQamVideoStreamMPTSProgramEntry 2 }
          
        -- 1.3.6.1.4.1.2011.6.187.8.15.3   
        hwDocsQamVideoStreamMPTSInputPMTPID        OBJECT-TYPE
            SYNTAX      Integer32 (-1 | 0..8191)
            MAX-ACCESS  read-only
            STATUS      current
            DESCRIPTION
                "Indicates the input PMT PID, the value -1 indicates that the input PMT PID is invalid.
                "
            ::= { hwDocsQamVideoStreamMPTSProgramEntry 3 }
          
        -- 1.3.6.1.4.1.2011.6.187.8.15.4   
        hwDocsQamVideoStreamMPTSInputPCRPID        OBJECT-TYPE
            SYNTAX      Integer32 (-1 | 0..8191)
            MAX-ACCESS  read-only
            STATUS      current
            DESCRIPTION
                "Indicates the input PCR PID, the value -1 indicates that the input PCR PID is invalid.
                "
            ::= { hwDocsQamVideoStreamMPTSProgramEntry 4 }
          
        -- 1.3.6.1.4.1.2011.6.187.8.15.5   
        hwDocsQamVideoStreamMPTSOutputProgram        OBJECT-TYPE
            SYNTAX      Integer32 (-1 | 0..65535)
            MAX-ACCESS  read-only
            STATUS      current
            DESCRIPTION
                "Indicates the program ID of the output stream, the value -1 indicates that the program ID of the output stream is invalid.
                "
            ::= { hwDocsQamVideoStreamMPTSProgramEntry 5 }
          
        -- 1.3.6.1.4.1.2011.6.187.8.15.6   
        hwDocsQamVideoStreamMPTSOutputPMTPID        OBJECT-TYPE
            SYNTAX      Integer32 (-1 | 0..8191)
            MAX-ACCESS  read-only
            STATUS      current
            DESCRIPTION
                "Indicates the PMT PID of the output stream, the value -1 indicates that the PMT PID of the output stream is invalid.
                "
            ::= { hwDocsQamVideoStreamMPTSProgramEntry 6 }
          
        -- 1.3.6.1.4.1.2011.6.187.8.15.7   
        hwDocsQamVideoStreamMPTSOutputPCRPID        OBJECT-TYPE
            SYNTAX      Integer32 (-1 | 0..8191)
            MAX-ACCESS  read-only
            STATUS      current
            DESCRIPTION
                "Indicates the PCR PID of the output stream, the value -1 indicates that the PCR PID of the output stream is invalid.
                "
            ::= { hwDocsQamVideoStreamMPTSProgramEntry 7 }
          
        -- 1.3.6.1.4.1.2011.6.187.8.15.8   
        hwDocsQamVideoStreamMPTSInputESPIDList        OBJECT-TYPE
            SYNTAX      OCTET STRING (SIZE (0..128))
            MAX-ACCESS  read-only
            STATUS      current
            DESCRIPTION
                "Indicates the ESPID list for input MPTS streams. PID consists of two bytes and must be in one-to-one mapping with ESTypeList.
                "
            ::= { hwDocsQamVideoStreamMPTSProgramEntry 8 }
          
        -- 1.3.6.1.4.1.2011.6.187.8.15.9   
        hwDocsQamVideoStreamMPTSOutputESPIDList        OBJECT-TYPE
            SYNTAX      OCTET STRING (SIZE (0..128))
            MAX-ACCESS  read-only
            STATUS      current
            DESCRIPTION
                "Indicates the ESPID list for output MPTS streams. PID consists of two bytes and must be in one-to-one mapping with ESTypeList.
                "
            ::= { hwDocsQamVideoStreamMPTSProgramEntry 9 }
          
        -- 1.3.6.1.4.1.2011.6.187.8.15.10   
        hwDocsQamVideoStreamMPTSESTypeList        OBJECT-TYPE
            SYNTAX      OCTET STRING (SIZE (0..64))
            MAX-ACCESS  read-only
            STATUS      current
            DESCRIPTION
                "Indicate the ES type list. One byte indicates a type, which must be in one-to-one mapping with the ESPID list for input or output streams.
                "
            ::= { hwDocsQamVideoStreamMPTSProgramEntry 10 }
            
        -- 1.3.6.1.4.1.2011.6.187.16
        hwDocsQamInputTSTable    OBJECT-TYPE
            SYNTAX          SEQUENCE OF HwDocsQamInputTSEntry
            MAX-ACCESS      not-accessible
            STATUS          current
            DESCRIPTION
                "Indicates the input TS table.
                 The index of this table is hwDocsQamInputTSIndex.
                "
            ::= { hwEqamAn 16 }   
            
        -- 1.3.6.1.4.1.2011.6.187.16.1
        hwDocsQamInputTSEntry    OBJECT-TYPE
            SYNTAX          HwDocsQamInputTSEntry
            MAX-ACCESS      not-accessible
            STATUS          current
            DESCRIPTION
                "Indicates the input TS table.
                 The index of this entry is hwDocsQamInputTSIndex.
                "
            INDEX
                { 
                hwDocsQamInputTSIndex
                }
            ::= { hwDocsQamInputTSTable  1 }  
            
        HwDocsQamInputTSEntry ::=
            SEQUENCE 
                { 
                hwDocsQamInputTSIndex
                  Unsigned32,
                hwDocsQamInputTSIpAddressType
                  InetAddressType,
                hwDocsQamInputTSMulticastIpAddress
                  InetAddress,
                hwDocsQamInputTSSourceIpAddress
                  InetAddress,
                hwDocsQamInputTSSecondaryMulticastIpAddress
                  InetAddress,
                hwDocsQamInputTSSecondarySourceIpAddress
                  InetAddress,
                hwDocsQamInputTSState
                  INTEGER,
                hwDocsQamInputTSTraffic
                  Unsigned32,
                hwDocsQamInputTSDiscontinuityCounter
                  Counter64,
                hwDocsQamInputTSEPGInput
                  TruthValue,
                hwDocsQamInputTSJitter
                  Integer32,
                hwDocsQamInputTSRTPSequenceErrorCounter
                  Counter64, 
                hwDocsQamInputTSRedundancyMode 
                  INTEGER, 
                hwDocsQamInputTSUdpPort
                  InetPortNumber,
                hwDocsQamInputTSSecondaryUdpPort
                  InetPortNumber,
                hwDocsQamInputTSMode
                  INTEGER, 
                hwDocsQamInputTSTransportStreamID
                  Unsigned32, 
                hwDocsQamInputTSRedundancyTriggers
                  BITS,
                hwDocsQamInputTSRedundancyTriggersDefault
                  TruthValue,
                hwDocsQamInputTSRowStatus
                  RowStatus
                }          
                
        -- 1.3.6.1.4.1.2011.6.187.16.1.1   
        hwDocsQamInputTSIndex        OBJECT-TYPE
            SYNTAX      Unsigned32 (1..65535|4294967295)
            MAX-ACCESS  accessible-for-notify
            STATUS      current
            DESCRIPTION
                "Indicates the index of a input TS.
                 You can also fill 4294967295 and the system will automatically allocate an index.
                "
            ::= { hwDocsQamInputTSEntry 1 }     
            
        -- 1.3.6.1.4.1.2011.6.187.16.1.2
        hwDocsQamInputTSIpAddressType  OBJECT-TYPE
            SYNTAX      InetAddressType
            MAX-ACCESS  read-create
            STATUS      current
            DESCRIPTION
                "Indicates the address type of the multicast IP address in input TS. Only IPv4 addresses are supported.
                "
            ::= { hwDocsQamInputTSEntry 2 }    
            
        -- 1.3.6.1.4.1.2011.6.187.16.1.3   
        hwDocsQamInputTSMulticastIpAddress        OBJECT-TYPE
            SYNTAX       InetAddress
            MAX-ACCESS   read-create
            STATUS       current
            DESCRIPTION
                "Indicates the multicast IP address of the input TS.
                "
            ::= { hwDocsQamInputTSEntry 3 }     
            
        -- 1.3.6.1.4.1.2011.6.187.16.1.4   
        hwDocsQamInputTSSourceIpAddress        OBJECT-TYPE
            SYNTAX       InetAddress
            MAX-ACCESS   read-create
            STATUS       current
            DESCRIPTION
                "Indicates the source IP address of the input TS.
                "
            ::= { hwDocsQamInputTSEntry 4 }       
            
        -- 1.3.6.1.4.1.2011.6.187.16.1.5   
        hwDocsQamInputTSSecondaryMulticastIpAddress        OBJECT-TYPE
            SYNTAX       InetAddress
            MAX-ACCESS   read-create
            STATUS       current
            DESCRIPTION
                "Indicates the secondary multicast IP address of the input TS.
                "
            ::= { hwDocsQamInputTSEntry 5 }     
            
        -- 1.3.6.1.4.1.2011.6.187.16.1.6   
        hwDocsQamInputTSSecondarySourceIpAddress        OBJECT-TYPE
            SYNTAX       InetAddress
            MAX-ACCESS   read-create
            STATUS       current
            DESCRIPTION
                "Indicates the secondary source IP address of the input TS.
                "
            ::= { hwDocsQamInputTSEntry 6 }  
            
        -- 1.3.6.1.4.1.2011.6.187.16.1.7   
        hwDocsQamInputTSState        OBJECT-TYPE
            SYNTAX      INTEGER
                  {
                  offline(1),
                  online(2),
                  unknown(3)
                  }
            MAX-ACCESS  read-only
            STATUS      current
            DESCRIPTION
                "Indicates the state of input TS.
                 Options: 
                 1. offline(1)   -indicates the offline state
                 2. online(2)    -indicates the online state
                 3. unknown(3)   -indicates the unknown state
                "
            ::= { hwDocsQamInputTSEntry 7 }    
            
        -- 1.3.6.1.4.1.2011.6.187.16.1.8
        hwDocsQamInputTSTraffic  OBJECT-TYPE
            SYNTAX      Unsigned32
            UNITS       "kbps"
            MAX-ACCESS  read-only
            STATUS      current
            DESCRIPTION
                "Indicates the traffic of input TS.
                 Default: 0
                "
            ::= { hwDocsQamInputTSEntry 8 } 
            
        -- 1.3.6.1.4.1.2011.6.187.16.1.9 
        hwDocsQamInputTSDiscontinuityCounter  OBJECT-TYPE  
            SYNTAX      Counter64
            MAX-ACCESS  read-only
            STATUS      current
            DESCRIPTION
                "Indicates the discontinuity counter of input TS.
                 Default: 0
                "
            ::= { hwDocsQamInputTSEntry 9 }                
            
        -- 1.3.6.1.4.1.2011.6.187.16.1.10
        hwDocsQamInputTSEPGInput  OBJECT-TYPE  
            SYNTAX      TruthValue
            MAX-ACCESS  read-create
            STATUS      current
            DESCRIPTION
                "Indicates whether the transport stream is treated as the EPG input.
                 The default value is false.
                "
            ::= { hwDocsQamInputTSEntry 10 } 
            
         -- 1.3.6.1.4.1.2011.6.187.16.1.11
         hwDocsQamInputTSJitter  OBJECT-TYPE  
            SYNTAX      Integer32(0..250)
            UNITS       "millisecond"
            MAX-ACCESS  read-create
            STATUS      current
            DESCRIPTION
                "Indicates the network jitter allowed. The default value is 100. 0 indicatdes network jitter is not allowed.
                "
            ::= { hwDocsQamInputTSEntry 11 }
            
        -- 1.3.6.1.4.1.2011.6.187.16.1.12
        hwDocsQamInputTSRTPSequenceErrorCounter  OBJECT-TYPE  
            SYNTAX      Counter64
            MAX-ACCESS  read-only
            STATUS      current
            DESCRIPTION
                "Indicates the RTP sequence error counter of input TS.
                "
            ::= { hwDocsQamInputTSEntry 12 }
            
        -- 1.3.6.1.4.1.2011.6.187.16.1.13   
        hwDocsQamInputTSRedundancyMode        OBJECT-TYPE
            SYNTAX      INTEGER
                  {
                  backup(1),
                  seamless(2),
                  invalid(255)
                  }
            MAX-ACCESS  read-create
            STATUS      current
            DESCRIPTION
                "Indicates the redundancy mode of input TS. 
                 Options: 
                 1. backup(1)   -Indicates the redundancy mode in which one TS is selected from two input TSs. 
                                 When the secondary multicast IP address is valid and the protection mode is not configured, the default redundancy mode is backup. 
                 2. seamless(2) -Indicates that two input TSs are merged into one output TS, which is complete. 
                 3. invalid(255)-Indicates that the secondary multicast IP address is not configured and the redundancy mode is not used.  
                "
            ::= { hwDocsQamInputTSEntry 13 } 
            
        -- 1.3.6.1.4.1.2011.6.187.16.1.14   
        hwDocsQamInputTSUdpPort        OBJECT-TYPE
            SYNTAX      InetPortNumber
            MAX-ACCESS  read-create
            STATUS      current
            DESCRIPTION
                "Indicates the UDP port number of the input TS. The default value is 0, indicating that the UDP port number is invalid.
                 Range: 0-65535
                "
            ::= { hwDocsQamInputTSEntry 14 }
            
        -- 1.3.6.1.4.1.2011.6.187.16.1.15   
        hwDocsQamInputTSSecondaryUdpPort        OBJECT-TYPE
            SYNTAX      InetPortNumber
            MAX-ACCESS  read-create
            STATUS      current
            DESCRIPTION
                "Indicates the secondary UDP port number of the input TS. The default value is 0, indicating that the UDP port number is invalid.
                 Range: 0-65535
                "
            ::= { hwDocsQamInputTSEntry 15 }  
            
        -- 1.3.6.1.4.1.2011.6.187.16.1.16   
        hwDocsQamInputTSMode        OBJECT-TYPE
            SYNTAX      INTEGER
                  {
                  dvb(1),
                  mpeg(2)
                  }
            MAX-ACCESS  read-create
            STATUS      current
            DESCRIPTION
                "Indicates the PSI parsing mode of an input TS.The default value is dvb(1). 
                 Options: 
                 1. dvb(1) - The PSI parsing mode is dvb.
                 2. mpeg(2)- The PSI parsing mode is mpeg.
                "
            ::= { hwDocsQamInputTSEntry 16 } 
                        
         -- 1.3.6.1.4.1.2011.6.187.16.1.17
         hwDocsQamInputTSTransportStreamID        OBJECT-TYPE
             SYNTAX      Unsigned32(0..65535|4294967295)
             MAX-ACCESS  read-only
             STATUS      current
             DESCRIPTION
                 "Indicates the transport stream id of an input TS .The default value is 4294967295, which indicates that stream id is not learned.
                 "
             ::= { hwDocsQamInputTSEntry 17 } 
                                                   
        -- 1.3.6.1.4.1.2011.6.187.16.1.18
         hwDocsQamInputTSRedundancyTriggers        OBJECT-TYPE
             SYNTAX      BITS
                  {
                  nobitrate(0),
                  nosignal(1),
                  patmissing(2),
                  pmtmissing(3)
                  }            
            MAX-ACCESS  read-create
            STATUS      current
            DESCRIPTION
                "Indicates the trigger conditions for protection switching on input TSs. The format is 4 bits. 
                 The default value is 0, indicates that there is no trigger condition for protection switching.  
                 Bit 0 -indicates that the trigger condition is no-bitrate.
                 Bit 1 -indicates that the trigger condition is no-signal. 
                 Bit 2 -indicates that the trigger condition is pat-missing.  
                 Bit 3 -indicates that the trigger condition is pmt-missing. 
                "
             ::= { hwDocsQamInputTSEntry 18 } 
                         
         -- 1.3.6.1.4.1.2011.6.187.16.1.19
         hwDocsQamInputTSRedundancyTriggersDefault        OBJECT-TYPE
            SYNTAX      TruthValue
            MAX-ACCESS  read-create
            STATUS      current
            DESCRIPTION
                "Indicates whether the default trigger condition is used for protection switching. 
                 The default value is true, indicates that the trigger condition of hwDocsQamInputTSDefaultSwitchoverTriggers 
                 is used when the value is true.
                "
             ::= { hwDocsQamInputTSEntry 19 } 
                          
        -- 1.3.6.1.4.1.2011.6.187.16.1.255 
        hwDocsQamInputTSRowStatus        OBJECT-TYPE
            SYNTAX       RowStatus
            MAX-ACCESS   read-create
            STATUS       current
            DESCRIPTION
                "Row status, used to query, create, modify, and delete a input TS table. 
                 It supports the active(1), createAndGo(4), and destroy(6) operations.
                 During query, the value of this leaf is always active(1).
                 During deletion, specify the value of this leaf to destroy(6).
                 During creation, specify the value of this leaf to createAndGo(4).
                 To modify the parameters of a channel profile table, this leaf need not be issued together.
                 Options:
                 1. active(1)      -indicates the query operation
                 2. createAndGo(4) -indicates the creating operation
                 3. destroy(6)     -indicates the deleting operation
                "
            ::= { hwDocsQamInputTSEntry 255 }  
            
        -- 1.3.6.1.4.1.2011.6.187.17
        hwDocsQamDVBDomainTable    OBJECT-TYPE
            SYNTAX          SEQUENCE OF HwDocsQamDVBDomainEntry
            MAX-ACCESS      not-accessible
            STATUS          current
            DESCRIPTION
                "Indicates the DVB video domain table used to manage information, such as EQAM's profile name.
                 The index of this table is hwDocsQamDVBDomainName.
                "
            ::= { hwEqamAn 17 }
        
        -- 1.3.6.1.4.1.2011.6.187.17.1
        hwDocsQamDVBDomainEntry    OBJECT-TYPE
            SYNTAX          HwDocsQamDVBDomainEntry
            MAX-ACCESS      not-accessible
            STATUS          current
            DESCRIPTION
                "Indicates the DVB video domain table used to manage information, such as EQAM's profile name.
                 The index of this entry is hwDocsQamDVBDomainName.
                "
            INDEX   
                { 
                hwDocsQamDVBDomainName
                }
            ::= { hwDocsQamDVBDomainTable  1 }
            
        HwDocsQamDVBDomainEntry ::=
            SEQUENCE 
                { 
                hwDocsQamDVBDomainName
                  OCTET STRING,
                hwDocsQamDVBDomainBindVideoProfile
                  OCTET STRING,
                hwDocsQamDVBDomainRowStatus
                  RowStatus,                
                hwDocsQamDVBDomainPSISIDefModeSDTA
                  HwEqamPsiPolicyDvbDomain,
                hwDocsQamDVBDomainPSISIDefModeSDTO
                  HwEqamPsiPolicyDvbDomain,
                hwDocsQamDVBDomainPSISIDefModeEITpfA
                  HwEqamPsiPolicyDvbDomain,
                hwDocsQamDVBDomainPSISIDefModeEITpfO
                  HwEqamPsiPolicyDvbDomain,
                hwDocsQamDVBDomainPSISIDefModeEITsFirstA
                  HwEqamPsiPolicyDvbDomain,
                hwDocsQamDVBDomainPSISIDefModeEITsFirstO
                  HwEqamPsiPolicyDvbDomain,
                hwDocsQamDVBDomainPSISIDefModeEITsSecondA
                  HwEqamPsiPolicyDvbDomain,
                hwDocsQamDVBDomainPSISIDefModeEITsSecondO
                  HwEqamPsiPolicyDvbDomain,
                hwDocsQamDVBDomainPSISIDefIntervalPAT
                  Integer32,
                hwDocsQamDVBDomainPSISIDefIntervalPMT
                  Integer32,
                hwDocsQamDVBDomainPSISIDefIntervalSDTA
                  Integer32,
                hwDocsQamDVBDomainPSISIDefIntervalSDTO
                  Integer32,
                hwDocsQamDVBDomainPSISIDefIntervalEITpfA
                  Integer32,
                hwDocsQamDVBDomainPSISIDefIntervalEITpfO
                  Integer32,
                hwDocsQamDVBDomainPSISIDefIntervalEITsFirstA
                  Integer32,
                hwDocsQamDVBDomainPSISIDefIntervalEITsFirstO
                  Integer32,
                hwDocsQamDVBDomainPSISIDefIntervalEITsSecondA
                  Integer32,
                hwDocsQamDVBDomainPSISIDefIntervalEITsSecondO
                  Integer32,
                hwDocsQamDVBDomainPSISIDefSpeedEIT
                  Integer32,  
                hwDocsQamDVBDomainDefChannelOutputRate 
                  Unsigned32
                }
            
        -- 1.3.6.1.4.1.2011.6.187.17.1.1 
        hwDocsQamDVBDomainName        OBJECT-TYPE
            SYNTAX       OCTET STRING (SIZE (1..15))
            MAX-ACCESS   not-accessible
            STATUS       current
            DESCRIPTION
                "Indicates the DVB video domain name.
                "
            ::= { hwDocsQamDVBDomainEntry 1 }
          
        -- 1.3.6.1.4.1.2011.6.187.17.1.2  
        hwDocsQamDVBDomainBindVideoProfile        OBJECT-TYPE
            SYNTAX       OCTET STRING (SIZE (0..15))
            MAX-ACCESS   read-create
            STATUS       current
            DESCRIPTION
                "Indicates the bind video profile name.
                "
            ::= { hwDocsQamDVBDomainEntry 2 }
          
        -- 1.3.6.1.4.1.2011.6.187.17.1.3
        hwDocsQamDVBDomainRowStatus        OBJECT-TYPE
            SYNTAX       RowStatus
            MAX-ACCESS   read-create
            STATUS       current
            DESCRIPTION
                "Row status, used to query, create, and delete a DVB domain table. 
                 It supports the active(1), createAndGo(4), and destroy(6) operations.
                 During query, the value of this leaf is always active(1).
                 During deletion, specify the value of this leaf to destroy(6).
                 During creation, specify the value of this leaf to createAndGo(4).
                 Options:
                 1. active(1)      -indicates the query operation
                 2. createAndGo(4) -indicates the creating operation
                 3. destroy(6)     -indicates the deleting operation
                "
            ::= { hwDocsQamDVBDomainEntry 3 }
            
        -- 1.3.6.1.4.1.2011.6.187.17.1.4
        hwDocsQamDVBDomainPSISIDefModeSDTA        OBJECT-TYPE
            SYNTAX       HwEqamPsiPolicyDvbDomain
            MAX-ACCESS   read-create
            STATUS       current
            DESCRIPTION
                "Indicates the output policy of SDT(Service Information Table) actual.
                 The default value is stop(1).
                "
            ::= { hwDocsQamDVBDomainEntry 4 }
            
         -- 1.3.6.1.4.1.2011.6.187.17.1.5
         hwDocsQamDVBDomainPSISIDefModeSDTO        OBJECT-TYPE
            SYNTAX       HwEqamPsiPolicyDvbDomain
            MAX-ACCESS   read-create
            STATUS       current
            DESCRIPTION
                "Indicates the output policy of SDT(Service Information Table) other.
                 The default value is stop(1).
                "
            ::= { hwDocsQamDVBDomainEntry 5 }
         
         -- 1.3.6.1.4.1.2011.6.187.17.1.6
         hwDocsQamDVBDomainPSISIDefModeEITpfA        OBJECT-TYPE
            SYNTAX       HwEqamPsiPolicyDvbDomain
            MAX-ACCESS   read-create
            STATUS       current
            DESCRIPTION
                "Indicates the output policy of actual TS, present/following EIT(Event Information Table).
                 The default value is stop(1).
                "
            ::= { hwDocsQamDVBDomainEntry 6 }
            
         -- 1.3.6.1.4.1.2011.6.187.17.1.7
         hwDocsQamDVBDomainPSISIDefModeEITpfO        OBJECT-TYPE
            SYNTAX       HwEqamPsiPolicyDvbDomain
            MAX-ACCESS   read-create
            STATUS       current
            DESCRIPTION
                "Indicates the output policy of other TS, present/following EIT(Event Information Table).
                 The default value is stop(1).
                "
            ::= { hwDocsQamDVBDomainEntry 7 }
            
         -- 1.3.6.1.4.1.2011.6.187.17.1.8
         hwDocsQamDVBDomainPSISIDefModeEITsFirstA        OBJECT-TYPE
            SYNTAX       HwEqamPsiPolicyDvbDomain
            MAX-ACCESS   read-create
            STATUS       current
            DESCRIPTION
                "Indicates the output policy of actual TS, first(day 0-3) schedual EIT(Event Information Table).
                 The default value is stop(1).
                "
            ::= { hwDocsQamDVBDomainEntry 8 }
            
         -- 1.3.6.1.4.1.2011.6.187.17.1.9
         hwDocsQamDVBDomainPSISIDefModeEITsFirstO        OBJECT-TYPE
            SYNTAX       HwEqamPsiPolicyDvbDomain
            MAX-ACCESS   read-create
            STATUS       current
            DESCRIPTION
                "Indicates the output policy of other TS, first(day 0-3) schedual EIT(Event Information Table).
                 The default value is stop(1).
                "
            ::= { hwDocsQamDVBDomainEntry 9 }
            
         -- 1.3.6.1.4.1.2011.6.187.17.1.10
         hwDocsQamDVBDomainPSISIDefModeEITsSecondA        OBJECT-TYPE
            SYNTAX       HwEqamPsiPolicyDvbDomain
            MAX-ACCESS   read-create
            STATUS       current
            DESCRIPTION
                "Indicates the output policy of actual TS, second(day 4-7) schedual EIT(Event Information Table).
                 The default value is stop(1).
                "
            ::= { hwDocsQamDVBDomainEntry 10 }
                  
         -- 1.3.6.1.4.1.2011.6.187.17.1.11
         hwDocsQamDVBDomainPSISIDefModeEITsSecondO        OBJECT-TYPE
            SYNTAX       HwEqamPsiPolicyDvbDomain
            MAX-ACCESS   read-create
            STATUS       current
            DESCRIPTION
                "Indicates the output policy of other TS, second(day 4-7) schedual EIT(Event Information Table).
                 The default value is stop(1).
                "
            ::= { hwDocsQamDVBDomainEntry 11 }
            
         -- 1.3.6.1.4.1.2011.6.187.17.1.12
         hwDocsQamDVBDomainPSISIDefIntervalPAT        OBJECT-TYPE
             SYNTAX      Integer32(30..1000)
             UNITS       "millisecond"
             MAX-ACCESS  read-create
             STATUS      current
             DESCRIPTION
                 "Indicates the playout interval of PAT(Program Association Table).
                 Default: 100
                 "
             ::= { hwDocsQamDVBDomainEntry 12 }
         
         -- 1.3.6.1.4.1.2011.6.187.17.1.13
         hwDocsQamDVBDomainPSISIDefIntervalPMT        OBJECT-TYPE
             SYNTAX      Integer32(30..1000)
             UNITS       "millisecond"
             MAX-ACCESS  read-create
             STATUS      current
             DESCRIPTION
                 "Indicates the playout interval of PMT(Program Map Table).
                 Default: 100
                 "
             ::= { hwDocsQamDVBDomainEntry 13 }
             
         -- 1.3.6.1.4.1.2011.6.187.17.1.14
         hwDocsQamDVBDomainPSISIDefIntervalSDTA        OBJECT-TYPE
             SYNTAX      Integer32(25..2000)
             UNITS       "millisecond"
             MAX-ACCESS  read-create
             STATUS      current
             DESCRIPTION
                 "Indicates the playout interval of SDT(Service Information Table) actual.
                 Default: 1000
                 "
             ::= { hwDocsQamDVBDomainEntry 14 }
         
         -- 1.3.6.1.4.1.2011.6.187.17.1.15
         hwDocsQamDVBDomainPSISIDefIntervalSDTO        OBJECT-TYPE
             SYNTAX      Integer32(25..10000)
             UNITS       "millisecond"
             MAX-ACCESS  read-create
             STATUS      current
             DESCRIPTION
                 "Indicates the playout interval of SDT(Service Information Table) other.
                 Default: 2000
                 "
             ::= { hwDocsQamDVBDomainEntry 15 }
         
         -- 1.3.6.1.4.1.2011.6.187.17.1.16
         hwDocsQamDVBDomainPSISIDefIntervalEITpfA        OBJECT-TYPE
             SYNTAX      Integer32(5000..10000)
             UNITS       "millisecond"
             MAX-ACCESS  read-create
             STATUS      current
             DESCRIPTION
                 "Indicates the playout interval of actual TS, present/following EIT(Event Information Table).
                 Default: 5000
                 "
             ::= { hwDocsQamDVBDomainEntry 16 }
         
         -- 1.3.6.1.4.1.2011.6.187.17.1.17
         hwDocsQamDVBDomainPSISIDefIntervalEITpfO        OBJECT-TYPE
             SYNTAX      Integer32(5000..20000)
             UNITS       "millisecond"
             MAX-ACCESS  read-create
             STATUS      current
             DESCRIPTION
                 "Indicates the playout interval of other TS, present/following EIT(Event Information Table).
                 Default: 20000
                 "
             ::= { hwDocsQamDVBDomainEntry 17 }
         
         -- 1.3.6.1.4.1.2011.6.187.17.1.18
         hwDocsQamDVBDomainPSISIDefIntervalEITsFirstA        OBJECT-TYPE
             SYNTAX      Integer32(4000..150000)
             UNITS       "millisecond"
             MAX-ACCESS  read-create
             STATUS      current
             DESCRIPTION
                 "Indicates the playout interval of actual TS, first(day 0-3) schedual EIT(Event Information Table).
                 Default: 60000
                 "
             ::= { hwDocsQamDVBDomainEntry 18 }
         
         -- 1.3.6.1.4.1.2011.6.187.17.1.19
         hwDocsQamDVBDomainPSISIDefIntervalEITsFirstO        OBJECT-TYPE
             SYNTAX      Integer32(4000..1000000)
             UNITS       "millisecond"
             MAX-ACCESS  read-create
             STATUS      current
             DESCRIPTION
                 "Indicates the playout interval of other TS, first(day 0-3) schedual EIT(Event Information Table).
                 Default: 600000
                 "
             ::= { hwDocsQamDVBDomainEntry 19 }
         
         -- 1.3.6.1.4.1.2011.6.187.17.1.20
         hwDocsQamDVBDomainPSISIDefIntervalEITsSecondA        OBJECT-TYPE
             SYNTAX      Integer32(25000..1500000)
             UNITS       "millisecond"
             MAX-ACCESS  read-create
             STATUS      current
             DESCRIPTION
                 "Indicates the playout interval of actual TS, second(day 4-7) schedual EIT(Event Information Table).
                 Default: 600000
                 "
             ::= { hwDocsQamDVBDomainEntry 20 }
         
         -- 1.3.6.1.4.1.2011.6.187.17.1.21
         hwDocsQamDVBDomainPSISIDefIntervalEITsSecondO        OBJECT-TYPE
             SYNTAX      Integer32(25000..3600000)
             UNITS       "millisecond"
             MAX-ACCESS  read-create
             STATUS      current
             DESCRIPTION
                 "Indicates the playout interval of other TS, second(day 4-7) schedual EIT(Event Information Table).
                 Default: 1800000
                 "
             ::= { hwDocsQamDVBDomainEntry 21 }
         
         -- 1.3.6.1.4.1.2011.6.187.17.1.22
         hwDocsQamDVBDomainPSISIDefSpeedEIT        OBJECT-TYPE
             SYNTAX      Integer32(100..4000)
             UNITS       "kbps"
             MAX-ACCESS  read-create
             STATUS      current
             DESCRIPTION
                 "Indicates the output speed of EIT(Event Information Table).
                 Default: 1000
                 "
             ::= { hwDocsQamDVBDomainEntry 22 }  
             
         -- 1.3.6.1.4.1.2011.6.187.17.1.23
         hwDocsQamDVBDomainDefChannelOutputRate        OBJECT-TYPE
             SYNTAX      Unsigned32(0..10000000)
             UNITS       "kbps"
             MAX-ACCESS  read-create
             STATUS      current
             DESCRIPTION
                 "Indicates the default output rate of the channel in the DVB domain.
                 Default: 38015
                 "
             ::= { hwDocsQamDVBDomainEntry 23 }
            
        -- 1.3.6.1.4.1.2011.6.187.18
        hwDocsQamVODPortConfigTable    OBJECT-TYPE
            SYNTAX          SEQUENCE OF HwDocsQamVODPortConfigEntry
            MAX-ACCESS      not-accessible
            STATUS          current
            DESCRIPTION
                "Indicates the VOD domain port table used to manage relationships between VOD domains and ports.
                 The index of this table is ifIndex.
                "
            ::= { hwEqamAn 18 }
        
        -- 1.3.6.1.4.1.2011.6.187.18.1
        hwDocsQamVODPortConfigEntry    OBJECT-TYPE
            SYNTAX          HwDocsQamVODPortConfigEntry
            MAX-ACCESS      not-accessible
            STATUS          current
            DESCRIPTION
                "Indicates the  VOD domain port table used to manage relationships between VOD domains and ports.
                 The index of this entry is ifIndex.
                "
            INDEX   
                { 
                ifIndex
                }
            ::= { hwDocsQamVODPortConfigTable  1 }
            
        HwDocsQamVODPortConfigEntry ::=
            SEQUENCE 
                { 
                hwDocsQamVODPortConfigDomainName
                  OCTET STRING,
                hwDocsQamVODPortConfigStartUDPPort
                  InetPortNumber,
                hwDocsQamVODPortConfigRowStatus
                  RowStatus                 
                }
                
        -- 1.3.6.1.4.1.2011.6.187.18.1.1 
        hwDocsQamVODPortConfigDomainName        OBJECT-TYPE
            SYNTAX       OCTET STRING (SIZE (1..15))
            MAX-ACCESS   read-create
            STATUS       current
            DESCRIPTION
                "Indicates the VOD domain name.
                "
            ::= { hwDocsQamVODPortConfigEntry 1 }  
            
        -- 1.3.6.1.4.1.2011.6.187.18.1.2
        hwDocsQamVODPortConfigStartUDPPort   OBJECT-TYPE
            SYNTAX       InetPortNumber
            MAX-ACCESS   read-create
            STATUS       current
            DESCRIPTION
                "Indicates the start udp value of port.
                "
            ::= { hwDocsQamVODPortConfigEntry 2 }

        -- 1.3.6.1.4.1.2011.6.187.18.1.3
        hwDocsQamVODPortConfigRowStatus OBJECT-TYPE
            SYNTAX       RowStatus
            MAX-ACCESS   read-create
            STATUS       current
            DESCRIPTION
                "Row status, used to query, create, modify, and delete a port table. 
                 It supports the active(1), createAndGo(4), and destroy(6) operations.
                 During query, the value of this leaf is always active(1).
                 During deletion, specify the value of this leaf to destroy(6).
                 During creation, specify the value of this leaf to createAndGo(4).
                 To modify the parameters of a channel profile table, this leaf need not be issued together.
                 Options:
                 1. active(1)      -indicates the query operation
                 2. createAndGo(4) -indicates the creating operation
                 3. destroy(6)     -indicates the deleting operation
                "
            ::= { hwDocsQamVODPortConfigEntry 3} 
            
        -- 1.3.6.1.4.1.2011.6.187.19
        hwDocsQamDVBPortConfigTable    OBJECT-TYPE
            SYNTAX          SEQUENCE OF HwDocsQamDVBPortConfigEntry
            MAX-ACCESS      not-accessible
            STATUS          current
            DESCRIPTION
                "Indicates the DVB domain port table used to manage relationships between DVB domains and ports.
                 The index of this table is ifIndex.
                "
            ::= { hwEqamAn 19 }
        
        -- 1.3.6.1.4.1.2011.6.187.19.1
        hwDocsQamDVBPortConfigEntry    OBJECT-TYPE
            SYNTAX          HwDocsQamDVBPortConfigEntry
            MAX-ACCESS      not-accessible
            STATUS          current
            DESCRIPTION
                "Indicates the  DVB domain port table used to manage relationships between DVB domains and ports.
                 The index of this entry is ifIndex.
                "
            INDEX   
                { 
                ifIndex
                }
            ::= { hwDocsQamDVBPortConfigTable  1 }
            
        HwDocsQamDVBPortConfigEntry ::=
            SEQUENCE 
                { 
                hwDocsQamDVBPortConfigDomainName
                  OCTET STRING,
                hwDocsQamDVBPortConfigRowStatus
                  RowStatus                 
                }
                
        -- 1.3.6.1.4.1.2011.6.187.19.1.1       
        hwDocsQamDVBPortConfigDomainName OBJECT-TYPE
            SYNTAX       OCTET STRING (SIZE (1..15))
            MAX-ACCESS   read-create
            STATUS       current
            DESCRIPTION
                "Indicates the DVB domain name.
                "
            ::= { hwDocsQamDVBPortConfigEntry 1 }

        -- 1.3.6.1.4.1.2011.6.187.19.1.2
        hwDocsQamDVBPortConfigRowStatus OBJECT-TYPE
            SYNTAX       RowStatus
            MAX-ACCESS   read-create
            STATUS       current
            DESCRIPTION
                "Row status, used to query, create, modify, and delete a port table. 
                 It supports the active(1), createAndGo(4), and destroy(6) operations.
                 During query, the value of this leaf is always active(1).
                 During deletion, specify the value of this leaf to destroy(6).
                 During creation, specify the value of this leaf to createAndGo(4).
                 To modify the parameters of a channel profile table, this leaf need not be issued together.
                 Options:
                 1. active(1)      -indicates the query operation
                 2. createAndGo(4) -indicates the creating operation
                 3. destroy(6)     -indicates the deleting operation
                "
            ::= { hwDocsQamDVBPortConfigEntry 2}    
            
        -- 1.3.6.1.4.1.2011.6.187.20
        hwDocsQamInputTSStateTable    OBJECT-TYPE
            SYNTAX          SEQUENCE OF HwDocsQamInputTSStateEntry
            MAX-ACCESS      not-accessible
            STATUS          current
            DESCRIPTION
                "Indicates the EQAM TS state.
                 The index of this table is hwDocsQamInputTSIndex.
                "
            ::= { hwEqamAn 20 }
    
        -- 1.3.6.1.4.1.2011.6.187.20.1
        hwDocsQamInputTSStateEntry    OBJECT-TYPE
            SYNTAX          HwDocsQamInputTSStateEntry
            MAX-ACCESS      not-accessible
            STATUS          current
            DESCRIPTION
                "Indicates the EQAM TS state.
                 The index of this entry is hwDocsQamInputTSIndex.
                "
            INDEX   
                { 
                hwDocsQamInputTSIndex
                }
            ::= { hwDocsQamInputTSStateTable  1 }
        
        HwDocsQamInputTSStateEntry ::=
            SEQUENCE 
                { 
                hwDocsQamInputTSStateSwitchOver
                  INTEGER,
                hwDocsQamInputTSStateActive
                  INTEGER,
                hwDocsQamInputTSStateSwitchoverReason
                  INTEGER
                }
        
        -- 1.3.6.1.4.1.2011.6.187.20.1
        hwDocsQamInputTSStateSwitchOver        OBJECT-TYPE
            SYNTAX      INTEGER
                  {
                  switchover(1),
                  none(255)
                  }
            MAX-ACCESS  read-create
            STATUS      current
            DESCRIPTION
                "Indicates the opeartion for swiching over, the default value is none(255).
                 Options: 
                 1. switchover(1)   -switch over the input TS.
                 2. none(255)       -no operation.
                "
            ::= { hwDocsQamInputTSStateEntry 1 }
      
        -- 1.3.6.1.4.1.2011.6.187.20.2
        hwDocsQamInputTSStateActive        OBJECT-TYPE
            SYNTAX      INTEGER
                  {
                  primary(1),
                  secondary(2),
                  none(255)
                  }
            MAX-ACCESS  read-only
            STATUS      current
            DESCRIPTION
                "Indicates the active state of input TS.
                 Options: 
                 1. primary(1)           -indicates the active state of the input TS is primary.
                 2. secondary(2)         -indicates the active state of the input TS is secondary.
                 3. none(255)            -indicates it is not a redundancy input TS.
                "
            ::= { hwDocsQamInputTSStateEntry 2 }  
                                    
        -- 1.3.6.1.4.1.2011.6.187.20.3
        hwDocsQamInputTSStateSwitchoverReason        OBJECT-TYPE
            SYNTAX      INTEGER
                  {
                  manual(1),
                  nobitrate(2),
                  nosignal(3),
                  patmissing(4),
                  pmtmissing(5),
                  none(255)
                  }
            MAX-ACCESS  read-only
            STATUS      current
            DESCRIPTION
                "Indicates the protection switching cause, the default value is none(255).
                 Options: 
                 1. manual(1)       -indicates the protection switching cause is manual switching.
                 2. nobitrate(2)    -indicates switching is triggered because no bit rate.
                 3. nosignal(3)     -indicates switching is triggered because no signals. 
                 4. patmissing(4)   -indicates switching is triggered because of PAT missing.
                 5. pmtmissing(5)   -indicates switching is triggered because of PMT missing.
                 6. none(255)       -indicates no switching occurs.
                "
            ::= { hwDocsQamInputTSStateEntry 3 }
            
        -- 1.3.6.1.4.1.2011.6.187.21
        hwDocsQamInputTSProgramTable    OBJECT-TYPE
            SYNTAX          SEQUENCE OF HwDocsQamInputTSProgramEntry
            MAX-ACCESS      not-accessible
            STATUS          current
            DESCRIPTION
                "Indicates the program information of input TS.
                 The indexes of this table are hwDocsQamInputTSIndex and hwDocsQamInputTSProgramIndex.
                "
            ::= { hwEqamAn 21 }
    
        -- 1.3.6.1.4.1.2011.6.187.21.1
        hwDocsQamInputTSProgramEntry    OBJECT-TYPE
            SYNTAX          HwDocsQamInputTSProgramEntry
            MAX-ACCESS      not-accessible
            STATUS          current
            DESCRIPTION
                "Indicates the program information of input TS.
                 The indexes of this entry are hwDocsQamInputTSIndex and hwDocsQamInputTSProgramIndex.
                "
            INDEX
                { 
                hwDocsQamInputTSIndex,
                hwDocsQamInputTSProgramIndex
                }
            ::= { hwDocsQamInputTSProgramTable  1 }  
            
        HwDocsQamInputTSProgramEntry ::=
            SEQUENCE 
                { 
                hwDocsQamInputTSProgramIndex
                  Unsigned32,    
                hwDocsQamInputTSProgramID
                  Integer32,
                hwDocsQamInputTSProgramPMTPID
                  Integer32,
                hwDocsQamInputTSProgramPCRPID
                  Integer32,
                hwDocsQamInputTSProgramESPIDList
                  OCTET STRING,
                hwDocsQamInputTSProgramESTypeList
                  OCTET STRING,
                hwDocsQamInputTSProgramDiscontinuityCounter
                  Counter64,
                hwDocsQamInputTSProgramName
                  OCTET STRING,
                hwDocsQamInputTSProgramState 
                  INTEGER,
                hwDocsQamInputTSProgramRate
                  Unsigned32,
                hwDocsQamInputTSProgramMaxRate
                  Unsigned32,
                hwDocsQamInputTSProgramMinRate
                  Unsigned32,
                hwDocsQamInputTSProgramCaNumber 
                  Unsigned32,
                hwDocsQamInputTSProgramCaPIDList
                  OCTET STRING,
                hwDocsQamInputTSProgramCaSystemIDList
                  OCTET STRING
                } 
                
        -- 1.3.6.1.4.1.2011.6.187.21.1.1  
        hwDocsQamInputTSProgramIndex        OBJECT-TYPE
            SYNTAX      Unsigned32 (1..65535)
            MAX-ACCESS  not-accessible
            STATUS      current
            DESCRIPTION
                "Indicates the index of a program in input TS.
                "
            ::= { hwDocsQamInputTSProgramEntry 1 }  
            
        -- 1.3.6.1.4.1.2011.6.187.21.1.2  
        hwDocsQamInputTSProgramID        OBJECT-TYPE
            SYNTAX      Integer32 (-1|0..65535)
            MAX-ACCESS  read-only
            STATUS      current
            DESCRIPTION
                "Indicates the program ID , the value -1 indicates that the program ID is invalid.
                "
            ::= { hwDocsQamInputTSProgramEntry 2 }    
            
        -- 1.3.6.1.4.1.2011.6.187.21.1.3    
        hwDocsQamInputTSProgramPMTPID        OBJECT-TYPE
            SYNTAX      Integer32 (-1|0..8191)
            MAX-ACCESS  read-only
            STATUS      current
            DESCRIPTION
                "Indicates the PMT PID, the value -1 indicates that the PMT PID is invalid.
                "
            ::= { hwDocsQamInputTSProgramEntry 3 }  
            
        -- 1.3.6.1.4.1.2011.6.187.21.1.4   
        hwDocsQamInputTSProgramPCRPID        OBJECT-TYPE
            SYNTAX      Integer32 (-1|0..8191)
            MAX-ACCESS  read-only
            STATUS      current
            DESCRIPTION
                "Indicates the PCR PID, the value -1 indicates that the PCR PID is invalid.
                "
            ::= { hwDocsQamInputTSProgramEntry 4 }      
            
        -- 1.3.6.1.4.1.2011.6.187.21.1.5
        hwDocsQamInputTSProgramESPIDList        OBJECT-TYPE
            SYNTAX       OCTET STRING (SIZE (0..128))
            MAX-ACCESS   read-only
            STATUS       current
            DESCRIPTION
              "Indicates the ESPID list. PID consists of two bytes and must be in one-to-one mapping with ESTypeList.
              "
            ::= { hwDocsQamInputTSProgramEntry 5 }  
            
        -- 1.3.6.1.4.1.2011.6.187.21.1.6
        hwDocsQamInputTSProgramESTypeList        OBJECT-TYPE
            SYNTAX       OCTET STRING (SIZE (0..64))
            MAX-ACCESS   read-only
            STATUS       current
            DESCRIPTION
              "Indicate the ES type list. One byte indicates a type, which must be in one-to-one mapping with the ESPID list for program.
              "
            ::= { hwDocsQamInputTSProgramEntry 6 }  
            
        -- 1.3.6.1.4.1.2011.6.187.21.1.7
        hwDocsQamInputTSProgramDiscontinuityCounter        OBJECT-TYPE  
            SYNTAX      Counter64
            MAX-ACCESS  read-only
            STATUS      current
            DESCRIPTION
                "Indicates the discontinuity counter of program.
                 Default: 0
                "
            ::= { hwDocsQamInputTSProgramEntry 7 }
            
        -- 1.3.6.1.4.1.2011.6.187.21.1.8
        hwDocsQamInputTSProgramName        OBJECT-TYPE  
            SYNTAX      OCTET STRING(SIZE(0..63))
            MAX-ACCESS  read-only
            STATUS      current
            DESCRIPTION
                "Indicates the program name in input TS.
                "
            ::= { hwDocsQamInputTSProgramEntry 8 }   
            
        -- 1.3.6.1.4.1.2011.6.187.21.1.9
        hwDocsQamInputTSProgramState        OBJECT-TYPE  
            SYNTAX      INTEGER
            {
              offline(1),
              online(2),  
              unknown(3)
            }            
            MAX-ACCESS  read-only
            STATUS      current
            DESCRIPTION
                "Indicates the program state in input TS.
                 Options: 
                 1. offline(1)   -indicates the offline state
                 2. online(2)    -indicates the online state
                 3. unknown(3)   -indicates the unknown state
                 The default value is offline(1).
                "
            ::= { hwDocsQamInputTSProgramEntry 9 }  
            
        -- 1.3.6.1.4.1.2011.6.187.21.1.10
        hwDocsQamInputTSProgramRate        OBJECT-TYPE  
            SYNTAX      Unsigned32  (0..4294967295) 
            UNITS       "kbps"
            MAX-ACCESS  read-only
            STATUS      current
            DESCRIPTION
                "Indicates the rate of program in input TS. Unit: kbit/s.
                 The default value is 0.
                "
            ::= { hwDocsQamInputTSProgramEntry 10 }

        -- 1.3.6.1.4.1.2011.6.187.21.1.11
        hwDocsQamInputTSProgramMaxRate        OBJECT-TYPE  
            SYNTAX      Unsigned32  (0..4294967295)
            UNITS       "kbps"
            MAX-ACCESS  read-only
            STATUS      current
            DESCRIPTION
                "Indicates the maximum rate of program in input TS. Unit: kbit/s.
                 The default value is 0.
                "
            ::= { hwDocsQamInputTSProgramEntry 11 }

        -- 1.3.6.1.4.1.2011.6.187.21.1.12
        hwDocsQamInputTSProgramMinRate        OBJECT-TYPE  
            SYNTAX      Unsigned32  (0..4294967295)
            UNITS       "kbps"
            MAX-ACCESS  read-only
            STATUS      current
            DESCRIPTION
                "Indicates the minimum rate of program in input TS. Unit: kbit/s.
                 The default value is 0.
                "
            ::= { hwDocsQamInputTSProgramEntry 12 }
             
        -- 1.3.6.1.4.1.2011.6.187.21.1.13
        hwDocsQamInputTSProgramCaNumber        OBJECT-TYPE  
            SYNTAX      Unsigned32  (0..4)
            MAX-ACCESS  read-only
            STATUS      current
            DESCRIPTION
                "Indicates the CA number of program in input TS.
                "
            ::= { hwDocsQamInputTSProgramEntry 13 }

        -- 1.3.6.1.4.1.2011.6.187.21.1.14
        hwDocsQamInputTSProgramCaPIDList        OBJECT-TYPE  
            SYNTAX      OCTET STRING(SIZE(0..8))
            MAX-ACCESS  read-only
            STATUS      current
            DESCRIPTION
                "Indicates the CA PID list of an input program.  A PID is displayed as a 2-byte string in network order. A maximum of 4 CAs are supported.
                The default value is null string.
                "
            ::= { hwDocsQamInputTSProgramEntry 14 }   
            
        -- 1.3.6.1.4.1.2011.6.187.21.1.15
        hwDocsQamInputTSProgramCaSystemIDList        OBJECT-TYPE  
            SYNTAX      OCTET STRING(SIZE(0..8))
            MAX-ACCESS  read-only
            STATUS      current
            DESCRIPTION
                "Indicates the CA system ID list of an input program. A CA system ID is displayed as a 2-byte string in network order. A maximum of 4 CAs are supported.
                The default value is null string.
                "
            ::= { hwDocsQamInputTSProgramEntry 15 }
                        
        -- 1.3.6.1.4.1.2011.6.187.22
        hwDocsQamOutputTSProgramTable    OBJECT-TYPE
            SYNTAX          SEQUENCE OF HwDocsQamOutputTSProgramEntry
            MAX-ACCESS      not-accessible
            STATUS          current
            DESCRIPTION
                "Indicates the program information of output TS.
                 The indexes of this table are ifIndex and hwDocsQamOutputTSProgramIndex.
                "
            ::= { hwEqamAn 22 }
    
        -- 1.3.6.1.4.1.2011.6.187.22.1
        hwDocsQamOutputTSProgramEntry    OBJECT-TYPE
            SYNTAX          HwDocsQamOutputTSProgramEntry
            MAX-ACCESS      not-accessible
            STATUS          current
            DESCRIPTION
                "Indicates the program information of output TS.
                 The indexes of this entry are ifIndex and hwDocsQamOutputTSProgramIndex.
                "
            INDEX
                { 
                ifIndex,
                hwDocsQamOutputTSProgramIndex
                }
            ::= { hwDocsQamOutputTSProgramTable  1 }  
            
        HwDocsQamOutputTSProgramEntry ::=
            SEQUENCE 
                { 
                hwDocsQamOutputTSProgramIndex
                  Unsigned32,    
                hwDocsQamOutputTSProgramID
                  Integer32,
                hwDocsQamOutputTSProgramPMTPID
                  Integer32,
                hwDocsQamOutputTSProgramPCRPID
                  Integer32,
                hwDocsQamOutputTSProgramESPIDList
                  OCTET STRING,
                hwDocsQamOutputTSProgramESTypeList
                  OCTET STRING,
                hwDocsQamOutputTSProgramName
                  OCTET STRING,
                hwDocsQamOutputTSProgramState
                  INTEGER,
                hwDocsQamOutputTSProgramRate
                  Unsigned32,    
                hwDocsQamOutputTSProgramMaxRate 
                  Unsigned32,    
                hwDocsQamOutputTSProgramMinRate
                  Unsigned32,    
                hwDocsQamOutputTSProgramCaNumber
                  Unsigned32,    
                hwDocsQamOutputTSProgramCaPIDList
                  OCTET STRING,
                hwDocsQamOutputTSProgramCaSystemIDList
                  OCTET STRING
                } 
                
        -- 1.3.6.1.4.1.2011.6.187.22.1.1  
        hwDocsQamOutputTSProgramIndex        OBJECT-TYPE
            SYNTAX      Unsigned32 (1..65535)
            MAX-ACCESS  not-accessible
            STATUS      current
            DESCRIPTION
                "Indicates the index of a program in output TS.
                "
            ::= { hwDocsQamOutputTSProgramEntry 1 }  
            
        -- 1.3.6.1.4.1.2011.6.187.22.1.2  
        hwDocsQamOutputTSProgramID        OBJECT-TYPE
            SYNTAX      Integer32 (-1|0..65535)
            MAX-ACCESS  read-only
            STATUS      current
            DESCRIPTION
                "Indicates the program ID , the value -1 indicates that the program ID is invalid.
                "
            ::= { hwDocsQamOutputTSProgramEntry 2 }    
            
        -- 1.3.6.1.4.1.2011.6.187.22.1.3    
        hwDocsQamOutputTSProgramPMTPID        OBJECT-TYPE
            SYNTAX      Integer32 (-1|0..8191)
            MAX-ACCESS  read-only
            STATUS      current
            DESCRIPTION
                "Indicates the PMT PID, the value -1 indicates that the PMT PID is invalid.
                "
            ::= { hwDocsQamOutputTSProgramEntry 3 }  
            
        -- 1.3.6.1.4.1.2011.6.187.22.1.4   
        hwDocsQamOutputTSProgramPCRPID        OBJECT-TYPE
            SYNTAX      Integer32 (-1|0..8191)
            MAX-ACCESS  read-only
            STATUS      current
            DESCRIPTION
                "Indicates the PCR PID, the value -1 indicates that the PCR PID is invalid.
                "
            ::= { hwDocsQamOutputTSProgramEntry 4 }      
            
        -- 1.3.6.1.4.1.2011.6.187.22.1.5
        hwDocsQamOutputTSProgramESPIDList        OBJECT-TYPE
            SYNTAX       OCTET STRING (SIZE (0..128))
            MAX-ACCESS   read-only
            STATUS       current
            DESCRIPTION
              "Indicates the ESPID list. PID consists of two bytes and must be in one-to-one mapping with ESTypeList.
              "
            ::= { hwDocsQamOutputTSProgramEntry 5 }  
            
        -- 1.3.6.1.4.1.2011.6.187.22.1.6
        hwDocsQamOutputTSProgramESTypeList        OBJECT-TYPE
            SYNTAX       OCTET STRING (SIZE (0..64))
            MAX-ACCESS   read-only
            STATUS       current
            DESCRIPTION
              "Indicate the ES type list. One byte indicates a type, which must be in one-to-one mapping with the ESPID list for program.
              "
            ::= { hwDocsQamOutputTSProgramEntry 6 }       
            
        -- 1.3.6.1.4.1.2011.6.187.22.1.7
        hwDocsQamOutputTSProgramName        OBJECT-TYPE
            SYNTAX       OCTET STRING (SIZE (0..63))
            MAX-ACCESS   read-only
            STATUS       current
            DESCRIPTION
              "Indicate the program name in output TS.
              "
            ::= { hwDocsQamOutputTSProgramEntry 7 } 
            
        -- 1.3.6.1.4.1.2011.6.187.22.1.8
        hwDocsQamOutputTSProgramState        OBJECT-TYPE
            SYNTAX      INTEGER
            {
              offline(1),
              online(2),  
              unknown(3)
            }            
            MAX-ACCESS   read-only
            STATUS       current
            DESCRIPTION
              "Indicate the state of program in output TS. 
               Options: 
                 1. offline(1)   -indicates the offline state
                 2. online(2)    -indicates the online state
                 3. unknown(3)   -indicates the unknown state
               The default value is offline(1).
              "
            ::= { hwDocsQamOutputTSProgramEntry 8 }    
            
        -- 1.3.6.1.4.1.2011.6.187.22.1.9
        hwDocsQamOutputTSProgramRate        OBJECT-TYPE
            SYNTAX       Unsigned32(0..4294967295)  
            UNITS        "kbps"
            MAX-ACCESS   read-only
            STATUS       current
            DESCRIPTION
              "Indicate the rate of program in output TS. Unit: kbit/s.
               The default value is 0.
              "
            ::= { hwDocsQamOutputTSProgramEntry 9 }
            
        -- 1.3.6.1.4.1.2011.6.187.22.1.10
        hwDocsQamOutputTSProgramMaxRate        OBJECT-TYPE
            SYNTAX       Unsigned32(0..4294967295)  
            UNITS        "kbps"
            MAX-ACCESS   read-only
            STATUS       current
            DESCRIPTION
              "Indicate the maximum rate of program in output TS. Unit: kbit/s.
               The default value is 0.
              "
            ::= { hwDocsQamOutputTSProgramEntry 10 }
            
        -- 1.3.6.1.4.1.2011.6.187.22.1.11
        hwDocsQamOutputTSProgramMinRate        OBJECT-TYPE
            SYNTAX       Unsigned32(0..4294967295)  
            UNITS        "kbps"
            MAX-ACCESS   read-only
            STATUS       current
            DESCRIPTION
              "Indicate the minimum rate of program in output TS. Unit: kbit/s.
               The default value is 0.
              "
            ::= { hwDocsQamOutputTSProgramEntry 11 }
            
        -- 1.3.6.1.4.1.2011.6.187.22.1.12
        hwDocsQamOutputTSProgramCaNumber        OBJECT-TYPE
            SYNTAX       Unsigned32(0..4)  
            MAX-ACCESS   read-only
            STATUS       current
            DESCRIPTION
              "Indicate the CA number of program in output TS.
              "
            ::= { hwDocsQamOutputTSProgramEntry 12 }
            
        -- 1.3.6.1.4.1.2011.6.187.22.1.13
        hwDocsQamOutputTSProgramCaPIDList        OBJECT-TYPE
            SYNTAX       OCTET STRING (SIZE (0..8))
            MAX-ACCESS   read-only
            STATUS       current
            DESCRIPTION
              "Indicates the CA PID list of an output program. A PID is displayed as a 2-byte string in network order. A maximum of 4 CAs are supported.
              "
            ::= { hwDocsQamOutputTSProgramEntry 13 }
            
        -- 1.3.6.1.4.1.2011.6.187.22.1.14
        hwDocsQamOutputTSProgramCaSystemIDList        OBJECT-TYPE
            SYNTAX       OCTET STRING (SIZE (0..8))
            MAX-ACCESS   read-only
            STATUS       current
            DESCRIPTION
              "Indicates the CA system ID list of an output program. A CA system ID is displayed as a 2-byte string in network order. A maximum of 4 CAs are supported.
              "
            ::= { hwDocsQamOutputTSProgramEntry 14 }            
                                                                                                                                                       
        -- 1.3.6.1.4.1.2011.6.187.23 
        hwDocsQamDVBInputTSStatisticsTable    OBJECT-TYPE
            SYNTAX          SEQUENCE OF HwDocsQamDVBInputTSStatisticsEntry
            MAX-ACCESS      not-accessible
            STATUS          current
            DESCRIPTION
                "Indicates the statistics table for input TS.
                 The index of this table is hwDocsQamDVBInputTSStatisticsIndex.
                "
            ::= { hwEqamAn 23 }
    
        -- 1.3.6.1.4.1.2011.6.187.23.1
        hwDocsQamDVBInputTSStatisticsEntry    OBJECT-TYPE
            SYNTAX          HwDocsQamDVBInputTSStatisticsEntry
            MAX-ACCESS      not-accessible
            STATUS          current
            DESCRIPTION
                "Indicates the statistics table for input TS.
                 The index of this entry is hwDocsQamDVBInputTSStatisticsIndex.
                "
            INDEX   
                {
                hwDocsQamDVBInputTSStatisticsIndex
                }
            ::= { hwDocsQamDVBInputTSStatisticsTable  1 }
        
        HwDocsQamDVBInputTSStatisticsEntry ::=
            SEQUENCE 
                { 
                hwDocsQamDVBInputTSStatisticsIndex
                  Unsigned32,
                hwDocsQamDVBInputTSStatisticsOperMode
                  INTEGER,
                hwDocsQamDVBInputTSPackets
                  Counter64,
                hwDocsQamDVBInputTSCountOfJitterOverflow
                  Counter64,
                hwDocsQamDVBInputTSCountOfJitterUnderflow
                  Counter64,
                hwDocsQamDVBInputTSDiscontinuityCounter
                  Counter64,
                hwDocsQamDVBInputTSRTPSequenceErrorCounter
                  Counter64,
                hwDocsQamDVBInputTSPATErrors
                  Counter64,
                hwDocsQamDVBInputTSPATMissings
                  Counter64,
                hwDocsQamDVBInputTSPMTErrors
                  Counter64,              
                hwDocsQamDVBInputTSPMTMissings
                  Counter64,
                hwDocsQamDVBInputTSOriginalPrimaryRTPSequenceErrorCounter
                  Counter64,
                hwDocsQamDVBInputTSOriginalSecondaryRTPSequenceErrorCounter
                  Counter64,
                hwDocsQamDVBInputTSSeamlessAverageDelay
                  Unsigned32,
                hwDocsQamDVBInputTSSeamlessMaxDelay
                  Unsigned32,
                hwDocsQamDVBInputTSSeamlessMinDelay
                  Unsigned32,  
                hwDocsQamInputTSStatisticsLastCleared
                  DateAndTime,
                hwDocsQamInputTSSeamlessPrimaryPacketSpacing
                  Unsigned32,
                hwDocsQamInputTSSeamlessSecondaryPacketSpacing
                  Unsigned32,
                hwDocsQamInputTSSeamlessPrimaryPacketSpacingMax
                  Unsigned32,
                hwDocsQamInputTSSeamlessSecondaryPacketSpacingMax
                  Unsigned32
                }
        
        -- 1.3.6.1.4.1.2011.6.187.23.1.1   
        hwDocsQamDVBInputTSStatisticsIndex        OBJECT-TYPE
            SYNTAX      Unsigned32 (1..65535)
            MAX-ACCESS  not-accessible
            STATUS      current
            DESCRIPTION
                "Indicates the index of statistics table for input TS.
                "
            ::= { hwDocsQamDVBInputTSStatisticsEntry 1 }
          
        -- 1.3.6.1.4.1.2011.6.187.23.1.2   
        hwDocsQamDVBInputTSStatisticsOperMode        OBJECT-TYPE
            SYNTAX      INTEGER
            {
              clearStatistic(1),
              invalid(-1)
            }
            MAX-ACCESS  read-write
            STATUS      current
            DESCRIPTION
                "Indicates the operation mode. The set operation can clear statistics for input TS. 
                 Options: 
                 1. clearStatistic(1) -indicates clearing statistics for input TS
                 2. invalid(-1)       -indicates invalid
                "
            ::= { hwDocsQamDVBInputTSStatisticsEntry 2 }
          
        -- 1.3.6.1.4.1.2011.6.187.23.1.3   
        hwDocsQamDVBInputTSPackets        OBJECT-TYPE
            SYNTAX      Counter64
            MAX-ACCESS  read-only
            STATUS      current
            DESCRIPTION
                "Indicates packet statistics for input TS.
                "
            ::= { hwDocsQamDVBInputTSStatisticsEntry 3 }

        -- 1.3.6.1.4.1.2011.6.187.23.1.4   
        hwDocsQamDVBInputTSCountOfJitterOverflow        OBJECT-TYPE
            SYNTAX      Counter64
            MAX-ACCESS  read-only
            STATUS      current
            DESCRIPTION
                "Indicates the jitter overflow statistics.
                "
            ::= { hwDocsQamDVBInputTSStatisticsEntry 4 }
          
        -- 1.3.6.1.4.1.2011.6.187.23.1.5   
        hwDocsQamDVBInputTSCountOfJitterUnderflow        OBJECT-TYPE
            SYNTAX      Counter64
            MAX-ACCESS  read-only
            STATUS      current
            DESCRIPTION
                "Indicates the jitter underflow statistics.
                "
            ::= { hwDocsQamDVBInputTSStatisticsEntry 5 }   
            
        -- 1.3.6.1.4.1.2011.6.187.23.1.6  
        hwDocsQamDVBInputTSDiscontinuityCounter        OBJECT-TYPE
            SYNTAX      Counter64
            MAX-ACCESS  read-only
            STATUS      current
            DESCRIPTION
                "Indicates the discontinuity counter of input TS.
                "
            ::= { hwDocsQamDVBInputTSStatisticsEntry 6 }
            
        -- 1.3.6.1.4.1.2011.6.187.23.1.7
        hwDocsQamDVBInputTSRTPSequenceErrorCounter        OBJECT-TYPE
            SYNTAX      Counter64
            MAX-ACCESS  read-only
            STATUS      current
            DESCRIPTION
                "Indicates the RTP sequence error counter of input TS.
                "
            ::= { hwDocsQamDVBInputTSStatisticsEntry 7 }
                        
        -- 1.3.6.1.4.1.2011.6.187.23.1.8
        hwDocsQamDVBInputTSPATErrors        OBJECT-TYPE
            SYNTAX      Counter64
            MAX-ACCESS  read-only
            STATUS      current
            DESCRIPTION
                "Indicates the number of program association table (PAT) errors of the input transport stream (TS).
                "
            ::= { hwDocsQamDVBInputTSStatisticsEntry 8 }
                        
        -- 1.3.6.1.4.1.2011.6.187.23.1.9
        hwDocsQamDVBInputTSPATMissings        OBJECT-TYPE
            SYNTAX      Counter64
            MAX-ACCESS  read-only
            STATUS      current
            DESCRIPTION
                "Indicates the number of lost PATs of the input TS.
                "
            ::= { hwDocsQamDVBInputTSStatisticsEntry 9 }
                        
        -- 1.3.6.1.4.1.2011.6.187.23.1.10
        hwDocsQamDVBInputTSPMTErrors        OBJECT-TYPE
            SYNTAX      Counter64
            MAX-ACCESS  read-only
            STATUS      current
            DESCRIPTION
                "Indicates the number of program map table (PMT) errors of the input TS.
                "
            ::= { hwDocsQamDVBInputTSStatisticsEntry 10 }
                        
        -- 1.3.6.1.4.1.2011.6.187.23.1.11
        hwDocsQamDVBInputTSPMTMissings        OBJECT-TYPE
            SYNTAX      Counter64
            MAX-ACCESS  read-only
            STATUS      current
            DESCRIPTION
                "Indicates the number of lost PMTs of the input TS.
                "
            ::= { hwDocsQamDVBInputTSStatisticsEntry 11 }
             
        -- 1.3.6.1.4.1.2011.6.187.23.1.12
        hwDocsQamDVBInputTSOriginalPrimaryRTPSequenceErrorCounter  OBJECT-TYPE
            SYNTAX      Counter64
            MAX-ACCESS  read-only
            STATUS      current
            DESCRIPTION
                "Indicates the primary original RTP error count of the input TS.
                "
            ::= { hwDocsQamDVBInputTSStatisticsEntry 12 }
            
        -- 1.3.6.1.4.1.2011.6.187.23.1.13
        hwDocsQamDVBInputTSOriginalSecondaryRTPSequenceErrorCounter  OBJECT-TYPE
            SYNTAX      Counter64
            MAX-ACCESS  read-only
            STATUS      current
            DESCRIPTION
                "Indicates the secondary original RTP error count of the input TS. 
                "
            ::= { hwDocsQamDVBInputTSStatisticsEntry 13 }
            
        -- 1.3.6.1.4.1.2011.6.187.23.1.14
        hwDocsQamDVBInputTSSeamlessAverageDelay  OBJECT-TYPE
            SYNTAX      Unsigned32(0..4294967295)
            UNITS       "millisecond"
            MAX-ACCESS  read-only
            STATUS      current
            DESCRIPTION
                "Indicates the average delay of the input TS in seamless mode.
                The default value is 4294967295, indicates that no delay is detected.
                "
            ::= { hwDocsQamDVBInputTSStatisticsEntry 14 }
            
        -- 1.3.6.1.4.1.2011.6.187.23.1.15
        hwDocsQamDVBInputTSSeamlessMaxDelay  OBJECT-TYPE
            SYNTAX      Unsigned32(0..4294967295)
            UNITS       "millisecond"
            MAX-ACCESS  read-only
            STATUS      current
            DESCRIPTION
                "Indicates the maximum delay of the input TS in seamless mode. 
                The default value is 4294967295, indicates that no delay is detected.
                "
            ::= { hwDocsQamDVBInputTSStatisticsEntry 15 }
            
        -- 1.3.6.1.4.1.2011.6.187.23.1.16
        hwDocsQamDVBInputTSSeamlessMinDelay  OBJECT-TYPE
            SYNTAX      Unsigned32(0..4294967295)
            UNITS       "millisecond"
            MAX-ACCESS  read-only
            STATUS      current
            DESCRIPTION
                "Indicates the minimum delay of the input TS in seamless mode. 
                The default value is 4294967295, indicates that no delay is detected.
                "
            ::= { hwDocsQamDVBInputTSStatisticsEntry 16 }
           
        -- 1.3.6.1.4.1.2011.6.187.23.1.17
        hwDocsQamInputTSStatisticsLastCleared  OBJECT-TYPE
            SYNTAX      DateAndTime
            MAX-ACCESS  read-only
            STATUS      current
            DESCRIPTION
                "Indicates the time on which input TS statistics are cleared the last time.
                The default value is 1970-01-01 00:00:00, indicates 
                        input TS statistics has never been cleared.  
                "
            ::= { hwDocsQamDVBInputTSStatisticsEntry 17 }
                        
        -- 1.3.6.1.4.1.2011.6.187.23.1.18
        hwDocsQamInputTSSeamlessPrimaryPacketSpacing  OBJECT-TYPE
            SYNTAX      Unsigned32(0..4294967295)
            UNITS       "millisecond"
            MAX-ACCESS  read-only
            STATUS      current
            DESCRIPTION
                "Indicates the interval for packet transmission for the primary TS of the input TS in seamless mode.
                The default value is 4294967295, indicates that no interval is detected.
                "
            ::= { hwDocsQamDVBInputTSStatisticsEntry 18 }
                        
        -- 1.3.6.1.4.1.2011.6.187.23.1.19
        hwDocsQamInputTSSeamlessSecondaryPacketSpacing  OBJECT-TYPE
            SYNTAX      Unsigned32(0..4294967295)
            UNITS       "millisecond"
            MAX-ACCESS  read-only
            STATUS      current
            DESCRIPTION
                "Indicates the interval for packet transmission for the secondary TS of the input TS in seamless mode.
                The default value is 4294967295, indicates that no interval is detected.
                "
            ::= { hwDocsQamDVBInputTSStatisticsEntry 19 }
                        
        -- 1.3.6.1.4.1.2011.6.187.23.1.20
        hwDocsQamInputTSSeamlessPrimaryPacketSpacingMax  OBJECT-TYPE
            SYNTAX      Unsigned32(0..4294967295)
            UNITS       "millisecond"
            MAX-ACCESS  read-only
            STATUS      current
            DESCRIPTION
                "Indicates the maximum interval for packet transmission for the primary TS of the input TS in seamless mode.
                The default value is 4294967295, indicates that no interval is detected.
                "
            ::= { hwDocsQamDVBInputTSStatisticsEntry 20 }
                        
        -- 1.3.6.1.4.1.2011.6.187.23.1.21
        hwDocsQamInputTSSeamlessSecondaryPacketSpacingMax  OBJECT-TYPE
            SYNTAX      Unsigned32(0..4294967295)
            UNITS       "millisecond"
            MAX-ACCESS  read-only
            STATUS      current
            DESCRIPTION
                "Indicates the maximum interval for packet transmission for the secondary TS of the input TS in seamless mode. 
                The default value is 4294967295, indicates that no interval is detected.
                "
            ::= { hwDocsQamDVBInputTSStatisticsEntry 21 }
   
        -- 1.3.6.1.4.1.2011.6.187.30
        hwDocsQamDVBDomainChannelTable    OBJECT-TYPE
            SYNTAX          SEQUENCE OF HwDocsQamDVBDomainChannelEntry
            MAX-ACCESS      not-accessible
            STATUS          current
            DESCRIPTION
                "Indicates the DVB domain channel table used to configure the networkid, streamid and output policy of channels in a DVB domain.
                 The indexes of this table are hwDocsQamDVBDomainName and hwDocsQamDVBDomainChannelID.
                "
            ::= { hwEqamAn 30 }
            
        -- 1.3.6.1.4.1.2011.6.187.30.1
        hwDocsQamDVBDomainChannelEntry    OBJECT-TYPE
            SYNTAX          HwDocsQamDVBDomainChannelEntry
            MAX-ACCESS      not-accessible
            STATUS          current
            DESCRIPTION
                "Indicates the DVB domain channel table used to configure the networkid, streamid and output policy of channels in a DVB domain.
                 The indexes of this entry are hwDocsQamDVBDomainName and hwDocsQamDVBDomainChannelID.
                "
            INDEX   
                { 
                hwDocsQamDVBDomainName,
                hwDocsQamDVBDomainChannelID
                }
            ::= { hwDocsQamDVBDomainChannelTable 1 }
            
        HwDocsQamDVBDomainChannelEntry ::=
            SEQUENCE 
                { 
                hwDocsQamDVBDomainChannelID
                  Unsigned32,
                hwDocsQamDVBDomainChannelNetworkID
                  Unsigned32,
                hwDocsQamDVBDomainChannelTransportStreamID
                  Unsigned32,
                hwDocsQamDVBDomainChannelPSISIModeSDTA
                  HwEqamPsiPolicyChannnel,
                hwDocsQamDVBDomainChannelPSISIModeSDTO
                  HwEqamPsiPolicyChannnel,
                hwDocsQamDVBDomainChannelPSISIModeEITpfA
                  HwEqamPsiPolicyChannnel,
                hwDocsQamDVBDomainChannelPSISIModeEITpfO
                  HwEqamPsiPolicyChannnel,
                hwDocsQamDVBDomainChannelPSISIModeEITsFirstA
                  HwEqamPsiPolicyChannnel,
                hwDocsQamDVBDomainChannelPSISIModeEITsFirstO
                  HwEqamPsiPolicyChannnel,
                hwDocsQamDVBDomainChannelPSISIModeEITsSecondA
                  HwEqamPsiPolicyChannnel,
                hwDocsQamDVBDomainChannelPSISIModeEITsSecondO
                  HwEqamPsiPolicyChannnel,
                hwDocsQamDVBDomainChannelOriginalNetworkID   
                  Unsigned32,
                hwDocsQamDVBDomainChannelOutputRate
                  Unsigned32,  
                hwDocsQamDVBDomainChannelOutputEnable 
                  TruthValue
                }
        
        -- 1.3.6.1.4.1.2011.6.187.30.1.1
        hwDocsQamDVBDomainChannelID        OBJECT-TYPE
            SYNTAX       Unsigned32(1..255)
            MAX-ACCESS   not-accessible
            STATUS       current
            DESCRIPTION
                "Indicates the channel ID.
                "
            ::= { hwDocsQamDVBDomainChannelEntry 1 }
        
        -- 1.3.6.1.4.1.2011.6.187.30.1.2
        hwDocsQamDVBDomainChannelNetworkID        OBJECT-TYPE
            SYNTAX       Unsigned32(0..65535|4294967295)
            MAX-ACCESS   read-write
            STATUS       current
            DESCRIPTION
                "Indicates the network id of the channel.
                The default value is 4294967295, indicating the network id of the channel is invalid.
                "
            ::= { hwDocsQamDVBDomainChannelEntry 2 }
        
        -- 1.3.6.1.4.1.2011.6.187.30.1.3
        hwDocsQamDVBDomainChannelTransportStreamID        OBJECT-TYPE
            SYNTAX       Unsigned32(0..65535|4294967295)
            MAX-ACCESS   read-write
            STATUS       current
            DESCRIPTION
                "Indicates the transport stream id of the channel.
                The default value is 4294967295, indicating the stream id of the channel is invalid.
                "
            ::= { hwDocsQamDVBDomainChannelEntry 3 }
        
        -- 1.3.6.1.4.1.2011.6.187.30.1.4
        hwDocsQamDVBDomainChannelPSISIModeSDTA        OBJECT-TYPE
            SYNTAX       HwEqamPsiPolicyChannnel
            MAX-ACCESS   read-write
            STATUS       current
            DESCRIPTION
                "Indicates the output policy of SDT(Service Information Table) actual.
                 The default value is default(3).
                "
            ::= { hwDocsQamDVBDomainChannelEntry 4 }
        
        -- 1.3.6.1.4.1.2011.6.187.30.1.5
        hwDocsQamDVBDomainChannelPSISIModeSDTO        OBJECT-TYPE
            SYNTAX       HwEqamPsiPolicyChannnel
            MAX-ACCESS   read-write
            STATUS       current
            DESCRIPTION
                "Indicates the output policy of SDT(Service Information Table) other.
                 The default value is default(3).
                "
            ::= { hwDocsQamDVBDomainChannelEntry 5 }
        
        -- 1.3.6.1.4.1.2011.6.187.30.1.6
        hwDocsQamDVBDomainChannelPSISIModeEITpfA        OBJECT-TYPE
            SYNTAX       HwEqamPsiPolicyChannnel
            MAX-ACCESS   read-write
            STATUS       current
            DESCRIPTION
                "Indicates the output policy of actual TS, present/following EIT(Event Information Table).
                 The default value is default(3).
                "
            ::= { hwDocsQamDVBDomainChannelEntry 6 }
        
        -- 1.3.6.1.4.1.2011.6.187.30.1.7
        hwDocsQamDVBDomainChannelPSISIModeEITpfO        OBJECT-TYPE
            SYNTAX       HwEqamPsiPolicyChannnel
            MAX-ACCESS   read-write
            STATUS       current
            DESCRIPTION
                "Indicates the output policy of other TS, present/following EIT(Event Information Table).
                 The default value is default(3).
                "
            ::= { hwDocsQamDVBDomainChannelEntry 7 }
        
        -- 1.3.6.1.4.1.2011.6.187.30.1.8
        hwDocsQamDVBDomainChannelPSISIModeEITsFirstA        OBJECT-TYPE
            SYNTAX       HwEqamPsiPolicyChannnel
            MAX-ACCESS   read-write
            STATUS       current
            DESCRIPTION
                "Indicates the output policy of actual TS, first(day 0-3) schedual EIT(Event Information Table).
                 The default value is default(3).
                "
            ::= { hwDocsQamDVBDomainChannelEntry 8 }
        
        -- 1.3.6.1.4.1.2011.6.187.30.1.9
        hwDocsQamDVBDomainChannelPSISIModeEITsFirstO        OBJECT-TYPE
            SYNTAX       HwEqamPsiPolicyChannnel
            MAX-ACCESS   read-write
            STATUS       current
            DESCRIPTION
                "Indicates the output policy of other TS, first(day 0-3) schedual EIT(Event Information Table).
                 The default value is default(3).
                "
            ::= { hwDocsQamDVBDomainChannelEntry 9 }
        
        -- 1.3.6.1.4.1.2011.6.187.30.1.10
        hwDocsQamDVBDomainChannelPSISIModeEITsSecondA        OBJECT-TYPE
            SYNTAX       HwEqamPsiPolicyChannnel
            MAX-ACCESS   read-write
            STATUS       current
            DESCRIPTION
                "Indicates the output policy of actual TS, second(day 4-7) schedual EIT(Event Information Table).
                 The default value is default(3).
                "
            ::= { hwDocsQamDVBDomainChannelEntry 10 }
        
        -- 1.3.6.1.4.1.2011.6.187.30.1.11
        hwDocsQamDVBDomainChannelPSISIModeEITsSecondO        OBJECT-TYPE
            SYNTAX       HwEqamPsiPolicyChannnel
            MAX-ACCESS   read-write
            STATUS       current
            DESCRIPTION
                "Indicates the output policy of other TS, second(day 4-7) schedual EIT(Event Information Table).
                 The default value is default(3).
                "
            ::= { hwDocsQamDVBDomainChannelEntry 11 }
                        
                -- 1.3.6.1.4.1.2011.6.187.30.1.12
        hwDocsQamDVBDomainChannelOriginalNetworkID        OBJECT-TYPE
            SYNTAX       Unsigned32(0..65535|4294967295)
            MAX-ACCESS   read-write
            STATUS       current
            DESCRIPTION
                "Indicates the original network ID of a DVB channel.
                The default value is 4294967295, which indicates that no original network ID is configured.
                When no original network ID is configured, the value of hwDocsQamDVBDomainChannelNetworkID takes effect.
                "
            ::= { hwDocsQamDVBDomainChannelEntry 12 }
            
                -- 1.3.6.1.4.1.2011.6.187.30.1.13
        hwDocsQamDVBDomainChannelOutputRate        OBJECT-TYPE
            SYNTAX       Unsigned32(0..10000000|4294967295)  
            UNITS        "kbps"
            MAX-ACCESS   read-write
            STATUS       current
            DESCRIPTION
                "Indicates the output rate of the channel in the DVB domain.
                The default value is 4294967295, which indicates that no output rate of the channel is configured.
                And the value of hwDocsQamDVBDomainDefChannelOutputRate takes effect.
                "
            ::= { hwDocsQamDVBDomainChannelEntry 13 }  
            
        -- 1.3.6.1.4.1.2011.6.187.30.1.14
        hwDocsQamDVBDomainChannelOutputEnable        OBJECT-TYPE
            SYNTAX       TruthValue  
            MAX-ACCESS   read-create
            STATUS       current
            DESCRIPTION
                "Indicates the status of the channel in the DVB domain.
                 The default value is true.
                "
            ::= { hwDocsQamDVBDomainChannelEntry 14 }             
                        
        -- 1.3.6.1.4.1.2011.6.187.31
        hwDocsQamFMDomainTable    OBJECT-TYPE
            SYNTAX          SEQUENCE OF HwDocsQamFMDomainEntry
            MAX-ACCESS      not-accessible
            STATUS          current
            DESCRIPTION
                "Indicates the FM domain table used to create or destroy a FM domain.
                 The index of this table is hwDocsQamFMDomainName.
                "
            ::= { hwEqamAn 31 }
        
        -- 1.3.6.1.4.1.2011.6.187.31.1
        hwDocsQamFMDomainEntry    OBJECT-TYPE
            SYNTAX          HwDocsQamFMDomainEntry
            MAX-ACCESS      not-accessible
            STATUS          current
            DESCRIPTION
                "Indicates the FM domain table used to create or destroy a FM domain.
                 The index of this entry is hwDocsQamFMDomainName.
                "
            INDEX   
                { 
                hwDocsQamFMDomainName
                }
            ::= { hwDocsQamFMDomainTable 1 }
            
        HwDocsQamFMDomainEntry ::=
            SEQUENCE 
                { 
                hwDocsQamFMDomainName
                  OCTET STRING,
                hwDocsQamFMDomainMapNumber
                  Unsigned32,
                hwDocsQamFMDomainPortNumber
                  Unsigned32,
                hwDocsQamFMDomainRowStatus
                  RowStatus
                }

        -- 1.3.6.1.4.1.2011.6.187.31.1.1 
        hwDocsQamFMDomainName        OBJECT-TYPE
            SYNTAX       OCTET STRING (SIZE (1..15))
            MAX-ACCESS   not-accessible
            STATUS       current
            DESCRIPTION
                "Indicates the FM domain name.
                "
            ::= { hwDocsQamFMDomainEntry 1 }
            
        -- 1.3.6.1.4.1.2011.6.187.31.1.2
        hwDocsQamFMDomainMapNumber    OBJECT-TYPE   
            SYNTAX       Unsigned32 
            MAX-ACCESS   read-only
            STATUS       current
            DESCRIPTION
                "Indicates the number of FM mapping in the FM domain.
                "
            ::= { hwDocsQamFMDomainEntry 2 }
        
        -- 1.3.6.1.4.1.2011.6.187.31.1.3
        hwDocsQamFMDomainPortNumber    OBJECT-TYPE   
            SYNTAX       Unsigned32 
            MAX-ACCESS   read-only
            STATUS       current
            DESCRIPTION
                "Indicates the number of ports added in the FM domain.
                "
            ::= { hwDocsQamFMDomainEntry 3 }
          
        -- 1.3.6.1.4.1.2011.6.187.31.1.4  
        hwDocsQamFMDomainRowStatus        OBJECT-TYPE
            SYNTAX       RowStatus
            MAX-ACCESS   read-create
            STATUS       current
            DESCRIPTION
                "Row status, used to query, create, and delete a FM domain table. 
                 It supports the active(1), createAndGo(4) and destroy(6) operations.
                 During query, the value of this leaf is always active(1).
                 During deletion, specify the value of this leaf to destroy(6).
                 During creation, specify the value of this leaf to createAndGo(4).
                 Options:
                 1. active(1)      -indicates the query operation
                 2. createAndGo(4) -indicates the creating operation
                 3. destroy(6)     -indicates the deleting operation
                "
            ::= { hwDocsQamFMDomainEntry 4 }
            
        -- 1.3.6.1.4.1.2011.6.187.32
        hwDocsQamFmMapTable        OBJECT-TYPE
            SYNTAX          SEQUENCE OF HwDocsQamFmMapEntry
            MAX-ACCESS      not-accessible
            STATUS          current
            DESCRIPTION
                "Indicates the FM mapping table used to configure the mapping between video streams and cable channels.
                 The indexes of this table are hwDocsQamFMDomainName and hwDocsQamFmMapIndex.
                "
            ::= { hwEqamAn 32 }
    
        -- 1.3.6.1.4.1.2011.6.187.32.1
        hwDocsQamFmMapEntry    OBJECT-TYPE
            SYNTAX          HwDocsQamFmMapEntry
            MAX-ACCESS      not-accessible
            STATUS          current
            DESCRIPTION
                "Indicates the FM mapping table used to configure the mapping between video streams and cable channels.
                 The indexes of this entry are hwDocsQamFMDomainName and hwDocsQamFmMapIndex.
                "
            INDEX   
                { 
                hwDocsQamFMDomainName,
                hwDocsQamFmMapIndex
                }
            ::= { hwDocsQamFmMapTable  1 }
        
        HwDocsQamFmMapEntry ::=
            SEQUENCE 
                { 
                hwDocsQamFmMapIndex
                  Unsigned32,
                hwDocsQamFmInputTs
                  Unsigned32,
                hwDocsQamFmInputProgramID
                  Unsigned32,
                hwDocsQamFmChannelID
                  Unsigned32,
                hwDocsQamFmMapRowStatus
                  RowStatus
                }
                
        -- 1.3.6.1.4.1.2011.6.187.32.1.1   
        hwDocsQamFmMapIndex        OBJECT-TYPE
            SYNTAX      Unsigned32 (1..65535|4294967295)
            MAX-ACCESS  not-accessible
            STATUS      current
            DESCRIPTION
                "Indicates the index of a FM mapping table. 
                 You can also fill 4294967295 and the system will automatically allocate an index.
                "
            ::= { hwDocsQamFmMapEntry 1 }
          
        -- 1.3.6.1.4.1.2011.6.187.32.1.2   
        hwDocsQamFmInputTs        OBJECT-TYPE
            SYNTAX      Unsigned32(1..65535)
            MAX-ACCESS  read-create
            STATUS      current
            DESCRIPTION
                "Indicates the index of a input TS.
                "
            ::= { hwDocsQamFmMapEntry 2 }
          
        -- 1.3.6.1.4.1.2011.6.187.32.1.3   
        hwDocsQamFmInputProgramID        OBJECT-TYPE
            SYNTAX      Unsigned32(1..65535)
            MAX-ACCESS  read-create
            STATUS      current
            DESCRIPTION
                "Indicates the program ID in the input TS.
                "
            ::= { hwDocsQamFmMapEntry 3 }
          
        -- 1.3.6.1.4.1.2011.6.187.32.1.4   
        hwDocsQamFmChannelID        OBJECT-TYPE
            SYNTAX      Unsigned32(1..255)
            MAX-ACCESS  read-create
            STATUS      current
            DESCRIPTION
                "Indicates the channel ID.
                "
            ::= { hwDocsQamFmMapEntry 4 }
            
        -- 1.3.6.1.4.1.2011.6.187.32.1.5  
        hwDocsQamFmMapRowStatus        OBJECT-TYPE
            SYNTAX       RowStatus
            MAX-ACCESS   read-create
            STATUS       current
            DESCRIPTION
                "Row status, used to query, create, and delete a FM mapping. 
                 It supports the active(1), createAndGo(4) and destroy(6) operations.
                 During query, the value of this leaf is always active(1).
                 During deletion, specify the value of this leaf to destroy(6).
                 During creation, specify the value of this leaf to createAndGo(4).
                 Options:
                 1. active(1)      -indicates the query operation
                 2. createAndGo(4) -indicates the creating operation
                 3. destroy(6)     -indicates the deleting operation
                "
            ::= { hwDocsQamFmMapEntry 5 }
          
        -- 1.3.6.1.4.1.2011.6.187.33
        hwDocsQamFMPortConfigTable    OBJECT-TYPE
            SYNTAX          SEQUENCE OF HwDocsQamFMPortConfigEntry
            MAX-ACCESS      not-accessible
            STATUS          current
            DESCRIPTION
                "Indicates the FM domain port table used to manage relationships between FM domains and ports.
                 The index of this table is ifIndex.
                "
            ::= { hwEqamAn 33 }
        
        -- 1.3.6.1.4.1.2011.6.187.33.1
        hwDocsQamFMPortConfigEntry    OBJECT-TYPE
            SYNTAX          HwDocsQamFMPortConfigEntry
            MAX-ACCESS      not-accessible
            STATUS          current
            DESCRIPTION
                "Indicates the FM domain port table used to manage relationships between FM domains and ports.
                 The index of this entry is ifIndex.
                "
            INDEX   
                { 
                ifIndex
                }
            ::= { hwDocsQamFMPortConfigTable 1 }
            
        HwDocsQamFMPortConfigEntry ::=
            SEQUENCE 
                { 
                hwDocsQamFMPortConfigDomainName
                  OCTET STRING,
                hwDocsQamFMPortConfigRowStatus
                  RowStatus                 
                }
                
        -- 1.3.6.1.4.1.2011.6.187.33.1.1       
        hwDocsQamFMPortConfigDomainName OBJECT-TYPE
            SYNTAX       OCTET STRING (SIZE (1..15))
            MAX-ACCESS   read-create
            STATUS       current
            DESCRIPTION
                "Indicates the FM domain name.
                "
            ::= { hwDocsQamFMPortConfigEntry 1 }

        -- 1.3.6.1.4.1.2011.6.187.33.1.2
        hwDocsQamFMPortConfigRowStatus OBJECT-TYPE
            SYNTAX       RowStatus
            MAX-ACCESS   read-create
            STATUS       current
            DESCRIPTION
                "Row status, used to query, create, modify, and delete a port table. 
                 It supports the active(1), createAndGo(4), and destroy(6) operations.
                 During query, the value of this leaf is always active(1).
                 During deletion, specify the value of this leaf to destroy(6).
                 During creation, specify the value of this leaf to createAndGo(4).
                 Options:
                 1. active(1)      -indicates the query operation
                 2. createAndGo(4) -indicates the creating operation
                 3. destroy(6)     -indicates the deleting operation
                "
            ::= { hwDocsQamFMPortConfigEntry 2}    
            
        -- 1.3.6.1.4.1.2011.6.187.34
        hwDocsQamFmRDSTable    OBJECT-TYPE
            SYNTAX          SEQUENCE OF HwDocsQamFmRDSEntry
            MAX-ACCESS      not-accessible
            STATUS          current
            DESCRIPTION
                "Indicates the FM RDS table used to configure the RDS information of a FM mapping in FM domain.
                 The indexes of this table are hwDocsQamFMDomainName and hwDocsQamFmMapIndex.
                "
            ::= { hwEqamAn 34 }
    
        -- 1.3.6.1.4.1.2011.6.187.34.1
        hwDocsQamFmRDSEntry    OBJECT-TYPE
            SYNTAX          HwDocsQamFmRDSEntry
            MAX-ACCESS      not-accessible
            STATUS          current
            DESCRIPTION
                "Indicates the FM RDS table used to configure the RDS information of a FM mapping in FM domain.
                 The indexes of this entry are hwDocsQamFMDomainName and hwDocsQamFmMapIndex.
                "
            INDEX   
                { 
                hwDocsQamFMDomainName,
                hwDocsQamFmMapIndex
                }
            ::= { hwDocsQamFmRDSTable  1 }
        
        HwDocsQamFmRDSEntry ::=
            SEQUENCE 
                {
                hwDocsQamFmRDSAdminStatus
                  INTEGER,
                hwDocsQamFmRDSProgramType
                  Integer32,
                hwDocsQamFmRDSProgramServiceName
                  OCTET STRING,
                hwDocsQamFmRDSRadioText
                  OCTET STRING,
                hwDocsQamFmRDSCoverageArea
                  Integer32,
                hwDocsQamFmRDSProgramReference
                  Integer32,
                hwDocsQamFmRDSMode
                  INTEGER,              
                hwDocsQamFmRDSCTDef
                  INTEGER,              
                hwDocsQamFmRDSCountryCodeValue
                  Integer32,
                hwDocsQamFmRDSTATP
                  BITS,
                hwDocsQamFmRDSDI
                  BITS,
                hwDocsQamFmRDSMS
                  BITS,
                hwDocsQamFmRDSCT
                  INTEGER,              
                hwDocsQamFmRDSRealTimeClock 
                  DateAndTime
                }
                
        -- 1.3.6.1.4.1.2011.6.187.34.1.1
        hwDocsQamFmRDSAdminStatus        OBJECT-TYPE
            SYNTAX      INTEGER
                  {
                  disable(1),
                  enable(2)
                  }
            MAX-ACCESS  read-create
            STATUS      current
            DESCRIPTION
                "Indicates the status of RDS admin, the default value is disable(1).
                 Options: 
                 1. disable(1) -indicates the status of RDS admin is disable.
                 2. enable(2)  -indicates the status of RDS admin is enable.
                "
            ::= { hwDocsQamFmRDSEntry 1 }
        
        -- 1.3.6.1.4.1.2011.6.187.34.1.2   
        hwDocsQamFmRDSProgramType        OBJECT-TYPE
            SYNTAX      Integer32(0..31)
            MAX-ACCESS  read-create
            STATUS      current
            DESCRIPTION
                "Indicates the type of program. Refers to the section 3.2.1.2 of EN50067_RDS_Standard.pdf
                 0 - None.
                 1 - News.
                 2 - Affairs.
                 3 - Info.
                 4 - Sport.
                 5 - Educate.
                 6 - Drama.
                 7 - Culture.
                 8 - Science.
                 9 - Varied.
                 10 - Pop M.
                 11 - Rock M.
                 12 - Easy M.
                 13 - Light M.
                 14 - Classics.
                 15 - Other M.
                 16 - Weather.
                 17 - Finance.
                 18 - Children.
                 19 - Social.
                 20 - Religion.
                 21 - Phone In.
                 22 - Travel.
                 23 - Leisure.
                 24 - Jazz.
                 25 - Country.
                 26 - Nation M.
                 27 - Oldies.
                 28 - Folk M.
                 29 - Document.
                 30 - TEST.
                 31 - Alarm !.
                 the default value is 0.
                "
            ::= { hwDocsQamFmRDSEntry 2 }   
          
        -- 1.3.6.1.4.1.2011.6.187.34.1.3   
        hwDocsQamFmRDSProgramServiceName        OBJECT-TYPE
            SYNTAX      OCTET STRING (SIZE (0..8))
            MAX-ACCESS  read-create
            STATUS      current
            DESCRIPTION
                "Indicates the service name of the FM program.
                "
            ::= { hwDocsQamFmRDSEntry 3 }
          
        -- 1.3.6.1.4.1.2011.6.187.34.1.4   
        hwDocsQamFmRDSRadioText        OBJECT-TYPE
            SYNTAX      OCTET STRING (SIZE (0..64))
            MAX-ACCESS  read-create
            STATUS      current
            DESCRIPTION
                "Indicates the radio text of the FM program.
                "
            ::= { hwDocsQamFmRDSEntry 4 }
                    
        -- 1.3.6.1.4.1.2011.6.187.34.1.5   
        hwDocsQamFmRDSCoverageArea        OBJECT-TYPE
            SYNTAX      Integer32(0..15)
            MAX-ACCESS  read-create
            STATUS      current
            DESCRIPTION
                "Indicates the coverage area of the FM program. Refers to the section 3.2.1.1 of EN50067_RDS_Standard.pdf.
                0 - L.
                1 - I.
                2 - N.
                3 - S.
                4 - R1.
                5 - R2
                6 - R3.
                7 - R4.
                8 - R5.
                9 - R6.
                10 - R7.
                11 - R8.
                12 - R9.
                13 - R10.
                14 - R11.
                15 - R12.
                the default value is 0.
                "
            ::= { hwDocsQamFmRDSEntry 5 }
          
        -- 1.3.6.1.4.1.2011.6.187.34.1.6   
        hwDocsQamFmRDSProgramReference        OBJECT-TYPE
            SYNTAX      Integer32(0..255)
            MAX-ACCESS  read-create
            STATUS      current
            DESCRIPTION
                "Indicates the program reference value. 
                 The default value is 0.
                "
            ::= { hwDocsQamFmRDSEntry 6 }   
            
        -- 1.3.6.1.4.1.2011.6.187.34.1.7   
        hwDocsQamFmRDSMode        OBJECT-TYPE
            SYNTAX      INTEGER
                  {
                  manual(1),
                  embedded(2),
                  external(3)
                  }            
            MAX-ACCESS  read-write
            STATUS      current
            DESCRIPTION
                "Indicates the mode of RDS. The default value is manual(1).
                 Options: 
                 1. manual(1)  -indicates RDS is configured manually.
                 2. embedded(2)-indicates RDS information is embedded in the bit stream of FM.
                 3. external(3)-indicates RDS information is in the bit stream of PID.
                "
            ::= { hwDocsQamFmRDSEntry 7 }  
            
        -- 1.3.6.1.4.1.2011.6.187.34.1.8   
        hwDocsQamFmRDSCTDef        OBJECT-TYPE
            SYNTAX      INTEGER
                  {
                  enable(1),
                  disable(2),
                  invalid(3)
                  }             
            MAX-ACCESS  read-write
            STATUS      current
            DESCRIPTION
                "Indicates default Clock-time and date switch of RDS. The default value is invalid(3).
                 Options: 
                 1. enable(1)  -indicates the switch is on.
                 2. disable(2) -indicates the switch is off. 
                 3. invalid(3) -indicates the switch is invalid. 
                "
            ::= { hwDocsQamFmRDSEntry 8 }
            
        -- 1.3.6.1.4.1.2011.6.187.34.1.9   
        hwDocsQamFmRDSCountryCodeValue        OBJECT-TYPE
            SYNTAX      Integer32(0..15)           
            MAX-ACCESS  read-only
            STATUS      current
            DESCRIPTION
                "Indicates the country of the FM program. The default value is 0.
                "
            ::= { hwDocsQamFmRDSEntry 9 }

        -- 1.3.6.1.4.1.2011.6.187.34.1.10   
        hwDocsQamFmRDSTATP        OBJECT-TYPE
            SYNTAX      BITS
                  {
                  ta(0),
                  tp(1)
                  }            
            MAX-ACCESS  read-only
            STATUS      current
            DESCRIPTION
                "Indicates Traffic-announcement identification and Traffic-programme identification of RDS. The format is 2 bits. 
                The default value is 0. Refers to the section 3.2.1.3 of EN50067_RDS_Standard.pdf. 
                 Bit 0 -indicates Traffic-announcement identification.
                 Bit 1 -indicates Traffic-programme identification. 
                "
            ::= { hwDocsQamFmRDSEntry 10 }

        -- 1.3.6.1.4.1.2011.6.187.34.1.11   
        hwDocsQamFmRDSDI        OBJECT-TYPE
            SYNTAX      BITS
                  {
                  monostereo(0),
                  artificialhead(1),
                  compressed(2),
                  dynamicPtyIndicator(3)
                  }            
            MAX-ACCESS  read-only
            STATUS      current
            DESCRIPTION
                "Indicates the Decoder Identification and Dynamic PTY Indicator.The format is 4 bits. The default value is 0.
                Refers to the section 3.2.1.4 of EN50067_RDS_Standard.pdf. 
                 Bit 0 -Mono/Stereo.
                 Bit 1 -Not Artificial Head/Artificial Head. 
                 Bit 2 -Not Compressed/Compressed. 
                 Bit 3 -Static PTY/Dynamically switched. 
                "
            ::= { hwDocsQamFmRDSEntry 11 }

        -- 1.3.6.1.4.1.2011.6.187.34.1.12   
        hwDocsQamFmRDSMS        OBJECT-TYPE
            SYNTAX      BITS
                  {
                  ms(0)
                  } 
            MAX-ACCESS  read-only
            STATUS      current
            DESCRIPTION
                "Indicates the state of Music Speech switch. The format is 1 bit. The default value is 0, indicating the Music Speech switch is off. 
                Refers to the section 3.2.1.4 of EN50067_RDS_Standard.pdf. 
                "
            ::= { hwDocsQamFmRDSEntry 12 }

        -- 1.3.6.1.4.1.2011.6.187.34.1.13   
        hwDocsQamFmRDSCT        OBJECT-TYPE
            SYNTAX      INTEGER
                  {
                  on(1),
                  off(2),
                  invalid(3)
                  }             
            MAX-ACCESS  read-only
            STATUS      current
            DESCRIPTION
                "Indicates Clock-time and date switch. The default value is invalid(3).
                 Options: 
                 1. on(1)      -indicates the switch is on.
                 2. off(2)     -indicates the switch is off. 
                 3. invalid(3) -indicates the switch is invalid. 
                "
            ::= { hwDocsQamFmRDSEntry 13 }

        -- 1.3.6.1.4.1.2011.6.187.34.1.14   
        hwDocsQamFmRDSRealTimeClock        OBJECT-TYPE
            SYNTAX      DateAndTime
            MAX-ACCESS  read-only
            STATUS      current
            DESCRIPTION
                "Indicate date and time(with time zone) of RDS. The default value is 1900-01-01 00:00:00.
                "
            ::= { hwDocsQamFmRDSEntry 14 }
         
        -- 1.3.6.1.4.1.2011.6.187.35
        hwDocsQamDVBPIDMappingTable    OBJECT-TYPE
            SYNTAX          SEQUENCE OF HwDocsQamDVBPIDMappingEntry
            MAX-ACCESS      not-accessible
            STATUS          current
            DESCRIPTION
                "Indicates the DVB PID mapping table used to configure the input TS list, input PID list, output PID list of channels in a DVB domain.
                 The indexes of this table are hwDocsQamDVBDomainName and hwDocsQamDVBPIDMappingChannelID.
                "
            ::= { hwEqamAn 35 }
            
        -- 1.3.6.1.4.1.2011.6.187.35.1
        hwDocsQamDVBPIDMappingEntry    OBJECT-TYPE
            SYNTAX          HwDocsQamDVBPIDMappingEntry
            MAX-ACCESS      not-accessible
            STATUS          current
            DESCRIPTION
                "Indicates the DVB PID mapping table used to configure the input TS list, input PID list, output PID list of channels in a DVB domain.
                 The indexes of this entry are hwDocsQamDVBDomainName and hwDocsQamDVBPIDMappingChannelID.
                "
            INDEX   
                { 
                hwDocsQamDVBDomainName,
                hwDocsQamDVBPIDMappingChannelID
                }
            ::= { hwDocsQamDVBPIDMappingTable 1 }
            
        HwDocsQamDVBPIDMappingEntry ::=
            SEQUENCE 
                { 
                hwDocsQamDVBPIDMappingChannelID
                  Unsigned32,
                hwDocsQamDVBPIDMappingInputTSList
                  OCTET STRING,
                hwDocsQamDVBPIDMappingInputPIDList
                  OCTET STRING,
                hwDocsQamDVBPIDMappingOutputPIDList
                  OCTET STRING
               }
        
        -- 1.3.6.1.4.1.2011.6.187.35.1.1
        hwDocsQamDVBPIDMappingChannelID        OBJECT-TYPE
            SYNTAX       Unsigned32(1..255)
            MAX-ACCESS   not-accessible
            STATUS       current
            DESCRIPTION
                "Indicates the ChannelID.
                "
            ::= { hwDocsQamDVBPIDMappingEntry 1 }
        
        -- 1.3.6.1.4.1.2011.6.187.35.1.2
        hwDocsQamDVBPIDMappingInputTSList        OBJECT-TYPE
            SYNTAX       OCTET STRING(SIZE (0..16))
            MAX-ACCESS   read-create
            STATUS       current
            DESCRIPTION
                "Indicates the input TS list. Input TS ID consists of two bytes and must be in one-to-one mapping with input PID list and output PID list.
                "
            ::= { hwDocsQamDVBPIDMappingEntry 2 }
        
        -- 1.3.6.1.4.1.2011.6.187.35.1.3
        hwDocsQamDVBPIDMappingInputPIDList        OBJECT-TYPE
            SYNTAX       OCTET STRING(SIZE (0..16))
            MAX-ACCESS   read-create
            STATUS       current
            DESCRIPTION
                "Indicates the input PID list. Input PID consists of two bytes and must be in one-to-one mapping with input TS list and output PID list.
                "
            ::= { hwDocsQamDVBPIDMappingEntry 3 }
        
        -- 1.3.6.1.4.1.2011.6.187.35.1.4
        hwDocsQamDVBPIDMappingOutputPIDList        OBJECT-TYPE
            SYNTAX       OCTET STRING(SIZE (0..16))
            MAX-ACCESS   read-create
            STATUS       current
            DESCRIPTION
                "Indicates the output PID list. Output PID consists of two bytes and must be in one-to-one mapping with input TS list and input PID list.
                "
            ::= { hwDocsQamDVBPIDMappingEntry 4 }
            
        -- 1.3.6.1.4.1.2011.6.187.37
        hwDocsQamDVBProcessGroupTable    OBJECT-TYPE
            SYNTAX          SEQUENCE OF HwDocsQamDVBProcessGroupEntry
            MAX-ACCESS      not-accessible
            STATUS          current
            DESCRIPTION
                "Indicates the table for configuring the working board and protection board in the DVB service processing protection group, and perform switchover. 
                 The index of this table is hwDocsQamDVBProcessGroupID.
                "
            ::= { hwEqamAn 37 }
            
        -- 1.3.6.1.4.1.2011.6.187.37.1
        hwDocsQamDVBProcessGroupEntry    OBJECT-TYPE
            SYNTAX          HwDocsQamDVBProcessGroupEntry
            MAX-ACCESS      not-accessible
            STATUS          current
            DESCRIPTION
                "Indicates the table for configuring the working board and protection board in the DVB service processing protection group, and perform switchover. 
                 The index of this entry is hwDocsQamDVBProcessGroupID.
                "
            INDEX   
                { 
                hwDocsQamDVBProcessGroupID
                }
            ::= { hwDocsQamDVBProcessGroupTable 1 }
            
        HwDocsQamDVBProcessGroupEntry ::=
            SEQUENCE 
                { 
                hwDocsQamDVBProcessGroupID
                  Unsigned32,
                hwDocsQamDVBProcessGroupWorkFrameID
                  Unsigned32,
                hwDocsQamDVBProcessGroupWorkSlotID
                  Unsigned32,
                hwDocsQamDVBProcessGroupProtectFrameID
                  Unsigned32,
                hwDocsQamDVBProcessGroupProtectSlotID
                  Unsigned32,
                hwDocsQamDVBProcessGroupSwitchover
                  INTEGER,
                hwDocsQamDVBProcessGroupActiveFrameID
                  Unsigned32,
                hwDocsQamDVBProcessGroupActiveSlotID
                  Unsigned32,
                hwDocsQamDVBProcessGroupActive
                  INTEGER,
                hwDocsQamDVBProcessGroupRowStatus
                  RowStatus
               }
               
        -- 1.3.6.1.4.1.2011.6.187.37.1.1
        hwDocsQamDVBProcessGroupID        OBJECT-TYPE
            SYNTAX       Unsigned32(1..8|4294967295)
            MAX-ACCESS   not-accessible
            STATUS       current
            DESCRIPTION
                "Indicates the ID of a DVB service processing protection group.               
                "
            ::= { hwDocsQamDVBProcessGroupEntry 1 }
            
        -- 1.3.6.1.4.1.2011.6.187.37.1.2
        hwDocsQamDVBProcessGroupWorkFrameID        OBJECT-TYPE
            SYNTAX       Unsigned32(0..255|4294967295)
            MAX-ACCESS   read-create
            STATUS       current
            DESCRIPTION
                "Indicates the ID of the frame that accomdates the working board in a DVB service processing protection group. 
                "
            ::= { hwDocsQamDVBProcessGroupEntry 2 }
            
        -- 1.3.6.1.4.1.2011.6.187.37.1.3
        hwDocsQamDVBProcessGroupWorkSlotID        OBJECT-TYPE
            SYNTAX       Unsigned32(0..255|4294967295)
            MAX-ACCESS   read-create
            STATUS       current
            DESCRIPTION
                "Indicates the ID of the slot that accommodates the working board in a DVB service processing protection group. 
                "
            ::= { hwDocsQamDVBProcessGroupEntry 3 }
            
        -- 1.3.6.1.4.1.2011.6.187.37.1.4
        hwDocsQamDVBProcessGroupProtectFrameID        OBJECT-TYPE
            SYNTAX       Unsigned32(0..255|4294967295)
            MAX-ACCESS   read-create
            STATUS       current
            DESCRIPTION
                "Indicates the ID of the frame that accommodates the protection board in a DVB service processing protection group.
                "
            ::= { hwDocsQamDVBProcessGroupEntry 4 }
            
        -- 1.3.6.1.4.1.2011.6.187.37.1.5
        hwDocsQamDVBProcessGroupProtectSlotID        OBJECT-TYPE
            SYNTAX       Unsigned32(0..255|4294967295)
            MAX-ACCESS   read-create
            STATUS       current
            DESCRIPTION
                "Indicates the ID of the slot that accommodates the protection board in a DVB service processing protection group.
                "
            ::= { hwDocsQamDVBProcessGroupEntry 5 }
            
        -- 1.3.6.1.4.1.2011.6.187.37.1.6
        hwDocsQamDVBProcessGroupSwitchover        OBJECT-TYPE
            SYNTAX      INTEGER
                  {
                  switchover(1),
                  none(255)
                  }
            MAX-ACCESS  read-write
            STATUS      current
            DESCRIPTION
                "Indicates switchover in a DVB service processing protection group.
                 The default value is none(255).
                                 Options: 
                 1. switchover(1)   -Perform a switchover operation.
                 2. none(255)       -Do not perform any operation. 
                "
            ::= { hwDocsQamDVBProcessGroupEntry 6 }
            
        -- 1.3.6.1.4.1.2011.6.187.37.1.7
        hwDocsQamDVBProcessGroupActiveFrameID        OBJECT-TYPE
            SYNTAX       Unsigned32(0..255|4294967295)
            MAX-ACCESS   read-only
            STATUS       current
            DESCRIPTION
                "Indicates the ID of the frame that accommodates the active board in a DVB service processing protection group. 
                "
            ::= { hwDocsQamDVBProcessGroupEntry 7 }
            
        -- 1.3.6.1.4.1.2011.6.187.37.1.8
        hwDocsQamDVBProcessGroupActiveSlotID        OBJECT-TYPE
            SYNTAX       Unsigned32(0..255|4294967295)
            MAX-ACCESS   read-only
            STATUS       current
            DESCRIPTION
                "Indicates the ID of the slot that accommodates the active board in a DVB service processing protection group.
                "
            ::= { hwDocsQamDVBProcessGroupEntry 8 }
            
        -- 1.3.6.1.4.1.2011.6.187.37.1.9
        hwDocsQamDVBProcessGroupActive        OBJECT-TYPE
            SYNTAX       INTEGER
                  {
                  work(1),
                  protect(2),
                  none(255)
                  }
            MAX-ACCESS   read-only
            STATUS       current
            DESCRIPTION
                "Indicates the role of the active board in a DVB service processing protection group.
                Options:
                1. work(1)      -Indicates that the working board in a DVB service processing protection group is the active board.
                2. protect(2)   -Indicates that the protection board in a DVB service processing protection group is the active board.
                3. none(255)    -Indicates that the current DVB service processing protection group does not have an active board.
                "
            ::= { hwDocsQamDVBProcessGroupEntry 9 }
        
        -- 1.3.6.1.4.1.2011.6.187.37.1.10
        hwDocsQamDVBProcessGroupRowStatus        OBJECT-TYPE
            SYNTAX       RowStatus
            MAX-ACCESS   read-create
            STATUS       current
            DESCRIPTION
                "Indicates a row status for querying, creating, modifying, and deleting a DVB service processing protection group table. 
                 It supports active(1), createAndGo(4), and destroy(6) operations. 
                 During query operations, the value of this leaf is always active(1). 
                 During delete operations, the value of this leaf must be set to destroy(6).
                 During create operations, the value of this leaf must be set to createAndGo(4). 
                 This leaf is not mandatory when the table of a DVB service processing protection group needs to be modified.                            
                 Options:
                 1. active(1)      -indicates the query operation
                 2. createAndGo(4) -indicates the creating operation
                 3. destroy(6)     -indicates the deleting operation
                "
            ::= { hwDocsQamDVBProcessGroupEntry 10 }  
        
        -- 1.3.6.1.4.1.2011.6.187.38
        hwDocsQamInputPIDInfoTable    OBJECT-TYPE
            SYNTAX          SEQUENCE OF HwDocsQamInputPIDInfoEntry
            MAX-ACCESS      not-accessible
            STATUS          current
            DESCRIPTION
                "Indicates the input PID info table used to display the packet identifier (PID), PID type, PID subtype, PID rate,
                 maximum PID rate, minimum PID rate, PID scrambling information, program clock reference (PCR) association of the PID, 
                 continuity counter (CC) error count of the PID, ID and name of the program associated with the PID of the input TS.
                 The indexes of this table are hwDocsQamInputTSIndex and hwDocsQamInputPIDIndex.
                "
            ::= { hwEqamAn 38 }
            
        -- 1.3.6.1.4.1.2011.6.187.38.1
        hwDocsQamInputPIDInfoEntry    OBJECT-TYPE
            SYNTAX          HwDocsQamInputPIDInfoEntry
            MAX-ACCESS      not-accessible
            STATUS          current
            DESCRIPTION
                "Indicates the input PID info table used to display the packet identifier (PID), PID type, PID subtype, PID rate,
                 maximum PID rate, minimum PID rate, PID scrambling information, program clock reference (PCR) association of the PID, 
                 continuity counter (CC) error count of the PID, ID and name of the program associated with the PID of the input TS.
                 The indexes of this entry are hwDocsQamInputTSIndex and hwDocsQamInputPIDIndex.
                "
            INDEX   
                { 
                hwDocsQamInputTSIndex,
                hwDocsQamInputPIDIndex
                }
            ::= { hwDocsQamInputPIDInfoTable 1 }
            
        HwDocsQamInputPIDInfoEntry ::= 
            SEQUENCE 
                {
                hwDocsQamInputPIDIndex
                  Unsigned32,             
                hwDocsQamInputPID
                  Unsigned32, 
                hwDocsQamInputPIDType
                  HwEqamInputPIDType,
                hwDocsQamInputPIDStreamType
                  Integer32,
                hwDocsQamInputPIDRate
                  Unsigned32,
                hwDocsQamInputPIDMaxRate
                  Unsigned32,
                hwDocsQamInputPIDMinRate
                  Unsigned32,
                hwDocsQamInputPIDScambled
                  INTEGER,
                hwDocsQamInputPIDCCErrorCount
                  Counter64,
                hwDocsQamInputPIDPCRReference
                  TruthValue,
                hwDocsQamInputPIDProgramIDReference
                  Unsigned32,
                hwDocsQamInputPIDProgramNameReference
                  OCTET STRING
               } 
               
        -- 1.3.6.1.4.1.2011.6.187.38.1.1
        hwDocsQamInputPIDIndex        OBJECT-TYPE
            SYNTAX       Unsigned32(1..8192)
            MAX-ACCESS   not-accessible
            STATUS       current
            DESCRIPTION
                "Indicates the input PID index, whose value is obtained by adding 1 to the value of hwDocsQamInputPID.
                "
            ::= { hwDocsQamInputPIDInfoEntry 1 }
                      
        -- 1.3.6.1.4.1.2011.6.187.38.1.2
        hwDocsQamInputPID        OBJECT-TYPE
            SYNTAX       Unsigned32(0..8191)
            MAX-ACCESS   read-only
            STATUS       current
            DESCRIPTION
                "Indicates the value of input PID.
                "
            ::= { hwDocsQamInputPIDInfoEntry 2 }
        
        -- 1.3.6.1.4.1.2011.6.187.38.1.3
        hwDocsQamInputPIDType        OBJECT-TYPE
            SYNTAX       HwEqamInputPIDType
            MAX-ACCESS   read-only
            STATUS       current
            DESCRIPTION
                "Indicates the input PID type. The default value is unknown(255), indicating the unknown type. 
                "
            ::= { hwDocsQamInputPIDInfoEntry 3 }
        
        -- 1.3.6.1.4.1.2011.6.187.38.1.4
        hwDocsQamInputPIDStreamType        OBJECT-TYPE
            SYNTAX       Integer32(0..255)
            MAX-ACCESS   read-only
            STATUS       current
            DESCRIPTION
                "When the value of hwDocsQamInputPIDStreamType is 12, hwDocsQamInputPIDStreamType indicates the corresponding media type. 
                 For details about its value, see ISO/IEC 13818-1 [18] Program Map Table (PMT). Otherwise, the value of hwDocsQamInputPIDStreamType is 0. 
                "
            ::= { hwDocsQamInputPIDInfoEntry 4 }        

        -- 1.3.6.1.4.1.2011.6.187.38.1.5
        hwDocsQamInputPIDRate        OBJECT-TYPE
            SYNTAX       Unsigned32(0..4294967295)  
            UNITS        "kbps"
            MAX-ACCESS   read-only
            STATUS       current
            DESCRIPTION
                "Indicates the rate of the input PID. Unit: kbit/s.
                "
            ::= { hwDocsQamInputPIDInfoEntry 5 }        

        -- 1.3.6.1.4.1.2011.6.187.38.1.6
         hwDocsQamInputPIDMaxRate        OBJECT-TYPE
            SYNTAX       Unsigned32(0..4294967295)  
            UNITS        "kbps"
            MAX-ACCESS   read-only
            STATUS       current
            DESCRIPTION
                "Indicates the maximum rate of the input PID. Unit: kbit/s.
                "
            ::= { hwDocsQamInputPIDInfoEntry 6 }        
            
        -- 1.3.6.1.4.1.2011.6.187.38.1.7
        hwDocsQamInputPIDMinRate        OBJECT-TYPE
            SYNTAX       Unsigned32(0..4294967295)   
            UNITS        "kbps"
            MAX-ACCESS   read-only
            STATUS       current
            DESCRIPTION
                "Indicates the minimum rate of the input PID. Unit: kbit/s. 
                "
            ::= { hwDocsQamInputPIDInfoEntry 7 }        

        -- 1.3.6.1.4.1.2011.6.187.38.1.8
        hwDocsQamInputPIDScambled        OBJECT-TYPE
            SYNTAX       INTEGER
                  {
                  notScambled(1),
                  evenScambled(2),
                  oddScambled(3)
                  }
            MAX-ACCESS   read-only
            STATUS       current
            DESCRIPTION
                "Indicates the input PID scrambling information.
                Options:
                1. notScambled(1)  --Indicates no scrambling 
                2. evenScambled(2) --Indicates scrambling with even control word (CW)
                3. oddScambled(3)  --Indicates scrambling with odd CW
                "
            ::= { hwDocsQamInputPIDInfoEntry 8 }        

        -- 1.3.6.1.4.1.2011.6.187.38.1.9
        hwDocsQamInputPIDCCErrorCount        OBJECT-TYPE
            SYNTAX       Counter64           
            MAX-ACCESS   read-only
            STATUS       current
            DESCRIPTION
                "Indicates the CC error count of the input PID.
                "
            ::= { hwDocsQamInputPIDInfoEntry 9 }                

        -- 1.3.6.1.4.1.2011.6.187.38.1.10
        hwDocsQamInputPIDPCRReference        OBJECT-TYPE
            SYNTAX       TruthValue
            MAX-ACCESS   read-only
            STATUS       current
            DESCRIPTION
                "Indicates the PCR association of the input PID. The default value is false.
                "
            ::= { hwDocsQamInputPIDInfoEntry 10 }       

        -- 1.3.6.1.4.1.2011.6.187.38.1.11
        hwDocsQamInputPIDProgramIDReference        OBJECT-TYPE
            SYNTAX       Unsigned32(0..65535|4294967295)
            MAX-ACCESS   read-only
            STATUS       current
            DESCRIPTION
                "Indicates the ID of the program associated with the PID. The default value is 4294967295, indicating no associated program.
                "
            ::= { hwDocsQamInputPIDInfoEntry 11 }       

        -- 1.3.6.1.4.1.2011.6.187.38.1.12
        hwDocsQamInputPIDProgramNameReference        OBJECT-TYPE
            SYNTAX       OCTET STRING (SIZE (0..63))
            MAX-ACCESS   read-only
            STATUS       current
            DESCRIPTION
                "Indicates the name of the program associated with the PID.
                 The default value is an empty character string, indicating no associated program name..
                "
            ::= { hwDocsQamInputPIDInfoEntry 12 }       

        -- 1.3.6.1.4.1.2011.6.187.39
        hwDocsQamInputTSPIDTable    OBJECT-TYPE
            SYNTAX          SEQUENCE OF HwDocsQamInputTSPIDEntry
            MAX-ACCESS      not-accessible
            STATUS          current
            DESCRIPTION
                "Indicates the input TS PID table used to display the number of PIDs, PID list, and PID list status mask of the input TS.
                 The index of this table is hwDocsQamInputTSIndex.
                "
            ::= { hwEqamAn 39 }
            
        -- 1.3.6.1.4.1.2011.6.187.39.1
        hwDocsQamInputTSPIDEntry    OBJECT-TYPE
            SYNTAX          HwDocsQamInputTSPIDEntry
            MAX-ACCESS      not-accessible
            STATUS          current
            DESCRIPTION
                "Indicates the input TS PID table used to display the number of PIDs, PID list, and PID list status mask of the input TS.
                 The index of this entry is hwDocsQamInputTSIndex.
                "
            INDEX   
                { 
                hwDocsQamInputTSIndex
                }
            ::= { hwDocsQamInputTSPIDTable 1 }
            
        HwDocsQamInputTSPIDEntry ::=
            SEQUENCE 
                {
                hwDocsQamInputTSPIDNumber
                  Unsigned32, 
                hwDocsQamInputTSPIDList
                  OCTET STRING,
                hwDocsQamInputTSPIDStateMask
                  OCTET STRING
               }
                       
        -- 1.3.6.1.4.1.2011.6.187.39.1.1
        hwDocsQamInputTSPIDNumber        OBJECT-TYPE
            SYNTAX       Unsigned32(0..512)
            MAX-ACCESS   read-only
            STATUS       current
            DESCRIPTION
                "Indicates the number of the input TS PID.
                "
            ::= { hwDocsQamInputTSPIDEntry 1 }
        
        -- 1.3.6.1.4.1.2011.6.187.39.1.2
        hwDocsQamInputTSPIDList        OBJECT-TYPE
            SYNTAX       OCTET STRING (SIZE (0..1024))
            MAX-ACCESS   read-only
            STATUS       current
            DESCRIPTION
                "Format: 2 bytes in network byte order,
                 which indicates a PID. A maximum of 512 PIDs are supported.                  
                 a 2-byte bit-field value defined as follows:
                 Bit 0:xx
                 Bit 1:xx.
               "
            ::= { hwDocsQamInputTSPIDEntry 2 }
        
        -- 1.3.6.1.4.1.2011.6.187.39.1.3
        hwDocsQamInputTSPIDStateMask        OBJECT-TYPE
            SYNTAX       OCTET STRING (SIZE (0..1024))
            MAX-ACCESS   read-only
            STATUS       current
            DESCRIPTION
                "Indicates the PID list status mask of the input TS. The default value is an empty character string, indicating no PID list status mask.
                Format: 2 bytes in network byte order, which indicates a PID list status mask. A maximum of 512 PID list status masks are supported. 
                a 2-byte bit-field value defined as follows:
                 Bit 0:notScambled
                 Bit 1:evenScambled
                 Bit 2:oddScambled
                 Bit 3:pcrreferenced
                 Bit 4:ccerror.
                "
            ::= { hwDocsQamInputTSPIDEntry 3 }    
            
        -- 1.3.6.1.4.1.2011.6.187.40
        hwDocsQamLocationIDInsertionConfigObject   OBJECT IDENTIFIER 
        ::= { hwEqamAn 40 }
        
        -- 1.3.6.1.4.1.2011.6.187.40.1
        hwDocsQamLocationIDInsertionSwitch  OBJECT-TYPE
            SYNTAX       INTEGER
                  {
                  enabled(1),
                  disabled(2)
                  }
             MAX-ACCESS   read-write
            STATUS       current
            DESCRIPTION
                "Indicates the insertion function of the location ID. The default value is disabled(2).
                 Options:
                 1. enabled(1)  -indicates that the insertion function of the location ID is enabled.
                 2. disabled(2) -indicates that the insertion function of the location ID is disabled.
                "
            ::= { hwDocsQamLocationIDInsertionConfigObject 1 }               
        
        -- 1.3.6.1.4.1.2011.6.187.40.2
        hwDocsQamLocationIDInsertionPID   OBJECT-TYPE
            SYNTAX       Unsigned32 (3..15)
            MAX-ACCESS   read-write
            STATUS       current
            DESCRIPTION
                "Indicates the PID for the insertion function of the location ID. 
                 Range: 3-15
                 Default: 14
                "
            ::= { hwDocsQamLocationIDInsertionConfigObject 2 }               
                                   
        -- 1.3.6.1.4.1.2011.6.187.40.3
        hwDocsQamLocationIDInsertionInterval   OBJECT-TYPE
            SYNTAX       Unsigned32 (2..10)
            UNITS        "seconds"
            MAX-ACCESS   read-write
            STATUS       current
            DESCRIPTION
                "Indicates the Tx interval for the insertion function of the location ID.  
                 Range: 2-10 
                 Unit: second 
                 Default: 2
                "           
            ::= { hwDocsQamLocationIDInsertionConfigObject 3 }               
        
        -- 1.3.6.1.4.1.2011.6.187.41
        hwDocsQamLocationIDConfigTable   OBJECT-TYPE
            SYNTAX SEQUENCE OF HwDocsQamLocationIDConfigEntry
            MAX-ACCESS not-accessible
            STATUS current
            DESCRIPTION
                "Indicates the location ID of a port on the extended subrack.
                 The index of this table is ifIndex. 
                "
            ::= { hwEqamAn 41 }
        
        -- 1.3.6.1.4.1.2011.6.187.41.1
          hwDocsQamLocationIDConfigEntry OBJECT-TYPE
            SYNTAX HwDocsQamLocationIDConfigEntry
            MAX-ACCESS not-accessible
            STATUS current
            DESCRIPTION
                "Indicates the location ID of a port on the extended subrack.
                 The index of this entry is ifIndex. 
                "
            INDEX 
                { 
                ifIndex
                }
            ::= { hwDocsQamLocationIDConfigTable 1 }
        
          HwDocsQamLocationIDConfigEntry ::= 
            SEQUENCE 
                {
                hwDocsQamLocationID 
                    Unsigned32
                }
            
        -- 1.3.6.1.4.1.2011.6.187.41.1.1
          hwDocsQamLocationID OBJECT-TYPE
            SYNTAX       Unsigned32 (0..4294967295)
            MAX-ACCESS   read-write
            STATUS       current
            DESCRIPTION
                "Indicates the configured location ID.
                 4294967295 indicates the unconfigured location ID.
                 Range: 0..4294967295 
                 Default: 4294967295
                "           
            ::= { hwDocsQamLocationIDConfigEntry 1 }                       
   
        -- 1.3.6.1.4.1.2011.6.187.42
        hwDocsQamInputTSProgramEsTable    OBJECT-TYPE
            SYNTAX          SEQUENCE OF HwDocsQamInputTSProgramEsEntry
            MAX-ACCESS      not-accessible
            STATUS          current
            DESCRIPTION
                "Indicates the program elementary stream (ES) table of an input TS, which is used to query the rate, maximum rate, minimum rate,
                 number of CAs, CA PID list, and CA system ID list.
                 The indexes of this table are hwDocsQamInputTSIndex, hwDocsQamInputTSProgramIndex and hwDocsQamInputTSProgramEsIndex.
                "
            ::= { hwEqamAn 42}
            
        -- 1.3.6.1.4.1.2011.6.187.42.1
        hwDocsQamInputTSProgramEsEntry    OBJECT-TYPE
            SYNTAX          HwDocsQamInputTSProgramEsEntry
            MAX-ACCESS      not-accessible
            STATUS          current
            DESCRIPTION
                "Indicates the program elementary stream (ES) table of an input TS, which is used to query the rate, maximum rate, minimum rate,
                 number of CAs, CA PID list, and CA system ID list.
                 The indexes of this entry are hwDocsQamInputTSIndex, hwDocsQamInputTSProgramIndex and hwDocsQamInputTSProgramEsIndex.
                "
            INDEX   
                { 
                hwDocsQamInputTSIndex,
                hwDocsQamInputTSProgramIndex,
                hwDocsQamInputTSProgramEsIndex
                }
            ::= { hwDocsQamInputTSProgramEsTable 1 } 
            
        HwDocsQamInputTSProgramEsEntry ::=
            SEQUENCE 
                {
                hwDocsQamInputTSProgramEsIndex
                  Unsigned32, 
                hwDocsQamInputTSProgramEsType
                  Integer32,
                hwDocsQamInputTSProgramEsPID 
                  Unsigned32,
                hwDocsQamInputTSProgramEsRate 
                  Unsigned32,
                hwDocsQamInputTSProgramEsMaxRate
                  Unsigned32,
                hwDocsQamInputTSProgramEsMinRate 
                  Unsigned32,
                hwDocsQamInputTSProgramEsCaNumber
                  Unsigned32,
                hwDocsQamInputTSProgramEsCaPIDList
                  OCTET STRING,
                hwDocsQamInputTSProgramEsCaSystemIDList
                  OCTET STRING
               }
                     
        -- 1.3.6.1.4.1.2011.6.187.42.1.1
        hwDocsQamInputTSProgramEsIndex        OBJECT-TYPE
            SYNTAX       Unsigned32(1..4294967295)
            MAX-ACCESS   not-accessible
            STATUS       current
            DESCRIPTION
                "Indicates the index of program ES in input TS.
                "
            ::= { hwDocsQamInputTSProgramEsEntry 1 }
   
        -- 1.3.6.1.4.1.2011.6.187.42.1.2
        hwDocsQamInputTSProgramEsType        OBJECT-TYPE
            SYNTAX       Integer32(0..255)
            MAX-ACCESS   read-only
            STATUS       current
            DESCRIPTION
                "Indicates the type of program ES in input TS. For details about its value, see ISO/IEC 13818-1 [18] Program Map Table (PMT).
                 The default value is 0.
                "
            ::= { hwDocsQamInputTSProgramEsEntry 2 }     
            
        -- 1.3.6.1.4.1.2011.6.187.42.1.3
        hwDocsQamInputTSProgramEsPID        OBJECT-TYPE
            SYNTAX       Unsigned32(0..8191)
            MAX-ACCESS   read-only
            STATUS       current
            DESCRIPTION
                "Indicates the PID of program ES in input TS.
                "
            ::= { hwDocsQamInputTSProgramEsEntry 3 }
            
        -- 1.3.6.1.4.1.2011.6.187.42.1.4
        hwDocsQamInputTSProgramEsRate        OBJECT-TYPE
            SYNTAX       Unsigned32(0..4294967295) 
            UNITS        "kbps"
            MAX-ACCESS   read-only
            STATUS       current
            DESCRIPTION
                "Indicates the rate of program ES in input TS. Unit: kbit/s.
                 The default value is 0.
                "
            ::= { hwDocsQamInputTSProgramEsEntry 4 }
            
        -- 1.3.6.1.4.1.2011.6.187.42.1.5
        hwDocsQamInputTSProgramEsMaxRate        OBJECT-TYPE
            SYNTAX       Unsigned32(0..4294967295)     
            UNITS        "kbps"
            MAX-ACCESS   read-only
            STATUS       current
            DESCRIPTION
                "Indicates the maximum rate of program ES in input TS. Unit: kbit/s.
                 The default value is 0.
                "
            ::= { hwDocsQamInputTSProgramEsEntry 5 }
            
        -- 1.3.6.1.4.1.2011.6.187.42.1.6
        hwDocsQamInputTSProgramEsMinRate        OBJECT-TYPE
            SYNTAX       Unsigned32(0..4294967295) 
            UNITS        "kbps"
            MAX-ACCESS   read-only
            STATUS       current
            DESCRIPTION
                "Indicates the minimum rate of program ES in input TS. Unit: kbit/s.
                 The default value is 0.
                "
            ::= { hwDocsQamInputTSProgramEsEntry 6 }
            
        -- 1.3.6.1.4.1.2011.6.187.42.1.7
        hwDocsQamInputTSProgramEsCaNumber        OBJECT-TYPE
            SYNTAX       Unsigned32(0..4)
            MAX-ACCESS   read-only
            STATUS       current
            DESCRIPTION
                "Indicates the CA number of program ES in input TS.
                "
            ::= { hwDocsQamInputTSProgramEsEntry 7 }
            
        -- 1.3.6.1.4.1.2011.6.187.42.1.8
        hwDocsQamInputTSProgramEsCaPIDList        OBJECT-TYPE
            SYNTAX       OCTET STRING (SIZE (0..8))
            MAX-ACCESS   read-only
            STATUS       current
            DESCRIPTION
                "Indicates the CA PID list of an input program ES. A PID is displayed as a 2-byte string in network order. A maximum of 4 CAs are supported.
                The default value is null string. 
                "
            ::= { hwDocsQamInputTSProgramEsEntry 8 }
            
        -- 1.3.6.1.4.1.2011.6.187.42.1.9
        hwDocsQamInputTSProgramEsCaSystemIDList        OBJECT-TYPE
            SYNTAX       OCTET STRING (SIZE (0..8))
            MAX-ACCESS   read-only
            STATUS       current
            DESCRIPTION
                "Indicates the CA system ID list of an input program ES. A CA system ID is displayed as a 2-byte string in network order. A maximum of 4 CAs are supported.
                "
            ::= { hwDocsQamInputTSProgramEsEntry 9 }
                        
        -- 1.3.6.1.4.1.2011.6.187.43
        hwDocsQamOutputTSTable    OBJECT-TYPE
            SYNTAX          SEQUENCE OF HwDocsQamOutputTSEntry
            MAX-ACCESS      not-accessible
            STATUS          current
            DESCRIPTION
                "Indicates the output TS table.
                 The index of this table is ifIndex.
                "
            ::= { hwEqamAn 43 }
            
        -- 1.3.6.1.4.1.2011.6.187.43.1
        hwDocsQamOutputTSEntry    OBJECT-TYPE
            SYNTAX          HwDocsQamOutputTSEntry
            MAX-ACCESS      not-accessible
            STATUS          current
            DESCRIPTION
                "Indicates the output TS table.
                 The index of this entry is ifIndex.
                "
            INDEX   
                { 
                ifIndex
                }
            ::= { hwDocsQamOutputTSTable 1 } 
      
        HwDocsQamOutputTSEntry ::=
            SEQUENCE 
                {
                hwDocsQamOutputTSProgramNumber 
                  Unsigned32,  
                hwDocsQamOutputTSRate 
                  Unsigned32,  
                hwDocsQamOutputTSMaxRate
                  Unsigned32,  
                hwDocsQamOutputTSMinRate
                  Unsigned32,  
                hwDocsQamOutputTSDiscards
                  Counter64,
                hwDocsQamOutputTSEPG
                  TruthValue,
                hwDocsQamOutputTSStatisticsOperMode
                  INTEGER
               }
                             
        -- 1.3.6.1.4.1.2011.6.187.43.1.1
        hwDocsQamOutputTSProgramNumber        OBJECT-TYPE
            SYNTAX       Unsigned32(0..64)
            MAX-ACCESS   read-only
            STATUS       current
            DESCRIPTION
                "Indicates the program number in output TS.
                "
            ::= { hwDocsQamOutputTSEntry 1 }
            
        -- 1.3.6.1.4.1.2011.6.187.43.1.2
        hwDocsQamOutputTSRate        OBJECT-TYPE
            SYNTAX       Unsigned32(0..4294967295) 
            UNITS        "kbps"
            MAX-ACCESS   read-only
            STATUS       current
            DESCRIPTION
                "Indicates the rate of program in output TS. Unit: kbit/s.
                 The default value is 0.
                "
            ::= { hwDocsQamOutputTSEntry 2 }
            
        -- 1.3.6.1.4.1.2011.6.187.43.1.3
        hwDocsQamOutputTSMaxRate        OBJECT-TYPE
            SYNTAX       Unsigned32(0..4294967295)   
            UNITS        "kbps"
            MAX-ACCESS   read-only
            STATUS       current
            DESCRIPTION
                "Indicates the maximum rate of program in output TS. Unit: kbit/s.
                 The default value is 0.
                "
            ::= { hwDocsQamOutputTSEntry 3 }
            
        -- 1.3.6.1.4.1.2011.6.187.43.1.4
        hwDocsQamOutputTSMinRate        OBJECT-TYPE
            SYNTAX       Unsigned32(0..4294967295) 
            UNITS        "kbps"
            MAX-ACCESS   read-only
            STATUS       current
            DESCRIPTION
                "Indicates the mininum rate of program in output TS. Unit: kbit/s.
                 The default value is 0.
                "
            ::= { hwDocsQamOutputTSEntry 4 }
            
        -- 1.3.6.1.4.1.2011.6.187.43.1.5
        hwDocsQamOutputTSDiscards        OBJECT-TYPE
            SYNTAX       Counter64
            MAX-ACCESS   read-only
            STATUS       current
            DESCRIPTION
                "Indicates the packet loss of output TS.
                "
            ::= { hwDocsQamOutputTSEntry 5 }
            
        -- 1.3.6.1.4.1.2011.6.187.43.1.6
        hwDocsQamOutputTSEPG        OBJECT-TYPE
            SYNTAX       TruthValue
            MAX-ACCESS   read-only
            STATUS       current
            DESCRIPTION
                "Indicates whether the transport stream is treated as the EPG input.
                 The default value is false(2).
                "
            ::= { hwDocsQamOutputTSEntry 6 }
                        
        -- 1.3.6.1.4.1.2011.6.187.43.1.7
        hwDocsQamOutputTSStatisticsOperMode        OBJECT-TYPE
            SYNTAX   INTEGER{
                              clearStatistic(1)
                            }
            MAX-ACCESS   read-write
            STATUS       current
            DESCRIPTION
                "Clear output TS statistics.
                 Options:
                 1. clearStatistic(1)   -indicates clearing the statistics of output TS.
                "
            ::= { hwDocsQamOutputTSEntry 7 }
            
        -- 1.3.6.1.4.1.2011.6.187.44
        hwDocsQamOutputTSProgramEsTable    OBJECT-TYPE
            SYNTAX          SEQUENCE OF HwDocsQamOutputTSProgramEsEntry
            MAX-ACCESS      not-accessible
            STATUS          current
            DESCRIPTION
                "Indicates the program elementary stream (ES) table of an output TS, which is used to query the rate, maximum rate, minimum rate,
                 number of CAs, CA PID list, and CA system ID list.
                 The indexes of this table are ifIndex, hwDocsQamOutputTSProgramIndex and hwDocsQamOutputTSProgramEsIndex.
                "
            ::= { hwEqamAn 44 }
            
        -- 1.3.6.1.4.1.2011.6.187.44.1
        hwDocsQamOutputTSProgramEsEntry    OBJECT-TYPE
            SYNTAX          HwDocsQamOutputTSProgramEsEntry
            MAX-ACCESS      not-accessible
            STATUS          current
            DESCRIPTION
                "Indicates the program elementary stream (ES) table of an output TS, which is used to query the rate, maximum rate, minimum rate,
                 number of CAs, CA PID list, and CA system ID list.
                 The indexes of this entry are ifIndex, hwDocsQamOutputTSProgramIndex and hwDocsQamOutputTSProgramEsIndex.
                "
            INDEX   
                { 
                ifIndex,
                hwDocsQamOutputTSProgramIndex,
                hwDocsQamOutputTSProgramEsIndex
                }
            ::= { hwDocsQamOutputTSProgramEsTable 1 } 
            
        HwDocsQamOutputTSProgramEsEntry ::=
            SEQUENCE 
                {
                hwDocsQamOutputTSProgramEsIndex
                  Unsigned32, 
                hwDocsQamOutputTSProgramEsType
                  Integer32,
                hwDocsQamOutputTSProgramEsPID 
                  Unsigned32,
                hwDocsQamOutputTSProgramEsRate 
                  Unsigned32,
                hwDocsQamOutputTSProgramEsMaxRate
                  Unsigned32,
                hwDocsQamOutputTSProgramEsMinRate 
                  Unsigned32,
                hwDocsQamOutputTSProgramEsCaNumber
                  Unsigned32,
                hwDocsQamOutputTSProgramEsCaPIDList
                  OCTET STRING,
                hwDocsQamOutputTSProgramEsCaSystemIDList
                  OCTET STRING
               }
                     
        -- 1.3.6.1.4.1.2011.6.187.44.1.1
        hwDocsQamOutputTSProgramEsIndex        OBJECT-TYPE
            SYNTAX       Unsigned32(1..4294967295)
            MAX-ACCESS   not-accessible
            STATUS       current
            DESCRIPTION
                "Indicates the index of program ES in output TS.
                "
            ::= { hwDocsQamOutputTSProgramEsEntry 1 }
   
        -- 1.3.6.1.4.1.2011.6.187.44.1.2
        hwDocsQamOutputTSProgramEsType        OBJECT-TYPE
            SYNTAX       Integer32(0..255)
            MAX-ACCESS   read-only
            STATUS       current
            DESCRIPTION
                "Indicates the type of program ES in output TS. For details about its value, see ISO/IEC 13818-1 [18] Program Map Table (PMT).
                 The default value is 0.
                "
            ::= { hwDocsQamOutputTSProgramEsEntry 2 }     
            
        -- 1.3.6.1.4.1.2011.6.187.44.1.3
        hwDocsQamOutputTSProgramEsPID        OBJECT-TYPE
            SYNTAX       Unsigned32(0..8191)
            MAX-ACCESS   read-only
            STATUS       current
            DESCRIPTION
                "Indicates the PID of program ES in output TS.
                "
            ::= { hwDocsQamOutputTSProgramEsEntry 3 }
            
        -- 1.3.6.1.4.1.2011.6.187.44.1.4
        hwDocsQamOutputTSProgramEsRate        OBJECT-TYPE
            SYNTAX       Unsigned32(0..4294967295) 
            UNITS        "kbps"
            MAX-ACCESS   read-only
            STATUS       current
            DESCRIPTION
                "Indicates the rate of program ES in output TS. Unit: kbit/s.
                 The default value is 0.
                "
            ::= { hwDocsQamOutputTSProgramEsEntry 4 }
            
        -- 1.3.6.1.4.1.2011.6.187.44.1.5
        hwDocsQamOutputTSProgramEsMaxRate        OBJECT-TYPE
            SYNTAX       Unsigned32(0..4294967295)     
            UNITS        "kbps"
            MAX-ACCESS   read-only
            STATUS       current
            DESCRIPTION
                "Indicates the maximum rate of program ES in output TS. Unit: kbit/s.
                 The default value is 0.
                "
            ::= { hwDocsQamOutputTSProgramEsEntry 5 }
            
        -- 1.3.6.1.4.1.2011.6.187.44.1.6
        hwDocsQamOutputTSProgramEsMinRate        OBJECT-TYPE
            SYNTAX       Unsigned32(0..4294967295) 
            UNITS        "kbps"
            MAX-ACCESS   read-only
            STATUS       current
            DESCRIPTION
                "Indicates the minimum rate of program ES in output TS. Unit: kbit/s.
                 The default value is 0.
                "
            ::= { hwDocsQamOutputTSProgramEsEntry 6 }
            
        -- 1.3.6.1.4.1.2011.6.187.44.1.7
        hwDocsQamOutputTSProgramEsCaNumber        OBJECT-TYPE
            SYNTAX       Unsigned32(0..4)
            MAX-ACCESS   read-only
            STATUS       current
            DESCRIPTION
                "Indicates the CA number of program ES in output TS.
                "
            ::= { hwDocsQamOutputTSProgramEsEntry 7 }
            
        -- 1.3.6.1.4.1.2011.6.187.44.1.8
        hwDocsQamOutputTSProgramEsCaPIDList        OBJECT-TYPE
            SYNTAX       OCTET STRING (SIZE (0..8))
            MAX-ACCESS   read-only
            STATUS       current
            DESCRIPTION
                "Indicates the CA PID list of an output program ES. A PID is displayed as a 2-byte string in network order. A maximum of 4 CAs are supported.
                The default value is null string.
                "
            ::= { hwDocsQamOutputTSProgramEsEntry 8 }
            
        -- 1.3.6.1.4.1.2011.6.187.44.1.9
        hwDocsQamOutputTSProgramEsCaSystemIDList        OBJECT-TYPE
            SYNTAX       OCTET STRING (SIZE (0..8))
            MAX-ACCESS   read-only
            STATUS       current
            DESCRIPTION
                "Indicates the CA system ID list of an output program ES. A CA system ID is displayed as a 2-byte string in network order. A maximum of 4 CAs are supported.
                "
            ::= { hwDocsQamOutputTSProgramEsEntry 9 }  
            
       -- 1.3.6.1.4.1.2011.6.187.45
        hwDocsQamOutputPIDInfoTable    OBJECT-TYPE
            SYNTAX          SEQUENCE OF HwDocsQamOutputPIDInfoEntry
            MAX-ACCESS      not-accessible
            STATUS          current
            DESCRIPTION
                "Indicates the output PID info table used to display the packet identifier (PID), PID type, PID subtype, PID rate,
                 maximum PID rate, minimum PID rate, PID scrambling information, program clock reference (PCR) association of the PID, 
                 continuity counter (CC) error count of the PID, ID and name of the program associated with the PID of the output TS.
                 The indexes of this table are ifIndex and hwDocsQamOutputPIDIndex.
                "
            ::= { hwEqamAn 45 }
            
        -- 1.3.6.1.4.1.2011.6.187.45.1
        hwDocsQamOutputPIDInfoEntry    OBJECT-TYPE
            SYNTAX          HwDocsQamOutputPIDInfoEntry
            MAX-ACCESS      not-accessible
            STATUS          current
            DESCRIPTION
                "Indicates the output PID info table used to display the packet identifier (PID), PID type, PID subtype, PID rate,
                 maximum PID rate, minimum PID rate, PID scrambling information, program clock reference (PCR) association of the PID, 
                 continuity counter (CC) error count of the PID, ID and name of the program associated with the PID of the output TS.
                 The indexes of this entry are ifIndex and hwDocsQamOutputPIDIndex.
                "
            INDEX   
                { 
                ifIndex,
                hwDocsQamOutputPIDIndex
                }
            ::= { hwDocsQamOutputPIDInfoTable 1 }
            
        HwDocsQamOutputPIDInfoEntry ::= 
            SEQUENCE 
                {
                hwDocsQamOutputPIDIndex
                  Unsigned32,             
                hwDocsQamOutputPID
                  Unsigned32, 
                hwDocsQamOutputPIDType
                  HwEqamInputPIDType,
                hwDocsQamOutputPIDStreamType
                  Integer32,
                hwDocsQamOutputPIDRate
                  Unsigned32,
                hwDocsQamOutputPIDMaxRate
                  Unsigned32,
                hwDocsQamOutputPIDMinRate
                  Unsigned32,
                hwDocsQamOutputPIDScambled
                  INTEGER,
                hwDocsQamOutputPIDCCErrorCount
                  Counter64,
                hwDocsQamOutputPIDPCRReference
                  TruthValue,
                hwDocsQamOutputPIDProgramIDReference
                  Unsigned32,
                hwDocsQamOutputPIDProgramNameReference
                  OCTET STRING
               } 
               
        -- 1.3.6.1.4.1.2011.6.187.45.1.1
        hwDocsQamOutputPIDIndex        OBJECT-TYPE
            SYNTAX       Unsigned32(1..8192)
            MAX-ACCESS   not-accessible
            STATUS       current
            DESCRIPTION
                "Indicates the output PID index, whose value is obtained by adding 1 to the value of hwDocsQamOutputPID.
                "
            ::= { hwDocsQamOutputPIDInfoEntry 1 }
                      
        -- 1.3.6.1.4.1.2011.6.187.45.1.2
        hwDocsQamOutputPID        OBJECT-TYPE
            SYNTAX       Unsigned32(0..8191)
            MAX-ACCESS   read-only
            STATUS       current
            DESCRIPTION
                "Indicates the value of output PID.
                "
            ::= { hwDocsQamOutputPIDInfoEntry 2 }
        
        -- 1.3.6.1.4.1.2011.6.187.45.1.3
        hwDocsQamOutputPIDType        OBJECT-TYPE
            SYNTAX       HwEqamInputPIDType
            MAX-ACCESS   read-only
            STATUS       current
            DESCRIPTION
                "Indicates the output PID type. The default value is unknown(255), indicating the unknown type. 
                "
            ::= { hwDocsQamOutputPIDInfoEntry 3 }
        
        -- 1.3.6.1.4.1.2011.6.187.45.1.4
        hwDocsQamOutputPIDStreamType        OBJECT-TYPE
            SYNTAX       Integer32(0..255)
            MAX-ACCESS   read-only
            STATUS       current
            DESCRIPTION
                "When the value of hwDocsQamOutputPIDStreamType is 12, hwDocsQamOutputPIDStreamType indicates the corresponding media type. 
                 For details about its value, see ISO/IEC 13818-1 [18] Program Map Table (PMT). Otherwise, the value of hwDocsQamOutputPIDStreamType is 0. 
                "
            ::= { hwDocsQamOutputPIDInfoEntry 4 }       

        -- 1.3.6.1.4.1.2011.6.187.45.1.5
        hwDocsQamOutputPIDRate        OBJECT-TYPE
            SYNTAX       Unsigned32(0..4294967295)  
            UNITS        "kbps"
            MAX-ACCESS   read-only
            STATUS       current
            DESCRIPTION
                "Indicates the rate of the output PID. Unit: kbit/s.
                "
            ::= { hwDocsQamOutputPIDInfoEntry 5 }       

        -- 1.3.6.1.4.1.2011.6.187.45.1.6
         hwDocsQamOutputPIDMaxRate        OBJECT-TYPE
            SYNTAX       Unsigned32(0..4294967295)  
            UNITS        "kbps"
            MAX-ACCESS   read-only
            STATUS       current
            DESCRIPTION
                "Indicates the maximum rate of the output PID. Unit: kbit/s.
                "
            ::= { hwDocsQamOutputPIDInfoEntry 6 }       
            
        -- 1.3.6.1.4.1.2011.6.187.45.1.7
        hwDocsQamOutputPIDMinRate        OBJECT-TYPE
            SYNTAX       Unsigned32(0..4294967295)   
            UNITS        "kbps"
            MAX-ACCESS   read-only
            STATUS       current
            DESCRIPTION
                "Indicates the minimum rate of the output PID. Unit: kbit/s. 
                "
            ::= { hwDocsQamOutputPIDInfoEntry 7 }       

        -- 1.3.6.1.4.1.2011.6.187.45.1.8
        hwDocsQamOutputPIDScambled        OBJECT-TYPE
            SYNTAX       INTEGER
                  {
                  notScambled(1),
                  evenScambled(2),
                  oddScambled(3)
                  }
            MAX-ACCESS   read-only
            STATUS       current
            DESCRIPTION
                "Indicates the output PID scrambling information.
                Options:
                1. notScambled(1)  --Indicates no scrambling 
                2. evenScambled(2) --Indicates scrambling with even control word (CW)
                3. oddScambled(3)  --Indicates scrambling with odd CW
                "
            ::= { hwDocsQamOutputPIDInfoEntry 8 }       

        -- 1.3.6.1.4.1.2011.6.187.45.1.9
        hwDocsQamOutputPIDCCErrorCount        OBJECT-TYPE
            SYNTAX       Counter64           
            MAX-ACCESS   read-only
            STATUS       current
            DESCRIPTION
                "Indicates the CC error count of the output PID.
                "
            ::= { hwDocsQamOutputPIDInfoEntry 9 }               

        -- 1.3.6.1.4.1.2011.6.187.45.1.10
        hwDocsQamOutputPIDPCRReference        OBJECT-TYPE
            SYNTAX       TruthValue
            MAX-ACCESS   read-only
            STATUS       current
            DESCRIPTION
                "Indicates the PCR association of the output PID. The default value is false.
                "
            ::= { hwDocsQamOutputPIDInfoEntry 10 }      

        -- 1.3.6.1.4.1.2011.6.187.45.1.11
        hwDocsQamOutputPIDProgramIDReference        OBJECT-TYPE
            SYNTAX       Unsigned32(0..4294967295)
            MAX-ACCESS   read-only
            STATUS       current
            DESCRIPTION
                "Indicates the ID of the program associated with the PID. The default value is 4294967295, indicating no associated program.
                "
            ::= { hwDocsQamOutputPIDInfoEntry 11 }      

        -- 1.3.6.1.4.1.2011.6.187.45.1.12
        hwDocsQamOutputPIDProgramNameReference        OBJECT-TYPE
            SYNTAX       OCTET STRING (SIZE (0..63))
            MAX-ACCESS   read-only
            STATUS       current
            DESCRIPTION
                "Indicates the name of the program associated with the PID.
                 The default value is an empty character string, indicating no associated program name..
                "
            ::= { hwDocsQamOutputPIDInfoEntry 12 }      

        -- 1.3.6.1.4.1.2011.6.187.46
        hwDocsQamOutputTSPIDTable    OBJECT-TYPE
            SYNTAX          SEQUENCE OF HwDocsQamOutputTSPIDEntry
            MAX-ACCESS      not-accessible
            STATUS          current
            DESCRIPTION
                "Indicates the output TS PID table used to display the number of PIDs, PID list, and PID list status mask of the output TS.
                 The index of this table is ifIndex.
                "
            ::= { hwEqamAn 46 }
            
        -- 1.3.6.1.4.1.2011.6.187.46.1
        hwDocsQamOutputTSPIDEntry    OBJECT-TYPE
            SYNTAX          HwDocsQamOutputTSPIDEntry
            MAX-ACCESS      not-accessible
            STATUS          current
            DESCRIPTION
                "Indicates the output TS PID table used to display the number of PIDs, PID list, and PID list status mask of the output TS.
                 The index of this entry is ifIndex.
                "
            INDEX   
                { 
                ifIndex
                }
            ::= { hwDocsQamOutputTSPIDTable 1 }
            
        HwDocsQamOutputTSPIDEntry ::=
            SEQUENCE 
                {
                hwDocsQamOutputTSPIDNumber
                  Unsigned32, 
                hwDocsQamOutputTSPIDList
                  OCTET STRING,
                hwDocsQamOutputTSPIDStateMask
                  OCTET STRING
               }
                       
        -- 1.3.6.1.4.1.2011.6.187.46.1.1
        hwDocsQamOutputTSPIDNumber        OBJECT-TYPE
            SYNTAX       Unsigned32(0..512)
            MAX-ACCESS   read-only
            STATUS       current
            DESCRIPTION
                "Indicates the number of the output TS PID.
                "
            ::= { hwDocsQamOutputTSPIDEntry 1 }
        
        -- 1.3.6.1.4.1.2011.6.187.46.1.2
        hwDocsQamOutputTSPIDList        OBJECT-TYPE
            SYNTAX       OCTET STRING (SIZE (0..1024))
            MAX-ACCESS   read-only
            STATUS       current
            DESCRIPTION
                "Format: 2 bytes in network byte order,
                 which indicates a PID. A maximum of 512 PIDs are supported.                  
                 a 2-byte bit-field value defined as follows:
                 Bit 0:xx
                 Bit 1:xx.
               "
            ::= { hwDocsQamOutputTSPIDEntry 2 }
        
        -- 1.3.6.1.4.1.2011.6.187.46.1.3
        hwDocsQamOutputTSPIDStateMask        OBJECT-TYPE
            SYNTAX       OCTET STRING (SIZE (0..1024))
            MAX-ACCESS   read-only
            STATUS       current
            DESCRIPTION
                "Indicates the PID list status mask of the output TS. The default value is an empty character string, indicating no PID list status mask.
                Format: 2 bytes in network byte order, which indicates a PID list status mask. A maximum of 512 PID list status masks are supported. 
                a 2-byte bit-field value defined as follows:
                 Bit 0:notScambled
                 Bit 1:evenScambled
                 Bit 2:oddScambled
                 Bit 3:pcrreferenced
                 Bit 4:ccerror.
                "
            ::= { hwDocsQamOutputTSPIDEntry 3 }                         
                                                        
        -- 1.3.6.1.4.1.2011.6.187.47
        hwDocsQamEPGTable    OBJECT-TYPE
            SYNTAX          SEQUENCE OF HwDocsQamEPGEntry
            MAX-ACCESS      not-accessible
            STATUS          current
            DESCRIPTION
                "Indicates a table used to query the electronic program guide (EPG) status of a DVB video domain.
                 The indexes of this table are ifIndex and hwDocsQamEPGProgramID.
                "
            ::= { hwEqamAn 47 }
            
        -- 1.3.6.1.4.1.2011.6.187.47.1
        hwDocsQamEPGEntry    OBJECT-TYPE
            SYNTAX          HwDocsQamEPGEntry
            MAX-ACCESS      not-accessible
            STATUS          current
            DESCRIPTION
                "Indicates a table used to query the electronic program guide (EPG) status of a DVB video domain.
                 The indexes of this entry are ifIndex and hwDocsQamEPGProgramID.
                "
            INDEX   
                { 
                ifIndex,
                hwDocsQamEPGProgramID
                }
            ::= { hwDocsQamEPGTable 1 }
            
        HwDocsQamEPGEntry ::=
            SEQUENCE 
                {
                hwDocsQamEPGProgramID 
                  Unsigned32, 
                hwDocsQamEPGProgramName 
                  OCTET STRING,
                hwDocsQamEPGProgramInputTSIndex  
                  Unsigned32, 
                hwDocsQamEPGProgramInputProgramID 
                  Unsigned32, 
                hwDocsQamEPGSourceTSIndex  
                  Unsigned32, 
                hwDocsQamEPGSourceProgramID  
                  Unsigned32, 
                hwDocsQamEPGPresentAndFollowingMatched
                  TruthValue,
                hwDocsQamEPGScheduleMatched
                  TruthValue
               }

        -- 1.3.6.1.4.1.2011.6.187.47.1.1
        hwDocsQamEPGProgramID        OBJECT-TYPE
            SYNTAX       Unsigned32(1..4294967295)
            MAX-ACCESS   read-only
            STATUS       current
            DESCRIPTION
                "Indicates the output program ID.
                "
            ::= { hwDocsQamEPGEntry 1 }  
                                  
        -- 1.3.6.1.4.1.2011.6.187.47.1.2
        hwDocsQamEPGProgramName        OBJECT-TYPE
            SYNTAX       OCTET STRING(SIZE (0..63))
            MAX-ACCESS   read-only
            STATUS       current
            DESCRIPTION
                "Indicates the output program name.
                 The default value is null string.
                "
            ::= { hwDocsQamEPGEntry 2 }   
            
        -- 1.3.6.1.4.1.2011.6.187.47.1.3
        hwDocsQamEPGProgramInputTSIndex         OBJECT-TYPE
            SYNTAX       Unsigned32(1..65535 | 4294967295)
            MAX-ACCESS   read-only
            STATUS       current
            DESCRIPTION
                "Indicates the index of the input TS corresponding to a program. 
                The default value is 4294967295, which indicates that no input TS is associated.
                "
            ::= { hwDocsQamEPGEntry 3 }

        -- 1.3.6.1.4.1.2011.6.187.47.1.4
        hwDocsQamEPGProgramInputProgramID        OBJECT-TYPE
            SYNTAX       Unsigned32(1..65535 | 4294967295)
            MAX-ACCESS   read-only
            STATUS       current
            DESCRIPTION
                "Indicates the input program id corresponding to a program. 
                The default value is 4294967295, which indicates that no input program is associated.            
                "
            ::= { hwDocsQamEPGEntry 4 }

        -- 1.3.6.1.4.1.2011.6.187.47.1.5
        hwDocsQamEPGSourceTSIndex         OBJECT-TYPE
            SYNTAX       Unsigned32(1..65535 | 4294967295)
            MAX-ACCESS   read-only
            STATUS       current
            DESCRIPTION
                "Indicates the index of the source TS corresponding to an EPG. 
                The default value is 4294967295, which indicates that no input TS is associated.
                "
            ::= { hwDocsQamEPGEntry 5 }

        -- 1.3.6.1.4.1.2011.6.187.47.1.6
        hwDocsQamEPGSourceProgramID        OBJECT-TYPE
            SYNTAX       Unsigned32(1..65535 | 4294967295)
            MAX-ACCESS   read-only
            STATUS       current
            DESCRIPTION
                "Indicates the ID of the source program corresponding to an EPG. 
                The default value is 4294967295, which indicates that no input program is associated.   
                "
            ::= { hwDocsQamEPGEntry 6 }

        -- 1.3.6.1.4.1.2011.6.187.47.1.7
        hwDocsQamEPGPresentAndFollowingMatched        OBJECT-TYPE
            SYNTAX       TruthValue
            MAX-ACCESS   read-only
            STATUS       current
            DESCRIPTION
                "Indicates whether an EPG matches the present/follow-up event information. true indicates that they are matched and the default value false indicates that they are not matched.
                "
            ::= { hwDocsQamEPGEntry 7 }

        -- 1.3.6.1.4.1.2011.6.187.47.1.8
        hwDocsQamEPGScheduleMatched        OBJECT-TYPE
            SYNTAX       TruthValue
            MAX-ACCESS   read-only
            STATUS       current
            DESCRIPTION
                "Indicates whether an EPG matches event schedule information. true indicates that they are matched and the default value false indicates that they are not matched.
                "
            ::= { hwDocsQamEPGEntry 8 }
            
        -- 1.3.6.1.4.1.2011.6.187.48
        hwDocsQamVODSummaryTable    OBJECT-TYPE
            SYNTAX          SEQUENCE OF HwDocsQamVODSummaryEntry
            MAX-ACCESS      not-accessible
            STATUS          current
            DESCRIPTION
                "Indicates the video program abstract.
                 The index of this table is ifIndex.
                "
            ::= { hwEqamAn 48 }
        
        -- 1.3.6.1.4.1.2011.6.187.48.1
        hwDocsQamVODSummaryEntry    OBJECT-TYPE
            SYNTAX          HwDocsQamVODSummaryEntry
            MAX-ACCESS      not-accessible
            STATUS          current
            DESCRIPTION
                "Indicates the video program abstract.
                 The index of this entry is ifIndex.
                "
            INDEX   
                { 
                ifIndex
                }
            ::= { hwDocsQamVODSummaryTable  1 }
            
        HwDocsQamVODSummaryEntry ::=
            SEQUENCE 
                { 
                hwDocsQamVODProgramNumberTotal
                  Unsigned32,
                hwDocsQamVODProgramNumberOnline
                  Unsigned32
                }
            
        -- 1.3.6.1.4.1.2011.6.187.48.1.1   
        hwDocsQamVODProgramNumberTotal        OBJECT-TYPE
            SYNTAX       Unsigned32(0..4294967295)
            MAX-ACCESS   read-only
            STATUS       current
            DESCRIPTION
              "Indicates the number of VOD programs on a RF port.
              "
            ::= { hwDocsQamVODSummaryEntry 1 }
          
        -- 1.3.6.1.4.1.2011.6.187.48.1.2   
        hwDocsQamVODProgramNumberOnline        OBJECT-TYPE
            SYNTAX       Unsigned32(0..4294967295)
            MAX-ACCESS   read-only
            STATUS       current
            DESCRIPTION
              "Indicates the number of online VOD programs on a RF port.
              "
            ::= { hwDocsQamVODSummaryEntry 2 }
                        
        -- 1.3.6.1.4.1.2011.6.187.49
        hwDocsQamDVBChannelMonitoringControlTable    OBJECT-TYPE
            SYNTAX          SEQUENCE OF HwDocsQamDVBChannelMonitoringControlEntry
            MAX-ACCESS      not-accessible
            STATUS          current
            DESCRIPTION
                "Indicates the table for DVB channel monitoring, which is used to configure channel monitoring locking and query the ID of the channel being monitored.
                 The index of this table is ifIndex.
                "
            ::= { hwEqamAn 49 }
            
        -- 1.3.6.1.4.1.2011.6.187.49.1
        hwDocsQamDVBChannelMonitoringControlEntry    OBJECT-TYPE
            SYNTAX          HwDocsQamDVBChannelMonitoringControlEntry
            MAX-ACCESS      not-accessible
            STATUS          current
            DESCRIPTION
                "Indicates the table for DVB channel monitoring, which is used to configure channel monitoring locking and query the ID of the channel being monitored.
                 The index of this entry is ifIndex.
                "
            INDEX   
                { 
                ifIndex
                }
            ::= { hwDocsQamDVBChannelMonitoringControlTable 1 }
            
        HwDocsQamDVBChannelMonitoringControlEntry ::=
            SEQUENCE 
                {
                hwDocsQamDVBChannelMonitoringControlCurrentChannelID 
                  Unsigned32, 
                hwDocsQamDVBChannelMonitoringControlLockedChannelID  
                  Unsigned32
               }
                           
        -- 1.3.6.1.4.1.2011.6.187.49.1.1
        hwDocsQamDVBChannelMonitoringControlCurrentChannelID        OBJECT-TYPE
            SYNTAX       Unsigned32(0..255)
            MAX-ACCESS   read-only
            STATUS       current
            DESCRIPTION
                "Indicates the ID of the channel being monitored.      
                The default value is 0, indicates that no channel is in the monitoring state.    
                "
            ::= { hwDocsQamDVBChannelMonitoringControlEntry 1 }
                        
        -- 1.3.6.1.4.1.2011.6.187.49.1.2
        hwDocsQamDVBChannelMonitoringControlLockedChannelID        OBJECT-TYPE
            SYNTAX       Unsigned32(0..255)
            MAX-ACCESS   read-write
            STATUS       current
            DESCRIPTION
                "Indicates the ID of the channel locked by monitoring. 
                 The default value is 0, indicates that no channel is locked by monitoring.   
                "
            ::= { hwDocsQamDVBChannelMonitoringControlEntry 2 }
                        
        -- 1.3.6.1.4.1.2011.6.187.50
        hwDocsQamDVBChannelMonitoringTable    OBJECT-TYPE
            SYNTAX          SEQUENCE OF HwDocsQamDVBChannelMonitoringEntry
            MAX-ACCESS      not-accessible
            STATUS          current
            DESCRIPTION
                "Indicates the DVB channel monitoring table, which is used to query the monitoring information and reset DVB monitoring.
                 The index of this table is ifIndex.
                "
            ::= { hwEqamAn 50 }
                        
        -- 1.3.6.1.4.1.2011.6.187.50.1
        hwDocsQamDVBChannelMonitoringEntry    OBJECT-TYPE
            SYNTAX          HwDocsQamDVBChannelMonitoringEntry
            MAX-ACCESS      not-accessible
            STATUS          current
            DESCRIPTION
                "Indicates the DVB channel monitoring table, which is used to query the monitoring information and reset DVB monitoring.
                 The index of this entry is ifIndex.
                "
            INDEX   
                { 
                ifIndex
                }
            ::= { hwDocsQamDVBChannelMonitoringTable 1 }
            
        HwDocsQamDVBChannelMonitoringEntry ::=
            SEQUENCE 
                {
                hwDocsQamChannelMonitoringRTPSequenceErrorCounter 
                  Counter64, 
                hwDocsQamChannelMonitoringOperMode  
                  INTEGER,
                hwDocsQamChannelMonitoringPIDList
                  OCTET STRING,
                hwDocsQamChannelMonitoringPIDStateMask
                  OCTET STRING
               }
                           
        -- 1.3.6.1.4.1.2011.6.187.50.1.1
        hwDocsQamChannelMonitoringRTPSequenceErrorCounter        OBJECT-TYPE
            SYNTAX      Counter64
            MAX-ACCESS  read-only
            STATUS      current
            DESCRIPTION
                "Indicates RTP error statistics of a monitored channel.
                "   
            ::= { hwDocsQamDVBChannelMonitoringEntry 1 }
                        
        -- 1.3.6.1.4.1.2011.6.187.50.1.2
        hwDocsQamChannelMonitoringOperMode        OBJECT-TYPE
            SYNTAX       INTEGER{
                                  reset(1)
                                }
            MAX-ACCESS   read-write
            STATUS       current
            DESCRIPTION
                "Indicates reseting channel monitoring.
                 Options:
                 1. reset(1)   -indicates reseting channel monitoring. 
                "
            ::= { hwDocsQamDVBChannelMonitoringEntry 2 }
                        
        -- 1.3.6.1.4.1.2011.6.187.50.1.3
        hwDocsQamChannelMonitoringPIDList        OBJECT-TYPE
            SYNTAX       OCTET STRING (SIZE (0..512))
            MAX-ACCESS   read-only
            STATUS       current
            DESCRIPTION
                "Indicates the PID list of a monitored channel. The default value is null string.
                 Format: 2 bytes in network byte order,  which indicates a PID. A maximum of 256 PIDs are supported.  
               "
            ::= { hwDocsQamDVBChannelMonitoringEntry 3 }
        
        -- 1.3.6.1.4.1.2011.6.187.50.1.4
        hwDocsQamChannelMonitoringPIDStateMask        OBJECT-TYPE
            SYNTAX       OCTET STRING (SIZE (0..512))
            MAX-ACCESS   read-only
            STATUS       current
            DESCRIPTION
                "Indicates the PID list status mask of the monitoring channel. The default value is an empty character string.
                Format: 2 bytes in network byte order, which indicates a PID list status mask. A maximum of 256 PID list status masks are supported. 
                A 2-byte bit-field value defined as follows:
                 Bit 0:reserved     
                 Bit 1:reserved     
                 Bit 2:reserved     
                 Bit 3:reserved     
                 Bit 4:ccerror. 
                "
            ::= { hwDocsQamDVBChannelMonitoringEntry 4 }
                        
        -- 1.3.6.1.4.1.2011.6.187.51
        hwDocsQamDVBChannelPidMonitoringTable    OBJECT-TYPE
            SYNTAX          SEQUENCE OF HwDocsQamDVBChannelPidMonitoringEntry
            MAX-ACCESS      not-accessible
            STATUS          current
            DESCRIPTION
                "Indicates PID table for DVB channel monitoring.
                 The indexes of this table are ifIndex and hwDocsQamDVBChannelMonitoringPIDIndex.
                "
            ::= { hwEqamAn 51 }
                        
        -- 1.3.6.1.4.1.2011.6.187.51.1
        hwDocsQamDVBChannelPidMonitoringEntry    OBJECT-TYPE
            SYNTAX          HwDocsQamDVBChannelPidMonitoringEntry
            MAX-ACCESS      not-accessible
            STATUS          current
            DESCRIPTION
                "Indicates PID table for DVB channel monitoring.
                 The indexes of this entry are ifIndex and hwDocsQamDVBChannelMonitoringPIDIndex.
                "
            INDEX   
                { 
                ifIndex,
                hwDocsQamDVBChannelMonitoringPIDIndex
                }
            ::= { hwDocsQamDVBChannelPidMonitoringTable 1 }
            
        HwDocsQamDVBChannelPidMonitoringEntry ::=
            SEQUENCE 
                {
                hwDocsQamDVBChannelMonitoringPIDIndex 
                  Unsigned32, 
                hwDocsQamDVBChannelMonitoringPID  
                  Unsigned32,
                hwDocsQamDVBChannelMonitoringPIDCCErrorCount
                  Counter64
               }
                           
        -- 1.3.6.1.4.1.2011.6.187.51.1.1
        hwDocsQamDVBChannelMonitoringPIDIndex        OBJECT-TYPE
            SYNTAX      Unsigned32(1..8192)
            MAX-ACCESS  not-accessible
            STATUS      current
            DESCRIPTION
                "Indicates PID index of a DVB monitoring channel.
                "   
            ::= { hwDocsQamDVBChannelPidMonitoringEntry 1 }
                        
        -- 1.3.6.1.4.1.2011.6.187.51.1.2
        hwDocsQamDVBChannelMonitoringPID        OBJECT-TYPE
            SYNTAX      Unsigned32(0..8191)
            MAX-ACCESS  read-only
            STATUS      current
            DESCRIPTION
                "Indicates the PID of a DVB monitoring channel.
                "   
            ::= { hwDocsQamDVBChannelPidMonitoringEntry 2 }
                        
        -- 1.3.6.1.4.1.2011.6.187.51.1.3
        hwDocsQamDVBChannelMonitoringPIDCCErrorCount        OBJECT-TYPE
            SYNTAX      Counter64
            MAX-ACCESS  read-only
            STATUS      current
            DESCRIPTION
                "Indicates the number of PID CC errors of a DVB monitoring channel.
                "   
            ::= { hwDocsQamDVBChannelPidMonitoringEntry 3 }
            
        -- 1.3.6.1.4.1.2011.6.187.52
        hwDocsQamETR290MonitoringObj   OBJECT IDENTIFIER ::= { hwEqamAn 52 }
        
        -- 1.3.6.1.4.1.2011.6.187.52.1
        hwDocsQamETR290MonitoringCurrentTSIndex  OBJECT-TYPE
            SYNTAX      Unsigned32(0..65535 | 4294967295)
            MAX-ACCESS  read-only
            STATUS      current
            DESCRIPTION
                "Indicates the index of the input TS being monitored.      
                The default value is 4294967295, indicating that no input TS is in the monitoring state.
                "
            ::= { hwDocsQamETR290MonitoringObj 1 }

        -- 1.3.6.1.4.1.2011.6.187.52.2
        hwDocsQamETR290MonitoringLockedTSIndex  OBJECT-TYPE
            SYNTAX      Unsigned32(0..65535 | 4294967295)
            MAX-ACCESS  read-write
            STATUS      current
            DESCRIPTION
                "Indicates the index of the input TS being locked by monitoring.      
                The default value is 4294967295, indicating that no input TS is locked by monitoring.
                "
            ::= { hwDocsQamETR290MonitoringObj 2 }
            
        -- 1.3.6.1.4.1.2011.6.187.53
        hwDocsQamETR290MonitoringProfileTable    OBJECT-TYPE
            SYNTAX          SEQUENCE OF HwDocsQamETR290MonitoringProfileEntry
            MAX-ACCESS      not-accessible
            STATUS          current
            DESCRIPTION
                "Indicates the ETR290 monitoring profile table.
                 The index of this table is hwDocsQamETR290MonitoringProfileName.
                "
            ::= { hwEqamAn 53 }
                        
        -- 1.3.6.1.4.1.2011.6.187.53.1
        hwDocsQamETR290MonitoringProfileEntry    OBJECT-TYPE
            SYNTAX          HwDocsQamETR290MonitoringProfileEntry
            MAX-ACCESS      not-accessible
            STATUS          current
            DESCRIPTION
                "Indicates the ETR290 monitoring profile table.
                 The index of this entry is hwDocsQamETR290MonitoringProfileName.
                "
            INDEX   
                { 
                hwDocsQamETR290MonitoringProfileName
                }
            ::= { hwDocsQamETR290MonitoringProfileTable 1 }
            
        HwDocsQamETR290MonitoringProfileEntry ::=
            SEQUENCE 
                {
                hwDocsQamETR290MonitoringProfileName 
                  OCTET STRING, 
                hwDocsQamETR290MonitoringEnableMask  
                  BITS,
                hwDocsQamETR290MonitoringAlarmEnableMask
                  BITS,
                hwDocsQamETR290MonitoringErrorTimeout
                  Unsigned32,
                hwDocsQamETR290MonitoringAlarmDetectTime
                  Unsigned32,
                hwDocsQamETR290MonitoringProbeDuration
                  Unsigned32,
                hwDocsQamETR290MonitoringTsSyncLossDetectTime
                  Unsigned32,
                hwDocsQamETR290MonitoringPATInterval
                  Unsigned32,
                hwDocsQamETR290MonitoringPMTInterval
                  Unsigned32,
                hwDocsQamETR290MonitoringPIDLossThreshold
                  Unsigned32,
                hwDocsQamETR290MonitoringPCRInterval
                  Unsigned32, 
                hwDocsQamETR290MonitoringPCRDiscontinuityThreshold
                  Unsigned32,
                hwDocsQamETR290MonitoringPCRAccuracyJitterThreshold
                  Unsigned32,
                hwDocsQamETR290MonitoringCATInterval
                  Unsigned32,
                hwDocsQamETR290MonitoringRowStatus
                  RowStatus
               }
                           
        -- 1.3.6.1.4.1.2011.6.187.53.1.1
        hwDocsQamETR290MonitoringProfileName        OBJECT-TYPE
            SYNTAX      OCTET STRING (SIZE (1..15))
            MAX-ACCESS  not-accessible
            STATUS      current
            DESCRIPTION
                "Indicates the ETR290 monitoring profile name.
                "   
            ::= { hwDocsQamETR290MonitoringProfileEntry 1 }
                        
        -- 1.3.6.1.4.1.2011.6.187.53.1.2
        hwDocsQamETR290MonitoringEnableMask        OBJECT-TYPE
            SYNTAX      BITS
                 {
                  tsSyncLoss(0),
                  syncByteError(1),
                  patError(2),
                  ccError(3),
                  pmtError(4),
                  pidError(5),
                  transportError(6),
                  crcError(7),
                  pcrError(8),
                  pcrAccuracyError(9),
                  catError(10)
                  }
            MAX-ACCESS  read-create
            STATUS      current
            DESCRIPTION
                "Indicates the mask of ETR290 monitoring. 1 indicates enabled and 0 indicates disabled. 
                By default, patError and pmtError are enabled.
                "   
            ::= { hwDocsQamETR290MonitoringProfileEntry 2 }
                        
        -- 1.3.6.1.4.1.2011.6.187.53.1.3
        hwDocsQamETR290MonitoringAlarmEnableMask        OBJECT-TYPE
            SYNTAX      BITS
                 {
                  tsSyncLossAlarm(0),
                  syncByteErrorAlarm(1),
                  patErrorAlarm(2),
                  ccErrorAlarm(3),
                  pmtErrorAlarm(4),
                  pidErrorAlarm(5),
                  transportErrorAlarm(6),
                  crcErrorAlarm(7),
                  pcrErrorAlarm(8),
                  pcrAccuracyErroAlarmr(9),
                  catErrorAlarm(10)
                  }
            MAX-ACCESS  read-create
            STATUS      current
            DESCRIPTION
                "Indicates the alarm mask of ETR290 monitoring. 1 indicates enabled and 0 indicates disabled. 
                By default, patErrorAlarm and pmtErrorAlarm are enabled.
                "   
            ::= { hwDocsQamETR290MonitoringProfileEntry 3 }
            
        -- 1.3.6.1.4.1.2011.6.187.53.1.4
        hwDocsQamETR290MonitoringErrorTimeout        OBJECT-TYPE
            SYNTAX      Unsigned32(10..60)
            UNITS       "second"             
            MAX-ACCESS  read-create
            STATUS      current
            DESCRIPTION
                "Indicates the error timeout time of ETR290 monitoring.
                The default value is 10.
                "   
            ::= { hwDocsQamETR290MonitoringProfileEntry 4 }
            
        -- 1.3.6.1.4.1.2011.6.187.53.1.5
        hwDocsQamETR290MonitoringAlarmDetectTime        OBJECT-TYPE
            SYNTAX      Unsigned32(10..30)
            UNITS       "second"             
            MAX-ACCESS  read-create
            STATUS      current
            DESCRIPTION
                "Indicates the alarm discovery time of ETR290 monitoring.
                The default value is 10.
                "   
            ::= { hwDocsQamETR290MonitoringProfileEntry 5 }
            
        -- 1.3.6.1.4.1.2011.6.187.53.1.6
        hwDocsQamETR290MonitoringProbeDuration        OBJECT-TYPE
            SYNTAX      Unsigned32(60..120)
            UNITS       "second"                 
            MAX-ACCESS  read-create
            STATUS      current
            DESCRIPTION
                "Indicates the probe duration of ETR290 monitoring.
                The default value is 70.
                "   
            ::= { hwDocsQamETR290MonitoringProfileEntry 6 }
            
        -- 1.3.6.1.4.1.2011.6.187.53.1.7
        hwDocsQamETR290MonitoringTsSyncLossDetectTime        OBJECT-TYPE
            SYNTAX      Unsigned32(15..60)
            UNITS       "second"             
            MAX-ACCESS  read-create
            STATUS      current
            DESCRIPTION
                "Indicates the discovery time of TS synchronization loss in ETR290 monitoring.
                The default value is 15.
                "   
            ::= { hwDocsQamETR290MonitoringProfileEntry 7 }
            
        -- 1.3.6.1.4.1.2011.6.187.53.1.8
        hwDocsQamETR290MonitoringPATInterval        OBJECT-TYPE
            SYNTAX      Unsigned32(500..1000)
            UNITS       "millisecond"                
            MAX-ACCESS  read-create
            STATUS      current
            DESCRIPTION
                "Indicates the PAT detection period in ETR290 monitoring. 
                The default value is 500.
                "   
            ::= { hwDocsQamETR290MonitoringProfileEntry 8 }
            
        -- 1.3.6.1.4.1.2011.6.187.53.1.9
        hwDocsQamETR290MonitoringPMTInterval        OBJECT-TYPE
            SYNTAX      Unsigned32(500..1000)
            UNITS       "millisecond"            
            MAX-ACCESS  read-create
            STATUS      current
            DESCRIPTION
                "Indicates the PMT detection period in ETR290 monitoring. 
                The default value is 500.
                "   
            ::= { hwDocsQamETR290MonitoringProfileEntry 9 }
            
        -- 1.3.6.1.4.1.2011.6.187.53.1.10
        hwDocsQamETR290MonitoringPIDLossThreshold        OBJECT-TYPE
            SYNTAX      Unsigned32(5..10)
            UNITS       "second"                 
            MAX-ACCESS  read-create
            STATUS      current
            DESCRIPTION
                "Indicates the detection threshold for PID loss in ETR290 monitoring. 
                The default value is 5.
                "   
            ::= { hwDocsQamETR290MonitoringProfileEntry 10 }
            
        -- 1.3.6.1.4.1.2011.6.187.53.1.11
        hwDocsQamETR290MonitoringPCRInterval        OBJECT-TYPE
            SYNTAX      Unsigned32(40..500)
            UNITS       "millisecond"            
            MAX-ACCESS  read-create
            STATUS      current
            DESCRIPTION
                "Indicates the PCR detection period in ETR290 monitoring.               
                The default value is 40.
                "   
            ::= { hwDocsQamETR290MonitoringProfileEntry 11 }
            
        -- 1.3.6.1.4.1.2011.6.187.53.1.12
        hwDocsQamETR290MonitoringPCRDiscontinuityThreshold        OBJECT-TYPE
            SYNTAX      Unsigned32(100..500)
            UNITS       "millisecond"            
            MAX-ACCESS  read-create
            STATUS      current
            DESCRIPTION
                "Indicates the PCR difference threshold in ETR290 monitoring. 
                The default value is 100.
                "   
            ::= { hwDocsQamETR290MonitoringProfileEntry 12 }
            
        -- 1.3.6.1.4.1.2011.6.187.53.1.13
        hwDocsQamETR290MonitoringPCRAccuracyJitterThreshold        OBJECT-TYPE
            SYNTAX      Unsigned32(500..1000)
            UNITS       "nanosecond"                 
            MAX-ACCESS  read-create
            STATUS      current
            DESCRIPTION
                "Indicates the PCR precise jitter threshold in ETR290 monitoring.                       
                The default value is 500.
                "   
            ::= { hwDocsQamETR290MonitoringProfileEntry 13 }
            
        -- 1.3.6.1.4.1.2011.6.187.53.1.14
        hwDocsQamETR290MonitoringCATInterval        OBJECT-TYPE
            SYNTAX      Unsigned32(500..2000)
            UNITS       "nanosecond"                 
            MAX-ACCESS  read-create
            STATUS      current
            DESCRIPTION
                "Indicates the CAT detection period in ETR290 monitoring.  
                The default value is 500.
                "   
            ::= { hwDocsQamETR290MonitoringProfileEntry 14 }
            
        -- 1.3.6.1.4.1.2011.6.187.53.1.255
        hwDocsQamETR290MonitoringRowStatus        OBJECT-TYPE
            SYNTAX       RowStatus
            MAX-ACCESS   read-create
            STATUS       current
            DESCRIPTION
                "Row status, used to query, create, modify, and delete a input TS table. 
                 It supports the active(1), createAndGo(4), and destroy(6) operations.
                 During query, the value of this leaf is always active(1).
                 During deletion, specify the value of this leaf to destroy(6).
                 During creation, specify the value of this leaf to createAndGo(4).
                 To modify the parameters of a channel profile table, this leaf need not be issued together.
                 Options:
                 1. active(1)      -indicates the query operation
                 2. createAndGo(4) -indicates the creating operation
                 3. destroy(6)     -indicates the deleting operation
                "   
            ::= { hwDocsQamETR290MonitoringProfileEntry 255 }
            
        -- 1.3.6.1.4.1.2011.6.187.54
        hwDocsQamETR290MonitoringInputTSTable    OBJECT-TYPE
            SYNTAX          SEQUENCE OF HwDocsQamETR290MonitoringInputTSEntry
            MAX-ACCESS      not-accessible
            STATUS          current
            DESCRIPTION
                "Indicates the ETR290 monitoring information table of an input TS.                  
                The index of this table is hwDocsQamInputTSIndex.
                "
            ::= { hwEqamAn 54 }
                        
        -- 1.3.6.1.4.1.2011.6.187.54.1
        hwDocsQamETR290MonitoringInputTSEntry    OBJECT-TYPE
            SYNTAX          HwDocsQamETR290MonitoringInputTSEntry
            MAX-ACCESS      not-accessible
            STATUS          current
            DESCRIPTION
                "Indicates the ETR290 monitoring information table of an input TS.                  
                The index of this entry is hwDocsQamInputTSIndex.
                "
            INDEX   
                { 
                hwDocsQamInputTSIndex
                }
            ::= { hwDocsQamETR290MonitoringInputTSTable 1 }
            
        HwDocsQamETR290MonitoringInputTSEntry ::=
            SEQUENCE 
                {
                hwDocsQamInputTSETR290MonitoringEnable 
                  TruthValue, 
                hwDocsQamInputTSETR290MonitoringProfileName  
                  OCTET STRING,
                hwDocsQamInputTSETR290MonitoringClearStatus
                  INTEGER
               }
                                 
        -- 1.3.6.1.4.1.2011.6.187.54.1.1
        hwDocsQamInputTSETR290MonitoringEnable        OBJECT-TYPE
            SYNTAX      TruthValue
            MAX-ACCESS  read-write
            STATUS      current
            DESCRIPTION
                "Indicates the ETR290 monitoring enabling status of an input TS.  
                The default value is false(2).
                "   
            ::= { hwDocsQamETR290MonitoringInputTSEntry 1 }
        
        -- 1.3.6.1.4.1.2011.6.187.54.1.2
        hwDocsQamInputTSETR290MonitoringProfileName        OBJECT-TYPE
            SYNTAX      OCTET STRING (SIZE (1..15))
            MAX-ACCESS  read-write
            STATUS      current
            DESCRIPTION
                "Indicates the ETR290 monitoring profile name.
                "   
            ::= { hwDocsQamETR290MonitoringInputTSEntry 2 }
            
        -- 1.3.6.1.4.1.2011.6.187.54.1.3
        hwDocsQamInputTSETR290MonitoringClearStatus        OBJECT-TYPE
            SYNTAX      INTEGER{
                                 clear(1)
                               }
            MAX-ACCESS  read-write
            STATUS      current
            DESCRIPTION
                "Indicates clearing the ETR290 detection status of an input TS.                  
                Options:
                1. clear(1)   -indicates clearing the ETR290 detection status of an input TS.                
                "   
            ::= { hwDocsQamETR290MonitoringInputTSEntry 3 }
            
        -- 1.3.6.1.4.1.2011.6.187.55
        hwDocsQamInputTSETR290DetailsTable    OBJECT-TYPE
            SYNTAX          SEQUENCE OF HwDocsQamInputTSETR290DetailsEntry
            MAX-ACCESS      not-accessible
            STATUS          current
            DESCRIPTION
                "Indicates the detailed ETR290 monitoring information table of an input TS.                 
                The indexes of this table are hwDocsQamInputTSIndex and hwDocsQamInputTSETR290MonitoringType.
                "
            ::= { hwEqamAn 55 }
                        
        -- 1.3.6.1.4.1.2011.6.187.55.1
        hwDocsQamInputTSETR290DetailsEntry    OBJECT-TYPE
            SYNTAX          HwDocsQamInputTSETR290DetailsEntry
            MAX-ACCESS      not-accessible
            STATUS          current
            DESCRIPTION
                "Indicates the detailed ETR290 monitoring information table of an input TS.                  
                The indexes of this entry are hwDocsQamInputTSIndex and hwDocsQamInputTSETR290MonitoringType.
                "
            INDEX   
                { 
                hwDocsQamInputTSIndex,
                hwDocsQamInputTSETR290MonitoringType
                }
            ::= { hwDocsQamInputTSETR290DetailsTable 1 }
            
        HwDocsQamInputTSETR290DetailsEntry ::=
            SEQUENCE 
                {
                hwDocsQamInputTSETR290MonitoringType 
                  INTEGER, 
                hwDocsQamInputTSETR290MonitoringState  
                  INTEGER,
                hwDocsQamInputTSETR290MonitoringLastErrorIndication
                  INTEGER,
                hwDocsQamInputTSETR290MonitoringLastErrorOccurTime
                  TimeTicks,
                hwDocsQamInputTSETR290MonitoringCurrentErrorCount
                  Counter64,
                hwDocsQamInputTSETR290MonitoringTotalErrorCount
                  Counter64
               }
                                 
        -- 1.3.6.1.4.1.2011.6.187.55.1.1
        hwDocsQamInputTSETR290MonitoringType        OBJECT-TYPE
            SYNTAX      INTEGER
                  {
                  tsSyncLoss(1),
                  syncByteError(2),
                  patError(3),
                  ccError(4),
                  pmtError(5),
                  pidError(6),
                  transportError(7),
                  crcError(8),
                  pcrError(9),
                  pcrAccuracyError(10),
                  catError(11)
                  }
            MAX-ACCESS  not-accessible
            STATUS      current
            DESCRIPTION
                "Indicates the ETR290 monitoring type of an input TS.
                 Options:
                 1. tsSyncLoss(1)           --TS sync loss
                 2. syncByteError(2)        --Sync byte error
                 3. patError(3)             --PAT error
                 4. ccError(4)              --Continuity count error
                 5. pmtError(5)             --PMT error
                 6. pidError(6)             --PID error
                 7. transportError(7)       --Transport error
                 8. crcError(8)             --CRC error
                 9. pcrError(9)             --PCR error
                 10. pcrAccuracyError(10)   --PCR accuracy error
                 11. catError(11)           --CAT error
                "   
            ::= { hwDocsQamInputTSETR290DetailsEntry 1 }
            
        -- 1.3.6.1.4.1.2011.6.187.55.1.2
        hwDocsQamInputTSETR290MonitoringState        OBJECT-TYPE
            SYNTAX      INTEGER
                  {
                  ok(1),
                  alarm(2),
                  unknown(3),
                  disable(4)
                  }
            MAX-ACCESS  read-only
            STATUS      current
            DESCRIPTION
                "Indicates the ETR290 monitoring status of an input TS.
                 Options:
                 1. ok(1)          --No error
                 2. alarm(2)       --Have error
                 3. unknown(3)     --Monitoring
                 4. disable(4)     --ETR290 monitor disable
                 The default value is unknown(3).
                "   
            ::= { hwDocsQamInputTSETR290DetailsEntry 2 }
            
        -- 1.3.6.1.4.1.2011.6.187.55.1.3
        hwDocsQamInputTSETR290MonitoringLastErrorIndication        OBJECT-TYPE
            SYNTAX      INTEGER
                  {
                  now(1),
                  never(2),
                  last(3)
                  }
            MAX-ACCESS  read-only
            STATUS      current
            DESCRIPTION
                "Indicates the last error indication of ETR290 monitoring for an input TS.
                 Options:
                 1. now(1)      --Now
                 2. never(2)    --No error
                 3. last(3)     --Last error
                 4. The default value is never(2).
                "   
            ::= { hwDocsQamInputTSETR290DetailsEntry 3 }
            
        -- 1.3.6.1.4.1.2011.6.187.55.1.4
        hwDocsQamInputTSETR290MonitoringLastErrorOccurTime        OBJECT-TYPE
            SYNTAX      TimeTicks
            MAX-ACCESS  read-only
            STATUS      current
            DESCRIPTION
                "Indicates the difference between the time when ETR290 monitoring of an input TS has an error and the current time.  
                The default value is 0.
                "   
            ::= { hwDocsQamInputTSETR290DetailsEntry 4 }
            
        -- 1.3.6.1.4.1.2011.6.187.55.1.5
        hwDocsQamInputTSETR290MonitoringCurrentErrorCount        OBJECT-TYPE
            SYNTAX      Counter64
            MAX-ACCESS  read-only
            STATUS      current
            DESCRIPTION
                "Indicates the error count of the current probe in ETR290 monitoring for an input TS.                
                "   
            ::= { hwDocsQamInputTSETR290DetailsEntry 5 }
            
        -- 1.3.6.1.4.1.2011.6.187.55.1.6
        hwDocsQamInputTSETR290MonitoringTotalErrorCount        OBJECT-TYPE
            SYNTAX      Counter64
            MAX-ACCESS  read-only
            STATUS      current
            DESCRIPTION
                "Indicates the total error count in ETR290 monitoring for an input TS.
                "   
            ::= { hwDocsQamInputTSETR290DetailsEntry 6 }
        
        -- 1.3.6.1.4.1.2011.6.187.56
        hwDocsQamInputPIDETR290DetailsTable    OBJECT-TYPE
            SYNTAX          SEQUENCE OF HwDocsQamInputPIDETR290DetailsEntry
            MAX-ACCESS      not-accessible
            STATUS          current
            DESCRIPTION
                "Indicates the detailed ETR290 monitoring information table for the PID of an input TS.
                 The indexes of this table are hwDocsQamInputTSIndex, hwDocsQamInputTSETR290MonitoringType, hwDocsQamInputPIDETR290DetailsPIDIndex 
                 and hwDocsQamInputPIDETR290DetailsTableIndex.
                "
            ::= { hwEqamAn 56 }
                        
        -- 1.3.6.1.4.1.2011.6.187.56.1
        hwDocsQamInputPIDETR290DetailsEntry    OBJECT-TYPE
            SYNTAX          HwDocsQamInputPIDETR290DetailsEntry
            MAX-ACCESS      not-accessible
            STATUS          current
            DESCRIPTION
                "Indicates the detailed ETR290 monitoring information table for the PID of an input TS.
                 The indexes of this entry are hwDocsQamInputTSIndex, hwDocsQamInputTSETR290MonitoringType, hwDocsQamInputPIDETR290DetailsPIDIndex 
                 and hwDocsQamInputPIDETR290DetailsTableIndex.
                "
            INDEX   
                { 
                hwDocsQamInputTSIndex,
                hwDocsQamInputTSETR290MonitoringType,
                hwDocsQamInputPIDETR290DetailsPIDIndex,
                hwDocsQamInputPIDETR290DetailsTableIndex
                }
            ::= { hwDocsQamInputPIDETR290DetailsTable 1 }
            
        HwDocsQamInputPIDETR290DetailsEntry ::=
            SEQUENCE 
                {
                hwDocsQamInputPIDETR290DetailsPIDIndex 
                  Unsigned32, 
                hwDocsQamInputPIDETR290DetailsTableIndex  
                  Unsigned32,
                hwDocsQamInputPIDETR290DetailsPID
                  Unsigned32,
                hwDocsQamInputPIDETR290DetailsTableID
                  Unsigned32,
                hwDocsQamInputPIDETR290MonitoringState
                  INTEGER,
                hwDocsQamInputPIDETR290MonitoringLastErrorIndication
                  INTEGER,
                hwDocsQamInputPIDETR290MonitoringLastErrorOccurTime
                  TimeTicks,
                hwDocsQamInputPIDETR290MonitoringCurrentErrorCount
                  Counter64,
                hwDocsQamInputPIDETR290MonitoringCurrentRecv
                  TruthValue,
                hwDocsQamInputPIDETR290MonitoringRecvCount
                  Counter64,
                hwDocsQamInputPIDETR290MonitoringPCRDiscontinuity
                  Unsigned32,
                hwDocsQamInputPIDETR290MonitoringPCRDiscontinuityMax
                  Unsigned32,
                hwDocsQamInputPIDETR290MonitoringPCRAccuracyJitter
                  Unsigned32,
                hwDocsQamInputPIDETR290MonitoringPCRAccuracyJitterMax
                  Unsigned32
               }
                                 
        -- 1.3.6.1.4.1.2011.6.187.56.1.1
        hwDocsQamInputPIDETR290DetailsPIDIndex        OBJECT-TYPE
            SYNTAX      Unsigned32(1..4294967295)
            MAX-ACCESS  not-accessible
            STATUS      current
            DESCRIPTION
                "Indicates the PID index of an input TS.
                "   
            ::= { hwDocsQamInputPIDETR290DetailsEntry 1 }
        
        -- 1.3.6.1.4.1.2011.6.187.56.1.2
        hwDocsQamInputPIDETR290DetailsTableIndex        OBJECT-TYPE
            SYNTAX      Unsigned32(1..4294967295)
            MAX-ACCESS  not-accessible
            STATUS      current
            DESCRIPTION
                "Indicates the PID table index of an input TS.                
                "   
            ::= { hwDocsQamInputPIDETR290DetailsEntry 2 }
            
        -- 1.3.6.1.4.1.2011.6.187.56.1.3
        hwDocsQamInputPIDETR290DetailsPID        OBJECT-TYPE
            SYNTAX      Unsigned32(0..8191|4294967295)
            MAX-ACCESS  read-only
            STATUS      current
            DESCRIPTION
                "Indicates the PID value of an input TS.                
                "   
            ::= { hwDocsQamInputPIDETR290DetailsEntry 3 }
            
        -- 1.3.6.1.4.1.2011.6.187.56.1.4
        hwDocsQamInputPIDETR290DetailsTableID        OBJECT-TYPE
            SYNTAX      Unsigned32(0..255|4294967295)
            MAX-ACCESS  read-only
            STATUS      current
            DESCRIPTION
                "Indicates the PID table ID of an input TS.
                "   
            ::= { hwDocsQamInputPIDETR290DetailsEntry 4 }
            
        -- 1.3.6.1.4.1.2011.6.187.56.1.5
        hwDocsQamInputPIDETR290MonitoringState        OBJECT-TYPE
            SYNTAX      INTEGER
                  {
                  ok(1),
                  alarm(2),
                  unknown(3),
                  disable(4)
                  }
            MAX-ACCESS  read-only
            STATUS      current
            DESCRIPTION
                "Indicates the ETR290 monitoring status of the PID of an input TS. 
                 Options:
                 1. ok(1)          --No error
                 2. alarm(2)       --Have error
                 3. unknown(3)     --Monitoring
                 4. disable(4)     --ETR290 monitor disable
                 The default value is unknown(3).
                "   
            ::= { hwDocsQamInputPIDETR290DetailsEntry 5 }
            
        -- 1.3.6.1.4.1.2011.6.187.56.1.6
        hwDocsQamInputPIDETR290MonitoringLastErrorIndication        OBJECT-TYPE
            SYNTAX      INTEGER
                  {
                  now(1),
                  never(2),
                  last(3)
                  }
            MAX-ACCESS  read-only
            STATUS      current
            DESCRIPTION
                "Indicates the last error indication of ETR290 monitoring for the PID of an input TS.
                 Options:
                 1. now(1)      --Now
                 2. never(2)    --No error
                 3. last(3)     --Last error
                 4. The default value is never(2).
                "   
            ::= { hwDocsQamInputPIDETR290DetailsEntry 6 }
            
        -- 1.3.6.1.4.1.2011.6.187.56.1.7
        hwDocsQamInputPIDETR290MonitoringLastErrorOccurTime        OBJECT-TYPE
            SYNTAX      TimeTicks
            MAX-ACCESS  read-only
            STATUS      current
            DESCRIPTION
                "Indicates the difference between the time when ETR290 monitoring of the PID of an input TS has an error and the current time. 
                The default value is 0.
                "   
            ::= { hwDocsQamInputPIDETR290DetailsEntry 7 }
            
        -- 1.3.6.1.4.1.2011.6.187.56.1.8
        hwDocsQamInputPIDETR290MonitoringCurrentErrorCount        OBJECT-TYPE
            SYNTAX      Counter64
            MAX-ACCESS  read-only
            STATUS      current
            DESCRIPTION
                "Indicates the error count of the current probe in ETR290 monitoring for the PID of an input TS.
                "   
            ::= { hwDocsQamInputPIDETR290DetailsEntry 8 }
            
        -- 1.3.6.1.4.1.2011.6.187.56.1.9
        hwDocsQamInputPIDETR290MonitoringCurrentRecv        OBJECT-TYPE
            SYNTAX      TruthValue
            MAX-ACCESS  read-only
            STATUS      current
            DESCRIPTION
                "Indicates whether the ETR290 monitoring probe for the PID of an input TS receives packets. 
                The default value is false(2).
                "   
            ::= { hwDocsQamInputPIDETR290DetailsEntry 9 }
            
        -- 1.3.6.1.4.1.2011.6.187.56.1.10
        hwDocsQamInputPIDETR290MonitoringRecvCount        OBJECT-TYPE
            SYNTAX      Counter64
            MAX-ACCESS  read-only
            STATUS      current
            DESCRIPTION
                "Indicates the number of packets received in ETR290 monitoring for the PID of an input TS.                
                "   
            ::= { hwDocsQamInputPIDETR290DetailsEntry 10 }
            
        -- 1.3.6.1.4.1.2011.6.187.56.1.11
        hwDocsQamInputPIDETR290MonitoringPCRDiscontinuity        OBJECT-TYPE
            SYNTAX      Unsigned32(0..4294967295)
            UNITS       "millisecond"            
            MAX-ACCESS  read-only
            STATUS      current
            DESCRIPTION
                "Indicates the PCR discontinuity in ETR290 monitoring for the PID of an input TS. 
                The default value is 0, indicating that the PCR discontinuity is invalid.
                "    
            ::= { hwDocsQamInputPIDETR290DetailsEntry 11 }
            
        -- 1.3.6.1.4.1.2011.6.187.56.1.12
        hwDocsQamInputPIDETR290MonitoringPCRDiscontinuityMax        OBJECT-TYPE
            SYNTAX      Unsigned32(0..4294967295)
            UNITS       "millisecond"            
            MAX-ACCESS  read-only
            STATUS      current
            DESCRIPTION
                "Indicates the maximum PCR discontinuity in ETR290 monitoring for the PID of an input TS.
                The default value is 0, indicating that the maximum PCR discontinuity is invalid.
                "    
            ::= { hwDocsQamInputPIDETR290DetailsEntry 12 }
            
        -- 1.3.6.1.4.1.2011.6.187.56.1.13
        hwDocsQamInputPIDETR290MonitoringPCRAccuracyJitter        OBJECT-TYPE
            SYNTAX      Unsigned32(0..4294967295)
            UNITS       "nanosecond"                 
            MAX-ACCESS  read-only
            STATUS      current
            DESCRIPTION
                "Indicates the PCR accuracy jitter in ETR290 monitoring for the PID of an input TS. 
                The default value is 0, indicating that the PCR accuracy jitter is invalid.
                "    
            ::= { hwDocsQamInputPIDETR290DetailsEntry 13 }
            
        -- 1.3.6.1.4.1.2011.6.187.56.1.14
        hwDocsQamInputPIDETR290MonitoringPCRAccuracyJitterMax        OBJECT-TYPE
            SYNTAX      Unsigned32(0..4294967295)
            UNITS       "nanosecond"                 
            MAX-ACCESS  read-only
            STATUS      current
            DESCRIPTION
                "Indicates the maximum PCR accuracy jitter in ETR290 monitoring for the PID of an input TS.
                The default value is 0, indicating that the maximum PCR accuracy jitter is invalid.
                "    
            ::= { hwDocsQamInputPIDETR290DetailsEntry 14 }

    -- the traps VbOids
    hwDocsQamNotificationObject OBJECT IDENTIFIER ::= { hwEqamAn 24 }
    
    hwDocsQamNotificationProgramID OBJECT-TYPE
        SYNTAX Integer32(1..65535)
        MAX-ACCESS  accessible-for-notify
        STATUS current
        DESCRIPTION
            "Program ID."
        ::= { hwDocsQamNotificationObject 1 }

    hwDocsQamNotificationPID OBJECT-TYPE
        SYNTAX Integer32(0..8190)
        MAX-ACCESS  accessible-for-notify
        STATUS current
        DESCRIPTION
            "PID."
        ::= { hwDocsQamNotificationObject 2 }
        
    hwDocsQamNotificationPSIType        OBJECT-TYPE
            SYNTAX      INTEGER
                  {
                  pat(1),
                  cat(2),
                  pmt(3),
                  nit(4),
                  sdt(5),
                  eit(6),
                  tdttot(7)
                  }
            MAX-ACCESS  accessible-for-notify
            STATUS      current
            DESCRIPTION
                "Indicates the program stream type.
                 Options: 
                 1. pat(1)      --Program Association Table
                 2. cat(2)      --Conditional Access Table
                 3. pmt(3)      --Program Map Table
                 4. nit(4)      --Network Information Table
                 5. sdt(5)      --Service Description Table
                 6. eit(6)      --Event Information Table
                 7. tdttot(7)   --Time and Date Table/Time Offset Table
                "
            ::= { hwDocsQamNotificationObject 3 }
            
    hwDocsQamNotificationProgramName        OBJECT-TYPE
            SYNTAX       OCTET STRING (SIZE (0..63))
            MAX-ACCESS   accessible-for-notify
            STATUS       current
            DESCRIPTION
              "Indicate the program name.
              "
            ::= { hwDocsQamNotificationObject 4 } 
        
    hwDocsQamDVBPATErrorTrap NOTIFICATION-TYPE
        OBJECTS {
            hwDocsQamInputTSIndex
            }
        STATUS  current
        DESCRIPTION
            "The hwDocsQamDVBPATErrorTrap will be sent
             when the content of input PAT is incorrect.
            "
        ::= { hwEqamAn 25 } 

    hwDocsQamDVBPATMissingTrap NOTIFICATION-TYPE
        OBJECTS {
            hwDocsQamInputTSIndex
            }
        STATUS  current
        DESCRIPTION
            "The hwDocsQamDVBPATMissingTrap will be sent
             when PAT is missing.
            "
        ::= { hwEqamAn 26 }

    hwDocsQamDVBPMTErrorTrap NOTIFICATION-TYPE
        OBJECTS {
            hwDocsQamInputTSIndex,
            hwDocsQamNotificationProgramID,
            hwDocsQamNotificationPID
            }
        STATUS  current
        DESCRIPTION
            "The hwDocsQamDVBPMTErrorTrap will be sent
             when the content of input PMT is incorrect.
            "
        ::= { hwEqamAn 27 } 

    hwDocsQamDVBPMTMissingTrap NOTIFICATION-TYPE
        OBJECTS {
            hwDocsQamInputTSIndex,
            hwDocsQamNotificationProgramID,
            hwDocsQamNotificationPID
            }
        STATUS  current
        DESCRIPTION
            "The hwDocsQamDVBPMTMissingTrap will be sent
             when PMT is missing.
            "
        ::= { hwEqamAn 28 } 

    hwDocsQamDVBContinutyCounterErrorTrap NOTIFICATION-TYPE
        OBJECTS {
            hwDocsQamInputTSIndex
            }
        STATUS  current
        DESCRIPTION
            "The hwDocsQamDVBContinutyCounterErrorTrap will be sent
             when the continuity counter error rate is too high.
            "
        ::= { hwEqamAn 29 } 
        
    hwDocsQamDVBRTPSequenceErrorTrap NOTIFICATION-TYPE
        OBJECTS {
            hwDocsQamInputTSIndex
            }
        STATUS  current
        DESCRIPTION
            "The hwDocsQamDVBRTPSequenceErrorTrap will be sent
             when the counter of RTP sequence error reaches the uplimit.
            "
        ::= { hwEqamAn 36 }
        
    hwDocsQamETR290MonitoringAlarmTsSyncLossTrap NOTIFICATION-TYPE
        OBJECTS {
            hwDocsQamInputTSIndex
            }
        STATUS  current
        DESCRIPTION
            "The hwDocsQamETR290MonitoringAlarmTsSyncLossTrap will be sent
             when the TS loss of synchronization.
            "
        ::= { hwEqamAn 57 }

    hwDocsQamETR290MonitoringAlarmSyncByteErrorTrap NOTIFICATION-TYPE
        OBJECTS {
            hwDocsQamInputTSIndex
            }
        STATUS  current
        DESCRIPTION
            "The hwDocsQamETR290MonitoringAlarmSyncByteErrorTrap will be sent
             when the TS sync_byte not equal 0x47.
            "
        ::= { hwEqamAn 58 }

    hwDocsQamETR290MonitoringAlarmPATErrorTrap NOTIFICATION-TYPE
        OBJECTS {
            hwDocsQamInputTSIndex,
            hwDocsQamNotificationPID
            }
        STATUS  current
        DESCRIPTION
            "The hwDocsQamETR290MonitoringAlarmPATErrorTrap will be sent
             when the PID 0x0000 does not occur at least every specified interval.
            "
        ::= { hwEqamAn 59 }

    hwDocsQamETR290MonitoringAlarmContinuitycountErrorTrap NOTIFICATION-TYPE
        OBJECTS {
            hwDocsQamInputTSIndex,
            hwDocsQamNotificationPID
            }
        STATUS  current
        DESCRIPTION
            "The hwDocsQamETR290MonitoringAlarmContinuitycountErrorTrap will be sent
             when the incorrect packet order a packet occurs more than twice.
            "
        ::= { hwEqamAn 60 }

    hwDocsQamETR290MonitoringAlarmPMTErrorTrap NOTIFICATION-TYPE
        OBJECTS {
            hwDocsQamInputTSIndex,
            hwDocsQamNotificationPID,
            hwDocsQamNotificationProgramID,
            hwDocsQamNotificationProgramName
            }
        STATUS  current
        DESCRIPTION
            "The hwDocsQamETR290MonitoringAlarmPMTErrorTrap will be sent
             when the sections with table_id 0x02 , do not occur at least every specified interval on the PID which is referred to in the PAT.
            "
        ::= { hwEqamAn 61 }

    hwDocsQamETR290MonitoringAlarmPIDErrorTrap NOTIFICATION-TYPE
        OBJECTS {
            hwDocsQamInputTSIndex,
            hwDocsQamNotificationPID,
            hwDocsQamNotificationProgramID,
            hwDocsQamNotificationProgramName
            }
        STATUS  current
        DESCRIPTION
            "The hwDocsQamETR290MonitoringAlarmPIDErrorTrap will be sent
             when the referred PID does not occur for a user specified period.
            "
        ::= { hwEqamAn 62 }

    hwDocsQamETR290MonitoringAlarmTransportErrorTrap NOTIFICATION-TYPE
        OBJECTS {
            hwDocsQamInputTSIndex,
            hwDocsQamNotificationPID
            }
        STATUS  current
        DESCRIPTION
            "The hwDocsQamETR290MonitoringAlarmTransportErrorTrap will be sent
             when the transport_error_indicator in the TS-Header is set to 1.
            "
        ::= { hwEqamAn 63 }

    hwDocsQamETR290MonitoringAlarmCRCErrorTrap NOTIFICATION-TYPE
        OBJECTS {
            hwDocsQamInputTSIndex,
            hwDocsQamNotificationPID,
            hwDocsQamNotificationPSIType
            }
        STATUS  current
        DESCRIPTION
            "The hwDocsQamETR290MonitoringAlarmCRCErrorTrap will be sent
             when the CRC error occurred in CAT, PAT, PMT, NIT, EIT,BAT, SDT or TOT table.
            "
        ::= { hwEqamAn 64 }

    hwDocsQamETR290MonitoringAlarmPCRErrorTrap NOTIFICATION-TYPE
        OBJECTS {
            hwDocsQamInputTSIndex,
            hwDocsQamNotificationPID,
            hwDocsQamNotificationProgramID,
            hwDocsQamNotificationProgramName
            }
        STATUS  current
        DESCRIPTION
            "The hwDocsQamETR290MonitoringAlarmPCRErrorTrap will be sent
             when PCR discontinuity of more than specified interval occurring without specific indication.
            "
        ::= { hwEqamAn 65 }

    hwDocsQamETR290MonitoringAlarmPCRAccuracyErrorTrap NOTIFICATION-TYPE
        OBJECTS {
            hwDocsQamInputTSIndex,
            hwDocsQamNotificationPID,
            hwDocsQamNotificationProgramID,
            hwDocsQamNotificationProgramName
            }
        STATUS  current
        DESCRIPTION
            "The hwDocsQamETR290MonitoringAlarmPCRAccuracyErrorTrap will be sent
             when the PCR accuracy of selected programme is not within positive and negative 500 ns.
            "
        ::= { hwEqamAn 66 }

    hwDocsQamETR290MonitoringAlarmCATErrorTrap NOTIFICATION-TYPE
        OBJECTS {
            hwDocsQamInputTSIndex,
            hwDocsQamNotificationPID
            }
        STATUS  current
        DESCRIPTION
            "The hwDocsQamETR290MonitoringAlarmCATErrorTrap will be sent
             when the packets with transport_scrambling_control not 00 present, but no section with table_id 0x01 present.
            "
        ::= { hwEqamAn 67 }
        
    hwDocsQamDVBPrimaryInputTSLossTrap NOTIFICATION-TYPE
        OBJECTS {
            hwDocsQamInputTSIndex,
            hwDocsQamInputTSIpAddressType,
            hwDocsQamInputTSMulticastIpAddress,
            hwDocsQamInputTSSourceIpAddress,
            hwDocsQamInputTSUdpPort
            }
        STATUS  current
        DESCRIPTION
            "The hwDocsQamDVBPrimaryInputTSLossTrap will be sent
             when the primary input TS is lost.
            "
        ::= { hwEqamAn 68 }
        
    hwDocsQamDVBPrimaryInputTSRecoveryTrap NOTIFICATION-TYPE
        OBJECTS {
            hwDocsQamInputTSIndex,
            hwDocsQamInputTSIpAddressType,
            hwDocsQamInputTSMulticastIpAddress,
            hwDocsQamInputTSSourceIpAddress,
            hwDocsQamInputTSUdpPort
            }
        STATUS  current
        DESCRIPTION
            "The hwDocsQamDVBPrimaryInputTSRecoveryTrap will be sent
             when the primary input TS recovers.
            "
        ::= { hwEqamAn 69 }
        
    hwDocsQamDVBSecondaryInputTSLossTrap NOTIFICATION-TYPE
        OBJECTS {
            hwDocsQamInputTSIndex,
            hwDocsQamInputTSIpAddressType,
            hwDocsQamInputTSSecondaryMulticastIpAddress,
            hwDocsQamInputTSSecondarySourceIpAddress,
            hwDocsQamInputTSSecondaryUdpPort
            }
        STATUS  current
        DESCRIPTION
            "The hwDocsQamDVBSecondaryInputTSLossTrap will be sent
             when the secondary input TS is lost.
            "
        ::= { hwEqamAn 70 }
        
    hwDocsQamDVBSecondaryInputTSRecoveryTrap NOTIFICATION-TYPE
        OBJECTS {
            hwDocsQamInputTSIndex,
            hwDocsQamInputTSIpAddressType,
            hwDocsQamInputTSSecondaryMulticastIpAddress,
            hwDocsQamInputTSSecondarySourceIpAddress,
            hwDocsQamInputTSSecondaryUdpPort
            }
        STATUS  current
        DESCRIPTION
            "The hwDocsQamDVBSecondaryInputTSRecoveryTrap will be sent
             when the secondary input TS recovers.
            "
        ::= { hwEqamAn 71 }
                
    hwDocsQamVODLocalIpHashConflictTrap NOTIFICATION-TYPE
        OBJECTS {
            hwFrameIndex,
            hwSlotIndex,
            hwPortIndex,
            hwDocsQamVideoDomainLocalIpAddressType,
            hwDocsQamVideoDomainLocalIpAddress
            }
        STATUS  current
        DESCRIPTION
            "The hwDocsQamVODLocalIpHashConflictTrap will be sent
             when the local VOD IP address has a hash conflict.
            "
        ::= { hwEqamAn 72 }
                
        -- 1.3.6.1.4.1.2011.6.187.73
        hwEqamLicControlObjects   OBJECT IDENTIFIER ::= { hwEqamAn 73 }
        
        -- 1.3.6.1.4.1.2011.6.187.73.1
        hwEqamExtendLicenseDVBPortUsed  OBJECT-TYPE
            SYNTAX      Unsigned32(0..4294967295)
            MAX-ACCESS  read-only
            STATUS      current
            DESCRIPTION
                "Indicates the total number of ports used being authorized by the extended license for DVB.  
                The default value is 0.
                " 
            ::= { hwEqamLicControlObjects 1 }
                        
        -- 1.3.6.1.4.1.2011.6.187.73.2
        hwEqamExtendLicenseDVBPortLockFlg  OBJECT-TYPE
                        SYNTAX      INTEGER
                  {
                  locked(1),
                  unlocked(2)
                  }
            MAX-ACCESS  read-write
            STATUS      current
            DESCRIPTION
                "Indicates whether the DVB extended license is locked.
                 Options: 
                 1. locked(1)      --License is locked
                 2. unlocked(2)    --License is unlocked
                 The default value is locked(1).
                "   
            ::= { hwEqamLicControlObjects 2 }
                        
        -- 1.3.6.1.4.1.2011.6.187.73.3
        hwEqamExtendLicenseDVBPortLack  OBJECT-TYPE
            SYNTAX      Unsigned32(0..4294967295)
            MAX-ACCESS  read-only
            STATUS      current
            DESCRIPTION
                "Indicates the number of ports to be authorized by the extended license for DVB.    
                The default value is 0.
                " 
            ::= { hwEqamLicControlObjects 3 }
                        
        -- 1.3.6.1.4.1.2011.6.187.73.4
        hwEqamExtendLicenseVODChannelUsed  OBJECT-TYPE
            SYNTAX      Unsigned32(0..4294967295)
            MAX-ACCESS  read-only
            STATUS      current
            DESCRIPTION
                "Indicates the total number of channels used being authorized by the extended license for VOD.  
                The default value is 0.
                " 
            ::= { hwEqamLicControlObjects 4 }
                        
        -- 1.3.6.1.4.1.2011.6.187.73.5
        hwEqamExtendLicenseVODChannelLockFlg  OBJECT-TYPE
                        SYNTAX      INTEGER
                  {
                  locked(1),
                  unlocked(2)
                  }
            MAX-ACCESS  read-write
            STATUS      current
            DESCRIPTION
                "Indicates whether the VOD extended license is locked.
                 Options: 
                 1. locked(1)      --License is locked
                 2. unlocked(2)    --License is unlocked
                 The default value is locked(1).
                "   
            ::= { hwEqamLicControlObjects 5 }
                        
        -- 1.3.6.1.4.1.2011.6.187.73.6
        hwEqamExtendLicenseVODChannelLack  OBJECT-TYPE
            SYNTAX      Unsigned32(0..4294967295)
            MAX-ACCESS  read-only
            STATUS      current
            DESCRIPTION
                "Indicates the number of channels to be authorized by the extended license for VOD.    
                The default value is 0.
                " 
            ::= { hwEqamLicControlObjects 6 }
                        
        -- 1.3.6.1.4.1.2011.6.187.73.7
        hwEqamLicenseSnmpControlValue  OBJECT-TYPE
            SYNTAX      Unsigned32(0..4294967295)
            MAX-ACCESS  read-write
            STATUS      current
            DESCRIPTION
                "Indicates SNMP cache for EQAM control.   
                The default value is 0.
                " 
            ::= { hwEqamLicControlObjects 7 }                        
                                                
        -- 1.3.6.1.4.1.2011.6.187.73.8
        hwEqamExtendLicenseVODScrambleChannelUsed  OBJECT-TYPE
            SYNTAX      Unsigned32(0..4294967295)
            MAX-ACCESS  read-only
            STATUS      current
            DESCRIPTION
                "Indicates the total number of channel being srcambled by the extended license for VOD.  
                The default value is 0.
                " 
            ::= { hwEqamLicControlObjects 8 }
                        
        -- 1.3.6.1.4.1.2011.6.187.73.9
        hwEqamExtendLicenseVODScrambleChannelLockFlg  OBJECT-TYPE
            SYNTAX      INTEGER
                  {
                  locked(1),
                  unlocked(2)
                  }
            MAX-ACCESS  read-write
            STATUS      current
            DESCRIPTION
                "Indicates whether the VOD srcamble channel extended license is locked.
                 Options: 
                 1. locked(1)      --License is locked
                 2. unlocked(2)    --License is unlocked
                 The default value is locked(1).
                "   
            ::= { hwEqamLicControlObjects 9 }
                        
        -- 1.3.6.1.4.1.2011.6.187.73.10
        hwEqamExtendLicenseVODScrambleChannelLack  OBJECT-TYPE
            SYNTAX      Unsigned32(0..4294967295)
            MAX-ACCESS  read-only
            STATUS      current
            DESCRIPTION
                "Indicates the number of channel to be srcambled by the extended license for VOD.    
                The default value is 0.
                " 
            ::= { hwEqamLicControlObjects 10 }
                        
        -- 1.3.6.1.4.1.2011.6.187.74
        hwDocsQamVODProcessGroupTable    OBJECT-TYPE
            SYNTAX          SEQUENCE OF HwDocsQamVODProcessGroupEntry
            MAX-ACCESS      not-accessible
            STATUS          current
            DESCRIPTION
                "Indicates the table for configuring the working board and protection board in the VOD service processing protection group, and perform switchover. 
                 The index of this table is hwDocsQamVODProcessGroupID.
                "
            ::= { hwEqamAn 74}
            
        -- 1.3.6.1.4.1.2011.6.187.74.1
        hwDocsQamVODProcessGroupEntry    OBJECT-TYPE
            SYNTAX          HwDocsQamVODProcessGroupEntry
            MAX-ACCESS      not-accessible
            STATUS          current
            DESCRIPTION
                "Indicates the table for configuring the working board and protection board in the VOD service processing protection group, and perform switchover. 
                 The index of this entry is hwDocsQamVODProcessGroupID.
                "
            INDEX   
                { 
                hwDocsQamVODProcessGroupID
                }
            ::= { hwDocsQamVODProcessGroupTable 1 }
            
        HwDocsQamVODProcessGroupEntry ::=
            SEQUENCE 
                { 
                hwDocsQamVODProcessGroupID
                  Unsigned32,
                hwDocsQamVODProcessGroupWorkFrameID
                  Unsigned32,
                hwDocsQamVODProcessGroupWorkSlotID
                  Unsigned32,
                hwDocsQamVODProcessGroupProtectFrameID
                  Unsigned32,
                hwDocsQamVODProcessGroupProtectSlotID
                  Unsigned32,
                hwDocsQamVODProcessGroupSwitchover
                  INTEGER,
                hwDocsQamVODProcessGroupActiveFrameID
                  Unsigned32,
                hwDocsQamVODProcessGroupActiveSlotID
                  Unsigned32,
                hwDocsQamVODProcessGroupActive
                  INTEGER,
                hwDocsQamVODProcessGroupRowStatus
                  RowStatus
               }
               
        -- 1.3.6.1.4.1.2011.6.187.74.1.1
        hwDocsQamVODProcessGroupID        OBJECT-TYPE
            SYNTAX       Unsigned32(1..8|4294967295)
            MAX-ACCESS   not-accessible
            STATUS       current
            DESCRIPTION
                "Indicates the ID of a VOD service processing protection group.               
                "
            ::= { hwDocsQamVODProcessGroupEntry 1 }
            
        -- 1.3.6.1.4.1.2011.6.187.74.1.2
        hwDocsQamVODProcessGroupWorkFrameID        OBJECT-TYPE
            SYNTAX       Unsigned32(0..255|4294967295)
            MAX-ACCESS   read-create
            STATUS       current
            DESCRIPTION
                "Indicates the ID of the frame that accomdates the working board in a VOD service processing protection group. 
                "
            ::= { hwDocsQamVODProcessGroupEntry 2 }
            
        -- 1.3.6.1.4.1.2011.6.187.74.1.3
        hwDocsQamVODProcessGroupWorkSlotID        OBJECT-TYPE
            SYNTAX       Unsigned32(0..255|4294967295)
            MAX-ACCESS   read-create
            STATUS       current
            DESCRIPTION
                "Indicates the ID of the slot that accommodates the working board in a VOD service processing protection group. 
                "
            ::= { hwDocsQamVODProcessGroupEntry 3 }
            
        -- 1.3.6.1.4.1.2011.6.187.74.1.4
        hwDocsQamVODProcessGroupProtectFrameID        OBJECT-TYPE
            SYNTAX       Unsigned32(0..255|4294967295)
            MAX-ACCESS   read-create
            STATUS       current
            DESCRIPTION
                "Indicates the ID of the frame that accommodates the protection board in a VOD service processing protection group.
                "
            ::= { hwDocsQamVODProcessGroupEntry 4 }
            
        -- 1.3.6.1.4.1.2011.6.187.74.1.5
        hwDocsQamVODProcessGroupProtectSlotID        OBJECT-TYPE
            SYNTAX       Unsigned32(0..255|4294967295)
            MAX-ACCESS   read-create
            STATUS       current
            DESCRIPTION
                "Indicates the ID of the slot that accommodates the protection board in a VOD service processing protection group.
                "
            ::= { hwDocsQamVODProcessGroupEntry 5 }
            
        -- 1.3.6.1.4.1.2011.6.187.74.1.6
        hwDocsQamVODProcessGroupSwitchover        OBJECT-TYPE
            SYNTAX      INTEGER
                  {
                  switchover(1),
                  none(255)
                  }
            MAX-ACCESS  read-write
            STATUS      current
            DESCRIPTION
                "Indicates switchover in a VOD service processing protection group.
                 The default value is none(255).
                                 Options: 
                 1. switchover(1)   -Perform a switchover operation.
                 2. none(255)       -Do not perform any operation. 
                "
            ::= { hwDocsQamVODProcessGroupEntry 6 }
            
        -- 1.3.6.1.4.1.2011.6.187.74.1.7
        hwDocsQamVODProcessGroupActiveFrameID        OBJECT-TYPE
            SYNTAX       Unsigned32(0..255|4294967295)
            MAX-ACCESS   read-only
            STATUS       current
            DESCRIPTION
                "Indicates the ID of the frame that accommodates the active board in a VOD service processing protection group. 
                "
            ::= { hwDocsQamVODProcessGroupEntry 7 }
            
        -- 1.3.6.1.4.1.2011.6.187.74.1.8
        hwDocsQamVODProcessGroupActiveSlotID        OBJECT-TYPE
            SYNTAX       Unsigned32(0..255|4294967295)
            MAX-ACCESS   read-only
            STATUS       current
            DESCRIPTION
                "Indicates the ID of the slot that accommodates the active board in a VOD service processing protection group.
                "
            ::= { hwDocsQamVODProcessGroupEntry 8 }
            
        -- 1.3.6.1.4.1.2011.6.187.74.1.9
        hwDocsQamVODProcessGroupActive        OBJECT-TYPE
            SYNTAX       INTEGER
                  {
                  work(1),
                  protect(2),
                  none(255)
                  }
            MAX-ACCESS   read-only
            STATUS       current
            DESCRIPTION
                "Indicates the role of the active board in a VOD service processing protection group.
                Options:
                1. work(1)      -Indicates that the working board in a VOD service processing protection group is the active board.
                2. protect(2)   -Indicates that the protection board in a VOD service processing protection group is the active board.
                3. none(255)    -Indicates that the current VOD service processing protection group does not have an active board.
                "
            ::= { hwDocsQamVODProcessGroupEntry 9 }
        
        -- 1.3.6.1.4.1.2011.6.187.74.1.255
        hwDocsQamVODProcessGroupRowStatus        OBJECT-TYPE
            SYNTAX       RowStatus
            MAX-ACCESS   read-create
            STATUS       current
            DESCRIPTION
                "Indicates a row status for querying, creating, modifying, and deleting a VOD service processing protection group table. 
                 It supports active(1), createAndGo(4), and destroy(6) operations. 
                 During query operations, the value of this leaf is always active(1). 
                 During delete operations, the value of this leaf must be set to destroy(6).
                 During create operations, the value of this leaf must be set to createAndGo(4). 
                 This leaf is not mandatory when the table of a VOD service processing protection group needs to be modified.                            
                 Options:
                 1. active(1)      -indicates the query operation
                 2. createAndGo(4) -indicates the creating operation
                 3. destroy(6)     -indicates the deleting operation
                "
            ::= { hwDocsQamVODProcessGroupEntry 255 } 
                        
        -- 1.3.6.1.4.1.2011.6.187.75
        hwDocsQamEISProfileTable    OBJECT-TYPE
            SYNTAX          SEQUENCE OF HwDocsQamEISProfileEntry
            MAX-ACCESS      not-accessible
            STATUS          current
            DESCRIPTION
                "Indicates the EQAM EIS profile table used for SCS.
                 The index of this table is hwDocsQamEISProfileName.
                "
            ::= { hwEqamAn 75 }
    
        -- 1.3.6.1.4.1.2011.6.187.75.1
        hwDocsQamEISProfileEntry    OBJECT-TYPE
            SYNTAX          HwDocsQamEISProfileEntry
            MAX-ACCESS      not-accessible
            STATUS          current
            DESCRIPTION
                "Indicates the EQAM EIS profile table used for SCS.
                 The index of this entry is hwDocsQamEISProfileName.
                "
            INDEX   
                { 
                hwDocsQamEISProfileName
                }
            ::= { hwDocsQamEISProfileTable  1 }
        
        HwDocsQamEISProfileEntry ::=
            SEQUENCE 
                { 
                hwDocsQamEISProfileName
                  OCTET STRING,
                hwDocsQamEISProfileTcpPort
                  InetPortNumber,
                hwDocsQamEISProfileCPDuration
                  Unsigned32,
                hwDocsQamEISProfileChannelTestInterval
                  Unsigned32,
                                hwDocsQamEISProfileChannelTestTimeout
                                  Unsigned32,
                                hwDocsQamEISProfileDSCP
                                  Integer32,
		hwDocsQamEISProfileProtocol
		  INTEGER,
                hwDocsQamEISProfileRowStatus
                  RowStatus   
                }
        
        -- 1.3.6.1.4.1.2011.6.187.75.1.1   
        hwDocsQamEISProfileName        OBJECT-TYPE
            SYNTAX       OCTET STRING (SIZE (1..31))
            MAX-ACCESS   not-accessible
            STATUS       current
            DESCRIPTION
              "Indicates the name of the EIS profile table.
              "
            ::= { hwDocsQamEISProfileEntry 1 }
      
        -- 1.3.6.1.4.1.2011.6.187.75.1.2
        hwDocsQamEISProfileTcpPort        OBJECT-TYPE
            SYNTAX      InetPortNumber
            MAX-ACCESS  read-create
            STATUS      current
            DESCRIPTION
                "Indicates the tcp port value. The default value is 0.
                 If the node value is set to 0, the TCP port of the EIS profile will be deleted.
                "
            ::= { hwDocsQamEISProfileEntry 2 }
          
        -- 1.3.6.1.4.1.2011.6.187.75.1.3
        hwDocsQamEISProfileCPDuration        OBJECT-TYPE
            SYNTAX      Unsigned32 (10..3600)
            UNITS       "second"
            MAX-ACCESS  read-create
            STATUS      current
            DESCRIPTION
                "Indicates the Scrambling duration. The default value is 10.
                "
            DEFVAL { 10 }
            ::= { hwDocsQamEISProfileEntry 3 }
      
        -- 1.3.6.1.4.1.2011.6.187.75.1.4
        hwDocsQamEISProfileChannelTestInterval        OBJECT-TYPE
            SYNTAX      Unsigned32 (10..300)
            UNITS       "second"
            MAX-ACCESS  read-create
            STATUS      current
            DESCRIPTION
                "Indicates the channel test interval. The default value is 30.
                "
            DEFVAL { 30 }
            ::= { hwDocsQamEISProfileEntry 4 }
                        
        -- 1.3.6.1.4.1.2011.6.187.75.1.5
        hwDocsQamEISProfileChannelTestTimeout        OBJECT-TYPE
            SYNTAX      Unsigned32 (5..60)
            UNITS       "second"
            MAX-ACCESS  read-create
            STATUS      current
            DESCRIPTION
                "Indicates the channel test timeout. The default value is 10.
                "
            DEFVAL { 10 }
            ::= { hwDocsQamEISProfileEntry 5 }
                        
        -- 1.3.6.1.4.1.2011.6.187.75.1.6
        hwDocsQamEISProfileDSCP        OBJECT-TYPE
            SYNTAX      Integer32 (0..63)
            MAX-ACCESS  read-create
            STATUS      current
            DESCRIPTION
                "Indicates the dscp value. The default value is 0.
                "
            DEFVAL { 0 }
            ::= { hwDocsQamEISProfileEntry 6 }

        -- 1.3.6.1.4.1.2011.6.187.75.1.7
        hwDocsQamEISProfileProtocol        OBJECT-TYPE
            SYNTAX      INTEGER
                  {
                  opencas(1),
                  etsi(2)
                  }
            MAX-ACCESS  read-create
            STATUS      current
            DESCRIPTION
                "Indicates the protocol standard for EIS. The default value is 1.
                 Options: 
                 1. opencas(1) - The protocol standard is OpenCAS.
                 2. etsi(2)    - The protocol standard is ETSI.
                "
            DEFVAL { opencas }
            ::= { hwDocsQamEISProfileEntry 7 }
      
        -- 1.3.6.1.4.1.2011.6.187.75.1.255 
        hwDocsQamEISProfileRowStatus        OBJECT-TYPE
            SYNTAX       RowStatus
            MAX-ACCESS   read-create
            STATUS       current
            DESCRIPTION
                "Row status, used to query, create, modify, and delete a EIS profile table. 
                 It supports the active(1), createAndGo(4), and destroy(6) operations.
                 During query, the value of this leaf is always active(1).
                 During deletion, specify the value of this leaf to destroy(6).
                 During creation, specify the value of this leaf to createAndGo(4).
                 To modify the parameters of a EIS profile table, this leaf need not be issued together.
                 Options:
                 1. active(1)      -indicates the query operation
                 2. createAndGo(4) -indicates the creating operation
                 3. destroy(6)     -indicates the deleting operation
                "
            ::= { hwDocsQamEISProfileEntry 255 }
                                                
        -- 1.3.6.1.4.1.2011.6.187.76
        hwDocsQamECMGTable    OBJECT-TYPE
            SYNTAX          SEQUENCE OF HwDocsQamECMGEntry
            MAX-ACCESS      not-accessible
            STATUS          current
            DESCRIPTION
                "Indicates the EQAM ECMG table used for SCS.
                 The index of this table is hwDocsQamECMGName.
                "
            ::= { hwEqamAn 76 }
    
        -- 1.3.6.1.4.1.2011.6.187.76.1
        hwDocsQamECMGEntry    OBJECT-TYPE
            SYNTAX          HwDocsQamECMGEntry
            MAX-ACCESS      not-accessible
            STATUS          current
            DESCRIPTION
                "Indicates the EQAM ECMG table used for SCS.
                 The index of this entry is hwDocsQamECMGName.
                "
            INDEX   
                { 
                hwDocsQamECMGName
                }
            ::= { hwDocsQamECMGTable  1 }
        
        HwDocsQamECMGEntry ::=
            SEQUENCE 
                { 
                hwDocsQamECMGName
                  OCTET STRING,
                hwDocsQamECMGCASystemId
                  Unsigned32,
                hwDocsQamECMGCASubSystemId
                  Unsigned32,
                hwDocsQamECMGProtocolVersion
                  INTEGER,
                                hwDocsQamECMGChannelSetupTimeout
                                  Unsigned32,
                                hwDocsQamECMGChannelTestInterval
                                  Unsigned32,
                                hwDocsQamECMGChannelTestTimeout
                                  Unsigned32,
				hwDocsQamECMGDSCP
				  Integer32,
                hwDocsQamECMGRowStatus
                  RowStatus   
                }
        
        -- 1.3.6.1.4.1.2011.6.187.76.1.1   
        hwDocsQamECMGName        OBJECT-TYPE
            SYNTAX       OCTET STRING (SIZE (1..31))
            MAX-ACCESS   not-accessible
            STATUS       current
            DESCRIPTION
              "Indicates the name of the ECMG table.
              "
            ::= { hwDocsQamECMGEntry 1 }
      
        -- 1.3.6.1.4.1.2011.6.187.76.1.2
        hwDocsQamECMGCASystemId        OBJECT-TYPE
            SYNTAX      Unsigned32 (0..65535 | 4294967295)
            MAX-ACCESS  read-create
            STATUS      current
            DESCRIPTION
                "Indicates the super conditional access system ID. The default value is 4294967295.
                "
            DEFVAL { 4294967295 }
            ::= { hwDocsQamECMGEntry 2 }
          
        -- 1.3.6.1.4.1.2011.6.187.76.1.3
        hwDocsQamECMGCASubSystemId        OBJECT-TYPE
            SYNTAX      Unsigned32 (0..65535 | 4294967295)
            MAX-ACCESS  read-create
            STATUS      current
            DESCRIPTION
                "Indicates the super conditional access subsystem ID. The default value is 4294967295.
                 If both hwDocsQamECMGCASystemId and hwDocsQamECMGCASubSystemId are set to 4294967295, the super conditional access system ID will be deleted.
                "
            DEFVAL { 4294967295 }
            ::= { hwDocsQamECMGEntry 3 }
      
        -- 1.3.6.1.4.1.2011.6.187.76.1.4
        hwDocsQamECMGProtocolVersion        OBJECT-TYPE
            SYNTAX      INTEGER
                                {
                  ver2(1),
                  ver3(2)
                }
            MAX-ACCESS  read-create
            STATUS      current
            DESCRIPTION
                "Indicates the protocol version. The default value is ver2.
                                 Options: 
                 1. ver2(1) - The protocol version is ver2.
                 2. ver3(2) - The protocol version is ver3.
                "
            DEFVAL { ver2 }
            ::= { hwDocsQamECMGEntry 4 }
                                                
        -- 1.3.6.1.4.1.2011.6.187.76.1.5
        hwDocsQamECMGChannelSetupTimeout        OBJECT-TYPE
            SYNTAX      Unsigned32 (5..60)
            UNITS       "second"
            MAX-ACCESS  read-create
            STATUS      current
            DESCRIPTION
                "Indicates the channel test setup timeout. The default value is 10.
                "
            DEFVAL { 10 }
            ::= { hwDocsQamECMGEntry 5 }
                        
        -- 1.3.6.1.4.1.2011.6.187.76.1.6
        hwDocsQamECMGChannelTestInterval        OBJECT-TYPE
            SYNTAX      Unsigned32 (10..300)
                        UNITS       "second"
            MAX-ACCESS  read-create
            STATUS      current
            DESCRIPTION
                "Indicates the channel test interval. The default value is 30.
                "
            DEFVAL { 30 }
            ::= { hwDocsQamECMGEntry 6 }
                        
                -- 1.3.6.1.4.1.2011.6.187.76.1.7
        hwDocsQamECMGChannelTestTimeout        OBJECT-TYPE
            SYNTAX      Unsigned32 (5..60)
            UNITS       "second"
            MAX-ACCESS  read-create
            STATUS      current
            DESCRIPTION
                "Indicates the channel test timeout. The default value is 10.
                "
            DEFVAL { 10 }
            ::= { hwDocsQamECMGEntry 7 }
			
		-- 1.3.6.1.4.1.2011.6.187.76.1.8
        hwDocsQamECMGDSCP        OBJECT-TYPE
            SYNTAX      Integer32 (0..63)
            MAX-ACCESS  read-create
            STATUS      current
            DESCRIPTION
                "Indicates the ECMG dscp value. The default value is 0.
                "
            DEFVAL { 0 }
            ::= { hwDocsQamECMGEntry 8 }
      
        -- 1.3.6.1.4.1.2011.6.187.76.1.255 
        hwDocsQamECMGRowStatus        OBJECT-TYPE
            SYNTAX       RowStatus
            MAX-ACCESS   read-create
            STATUS       current
            DESCRIPTION
                "Row status, used to query, create, modify, and delete a ECMG table. 
                 It supports the active(1), createAndGo(4), and destroy(6) operations.
                 During query, the value of this leaf is always active(1).
                 During deletion, specify the value of this leaf to destroy(6).
                 During creation, specify the value of this leaf to createAndGo(4).
                 To modify the parameters of a ECMG table, this leaf need not be issued together.
                 Options:
                 1. active(1)      -indicates the query operation
                 2. createAndGo(4) -indicates the creating operation
                 3. destroy(6)     -indicates the deleting operation
                "
            ::= { hwDocsQamECMGEntry 255 }
                                                                        
        -- 1.3.6.1.4.1.2011.6.187.77
        hwDocsQamECMGChannelTable    OBJECT-TYPE
            SYNTAX          SEQUENCE OF HwDocsQamECMGChannelEntry
            MAX-ACCESS      not-accessible
            STATUS          current
            DESCRIPTION
                "Indicates the EQAM ECMG Channel table.
                 The index of this table is hwDocsQamECMGName and hwDocsQamECMGChannelID.
                "
            ::= { hwEqamAn 77 }
    
        -- 1.3.6.1.4.1.2011.6.187.77.1
        hwDocsQamECMGChannelEntry    OBJECT-TYPE
            SYNTAX          HwDocsQamECMGChannelEntry
            MAX-ACCESS      not-accessible
            STATUS          current
            DESCRIPTION
                "Indicates the EQAM ECMG Channel table.
                 The index of this entry is hwDocsQamECMGName and hwDocsQamECMGChannelID.
                "
            INDEX   
                { 
                hwDocsQamECMGName,
                                hwDocsQamECMGChannelID
                }
            ::= { hwDocsQamECMGChannelTable  1 }
        
        HwDocsQamECMGChannelEntry ::=
            SEQUENCE 
                { 
                hwDocsQamECMGChannelID
                  Unsigned32,
                hwDocsQamECMGChannelIpAddressType
                  InetAddressType,
                hwDocsQamECMGChannelIpAddress
                  InetAddress,
				hwDocsQamECMGTcpPort
				  InetPortNumber,
				hwDocsQamECMGChannelPriority
				  Unsigned32,
                hwDocsQamECMGChannelRowStatus
                  RowStatus   
                }
              
        -- 1.3.6.1.4.1.2011.6.187.77.1.1
        hwDocsQamECMGChannelID        OBJECT-TYPE
            SYNTAX      Unsigned32 (0..65535)
            MAX-ACCESS  not-accessible
            STATUS      current
            DESCRIPTION
                "Indicates the ECMG Channel ID.
                "
            ::= { hwDocsQamECMGChannelEntry 1 }
          
        -- 1.3.6.1.4.1.2011.6.187.77.1.2
        hwDocsQamECMGChannelIpAddressType        OBJECT-TYPE
            SYNTAX      InetAddressType
            MAX-ACCESS  read-create
            STATUS      current
            DESCRIPTION
                "Indicates the ECMG channel ip address type. The default value is ipv4.
                "
            ::= { hwDocsQamECMGChannelEntry 2 }
      
        -- 1.3.6.1.4.1.2011.6.187.77.1.3
        hwDocsQamECMGChannelIpAddress        OBJECT-TYPE
            SYNTAX      InetAddress
            MAX-ACCESS  read-create
            STATUS      current
            DESCRIPTION
                "Indicates the ECMG channel IpAddress. The default value is 0.0.0.0 .
                "
            DEFVAL { 0 }
            ::= { hwDocsQamECMGChannelEntry 3 }
                                                
        -- 1.3.6.1.4.1.2011.6.187.77.1.4
        hwDocsQamECMGTcpPort        OBJECT-TYPE
            SYNTAX      InetPortNumber
            MAX-ACCESS  read-create
            STATUS      current
            DESCRIPTION
                "Indicates the ECMG tcp port. The default value is 0.
                 If the value is set to 0, the ECMG TCP port will be deleted.
                "
            ::= { hwDocsQamECMGChannelEntry 4 }
                        
        -- 1.3.6.1.4.1.2011.6.187.77.1.5
        hwDocsQamECMGChannelPriority        OBJECT-TYPE
            SYNTAX      Unsigned32 (0..127)
            MAX-ACCESS  read-create
            STATUS      current
            DESCRIPTION
                "Indicates the ECMG channel priority . The default value is 0.
                "
            DEFVAL { 0 }
            ::= { hwDocsQamECMGChannelEntry 5 }
      
        -- 1.3.6.1.4.1.2011.6.187.77.1.255 
        hwDocsQamECMGChannelRowStatus        OBJECT-TYPE
            SYNTAX       RowStatus
            MAX-ACCESS   read-create
            STATUS       current
            DESCRIPTION
                "Row status, used to query, create, modify, and delete a ECMG channel table. 
                 It supports the active(1), createAndGo(4), and destroy(6) operations.
                 During query, the value of this leaf is always active(1).
                 During deletion, specify the value of this leaf to destroy(6).
                 During creation, specify the value of this leaf to createAndGo(4).
                 To modify the parameters of a ECMG channel table, this leaf need not be issued together.
                 Options:
                 1. active(1)      -indicates the query operation
                 2. createAndGo(4) -indicates the creating operation
                 3. destroy(6)     -indicates the deleting operation
                "
            ::= { hwDocsQamECMGChannelEntry 255 }
                                                                        
        -- 1.3.6.1.4.1.2011.6.187.78
        hwDocsQamSCSTable    OBJECT-TYPE
            SYNTAX          SEQUENCE OF HwDocsQamSCSEntry
            MAX-ACCESS      not-accessible
            STATUS          current
            DESCRIPTION
                "Indicates the EQAM SCS table.
                 The index of this table is hwDocsQamSCSName.
                "
            ::= { hwEqamAn 78 }
    
        -- 1.3.6.1.4.1.2011.6.187.78.1
        hwDocsQamSCSEntry    OBJECT-TYPE
            SYNTAX          HwDocsQamSCSEntry
            MAX-ACCESS      not-accessible
            STATUS          current
            DESCRIPTION
                "Indicates the EQAM SCS table.
                 The index of this entry is hwDocsQamSCSName.
                "
            INDEX   
                { 
                hwDocsQamSCSName
                }
            ::= { hwDocsQamSCSTable  1 }
        
        HwDocsQamSCSEntry ::=
            SEQUENCE 
                { 
                hwDocsQamSCSName
                  OCTET STRING,
                hwDocsQamSCSScramblingAlgorithm 
                  INTEGER,
                hwDocsQamSCSEISProfileName
                  OCTET STRING,
                hwDocsQamSCSEISSourceInterfaceType
                  INTEGER,
                hwDocsQamSCSEISSourceInterfaceNumber
                  Unsigned32,
                hwDocsQamSCSRowStatus
                  RowStatus   
                }
        
        -- 1.3.6.1.4.1.2011.6.187.78.1.1   
        hwDocsQamSCSName        OBJECT-TYPE
            SYNTAX       OCTET STRING (SIZE (1..31))
            MAX-ACCESS   not-accessible
            STATUS       current
            DESCRIPTION
              "Indicates the name of the SCS table.
              "
            ::= { hwDocsQamSCSEntry 1 }
      
        -- 1.3.6.1.4.1.2011.6.187.78.1.2
        hwDocsQamSCSScramblingAlgorithm        OBJECT-TYPE
            SYNTAX      INTEGER
                                {
                  csav1(1),
                  csav2(2)
                }
            MAX-ACCESS  read-create
            STATUS      current
            DESCRIPTION
                "Indicates the super conditional access system ID. The default value is csav2.
                                Options: 
                 1. csav1(1) - The protocol version is ver2.
                 2. csav2(2) - The protocol version is ver3.
                "
            DEFVAL { csav2 }
            ::= { hwDocsQamSCSEntry 2 }
          
        -- 1.3.6.1.4.1.2011.6.187.78.1.3
        hwDocsQamSCSEISProfileName        OBJECT-TYPE
            SYNTAX       OCTET STRING (SIZE (0..31))
            MAX-ACCESS   read-create
            STATUS       current
            DESCRIPTION
              "Indicates the name of the EIS profile table.
               If the node value is set to a null string, the bound EIS profile will be deleted.
              "
            ::= { hwDocsQamSCSEntry 3 }
      
        -- 1.3.6.1.4.1.2011.6.187.78.1.4
        hwDocsQamSCSEISSourceInterfaceType        OBJECT-TYPE
            SYNTAX      INTEGER
                                {
                  loopback(1),
                  vlanif(2),
                  invalid(255)
                }
            MAX-ACCESS  read-create
            STATUS      current
            DESCRIPTION
                "Indicates the EIS source interface type. The default value is invalid.
                                 Options: 
                 1. loopback(1)  - The EIS source interface type is loopback.
                 2. vlanif(2)    - The EIS source interface type is vlanif.
                 3. invalid(255) - The EIS source interface type is not configured.
                "
            DEFVAL { invalid }
            ::= { hwDocsQamSCSEntry 4 }
                                                
        -- 1.3.6.1.4.1.2011.6.187.78.1.5
        hwDocsQamSCSEISSourceInterfaceNumber        OBJECT-TYPE
            SYNTAX      Unsigned32 (0..4294967295)
            MAX-ACCESS  read-create
            STATUS      current
            DESCRIPTION
                "Indicates the EIS source interface number. The default value is 4294967295.
                "
            DEFVAL { 4294967295 }
            ::= { hwDocsQamSCSEntry 5 }
                             
        -- 1.3.6.1.4.1.2011.6.187.78.1.255 
        hwDocsQamSCSRowStatus        OBJECT-TYPE
            SYNTAX       RowStatus
            MAX-ACCESS   read-create
            STATUS       current
            DESCRIPTION
                "Row status, used to query, create, modify, and delete a SCS table. 
                 It supports the active(1), createAndGo(4), and destroy(6) operations.
                 During query, the value of this leaf is always active(1).
                 During deletion, specify the value of this leaf to destroy(6).
                 During creation, specify the value of this leaf to createAndGo(4).
                 To modify the parameters of a SCS table, this leaf need not be issued together.
                 Options:
                 1. active(1)      -indicates the query operation
                 2. createAndGo(4) -indicates the creating operation
                 3. destroy(6)     -indicates the deleting operation
                "
            ::= { hwDocsQamSCSEntry 255 }
                                                
        -- 1.3.6.1.4.1.2011.6.187.79
        hwDocsQamSCSECMGTable    OBJECT-TYPE
            SYNTAX          SEQUENCE OF HwDocsQamSCSECMGEntry
            MAX-ACCESS      not-accessible
            STATUS          current
            DESCRIPTION
                "Indicates the EQAM SCSECMG table.
                 The index of this table is hwDocsQamSCSName and hwDocsQamECMGName.
                "
            ::= { hwEqamAn 79 }
    
        -- 1.3.6.1.4.1.2011.6.187.79.1
        hwDocsQamSCSECMGEntry    OBJECT-TYPE
            SYNTAX          HwDocsQamSCSECMGEntry
            MAX-ACCESS      not-accessible
            STATUS          current
            DESCRIPTION
                "Indicates the EQAM SCSECMG table.
                 The index of this entry is hwDocsQamSCSName and hwDocsQamECMGName.
                "
            INDEX   
                { 
                hwDocsQamSCSName,
                                hwDocsQamECMGName
                }
            ::= { hwDocsQamSCSECMGTable  1 }
        
        HwDocsQamSCSECMGEntry ::=
            SEQUENCE 
                { 
                hwDocsQamSCSECMGSourceInterfaceType
                  INTEGER,
                                hwDocsQamSCSECMGSourceInterfaceNumber
                                  Unsigned32,
                hwDocsQamSCSECMGRowStatus
                  RowStatus   
                }
              
        -- 1.3.6.1.4.1.2011.6.187.79.1.1
        hwDocsQamSCSECMGSourceInterfaceType        OBJECT-TYPE
            SYNTAX      INTEGER
                                {
                  loopback(1),
                  vlanif(2),
                  invalid(255)
                }
            MAX-ACCESS  read-create
            STATUS      current
            DESCRIPTION
                "Indicates the ECMG source interface type. The default value is invalid.
                                 Options: 
                 1. loopback(1)  - The ECMG source interface type is loopback.
                 2. vlanif(2)    - The ECMG source interface type is vlanif.
                 3. invalid(255) - The ECMG source interface type is not configured.
                "
            DEFVAL { invalid }
            ::= { hwDocsQamSCSECMGEntry 1 }
                                                
        -- 1.3.6.1.4.1.2011.6.187.79.1.2
        hwDocsQamSCSECMGSourceInterfaceNumber        OBJECT-TYPE
            SYNTAX      Unsigned32 (0..4294967295)
            MAX-ACCESS  read-create
            STATUS      current
            DESCRIPTION
                "Indicates the ECMG source interface number. The default value is 4294967295.
                "
            DEFVAL { 4294967295 }
            ::= { hwDocsQamSCSECMGEntry 2 }
                             
        -- 1.3.6.1.4.1.2011.6.187.79.1.255 
        hwDocsQamSCSECMGRowStatus        OBJECT-TYPE
            SYNTAX       RowStatus
            MAX-ACCESS   read-create
            STATUS       current
            DESCRIPTION
                "Row status, used to query, create, modify, and delete a SCSECMG table. 
                 It supports the active(1), createAndGo(4), and destroy(6) operations.
                 During query, the value of this leaf is always active(1).
                 During deletion, specify the value of this leaf to destroy(6).
                 During creation, specify the value of this leaf to createAndGo(4).
                 To modify the parameters of a SCSECMG table, this leaf need not be issued together.
                 Options:
                 1. active(1)      -indicates the query operation
                 2. createAndGo(4) -indicates the creating operation
                 3. destroy(6)     -indicates the deleting operation
                "
            ::= { hwDocsQamSCSECMGEntry 255 }
              
        -- 1.3.6.1.4.1.2011.6.187.80
        hwDocsQamScsEisScgTable    OBJECT-TYPE
            SYNTAX          SEQUENCE OF HwDocsQamScsEisScgEntry
            MAX-ACCESS      not-accessible
            STATUS          current
            DESCRIPTION
                "Indicates the EQAM SCG table used for SCS and EIS.
                 The index of this table is hwDocsQamSCSName and hwDocsQamScsEisScgID.
                "
            ::= { hwEqamAn 80 }
    
        -- 1.3.6.1.4.1.2011.6.187.80.1
        hwDocsQamScsEisScgEntry    OBJECT-TYPE
            SYNTAX          HwDocsQamScsEisScgEntry
            MAX-ACCESS      not-accessible
            STATUS          current
            DESCRIPTION
                "Indicates the EQAM SCG table used for SCS and EIS.
                 The index of this entry is hwDocsQamSCSName and hwDocsQamScsEisScgID.
                "
            INDEX   
                { 
                hwDocsQamSCSName,
                hwDocsQamScsEisScgID
                }
            ::= { hwDocsQamScsEisScgTable  1 }
                
        HwDocsQamScsEisScgEntry ::=
            SEQUENCE 
                { 
                hwDocsQamScsEisScgID
                  Unsigned32,
                hwDocsQamScsEisScgTransportStreamID
                  Unsigned32,
                hwDocsQamScsEisScgOriginalNetworkID
                  Unsigned32,
                hwDocsQamScsEisScgReferenceID
                  Unsigned32,
                hwDocsQamScsEisScgActivationTime
                  DateAndTime,
                hwDocsQamScsEisScgRecommendedCPDuration
                  Unsigned32,
                hwDocsQamScsEisScgServiceList
                  OCTET STRING
                }

        -- 1.3.6.1.4.1.2011.6.187.80.1.1
        hwDocsQamScsEisScgID        OBJECT-TYPE
            SYNTAX      Unsigned32(0..4294967295)
            MAX-ACCESS  not-accessible
            STATUS      current
            DESCRIPTION
                "Indicates the index of a SCG mapping table.
                "
            ::= { hwDocsQamScsEisScgEntry 1 }
          
        -- 1.3.6.1.4.1.2011.6.187.80.1.2
        hwDocsQamScsEisScgTransportStreamID        OBJECT-TYPE
            SYNTAX      Unsigned32 (0..4294967295)
            MAX-ACCESS  read-only
            STATUS      current
            DESCRIPTION
                "Indicates the Transport stream ID of SCG. The default value is 4294967295.
                "
            DEFVAL { 4294967295 }
            ::= { hwDocsQamScsEisScgEntry 2 }
      
        -- 1.3.6.1.4.1.2011.6.187.80.1.3
        hwDocsQamScsEisScgOriginalNetworkID        OBJECT-TYPE
            SYNTAX      Unsigned32 (0..4294967295)
            MAX-ACCESS  read-only
            STATUS      current
            DESCRIPTION
                "Indicates the original network ID of SCG. The default value is 4294967295.
                 If the queried node value is 4294967295, the server has not issued a valid original network ID of the SCG.
                "
            DEFVAL { 4294967295 }
            ::= { hwDocsQamScsEisScgEntry 3 }
      
        -- 1.3.6.1.4.1.2011.6.187.80.1.4
        hwDocsQamScsEisScgReferenceID        OBJECT-TYPE
            SYNTAX      Unsigned32 (0..4294967295)
            MAX-ACCESS  read-only
            STATUS      current
            DESCRIPTION
                "Indicates the reference ID of SCG. The default value is 4294967295.
                 If the queried node value is 4294967295, the server has not issued a valid reference ID of the SCG.
                "
            DEFVAL { 4294967295 }
            ::= { hwDocsQamScsEisScgEntry 4 }
      
        -- 1.3.6.1.4.1.2011.6.187.80.1.5
        hwDocsQamScsEisScgActivationTime        OBJECT-TYPE
            SYNTAX      DateAndTime
            MAX-ACCESS  read-only
            STATUS      current
            DESCRIPTION
                "Indicates the time on which SCG actived.
                The default value is 1900-01-01 00:00:00, which indicates that the SCG issued by the EIS takes effect immediately.
                "
            ::= { hwDocsQamScsEisScgEntry 5 }
      
        -- 1.3.6.1.4.1.2011.6.187.80.1.6
        hwDocsQamScsEisScgRecommendedCPDuration        OBJECT-TYPE
            SYNTAX      Unsigned32 (0..4294967295)
            UNITS       "milli-seconds"
            MAX-ACCESS  read-only
            STATUS      current
            DESCRIPTION
                "Indicates the cp duration of SCG. The default value is 4294967295 ms.
                 If the queried node value is 4294967295, the server has not issued a valid CP duration of the SCG.
                "
            DEFVAL { 4294967295 }
            ::= { hwDocsQamScsEisScgEntry 6 }
      
        -- 1.3.6.1.4.1.2011.6.187.80.1.7
        hwDocsQamScsEisScgServiceList        OBJECT-TYPE
            SYNTAX      OCTET STRING (SIZE (0..128))
            MAX-ACCESS  read-only
            STATUS      current
            DESCRIPTION
                "Indicates the service list of SCG. The default value is 0.
                "
            ::= { hwDocsQamScsEisScgEntry 7 }
      
        -- 1.3.6.1.4.1.2011.6.187.81
        hwDocsQamScsEisTable    OBJECT-TYPE
            SYNTAX          SEQUENCE OF HwDocsQamScsEisEntry
            MAX-ACCESS      not-accessible
            STATUS          current
            DESCRIPTION
                "Indicates the EQAM EIS table used for SCS.
                 The index of this table is hwDocsQamSCSName and hwDocsQamScsEisChannelID.
                "
            ::= { hwEqamAn 81 }
    
        -- 1.3.6.1.4.1.2011.6.187.81.1
        hwDocsQamScsEisEntry    OBJECT-TYPE
            SYNTAX          HwDocsQamScsEisEntry
            MAX-ACCESS      not-accessible
            STATUS          current
            DESCRIPTION
                "Indicates the EQAM EIS table used for SCS.
                 The index of this entry is hwDocsQamSCSName and hwDocsQamScsEisChannelID.
                "
            INDEX   
                { 
                hwDocsQamSCSName,
                hwDocsQamScsEisChannelID
                }
            ::= { hwDocsQamScsEisTable  1 }
                
        HwDocsQamScsEisEntry ::=
            SEQUENCE 
                { 
                hwDocsQamScsEisChannelID
                  Unsigned32,
                hwDocsQamScsEisIpAddressType
                  InetAddressType,
                hwDocsQamScsEisPeerIpAddress
                  InetAddress,
                hwDocsQamScsEisPeerTcpPort
                  InetPortNumber,
                hwDocsQamScsEisLocalIpAddress
                  InetAddress,
                hwDocsQamScsEisLocalTcpPort
                  InetPortNumber,
                hwDocsQamScsEisState
                  INTEGER,
                hwDocsQamScsEisProtocolVersion
                  INTEGER,
                hwDocsQamScsEisServiceFlag
                  TruthValue,
                hwDocsQamScsEisComponentFlag
                  TruthValue,
                hwDocsQamScsEisMaxSCG
                  Unsigned32,
                hwDocsQamScsEisCPDurationFlag
                  TruthValue,
                hwDocsQamScsEisErroStatusCode
                  Unsigned32,
                hwDocsQamScsEisStatisticsReset
                  INTEGER,
                hwDocsQamScsEisStatisticsReceivedTotalMessages
                  Counter64,
                hwDocsQamScsEisStatisticsReceivedChannelSetupMessages
                  Counter64,
                hwDocsQamScsEisStatisticsReceivedChannelTestMessages
                  Counter64,
                hwDocsQamScsEisStatisticsReceivedChannelStatusMessages
                  Counter64,
                hwDocsQamScsEisStatisticsReceivedChannelCloseMessages
                  Counter64,
                hwDocsQamScsEisStatisticsReceivedChannelResetMessages
                  Counter64,
                hwDocsQamScsEisStatisticsReceivedChannelErrorMessages
                  Counter64,
                hwDocsQamScsEisStatisticsReceivedSCGProvisionMessages
                  Counter64,
                hwDocsQamScsEisStatisticsReceivedSCGTestMessages
                  Counter64,
                hwDocsQamScsEisStatisticsReceivedSCGListRequestMessages
                  Counter64,
                hwDocsQamScsEisStatisticsSentTotalMessages
                  Counter64,
                hwDocsQamScsEisStatisticsSentChannelTestMessages
                  Counter64,
                hwDocsQamScsEisStatisticsSentChannelStatusMessages
                  Counter64,
                hwDocsQamScsEisStatisticsSentChannelErrorMessages
                  Counter64,
                hwDocsQamScsEisStatisticsSentSCGStatusMessages
                  Counter64,
                hwDocsQamScsEisStatisticsSentSCGListResponseMessages
                  Counter64,
                hwDocsQamScsEisStatisticsSentSCGErrorMessages
                  Counter64,
                hwDocsQamScsEisNominalCPDuration
                  Unsigned32,
                hwDocsQamScsEisMinAcDelayStart
                  Integer32,
                hwDocsQamScsEisCpDurationConfigMode
                  Unsigned32
                }

        -- 1.3.6.1.4.1.2011.6.187.81.1.1
        hwDocsQamScsEisChannelID        OBJECT-TYPE
            SYNTAX      Unsigned32(0..4294967295)
            MAX-ACCESS  not-accessible
            STATUS      current
            DESCRIPTION
                "Indicates the channel ID for EIS.
                "
            ::= { hwDocsQamScsEisEntry 1 }
          
        -- 1.3.6.1.4.1.2011.6.187.81.1.2
        hwDocsQamScsEisIpAddressType        OBJECT-TYPE
            SYNTAX      InetAddressType
            MAX-ACCESS  read-only
            STATUS      current
            DESCRIPTION
                "This attribute identifies the IP address type of the EIS. The default value is ipv4.
                "
            ::= { hwDocsQamScsEisEntry 2 }
      
        -- 1.3.6.1.4.1.2011.6.187.81.1.3
        hwDocsQamScsEisPeerIpAddress        OBJECT-TYPE
            SYNTAX      InetAddress
            MAX-ACCESS  read-only
            STATUS      current
            DESCRIPTION
                "This attribute identifies the peer IP address of the EIS. The default value is 0.0.0.0.
                "
            ::= { hwDocsQamScsEisEntry 3 }
      
        -- 1.3.6.1.4.1.2011.6.187.81.1.4
        hwDocsQamScsEisPeerTcpPort        OBJECT-TYPE
            SYNTAX      InetPortNumber
            MAX-ACCESS  read-only
            STATUS      current
            DESCRIPTION
                "Indicates the peer tcp port of EIS. The default value is 0.
                "
            DEFVAL { 0 }
            ::= { hwDocsQamScsEisEntry 4 }
      
        -- 1.3.6.1.4.1.2011.6.187.81.1.5
        hwDocsQamScsEisLocalIpAddress        OBJECT-TYPE
            SYNTAX      InetAddress
            MAX-ACCESS  read-only
            STATUS      current
            DESCRIPTION
                "This attribute identifies the IP address type of the SCS EIS local.
                "
            ::= { hwDocsQamScsEisEntry 5 }
      
        -- 1.3.6.1.4.1.2011.6.187.81.1.6
        hwDocsQamScsEisLocalTcpPort        OBJECT-TYPE
            SYNTAX      InetPortNumber
            MAX-ACCESS  read-only
            STATUS      current
            DESCRIPTION
                "Indicates the local tcpport of EIS. The default value is 0.
                "
            DEFVAL { 0 }
            ::= { hwDocsQamScsEisEntry 6 }
      
        -- 1.3.6.1.4.1.2011.6.187.81.1.7
        hwDocsQamScsEisState        OBJECT-TYPE
            SYNTAX      INTEGER
                  {
                  listening(1),
                  tcpestablished(2),
                  notopen(3),
                  settingup(4),
                  open(5),
                  error(6)
                  }
            MAX-ACCESS  read-only
            STATUS      current
            DESCRIPTION
                "Indicates the status of EIS. The default value is listening(1).
                 Options:
                 1. listening(1)       --listening state
                 2. tcpestablished(2)  --tcpestablished state
                 3. notopen(3)         --notopen state
                 4. settingup(4)       --settingup state
                 5. open(5)            --open state
                 6. error(6)           --error state
                "
            ::= { hwDocsQamScsEisEntry 7 }
      
        -- 1.3.6.1.4.1.2011.6.187.81.1.8
        hwDocsQamScsEisProtocolVersion    OBJECT-TYPE
            SYNTAX      INTEGER
                  {
                  ver3(1),
                  ver4(2),
                  ver2(3),
		          invalid(255)
                  }
            MAX-ACCESS  read-only
            STATUS      current
            DESCRIPTION
                "Indicates the protocol version.	
                 Options:
                 1. ver3(1)       --version 3
                 2. ver4(2)       --version 4
		         3. ver2(3)       --version 2
		         4. invalid(255)  --version invalid
                "
            ::= { hwDocsQamScsEisEntry 8 }

        -- 1.3.6.1.4.1.2011.6.187.81.1.9
        hwDocsQamScsEisServiceFlag        OBJECT-TYPE
            SYNTAX      TruthValue
            MAX-ACCESS  read-only
            STATUS      current
            DESCRIPTION
                "Indicates the service flag of EIS.The default value is true(1).
                "
            ::= { hwDocsQamScsEisEntry 9 }

        -- 1.3.6.1.4.1.2011.6.187.81.1.10
        hwDocsQamScsEisComponentFlag        OBJECT-TYPE
            SYNTAX      TruthValue
            MAX-ACCESS  read-only
            STATUS      current
            DESCRIPTION
                "Indicates the component flag of EIS.The default value is false(2).
                "
            ::= { hwDocsQamScsEisEntry 10 }

        -- 1.3.6.1.4.1.2011.6.187.81.1.11
        hwDocsQamScsEisMaxSCG        OBJECT-TYPE
            SYNTAX      Unsigned32(0..4294967295)
            MAX-ACCESS  read-only
            STATUS      current
            DESCRIPTION
                "Indicates the max count of SCG. The default value is 7500.
                "
			DEFVAL { 7500 }
            ::= { hwDocsQamScsEisEntry 11 }

        -- 1.3.6.1.4.1.2011.6.187.81.1.12
        hwDocsQamScsEisCPDurationFlag        OBJECT-TYPE
            SYNTAX      TruthValue
            MAX-ACCESS  read-only
            STATUS      current
            DESCRIPTION
                "Indicates the CP duration flag. The default value is true(1).
                "
            ::= { hwDocsQamScsEisEntry 12 }

        -- 1.3.6.1.4.1.2011.6.187.81.1.13
        hwDocsQamScsEisErroStatusCode        OBJECT-TYPE
            SYNTAX      Unsigned32(0..4294967295)
            MAX-ACCESS  read-only
            STATUS      current
            DESCRIPTION
                "Indicates the error status code of EIS,please read 'ETSI TS 103 197 V1.5.1,chapter 10.7 Error status' for reference. The default value is 0.
                "
			DEFVAL { 0 }
            ::= { hwDocsQamScsEisEntry 13 }

        -- 1.3.6.1.4.1.2011.6.187.81.1.14
        hwDocsQamScsEisStatisticsReset        OBJECT-TYPE
            SYNTAX      INTEGER
                  {
                  clear(1)
                  }
            MAX-ACCESS  read-write
            STATUS      current
            DESCRIPTION
                "Indicates the reset process of EIS. The default value is clear(1).
                 Options:
                 1. clear(1)       --clear info
                "
            ::= { hwDocsQamScsEisEntry 14 }

        -- 1.3.6.1.4.1.2011.6.187.81.1.15
        hwDocsQamScsEisStatisticsReceivedTotalMessages        OBJECT-TYPE
            SYNTAX      Counter64
            MAX-ACCESS  read-only
            STATUS      current
            DESCRIPTION
                "Indicates the number of received total messages. The default value is 0.
                "
            ::= { hwDocsQamScsEisEntry 15 }

        -- 1.3.6.1.4.1.2011.6.187.81.1.16
        hwDocsQamScsEisStatisticsReceivedChannelSetupMessages        OBJECT-TYPE
            SYNTAX      Counter64
            MAX-ACCESS  read-only
            STATUS      current
            DESCRIPTION
                "Indicates the number of received channel setup messages. The default value is 0.
                "
            ::= { hwDocsQamScsEisEntry 16 }

        -- 1.3.6.1.4.1.2011.6.187.81.1.17
        hwDocsQamScsEisStatisticsReceivedChannelTestMessages        OBJECT-TYPE
            SYNTAX      Counter64
            MAX-ACCESS  read-only
            STATUS      current
            DESCRIPTION
                "Indicates the number of received channel test messages. The default value is 0.
                "
            ::= { hwDocsQamScsEisEntry 17 }

        -- 1.3.6.1.4.1.2011.6.187.81.1.18
        hwDocsQamScsEisStatisticsReceivedChannelStatusMessages        OBJECT-TYPE
            SYNTAX      Counter64
            MAX-ACCESS  read-only
            STATUS      current
            DESCRIPTION
                "Indicates the number of received channel status messages. The default value is 0.
                "
            ::= { hwDocsQamScsEisEntry 18 }

        -- 1.3.6.1.4.1.2011.6.187.81.1.19
        hwDocsQamScsEisStatisticsReceivedChannelCloseMessages        OBJECT-TYPE
            SYNTAX      Counter64
            MAX-ACCESS  read-only
            STATUS      current
            DESCRIPTION
                "Indicates the number of received channel close messages. The default value is 0.
                "
            ::= { hwDocsQamScsEisEntry 19 }

        -- 1.3.6.1.4.1.2011.6.187.81.1.20
        hwDocsQamScsEisStatisticsReceivedChannelResetMessages        OBJECT-TYPE
            SYNTAX      Counter64
            MAX-ACCESS  read-only
            STATUS      current
            DESCRIPTION
                "Indicates the number of received channel reset messages. The default value is 0.
                "
            ::= { hwDocsQamScsEisEntry 20 }

        -- 1.3.6.1.4.1.2011.6.187.81.1.21
        hwDocsQamScsEisStatisticsReceivedChannelErrorMessages        OBJECT-TYPE
            SYNTAX      Counter64
            MAX-ACCESS  read-only
            STATUS      current
            DESCRIPTION
                "Indicates the number of received channel error messages. The default value is 0.
                "
            ::= { hwDocsQamScsEisEntry 21 }

        -- 1.3.6.1.4.1.2011.6.187.81.1.22
        hwDocsQamScsEisStatisticsReceivedSCGProvisionMessages        OBJECT-TYPE
            SYNTAX      Counter64
            MAX-ACCESS  read-only
            STATUS      current
            DESCRIPTION
                "Indicates the number of received SCG provision messages. The default value is 0.
                "
            ::= { hwDocsQamScsEisEntry 22 }

        -- 1.3.6.1.4.1.2011.6.187.81.1.23
        hwDocsQamScsEisStatisticsReceivedSCGTestMessages        OBJECT-TYPE
            SYNTAX      Counter64
            MAX-ACCESS  read-only
            STATUS      current
            DESCRIPTION
                "Indicates the number of received SCG test messages. The default value is 0.
                "
            ::= { hwDocsQamScsEisEntry 23 }

        -- 1.3.6.1.4.1.2011.6.187.81.1.24
        hwDocsQamScsEisStatisticsReceivedSCGListRequestMessages        OBJECT-TYPE
            SYNTAX      Counter64
            MAX-ACCESS  read-only
            STATUS      current
            DESCRIPTION
                "Indicates the number of received SCG list request messages. The default value is 0.
                "
            ::= { hwDocsQamScsEisEntry 24 }

        -- 1.3.6.1.4.1.2011.6.187.81.1.25
        hwDocsQamScsEisStatisticsSentTotalMessages        OBJECT-TYPE
            SYNTAX      Counter64
            MAX-ACCESS  read-only
            STATUS      current
            DESCRIPTION
                "Indicates the number of sent total messages. The default value is 0.
                "
            ::= { hwDocsQamScsEisEntry 25 }

        -- 1.3.6.1.4.1.2011.6.187.81.1.26
        hwDocsQamScsEisStatisticsSentChannelTestMessages        OBJECT-TYPE
            SYNTAX      Counter64
            MAX-ACCESS  read-only
            STATUS      current
            DESCRIPTION
                "Indicates the number of sent channel test messages. The default value is 0.
                "
            ::= { hwDocsQamScsEisEntry 26 }

        -- 1.3.6.1.4.1.2011.6.187.81.1.27
        hwDocsQamScsEisStatisticsSentChannelStatusMessages        OBJECT-TYPE
            SYNTAX      Counter64
            MAX-ACCESS  read-only
            STATUS      current
            DESCRIPTION
                "Indicates the number of sent channel status messages. The default value is 0.
                "
            ::= { hwDocsQamScsEisEntry 27 }

        -- 1.3.6.1.4.1.2011.6.187.81.1.28
        hwDocsQamScsEisStatisticsSentChannelErrorMessages        OBJECT-TYPE
            SYNTAX      Counter64
            MAX-ACCESS  read-only
            STATUS      current
            DESCRIPTION
                "Indicates the number of sent channel error messages. The default value is 0.
                "
            ::= { hwDocsQamScsEisEntry 28 }

        -- 1.3.6.1.4.1.2011.6.187.81.1.29
        hwDocsQamScsEisStatisticsSentSCGStatusMessages        OBJECT-TYPE
            SYNTAX      Counter64
            MAX-ACCESS  read-only
            STATUS      current
            DESCRIPTION
                "Indicates the number of sent SCG status messages. The default value is 0.
                "
            ::= { hwDocsQamScsEisEntry 29 }

        -- 1.3.6.1.4.1.2011.6.187.81.1.30
        hwDocsQamScsEisStatisticsSentSCGListResponseMessages        OBJECT-TYPE
            SYNTAX      Counter64
            MAX-ACCESS  read-only
            STATUS      current
            DESCRIPTION
                "Indicates the number of sent SCG list response messages. The default value is 0.
                "
            ::= { hwDocsQamScsEisEntry 30 }

        -- 1.3.6.1.4.1.2011.6.187.81.1.31
        hwDocsQamScsEisStatisticsSentSCGErrorMessages        OBJECT-TYPE
            SYNTAX      Counter64
            MAX-ACCESS  read-only
            STATUS      current
            DESCRIPTION
                "Indicates the number of sent SCG error messages. The default value is 0.
                "
            ::= { hwDocsQamScsEisEntry 31 }

        -- 1.3.6.1.4.1.2011.6.187.81.1.32
        hwDocsQamScsEisNominalCPDuration        OBJECT-TYPE
            SYNTAX      Unsigned32(0..4294967295)
            UNITS       "millisecond"
            MAX-ACCESS  read-only
            STATUS      current
            DESCRIPTION
                "Indicates the nominal CP duration of EIS. This node is only valid under the OpenCAS protocol standard. The default value is 4294967295.
                 If the current protocol is the OpenCAS protocol standard and the queried node value is 4294967295, the EIS server has not issued a valid CP duration of the SCG.
				 If the current protocol is the ETSI protocol standard, the queried node is invalid and the value is 4294967295.
                "
            DEFVAL { 4294967295 }
            ::= { hwDocsQamScsEisEntry 32 }

        -- 1.3.6.1.4.1.2011.6.187.81.1.33
        hwDocsQamScsEisMinAcDelayStart        OBJECT-TYPE
            SYNTAX      Integer32(-32768..32767)
            UNITS       "millisecond"
            MAX-ACCESS  read-only
            STATUS      current
            DESCRIPTION
                "Indicates the minimum ac delay start time of EIS. This node is only valid under the OpenCAS protocol standard. The default value is 0.
                 If the current protocol is the OpenCAS protocol standard and the queried node value is 0, the minimum ac delay start time of EIS is 0.
                 If the current protocol is the ETSI protocol standard, the queried node is invalid and the value is 0.
                "
            DEFVAL { 0 }
            ::= { hwDocsQamScsEisEntry 33 }

        -- 1.3.6.1.4.1.2011.6.187.81.1.34
        hwDocsQamScsEisCpDurationConfigMode        OBJECT-TYPE
            SYNTAX      Unsigned32(0..1)
            MAX-ACCESS  read-only
            STATUS      current
            DESCRIPTION
                "Indicates the CP duration configuration mode of the EIS. This node is only valid under the OpenCAS protocol standard. The default value is 0.
                 If the current protocol is the OpenCAS protocol standard and the queried node value is 0, the CP duration configuration is not supported.
                 If the current protocol is the ETSI protocol standard, the queried node is invalid and the value is 0.
                "
            DEFVAL { 0 }
            ::= { hwDocsQamScsEisEntry 34 }
      
        -- 1.3.6.1.4.1.2011.6.187.82
        hwDocsQamScsEisScgEcmTable    OBJECT-TYPE
            SYNTAX          SEQUENCE OF HwDocsQamScsEisScgEcmEntry
            MAX-ACCESS      not-accessible
            STATUS          current
            DESCRIPTION
                "Indicates the EQAM scs eis scg ecm table used.
                 The index of this table is hwDocsQamSCSName, hwDocsQamScsEisScgID and hwDocsQamScsEisScgEcmGroupIndex.
                "
            ::= { hwEqamAn 82 }
    
        -- 1.3.6.1.4.1.2011.6.187.82.1
        hwDocsQamScsEisScgEcmEntry    OBJECT-TYPE
            SYNTAX          HwDocsQamScsEisScgEcmEntry
            MAX-ACCESS      not-accessible
            STATUS          current
            DESCRIPTION
                "Indicates the EQAM scs eis scg ecm table used.
                 The index of this entry is hwDocsQamSCSName, hwDocsQamScsEisScgID and hwDocsQamScsEisScgEcmGroupIndex.
                "
            INDEX   
                { 
                hwDocsQamSCSName,
                hwDocsQamScsEisScgID,
                hwDocsQamScsEisScgEcmGroupIndex
                }
            ::= { hwDocsQamScsEisScgEcmTable  1 }
                
        HwDocsQamScsEisScgEcmEntry ::=
            SEQUENCE 
                { 
                hwDocsQamScsEisScgEcmGroupIndex
                  Unsigned32,
                hwDocsQamScsEisScgEcmSuperCasID
                  Unsigned32,				
                hwDocsQamScsEisScgEcmID
                  Unsigned32,				
                hwDocsQamScsEisScgEcmAccessCriteria
                  OCTET STRING,
                hwDocsQamScsEisScgEcmACTransferMode
                  Unsigned32
                }

        -- 1.3.6.1.4.1.2011.6.187.82.1.1
        hwDocsQamScsEisScgEcmGroupIndex        OBJECT-TYPE
            SYNTAX      Unsigned32(0..4294967295)
            MAX-ACCESS  not-accessible
            STATUS      current
            DESCRIPTION
                "Indicates the index of a ECM group table.
                "
            ::= { hwDocsQamScsEisScgEcmEntry 1 }
          
        -- 1.3.6.1.4.1.2011.6.187.82.1.2
        hwDocsQamScsEisScgEcmSuperCasID        OBJECT-TYPE
            SYNTAX      Unsigned32 (0..4294967295)
            MAX-ACCESS  read-only
            STATUS      current
            DESCRIPTION
                "Indicates the super CAS ID. The default value is 0.
                "
            DEFVAL { 0 }
            ::= { hwDocsQamScsEisScgEcmEntry 2 }
      
        -- 1.3.6.1.4.1.2011.6.187.82.1.3
        hwDocsQamScsEisScgEcmID        OBJECT-TYPE
            SYNTAX      Unsigned32 (0..4294967295)
            MAX-ACCESS  read-only
            STATUS      current
            DESCRIPTION
                "Indicates the ECM ID. The default value is 0.
                "
            DEFVAL { 0 }
            ::= { hwDocsQamScsEisScgEcmEntry 3 }
      
        -- 1.3.6.1.4.1.2011.6.187.82.1.4
        hwDocsQamScsEisScgEcmAccessCriteria        OBJECT-TYPE
            SYNTAX      OCTET STRING (SIZE (0..127))
            MAX-ACCESS  read-only
            STATUS      current
            DESCRIPTION
                "Indicates the access criteria. The default value is 0.
                "
            ::= { hwDocsQamScsEisScgEcmEntry 4 }
      
        -- 1.3.6.1.4.1.2011.6.187.82.1.5
        hwDocsQamScsEisScgEcmACTransferMode        OBJECT-TYPE
            SYNTAX      Unsigned32 (0..1)
            MAX-ACCESS  read-only
            STATUS      current
            DESCRIPTION
                "Indicates the AC transfer mode. The default value is 0.
                 If it equals 0, it indicates that the access_criteria parameter is required in the CW_provision message only when the contents of this parameter change.
		 If it equals 1, it indicates that the ECMG requires the access_criteria parameter be present in each CW_provision message.
                "
            DEFVAL { 0 }
            ::= { hwDocsQamScsEisScgEcmEntry 5 }
      
        -- 1.3.6.1.4.1.2011.6.187.83
        hwDocsQamScsEcmgInfoTable    OBJECT-TYPE
            SYNTAX          SEQUENCE OF HwDocsQamScsEcmgInfoEntry
            MAX-ACCESS      not-accessible
            STATUS          current
            DESCRIPTION
                "Indicates the EQAM SCS ECMG Info table.
                 The index of this table is hwDocsQamSCSName and hwDocsQamScsEcmgChannelID.
                "
            ::= { hwEqamAn 83 }
    
        -- 1.3.6.1.4.1.2011.6.187.83.1
        hwDocsQamScsEcmgInfoEntry    OBJECT-TYPE
            SYNTAX          HwDocsQamScsEcmgInfoEntry
            MAX-ACCESS      not-accessible
            STATUS          current
            DESCRIPTION
                "Indicates the EQAM SCS ECMG Info table.
                 The index of this entry is hwDocsQamSCSName and hwDocsQamScsEcmgChannelID.
                "
            INDEX   
                { 
                hwDocsQamSCSName,
				hwDocsQamScsEcmgChannelID
                }
            ::= { hwDocsQamScsEcmgInfoTable  1 }
        
        HwDocsQamScsEcmgInfoEntry ::=
            SEQUENCE 
                { 
                hwDocsQamScsEcmgChannelID
                  Unsigned32,
                hwDocsQamScsEcmgInfoName
                  OCTET STRING,
				hwDocsQamScsEcmgIpAddressType
				  InetAddressType,
                hwDocsQamScsEcmgPeerIpAddress
                  InetAddress,
				hwDocsQamScsEcmgPeerTcpPort
				  InetPortNumber,
				hwDocsQamScsEcmgLocalIpAddress
				  InetAddress,
				hwDocsQamScsEcmgLocalTcpPort
				  InetPortNumber,
				hwDocsQamScsEcmgState
				  INTEGER,
				hwDocsQamScsEcmgProtocolVersion
				  INTEGER,
				hwDocsQamScsEcmgSuperCasId
				  Unsigned32,
				hwDocsQamScsEcmgSectionTsPacketFlag
				  Unsigned32,
				hwDocsQamScsEcmgACDelayStart
				  Integer32,
				hwDocsQamScsEcmgACDelayStop
				  Integer32,
				hwDocsQamScsEcmgDelayStart
				  Integer32,
				hwDocsQamScsEcmgDelayStop
				  Integer32,
				hwDocsQamScsEcmgTransitionDelayStart
				  Integer32,
				hwDocsQamScsEcmgTransitionDelayStop
				  Integer32,
				hwDocsQamScsEcmgECMRepetitionPeriod
				  Unsigned32,
				hwDocsQamScsEcmgMaxStreams
				  Unsigned32,
				hwDocsQamScsEcmgMinCPDuration
				  Unsigned32,
				hwDocsQamScsEcmgLeadCW
				  Unsigned32,
				hwDocsQamScsEcmgCWperMsg
				  Unsigned32,
				hwDocsQamScsEcmgMaxComputeTime
				  Unsigned32,
				hwDocsQamScsEcmgErroStatusCode
				  Unsigned32,
				hwDocsQamScsEcmgStatisticsReset
				  INTEGER,
				hwDocsQamScsEcmgStatisticsReceivedTotalMessages
				  Counter64,
				hwDocsQamScsEcmgStatisticsReceivedChannelTestMessages
				  Counter64,
				hwDocsQamScsEcmgStatisticsReceivedChannelStatusMessages
				  Counter64,
				hwDocsQamScsEcmgStatisticsReceivedChannelErrorMessages
				  Counter64,
				hwDocsQamScsEcmgStatisticsReceivedStreamTestMessages
				  Counter64,
				hwDocsQamScsEcmgStatisticsReceivedStreamStatusMessages
				  Counter64,
				hwDocsQamScsEcmgStatisticsReceivedStreamCloseResponseMessages
				  Counter64,
				hwDocsQamScsEcmgStatisticsReceivedStreamErrorMessages
				  Counter64,
				hwDocsQamScsEcmgStatisticsReceivedECMResponseMessages
				  Counter64,
				hwDocsQamScsEcmgStatisticsSentTotalMessages
				  Counter64,
				hwDocsQamScsEcmgStatisticsSentChannelSetupMessages
				  Counter64,
				hwDocsQamScsEcmgStatisticsSentChannelTestMessages
				  Counter64,
				hwDocsQamScsEcmgStatisticsSentChannelStatusMessages
				  Counter64,
				hwDocsQamScsEcmgStatisticsSentChannelCloseMessages
				  Counter64,
				hwDocsQamScsEcmgStatisticsSentChannelErrorMessages
				  Counter64,
				hwDocsQamScsEcmgStatisticsSentStreamSetupMessages
				  Counter64,
				hwDocsQamScsEcmgStatisticsSentStreamTestMessages
				  Counter64,
				hwDocsQamScsEcmgStatisticsSentStreamStatusMessages
				  Counter64,
				hwDocsQamScsEcmgStatisticsSentStreamCloseRequestMessages
				  Counter64,
				hwDocsQamScsEcmgStatisticsSentStreamErrorMessages
				  Counter64,
				hwDocsQamScsEcmgStatisticsSentCWProvisionMessages
				  Counter64
                }
              
        -- 1.3.6.1.4.1.2011.6.187.83.1.1
        hwDocsQamScsEcmgChannelID        OBJECT-TYPE
            SYNTAX      Unsigned32 (0..4294967295)
            MAX-ACCESS  not-accessible
            STATUS      current
            DESCRIPTION
                "Indicates the ECMG Channel ID.
                "
            ::= { hwDocsQamScsEcmgInfoEntry 1 }
			
        -- 1.3.6.1.4.1.2011.6.187.83.1.2   
        hwDocsQamScsEcmgInfoName        OBJECT-TYPE
            SYNTAX       OCTET STRING (SIZE (0..31))
            MAX-ACCESS   read-only
            STATUS       current
            DESCRIPTION
              "Indicates the ECMG name. The default value is null string.
              "
            ::= { hwDocsQamScsEcmgInfoEntry 2 }
			
        -- 1.3.6.1.4.1.2011.6.187.83.1.3
        hwDocsQamScsEcmgIpAddressType        OBJECT-TYPE
            SYNTAX      InetAddressType
            MAX-ACCESS  read-only
            STATUS      current
            DESCRIPTION
                "Indicates the ip address type of ECMG session. The default value is ipv4.
                "
            ::= { hwDocsQamScsEcmgInfoEntry 3 }
      
        -- 1.3.6.1.4.1.2011.6.187.83.1.4
        hwDocsQamScsEcmgPeerIpAddress        OBJECT-TYPE
            SYNTAX      InetAddress
            MAX-ACCESS  read-only
            STATUS      current
            DESCRIPTION
                "Indicates the peer IpAddress of ECMG session. The default value is 0.0.0.0 .
                "
            DEFVAL { 0 }
            ::= { hwDocsQamScsEcmgInfoEntry 4 }
						
        -- 1.3.6.1.4.1.2011.6.187.83.1.5
        hwDocsQamScsEcmgPeerTcpPort        OBJECT-TYPE
            SYNTAX      InetPortNumber
            MAX-ACCESS  read-only
            STATUS      current
            DESCRIPTION
                "Indicates the peer tcp port of ECMG session. The default value is 0.
                "
			DEFVAL { 0 }
            ::= { hwDocsQamScsEcmgInfoEntry 5 }
			
        -- 1.3.6.1.4.1.2011.6.187.83.1.6
        hwDocsQamScsEcmgLocalIpAddress        OBJECT-TYPE
            SYNTAX      InetAddress
            MAX-ACCESS  read-only
            STATUS      current
            DESCRIPTION
                "Indicates the local IpAddress of ECMG session. The default value is 0.0.0.0 .
                "
            DEFVAL { 0 }
            ::= { hwDocsQamScsEcmgInfoEntry 6 }
						
        -- 1.3.6.1.4.1.2011.6.187.83.1.7
        hwDocsQamScsEcmgLocalTcpPort        OBJECT-TYPE
            SYNTAX      InetPortNumber
            MAX-ACCESS  read-only
            STATUS      current
            DESCRIPTION
                "Indicates the local tcp port of ECMG session. The default value is 0.
                "
			DEFVAL { 0 }
            ::= { hwDocsQamScsEcmgInfoEntry 7 }
			
        -- 1.3.6.1.4.1.2011.6.187.83.1.8
        hwDocsQamScsEcmgState        OBJECT-TYPE
            SYNTAX      INTEGER
				{
                  connecting(1),
                  connected(2),
                  notopen(3),
                  settingup(4),
                  open(5),
                  error(6)
                }
            MAX-ACCESS  read-only
            STATUS      current
            DESCRIPTION
                "Indicates the state of ECMG session. The default value is connecting.
				 Options: 
                 1. connecting(1) - The ECMG is connecting.
                 2. connected(2) - The ECMG is connected.
				 3. notopen(3) - The ECMG is not open.
                 4. settingup(4) - The ECMG is setting up.
				 5. open(5) - The ECMG is open.
                 6. error(6) - The ECMG is error.
                "
            DEFVAL { connecting }
            ::= { hwDocsQamScsEcmgInfoEntry 8 }	
			
        -- 1.3.6.1.4.1.2011.6.187.83.1.9
        hwDocsQamScsEcmgProtocolVersion        OBJECT-TYPE
            SYNTAX      INTEGER
				{
                  ver2(1),
                  ver3(2),
		          invalid(255)
                }
            MAX-ACCESS  read-only
            STATUS      current
            DESCRIPTION
                "Indicates the protocol version of ECMG session. The default value is ver2.
				 Options: 
                 1. ver2(1) - The protocol version is ver2.
                 2. ver3(2) - The protocol version is ver3.
		         3. invalid(255) - The protocol version is invalid.
                "
            DEFVAL { ver2 }
            ::= { hwDocsQamScsEcmgInfoEntry 9 }

        -- 1.3.6.1.4.1.2011.6.187.83.1.10
        hwDocsQamScsEcmgSuperCasId        OBJECT-TYPE
            SYNTAX      Unsigned32 (0..4294967295)
            MAX-ACCESS  read-only
            STATUS      current
            DESCRIPTION
                "Indicates the super conditional access system ID of ECMG session. The default value is 4294967295.
                "
            DEFVAL { 4294967295 }
            ::= { hwDocsQamScsEcmgInfoEntry 10 }

        -- 1.3.6.1.4.1.2011.6.187.83.1.11
        hwDocsQamScsEcmgSectionTsPacketFlag        OBJECT-TYPE
            SYNTAX      Unsigned32 (0..2)
            MAX-ACCESS  read-only
            STATUS      current
            DESCRIPTION
                "Indicates the ECM encapsulation format of the ECMG. The default value is 0.
                "
            DEFVAL { 0 }
            ::= { hwDocsQamScsEcmgInfoEntry 11 }

        -- 1.3.6.1.4.1.2011.6.187.83.1.12
        hwDocsQamScsEcmgACDelayStart        OBJECT-TYPE
            SYNTAX      Integer32 (-32768..32767 )
            UNITS       "millisecond"
            MAX-ACCESS  read-only
            STATUS      current
            DESCRIPTION
                "Indicates the ECM AC delay start time of the ECMG. The default value is 0.
                "
            DEFVAL { 0 }
            ::= { hwDocsQamScsEcmgInfoEntry 12 }

        -- 1.3.6.1.4.1.2011.6.187.83.1.13
        hwDocsQamScsEcmgACDelayStop        OBJECT-TYPE
            SYNTAX      Integer32 (-32768..32767 )
            UNITS       "millisecond"
            MAX-ACCESS  read-only
            STATUS      current
            DESCRIPTION
                "Indicates the ECM AC delay stop time of the ECMG. The default value is 0.
                "
            DEFVAL { 0 }
            ::= { hwDocsQamScsEcmgInfoEntry 13 }

        -- 1.3.6.1.4.1.2011.6.187.83.1.14
        hwDocsQamScsEcmgDelayStart        OBJECT-TYPE
            SYNTAX      Integer32 (-32768..32767 )
            UNITS       "millisecond"
            MAX-ACCESS  read-only
            STATUS      current
            DESCRIPTION
                "Indicates the ECM delay start time of the ECMG. The default value is 0.
                "
            DEFVAL { 0 }
            ::= { hwDocsQamScsEcmgInfoEntry 14 }

        -- 1.3.6.1.4.1.2011.6.187.83.1.15
        hwDocsQamScsEcmgDelayStop        OBJECT-TYPE
            SYNTAX      Integer32 (-32768..32767 )
            UNITS       "millisecond"
            MAX-ACCESS  read-only
            STATUS      current
            DESCRIPTION
                "Indicates the ECM delay stop time of the ECMG. The default value is 0.
                "
            DEFVAL { 0 }
            ::= { hwDocsQamScsEcmgInfoEntry 15 }

        -- 1.3.6.1.4.1.2011.6.187.83.1.16
        hwDocsQamScsEcmgTransitionDelayStart        OBJECT-TYPE
            SYNTAX      Integer32 (-32768..32767 )
            UNITS       "millisecond"
            MAX-ACCESS  read-only
            STATUS      current
            DESCRIPTION
                "Indicates the ECM transmission delay start time of the ECMG. The default value is 0.
                "
            DEFVAL { 0 }
            ::= { hwDocsQamScsEcmgInfoEntry 16 }

        -- 1.3.6.1.4.1.2011.6.187.83.1.17
        hwDocsQamScsEcmgTransitionDelayStop        OBJECT-TYPE
            SYNTAX      Integer32 (-32768..32767 )
            UNITS       "millisecond"
            MAX-ACCESS  read-only
            STATUS      current
            DESCRIPTION
                "Indicates the ECM transmission delay stop time of the ECMG. The default value is 0.
                "
            DEFVAL { 0 }
            ::= { hwDocsQamScsEcmgInfoEntry 17 }

        -- 1.3.6.1.4.1.2011.6.187.83.1.18 
        hwDocsQamScsEcmgECMRepetitionPeriod        OBJECT-TYPE
            SYNTAX      Unsigned32 (0..4294967295)
            UNITS       "millisecond"
            MAX-ACCESS  read-only
            STATUS      current
            DESCRIPTION
                "Indicates the ECM send cycle of the ECMG. The default value is 4294967295.
                "
            DEFVAL { 4294967295 }
            ::= { hwDocsQamScsEcmgInfoEntry 18 }

        -- 1.3.6.1.4.1.2011.6.187.83.1.19 
        hwDocsQamScsEcmgMaxStreams        OBJECT-TYPE
            SYNTAX      Unsigned32 (0..4294967295)
            MAX-ACCESS  read-only
            STATUS      current
            DESCRIPTION
                "Indicates the ECM maximum flow quantity of the ECMG. The default value is 0.
                "
            DEFVAL { 0 }
            ::= { hwDocsQamScsEcmgInfoEntry 19 }

        -- 1.3.6.1.4.1.2011.6.187.83.1.20 
        hwDocsQamScsEcmgMinCPDuration        OBJECT-TYPE
            SYNTAX      Unsigned32 (0..4294967295)
            UNITS       "millisecond"
            MAX-ACCESS  read-only
            STATUS      current
            DESCRIPTION
                "Indicates the Minimum scrambling cycle of the ECMG. The default value is 4294967295.
                "
            DEFVAL { 4294967295 }
            ::= { hwDocsQamScsEcmgInfoEntry 20 }

        -- 1.3.6.1.4.1.2011.6.187.83.1.21
        hwDocsQamScsEcmgLeadCW        OBJECT-TYPE
            SYNTAX      Unsigned32 (0..4294967295)
            MAX-ACCESS  read-only
            STATUS      current
            DESCRIPTION
                "Indicates the starting CW of the ECMG. The default value is 0.
                "
            DEFVAL { 0 }
            ::= { hwDocsQamScsEcmgInfoEntry 21 }			

        -- 1.3.6.1.4.1.2011.6.187.83.1.22
        hwDocsQamScsEcmgCWperMsg        OBJECT-TYPE
            SYNTAX      Unsigned32 (0..4294967295)
            MAX-ACCESS  read-only
            STATUS      current
            DESCRIPTION
                "Indicates the CW number of one message. The default value is 1.
                "
            DEFVAL { 1 }
            ::= { hwDocsQamScsEcmgInfoEntry 22 }

        -- 1.3.6.1.4.1.2011.6.187.83.1.23 
        hwDocsQamScsEcmgMaxComputeTime        OBJECT-TYPE
            SYNTAX      Unsigned32 (0..4294967295)
            UNITS       "millisecond"
            MAX-ACCESS  read-only
            STATUS      current
            DESCRIPTION
                "Indicates The max computing time of the ECMG. The default value is 4294967295.
                "
            DEFVAL { 4294967295 }
            ::= { hwDocsQamScsEcmgInfoEntry 23 }

        -- 1.3.6.1.4.1.2011.6.187.83.1.24
        hwDocsQamScsEcmgErroStatusCode        OBJECT-TYPE
            SYNTAX      Unsigned32 (0..4294967295)
            MAX-ACCESS  read-only
            STATUS      current
            DESCRIPTION
                "Indicates the error code of ECMG session,please read 'ETSI TS 103 197 V1.5.1,chapter 5.6 Error status' for reference. The default value is 0.
                "
            DEFVAL { 0 }
            ::= { hwDocsQamScsEcmgInfoEntry 24 }

        -- 1.3.6.1.4.1.2011.6.187.83.1.25
        hwDocsQamScsEcmgStatisticsReset        OBJECT-TYPE
            SYNTAX      INTEGER
            {
            clear(1)
            }
            MAX-ACCESS  read-write
            STATUS      current
            DESCRIPTION
                "Indicates the statistics action. The default value is clear.
                        Options: 
                 1. clear(1) - The statistics action is clear.
                "
            DEFVAL { clear }
            ::= { hwDocsQamScsEcmgInfoEntry 25 }

        -- 1.3.6.1.4.1.2011.6.187.83.1.26
        hwDocsQamScsEcmgStatisticsReceivedTotalMessages        OBJECT-TYPE
            SYNTAX      Counter64
            MAX-ACCESS  read-only
            STATUS      current
            DESCRIPTION
                "Indicates the total number of receiving messages of SCS ECMG. The default value is 0.
                "
            ::= { hwDocsQamScsEcmgInfoEntry 26 }

        -- 1.3.6.1.4.1.2011.6.187.83.1.27
        hwDocsQamScsEcmgStatisticsReceivedChannelTestMessages        OBJECT-TYPE
            SYNTAX      Counter64
            MAX-ACCESS  read-only
            STATUS      current
            DESCRIPTION
                "Indicates the total number of test messages in the receive channel of SCS ECMG. The default value is 0.
                "
            ::= { hwDocsQamScsEcmgInfoEntry 27 }

        -- 1.3.6.1.4.1.2011.6.187.83.1.28
        hwDocsQamScsEcmgStatisticsReceivedChannelStatusMessages        OBJECT-TYPE
            SYNTAX      Counter64
            MAX-ACCESS  read-only
            STATUS      current
            DESCRIPTION
                "Indicates the total number of staus messages in the receive channel of SCS ECMG. The default value is 0.
                "
            ::= { hwDocsQamScsEcmgInfoEntry 28 }

        -- 1.3.6.1.4.1.2011.6.187.83.1.29
        hwDocsQamScsEcmgStatisticsReceivedChannelErrorMessages        OBJECT-TYPE
            SYNTAX      Counter64
            MAX-ACCESS  read-only
            STATUS      current
            DESCRIPTION
                "Indicates the total number of error messages in the receive channel of SCS ECMG. The default value is 0.
                "
            ::= { hwDocsQamScsEcmgInfoEntry 29 }

        -- 1.3.6.1.4.1.2011.6.187.83.1.30
        hwDocsQamScsEcmgStatisticsReceivedStreamTestMessages        OBJECT-TYPE
            SYNTAX      Counter64
            MAX-ACCESS  read-only
            STATUS      current
            DESCRIPTION
                "Indicates the total number of test messages in the receive flow of SCS ECMG. The default value is 0.
                "
            ::= { hwDocsQamScsEcmgInfoEntry 30 }

        -- 1.3.6.1.4.1.2011.6.187.83.1.31
        hwDocsQamScsEcmgStatisticsReceivedStreamStatusMessages        OBJECT-TYPE
            SYNTAX      Counter64
            MAX-ACCESS  read-only
            STATUS      current
            DESCRIPTION
                "Indicates the total number of status messages in the receive flow of SCS ECMG. The default value is 0.
                "
            ::= { hwDocsQamScsEcmgInfoEntry 31 }

            -- 1.3.6.1.4.1.2011.6.187.83.1.32
        hwDocsQamScsEcmgStatisticsReceivedStreamCloseResponseMessages        OBJECT-TYPE
            SYNTAX      Counter64
            MAX-ACCESS  read-only
            STATUS      current
            DESCRIPTION
                "Indicates the total number of close response messages in the receive flow of SCS ECMG. The default value is 0.
                "
            ::= { hwDocsQamScsEcmgInfoEntry 32 }
			
		-- 1.3.6.1.4.1.2011.6.187.83.1.33
        hwDocsQamScsEcmgStatisticsReceivedStreamErrorMessages        OBJECT-TYPE
            SYNTAX      Counter64
            MAX-ACCESS  read-only
            STATUS      current
            DESCRIPTION
                "Indicates the total number of error messages in the receive flow of SCS ECMG. The default value is 0.
                "
            ::= { hwDocsQamScsEcmgInfoEntry 33 }
			
		-- 1.3.6.1.4.1.2011.6.187.83.1.34
        hwDocsQamScsEcmgStatisticsReceivedECMResponseMessages        OBJECT-TYPE
            SYNTAX      Counter64
            MAX-ACCESS  read-only
            STATUS      current
            DESCRIPTION
                "Indicates the total number of response messages in the receive flow of SCS ECMG. The default value is 0.
                "
            ::= { hwDocsQamScsEcmgInfoEntry 34 }
			
		-- 1.3.6.1.4.1.2011.6.187.83.1.35
        hwDocsQamScsEcmgStatisticsSentTotalMessages        OBJECT-TYPE
            SYNTAX      Counter64
            MAX-ACCESS  read-only
            STATUS      current
            DESCRIPTION
                "Indicates the total number of send messages of SCS ECMG. The default value is 0.
                "
            ::= { hwDocsQamScsEcmgInfoEntry 35 }
			
		-- 1.3.6.1.4.1.2011.6.187.83.1.36
        hwDocsQamScsEcmgStatisticsSentChannelSetupMessages        OBJECT-TYPE
            SYNTAX      Counter64
            MAX-ACCESS  read-only
            STATUS      current
            DESCRIPTION
                "Indicates the total number of setup messages in the send channel of SCS ECMG. The default value is 0.
                "
            ::= { hwDocsQamScsEcmgInfoEntry 36 }
			
		-- 1.3.6.1.4.1.2011.6.187.83.1.37
        hwDocsQamScsEcmgStatisticsSentChannelTestMessages        OBJECT-TYPE
            SYNTAX      Counter64
            MAX-ACCESS  read-only
            STATUS      current
            DESCRIPTION
                "Indicates the total number of test messages in the send channel of SCS ECMG. The default value is 0.
                "
            ::= { hwDocsQamScsEcmgInfoEntry 37 }
			
		-- 1.3.6.1.4.1.2011.6.187.83.1.38
        hwDocsQamScsEcmgStatisticsSentChannelStatusMessages        OBJECT-TYPE
            SYNTAX      Counter64
            MAX-ACCESS  read-only
            STATUS      current
            DESCRIPTION
                "Indicates the total number of status messages in the send channel of SCS ECMG. The default value is 0.
                "
            ::= { hwDocsQamScsEcmgInfoEntry 38 }
			
		-- 1.3.6.1.4.1.2011.6.187.83.1.39
        hwDocsQamScsEcmgStatisticsSentChannelCloseMessages        OBJECT-TYPE
            SYNTAX      Counter64
            MAX-ACCESS  read-only
            STATUS      current
            DESCRIPTION
                "Indicates the total number of close messages in the send channel of SCS ECMG. The default value is 0.
                "
            ::= { hwDocsQamScsEcmgInfoEntry 39 }
			
		-- 1.3.6.1.4.1.2011.6.187.83.1.40
        hwDocsQamScsEcmgStatisticsSentChannelErrorMessages        OBJECT-TYPE
            SYNTAX      Counter64
            MAX-ACCESS  read-only
            STATUS      current
            DESCRIPTION
                "Indicates the total number of error messages in the send channel of SCS ECMG. The default value is 0.
                "
            ::= { hwDocsQamScsEcmgInfoEntry 40 }
			
		-- 1.3.6.1.4.1.2011.6.187.83.1.41
        hwDocsQamScsEcmgStatisticsSentStreamSetupMessages        OBJECT-TYPE
            SYNTAX      Counter64
            MAX-ACCESS  read-only
            STATUS      current
            DESCRIPTION
                "Indicates the total number of setup messages in the send flow of SCS ECMG. The default value is 0.
                "
            ::= { hwDocsQamScsEcmgInfoEntry 41 }
			
		-- 1.3.6.1.4.1.2011.6.187.83.1.42
        hwDocsQamScsEcmgStatisticsSentStreamTestMessages        OBJECT-TYPE
            SYNTAX      Counter64
            MAX-ACCESS  read-only
            STATUS      current
            DESCRIPTION
                "Indicates the total number of test messages in the send flow of SCS ECMG. The default value is 0.
                "
            ::= { hwDocsQamScsEcmgInfoEntry 42 }
			
		-- 1.3.6.1.4.1.2011.6.187.83.1.43
        hwDocsQamScsEcmgStatisticsSentStreamStatusMessages        OBJECT-TYPE
            SYNTAX      Counter64
            MAX-ACCESS  read-only
            STATUS      current
            DESCRIPTION
                "Indicates the total number of status messages in the send flow of SCS ECMG. The default value is 0.
                "
            ::= { hwDocsQamScsEcmgInfoEntry 43 }
			
		-- 1.3.6.1.4.1.2011.6.187.83.1.44
        hwDocsQamScsEcmgStatisticsSentStreamCloseRequestMessages        OBJECT-TYPE
            SYNTAX      Counter64
            MAX-ACCESS  read-only
            STATUS      current
            DESCRIPTION
                "Indicates the total number of close request messages in the send flow of SCS ECMG. The default value is 0.
                "
            ::= { hwDocsQamScsEcmgInfoEntry 44 }
			
		-- 1.3.6.1.4.1.2011.6.187.83.1.45
        hwDocsQamScsEcmgStatisticsSentStreamErrorMessages        OBJECT-TYPE
            SYNTAX      Counter64
            MAX-ACCESS  read-only
            STATUS      current
            DESCRIPTION
                "Indicates the total number of error messages in the send flow of SCS ECMG. The default value is 0.
                "
            ::= { hwDocsQamScsEcmgInfoEntry 45 }
			
		-- 1.3.6.1.4.1.2011.6.187.83.1.46
        hwDocsQamScsEcmgStatisticsSentCWProvisionMessages        OBJECT-TYPE
            SYNTAX      Counter64
            MAX-ACCESS  read-only
            STATUS      current
            DESCRIPTION
                "Indicates the total number of CW provision messages of SCS ECMG. The default value is 0.
                "
            ::= { hwDocsQamScsEcmgInfoEntry 46 }
			
		-- 1.3.6.1.4.1.2011.6.187.84
        hwDocsQamScsEcmgEcmTable    OBJECT-TYPE
            SYNTAX          SEQUENCE OF HwDocsQamScsEcmgEcmEntry
            MAX-ACCESS      not-accessible
            STATUS          current
            DESCRIPTION
                "Indicates the EQAM SCS ECMG ECM table.
                 The index of this table is hwDocsQamSCSName, hwDocsQamScsEcmgChannelID and hwDocsQamScsEcmgStreamID.
                "
            ::= { hwEqamAn 84 }
    
        -- 1.3.6.1.4.1.2011.6.187.84.1
        hwDocsQamScsEcmgEcmEntry    OBJECT-TYPE
            SYNTAX          HwDocsQamScsEcmgEcmEntry
            MAX-ACCESS      not-accessible
            STATUS          current
            DESCRIPTION
                "Indicates the EQAM SCS ECMG ECM table.
                 The index of this entry is hwDocsQamSCSName, hwDocsQamScsEcmgChannelID and hwDocsQamScsEcmgStreamID.
                "
            INDEX   
                { 
                hwDocsQamSCSName,
				hwDocsQamScsEcmgChannelID,
				hwDocsQamScsEcmgStreamID
                }
            ::= { hwDocsQamScsEcmgEcmTable  1 }
        
        HwDocsQamScsEcmgEcmEntry ::=
            SEQUENCE 
                { 
                hwDocsQamScsEcmgStreamID
                  Unsigned32,
                hwDocsQamScsEcmgECMID
                  Unsigned32,
                hwDocsQamScsEcmgName
                  OCTET STRING,
                hwDocsQamScsEcmgEcmSuperCasID
                  Unsigned32,
                hwDocsQamScsEcmgEcmAccessCriteria
                  OCTET STRING,
                hwDocsQamScsEcmgEcmACTransferMode
                  Unsigned32
                }

        -- 1.3.6.1.4.1.2011.6.187.84.1.1
	hwDocsQamScsEcmgStreamID        OBJECT-TYPE
            SYNTAX      Unsigned32 (0..4294967295)
            MAX-ACCESS  not-accessible
            STATUS      current
            DESCRIPTION
                "Indicates the stream ID of ECMG.
                "
            ::= { hwDocsQamScsEcmgEcmEntry 1 }
			
		-- 1.3.6.1.4.1.2011.6.187.84.1.2
        hwDocsQamScsEcmgECMID        OBJECT-TYPE
            SYNTAX      Unsigned32 (0..4294967295)
            MAX-ACCESS  read-only
            STATUS      current
            DESCRIPTION
                "Indicates the ECM ID.
                "
			DEFVAL { 4294967295 }
            ::= { hwDocsQamScsEcmgEcmEntry 2 }
			
		-- 1.3.6.1.4.1.2011.6.187.84.1.3   
        hwDocsQamScsEcmgName        OBJECT-TYPE
            SYNTAX       OCTET STRING (SIZE (0..31))
            MAX-ACCESS   read-only
            STATUS       current
            DESCRIPTION
              "Indicates the ECMG name. The default value is null string.
              "
            ::= { hwDocsQamScsEcmgEcmEntry 3 }
			
		-- 1.3.6.1.4.1.2011.6.187.84.1.4
        hwDocsQamScsEcmgEcmSuperCasID        OBJECT-TYPE
            SYNTAX      Unsigned32 (0..4294967295)
            MAX-ACCESS  read-only
            STATUS      current
            DESCRIPTION
                "Indicates the super conditional access system ID of ECMG session. The default value is 0.
                "
			DEFVAL { 0 }
            ::= { hwDocsQamScsEcmgEcmEntry 4 }
			
		-- 1.3.6.1.4.1.2011.6.187.84.1.5   
        hwDocsQamScsEcmgEcmAccessCriteria        OBJECT-TYPE
            SYNTAX       OCTET STRING (SIZE (0..127))
            MAX-ACCESS   read-only
            STATUS       current
            DESCRIPTION
              "Indicates the ECMG access criteria. The default value is null string.
              "
            ::= { hwDocsQamScsEcmgEcmEntry 5 }
			
		-- 1.3.6.1.4.1.2011.6.187.84.1.6
        hwDocsQamScsEcmgEcmACTransferMode        OBJECT-TYPE
            SYNTAX      Unsigned32 (0..1)
            MAX-ACCESS  read-only
            STATUS      current
            DESCRIPTION
                "Indicates the send mode of ECMG AC.
                "
			DEFVAL { 0 }
            ::= { hwDocsQamScsEcmgEcmEntry 6 }
END

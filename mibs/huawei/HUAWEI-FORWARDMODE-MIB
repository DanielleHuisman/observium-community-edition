-- =================================================================
-- Copyright (C) 2018 by  HUAWEI TECHNOLOGIES. All rights reserved.
--
-- Description:HUAWEI-FORWARDMODE-MIB DEFINITIONS
-- Reference:
-- Version: V2.02
-- History:
--     
-- =================================================================

HUAWEI-FORWARDMODE-MIB    DEFINITIONS ::= BEGIN

    IMPORTS
            hwDatacomm            
                FROM HUAWEI-MIB
            OBJECT-GROUP, MODULE-COMPLIANCE, NOTIFICATION-GROUP            
                FROM SNMPv2-CONF 
            Integer32, OBJECT-TYPE , MODULE-IDENTITY , NOTIFICATION-TYPE           
                FROM SNMPv2-SMI
            InterfaceIndex, ifIndex                  
                FROM IF-MIB 
            DisplayString   
                FROM SNMPv2-TC;       
              
          hwForwardMode MODULE-IDENTITY 
          LAST-UPDATED "201801181414Z"    
          ORGANIZATION 
              "Huawei Technologies Co.,Ltd."
          CONTACT-INFO 
 "Huawei Industrial Base  Bantian, Longgang   Shenzhen 518129   People's Republic of China   Website: http://www.huawei.com   Email: support@huawei.com "  
          
		  DESCRIPTION 
              "The private mib file add forward-mode includes the general extent 
              information of the device.hwDatacomm(231).hwForwardMode"  
          REVISION "201801181414Z"
          DESCRIPTION  
            "V2.02, The modify revision of this MIB module. modify the description of hwFwdFibAlarmOccur hwFwdFibAlarmResume hwForwardModeStaVpnSlotId hwForwardModeV4V6Flag."
          REVISION "201703291414Z"        -- MAR 29, 2017 at 10:40GMT  
          DESCRIPTION  
            "V2.01, The modify revision of this MIB module. Add  hwFwdFibAlarmOccur, hwFwdFibAlarmResume, in case that some boards do not support IPv4 or IPv6 static routes imported between public and VPN instances."  
          ::= { hwDatacomm 231 }
          
      hwForwardModeMibObjects OBJECT IDENTIFIER ::= { hwForwardMode 1 }
      
      hwForwardModeTable OBJECT-TYPE
          SYNTAX      SEQUENCE OF HwForwardModeEntry
          MAX-ACCESS  not-accessible
          STATUS      current
          DESCRIPTION
              "A binding relationship table of virutal Ethernet interfaces that use ID as the index."
          ::= { hwForwardModeMibObjects 1 }
            
      hwForwardModeEntry OBJECT-TYPE
          SYNTAX HwForwardModeEntry
          MAX-ACCESS not-accessible
          STATUS current
          DESCRIPTION
              "Binding entry of virutal Etherent interfaces that use ID as the index. Each entry has one 
               Layer 2 virutal Ethernet interface and one Layer 3 virtual Ethernet interface." 
          INDEX  { hwForwardModeInstanceId,hwForwardModeInstanceType }    
          ::= { hwForwardModeTable 1 }           
    
      HwForwardModeEntry  ::= 
          SEQUENCE{
              hwForwardModeInstanceId
                  Integer32, 
              hwForwardModeInstanceType
                  INTEGER,   
              hwForwardModeInstanceName
                  DisplayString,  
              hwForwardModeType       
                  INTEGER
          }
      --  ============== hwForwardModeTable  define beginning ==============

       hwForwardModeInstanceId   OBJECT-TYPE
       SYNTAX         Integer32 (1..4294967295)
       MAX-ACCESS     not-accessible
       STATUS         current
       DESCRIPTION    "Interface Index"
       ::= { hwForwardModeEntry 1 }
       
       hwForwardModeInstanceType   OBJECT-TYPE
       SYNTAX        INTEGER {
                                ve(1),
                                gre(2)
                                }
       MAX-ACCESS     not-accessible
       STATUS        current
       DESCRIPTION    
       " 1 : ve, 2 : gre."
       ::= { hwForwardModeEntry 2 }  
       
       hwForwardModeInstanceName   OBJECT-TYPE
       SYNTAX        DisplayString
       MAX-ACCESS    read-only
       STATUS        current
       DESCRIPTION
            "Name of a virtual Ethernet interface, such as Virtual-Ethernet 3/0/0"
       ::= { hwForwardModeEntry 3 }
       
       hwForwardModeType   OBJECT-TYPE
       SYNTAX        INTEGER {
                                through(1),
                                loopback(2)
                                }
       MAX-ACCESS    read-write
       STATUS        current
       DESCRIPTION    
       " 1 : through, 2 : loopback."
       ::= { hwForwardModeEntry 4 }   
  

       hwForwardModeStaVpnTable OBJECT-TYPE
          SYNTAX      SEQUENCE OF HwForwardModeStaVpnEntry
          MAX-ACCESS  not-accessible
          STATUS      current
          DESCRIPTION
              "The board in the current slot does not support IPv4 or IPv6 static routes imported between public and VPN instances."
          ::= { hwForwardModeMibObjects 2 }
            
       hwForwardModeStaVpnEntry OBJECT-TYPE
          SYNTAX HwForwardModeStaVpnEntry
          MAX-ACCESS not-accessible
          STATUS current
          DESCRIPTION
              "The board in the current slot does not support IPv4 or IPv6 static routes imported between public and VPN instances." 
          INDEX  { hwForwardModeStaVpnSlotId }    
          ::= { hwForwardModeStaVpnTable 1 }           
    
       HwForwardModeStaVpnEntry  ::= 
          SEQUENCE{ 
              hwForwardModeStaVpnSlotId
                  DisplayString,  
              hwForwardModeV4V6Flag       
                  DisplayString
          }
		  
		  
    hwForwardModeStaVpnSlotId   OBJECT-TYPE
       SYNTAX        DisplayString
       MAX-ACCESS    accessible-for-notify
       STATUS        current
       DESCRIPTION
            "This object indicates the slot ID of the board on which IPv4 or IPv6 static routes imported between VPN and public network instances exist."
       ::= { hwForwardModeStaVpnEntry 1 }
	  
    hwForwardModeV4V6Flag   OBJECT-TYPE
       SYNTAX        DisplayString
       MAX-ACCESS    read-only
       STATUS        current
       DESCRIPTION
            "This object indicates the type of static routes imported between VPN and public network instances."
       ::= { hwForwardModeStaVpnEntry 2 }

	--  Notifications(trap) Definitions
       
    hwForwardModeNotifications OBJECT IDENTIFIER ::= { hwForwardMode 3}
     
	hwFwdFibAlarmOccur NOTIFICATION-TYPE
			OBJECTS { hwForwardModeStaVpnSlotId , hwForwardModeV4V6Flag}
			STATUS current
			DESCRIPTION 
				"This object indicates that import of IPv4/IPv6 static routes between public networks and VPN instances is not supported on the board."
			::= { hwForwardModeNotifications 1 }
			
	hwFwdFibAlarmResume NOTIFICATION-TYPE
			OBJECTS { hwForwardModeStaVpnSlotId , hwForwardModeV4V6Flag}
			STATUS current
			DESCRIPTION 
				"This object indicates that the board in the current slot supports IPv4 or IPv6 static routes imported between VPN and public network instances."
			::= { hwForwardModeNotifications 2 } 
			
  --  ============== conformance information ==============
        hwForwardModeConformance OBJECT IDENTIFIER ::= { hwForwardMode 2 }
        
        
        hwForwardModeCompliances OBJECT IDENTIFIER ::= { hwForwardModeConformance 2 }
		hwForwardVPNTrapCompliances  OBJECT IDENTIFIER ::= { hwForwardModeConformance 3 }
        
		hwForwardModeCompliance MODULE-COMPLIANCE
               STATUS      current
               DESCRIPTION
                   "The compliance statement for systems supporting 
                the this module."

               MODULE
                   MANDATORY-GROUPS { hwForwardModeObjectGroup }
               ::= { hwForwardModeCompliances 1 }
			   
        hwForwardVPNTrapCompliance 	 MODULE-COMPLIANCE	
 		       STATUS      current
               DESCRIPTION
                   "The compliance statement for systems supporting 
                the this module."
               MODULE
                   MANDATORY-GROUPS { hwForwardModeVPNGroup }
               ::= { hwForwardVPNTrapCompliances 1 }
    --  ============== groups ==============  
        hwForwardModeGroups OBJECT IDENTIFIER ::= { hwForwardModeConformance 1 } 
		
        hwForwardModeObjectGroup OBJECT-GROUP
            OBJECTS {hwForwardModeInstanceName, hwForwardModeType}
            STATUS current
            DESCRIPTION 
                "The forword-mode attribute table."
            ::= { hwForwardModeGroups 1 }
			
		hwForwardModeVPNGroup OBJECT-GROUP
            OBJECTS {hwForwardModeStaVpnSlotId, hwForwardModeV4V6Flag}
            STATUS current
            DESCRIPTION 
                "The forword-mode attribute table."
            ::= { hwForwardModeGroups 2 }
			
		hwForwardModeVPNTrapGroup NOTIFICATION-GROUP
            NOTIFICATIONS {hwFwdFibAlarmOccur, hwFwdFibAlarmResume}
            STATUS current
            DESCRIPTION 
                "The forword-mode attribute table."
            ::= { hwForwardModeGroups 3 }
        
    --  ============== conformance information define end ============== 
END

--
-- HUAWEI-FORWARDMODE-MIB.mib
--

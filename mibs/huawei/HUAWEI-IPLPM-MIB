--  ==================================================================
-- Copyright (C) 2014 by  HUAWEI TECHNOLOGIES. All rights reserved.
-- 
-- Description: HUAWEI Private IPLPM MIB
-- Reference:
-- Version: V1.01
-- History:
--          Xie YeZhuan,2014-01-09,Create 
-- ==================================================================

	HUAWEI-IPLPM-MIB DEFINITIONS ::= BEGIN
 
		IMPORTS
			hwDatacomm			
				FROM HUAWEI-MIB			
			OBJECT-GROUP, MODULE-COMPLIANCE, NOTIFICATION-GROUP			
				FROM SNMPv2-CONF			
			IpAddress, Integer32, Unsigned32, Counter64, OBJECT-TYPE, 
			MODULE-IDENTITY, NOTIFICATION-TYPE			
				FROM SNMPv2-SMI			
			RowStatus, TEXTUAL-CONVENTION			
				FROM SNMPv2-TC;
	
	
		hwIplpmMib MODULE-IDENTITY 
			LAST-UPDATED "201404252000Z"
			ORGANIZATION 
				"Huawei Technologies Co.,Ltd."
			CONTACT-INFO 
				"Huawei Industrial Base
				Bantian, Longgang
				 Shenzhen 518129
				 People's Republic of China
				 Website: http://www.huawei.com
				 Email: support@huawei.com
				"
			DESCRIPTION 
				"This MIB describes objects to manage IPLPM (IP Local 
				Performance Monitoring). "  
		    REVISION "201404252000Z"  
		    DESCRIPTION
		        "Import hwIplpmMib file at 2014-04-25"
	

                                             REVISION "201310252000Z"  
		    DESCRIPTION
		        "Import hwIplpmMib file at 2014-03-19"
			::= { hwDatacomm 328 }
		
	
		HWIplpmLossStatsErrorInfo ::= TEXTUAL-CONVENTION
			STATUS current
			DESCRIPTION 
				"Description."
			SYNTAX INTEGER
				{
				init(0),
				ok(1),
				noRecvData(2),
				dataErr(3),
				diffAuth(4),
				diffIntvl(5),
				aSynClock(6),
				incomplete(7),
				portIsDown(8)
				}
			
	
--
-- Node definitions
--
	
		-- 1.3.6.1.4.1.2011.5.25.328.1
		hwIplpmObjects OBJECT IDENTIFIER ::= { hwIplpmMib 1 }
		
		-- 1.3.6.1.4.1.2011.5.25.328.1.1
		hwIplpmConfiguration OBJECT IDENTIFIER ::= { hwIplpmObjects 1 }
		
		-- 1.3.6.1.4.1.2011.5.25.328.1.1.1
		hwIplpmGlobalConfiguration OBJECT IDENTIFIER ::= { hwIplpmConfiguration 1 }
		
		-- 1.3.6.1.4.1.2011.5.25.328.1.1.1.1
		hwIplpmGlobalTable OBJECT IDENTIFIER ::= { hwIplpmGlobalConfiguration 1 }
		
		-- 1.3.6.1.4.1.2011.5.25.328.1.1.1.1.1
		hwIplpmLossMeasureEnable OBJECT-TYPE
			SYNTAX INTEGER
				{
				enabled(1),
				disabled(2)
				}
			MAX-ACCESS read-write
			STATUS current
			DESCRIPTION
				"This object indicates that the global loss measure 
				function is 'enabled(1)' or 'disabled(2)'."
			DEFVAL { disabled }
			::= { hwIplpmGlobalTable 1 }
		
		-- 1.3.6.1.4.1.2011.5.25.328.1.1.1.1.2
		hwIplpmLossMeasureColorFlag OBJECT-TYPE
			SYNTAX INTEGER
				{
				flagsBit0(1),
				tosBit6(2),
				tosBit7(3)
				}
			MAX-ACCESS read-write
			STATUS current
			DESCRIPTION
				"This value indicates the bits of an IP packet used for color 
				measurement. 
				The character '1' represents the bit0 of the FLAGS byte.
				The character '2' represents the bit6 of the TOS byte. 
				The character '3' represents the bit7 of the TOS byte."
			DEFVAL { flagsbit0 }
			::= { hwIplpmGlobalTable 2 }
		
		-- 1.3.6.1.4.1.2011.5.25.328.1.1.1.1.3
		hwIplpmLossMeasureInterval OBJECT-TYPE
			SYNTAX INTEGER
				{
				interval1s(1),
				interval10s(10),
				interval60s(60),
				interval600s(600)
				}
			MAX-ACCESS read-write
			STATUS current
			DESCRIPTION
				"This object indicates that interval of global loss measure is
				'interval1s(1)' or 'interval10s(10)' or 'interval60s(60)'
				or 'interval600s(600)'."
			DEFVAL { interval10s }
			::= { hwIplpmGlobalTable 3 }
		
		-- 1.3.6.1.4.1.2011.5.25.328.1.1.1.1.4
		hwIplpmLossMeasureAlarmEnable OBJECT-TYPE
			SYNTAX INTEGER
				{
				enabled(1),
				disabled(2)
				}
			MAX-ACCESS read-write
			STATUS current
			DESCRIPTION
				"This object indicates that the global loss measure alarm 
				function is 'enabled(1)' or 'disabled(2)'."
			DEFVAL { disabled }
			::= { hwIplpmGlobalTable 4 }
		
		-- 1.3.6.1.4.1.2011.5.25.328.1.1.2
		hwIplpmInterfaceConguration OBJECT IDENTIFIER ::= { hwIplpmConfiguration 2 }
		
		-- 1.3.6.1.4.1.2011.5.25.328.1.1.2.1
		hwIplpmIntfConfigTable OBJECT-TYPE
			SYNTAX SEQUENCE OF HwIplpmIntfConfigEntry
			MAX-ACCESS not-accessible
			STATUS current
			DESCRIPTION
				"IPLPM configuration information for a link loss measure instance."
			::= { hwIplpmInterfaceConguration 1 }
		
		-- 1.3.6.1.4.1.2011.5.25.328.1.1.2.1.1
		hwIplpmIntfConfigEntry OBJECT-TYPE
			SYNTAX HwIplpmIntfConfigEntry
			MAX-ACCESS not-accessible
			STATUS current
			DESCRIPTION
				"IPLPM configuration information for a link loss measure instance."
			INDEX { hwIplpmIntfIfIndex }
			::= { hwIplpmIntfConfigTable 1 }
		
		HwIplpmIntfConfigEntry ::=
			SEQUENCE { 
				hwIplpmIntfIfIndex
					Integer32,
				hwIplpmIntfInterval
					INTEGER,
				hwIplpmIntfAuthKeyId
					Integer32,
				hwIplpmIntfAuthType
					INTEGER,
				hwIplpmIntfAuthKey
					OCTET STRING,
				hwIplpmIntfLossMeasureEnable
					INTEGER,
				hwIplpmIntfLossMeasureAlarmEnable
					INTEGER,
				hwIplpmIntfConfigRowStatus
					RowStatus
			 }

		-- 1.3.6.1.4.1.2011.5.25.328.1.1.2.1.1.1
		hwIplpmIntfIfIndex OBJECT-TYPE
			SYNTAX Integer32 (1..2147483647)
			MAX-ACCESS not-accessible
			STATUS current
			DESCRIPTION
				"The port index of the link loss measure."
			::= { hwIplpmIntfConfigEntry 1 }
		
		-- 1.3.6.1.4.1.2011.5.25.328.1.1.2.1.1.2
		hwIplpmIntfInterval OBJECT-TYPE
			SYNTAX INTEGER
				{
				interval1s(1),
				interval10s(10),
				interval60s(60),
				interval600s(600)
				}
			MAX-ACCESS read-write
			STATUS current
			DESCRIPTION
				"This object indicates that interval of link loss measure is
				'interval1s(1)' or 'interval10s(10)' or 'interval60s(60)'
				or 'interval600s(600)'."
			DEFVAL { interval10s }
			::= { hwIplpmIntfConfigEntry 2 }
		
		-- 1.3.6.1.4.1.2011.5.25.328.1.1.2.1.1.3
		hwIplpmIntfAuthKeyId OBJECT-TYPE
			SYNTAX Integer32 (1..64)
			MAX-ACCESS read-write
			STATUS current
			DESCRIPTION
				"Authentication identification of the link loss measure."
			::= { hwIplpmIntfConfigEntry 3 }
		
		-- 1.3.6.1.4.1.2011.5.25.328.1.1.2.1.1.4
		hwIplpmIntfAuthType OBJECT-TYPE
			SYNTAX INTEGER
				{
				hmacsha256(1),
				none(2)
				}
			MAX-ACCESS read-write
			STATUS current
			DESCRIPTION
				"Authentication type of the link loss measure. The enumeration 
				'hmac-sha256(1)' represents the password is sent after being 
				encrypted through hmac-sha256. By default, authentication is not configured.
				"
			DEFVAL { none }
			::= { hwIplpmIntfConfigEntry 4 }
		
		-- 1.3.6.1.4.1.2011.5.25.328.1.1.2.1.1.5
		hwIplpmIntfAuthKey OBJECT-TYPE
			SYNTAX OCTET STRING (SIZE (0..392))
			MAX-ACCESS read-write
			STATUS current
			DESCRIPTION
				"The password used as authentication key for link loss measure."
			::= { hwIplpmIntfConfigEntry 5 }
		
		-- 1.3.6.1.4.1.2011.5.25.328.1.1.2.1.1.6
		hwIplpmIntfLossMeasureEnable OBJECT-TYPE
			SYNTAX INTEGER
				{
				enabled(1),
				disabled(2)
				}
			MAX-ACCESS read-write
			STATUS current
			DESCRIPTION
				"This object indicates that the link loss measure 
				function is 'enabled(1)' or 'disabled(2)'."
			DEFVAL { disabled }
			::= { hwIplpmIntfConfigEntry 6 }
		
		-- 1.3.6.1.4.1.2011.5.25.328.1.1.2.1.1.7
		hwIplpmIntfLossMeasureAlarmEnable OBJECT-TYPE
			SYNTAX INTEGER
				{
				enabled(1),
				disabled(2)
				}
			MAX-ACCESS read-write
			STATUS current
			DESCRIPTION
				"This object indicates that the link loss measure alarm 
				function is 'enabled(1)' or 'disabled(2)'."
			DEFVAL { disabled }
			::= { hwIplpmIntfConfigEntry 7 }
		
		-- 1.3.6.1.4.1.2011.5.25.328.1.1.2.1.1.8
		hwIplpmIntfConfigRowStatus OBJECT-TYPE
			SYNTAX RowStatus
			MAX-ACCESS read-create
			STATUS current
			DESCRIPTION
				"Used for controlling the creation and deletion of this row."
			::= { hwIplpmIntfConfigEntry 8 }
		
		-- 1.3.6.1.4.1.2011.5.25.328.1.2
		hwIplpmStatistics OBJECT IDENTIFIER ::= { hwIplpmObjects 2 }
		
		-- 1.3.6.1.4.1.2011.5.25.328.1.2.1
		hwIplpmGlobalStatsInfo OBJECT IDENTIFIER ::= { hwIplpmStatistics 1 }
		
		-- 1.3.6.1.4.1.2011.5.25.328.1.2.1.1
		hwIplpmGlobalLatestPeriodNo OBJECT-TYPE
			SYNTAX Counter64
			MAX-ACCESS read-only
			STATUS current
			DESCRIPTION
				"The object identifies the latest period number of global loss."
			::= { hwIplpmGlobalStatsInfo 1 }
		
		-- 1.3.6.1.4.1.2011.5.25.328.1.2.1.2
		hwIplpmGlobalLatestHisRecordNo OBJECT-TYPE
			SYNTAX Integer32
			MAX-ACCESS read-only
			STATUS current
			DESCRIPTION
				"The object identifies the latest history record number of global loss. The value of -1 means it has not created history record."
			::= { hwIplpmGlobalStatsInfo 2 }
		
		-- 1.3.6.1.4.1.2011.5.25.328.1.2.2
		hwIplpmBoardEntityTable OBJECT-TYPE
			SYNTAX SEQUENCE OF HwIplpmBoardEntityEntry
			MAX-ACCESS not-accessible
			STATUS current
			DESCRIPTION
				"This table contains board entity number.
				"
			::= { hwIplpmStatistics 2 }
		
		-- 1.3.6.1.4.1.2011.5.25.328.1.2.2.1
		hwIplpmBoardEntityEntry OBJECT-TYPE
			SYNTAX HwIplpmBoardEntityEntry
			MAX-ACCESS not-accessible
			STATUS current
			DESCRIPTION
				"This table contains board entity number."
			INDEX { hwIplpmBoardNumber }
			::= { hwIplpmBoardEntityTable 1 }
		
		HwIplpmBoardEntityEntry ::=
			SEQUENCE { 
				hwIplpmBoardNumber
					Integer32,
				hwIplpmBoardPhysicalIndex
					Integer32
			 }

		-- 1.3.6.1.4.1.2011.5.25.328.1.2.2.1.1
		hwIplpmBoardNumber OBJECT-TYPE
			SYNTAX Integer32 (1..48)
			MAX-ACCESS not-accessible
			STATUS current
			DESCRIPTION
				"This object indicates board entity number."
			::= { hwIplpmBoardEntityEntry 1 }
		
		-- 1.3.6.1.4.1.2011.5.25.328.1.2.2.1.2
		hwIplpmBoardPhysicalIndex OBJECT-TYPE
			SYNTAX Integer32
			MAX-ACCESS read-only
			STATUS current
			DESCRIPTION
				"This object indicates board physical index."
			::= { hwIplpmBoardEntityEntry 2 }
		
		-- 1.3.6.1.4.1.2011.5.25.328.1.2.3
		hwIplpmGlobalStatsTable OBJECT-TYPE
			SYNTAX SEQUENCE OF HwIplpmGlobalStatsEntry
			MAX-ACCESS not-accessible
			STATUS current
			DESCRIPTION
				"The table contains global loss measure information."
			::= { hwIplpmStatistics 3 }
		
		-- 1.3.6.1.4.1.2011.5.25.328.1.2.3.1
		hwIplpmGlobalStatsEntry OBJECT-TYPE
			SYNTAX HwIplpmGlobalStatsEntry
			MAX-ACCESS not-accessible
			STATUS current
			DESCRIPTION
				"IPLPM global loss measure configuration information."
			INDEX { hwIplpmGlobalPeriodHigh, hwIplpmGlobalPeriodLow }
			::= { hwIplpmGlobalStatsTable 1 }
		
		HwIplpmGlobalStatsEntry ::=
			SEQUENCE { 
				hwIplpmGlobalPeriodHigh
					Unsigned32,
				hwIplpmGlobalPeriodLow
					Unsigned32,
				hwIplpmGlobalLossStatsErrInfo
					HWIplpmLossStatsErrorInfo,
				hwIplpmGlobalPeriodClock
					OCTET STRING,
				hwIplpmGlobalLossPkts
					Counter64,
				hwIplpmGlobalLossRatio
					Integer32
			 }

		-- 1.3.6.1.4.1.2011.5.25.328.1.2.3.1.1
		hwIplpmGlobalPeriodHigh OBJECT-TYPE
			SYNTAX Unsigned32
			MAX-ACCESS not-accessible
			STATUS current
			DESCRIPTION
				"The high period number of global loss statistics."
			::= { hwIplpmGlobalStatsEntry 1 }
		
		-- 1.3.6.1.4.1.2011.5.25.328.1.2.3.1.2
		hwIplpmGlobalPeriodLow OBJECT-TYPE
			SYNTAX Unsigned32
			MAX-ACCESS not-accessible
			STATUS current
			DESCRIPTION
				"The low period number of global loss statistics."
			::= { hwIplpmGlobalStatsEntry 2 }
		
		-- 1.3.6.1.4.1.2011.5.25.328.1.2.3.1.3
		hwIplpmGlobalLossStatsErrInfo OBJECT-TYPE
			SYNTAX HWIplpmLossStatsErrorInfo
			MAX-ACCESS read-only
			STATUS current
			DESCRIPTION
				"Error information of global loss statistics."
			::= { hwIplpmGlobalStatsEntry 3 }
		
		-- 1.3.6.1.4.1.2011.5.25.328.1.2.3.1.4
		hwIplpmGlobalPeriodClock OBJECT-TYPE
			SYNTAX OCTET STRING (SIZE (0..32))
			MAX-ACCESS read-only
			STATUS current
			DESCRIPTION
				"The string object indicates the time and data."
			::= { hwIplpmGlobalStatsEntry 4 }
		
		-- 1.3.6.1.4.1.2011.5.25.328.1.2.3.1.5
		hwIplpmGlobalLossPkts OBJECT-TYPE
			SYNTAX Counter64
			MAX-ACCESS read-only
			STATUS current
			DESCRIPTION
				"The object indicates the number of loss packets for global loss measure."
			::= { hwIplpmGlobalStatsEntry 5 }
		
		-- 1.3.6.1.4.1.2011.5.25.328.1.2.3.1.6
		hwIplpmGlobalLossRatio OBJECT-TYPE
			SYNTAX Integer32
			MAX-ACCESS read-only
			STATUS current
			DESCRIPTION
				"The object indicates the ratio of loss packets for global loss measure."
			::= { hwIplpmGlobalStatsEntry 6 }
		
		-- 1.3.6.1.4.1.2011.5.25.328.1.2.4
		hwIplpmLinkPeriodNoTable OBJECT-TYPE
			SYNTAX SEQUENCE OF HwIplpmLinkPeriodNoEntry
			MAX-ACCESS not-accessible
			STATUS current
			DESCRIPTION
				"The table contains link loss period number information."
			::= { hwIplpmStatistics 4 }
		
		-- 1.3.6.1.4.1.2011.5.25.328.1.2.4.1
		hwIplpmLinkPeriodNoEntry OBJECT-TYPE
			SYNTAX HwIplpmLinkPeriodNoEntry
			MAX-ACCESS not-accessible
			STATUS current
			DESCRIPTION
				"The table contains link loss period number information."
			INDEX { hwIplpmIntfIfIndex }
			::= { hwIplpmLinkPeriodNoTable 1 }
		
		HwIplpmLinkPeriodNoEntry ::=
			SEQUENCE { 
				hwIplpmLinkLatestPeriodNo
					Counter64,
				hwIplpmLinkLatestHisRecordNo
					Integer32
			 }

		-- 1.3.6.1.4.1.2011.5.25.328.1.2.4.1.1
		hwIplpmLinkLatestPeriodNo OBJECT-TYPE
			SYNTAX Counter64
			MAX-ACCESS read-only
			STATUS current
			DESCRIPTION
				"The object identifies the latest period number of a link loss measure instance."
			::= { hwIplpmLinkPeriodNoEntry 1 }
		
		-- 1.3.6.1.4.1.2011.5.25.328.1.2.4.1.2
		hwIplpmLinkLatestHisRecordNo OBJECT-TYPE
			SYNTAX Integer32
			MAX-ACCESS read-only
			STATUS current
			DESCRIPTION
				"The object identifies the latest history record number of a link loss measure instance. The value of -1 means it has not created history record."
			::= { hwIplpmLinkPeriodNoEntry 2 }
		
		-- 1.3.6.1.4.1.2011.5.25.328.1.2.5
		hwIplpmLinkLossStatsTable OBJECT-TYPE
			SYNTAX SEQUENCE OF HwIplpmLinkLossStatsEntry
			MAX-ACCESS not-accessible
			STATUS current
			DESCRIPTION
				"The table contains link loss measure information."
			::= { hwIplpmStatistics 5 }
		
		-- 1.3.6.1.4.1.2011.5.25.328.1.2.5.1
		hwIplpmLinkLossStatsEntry OBJECT-TYPE
			SYNTAX HwIplpmLinkLossStatsEntry
			MAX-ACCESS not-accessible
			STATUS current
			DESCRIPTION
				"IPLPM link loss measure statistics."
			INDEX { hwIplpmIntfIfIndex, hwIplpmLinkPeriodHigh, hwIplpmLinkPeriodLow }
			::= { hwIplpmLinkLossStatsTable 1 }
		
		HwIplpmLinkLossStatsEntry ::=
			SEQUENCE { 
				hwIplpmLinkPeriodHigh
					Unsigned32,
				hwIplpmLinkPeriodLow
					Unsigned32,
				hwIplpmLinkLossStatsErrInfo
					HWIplpmLossStatsErrorInfo,
				hwIplpmLinkPeriodClock
					OCTET STRING,
				hwIplpmLinkForwardLossPkts
					Counter64,
				hwIplpmLinkForwardLossRatio
					Integer32,
				hwIplpmLinkBackwardLossPkts
					Counter64,
				hwIplpmLinkBackwardLossRatio
					Integer32
			 }

		-- 1.3.6.1.4.1.2011.5.25.328.1.2.5.1.1
		hwIplpmLinkPeriodHigh OBJECT-TYPE
			SYNTAX Unsigned32
			MAX-ACCESS not-accessible
			STATUS current
			DESCRIPTION
				"The high period number of a link loss statistics."
			::= { hwIplpmLinkLossStatsEntry 1 }
		
		-- 1.3.6.1.4.1.2011.5.25.328.1.2.5.1.2
		hwIplpmLinkPeriodLow OBJECT-TYPE
			SYNTAX Unsigned32
			MAX-ACCESS not-accessible
			STATUS current
			DESCRIPTION
				"The low period number of a link loss statistics."
			::= { hwIplpmLinkLossStatsEntry 2 }
		
		-- 1.3.6.1.4.1.2011.5.25.328.1.2.5.1.3
		hwIplpmLinkLossStatsErrInfo OBJECT-TYPE
			SYNTAX HWIplpmLossStatsErrorInfo
			MAX-ACCESS read-only
			STATUS current
			DESCRIPTION
				"Error information of a link loss statistics."
			::= { hwIplpmLinkLossStatsEntry 3 }
		
		-- 1.3.6.1.4.1.2011.5.25.328.1.2.5.1.4
		hwIplpmLinkPeriodClock OBJECT-TYPE
			SYNTAX OCTET STRING (SIZE (0..32))
			MAX-ACCESS read-only
			STATUS current
			DESCRIPTION
				"The string object indicates the time and data for a link loss measure."
			::= { hwIplpmLinkLossStatsEntry 4 }
		
		-- 1.3.6.1.4.1.2011.5.25.328.1.2.5.1.5
		hwIplpmLinkForwardLossPkts OBJECT-TYPE
			SYNTAX Counter64
			MAX-ACCESS read-only
			STATUS current
			DESCRIPTION
				"The object indicates the number of forward loss packets for link loss measure."
			::= { hwIplpmLinkLossStatsEntry 5 }
		
		-- 1.3.6.1.4.1.2011.5.25.328.1.2.5.1.6
		hwIplpmLinkForwardLossRatio OBJECT-TYPE
			SYNTAX Integer32
			MAX-ACCESS read-only
			STATUS current
			DESCRIPTION
				"The object indicates the ratio of forward loss packets for link loss measure."
			::= { hwIplpmLinkLossStatsEntry 6 }
		
		-- 1.3.6.1.4.1.2011.5.25.328.1.2.5.1.7
		hwIplpmLinkBackwardLossPkts OBJECT-TYPE
			SYNTAX Counter64
			MAX-ACCESS read-only
			STATUS current
			DESCRIPTION
				"The object indicates the number of backward loss packets for link loss measure."
			::= { hwIplpmLinkLossStatsEntry 7 }
		
		-- 1.3.6.1.4.1.2011.5.25.328.1.2.5.1.8
		hwIplpmLinkBackwardLossRatio OBJECT-TYPE
			SYNTAX Integer32
			MAX-ACCESS read-only
			STATUS current
			DESCRIPTION
				"The object indicates the ratio of backward loss packets for link loss measure."
			::= { hwIplpmLinkLossStatsEntry 8 }
		
		-- 1.3.6.1.4.1.2011.5.25.328.1.2.6
		hwIplpmPortQosQueStatsTable OBJECT-TYPE
			SYNTAX SEQUENCE OF HwIplpmPortQosQueStatsEntry
			MAX-ACCESS not-accessible
			STATUS current
			DESCRIPTION
				"The table contains loss measure information of qos queue."
			::= { hwIplpmStatistics 6 }
		
		-- 1.3.6.1.4.1.2011.5.25.328.1.2.6.1
		hwIplpmPortQosQueStatsEntry OBJECT-TYPE
			SYNTAX HwIplpmPortQosQueStatsEntry
			MAX-ACCESS not-accessible
			STATUS current
			DESCRIPTION
				"The table contains loss measure information of qos queue."
			INDEX { hwIplpmIntfIfIndex, hwIplpmLinkPeriodHigh, hwIplpmLinkPeriodLow }
			::= { hwIplpmPortQosQueStatsTable 1 }
		
		HwIplpmPortQosQueStatsEntry ::=
			SEQUENCE { 
				hwIplpmPortQosQ0LossRatio
					Integer32,
				hwIplpmPortQosQ1LossRatio
					Integer32,
				hwIplpmPortQosQ2LossRatio
					Integer32,
				hwIplpmPortQosQ3LossRatio
					Integer32,
				hwIplpmPortQosQ4LossRatio
					Integer32,
				hwIplpmPortQosQ5LossRatio
					Integer32,
				hwIplpmPortQosQ6LossRatio
					Integer32,
				hwIplpmPortQosQ7LossRatio
					Integer32,
				hwIplpmPortUserQueLossRatio
					Integer32
			 }

		-- 1.3.6.1.4.1.2011.5.25.328.1.2.6.1.1
		hwIplpmPortQosQ0LossRatio OBJECT-TYPE
			SYNTAX Integer32
			MAX-ACCESS read-only
			STATUS current
			DESCRIPTION
				"The object indicates the loss ratio of qos queue 0."
			::= { hwIplpmPortQosQueStatsEntry 1 }
		
		-- 1.3.6.1.4.1.2011.5.25.328.1.2.6.1.2
		hwIplpmPortQosQ1LossRatio OBJECT-TYPE
			SYNTAX Integer32
			MAX-ACCESS read-only
			STATUS current
			DESCRIPTION
				"The object indicates the loss ratio of qos queue 1."
			::= { hwIplpmPortQosQueStatsEntry 2 }
		
		-- 1.3.6.1.4.1.2011.5.25.328.1.2.6.1.3
		hwIplpmPortQosQ2LossRatio OBJECT-TYPE
			SYNTAX Integer32
			MAX-ACCESS read-only
			STATUS current
			DESCRIPTION
				"The object indicates the loss ratio of qos queue 2."
			::= { hwIplpmPortQosQueStatsEntry 3 }
		
		-- 1.3.6.1.4.1.2011.5.25.328.1.2.6.1.4
		hwIplpmPortQosQ3LossRatio OBJECT-TYPE
			SYNTAX Integer32
			MAX-ACCESS read-only
			STATUS current
			DESCRIPTION
				"The object indicates the loss ratio of qos queue 3."
			::= { hwIplpmPortQosQueStatsEntry 4 }
		
		-- 1.3.6.1.4.1.2011.5.25.328.1.2.6.1.5
		hwIplpmPortQosQ4LossRatio OBJECT-TYPE
			SYNTAX Integer32
			MAX-ACCESS read-only
			STATUS current
			DESCRIPTION
				"The object indicates the loss ratio of qos queue 4."
			::= { hwIplpmPortQosQueStatsEntry 5 }
		
		-- 1.3.6.1.4.1.2011.5.25.328.1.2.6.1.6
		hwIplpmPortQosQ5LossRatio OBJECT-TYPE
			SYNTAX Integer32
			MAX-ACCESS read-only
			STATUS current
			DESCRIPTION
				"The object indicates the loss ratio of qos queue 5."
			::= { hwIplpmPortQosQueStatsEntry 6 }
		
		-- 1.3.6.1.4.1.2011.5.25.328.1.2.6.1.7
		hwIplpmPortQosQ6LossRatio OBJECT-TYPE
			SYNTAX Integer32
			MAX-ACCESS read-only
			STATUS current
			DESCRIPTION
				"The object indicates the loss ratio of qos queue 6."
			::= { hwIplpmPortQosQueStatsEntry 7 }
		
		-- 1.3.6.1.4.1.2011.5.25.328.1.2.6.1.8
		hwIplpmPortQosQ7LossRatio OBJECT-TYPE
			SYNTAX Integer32
			MAX-ACCESS read-only
			STATUS current
			DESCRIPTION
				"The object indicates the loss ratio of qos queue 7."
			::= { hwIplpmPortQosQueStatsEntry 8 }
		
		-- 1.3.6.1.4.1.2011.5.25.328.1.2.6.1.9
		hwIplpmPortUserQueLossRatio OBJECT-TYPE
			SYNTAX Integer32
			MAX-ACCESS read-only
			STATUS current
			DESCRIPTION
				"The object indicates the loss ratio of user queue."
			::= { hwIplpmPortQosQueStatsEntry 9 }
		
		-- 1.3.6.1.4.1.2011.5.25.328.1.2.7
		hwIplpmPortFlowStatsTable OBJECT-TYPE
			SYNTAX SEQUENCE OF HwIplpmPortFlowStatsEntry
			MAX-ACCESS not-accessible
			STATUS current
			DESCRIPTION
				"The table contains loss measure information of port."
			::= { hwIplpmStatistics 7 }
		
		-- 1.3.6.1.4.1.2011.5.25.328.1.2.7.1
		hwIplpmPortFlowStatsEntry OBJECT-TYPE
			SYNTAX HwIplpmPortFlowStatsEntry
			MAX-ACCESS not-accessible
			STATUS current
			DESCRIPTION
				"The table contains loss measure information of port."
			INDEX { hwIplpmIntfIfIndex, hwIplpmLinkPeriodHigh, hwIplpmLinkPeriodLow }
			::= { hwIplpmPortFlowStatsTable 1 }
		
		HwIplpmPortFlowStatsEntry ::=
			SEQUENCE { 
				hwIplpmPortInputLossRatio
					Integer32,
				hwIplpmPortOutputLossRatio
					Integer32
			 }

		-- 1.3.6.1.4.1.2011.5.25.328.1.2.7.1.1
		hwIplpmPortInputLossRatio OBJECT-TYPE
			SYNTAX Integer32
			MAX-ACCESS read-only
			STATUS current
			DESCRIPTION
				"The object indicates the input loss ratio of port."
			::= { hwIplpmPortFlowStatsEntry 1 }
		
		-- 1.3.6.1.4.1.2011.5.25.328.1.2.7.1.2
		hwIplpmPortOutputLossRatio OBJECT-TYPE
			SYNTAX Integer32
			MAX-ACCESS read-only
			STATUS current
			DESCRIPTION
				"The object indicates the output loss ratio of port."
			::= { hwIplpmPortFlowStatsEntry 2 }
		
		-- 1.3.6.1.4.1.2011.5.25.328.1.3
		hwIplpmHistoryRecord OBJECT IDENTIFIER ::= { hwIplpmObjects 3 }
		
		-- 1.3.6.1.4.1.2011.5.25.328.1.3.1
		hwIplpmGlobalHisRecordTable OBJECT-TYPE
			SYNTAX SEQUENCE OF HwIplpmGlobalHisRecordEntry
			MAX-ACCESS not-accessible
			STATUS current
			DESCRIPTION
				"The table contains global loss measure history record."
			::= { hwIplpmHistoryRecord 1 }
		
		-- 1.3.6.1.4.1.2011.5.25.328.1.3.1.1
		hwIplpmGlobalHisRecordEntry OBJECT-TYPE
			SYNTAX HwIplpmGlobalHisRecordEntry
			MAX-ACCESS not-accessible
			STATUS current
			DESCRIPTION
				"IPLPM global loss measure history record."
			INDEX { hwIplpmGlobalHisRecordNo }
			::= { hwIplpmGlobalHisRecordTable 1 }
		
		HwIplpmGlobalHisRecordEntry ::=
			SEQUENCE { 
				hwIplpmGlobalHisRecordNo
					Integer32,
				hwIplpmGlobalLossRatioMax
					Integer32,
				hwIplpmGlobalLossRatioMin
					Integer32,
				hwIplpmGlobalTotalLossPkts
					Counter64,
				hwIplpmGlobalTotalRecvPkts
					Counter64,
				hwIplpmGlobalHisRecStartTime
					OCTET STRING,
				hwIplpmGlobalHisRecEndTime
					OCTET STRING,
				hwIplpmGlobalValidStatDataNum
					Integer32
			 }

		-- 1.3.6.1.4.1.2011.5.25.328.1.3.1.1.1
		hwIplpmGlobalHisRecordNo OBJECT-TYPE
			SYNTAX Integer32 (1..2147483647)
			MAX-ACCESS not-accessible
			STATUS current
			DESCRIPTION
				"The history record number of global loss measure."
			::= { hwIplpmGlobalHisRecordEntry 1 }
		
		-- 1.3.6.1.4.1.2011.5.25.328.1.3.1.1.2
		hwIplpmGlobalLossRatioMax OBJECT-TYPE
			SYNTAX Integer32
			MAX-ACCESS read-only
			STATUS current
			DESCRIPTION
				"The maximum loss ratio of global loss measure during a time."
			::= { hwIplpmGlobalHisRecordEntry 2 }
		
		-- 1.3.6.1.4.1.2011.5.25.328.1.3.1.1.3
		hwIplpmGlobalLossRatioMin OBJECT-TYPE
			SYNTAX Integer32
			MAX-ACCESS read-only
			STATUS current
			DESCRIPTION
				"The minimum loss ratio of global loss measure during a time."
			::= { hwIplpmGlobalHisRecordEntry 3 }
		
		-- 1.3.6.1.4.1.2011.5.25.328.1.3.1.1.4
		hwIplpmGlobalTotalLossPkts OBJECT-TYPE
			SYNTAX Counter64
			MAX-ACCESS read-only
			STATUS current
			DESCRIPTION
				"The loss packets number of global loss measure during a time."
			::= { hwIplpmGlobalHisRecordEntry 4 }
		
		-- 1.3.6.1.4.1.2011.5.25.328.1.3.1.1.5
		hwIplpmGlobalTotalRecvPkts OBJECT-TYPE
			SYNTAX Counter64
			MAX-ACCESS read-only
			STATUS current
			DESCRIPTION
				"The receive packets number of global loss measure during a time."
			::= { hwIplpmGlobalHisRecordEntry 5 }
		
		-- 1.3.6.1.4.1.2011.5.25.328.1.3.1.1.6
		hwIplpmGlobalHisRecStartTime OBJECT-TYPE
			SYNTAX OCTET STRING (SIZE (0..32))
			MAX-ACCESS read-only
			STATUS current
			DESCRIPTION
				"The start time of a global loss history record."
			::= { hwIplpmGlobalHisRecordEntry 6 }
		
		-- 1.3.6.1.4.1.2011.5.25.328.1.3.1.1.7
		hwIplpmGlobalHisRecEndTime OBJECT-TYPE
			SYNTAX OCTET STRING (SIZE (0..32))
			MAX-ACCESS read-only
			STATUS current
			DESCRIPTION
				"The end time of a global loss history record."
			::= { hwIplpmGlobalHisRecordEntry 7 }
		
		-- 1.3.6.1.4.1.2011.5.25.328.1.3.1.1.8
		hwIplpmGlobalValidStatDataNum OBJECT-TYPE
			SYNTAX Integer32
			MAX-ACCESS read-only
			STATUS current
			DESCRIPTION
				"The valid statistics number of a global loss history record."
			::= { hwIplpmGlobalHisRecordEntry 8 }
		
		-- 1.3.6.1.4.1.2011.5.25.328.1.3.2
		hwIplpmLinkHisRecordEntryTable OBJECT-TYPE
			SYNTAX SEQUENCE OF HwIplpmLinkHisRecordEntryEntry
			MAX-ACCESS not-accessible
			STATUS current
			DESCRIPTION
				"The table contains link loss measure history record."
			::= { hwIplpmHistoryRecord 2 }
		
		-- 1.3.6.1.4.1.2011.5.25.328.1.3.2.1
		hwIplpmLinkHisRecordEntryEntry OBJECT-TYPE
			SYNTAX HwIplpmLinkHisRecordEntryEntry
			MAX-ACCESS not-accessible
			STATUS current
			DESCRIPTION
				"IPLPM link loss measure history record."
			INDEX { hwIplpmIntfIfIndex, hwIplpmLinkHisRecordNo }
			::= { hwIplpmLinkHisRecordEntryTable 1 }
		
		HwIplpmLinkHisRecordEntryEntry ::=
			SEQUENCE { 
				hwIplpmLinkHisRecordNo
					Integer32,
				hwIplpmLinkForwardLossRatioMax
					Integer32,
				hwIplpmLinkForwardLossRatioMin
					Integer32,
				hwIplpmLinkForwardTotalLossPkts
					Counter64,
				hwIplpmLinkForwardTotalRecvPkts
					Counter64,
				hwIplpmLinkBackwardLossRatioMax
					Integer32,
				hwIplpmLinkBackwardLossRatioMin
					Integer32,
				hwIplpmLinkBackwardTotalLossPkts
					Counter64,
				hwIplpmLinkBackwardTotalRecvPkts
					Counter64,
				hwIplpmLinkHisRecordStartTime
					OCTET STRING,
				hwIplpmLinkHisRecordEndTime
					OCTET STRING,
				hwIplpmLinkValidStatDataNum
					Integer32
			 }

		-- 1.3.6.1.4.1.2011.5.25.328.1.3.2.1.1
		hwIplpmLinkHisRecordNo OBJECT-TYPE
			SYNTAX Integer32 (1..2147483647)
			MAX-ACCESS not-accessible
			STATUS current
			DESCRIPTION
				"The history record number of link loss measure."
			::= { hwIplpmLinkHisRecordEntryEntry 1 }
		
		-- 1.3.6.1.4.1.2011.5.25.328.1.3.2.1.2
		hwIplpmLinkForwardLossRatioMax OBJECT-TYPE
			SYNTAX Integer32
			MAX-ACCESS read-only
			STATUS current
			DESCRIPTION
				"The maximum loss ratio of link forward measure during a time."
			::= { hwIplpmLinkHisRecordEntryEntry 2 }
		
		-- 1.3.6.1.4.1.2011.5.25.328.1.3.2.1.3
		hwIplpmLinkForwardLossRatioMin OBJECT-TYPE
			SYNTAX Integer32
			MAX-ACCESS read-only
			STATUS current
			DESCRIPTION
				"The minimum loss ratio of link forward measure during a time."
			::= { hwIplpmLinkHisRecordEntryEntry 3 }
		
		-- 1.3.6.1.4.1.2011.5.25.328.1.3.2.1.4
		hwIplpmLinkForwardTotalLossPkts OBJECT-TYPE
			SYNTAX Counter64
			MAX-ACCESS read-only
			STATUS current
			DESCRIPTION
				"The loss packets number of link forward measure during a time."
			::= { hwIplpmLinkHisRecordEntryEntry 4 }
		
		-- 1.3.6.1.4.1.2011.5.25.328.1.3.2.1.5
		hwIplpmLinkForwardTotalRecvPkts OBJECT-TYPE
			SYNTAX Counter64
			MAX-ACCESS read-only
			STATUS current
			DESCRIPTION
				"The received packets number of link forward measure during a time."
			::= { hwIplpmLinkHisRecordEntryEntry 5 }
		
		-- 1.3.6.1.4.1.2011.5.25.328.1.3.2.1.6
		hwIplpmLinkBackwardLossRatioMax OBJECT-TYPE
			SYNTAX Integer32
			MAX-ACCESS read-only
			STATUS current
			DESCRIPTION
				"The maximum loss ratio of link backward measure during a time."
			::= { hwIplpmLinkHisRecordEntryEntry 6 }
		
		-- 1.3.6.1.4.1.2011.5.25.328.1.3.2.1.7
		hwIplpmLinkBackwardLossRatioMin OBJECT-TYPE
			SYNTAX Integer32
			MAX-ACCESS read-only
			STATUS current
			DESCRIPTION
				"The minimum loss ratio of link backward measure during a time."
			::= { hwIplpmLinkHisRecordEntryEntry 7 }
		
		-- 1.3.6.1.4.1.2011.5.25.328.1.3.2.1.8
		hwIplpmLinkBackwardTotalLossPkts OBJECT-TYPE
			SYNTAX Counter64
			MAX-ACCESS read-only
			STATUS current
			DESCRIPTION
				"The loss packets number of link backward measure during a time."
			::= { hwIplpmLinkHisRecordEntryEntry 8 }
		
		-- 1.3.6.1.4.1.2011.5.25.328.1.3.2.1.9
		hwIplpmLinkBackwardTotalRecvPkts OBJECT-TYPE
			SYNTAX Counter64
			MAX-ACCESS read-only
			STATUS current
			DESCRIPTION
				"The received packets number of link backward measure during a time."
			::= { hwIplpmLinkHisRecordEntryEntry 9 }
		
		-- 1.3.6.1.4.1.2011.5.25.328.1.3.2.1.10
		hwIplpmLinkHisRecordStartTime OBJECT-TYPE
			SYNTAX OCTET STRING (SIZE (0..32))
			MAX-ACCESS read-only
			STATUS current
			DESCRIPTION
				"The start time of a link loss history record."
			::= { hwIplpmLinkHisRecordEntryEntry 10 }
		
		-- 1.3.6.1.4.1.2011.5.25.328.1.3.2.1.11
		hwIplpmLinkHisRecordEndTime OBJECT-TYPE
			SYNTAX OCTET STRING (SIZE (0..32))
			MAX-ACCESS read-only
			STATUS current
			DESCRIPTION
				"The end time of a link loss history record."
			::= { hwIplpmLinkHisRecordEntryEntry 11 }
		
		-- 1.3.6.1.4.1.2011.5.25.328.1.3.2.1.12
		hwIplpmLinkValidStatDataNum OBJECT-TYPE
			SYNTAX Integer32
			MAX-ACCESS read-only
			STATUS current
			DESCRIPTION
				"The valid statistics number of a link loss history record."
			::= { hwIplpmLinkHisRecordEntryEntry 12 }
		
		-- 1.3.6.1.4.1.2011.5.25.328.1.4
		hwIplpmFwdPathSearch OBJECT IDENTIFIER ::= { hwIplpmObjects 4 }
		
		-- 1.3.6.1.4.1.2011.5.25.328.1.4.1
		hwIplpmGateWaySearchTable OBJECT-TYPE
			SYNTAX SEQUENCE OF HwIplpmGateWaySearchEntry
			MAX-ACCESS not-accessible
			STATUS current
			DESCRIPTION
				"This table contains gateway information which found by IP address and mask."
			::= { hwIplpmFwdPathSearch 1 }
		
		-- 1.3.6.1.4.1.2011.5.25.328.1.4.1.1
		hwIplpmGateWaySearchEntry OBJECT-TYPE
			SYNTAX HwIplpmGateWaySearchEntry
			MAX-ACCESS not-accessible
			STATUS current
			DESCRIPTION
				"This entry contains gateway information which found by IP address and mask."
			INDEX { hwIplpmNetAddress, hwIplpmNetMask }
			::= { hwIplpmGateWaySearchTable 1 }
		
		HwIplpmGateWaySearchEntry ::=
			SEQUENCE { 
				hwIplpmNetAddress
					IpAddress,
				hwIplpmNetMask
					IpAddress,
				hwIplpmNetIfIndex
					Integer32,
				hwIplpmNetIfName
					OCTET STRING,
				hwIplpmNetIfMacAddress
					OCTET STRING,
				hwIplpmNetIfAddress
					IpAddress,
				hwIplpmNetIfMask
					IpAddress,
				hwIplpmNetIfVpnName
					OCTET STRING,
				hwIplpmNetIfVrf
					Integer32,
				hwIplpmNetIfVlan
					Integer32,
				hwIplpmNetSystemMac
					OCTET STRING,
				hwIplpmNetIfVrrpVip
					IpAddress,
				hwIplpmNetIfVrrpMac
					OCTET STRING,
				hwIplpmNetIfVrrpState
					INTEGER,
				hwIplpmNetIfHostAddress
					IpAddress
			 }

		-- 1.3.6.1.4.1.2011.5.25.328.1.4.1.1.1
		hwIplpmNetAddress OBJECT-TYPE
			SYNTAX IpAddress
			MAX-ACCESS not-accessible
			STATUS current
			DESCRIPTION
				"The IP address which used to find gateway information."
			::= { hwIplpmGateWaySearchEntry 1 }
		
		-- 1.3.6.1.4.1.2011.5.25.328.1.4.1.1.2
		hwIplpmNetMask OBJECT-TYPE
			SYNTAX IpAddress
			MAX-ACCESS not-accessible
			STATUS current
			DESCRIPTION
				"The mask which used to find gateway information."
			::= { hwIplpmGateWaySearchEntry 2 }
		
		-- 1.3.6.1.4.1.2011.5.25.328.1.4.1.1.3
		hwIplpmNetIfIndex OBJECT-TYPE
			SYNTAX Integer32
			MAX-ACCESS read-only
			STATUS current
			DESCRIPTION
				"The interface index to which this entry pertains."
			::= { hwIplpmGateWaySearchEntry 3 }
		
		-- 1.3.6.1.4.1.2011.5.25.328.1.4.1.1.4
		hwIplpmNetIfName OBJECT-TYPE
			SYNTAX OCTET STRING (SIZE (0..64))
			MAX-ACCESS read-only
			STATUS current
			DESCRIPTION
				"The interface name to which this entry pertains."
			::= { hwIplpmGateWaySearchEntry 4 }
		
		-- 1.3.6.1.4.1.2011.5.25.328.1.4.1.1.5
		hwIplpmNetIfMacAddress OBJECT-TYPE
			SYNTAX OCTET STRING (SIZE (0..32))
			MAX-ACCESS read-only
			STATUS current
			DESCRIPTION
				"The mac address of interface to which this entry pertains."
			::= { hwIplpmGateWaySearchEntry 5 }
		
		-- 1.3.6.1.4.1.2011.5.25.328.1.4.1.1.6
		hwIplpmNetIfAddress OBJECT-TYPE
			SYNTAX IpAddress
			MAX-ACCESS read-only
			STATUS current
			DESCRIPTION
				"The IP address of interface to which this entry pertains."
			::= { hwIplpmGateWaySearchEntry 6 }
		
		-- 1.3.6.1.4.1.2011.5.25.328.1.4.1.1.7
		hwIplpmNetIfMask OBJECT-TYPE
			SYNTAX IpAddress
			MAX-ACCESS read-only
			STATUS current
			DESCRIPTION
				"The mask of interface to which this entry pertains."
			::= { hwIplpmGateWaySearchEntry 7 }
		
		-- 1.3.6.1.4.1.2011.5.25.328.1.4.1.1.8
		hwIplpmNetIfVpnName OBJECT-TYPE
			SYNTAX OCTET STRING (SIZE (0..32))
			MAX-ACCESS read-only
			STATUS current
			DESCRIPTION
				"The vpn name of interface to which this entry pertains."
			::= { hwIplpmGateWaySearchEntry 8 }
		
		-- 1.3.6.1.4.1.2011.5.25.328.1.4.1.1.9
		hwIplpmNetIfVrf OBJECT-TYPE
			SYNTAX Integer32
			MAX-ACCESS read-only
			STATUS current
			DESCRIPTION
				"The vpn instance ID of interface to which this entry pertains."
			::= { hwIplpmGateWaySearchEntry 9 }
		
		-- 1.3.6.1.4.1.2011.5.25.328.1.4.1.1.10
		hwIplpmNetIfVlan OBJECT-TYPE
			SYNTAX Integer32
			MAX-ACCESS read-only
			STATUS current
			DESCRIPTION
				"The vlan of interface to which this entry pertains."
			::= { hwIplpmGateWaySearchEntry 10 }
		
		-- 1.3.6.1.4.1.2011.5.25.328.1.4.1.1.11
		hwIplpmNetSystemMac OBJECT-TYPE
			SYNTAX OCTET STRING (SIZE (0..32))
			MAX-ACCESS read-only
			STATUS current
			DESCRIPTION
				"The system mac address of the device."
			::= { hwIplpmGateWaySearchEntry 11 }
		
		-- 1.3.6.1.4.1.2011.5.25.328.1.4.1.1.12
		hwIplpmNetIfVrrpVip OBJECT-TYPE
			SYNTAX IpAddress
			MAX-ACCESS read-only
			STATUS current
			DESCRIPTION
				"The vrrp virtual IP address to which this entry pertains."
			::= { hwIplpmGateWaySearchEntry 12 }
		
		-- 1.3.6.1.4.1.2011.5.25.328.1.4.1.1.13
		hwIplpmNetIfVrrpMac OBJECT-TYPE
			SYNTAX OCTET STRING (SIZE (0..32))
			MAX-ACCESS read-only
			STATUS current
			DESCRIPTION
				"The vrrp virtual mac address to which this entry pertains."
			::= { hwIplpmGateWaySearchEntry 13 }
		
		-- 1.3.6.1.4.1.2011.5.25.328.1.4.1.1.14
		hwIplpmNetIfVrrpState OBJECT-TYPE
			SYNTAX INTEGER
				{
				initialize(1),
				backup(2),
				master(3),
				notexist(255)
				}
			MAX-ACCESS read-only
			STATUS current
			DESCRIPTION
				"The vrrp state to which this entry pertains."
			::= { hwIplpmGateWaySearchEntry 14 }
		
		-- 1.3.6.1.4.1.2011.5.25.328.1.4.1.1.15
		hwIplpmNetIfHostAddress OBJECT-TYPE
			SYNTAX IpAddress
			MAX-ACCESS read-only
			STATUS current
			DESCRIPTION
				"The next host IP address to which this entry pertains."
			::= { hwIplpmGateWaySearchEntry 15 }
		
		-- 1.3.6.1.4.1.2011.5.25.328.1.4.2
		hwIplpmHostInfoSearchTable OBJECT-TYPE
			SYNTAX SEQUENCE OF HwIplpmHostInfoSearchEntry
			MAX-ACCESS not-accessible
			STATUS current
			DESCRIPTION
				"This table contains host information which found by nexthop IP address and vpn instance ID."
			::= { hwIplpmFwdPathSearch 2 }
		
		-- 1.3.6.1.4.1.2011.5.25.328.1.4.2.1
		hwIplpmHostInfoSearchEntry OBJECT-TYPE
			SYNTAX HwIplpmHostInfoSearchEntry
			MAX-ACCESS not-accessible
			STATUS current
			DESCRIPTION
				"This entry contains host information which found by nexthop IP address and vpn instance ID."
			INDEX { hwIplpmHostIpAddress, hwIplpmHostVrf }
			::= { hwIplpmHostInfoSearchTable 1 }
		
		HwIplpmHostInfoSearchEntry ::=
			SEQUENCE { 
				hwIplpmHostIpAddress
					IpAddress,
				hwIplpmHostVrf
					Integer32,
				hwIplpmHostIfIndex
					Integer32,
				hwIplpmHostIfName
					OCTET STRING,
				hwIplpmHostMacAddress
					OCTET STRING,
				hwIplpmHostVlan
					Integer32,
				hwIplpmHostCeVlan
					Integer32
			 }

		-- 1.3.6.1.4.1.2011.5.25.328.1.4.2.1.1
		hwIplpmHostIpAddress OBJECT-TYPE
			SYNTAX IpAddress
			MAX-ACCESS not-accessible
			STATUS current
			DESCRIPTION
				"The IP address to which this entry pertains."
			::= { hwIplpmHostInfoSearchEntry 1 }
		
		-- 1.3.6.1.4.1.2011.5.25.328.1.4.2.1.2
		hwIplpmHostVrf OBJECT-TYPE
			SYNTAX Integer32
			MAX-ACCESS not-accessible
			STATUS current
			DESCRIPTION
				"The vpn instance ID to which this entry pertains."
			::= { hwIplpmHostInfoSearchEntry 2 }
		
		-- 1.3.6.1.4.1.2011.5.25.328.1.4.2.1.3
		hwIplpmHostIfIndex OBJECT-TYPE
			SYNTAX Integer32
			MAX-ACCESS read-only
			STATUS current
			DESCRIPTION
				"The interface index to which this entry pertains."
			::= { hwIplpmHostInfoSearchEntry 3 }
		
		-- 1.3.6.1.4.1.2011.5.25.328.1.4.2.1.4
		hwIplpmHostIfName OBJECT-TYPE
			SYNTAX OCTET STRING (SIZE (0..64))
			MAX-ACCESS read-only
			STATUS current
			DESCRIPTION
				"The interface name to which this entry pertains."
			::= { hwIplpmHostInfoSearchEntry 4 }
		
		-- 1.3.6.1.4.1.2011.5.25.328.1.4.2.1.5
		hwIplpmHostMacAddress OBJECT-TYPE
			SYNTAX OCTET STRING (SIZE (0..32))
			MAX-ACCESS read-only
			STATUS current
			DESCRIPTION
				"The mac address to which this entry pertains."
			::= { hwIplpmHostInfoSearchEntry 5 }
		
		-- 1.3.6.1.4.1.2011.5.25.328.1.4.2.1.6
		hwIplpmHostVlan OBJECT-TYPE
			SYNTAX Integer32
			MAX-ACCESS read-only
			STATUS current
			DESCRIPTION
				"The interface vlan to which this entry pertains."
			::= { hwIplpmHostInfoSearchEntry 6 }
		
		-- 1.3.6.1.4.1.2011.5.25.328.1.4.2.1.7
		hwIplpmHostCeVlan OBJECT-TYPE
			SYNTAX Integer32
			MAX-ACCESS read-only
			STATUS current
			DESCRIPTION
				"The interface ce-vlan to which this entry pertains."
			::= { hwIplpmHostInfoSearchEntry 7 }
		
		-- 1.3.6.1.4.1.2011.5.25.328.1.4.3
		hwIplpmLocalIpSearchTable OBJECT-TYPE
			SYNTAX SEQUENCE OF HwIplpmLocalIpSearchEntry
			MAX-ACCESS not-accessible
			STATUS current
			DESCRIPTION
				"This table contains local IP address information of this entity."
			::= { hwIplpmFwdPathSearch 3 }
		
		-- 1.3.6.1.4.1.2011.5.25.328.1.4.3.1
		hwIplpmLocalIpSearchEntry OBJECT-TYPE
			SYNTAX HwIplpmLocalIpSearchEntry
			MAX-ACCESS not-accessible
			STATUS current
			DESCRIPTION
				"This entry contains local IP address information of this entity."
			INDEX { hwIplpmLocalIpAddress }
			::= { hwIplpmLocalIpSearchTable 1 }
		
		HwIplpmLocalIpSearchEntry ::=
			SEQUENCE { 
				hwIplpmLocalIpAddress
					IpAddress,
				hwIplpmLocalIfIndex
					Integer32,
				hwIplpmLocalIfType
					INTEGER,
				hwIplpmLocalIfVrf
					Integer32,
				hwIplpmLocalPortList
					OCTET STRING
			 }

		-- 1.3.6.1.4.1.2011.5.25.328.1.4.3.1.1
		hwIplpmLocalIpAddress OBJECT-TYPE
			SYNTAX IpAddress
			MAX-ACCESS not-accessible
			STATUS current
			DESCRIPTION
				"The IP address to which this entry's addressing information pertains."
			::= { hwIplpmLocalIpSearchEntry 1 }
		
		-- 1.3.6.1.4.1.2011.5.25.328.1.4.3.1.2
		hwIplpmLocalIfIndex OBJECT-TYPE
			SYNTAX Integer32
			MAX-ACCESS read-only
			STATUS current
			DESCRIPTION
				"The interface index to which this entity's local IP address pertains."
			::= { hwIplpmLocalIpSearchEntry 2 }
		
		-- 1.3.6.1.4.1.2011.5.25.328.1.4.3.1.3
		hwIplpmLocalIfType OBJECT-TYPE
			SYNTAX INTEGER
				{
				ethernet(1),
				ethtrunk(2),
				vlanif(3),
				other(4)
				}
			MAX-ACCESS read-only
			STATUS current
			DESCRIPTION
				"The interface type to which this entity's local IP address pertains."
			::= { hwIplpmLocalIpSearchEntry 3 }
		
		-- 1.3.6.1.4.1.2011.5.25.328.1.4.3.1.4
		hwIplpmLocalIfVrf OBJECT-TYPE
			SYNTAX Integer32
			MAX-ACCESS read-only
			STATUS current
			DESCRIPTION
				"The vpn instance ID to which this entry's IP address binds."
			::= { hwIplpmLocalIpSearchEntry 4 }
		
		-- 1.3.6.1.4.1.2011.5.25.328.1.4.3.1.5
		hwIplpmLocalPortList OBJECT-TYPE
			SYNTAX OCTET STRING (SIZE (0..128))
			MAX-ACCESS read-only
			STATUS current
			DESCRIPTION
				"The interface index list to which this entity's local IP address pertains."
			::= { hwIplpmLocalIpSearchEntry 5 }
		
		-- 1.3.6.1.4.1.2011.5.25.328.1.4.4
		hwIplpmIpRouteSearchTable OBJECT-TYPE
			SYNTAX SEQUENCE OF HwIplpmIpRouteSearchEntry
			MAX-ACCESS not-accessible
			STATUS current
			DESCRIPTION
				"This table contains IP routing information which found by destination IP address and vpn instance ID."
			::= { hwIplpmFwdPathSearch 4 }
		
		-- 1.3.6.1.4.1.2011.5.25.328.1.4.4.1
		hwIplpmIpRouteSearchEntry OBJECT-TYPE
			SYNTAX HwIplpmIpRouteSearchEntry
			MAX-ACCESS not-accessible
			STATUS current
			DESCRIPTION
				"IP routing entry which found by destination IP address and vpn instance ID."
			INDEX { hwIplpmDestIpAddress, hwIplpmDestMask, hwIplpmDestVrf }
			::= { hwIplpmIpRouteSearchTable 1 }
		
		HwIplpmIpRouteSearchEntry ::=
			SEQUENCE { 
				hwIplpmDestIpAddress
					IpAddress,
				hwIplpmDestMask
					IpAddress,
				hwIplpmDestVrf
					Integer32,
				hwIplpmRouteDstAddr
					IpAddress,
				hwIplpmRouteDstMask
					IpAddress,
				hwIplpmRouteIfIndex
					Integer32,
				hwIplpmOutPortIfIndex
					Integer32
			 }

		-- 1.3.6.1.4.1.2011.5.25.328.1.4.4.1.1
		hwIplpmDestIpAddress OBJECT-TYPE
			SYNTAX IpAddress
			MAX-ACCESS not-accessible
			STATUS current
			DESCRIPTION
				"The destination IP address which used to search IP routing table."
			::= { hwIplpmIpRouteSearchEntry 1 }
		
		-- 1.3.6.1.4.1.2011.5.25.328.1.4.4.1.2
		hwIplpmDestMask OBJECT-TYPE
			SYNTAX IpAddress
			MAX-ACCESS not-accessible
			STATUS current
			DESCRIPTION
				"The destination mask which used to search IP routing table."
			::= { hwIplpmIpRouteSearchEntry 2 }
		
		-- 1.3.6.1.4.1.2011.5.25.328.1.4.4.1.3
		hwIplpmDestVrf OBJECT-TYPE
			SYNTAX Integer32
			MAX-ACCESS not-accessible
			STATUS current
			DESCRIPTION
				"The vpn instance ID which used to search IP routing table."
			::= { hwIplpmIpRouteSearchEntry 3 }
		
		-- 1.3.6.1.4.1.2011.5.25.328.1.4.4.1.4
		hwIplpmRouteDstAddr OBJECT-TYPE
			SYNTAX IpAddress
			MAX-ACCESS read-only
			STATUS current
			DESCRIPTION
				"The destination IP address to which this entry's information pertains."
			::= { hwIplpmIpRouteSearchEntry 4 }
		
		-- 1.3.6.1.4.1.2011.5.25.328.1.4.4.1.5
		hwIplpmRouteDstMask OBJECT-TYPE
			SYNTAX IpAddress
			MAX-ACCESS read-only
			STATUS current
			DESCRIPTION
				"The mask to which this entry's information pertains."
			::= { hwIplpmIpRouteSearchEntry 5 }
		
		-- 1.3.6.1.4.1.2011.5.25.328.1.4.4.1.6
		hwIplpmRouteIfIndex OBJECT-TYPE
			SYNTAX Integer32
			MAX-ACCESS read-only
			STATUS current
			DESCRIPTION
				"The logic interface ifindex to which this entry's information pertains."
			::= { hwIplpmIpRouteSearchEntry 6 }
		
		-- 1.3.6.1.4.1.2011.5.25.328.1.4.4.1.7
		hwIplpmOutPortIfIndex OBJECT-TYPE
			SYNTAX Integer32
			MAX-ACCESS read-only
			STATUS current
			DESCRIPTION
				"The physical interface ifindex to which this entry's information pertains."
			::= { hwIplpmIpRouteSearchEntry 7 }
		
		-- 1.3.6.1.4.1.2011.5.25.328.2
		hwIplpmTraps OBJECT IDENTIFIER ::= { hwIplpmMib 2 }
		
		-- 1.3.6.1.4.1.2011.5.25.328.2.1
		hwIplpmGlobalLossRatioExceed NOTIFICATION-TYPE
			OBJECTS { hwIplpmGlobalLossPkts, hwIplpmGlobalLossRatio, hwIplpmGlobalLatestPeriodNo }
			STATUS current
			DESCRIPTION 
				"A hwIplpmGlobalLossRatioExceed trap is sent when the global loss ratio 
				exceeds the uppper threshold in continuous five test intervals.
				"
			::= { hwIplpmTraps 1 }
		
		-- 1.3.6.1.4.1.2011.5.25.328.2.2
		hwIplpmGlobalLossRatioRecovery NOTIFICATION-TYPE
			OBJECTS { hwIplpmGlobalLossPkts, hwIplpmGlobalLossRatio, hwIplpmGlobalLatestPeriodNo }
			STATUS current
			DESCRIPTION 
				"A hwIplpmGlobalLossRatioRecovery trap is sent when the global loss ratio 
				is under the lower threshold in continuous five test intervals.
				"
			::= { hwIplpmTraps 2 }
		
		-- 1.3.6.1.4.1.2011.5.25.328.2.3
		hwIplpmLinkForwardLossRatioExceed NOTIFICATION-TYPE
			OBJECTS { hwIplpmLinkForwardLossPkts, hwIplpmLinkForwardLossRatio, hwIplpmPortQosQ0LossRatio, hwIplpmPortQosQ1LossRatio, hwIplpmPortQosQ2LossRatio, 
				hwIplpmPortQosQ3LossRatio, hwIplpmPortQosQ4LossRatio, hwIplpmPortQosQ5LossRatio, hwIplpmPortQosQ6LossRatio, hwIplpmPortQosQ7LossRatio, 
				hwIplpmPortUserQueLossRatio, hwIplpmPortOutputLossRatio, hwIplpmLinkLatestPeriodNo }
			STATUS current
			DESCRIPTION 
				"A hwIplpmLinkForwardLossRatioExceed trap is sent when the link forward loss ratio 
				exceeds the uppper threshold in continuous five test intervals.
				"
			::= { hwIplpmTraps 3 }
		
		-- 1.3.6.1.4.1.2011.5.25.328.2.4
		hwIplpmLinkForwardLossRatioRecovery NOTIFICATION-TYPE
			OBJECTS { hwIplpmLinkForwardLossPkts, hwIplpmLinkForwardLossRatio, hwIplpmLinkLatestPeriodNo }
			STATUS current
			DESCRIPTION 
				"A hwIplpmLinkForwardLossRatioRecovery trap is sent when the link forward loss ratio 
				is under the lower threshold in continuous five test intervals.
				"
			::= { hwIplpmTraps 4 }
		
		-- 1.3.6.1.4.1.2011.5.25.328.3
		hwIplpmConformance OBJECT IDENTIFIER ::= { hwIplpmMib 3 }
		
		-- 1.3.6.1.4.1.2011.5.25.328.3.1
		hwIplpmCompliances OBJECT IDENTIFIER ::= { hwIplpmConformance 1 }
		
		-- 1.3.6.1.4.1.2011.5.25.328.3.1.1
		hwIplpmCompliance MODULE-COMPLIANCE
			STATUS current
			DESCRIPTION 
				"The compliance statement for entities which implement the IPLPM MIB."
			MODULE -- this module
				MANDATORY-GROUPS { hwIplpmGlobalConfigGroup, hwIplpmInterfacelConfigGroup, hwIplpmStatisticsGroup, hwIplpmHistoryRecordGroup, hwIplpmTrapsGroup
					 }
			::= { hwIplpmCompliances 1 }
		
		-- 1.3.6.1.4.1.2011.5.25.328.3.3
		hwIplpmGroups OBJECT IDENTIFIER ::= { hwIplpmConformance 3 }
		
		-- 1.3.6.1.4.1.2011.5.25.328.3.3.1
		hwIplpmGlobalConfigGroup OBJECT-GROUP
			OBJECTS { hwIplpmLossMeasureColorFlag, hwIplpmLossMeasureInterval, hwIplpmLossMeasureEnable, hwIplpmIntfLossMeasureAlarmEnable }
			STATUS current
			DESCRIPTION 
				"The collection of objects which are used to configure the
				IPLPM global behavior.
				"
			::= { hwIplpmGroups 1 }
		
		-- 1.3.6.1.4.1.2011.5.25.328.3.3.2
		hwIplpmInterfacelConfigGroup OBJECT-GROUP
			OBJECTS { hwIplpmIntfConfigRowStatus, hwIplpmIntfInterval, hwIplpmIntfAuthKeyId, hwIplpmIntfAuthType, hwIplpmIntfAuthKey, 
				hwIplpmIntfLossMeasureEnable, hwIplpmLossMeasureAlarmEnable }
			STATUS current
			DESCRIPTION 
				"The collection of objects which are used to configure the
				IPLPM link behavior."
			::= { hwIplpmGroups 2 }
		
		-- 1.3.6.1.4.1.2011.5.25.328.3.3.3
		hwIplpmStatisticsGroup OBJECT-GROUP
			OBJECTS { hwIplpmLinkPeriodClock, hwIplpmLinkForwardLossPkts, hwIplpmLinkForwardLossRatio, hwIplpmLinkBackwardLossPkts, hwIplpmLinkLossStatsErrInfo, 
				hwIplpmBoardPhysicalIndex, hwIplpmPortUserQueLossRatio, hwIplpmLinkBackwardLossRatio, hwIplpmGlobalLossStatsErrInfo, hwIplpmGlobalPeriodClock, 
				hwIplpmGlobalLossPkts, hwIplpmGlobalLossRatio, hwIplpmPortQosQ0LossRatio, hwIplpmPortQosQ1LossRatio, hwIplpmPortQosQ2LossRatio, 
				hwIplpmPortQosQ3LossRatio, hwIplpmPortQosQ4LossRatio, hwIplpmPortQosQ5LossRatio, hwIplpmPortQosQ6LossRatio, hwIplpmPortQosQ7LossRatio, 
				hwIplpmPortInputLossRatio, hwIplpmPortOutputLossRatio, hwIplpmGlobalLatestPeriodNo, hwIplpmGlobalLatestHisRecordNo, hwIplpmLinkLatestPeriodNo, 
				hwIplpmLinkLatestHisRecordNo }
			STATUS current
			DESCRIPTION 
				"The collection of objects which are used to represent the
				IPLPM test instance statistics."
			::= { hwIplpmGroups 3 }
		
		-- 1.3.6.1.4.1.2011.5.25.328.3.3.4
		hwIplpmHistoryRecordGroup OBJECT-GROUP
			OBJECTS { hwIplpmGlobalLossRatioMax, hwIplpmGlobalLossRatioMin, hwIplpmGlobalTotalLossPkts, hwIplpmGlobalTotalRecvPkts, hwIplpmLinkForwardLossRatioMax, 
				hwIplpmLinkForwardLossRatioMin, hwIplpmLinkForwardTotalLossPkts, hwIplpmLinkForwardTotalRecvPkts, hwIplpmLinkBackwardLossRatioMax, hwIplpmLinkBackwardLossRatioMin, 
				hwIplpmLinkBackwardTotalLossPkts, hwIplpmGlobalValidStatDataNum, hwIplpmLinkValidStatDataNum, hwIplpmLinkBackwardTotalRecvPkts, hwIplpmGlobalHisRecStartTime, 
				hwIplpmGlobalHisRecEndTime, hwIplpmLinkHisRecordStartTime, hwIplpmLinkHisRecordEndTime }
			STATUS current
			DESCRIPTION 
				"The collection of objects which are used to represent the
				IPLPM test instance history records."
			::= { hwIplpmGroups 4 }
		
		-- 1.3.6.1.4.1.2011.5.25.328.3.3.5
		hwIplpmFwdPathSearchGroup OBJECT-GROUP
			OBJECTS { hwIplpmNetIfIndex, hwIplpmNetIfName, hwIplpmNetIfMacAddress, hwIplpmNetIfAddress, hwIplpmNetIfMask, 
				hwIplpmNetIfVpnName, hwIplpmNetIfVrf, hwIplpmNetIfVlan, hwIplpmNetSystemMac, hwIplpmHostIfIndex, 
				hwIplpmHostIfName, hwIplpmHostMacAddress, hwIplpmHostVlan, hwIplpmHostCeVlan, hwIplpmLocalIfIndex, 
				hwIplpmLocalIfType, hwIplpmLocalIfVrf, hwIplpmLocalPortList, hwIplpmRouteIfIndex, hwIplpmRouteDstAddr, 
				hwIplpmRouteDstMask, hwIplpmOutPortIfIndex, hwIplpmNetIfVrrpVip, hwIplpmNetIfVrrpMac, hwIplpmNetIfVrrpState,hwIplpmNetIfHostAddress
				 }
			STATUS current
			DESCRIPTION 
				"Description."
			::= { hwIplpmGroups 5 }
		
		-- 1.3.6.1.4.1.2011.5.25.328.3.3.6
		hwIplpmTrapsGroup NOTIFICATION-GROUP
			NOTIFICATIONS { hwIplpmLinkForwardLossRatioExceed, hwIplpmLinkForwardLossRatioRecovery, hwIplpmGlobalLossRatioRecovery, hwIplpmGlobalLossRatioExceed }
			STATUS current
			DESCRIPTION 
				"The collection of objects which are used to represent the
				IPLPM traps."
			::= { hwIplpmGroups 6 }
		
	
	END

--
-- HUAWEI-IPLPM-MIB.mib
--

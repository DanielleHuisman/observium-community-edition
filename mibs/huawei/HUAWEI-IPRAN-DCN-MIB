-- =================================================================
-- Copyright (C) 2018 by  HUAWEI TECHNOLOGIES. All rights reserved.
-- 
-- Description: HUAWEI-IPRAN-DCN-MIB
-- Reference:
-- Version:     V2.11
-- History:     
--     <YaoShuran>, <2011-09-30>, <V1.00 publish>
--     <Jiangyu>, <2011-12-01>, <V1.00 publish>
-- ==================================================================

    HUAWEI-IPRAN-DCN-MIB DEFINITIONS ::= BEGIN
 
        IMPORTS  
            hwDatacomm            
                FROM HUAWEI-MIB                                
            Integer32, Unsigned32, OBJECT-TYPE, MODULE-IDENTITY, NOTIFICATION-TYPE            
                FROM SNMPv2-SMI
            OBJECT-GROUP, MODULE-COMPLIANCE, NOTIFICATION-GROUP            
                FROM SNMPv2-CONF
            InetAddressType, InetAddress
                FROM INET-ADDRESS-MIB
            TEXTUAL-CONVENTION, DisplayString, MacAddress             
        FROM SNMPv2-TC
            ;     
    
        hwIpRanDcnMib MODULE-IDENTITY 
            LAST-UPDATED "201806301638Z" 
            ORGANIZATION 
                "Huawei Technologies Co.,Ltd."
            CONTACT-INFO 
                "Huawei Industrial Base
                  Bantian, Longgang
                   Shenzhen 518129
                   People's Republic of China
                   Website: http://www.huawei.com
                   Email: support@huawei.com
                 "
            DESCRIPTION 
                "IPRAN DCN MIB" 
                
            -- Revision history
           REVISION     "201806301638Z" 
           DESCRIPTION  "Modify the MAX-ACCESS of hwIpRanDcnNvInfoApVer and hwIpRanDcnNvInfoMasterVer"

           REVISION     "201802131937Z" 
           DESCRIPTION  "Add node hwIpRanDcnApVerMismatch"

           REVISION     "201512250000Z" 
           DESCRIPTION  "Add node hwIpRanDcnNeInfoVlanId"
		   
           REVISION     "201507230000Z" 
           DESCRIPTION  "Add node hwIpRanDcnACLName, hwIpRanDcnACLNumber"

           REVISION     "201504250000Z" 
           DESCRIPTION  "Add node hwIpRanDcnNeInfoPnpState, hwIpRanDcnNeInfoEsn, hwIpRanDcnNeInfoVlanId; add node hwIpRanDcnNeInfoPnpState, hwIpRanDcnNeInfoEsn, hwIpRanDcnNeInfoVlanId for hwIpRanDcnNeOnline"
    
           REVISION     "201504240000Z" 
           DESCRIPTION  "Add node hwIpRanSourceAddress, hwIpRanSourcePort, hwIpRanDestinationAddress, hwIpRanDestinationPort, hwIpRanVpn, hwIpRanSSLAuthFailedTimes, hwIpRanSSLAuthFailedPeriod;add note hwIpRanSSLAuthFailure"

           REVISION     "201503280000Z" 
           DESCRIPTION  "Add PTN trap node,add node:hwIpRanDcnGNENeOnlineNotifyMode ,hwIpRanDcnGNEFlag ,hwIpRanDcnNodeId ,hwIpRanDcnGNENSAP ,hwIpRanDcnGNENeOnline"

           REVISION     "201408210000Z" 
           DESCRIPTION  "Add hwIpRanDcnConnectMode invalid(0) enum."

           REVISION     "201403290000Z" 
           DESCRIPTION  "Add hwIpRanDcnElementInfoTable and hwIpRanCTDcnNeOnline trap."
 
           REVISION     "201403170000Z" 
           DESCRIPTION  "Add node hwIpRanDcnNeInfoNeLoginMode for hwIpRanDcnNeInfoTable, and add it as VB for hwIpRanDcnNeOnline and hwIpRanDcnNeOffline."

           REVISION     "201403120000Z"
           DESCRIPTION  "modify HwIpRanNeId  SYNTAX."
           
           REVISION     "201307240000Z"
           DESCRIPTION  "add node hwIpRanDcnSSLPort."

            REVISION     "201109300000Z"
            DESCRIPTION  "V1.00, initial version. Created HwIpRanDcnInfoEntry."

            ::= { hwIpRanDcn 1 }
  
--
-- Textual conventions
--
    
        HwIpRanNeId ::= TEXTUAL-CONVENTION
                DISPLAY-HINT "1d.1d.1d.1d"
            STATUS current
            DESCRIPTION 
                "Uniquely identify the network entity ID.
                        The total valid length is 24 bit, 
                        the high 8 bit is subnet number;
                        the low 16 bit is base id;
                        keep value range: subnet number should within 0x1-0xFE
                                          base id should within 0xBFF1-0xFFFE,
                        valid value range: subnet number should within 0x1-0xFE,
                                           base id should within 0x1-0xBFEF,
                        keep range will only use as factory value,
                        in the running network must use the valid value.
                        the IpRanNeId will be showed as 0.x.x.x."
            SYNTAX OCTET STRING (SIZE (4))
            
    
--
-- Node definitions
--
    
        hwIpRanDcn OBJECT IDENTIFIER ::= { hwDatacomm 300 }
                            
        hwIpRanDcnObjects OBJECT IDENTIFIER ::= { hwIpRanDcnMib 1 }
        
        hwIpRanDcnInfoObject OBJECT IDENTIFIER ::= { hwIpRanDcnObjects 1 }
        hwIpRanDcnNeId OBJECT-TYPE
            SYNTAX HwIpRanNeId
            MAX-ACCESS read-only
            STATUS current
            DESCRIPTION
                "
                This object indicates the ID of the node.
                "
            ::= { hwIpRanDcnInfoObject 1 }
                           
        hwIpRanDcnNeIpType OBJECT-TYPE
            SYNTAX InetAddressType
            MAX-ACCESS read-only
            STATUS current
            DESCRIPTION
                " 
                This object indicates the type of the node IP.
                "
            ::= { hwIpRanDcnInfoObject 2 } 
        
        hwIpRanDcnNeIp OBJECT-TYPE
            SYNTAX InetAddress
            MAX-ACCESS read-only
            STATUS current
            DESCRIPTION
                " 
                This object indicates the IP of the node.
                "
            ::= { hwIpRanDcnInfoObject 3 }
            
        hwIpRanDcnMask OBJECT-TYPE
            SYNTAX InetAddress
            MAX-ACCESS read-only
            STATUS current
            DESCRIPTION
                " 
                This object indicates the IP address mask.
                "
            ::= { hwIpRanDcnInfoObject 4 }   
        
        hwIpRanDcnPort OBJECT-TYPE
            SYNTAX Unsigned32
            MAX-ACCESS read-only
            STATUS current
            DESCRIPTION
                "
                This object indicates the port of TCP.
                "
             ::= { hwIpRanDcnInfoObject 5 }    
             
        hwIpRanDcnConnectMode OBJECT-TYPE
            SYNTAX INTEGER{
                normal (1),
                ssl (2),
                both (3),
                invalid(255)
                }
            MAX-ACCESS read-only
            STATUS current
            DESCRIPTION
                "
                This object indicates the mode of connect.
                "
            ::= { hwIpRanDcnInfoObject 6 }   
            
         hwIpRanDcnSSLPort OBJECT-TYPE
            SYNTAX Unsigned32
            MAX-ACCESS read-only
            STATUS current
            DESCRIPTION
                "
                This object indicates the ssl port of TCP.
                "
             ::= { hwIpRanDcnInfoObject 7 }   
 
         hwIpRanDcnGNENeOnlineNotifyMode OBJECT-TYPE
            SYNTAX INTEGER{
                udp (1),
                trap (2),
                invalid(255)
                }
            MAX-ACCESS read-only
            STATUS current
            DESCRIPTION
                "
                This object indicates mode in which NE-reported information was sent to an NMS.
                "
             ::= { hwIpRanDcnInfoObject 8 }   

         hwIpRanDcnACLName OBJECT-TYPE
            SYNTAX DisplayString (SIZE (0..40))
            MAX-ACCESS read-only
            STATUS current
            DESCRIPTION
                "
                This object indicates mode in which bind ACL name,if name length is 0 means no config.
                "
             ::= { hwIpRanDcnInfoObject 9 }   
             
         hwIpRanDcnACLNumber OBJECT-TYPE
            SYNTAX Integer32 
            MAX-ACCESS read-only
            STATUS current
            DESCRIPTION
                "
                This object indicates mode in which bind ACL number, if number is 0 means no config.
                "
             ::= { hwIpRanDcnInfoObject 10 }          

-- 1.3.6.1.4.1.2011.5.25.300.1.1.2
        hwIpRanDcnNeInfoTable OBJECT-TYPE                               
            SYNTAX SEQUENCE OF HwIpRanDcnNeInfoEntry
            MAX-ACCESS not-accessible
            STATUS current
            DESCRIPTION
                "A table of network element information."
            ::= { hwIpRanDcnObjects 2 }
        
        -- 1.3.6.1.4.1.2011.5.25.300.1.1.2.1
        hwIpRanDcnNeInfoEntry OBJECT-TYPE
            SYNTAX HwIpRanDcnNeInfoEntry
            MAX-ACCESS not-accessible
            STATUS current
            DESCRIPTION
                "A single network element information entry."
            INDEX { hwIpRanDcnNeInfoNeId }
            ::= { hwIpRanDcnNeInfoTable 1 }
        
        HwIpRanDcnNeInfoEntry ::=
            SEQUENCE { 
                hwIpRanDcnNeInfoNeId
                    HwIpRanNeId,
                hwIpRanDcnNeInfoNeIpType
                    InetAddressType,
                hwIpRanDcnNeInfoNeIp
                    InetAddress,
                hwIpRanDcnNeInfoDistance
                    Integer32,
                hwIpRanDcnNeInfoLifeCycle
                    Integer32,
                hwIpRanDcnNeInfoHostName
                    DisplayString,
                hwIpRanDcnNeInfoNeIpMask
                    InetAddress,
                hwIpRanDcnNeInfoNeLoginMode
                    INTEGER,
                hwIpRanDcnNeInfoPnpState
                    INTEGER,
                hwIpRanDcnNeInfoEsn
                    DisplayString,
                hwIpRanDcnNeInfoVlanId
		    Unsigned32
                    }

        -- 1.3.6.1.4.1.2011.5.25.300.1.1.2.1.1
        hwIpRanDcnNeInfoNeId OBJECT-TYPE
            SYNTAX HwIpRanNeId
            MAX-ACCESS accessible-for-notify
            STATUS current
            DESCRIPTION
                "The network element id, uniquely identifying 
                one network element in the routing domain."
            ::= { hwIpRanDcnNeInfoEntry 1 }
        
        -- 1.3.6.1.4.1.2011.5.25.300.1.1.2.1.2
        hwIpRanDcnNeInfoNeIpType OBJECT-TYPE
            SYNTAX InetAddressType
            MAX-ACCESS read-only
            STATUS current
            DESCRIPTION
                "The IP type of the network element node."
            ::= { hwIpRanDcnNeInfoEntry 2 }
        
        -- 1.3.6.1.4.1.2011.5.25.300.1.1.2.1.3
        hwIpRanDcnNeInfoNeIp OBJECT-TYPE
            SYNTAX InetAddress
            MAX-ACCESS read-only
            STATUS current
            DESCRIPTION
                "The IP address of the network element node."
            ::= { hwIpRanDcnNeInfoEntry 3 }
        
        -- 1.3.6.1.4.1.2011.5.25.300.1.1.2.1.4
        hwIpRanDcnNeInfoDistance OBJECT-TYPE
            SYNTAX Integer32
            MAX-ACCESS read-only
            STATUS current
            DESCRIPTION
                "The distance from current network element to the remote network element node."
            ::= { hwIpRanDcnNeInfoEntry 4 }
        
        -- 1.3.6.1.4.1.2011.5.25.300.1.1.2.1.5
        hwIpRanDcnNeInfoLifeCycle OBJECT-TYPE
            SYNTAX Integer32
            MAX-ACCESS read-only
            STATUS current
            DESCRIPTION
                "The left time period for the network element node exist, 
                The value will set to the initial period value when current 
                network element receive new advertisement packet for the 
                node, it will reduce one each period time and delete the 
                entry when Tm decrease to zero (The initial period value and
                one period time value may be different for different device version, 
                user no need care it's value)."
            ::= { hwIpRanDcnNeInfoEntry 5 }
        
        -- 1.3.6.1.4.1.2011.5.25.300.1.1.2.1.6
        hwIpRanDcnNeInfoHostName OBJECT-TYPE
            SYNTAX DisplayString (SIZE (0..255))
            MAX-ACCESS read-only
            STATUS current
            DESCRIPTION
                "The hostname of the network element."
            ::= { hwIpRanDcnNeInfoEntry 6 }
            
        -- 1.3.6.1.4.1.2011.5.25.300.1.1.2.1.7
        hwIpRanDcnNeInfoNeIpMask OBJECT-TYPE
            SYNTAX InetAddress
            MAX-ACCESS read-only
            STATUS current
            DESCRIPTION
                "The ip mask of the network element."
            ::= { hwIpRanDcnNeInfoEntry 7 }  

        -- 1.3.6.1.4.1.2011.5.25.300.1.1.2.1.8
        hwIpRanDcnNeInfoNeLoginMode OBJECT-TYPE
            SYNTAX INTEGER
                {
                unknown(1),
                ip(2),
                transmission(3)
                }
            MAX-ACCESS read-only
            STATUS current
            DESCRIPTION
                "The device type of the network element."
            ::= { hwIpRanDcnNeInfoEntry 8 }

        -- 1.3.6.1.4.1.2011.5.25.300.1.1.2.1.9
        hwIpRanDcnNeInfoPnpState OBJECT-TYPE
            SYNTAX INTEGER
                {
                init(1),
                start(2),
                finish(3)
                }
            MAX-ACCESS read-only
            STATUS current
            DESCRIPTION
                "The pnp state of the network element."
            ::= { hwIpRanDcnNeInfoEntry 9 }

        -- 1.3.6.1.4.1.2011.5.25.300.1.1.2.1.10
        hwIpRanDcnNeInfoEsn OBJECT-TYPE
            SYNTAX DisplayString (SIZE (0..64))
            MAX-ACCESS read-only
            STATUS current
            DESCRIPTION
                "The esn of the network element."
            ::= { hwIpRanDcnNeInfoEntry 10 }
			
		-- 1.3.6.1.4.1.2011.5.25.300.1.1.2.1.11
        hwIpRanDcnNeInfoVlanId OBJECT-TYPE
            SYNTAX Unsigned32
            MAX-ACCESS read-only
            STATUS current
            DESCRIPTION
                "The vlan of the network element."
            ::= { hwIpRanDcnNeInfoEntry 11 }

        -- 1.3.6.1.4.1.2011.5.25.300.1.1.3
        hwIpRanDcnElementInfoTable OBJECT-TYPE                               
            SYNTAX SEQUENCE OF HwIpRanDcnElementInfoEntry
            MAX-ACCESS not-accessible
            STATUS current
            DESCRIPTION
                "A table of network element information."
            ::= { hwIpRanDcnObjects 3 }
        
        -- 1.3.6.1.4.1.2011.5.25.300.1.1.3.1
        hwIpRanDcnElementInfoEntry OBJECT-TYPE
            SYNTAX HwIpRanDcnElementInfoEntry
            MAX-ACCESS not-accessible
            STATUS current
            DESCRIPTION
                "A single network element information entry."
            INDEX { hwIpRanDcnElementInfoNeId }
            ::= { hwIpRanDcnElementInfoTable 1 }
        
        HwIpRanDcnElementInfoEntry ::=
            SEQUENCE { 
                hwIpRanDcnElementInfoNeId
                    HwIpRanNeId,
                hwIpRanDcnElementInfoNeIpType
                    InetAddressType,
                hwIpRanDcnElementInfoNeIp
                    InetAddress,
                hwIpRanDcnElementInfoCompany
                    DisplayString,
                hwIpRanDcnElementInfoDeviceType
                    DisplayString,
                hwIpRanDcnElementInfoMacAddress
                    MacAddress
                    }

        -- 1.3.6.1.4.1.2011.5.25.300.1.1.3.1.1
        hwIpRanDcnElementInfoNeId OBJECT-TYPE
            SYNTAX HwIpRanNeId
            MAX-ACCESS accessible-for-notify
            STATUS current
            DESCRIPTION
                "The network element id, uniquely identifying 
                one network element in the routing domain."
            ::= { hwIpRanDcnElementInfoEntry 1 }
        
        -- 1.3.6.1.4.1.2011.5.25.300.1.1.3.1.2
        hwIpRanDcnElementInfoNeIpType OBJECT-TYPE
            SYNTAX InetAddressType
            MAX-ACCESS read-only
            STATUS current
            DESCRIPTION
                "The IP type of the network element node."
            ::= { hwIpRanDcnElementInfoEntry 2 }
        
        -- 1.3.6.1.4.1.2011.5.25.300.1.1.3.1.3
        hwIpRanDcnElementInfoNeIp OBJECT-TYPE
            SYNTAX InetAddress
            MAX-ACCESS read-only
            STATUS current
            DESCRIPTION
                "The IP address of the network element node."
            ::= { hwIpRanDcnElementInfoEntry 3 }
        
        -- 1.3.6.1.4.1.2011.5.25.300.1.1.3.1.4
        hwIpRanDcnElementInfoCompany OBJECT-TYPE
            SYNTAX DisplayString (SIZE (0..255))
            MAX-ACCESS read-only
            STATUS current
            DESCRIPTION
                "The company of the network element."
            ::= { hwIpRanDcnElementInfoEntry 4 }
                                             
         -- 1.3.6.1.4.1.2011.5.25.300.1.1.3.1.5
        hwIpRanDcnElementInfoDeviceType OBJECT-TYPE
            SYNTAX DisplayString (SIZE (0..255))
            MAX-ACCESS read-only
            STATUS current
            DESCRIPTION
                "The device type of the network element."
            ::= { hwIpRanDcnElementInfoEntry 5 }                                            
                                             
          -- 1.3.6.1.4.1.2011.5.25.300.1.1.3.1.6
        hwIpRanDcnElementInfoMacAddress OBJECT-TYPE
            SYNTAX MacAddress
            MAX-ACCESS read-only
            STATUS current
            DESCRIPTION
                "The MAC Address of the network element."
            ::= { hwIpRanDcnElementInfoEntry 6 }   

        hwIpRanDcnTrapObjects OBJECT IDENTIFIER ::= { hwIpRanDcnMib 2 }
    
    hwIpRanDcnNeNumber OBJECT-TYPE
        SYNTAX Integer32                
        MAX-ACCESS accessible-for-notify
        STATUS current
        DESCRIPTION
            "The NE number."
        ::= { hwIpRanDcnTrapObjects 1 }
        
       hwIpRanDcnNeChangeMode OBJECT-TYPE
        SYNTAX INTEGER{
            online (1),
            offline (2)
            }
        MAX-ACCESS accessible-for-notify
        STATUS current
        DESCRIPTION
            "
            This object is used to indicate the mode of NE added.
            "
        ::= { hwIpRanDcnTrapObjects 2 }

    hwIpRanDcnFlag OBJECT-TYPE
        SYNTAX Integer32                
        MAX-ACCESS accessible-for-notify
        STATUS current
        DESCRIPTION
            "The packet format flag."
        ::= { hwIpRanDcnTrapObjects 3 }

    hwIpRanDcnGNEFlag OBJECT-TYPE
        SYNTAX Integer32                
        MAX-ACCESS accessible-for-notify
        STATUS current
        DESCRIPTION
            "The GNE flag."
        ::= { hwIpRanDcnTrapObjects 4 }
        
     hwIpRanDcnNodeId OBJECT-TYPE
        SYNTAX Integer32                
        MAX-ACCESS accessible-for-notify
        STATUS current
        DESCRIPTION
            "The node ID."
        ::= { hwIpRanDcnTrapObjects 5 } 

     hwIpRanDcnGNENSAP OBJECT-TYPE
        SYNTAX DisplayString (SIZE (0..20))                
        MAX-ACCESS accessible-for-notify
        STATUS current
        DESCRIPTION
            "The GNE NSAP address."
        ::= { hwIpRanDcnTrapObjects 6 }
	
    hwIpRanSourceAddress OBJECT-TYPE
        SYNTAX InetAddress                
        MAX-ACCESS accessible-for-notify
        STATUS current
        DESCRIPTION
            "Source address."
        ::= { hwIpRanDcnTrapObjects 7 }
		
	hwIpRanSourcePort OBJECT-TYPE
        SYNTAX Integer32                
        MAX-ACCESS accessible-for-notify
        STATUS current
        DESCRIPTION
            "Source port."
        ::= { hwIpRanDcnTrapObjects 8 }
		
	hwIpRanDestinationAddress OBJECT-TYPE
        SYNTAX InetAddress                
        MAX-ACCESS accessible-for-notify
        STATUS current
        DESCRIPTION
            "Destination address."
        ::= { hwIpRanDcnTrapObjects 9 }
		
	hwIpRanDestinationPort  OBJECT-TYPE
        SYNTAX Integer32                
        MAX-ACCESS accessible-for-notify
        STATUS current
        DESCRIPTION
            "Destination port."
        ::= { hwIpRanDcnTrapObjects 10 }
		
	hwIpRanVpn  OBJECT-TYPE
        SYNTAX DisplayString (SIZE (0..255))                
        MAX-ACCESS accessible-for-notify
        STATUS current
        DESCRIPTION
            "VPN name."
        ::= { hwIpRanDcnTrapObjects 11 }
		
	hwIpRanSSLAuthFailedTimes  OBJECT-TYPE
        SYNTAX Integer32                
        MAX-ACCESS accessible-for-notify
        STATUS current
        DESCRIPTION
            "SSL certificate authentication failed times."
        ::= { hwIpRanDcnTrapObjects 12 }
		
	hwIpRanSSLAuthFailedPeriod  OBJECT-TYPE
        SYNTAX Integer32                
        MAX-ACCESS accessible-for-notify
        STATUS current
        DESCRIPTION
            "SSL certificate authentication failed period, the default value is 60s."
        ::= { hwIpRanDcnTrapObjects 13 }

	hwIpRanDcnNvInfoApId  OBJECT-TYPE
		SYNTAX Integer32
		MAX-ACCESS accessible-for-notify
		STATUS current
		DESCRIPTION
			"The NV AP id, uniquely identifying."
        ::= { hwIpRanDcnTrapObjects 14 }

	hwIpRanDcnNvInfoApVer  OBJECT-TYPE
		SYNTAX DisplayString
		MAX-ACCESS accessible-for-notify
		STATUS current
		DESCRIPTION
			"The version of the AP node."
        ::= { hwIpRanDcnTrapObjects 15 }

	hwIpRanDcnNvInfoMasterVer OBJECT-TYPE
		SYNTAX DisplayString
		MAX-ACCESS accessible-for-notify
		STATUS current
		DESCRIPTION
			"The version of the Master node."
        ::= { hwIpRanDcnTrapObjects 16 }

        hwIpRanDcnTraps OBJECT IDENTIFIER ::= { hwIpRanDcnMib 3 }
        
    hwIpRanDcnNeNumberOverLoad NOTIFICATION-TYPE
            OBJECTS { hwIpRanDcnNeNumber }
            STATUS current
            DESCRIPTION 
                "This object is used to indicate NE number overload."
            ::= { hwIpRanDcnTraps 1 }
        
        hwIpRanDcnNeNumberOverLoadRecovery NOTIFICATION-TYPE
            OBJECTS { hwIpRanDcnNeNumber }
            STATUS current
            DESCRIPTION 
                "This object is used to indicate NE number overload recovery."
            ::= { hwIpRanDcnTraps 2 }  
                      
        hwIpRanDcnNeOnline NOTIFICATION-TYPE
          OBJECTS { hwIpRanDcnNeChangeMode, hwIpRanDcnNeInfoNeId, hwIpRanDcnNeInfoNeIpType, hwIpRanDcnNeInfoNeIp, hwIpRanDcnNeInfoNeIpMask, hwIpRanDcnNeNumber, hwIpRanDcnNeInfoNeLoginMode, hwIpRanDcnNeInfoPnpState, hwIpRanDcnNeInfoEsn, hwIpRanDcnNeInfoVlanId }
          STATUS current
          DESCRIPTION 
              "This object is used to indicate NE on-line."
          ::= { hwIpRanDcnTraps 3 } 

        hwIpRanDcnNeOffline NOTIFICATION-TYPE
          OBJECTS { hwIpRanDcnNeInfoNeId, hwIpRanDcnNeInfoNeIpType, hwIpRanDcnNeInfoNeIp, hwIpRanDcnNeInfoNeLoginMode }
          STATUS current
          DESCRIPTION 
              "This object is used to indicate NE off-line."
          ::= { hwIpRanDcnTraps 4 } 
        
        hwIpRanCTDcnNeOnline NOTIFICATION-TYPE
          OBJECTS { hwIpRanDcnElementInfoNeId, hwIpRanDcnElementInfoNeIp, hwIpRanDcnElementInfoCompany, hwIpRanDcnElementInfoDeviceType, hwIpRanDcnElementInfoMacAddress}
          STATUS current
          DESCRIPTION 
              "This object is used to indicate CT NE on-line."
          ::= { hwIpRanDcnTraps 5 } 

        hwIpRanDcnGNENeOnline NOTIFICATION-TYPE
          OBJECTS { hwIpRanDcnFlag, hwIpRanDcnGNEFlag, hwIpRanDcnElementInfoNeId, hwIpRanDcnNeIpType, hwIpRanDcnNeIp, hwIpRanDcnNodeId, hwIpRanDcnGNENSAP, hwIpRanDcnElementInfoDeviceType,hwIpRanDcnNeInfoHostName, hwIpRanDcnNeInfoNeId}
          STATUS current
          DESCRIPTION 
              "When an NE went online in PTN mode, this trap will be triggered."
          ::= { hwIpRanDcnTraps  6 } 
 
        hwIpRanSSLAuthFailure NOTIFICATION-TYPE
          OBJECTS { hwIpRanSourceAddress, hwIpRanSourcePort, hwIpRanDestinationAddress, hwIpRanDestinationPort, hwIpRanVpn, hwIpRanSSLAuthFailedTimes, hwIpRanSSLAuthFailedPeriod}
          STATUS current
          DESCRIPTION 
              "This  object is used to indicate SSL certificate login failure times during 60s. The default login failure report times is 10."
          ::= { hwIpRanDcnTraps 7 } 

        hwIpRanDcnApVerMismatch NOTIFICATION-TYPE
          OBJECTS { hwIpRanDcnNvInfoApId, hwIpRanDcnNvInfoApVer, hwIpRanDcnNvInfoMasterVer}
          STATUS current
          DESCRIPTION 
              "This object is used to indicate AP version mismatch with Master."
          ::= { hwIpRanDcnTraps 8 } 

        hwIpRanDcnConformance OBJECT IDENTIFIER ::= { hwIpRanDcnMib 4 }
        hwIpRanDcnCompliances OBJECT IDENTIFIER ::= { hwIpRanDcnConformance 1 }

        hwIpRanDcnFullCompliance MODULE-COMPLIANCE
            STATUS current
            DESCRIPTION 
                "The compliance statement for the HUAWEI-IPRAN-DCN-MIB."
            MODULE -- this module
                MANDATORY-GROUPS { hwIpRanDcnInfoGroup }
            ::= { hwIpRanDcnCompliances 1 }

        hwIpRanDcnGroups OBJECT IDENTIFIER ::= { hwIpRanDcnConformance 2 }

        hwIpRanDcnInfoGroup OBJECT-GROUP
            OBJECTS { hwIpRanDcnNeId,
                      hwIpRanDcnNeIpType,
                      hwIpRanDcnNeIp,
                      hwIpRanDcnMask,
                      hwIpRanDcnPort,
                      hwIpRanDcnConnectMode,
                      hwIpRanDcnSSLPort,
                      hwIpRanDcnGNENeOnlineNotifyMode,
                      hwIpRanDcnACLName,
                      hwIpRanDcnACLNumber                                               
                    }
            STATUS current
            DESCRIPTION 
                "The group for ipran dcn."
            ::= { hwIpRanDcnGroups 1 } 
            
        hwIpRanDcnTrapEventGroup NOTIFICATION-GROUP
            NOTIFICATIONS { hwIpRanDcnNeNumberOverLoad, hwIpRanDcnNeNumberOverLoadRecovery, hwIpRanDcnNeOnline, hwIpRanDcnNeOffline, hwIpRanCTDcnNeOnline, hwIpRanDcnGNENeOnline, hwIpRanSSLAuthFailure, hwIpRanDcnApVerMismatch}
            STATUS current
            DESCRIPTION 
                "These objects are used to indicate the NE number state."
            ::= { hwIpRanDcnGroups 2 }
        
        hwIpRanDcnTrapObjectsGroup OBJECT-GROUP
            OBJECTS { hwIpRanDcnNeInfoNeLoginMode,
                      hwIpRanDcnNeNumber, 
                      hwIpRanDcnNeInfoNeId, 
                      hwIpRanDcnNeInfoNeIpType, 
                      hwIpRanDcnNeInfoNeIp, 
                      hwIpRanDcnNeInfoNeIpMask, 
                      hwIpRanDcnNeChangeMode,
                      hwIpRanDcnElementInfoNeId,
                      hwIpRanDcnElementInfoNeIpType,
                      hwIpRanDcnElementInfoNeIp,
                      hwIpRanDcnElementInfoCompany, 
                      hwIpRanDcnElementInfoDeviceType, 
                      hwIpRanDcnElementInfoMacAddress,
                      hwIpRanDcnFlag,
                      hwIpRanDcnNodeId,
                      hwIpRanDcnGNEFlag,
                      hwIpRanDcnGNENSAP,
                      hwIpRanSourceAddress,
                      hwIpRanSourcePort,
                      hwIpRanDestinationAddress,
                      hwIpRanDestinationPort,
                      hwIpRanVpn,
                      hwIpRanSSLAuthFailedTimes,
                      hwIpRanSSLAuthFailedPeriod,
                      hwIpRanDcnNeInfoPnpState,
                      hwIpRanDcnNeInfoEsn,
                      hwIpRanDcnNeInfoVlanId,
                      hwIpRanDcnNvInfoApId,
                      hwIpRanDcnNvInfoApVer,
                      hwIpRanDcnNvInfoMasterVer}
            STATUS current
            DESCRIPTION 
                "The objects are used to indicate the NE number."
            ::= { hwIpRanDcnGroups 3 }                                    

        -- 1.3.6.1.4.1.2011.5.25.300.1.4.2.4
        hwIpRanDcnNeInfoGroup OBJECT-GROUP
            OBJECTS { hwIpRanDcnNeInfoNeIpType, hwIpRanDcnNeInfoNeIp, hwIpRanDcnNeInfoDistance, hwIpRanDcnNeInfoLifeCycle, hwIpRanDcnNeInfoHostName, hwIpRanDcnNeInfoNeIpMask, hwIpRanDcnNeInfoNeLoginMode, hwIpRanDcnNeInfoPnpState, hwIpRanDcnNeInfoEsn, hwIpRanDcnNeInfoVlanId }
            STATUS current
            DESCRIPTION 
                "These objects are required for display ne-info table."
            ::= { hwIpRanDcnGroups 4 }

    END

--
-- HUAWEI-L2VPN-OAM-MIB.mib
--

--  ==================================================================
-- Copyright (C) 2018 by  HUAWEI TECHNOLOGIES. All rights reserved.
-- 
-- Description: HUAWEI L2VPN OAM TRAP Management MIB
-- Reference:
-- Version:     V2.06
-- History:
--              V1.0 yueyongliang, 2011-04-21, publish
-- ==================================================================

    HUAWEI-L2VPN-OAM-MIB DEFINITIONS ::= BEGIN
 
        IMPORTS
            hwDatacomm            
                FROM HUAWEI-MIB            
            HWL2VpnVcEncapsType            
                FROM HUAWEI-VPLS-EXT-MIB            
            ifName, InterfaceIndexOrZero            
                FROM IF-MIB                                                                
            OBJECT-GROUP, MODULE-COMPLIANCE, NOTIFICATION-GROUP			
                FROM SNMPv2-CONF
            IpAddress, Unsigned32,
            OBJECT-TYPE, MODULE-IDENTITY, NOTIFICATION-TYPE            
                FROM SNMPv2-SMI;        
    
    
        -- 1.3.6.1.4.1.2011.5.25.119.9
    hwL2vpnOamTrap MODULE-IDENTITY 
        LAST-UPDATED "201801131530Z"        -- Jan 13, 2018 at 15:30 GMT
        ORGANIZATION 
            "Huawei Technologies Co.,Ltd."
        CONTACT-INFO 
            "Huawei Industrial Base
              Bantian, Longgang
               Shenzhen 518129
               People's Republic of China
               Website: http://www.huawei.com
               Email: support@huawei.com
             "
        DESCRIPTION 
            "The HUAWEI-L2VPN-OAM-MIB is used by L2VPN to report TP-OAM and MPLS OAM traps (including traps about PW connectivity, remote defect indication, and packet excess). The parameter of the MIB is accessible-for-notify, which cannot be modified."
        
        -- Revision history
        REVISION "201801131530Z"
    	DESCRIPTION 
            "V2.06, modify description."
        REVISION "201708171750Z"
    	DESCRIPTION 
            "V2.05, modify description of hwL2vpnVcType,hwL2vpnPeerAddr,hwL2vpnRmtSiteID,hwL2vpnInLabel,hwL2vpnOutLabel,hwL2vpnOamDloc,
			 hwL2vpnOamDlocClear,hwL2vpnOamSd1Near,hwL2vpnOamSd1NearClear,hwL2vpnOamAis,hwL2vpnOamAisClear,hwL2vpnOamSd2NearClear,
			 hwL2vpnOamLck,hwL2vpnOamLckClear,hwL2vpnOamCsf,hwL2vpnOamCsfClear,hwL2vpnOamExcess,hwL2vpnOamExcessClear,hwL2vpnOamFail,
			 hwL2vpnOamFailClear,hwL2vpnOamDbdi,hwL2vpnOamDbdiClear,hwL2vpnOamLocalLock,hwL2vpnOamLocalLockClear,hwL2vpnOamSd1Far,
			 hwL2vpnOamSd1FarClear,hwL2vpnOamSd2Far,hwL2vpnOamSd2FarClear,hwL2vpnOamFdi,hwL2vpnOamFdiClear."
        REVISION "201511271400Z"
    	DESCRIPTION 
            "V2.04, add hwL2vpnOamTunnelNonSupport, hwL2vpnOamTunnelNonSupportResumed for router."
        REVISION "201309051400Z"
    	DESCRIPTION 
            "V2.03, modify import error."
        REVISION "201305131330Z"
    	DESCRIPTION 
            "V2.02, add hwL2vpnOamFdi, hwL2vpnOamFdiClear for PTN5900."
        REVISION "201303251452Z"
    	DESCRIPTION 
            "V2.01, add hwL2vpnOamSd1Far, hwL2vpnOamSd1FarClear, hwL2vpnOamSd2Far, hwL2vpnOamSd2FarClear for far-end packet loss."
        
       ::= { hwL2Vpn 9 }
                    
    
--
-- Node definitions
--
    
--  Node definitions
-- 
        -- 1.3.6.1.4.1.2011.5.25.119
        hwL2Vpn OBJECT IDENTIFIER ::= { hwDatacomm 119 }

        
--           
-- The OAM TRAP Attribute Group
-- 
        -- 1.3.6.1.4.1.2011.5.25.119.9.1
        hwL2vpnOamTrapMIBObjects OBJECT IDENTIFIER ::= { hwL2vpnOamTrap 1 }
        
--           
-- The PW Info
-- 
        -- 1.3.6.1.4.1.2011.5.25.119.9.1.1
        hwL2vpnServiceType OBJECT-TYPE
            SYNTAX INTEGER
                {
                vpwsPw(0),
                vplsPw(1)
                }
            MAX-ACCESS accessible-for-notify
            STATUS current
            DESCRIPTION
                "This object indicates the PW type (VPWS or VPLS)."
            ::= { hwL2vpnOamTrapMIBObjects 1 }

        
        -- 1.3.6.1.4.1.2011.5.25.119.9.1.2
        hwL2vpnProtocolType OBJECT-TYPE
            SYNTAX INTEGER
                {
                static(0),
                ldp(1),
                bgp(2)
                }
            MAX-ACCESS accessible-for-notify
            STATUS current
            DESCRIPTION
                "This object indicates the protocol used by a PW (static, LDP, or BGP)."
            ::= { hwL2vpnOamTrapMIBObjects 2 }

        
        -- 1.3.6.1.4.1.2011.5.25.119.9.1.3
        hwL2vpnVcID OBJECT-TYPE
            SYNTAX Unsigned32
            MAX-ACCESS accessible-for-notify
            STATUS current
            DESCRIPTION
                "This object indicates the PW ID. The value 0 is invalid."
            ::= { hwL2vpnOamTrapMIBObjects 3 }

        
        -- 1.3.6.1.4.1.2011.5.25.119.9.1.4
        hwL2vpnVcType OBJECT-TYPE
            SYNTAX HWL2VpnVcEncapsType
            MAX-ACCESS accessible-for-notify
            STATUS current
            DESCRIPTION
                "This object indicates the PW encapsulation type. The value 0 is invalid."
            ::= { hwL2vpnOamTrapMIBObjects 4 }

        
        -- 1.3.6.1.4.1.2011.5.25.119.9.1.5
        hwL2vpnPeerAddr OBJECT-TYPE
            SYNTAX IpAddress    
            MAX-ACCESS accessible-for-notify
            STATUS current
            DESCRIPTION
                "This object indicates the IP address of a remote device. The value 0.0.0.0 is invalid."
            ::= { hwL2vpnOamTrapMIBObjects 5 }

        
        -- 1.3.6.1.4.1.2011.5.25.119.9.1.6
        hwL2vpnIfIndex OBJECT-TYPE
            SYNTAX InterfaceIndexOrZero
            MAX-ACCESS accessible-for-notify
            STATUS current
            DESCRIPTION
                "This object indicates the index of an AC interface. The value 0 is invalid."
            ::= { hwL2vpnOamTrapMIBObjects 6 }

        
        -- 1.3.6.1.4.1.2011.5.25.119.9.1.7
        hwL2vpnPwMaster OBJECT-TYPE
            SYNTAX INTEGER
                {
                primary(1),
                second(2)
                }
            MAX-ACCESS accessible-for-notify
            STATUS current
            DESCRIPTION
                "This object indicates the primary or secondary state of a PW. The value 0 is invalid."
            ::= { hwL2vpnOamTrapMIBObjects 7 }

        
        -- 1.3.6.1.4.1.2011.5.25.119.9.1.8
        hwL2vpnRmtSiteID OBJECT-TYPE
            SYNTAX Unsigned32
            MAX-ACCESS accessible-for-notify
            STATUS current
            DESCRIPTION
                "This object indicates the ID of a remote node. The value 0 is invalid."
            ::= { hwL2vpnOamTrapMIBObjects 8 }

        
        -- 1.3.6.1.4.1.2011.5.25.119.9.1.9
        hwL2vpnInLabel OBJECT-TYPE
            SYNTAX Unsigned32
            MAX-ACCESS accessible-for-notify
            STATUS current
            DESCRIPTION
                "This object indicates the incoming label of a PW. The value 0 is invalid."
            ::= { hwL2vpnOamTrapMIBObjects 9 }

        
        -- 1.3.6.1.4.1.2011.5.25.119.9.1.10
        hwL2vpnOutLabel OBJECT-TYPE
            SYNTAX Unsigned32
            MAX-ACCESS accessible-for-notify
            STATUS current
            DESCRIPTION
                "This object indicates the outgoing label of a PW. The value 0 is invalid."
            ::= { hwL2vpnOamTrapMIBObjects 10 }

        
        -- 1.3.6.1.4.1.2011.5.25.119.9.1.11
        hwL2vpnIfName OBJECT-TYPE
            SYNTAX OCTET STRING
            MAX-ACCESS accessible-for-notify
            STATUS current
            DESCRIPTION
                "This object indicates the name of an AC interface. The value null is invalid."
            ::= { hwL2vpnOamTrapMIBObjects 11 }

        
        -- 1.3.6.1.4.1.2011.5.25.119.9.1.12
        hwL2vpnVsiName OBJECT-TYPE
            SYNTAX OCTET STRING
            MAX-ACCESS accessible-for-notify
            STATUS current
            DESCRIPTION
                "This object indicates a VSI name. The value null is invalid."
            ::= { hwL2vpnOamTrapMIBObjects 12 }


        -- 1.3.6.1.4.1.2011.5.25.119.9.1.13
        hwL2vpnOamType OBJECT-TYPE
            SYNTAX INTEGER
                {
                mplsoam(1),
                mplstpoam(2)
                }
            MAX-ACCESS accessible-for-notify
            STATUS current
            DESCRIPTION
                "This object indicates the OAM type, MPLS OAM or MPLS-TP OAM."
            ::= { hwL2vpnOamTrapMIBObjects 13 }


--           
-- L2VPN OAM Trap Definitions
-- 

        -- 1.3.6.1.4.1.2011.5.25.119.9.2
        hwL2vpnOamMIBTraps OBJECT IDENTIFIER ::= { hwL2vpnOamTrap 2 }
      
      
        -- 1.3.6.1.4.1.2011.5.25.119.9.2.1
        hwL2vpnOamDloc NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm for the loss of PW connectivity."
            ::= { hwL2vpnOamMIBTraps 1 }

        
        -- 1.3.6.1.4.1.2011.5.25.119.9.2.2
        hwL2vpnOamDlocClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm for the loss of PW connectivity is cleared."
            ::= { hwL2vpnOamMIBTraps 2 }
                            
        
        -- 1.3.6.1.4.1.2011.5.25.119.9.2.3
        hwL2vpnOamSd1Near NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm when the near-end packet loss ratio exceeds the sd1 threshold."
            ::= { hwL2vpnOamMIBTraps 3 }

        
        -- 1.3.6.1.4.1.2011.5.25.119.9.2.4
        hwL2vpnOamSd1NearClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm, which was generated when the near-end packet loss ratio exceeded the sd1 threshold, is cleared."
            ::= { hwL2vpnOamMIBTraps 4 }
        
        
        -- 1.3.6.1.4.1.2011.5.25.119.9.2.5
        hwL2vpnOamRdi NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports a remote defect indication (RDI) alarm."
            ::= { hwL2vpnOamMIBTraps 5 }

        
        -- 1.3.6.1.4.1.2011.5.25.119.9.2.6
        hwL2vpnOamRdiClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported RDI alarm is cleared."
            ::= { hwL2vpnOamMIBTraps 6 }

        
        -- 1.3.6.1.4.1.2011.5.25.119.9.2.7
        hwL2vpnOamMeg NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm for the unexpected MEG."
            ::= { hwL2vpnOamMIBTraps 7 }

        
        -- 1.3.6.1.4.1.2011.5.25.119.9.2.8
        hwL2vpnOamMegClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm for the unexpected MEG is cleared."
            ::= { hwL2vpnOamMIBTraps 8 }

        
        -- 1.3.6.1.4.1.2011.5.25.119.9.2.9
        hwL2vpnOamMep NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm for the unexpected MEP."
            ::= { hwL2vpnOamMIBTraps 9 }

        
        -- 1.3.6.1.4.1.2011.5.25.119.9.2.10
        hwL2vpnOamMepClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm for the unexpected MEP is cleared."
            ::= { hwL2vpnOamMIBTraps 10 }

        
        -- 1.3.6.1.4.1.2011.5.25.119.9.2.11
        hwL2vpnOamPeriod NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm for the unexpected CV packet transmission interval."
            ::= { hwL2vpnOamMIBTraps 11 }

        
        -- 1.3.6.1.4.1.2011.5.25.119.9.2.12
        hwL2vpnOamPeriodClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm for the unexpected CV packet interval is cleared."
            ::= { hwL2vpnOamMIBTraps 12 }

        
        -- 1.3.6.1.4.1.2011.5.25.119.9.2.13
        hwL2vpnOamAis NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm indication signal (AIS) alarm."
            ::= { hwL2vpnOamMIBTraps 13 }

        
        -- 1.3.6.1.4.1.2011.5.25.119.9.2.14
        hwL2vpnOamAisClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported AIS alarm is cleared."
            ::= { hwL2vpnOamMIBTraps 14 }

        
        -- 1.3.6.1.4.1.2011.5.25.119.9.2.15
        hwL2vpnOamSd2Near NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm when the near-end packet loss ratio exceeds the sd2 threshold."
            ::= { hwL2vpnOamMIBTraps 15 }

        
        -- 1.3.6.1.4.1.2011.5.25.119.9.2.16
        hwL2vpnOamSd2NearClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm, which was generated when the near-end packet loss ratio exceeded the sd2 threshold, is cleared."
            ::= { hwL2vpnOamMIBTraps 16 }

        
        -- 1.3.6.1.4.1.2011.5.25.119.9.2.17
        hwL2vpnOamLck NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports a locking (LCK) alarm."
            ::= { hwL2vpnOamMIBTraps 17 }

        
        -- 1.3.6.1.4.1.2011.5.25.119.9.2.18
        hwL2vpnOamLckClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm for the LCK failure is cleared."
            ::= { hwL2vpnOamMIBTraps 18 }

        
        -- 1.3.6.1.4.1.2011.5.25.119.9.2.19
        hwL2vpnOamCsf NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm when a client-layer signal fails."
            ::= { hwL2vpnOamMIBTraps 19 }

        
        -- 1.3.6.1.4.1.2011.5.25.119.9.2.20
        hwL2vpnOamCsfClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm for the client-layer signal failure is cleared."
            ::= { hwL2vpnOamMIBTraps 20 }        


        -- 1.3.6.1.4.1.2011.5.25.119.9.2.21
        hwL2vpnOamExcess NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm when the number of received TTSIs on a PW exceeds the upper threshold."
            ::= { hwL2vpnOamMIBTraps 21 }

        -- 1.3.6.1.4.1.2011.5.25.119.9.2.22
        hwL2vpnOamExcessClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm, which was generated when the number of received TTSIs on a PW exceeded the upper threshold, is cleared."
            ::= { hwL2vpnOamMIBTraps 22 }

        -- 1.3.6.1.4.1.2011.5.25.119.9.2.23
        hwL2vpnOamMismatch NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a TTSI mismatch alarm."
            ::= { hwL2vpnOamMIBTraps 23 }


        -- 1.3.6.1.4.1.2011.5.25.119.9.2.24
        hwL2vpnOamMismatchClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the TTSI mismatch alarm disappearance."
            ::= { hwL2vpnOamMIBTraps 24 }

        -- 1.3.6.1.4.1.2011.5.25.119.9.2.25
        hwL2vpnOamMismerge NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported a TTSI mismerge alarm."
            ::= { hwL2vpnOamMIBTraps 25 }


        -- 1.3.6.1.4.1.2011.5.25.119.9.2.26
        hwL2vpnOamMismergeClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the TTSI mismerge alarm disappearance."
            ::= { hwL2vpnOamMIBTraps 26 }

        -- 1.3.6.1.4.1.2011.5.25.119.9.2.27
        hwL2vpnOamFail NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm when no detection-triggering packet is received from the remote end after automatic protocol-based detection expires."
            ::= { hwL2vpnOamMIBTraps 27 }


        -- 1.3.6.1.4.1.2011.5.25.119.9.2.28
        hwL2vpnOamFailClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm, which was generated when a detection-triggering packet was received from the remote end after automatic protocol-based detection expired, is cleared."
            ::= { hwL2vpnOamMIBTraps 28 }

        -- 1.3.6.1.4.1.2011.5.25.119.9.2.29
        hwL2vpnOamDbdi NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports a PW backward defect indication (BDI) alarm."
            ::= { hwL2vpnOamMIBTraps 29 }


        -- 1.3.6.1.4.1.2011.5.25.119.9.2.30
        hwL2vpnOamDbdiClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported PW BDI alarm is cleared."
            ::= { hwL2vpnOamMIBTraps 30 }
                        
        -- 1.3.6.1.4.1.2011.5.25.119.9.2.31
        hwL2vpnOamUnknown NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported an unknown limitation alarm."
            ::= { hwL2vpnOamMIBTraps 31 }


        -- 1.3.6.1.4.1.2011.5.25.119.9.2.32
        hwL2vpnOamUnknownClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "OAM reported the unknown limitation alarm disappearance."
            ::= { hwL2vpnOamMIBTraps 32 }

        -- 1.3.6.1.4.1.2011.5.25.119.9.2.33
        hwL2vpnOamLocalLock NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an LCK alarm at the PW layer."
            ::= { hwL2vpnOamMIBTraps 33 }
        
        -- 1.3.6.1.4.1.2011.5.25.119.9.2.34
        hwL2vpnOamLocalLockClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported LCK alarm at the PW layer is cleared."
            ::= { hwL2vpnOamMIBTraps 34 }
            
        -- 1.3.6.1.4.1.2011.5.25.119.9.2.35
        hwL2vpnOamSd1Far NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm when the far-end packet loss ratio exceeds the sd1 threshold."
            ::= { hwL2vpnOamMIBTraps 35 }
      
        -- 1.3.6.1.4.1.2011.5.25.119.9.2.36
        hwL2vpnOamSd1FarClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm, which was generated when the far-end packet loss ratio exceeded the sd1 threshold, is cleared."
            ::= { hwL2vpnOamMIBTraps 36 }
       
        -- 1.3.6.1.4.1.2011.5.25.119.9.2.37
        hwL2vpnOamSd2Far NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports an alarm when the far-end packet loss ratio exceeds the sd2 threshold."
            ::= { hwL2vpnOamMIBTraps 37 }
        
        -- 1.3.6.1.4.1.2011.5.25.119.9.2.38
        hwL2vpnOamSd2FarClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported alarm, which was generated when the far-end packet loss ratio exceeded the sd2 threshold, is cleared."
            ::= { hwL2vpnOamMIBTraps 38 }

        -- 1.3.6.1.4.1.2011.5.25.119.9.2.39
        hwL2vpnOamFdi NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that OAM reports a forward defect indication (FDI) alarm."
            ::= { hwL2vpnOamMIBTraps 39 }
        
        -- 1.3.6.1.4.1.2011.5.25.119.9.2.40
        hwL2vpnOamFdiClear NOTIFICATION-TYPE
            OBJECTS { hwL2vpnServiceType, hwL2vpnProtocolType, hwL2vpnVcID, hwL2vpnVcType, hwL2vpnPeerAddr, 
                      hwL2vpnIfIndex, hwL2vpnPwMaster, hwL2vpnRmtSiteID, hwL2vpnInLabel, hwL2vpnOutLabel, 
                      hwL2vpnIfName, hwL2vpnVsiName}
            STATUS current
            DESCRIPTION 
                "This object indicates that the OAM-reported FDI alarm is cleared."
            ::= { hwL2vpnOamMIBTraps 40 }

        -- 1.3.6.1.4.1.2011.5.25.119.9.2.41
        hwL2vpnOamTunnelNonSupport NOTIFICATION-TYPE
            OBJECTS { hwL2vpnVcID, hwL2vpnVcType, hwL2vpnPeerAddr, hwL2vpnOamType}
            STATUS current
            DESCRIPTION 
                "This object indicates that an alarm is generated when MPLS OAM or MPLS-TP OAM for a PW detects a non-supported public network tunnel."
            ::= { hwL2vpnOamMIBTraps 41 }

        -- 1.3.6.1.4.1.2011.5.25.119.9.2.42
        hwL2vpnOamTunnelNonSupportResumed NOTIFICATION-TYPE
            OBJECTS { hwL2vpnVcID, hwL2vpnVcType, hwL2vpnPeerAddr, hwL2vpnOamType}
            STATUS current
            DESCRIPTION 
                "This object indicates that the alarm, which was generated when MPLS OAM or MPLS-TP OAM for a PW detected a non-supported public network tunnel, is cleared."
            ::= { hwL2vpnOamMIBTraps 42 }
 
--    Conformance information
-- 
		-- 1.3.6.1.4.1.2011.5.25.119.9.3
		hwL2vpnOamConformance OBJECT IDENTIFIER ::= { hwL2vpnOamTrap 3 }

		
		-- 1.3.6.1.4.1.2011.5.25.119.9.3.1
		hwL2vpnOamMIBCompliances OBJECT IDENTIFIER ::= { hwL2vpnOamConformance 1 }
		
		
		-- 1.3.6.1.4.1.2011.5.25.119.9.3.1.1
		hwL2vpnOamMIBCompliance MODULE-COMPLIANCE
			STATUS current
			DESCRIPTION 
				"The compliance statement for systems supporting the HUAWEI-L2VPN-OAM-MIB."
			MODULE -- this module
				MANDATORY-GROUPS { hwL2vpnOamGroup, hwL2vpnOamNotificationGroup }
			::= { hwL2vpnOamMIBCompliances 1 }
			
							
		-- 1.3.6.1.4.1.2011.5.25.119.9.3.2
		hwL2vpnOamGroups OBJECT IDENTIFIER ::= { hwL2vpnOamConformance 2 }

		
		-- 1.3.6.1.4.1.2011.5.25.119.9.3.2.1
		hwL2vpnOamGroup OBJECT-GROUP
			OBJECTS { hwL2vpnServiceType, hwL2vpnProtocolType, hwL2vpnVcID, hwL2vpnVcType, hwL2vpnPeerAddr, 
                                  hwL2vpnIfIndex, hwL2vpnPwMaster, hwL2vpnRmtSiteID, hwL2vpnInLabel, hwL2vpnOutLabel, 
                                  hwL2vpnIfName, hwL2vpnVsiName, hwL2vpnOamType}
			STATUS current
			DESCRIPTION 
				"The L2VPN OAM group."
			::= { hwL2vpnOamGroups 1 }
										
												
		-- 1.3.6.1.4.1.2011.5.25.119.9.3.2.2
		hwL2vpnOamNotificationGroup NOTIFICATION-GROUP
			NOTIFICATIONS { hwL2vpnOamDloc, hwL2vpnOamDlocClear, hwL2vpnOamSd1Near, hwL2vpnOamSd1NearClear,  
			                hwL2vpnOamRdi, hwL2vpnOamRdiClear, hwL2vpnOamMeg, hwL2vpnOamMegClear, 
			                hwL2vpnOamMep, hwL2vpnOamMepClear , hwL2vpnOamPeriod, hwL2vpnOamPeriodClear, 
			                hwL2vpnOamAis, hwL2vpnOamAisClear, hwL2vpnOamSd2Near, hwL2vpnOamSd2NearClear, 
			                hwL2vpnOamLck, hwL2vpnOamLckClear, hwL2vpnOamCsf, hwL2vpnOamCsfClear, 
			                hwL2vpnOamExcess, hwL2vpnOamExcessClear, hwL2vpnOamMismatch, hwL2vpnOamMismatchClear,
				        hwL2vpnOamMismerge, hwL2vpnOamMismergeClear, hwL2vpnOamFail, hwL2vpnOamFailClear,
				        hwL2vpnOamDbdi, hwL2vpnOamDbdiClear, hwL2vpnOamUnknown, hwL2vpnOamUnknownClear,
				        hwL2vpnOamLocalLock, hwL2vpnOamLocalLockClear, hwL2vpnOamSd1Far, hwL2vpnOamSd1FarClear, hwL2vpnOamSd2Far, hwL2vpnOamSd2FarClear, hwL2vpnOamFdi, hwL2vpnOamFdiClear,
                                                                               hwL2vpnOamTunnelNonSupport, hwL2vpnOamTunnelNonSupportResumed }
			STATUS current
			DESCRIPTION 
				"The L2VPN OAM Notification group."
			::= { hwL2vpnOamGroups 2 }			
			
    END

--
-- HUAWEI-L2VPN-OAM-MIB.mib
--

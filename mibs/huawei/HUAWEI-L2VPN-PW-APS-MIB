--
-- HUAWEI-L2VPN-PW-APS-MIB.mib
--

--  ==================================================================
-- Copyright (C) 2018 by  HUAWEI TECHNOLOGIES. All rights reserved.
-- 
-- Description: HUAWEI L2VPN PW APS TRAP Management MIB
-- Reference:
-- Version:     V2.16
-- History:
--              V1.0 houchengjie, 2011-04-21, publish
-- ==================================================================

    HUAWEI-L2VPN-PW-APS-MIB DEFINITIONS ::= BEGIN

        IMPORTS
            hwDatacomm
                FROM HUAWEI-MIB
            HWL2VpnVcEncapsType
                FROM HUAWEI-VPLS-EXT-MIB
            Unsigned32,OBJECT-TYPE, MODULE-IDENTITY, NOTIFICATION-TYPE
                FROM SNMPv2-SMI
            OBJECT-GROUP, MODULE-COMPLIANCE, NOTIFICATION-GROUP
                FROM SNMPv2-CONF
            RowStatus
                FROM SNMPv2-TC
            hwPWInterfaceIndex
                FROM HUAWEI-PWE3-MIB
            ifName, ifIndex            
                FROM IF-MIB
            hwL2vpnVcID,hwL2vpnVcType,hwL2vpnPeerAddr
                FROM HUAWEI-L2VPN-OAM-MIB;

        -- 1.3.6.1.4.1.2011.5.25.119.10
    hwL2vpnPwAps MODULE-IDENTITY 
        LAST-UPDATED "201801241630Z"        -- Jan 24, 2018 at 16:30GMT
        ORGANIZATION
            "Huawei Technologies Co.,Ltd."
        CONTACT-INFO 
            "Huawei Industrial Base
              Bantian, Longgang
               Shenzhen 518129
               People's Republic of China
               Website: http://www.huawei.com
               Email: support@huawei.com
             "
        DESCRIPTION 
            "The HUAWEI-L2VPN-PW-APS-MIB contains objects to
            manage PW APS."
        -- Revision history
        REVISION "201801241630Z"
             DESCRIPTION "V2.16, modify english description"

        REVISION "201801131630Z"
             DESCRIPTION "V2.15, modify english description"

        REVISION "201708041700Z"
             DESCRIPTION "V2.14, modify english description"

        REVISION "201607041400Z"
             DESCRIPTION "V2.13, modify compile error"

        REVISION "201511271400Z"
             DESCRIPTION "V2.12, add hwPwApsTunnelNonSupport hwPwApsTunnelNonSupportResumed for router"

        REVISION "201305131250Z"
             DESCRIPTION "V2.11, add hwPwApsDegraded for PTN5900"
        ::= { hwL2Vpn 10 }


--
-- Node definitions
--

--  Node definitions
-- 
        -- 1.3.6.1.4.1.2011.5.25.119
        hwL2Vpn OBJECT IDENTIFIER ::= { hwDatacomm 119 }


--           
-- The APS ALARM Attribute Group
-- 
        -- 1.3.6.1.4.1.2011.5.25.119.10.1
        hwPwApsObjects OBJECT IDENTIFIER ::= { hwL2vpnPwAps 1 }


--
-- The L2VPN's PwAps Table
-- 
        hwPwApsTable OBJECT-TYPE
            SYNTAX SEQUENCE OF HWPwApsEntry
            MAX-ACCESS not-accessible
            STATUS current
            DESCRIPTION
                "This table contains PW APS information."
            ::= { hwPwApsObjects 1 }

        hwPwApsEntry OBJECT-TYPE
            SYNTAX HWPwApsEntry
            MAX-ACCESS not-accessible
            STATUS current
            DESCRIPTION
                "Provides the information of a PW APS entry."
            INDEX { hwPwApsId }
            ::= { hwPwApsTable 1 }

        HWPwApsEntry ::=
            SEQUENCE { 
                hwPwApsId
                    Unsigned32,
                hwPwApsRole
                    INTEGER,
                hwPwApsRequestResult
                    INTEGER,
                hwPwApsState
                    INTEGER,
                hwPwApsWorkState
                    INTEGER,
                hwPwApsProtectState
                    INTEGER 
             }

        hwPwApsId OBJECT-TYPE
            SYNTAX Unsigned32
            MAX-ACCESS accessible-for-notify
            STATUS current
            DESCRIPTION
                "This object indicates the PW APS instance ID."
            ::= { hwPwApsEntry 1 }

        hwPwApsRole OBJECT-TYPE
            SYNTAX INTEGER
                {
                master(1),
                slave(2),
                unknown(255)
                }
            MAX-ACCESS read-only
            STATUS current
            DESCRIPTION
                "This object indicates the PW APS instance role."
            ::= { hwPwApsEntry 2 }

        hwPwApsRequestResult OBJECT-TYPE
            SYNTAX INTEGER
                {
                work(1),
                protect(2)
                }
            MAX-ACCESS read-only
            STATUS current
            DESCRIPTION
                "This object indicates the PW APS request result."
            ::= { hwPwApsEntry 3 }

       hwPwApsState OBJECT-TYPE
            SYNTAX INTEGER
                {
                lo(1),
                sfp(2),
                fs(3),
                sf(4),
                sdp(5),
                sd(6),
                ms(7),
                wtr(8),
                exer(9),
                rr(10),
                dnr(11),
                nr(12),
                unknown(255)
                }
            MAX-ACCESS read-only
            STATUS current
            DESCRIPTION
                "This object indicates the PW APS status."
            ::= { hwPwApsEntry 4 }

       hwPwApsWorkState OBJECT-TYPE
            SYNTAX INTEGER
                {
                nondefect(1),
                defect(2),
                defectsd(3),
                unknown(255)
                }
            MAX-ACCESS read-only
            STATUS current
            DESCRIPTION
                "This object indicates the working path status of PW APS."
            ::= { hwPwApsEntry 5 }

       hwPwApsProtectState OBJECT-TYPE
            SYNTAX INTEGER
                {
                nondefect(1),
                defect(2),
                defectsd(3),
                unknown(255)
                }
            MAX-ACCESS read-only
            STATUS current
            DESCRIPTION
                "This object indicates the protection path status of PW APS."
            ::= { hwPwApsEntry 6 }

--
-- L2VPN PW APS Trap Definitions
-- 
        -- 1.3.6.1.4.1.2011.5.25.119.10.2
        hwL2vpnPwApsTraps OBJECT IDENTIFIER ::= { hwL2vpnPwAps 2 }

        -- 1.3.6.1.4.1.2011.5.25.119.10.2.1
        hwPwApsTypeMismatch NOTIFICATION-TYPE
            OBJECTS { hwPwApsId, hwPWInterfaceIndex }
            STATUS current
            DESCRIPTION 
                "This object indicates that APS reports an alarm when protection types in APS packets received from the remote end and those on the local end are inconsistent."
            ::= { hwL2vpnPwApsTraps 1 }

        -- 1.3.6.1.4.1.2011.5.25.119.10.2.2
        hwPwApsTypeMismatchClear NOTIFICATION-TYPE
            OBJECTS { hwPwApsId, hwPWInterfaceIndex }
            STATUS current
            DESCRIPTION 
                "This object indicates that the APS-reported alarm for the protection type inconsistency in APS packets received from the remote end and those on the local end is cleared."
            ::= { hwL2vpnPwApsTraps 2 }

        -- 1.3.6.1.4.1.2011.5.25.119.10.2.3
        hwPwApsPathMismatch  NOTIFICATION-TYPE
            OBJECTS { hwPwApsId, hwPWInterfaceIndex }
            STATUS current
            DESCRIPTION 
                "This object indicates that APS reports an alarm when information about the working and protection paths in APS packets received from the remote end is inconsistent with that on the local end."
            ::= { hwL2vpnPwApsTraps 3 }

        -- 1.3.6.1.4.1.2011.5.25.119.10.2.4
        hwPwApsPathMismatchClear NOTIFICATION-TYPE
            OBJECTS { hwPwApsId, hwPWInterfaceIndex }
            STATUS current
            DESCRIPTION 
                "This object indicates that the APS-reported alarm for the information (about the working and protection paths in received APS packets) inconsistency between the remote and local ends is cleared."
            ::= { hwL2vpnPwApsTraps 4 }

        -- 1.3.6.1.4.1.2011.5.25.119.10.2.5
        hwPwApsSwitchFail  NOTIFICATION-TYPE
            OBJECTS { hwPwApsId, hwPWInterfaceIndex }
            STATUS current
            DESCRIPTION 
                "This object indicates that APS reports an alarm when the traffic switching results between the local and remote ends are inconsistent."
            ::= { hwL2vpnPwApsTraps 5 }

        -- 1.3.6.1.4.1.2011.5.25.119.10.2.6
        hwPwApsSwitchFailClear NOTIFICATION-TYPE
            OBJECTS { hwPwApsId, hwPWInterfaceIndex }
            STATUS current
            DESCRIPTION 
                "This object indicates that the APS-reported alarm for the inconsistency of the traffic switching results between the local and remote ends is cleared."
            ::= { hwL2vpnPwApsTraps 6 }

        -- 1.3.6.1.4.1.2011.5.25.119.10.2.7
        hwPwApsLost  NOTIFICATION-TYPE
            OBJECTS { hwPwApsId, hwPWInterfaceIndex }
            STATUS current
            DESCRIPTION 
                "This object indicates that APS reports an alarm when APS packets are lost."
            ::= { hwL2vpnPwApsTraps 7 }

        -- 1.3.6.1.4.1.2011.5.25.119.10.2.8
        hwPwApsLostClear NOTIFICATION-TYPE
            OBJECTS { hwPwApsId, hwPWInterfaceIndex }
            STATUS current
            DESCRIPTION 
                "This object indicates that the APS-reported alarm for the loss of APS packets is cleared."
            ::= { hwL2vpnPwApsTraps 8 }

        -- 1.3.6.1.4.1.2011.5.25.119.10.2.9
        hwPwApsIdMismatch  NOTIFICATION-TYPE
            OBJECTS { hwPwApsId, hwPWInterfaceIndex }
            STATUS current
            DESCRIPTION 
                "This object indicates that APS reports an alarm when the APS IDs of the master and backup RSGs do not match."
            ::= { hwL2vpnPwApsTraps 9 }

        -- 1.3.6.1.4.1.2011.5.25.119.10.2.10
        hwPwApsIdMismatchClear NOTIFICATION-TYPE
            OBJECTS { hwPwApsId, hwPWInterfaceIndex }
            STATUS current
            DESCRIPTION 
                "This object indicates that the APS-reported alarm for the APS ID inconsistency between the master and backup RSGs is cleared."
            ::= { hwL2vpnPwApsTraps 10 }

        -- 1.3.6.1.4.1.2011.5.25.119.10.2.11
        hwPwApsBypassPwMismatch  NOTIFICATION-TYPE
            OBJECTS { hwPwApsId, hwPWInterfaceIndex }
            STATUS current
            DESCRIPTION 
                "This object indicates that APS reports an alarm when the bypass PW between the master and backup RSGs is unavailable."
            ::= { hwL2vpnPwApsTraps 11 }

        -- 1.3.6.1.4.1.2011.5.25.119.10.2.12
        hwPwApsBypssPwMismatchClear NOTIFICATION-TYPE
            OBJECTS { hwPwApsId, hwPWInterfaceIndex }
            STATUS current
            DESCRIPTION 
                "This object indicates that the APS-reported alarm for the unavailability of the bypass PW between the master and backup RSGs is cleared."
            ::= { hwL2vpnPwApsTraps 12 }

        -- 1.3.6.1.4.1.2011.5.25.119.10.2.13
        hwPwApsSwitchEvent NOTIFICATION-TYPE
            OBJECTS { hwPwApsRole, hwPwApsRequestResult, hwPwApsState, hwPwApsWorkState, 
                      hwPwApsProtectState }
            STATUS current
            DESCRIPTION 
                "This object indicates that the PW APS status has changed."
            ::= { hwL2vpnPwApsTraps 13 }

        -- 1.3.6.1.4.1.2011.5.25.119.10.2.14
        hwPwApsOutAge  NOTIFICATION-TYPE
            OBJECTS { hwPwApsId, hwPWInterfaceIndex }
            STATUS current
            DESCRIPTION 
                "This object indicates that an alarm is generated when both the primary and secondary PWs in an APS protection group fail."
            ::= { hwL2vpnPwApsTraps 14 }
        -- 1.3.6.1.4.1.2011.5.25.119.10.2.15
        hwPwApsOutAgeClear NOTIFICATION-TYPE
            OBJECTS { hwPwApsId, hwPWInterfaceIndex }
            STATUS current
            DESCRIPTION 
                "This object indicates that the alarm can be cleared after one PW in the APS protection group recovers."
            ::= { hwL2vpnPwApsTraps 15 }

        -- 1.3.6.1.4.1.2011.5.25.119.10.2.16
        hwPwApsDegraded  NOTIFICATION-TYPE
            OBJECTS { hwPwApsId, hwPWInterfaceIndex }
            STATUS current
            DESCRIPTION 
                "This object indicates that an alarm is generated when a PW in the APS protection group is degraded."
            ::= { hwL2vpnPwApsTraps 16 }
        -- 1.3.6.1.4.1.2011.5.25.119.10.2.17
        hwPwApsDegradedClear NOTIFICATION-TYPE
            OBJECTS { hwPwApsId, hwPWInterfaceIndex }
            STATUS current
            DESCRIPTION 
                "This object indicates that the alarm for the degraded PW in the APS protection group is cleared."
            ::= { hwL2vpnPwApsTraps 17 }

        -- 1.3.6.1.4.1.2011.5.25.119.10.2.18
        hwPwApsTunnelNonSupport NOTIFICATION-TYPE
            OBJECTS { hwL2vpnVcID, hwL2vpnVcType, hwL2vpnPeerAddr}
            STATUS current
            DESCRIPTION 
                "This object indicates that PW APS does not support the current public network tunnel."
            ::= { hwL2vpnPwApsTraps 18 }

        -- 1.3.6.1.4.1.2011.5.25.119.10.2.19
        hwPwApsTunnelNonSupportResumed NOTIFICATION-TYPE
            OBJECTS { hwL2vpnVcID, hwL2vpnVcType, hwL2vpnPeerAddr}
            STATUS current
            DESCRIPTION 
                "This object indicates that the alarm, which indicated that PW APS did not support the current public network tunnel, is cleared."
            ::= { hwL2vpnPwApsTraps 19 }

-- the mib object of hwL2vpnPwApsScalarsObject is reserved
-- L2VPN PW APS Scalars Object Definitions
--
           hwL2vpnPwApsScalarsObject OBJECT IDENTIFIER ::= { hwL2vpnPwAps 3 }

--    Conformance information
--

                -- 1.3.6.1.4.1.2011.5.25.119.10.3
                hwPwApsMIBConformance OBJECT IDENTIFIER ::= { hwL2vpnPwAps 4 }


                -- 1.3.6.1.4.1.2011.5.25.119.10.3.1
                hwPwApsMIBCompliances OBJECT IDENTIFIER ::= { hwPwApsMIBConformance 1 }


                -- 1.3.6.1.4.1.2011.5.25.119.10.3.1.1
                hwPwApsMIBCompliance MODULE-COMPLIANCE
                        STATUS current
                        DESCRIPTION 
                                "The compliance statement for systems supporting the HUAWEI-L2VPN-PW-APS-MIB."
                        MODULE -- this module
                                MANDATORY-GROUPS { hwPwApsGroup, hwPwApsNotificationGroup }
                        ::= { hwPwApsMIBCompliances 1 }


                -- 1.3.6.1.4.1.2011.5.25.119.10.3.2
                hwPwApsMIBGroups OBJECT IDENTIFIER ::= { hwPwApsMIBConformance 2 }


                -- 1.3.6.1.4.1.2011.5.25.119.10.3.2.1
                hwPwApsGroup OBJECT-GROUP
                        OBJECTS { hwPwApsId, hwPwApsRole, hwPwApsRequestResult, hwPwApsState, 
                                  hwPwApsWorkState, hwPwApsProtectState }
                        STATUS current
                        DESCRIPTION 
                                "The PW APS group."
                        ::= { hwPwApsMIBGroups 1 }


                -- 1.3.6.1.4.1.2011.5.25.119.10.3.2.2
                hwPwApsNotificationGroup NOTIFICATION-GROUP
                        NOTIFICATIONS { hwPwApsTypeMismatch, hwPwApsTypeMismatchClear, hwPwApsPathMismatch, hwPwApsPathMismatchClear, 
                                        hwPwApsSwitchFail, hwPwApsSwitchFailClear, hwPwApsLost, hwPwApsLostClear ,
                                        hwPwApsIdMismatch, hwPwApsIdMismatchClear, hwPwApsBypassPwMismatch, hwPwApsBypssPwMismatchClear,
                                        hwPwApsSwitchEvent, hwPwApsOutAge, hwPwApsOutAgeClear, hwPwApsDegraded, hwPwApsDegradedClear,
                                        hwPwApsTunnelNonSupport, hwPwApsTunnelNonSupportResumed}
                        STATUS current
                        DESCRIPTION 
                                "The PW APS Notification group."
                        ::= { hwPwApsMIBGroups 2 }

    END

--
-- HUAWEI-L2VPN-PW-APS-MIB.mib
--

-- =================================================================
-- Copyright (C) 2014 by  HUAWEI TECHNOLOGIES. All rights reserved.
--
-- Description:HUAWEI-ESAP-MDNS-GATEWAY
-- Reference:
-- Version: V1.00
-- History:
--
-- =================================================================

    HUAWEI-MDNS-RELAY-MIB DEFINITIONS ::= BEGIN

        IMPORTS
            hwDatacomm
                FROM HUAWEI-MIB
            OBJECT-GROUP, NOTIFICATION-GROUP, MODULE-COMPLIANCE
                FROM SNMPv2-CONF
            TimeTicks, IpAddress, Integer32, Gauge32, OBJECT-TYPE,
            MODULE-IDENTITY, NOTIFICATION-TYPE
                FROM SNMPv2-SMI;
                
        hwMdnsRelayMIB MODULE-IDENTITY
            LAST-UPDATED "201401061116Z"
            ORGANIZATION
                "Huawei Technologies Co.,Ltd."
            CONTACT-INFO
                "Huawei Industrial Base
                  Bantian, Longgang
                   Shenzhen 518129
                   People's Republic of China
                   Website: http://www.huawei.com
                   Email: support@huawei.com"
                   
            DESCRIPTION
                "This MIB describes mDNS objects used for mDNS relay configuration."
                       
            REVISION    "201401061116Z"
            
            DESCRIPTION
                "This MIB describes modify mDNS objects."
                       
            REVISION    "201401061116Z"
            
            DESCRIPTION
                "The MIB contains objects of huawei-esap-mDNS."
            ::= { hwDatacomm 326 }
            
            hwMdnsRelayObjects OBJECT IDENTIFIER ::= { hwMdnsRelayMIB 1 }

-- node definitions

	hwMdnsRelayGatewayIPGlobal OBJECT-TYPE
	        SYNTAX     IpAddress
	        MAX-ACCESS read-write
	        STATUS current
	        DESCRIPTION
	            "This item shows the mDNS gateway ip.
                    Users can also set gateway ip through this item "
	        ::= { hwMdnsRelayObjects 1 }
        
	hwMdnsRelaySourceIPGlobal OBJECT-TYPE
                SYNTAX IpAddress
                MAX-ACCESS read-write
                STATUS current
                DESCRIPTION
                "
                This item shows the source ip of mDNS relay.
                Users can also set source ip through this item.
                "
                ::= { hwMdnsRelayObjects 2 }
                
                

-- mDNS relay configuration table
        hwMdnsRelayCfgTable OBJECT-TYPE
            SYNTAX SEQUENCE OF HwMdnsRelayCfgEntry
            MAX-ACCESS not-accessible
            STATUS current
            DESCRIPTION
                "This item shows the configuration of mDNS relay."
            ::= { hwMdnsRelayObjects 3 }

            hwMdnsRelayCfgEntry OBJECT-TYPE
                SYNTAX HwMdnsRelayCfgEntry
                MAX-ACCESS not-accessible
                STATUS current
                DESCRIPTION
                    "The mDNS relay configuration table struct."
                INDEX { hwMdnsRelayVlanId }
                ::= { hwMdnsRelayCfgTable 1 }

            HwMdnsRelayCfgEntry ::=
                SEQUENCE {
                    hwMdnsRelayVlanId
                        Integer32,
                    hwMdnsRelayEnable
                        INTEGER,
                    hwMdnsRelayProbeInterval
                        Integer32
                   }

-- mDNS relay configuration table index
                hwMdnsRelayVlanId OBJECT-TYPE
                    SYNTAX Integer32(1..4094)
                    MAX-ACCESS not-accessible
                    STATUS current
                    DESCRIPTION
                        "The VLAN-ID or other identifier referring to this VLAN."
                    ::= { hwMdnsRelayCfgEntry 1 }

-- mDNS relay enable status 
                hwMdnsRelayEnable OBJECT-TYPE
                    SYNTAX INTEGER
                    {
	                enable(1),
	                disable(0)
                    }
                    MAX-ACCESS read-write
                    STATUS current
                    DESCRIPTION
                    "This item shows the enable status of mDNS relay."
                    ::= { hwMdnsRelayCfgEntry 2 }

-- mDNS relay probe interval node
                hwMdnsRelayProbeInterval OBJECT-TYPE
                    SYNTAX Integer32 (0|60..38400)
                    MAX-ACCESS read-write
                    STATUS current
                    DESCRIPTION
                    "This item shows the service probe interval of mDNS relay.
                    Users can also set service probe interval through this item."
                    ::= { hwMdnsRelayCfgEntry 3 }
                                                                  

                                                                  



-- mDNS relay mib conformance
       hwMdnsRelayMibConformance OBJECT IDENTIFIER ::= { hwMdnsRelayMIB 2 }
       
       hwMdnsRelayMibGroups OBJECT IDENTIFIER ::= { hwMdnsRelayMibConformance 1 }
       
       hwMdnsRelayMibGroup OBJECT-GROUP
       OBJECTS { hwMdnsRelayGatewayIPGlobal, hwMdnsRelaySourceIPGlobal, hwMdnsRelayVlanId, hwMdnsRelayEnable, hwMdnsRelayProbeInterval }
            STATUS current
            DESCRIPTION
                "This is the mDNS relay cfg group."
            ::= { hwMdnsRelayMibGroups 1 } 
            
       hwMdnsRelayMIBCompliances OBJECT IDENTIFIER ::= { hwMdnsRelayMibConformance 2 }
       hwMdnsRelayMIBCompliance MODULE-COMPLIANCE
            STATUS current
            DESCRIPTION
                "The compliance statement for entities which implement the hwMdnsRelayMIB."
            MODULE
                MANDATORY-GROUPS {hwMdnsRelayMibGroup}
            ::= { hwMdnsRelayMIBCompliances 1 }


END

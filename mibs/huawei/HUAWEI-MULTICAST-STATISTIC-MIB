-- ============================================================================
-- Copyright (C) 2018 by  HUAWEI TECHNOLOGIES. All rights reserved.
-- 
-- Description: HUAWEI-MULTICAST-STATISTIC-MIB 
-- Reference:  
-- Version: V2.04
-- History:
--    Created by yaoli 00175617 2011-06-15
--    Modified by liuhongwu  2018-06-11
-- ============================================================================
HUAWEI-MULTICAST-STATISTIC-MIB DEFINITIONS ::= BEGIN
IMPORTS 
    MODULE-IDENTITY,OBJECT-TYPE, 
    Counter32,Integer32,Unsigned32,IpAddress, NOTIFICATION-TYPE,Counter64
        FROM SNMPv2-SMI
    InetAddress, InetAddressType
        FROM INET-ADDRESS-MIB
    TruthValue,TEXTUAL-CONVENTION,
    RowStatus,MacAddress,DisplayString
        FROM SNMPv2-TC
    MODULE-COMPLIANCE, OBJECT-GROUP, NOTIFICATION-GROUP
        FROM SNMPv2-CONF 
    hwDatacomm
        FROM HUAWEI-MIB; 
            
hwMulticastStatisticMIB MODULE-IDENTITY
    LAST-UPDATED "201806110000Z" 
    ORGANIZATION "Huawei Technologies Co.,Ltd."
    CONTACT-INFO 
"Huawei Industrial Base
  Bantian, Longgang
   Shenzhen 518129
   People's Republic of China
   Website: http://www.huawei.com
   Email: support@huawei.com
 "
    DESCRIPTION 
        "This MIB contains private managed object definitions
         for multicast statistics."  
    REVISION    "201806110000Z"
    DESCRIPTION "Add Unsigned32 instead of COUNTER64"
    REVISION    "201803010000Z"
    DESCRIPTION "Modify description of hwMulticastFlowStatisticsAddressType hwMulticastFlowStatisticsSourceIPAddress hwMulticastFlowStatisticsGroupIPAddress hwMulticastFlowStatisticsCeVLAN hwMulticastFlowStatisticsPeVLAN hwMulticastFlowStatisticsIfName hwMulticastFlowStatisticsMatchedPacketsSpeed hwMulticastFlowStatisticsMatchedBytesSpeed hwMulticastFlowStatisticsMatchedPackets hwMulticastFlowStatisticsMatchedBytes."       
    REVISION    "201801180000Z"
    DESCRIPTION "Modify description of hwMulticastFlowStatisticsDirection."       
    REVISION    "201608120000Z"
    DESCRIPTION "Add MatchedPackets and MatchedBytes to MIB file."       
    ::= { hwDatacomm 245 }
    
--    hwMulticastFlowStatisticObject  
hwMulticastFlowStatisticObject   
    OBJECT IDENTIFIER ::= { hwMulticastStatisticMIB 1 }
      
--    hwMulticastFlowStatisticsTable
hwMulticastFlowStatisticsTable OBJECT-TYPE
    SYNTAX SEQUENCE OF HwMulticastFlowStatisticsEntry
    MAX-ACCESS not-accessible
    STATUS current
    DESCRIPTION
        "Table that contains multicast flow statistics information."
    ::= { hwMulticastFlowStatisticObject 1 }

hwMulticastFlowStatisticsEntry OBJECT-TYPE
    SYNTAX HwMulticastFlowStatisticsEntry
    MAX-ACCESS not-accessible
    STATUS current
    DESCRIPTION
        "Entry for multicast flow statistics information."
    INDEX { hwMulticastFlowStatisticsAddressType,hwMulticastFlowStatisticsSourceIPAddress,hwMulticastFlowStatisticsGroupIPAddress,hwMulticastFlowStatisticsCeVLAN,hwMulticastFlowStatisticsPeVLAN,hwMulticastFlowStatisticsIfName,hwMulticastFlowStatisticsDirection }
    ::= { hwMulticastFlowStatisticsTable 1 }
    
HwMulticastFlowStatisticsEntry ::= SEQUENCE {
	hwMulticastFlowStatisticsAddressType          InetAddressType, 
    hwMulticastFlowStatisticsSourceIPAddress      InetAddress,
    hwMulticastFlowStatisticsGroupIPAddress       InetAddress,
    hwMulticastFlowStatisticsCeVLAN               Unsigned32,
    hwMulticastFlowStatisticsPeVLAN               Unsigned32,
    hwMulticastFlowStatisticsIfName               OCTET STRING,
    hwMulticastFlowStatisticsDirection            TruthValue,   
    hwMulticastFlowStatisticsMatchedPacketsSpeed  Counter64,
    hwMulticastFlowStatisticsMatchedBytesSpeed    Counter64,
    hwMulticastFlowStatisticsMatchedPackets  Counter64,
    hwMulticastFlowStatisticsMatchedBytes    Counter64
    }
    
hwMulticastFlowStatisticsAddressType OBJECT-TYPE
    SYNTAX InetAddressType (1..2)
    MAX-ACCESS not-accessible
    STATUS current
    DESCRIPTION "This object indicates the address type."
    ::= { hwMulticastFlowStatisticsEntry 1 }
        
hwMulticastFlowStatisticsSourceIPAddress OBJECT-TYPE
    SYNTAX InetAddress (SIZE (4|8|16|20))
    MAX-ACCESS not-accessible
    STATUS current
    DESCRIPTION
        "This object indicates the source IP address."
    ::= { hwMulticastFlowStatisticsEntry 2 }

hwMulticastFlowStatisticsGroupIPAddress OBJECT-TYPE
    SYNTAX InetAddress (SIZE (4|8|16|20))
    MAX-ACCESS not-accessible
    STATUS current
    DESCRIPTION
        "This object indicates the group IP address."
    ::= { hwMulticastFlowStatisticsEntry 3 }
    
hwMulticastFlowStatisticsCeVLAN OBJECT-TYPE
    SYNTAX Unsigned32 (0..4094)
    MAX-ACCESS not-accessible
    STATUS current
    DESCRIPTION
        "This object indicates the inner VLAN ID."
    ::= { hwMulticastFlowStatisticsEntry 4 }
    
hwMulticastFlowStatisticsPeVLAN OBJECT-TYPE
    SYNTAX Unsigned32 (0..4094)
    MAX-ACCESS not-accessible
    STATUS current
    DESCRIPTION
        "This object indicates the outer VLAN ID."
    ::= { hwMulticastFlowStatisticsEntry 5 } 
    
hwMulticastFlowStatisticsIfName OBJECT-TYPE
    SYNTAX OCTET STRING (SIZE(1..63))
    MAX-ACCESS not-accessible
    STATUS current
    DESCRIPTION
        "This object indicates the interface name."
    ::= { hwMulticastFlowStatisticsEntry 6 }
    
hwMulticastFlowStatisticsDirection OBJECT-TYPE
    SYNTAX TruthValue (1..2)
    MAX-ACCESS not-accessible
    STATUS current
    DESCRIPTION
        "This object indicates the flow direction. The value true indicates the inbound direction, and false indicates the outbound direction."
    ::= { hwMulticastFlowStatisticsEntry 7 }

hwMulticastFlowStatisticsMatchedPacketsSpeed OBJECT-TYPE
    SYNTAX Counter64
    MAX-ACCESS read-only
    STATUS current
    DESCRIPTION
        "This object indicates the number of packets sent or received per second in the statistics collection period."
    ::= { hwMulticastFlowStatisticsEntry 8 }
    
hwMulticastFlowStatisticsMatchedBytesSpeed OBJECT-TYPE                                                          
    SYNTAX Counter64
    MAX-ACCESS read-only
    STATUS current
    DESCRIPTION
        "This object indicates the number of bytes sent or received per second in the statistics collection period."
    ::= { hwMulticastFlowStatisticsEntry 9 }
 
hwMulticastFlowStatisticsMatchedPackets OBJECT-TYPE
    SYNTAX Counter64
    MAX-ACCESS read-only
    STATUS current
    DESCRIPTION
        "This object indicates the number of packets."
    ::= { hwMulticastFlowStatisticsEntry 10 }
    
hwMulticastFlowStatisticsMatchedBytes OBJECT-TYPE                                                          
    SYNTAX Counter64
    MAX-ACCESS read-only
    STATUS current
    DESCRIPTION
        "This object indicates the number of bytes."
    ::= { hwMulticastFlowStatisticsEntry 11 }

--    hwMulticastFlowStatisticObjectExt
hwMulticastFlowStatisticObjectExt   
    OBJECT IDENTIFIER ::= { hwMulticastStatisticMIB 3 }
      
--    hwMulticastFlowStatisticsExtTable
hwMulticastFlowStatisticsExtTable OBJECT-TYPE
    SYNTAX SEQUENCE OF HwMulticastFlowStatisticsExtEntry
    MAX-ACCESS not-accessible
    STATUS current
    DESCRIPTION
        "Table that contains multicast flow statistics information."
    ::= { hwMulticastFlowStatisticObjectExt 1 }

hwMulticastFlowStatisticsExtEntry OBJECT-TYPE
    SYNTAX HwMulticastFlowStatisticsExtEntry
    MAX-ACCESS not-accessible
    STATUS current
    DESCRIPTION
        "Entry for multicast flow statistics information."
    INDEX { hwMulticastFlowStatisticsAddressTypeExt,hwMulticastFlowStatisticsSourceIPAddressExt,hwMulticastFlowStatisticsGroupIPAddressExt,hwMulticastFlowStatisticsCeVLANExt,hwMulticastFlowStatisticsPeVLANExt,hwMulticastFlowStatisticsIfNameExt,hwMulticastFlowStatisticsDirectionExt }
    ::= { hwMulticastFlowStatisticsExtTable 1 }
    
HwMulticastFlowStatisticsExtEntry ::= SEQUENCE {
    hwMulticastFlowStatisticsAddressTypeExt          InetAddressType, 
    hwMulticastFlowStatisticsSourceIPAddressExt      InetAddress,
    hwMulticastFlowStatisticsGroupIPAddressExt       InetAddress,
    hwMulticastFlowStatisticsCeVLANExt               Unsigned32,
    hwMulticastFlowStatisticsPeVLANExt               Unsigned32,
    hwMulticastFlowStatisticsIfNameExt               OCTET STRING,
    hwMulticastFlowStatisticsDirectionExt            TruthValue,   
    hwMulticastFlowStatisticsMatchedPacketsSpeedHighExt  Unsigned32,
    hwMulticastFlowStatisticsMatchedPacketsSpeedLowExt  Unsigned32,
    hwMulticastFlowStatisticsMatchedBytesSpeedHighExt    Unsigned32,
    hwMulticastFlowStatisticsMatchedBytesSpeedLowExt    Unsigned32,
    hwMulticastFlowStatisticsMatchedPacketsHighExt  Unsigned32,
    hwMulticastFlowStatisticsMatchedPacketsLowExt  Unsigned32,
    hwMulticastFlowStatisticsMatchedBytesHighExt    Unsigned32,
    hwMulticastFlowStatisticsMatchedBytesLowExt    Unsigned32
    }
    
hwMulticastFlowStatisticsAddressTypeExt OBJECT-TYPE
    SYNTAX InetAddressType (1..2)
    MAX-ACCESS not-accessible
    STATUS current
    DESCRIPTION "This object indicates the address type."
    ::= { hwMulticastFlowStatisticsExtEntry 1 }
        
hwMulticastFlowStatisticsSourceIPAddressExt OBJECT-TYPE
    SYNTAX InetAddress (SIZE (4|8|16|20))
    MAX-ACCESS not-accessible
    STATUS current
    DESCRIPTION
        "This object indicates the source IP address."
    ::= { hwMulticastFlowStatisticsExtEntry 2 }

hwMulticastFlowStatisticsGroupIPAddressExt OBJECT-TYPE
    SYNTAX InetAddress (SIZE (4|8|16|20))
    MAX-ACCESS not-accessible
    STATUS current
    DESCRIPTION
        "This object indicates the group IP address."
    ::= { hwMulticastFlowStatisticsExtEntry 3 }
    
hwMulticastFlowStatisticsCeVLANExt OBJECT-TYPE
    SYNTAX Unsigned32 (0..4094)
    MAX-ACCESS not-accessible
    STATUS current
    DESCRIPTION
        "This object indicates the inner VLAN ID."
    ::= { hwMulticastFlowStatisticsExtEntry 4 }
    
hwMulticastFlowStatisticsPeVLANExt OBJECT-TYPE
    SYNTAX Unsigned32 (0..4094)
    MAX-ACCESS not-accessible
    STATUS current
    DESCRIPTION
        "This object indicates the outer VLAN ID."
    ::= { hwMulticastFlowStatisticsExtEntry 5 } 
    
hwMulticastFlowStatisticsIfNameExt OBJECT-TYPE
    SYNTAX OCTET STRING (SIZE(1..63))
    MAX-ACCESS not-accessible
    STATUS current
    DESCRIPTION
        "This object indicates the interface name."
    ::= { hwMulticastFlowStatisticsExtEntry 6 }
    
hwMulticastFlowStatisticsDirectionExt OBJECT-TYPE
    SYNTAX TruthValue (1..2)
    MAX-ACCESS not-accessible
    STATUS current
    DESCRIPTION
        "This object indicates the flow direction. The value true indicates the inbound direction, and false indicates the outbound direction."
    ::= { hwMulticastFlowStatisticsExtEntry 7 }

hwMulticastFlowStatisticsMatchedPacketsSpeedHighExt OBJECT-TYPE
    SYNTAX Unsigned32
    MAX-ACCESS read-only
    STATUS current
    DESCRIPTION
        "This object indicates the number of packets sent or received per second in the statistics collection period."
    ::= { hwMulticastFlowStatisticsExtEntry 8 }
hwMulticastFlowStatisticsMatchedPacketsSpeedLowExt OBJECT-TYPE
    SYNTAX Unsigned32
    MAX-ACCESS read-only
    STATUS current
    DESCRIPTION
        "This object indicates the number of packets sent or received per second in the statistics collection period."
    ::= { hwMulticastFlowStatisticsExtEntry 9 }
    
hwMulticastFlowStatisticsMatchedBytesSpeedHighExt OBJECT-TYPE
    SYNTAX Unsigned32
    MAX-ACCESS read-only
    STATUS current
    DESCRIPTION
        "This object indicates the number of bytes sent or received per second in the statistics collection period."
    ::= { hwMulticastFlowStatisticsExtEntry 10 }
hwMulticastFlowStatisticsMatchedBytesSpeedLowExt OBJECT-TYPE
    SYNTAX Unsigned32
    MAX-ACCESS read-only
    STATUS current
    DESCRIPTION
        "This object indicates the number of bytes sent or received per second in the statistics collection period."
    ::= { hwMulticastFlowStatisticsExtEntry 11 } 
hwMulticastFlowStatisticsMatchedPacketsHighExt OBJECT-TYPE
    SYNTAX Unsigned32
    MAX-ACCESS read-only
    STATUS current
    DESCRIPTION
        "This object indicates the number of packets."
    ::= { hwMulticastFlowStatisticsExtEntry 12 }
hwMulticastFlowStatisticsMatchedPacketsLowExt OBJECT-TYPE
    SYNTAX Unsigned32
    MAX-ACCESS read-only
    STATUS current
    DESCRIPTION
        "This object indicates the number of packets."
    ::= { hwMulticastFlowStatisticsExtEntry 13 }
hwMulticastFlowStatisticsMatchedBytesHighExt OBJECT-TYPE                                                          
    SYNTAX Unsigned32
    MAX-ACCESS read-only
    STATUS current
    DESCRIPTION
        "This object indicates the number of bytes."
    ::= { hwMulticastFlowStatisticsExtEntry 14 }
hwMulticastFlowStatisticsMatchedBytesLowExt OBJECT-TYPE                                                          
    SYNTAX Unsigned32
    MAX-ACCESS read-only
    STATUS current
    DESCRIPTION
        "This object indicates the number of bytes."
    ::= { hwMulticastFlowStatisticsExtEntry 15 }
--  Conformance information
        hwMulticastStatisticMIBConformance OBJECT IDENTIFIER ::= { hwMulticastStatisticMIB 2 }
        hwMulticastStatisticMIBCompliances OBJECT IDENTIFIER ::= { hwMulticastStatisticMIBConformance 1 }
        hwMulticastFlowStatisticMIBCompliance MODULE-COMPLIANCE
            STATUS current
            DESCRIPTION 
                "Compliance of multicast statistics module."
            MODULE
                MANDATORY-GROUPS { hwMulticastFlowStatisticGroup }
            ::= { hwMulticastStatisticMIBCompliances 1 } 
            
        hwMulticastStatisticMIBGroups OBJECT IDENTIFIER ::= { hwMulticastStatisticMIBConformance 2 }
        hwMulticastFlowStatisticGroup OBJECT-GROUP
            OBJECTS { 
            hwMulticastFlowStatisticsMatchedPacketsSpeed,
            hwMulticastFlowStatisticsMatchedBytesSpeed,
            hwMulticastFlowStatisticsMatchedPacketsSpeedHighExt,
            hwMulticastFlowStatisticsMatchedPacketsSpeedLowExt,
            hwMulticastFlowStatisticsMatchedBytesSpeedHighExt,
            hwMulticastFlowStatisticsMatchedBytesSpeedLowExt
            }
            STATUS current
            DESCRIPTION 
                "Multicast flow statistics table group."
            ::= { hwMulticastStatisticMIBGroups 1 }    
END

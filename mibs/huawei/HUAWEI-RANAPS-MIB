-- Copyright (C) 2018 by HUAWEI TECHNOLOGIES. All rights reserved.
-- Description: HUAWEI Private Extended Interface MIB
-- Reference:
-- Version: V2.19
-- History:
--      V1.0 
-- ==================================================================
-- ==================================================================
-- 
-- Varibles and types be imported
--
-- ==================================================================
HUAWEI-RANAPS-MIB DEFINITIONS ::= BEGIN

    IMPORTS         
    	InterfaceIndex, ifName,ifIndex			
			FROM IF-MIB                
    	OBJECT-GROUP, MODULE-COMPLIANCE, NOTIFICATION-GROUP            
			FROM SNMPv2-CONF  	          
    	IpAddress, Integer32, Unsigned32, OBJECT-TYPE,MODULE-IDENTITY, NOTIFICATION-TYPE            
        	FROM SNMPv2-SMI                           
    	PhysAddress,RowStatus            
        	FROM SNMPv2-TC 
    	hwDatacomm
        	FROM HUAWEI-MIB;
  
    hwRanApsMIB MODULE-IDENTITY
        LAST-UPDATED "201801131700Z"          -- Jan 13, 2018 at 17:00 GMT

        ORGANIZATION 
"Huawei Technologies Co.,Ltd."
        CONTACT-INFO 
"Huawei Industrial Base
  Bantian, Longgang
   Shenzhen 518129
   People's Republic of China
   Website: http://www.huawei.com
   Email: support@huawei.com
 "
       
        DESCRIPTION
            "Added trap node hwRanApsK1K2MisResume which corresponds to hwRanApsK1K2Mismatch."

        REVISION "201801131700Z"
        DESCRIPTION
            "modify node description."
		
        REVISION "201604281020Z"
        DESCRIPTION
            "Added node hwRanApsAntiReplay which indicates the anti-replay function."

        REVISION "201512191645Z"
        DESCRIPTION
            "Added available value <48> of hwRanApsAuthenticateString."

        REVISION "201512111645Z"
        DESCRIPTION
            "Added available value sha2(4) of hwRanApsAuthenticateType."

        REVISION "201509151645Z"
        DESCRIPTION
            "Added available value hmac(3) of hwRanApsAuthenticateType."        

        REVISION "201406111645Z"
        DESCRIPTION
            "Added available value forceback(4) and manualback(5) of hwRanApsProtectSwitch."

        REVISION "201406111645Z"
        DESCRIPTION
            "Added available value forceback(4) and manualback(5) of hwRanApsProtectSwitch."
 
        REVISION "201402151717Z"
        DESCRIPTION
            "Added available value forceback(4) and manualback(5) of hwRanApsProtectSwitch."
           
        REVISION "201402151717Z"
        DESCRIPTION
            "Added available value forceback(4) and manualback(5) of hwRanApsProtectSwitch."

        REVISION "200906020000Z"
        DESCRIPTION
            "This file is an Automatic Protection Switching MIB. It provides some 
            APS configurations MIB and some APS alarms."
            ::= { hwDatacomm 200 }  
         
      -- Textual Convention

-- ============================================================================
-- Node definitions
-- ============================================================================ 

    -- 1.3.6.1.4.1.2011.5.25.200.1
 
    hwRanApsObjects OBJECT IDENTIFIER ::= { hwRanApsMIB 1 }
        

-- ============================================================================
--
-- ======================= Objects definitions=================================
--
-- ============================================================================  
  
  		hwRanApsProtectionTable OBJECT-TYPE
			SYNTAX SEQUENCE OF HwRanApsProtectionEntry
			MAX-ACCESS not-accessible
			STATUS current
			DESCRIPTION
				"APS protection configuration."
			::= { hwRanApsObjects 1 }	

		hwRanApsProtectionEntry OBJECT-TYPE
			SYNTAX HwRanApsProtectionEntry
			MAX-ACCESS not-accessible
			STATUS current
			DESCRIPTION
				"APS protection configuration entry."
			INDEX { hwRanApsProGroupIdIndex,hwRanApsIfIndexIndex }
			::= { hwRanApsProtectionTable 1 }
		
		HwRanApsProtectionEntry ::=
			SEQUENCE {
				hwRanApsProGroupIdIndex 
					Unsigned32,
				hwRanApsIfIndexIndex 
					InterfaceIndex,				 
				hwRanApsProtectionGroupNum 
					Unsigned32,
				hwRanApsIfIndex 
					InterfaceIndex,
				hwRanApsIfType
					INTEGER, 
				hwRanApsRestoreWaitTime  
					Integer32,
				hwRanApsProtectSwitch 
					INTEGER,
				hwRanApsProtectMode
					INTEGER,
				hwRanApsWorkingIfStatus 
					INTEGER,
				hwRanApsIfPeerIp
					IpAddress,
				hwRanApsIfLocalIp
					IpAddress,
				hwRanApsKeepaliveTimer
					Integer32,
				hwRanApsHoldTimer 
					Integer32, 
				hwRanApsIfName
				    OCTET STRING,
				hwRanApsSystemId
					PhysAddress,
				hwRanApsRowStatus
					RowStatus,
				hwRanApsTrackBfdName
					OCTET STRING, 
				hwRanApsAuthenticateString
					OCTET STRING,
				hwRanApsSignalPriority
					INTEGER,
			                  hwRanApsAuthenticateType
					INTEGER,
                                                                         hwRanApsAntiReplay
					INTEGER
			 }
-- ==============================================================================			 
		hwRanApsProGroupIdIndex OBJECT-TYPE
			SYNTAX Unsigned32  (1..192)
			MAX-ACCESS read-create
			STATUS current
			DESCRIPTION
				"The table's index that is APS protection group number from 1 to 192."
			::= { hwRanApsProtectionEntry 1 }
		hwRanApsIfIndexIndex OBJECT-TYPE
			SYNTAX InterfaceIndex
			MAX-ACCESS read-only
			STATUS current
			DESCRIPTION
				"The APS interface index."
			::= { hwRanApsProtectionEntry 2 }

		hwRanApsProtectionGroupNum OBJECT-TYPE
			SYNTAX Unsigned32  (1..192)
			MAX-ACCESS read-create
			STATUS current
			DESCRIPTION
				"The table's index that is APS protection group number from 1 to 192."
			::= { hwRanApsProtectionEntry 3 }
		hwRanApsIfIndex OBJECT-TYPE
			SYNTAX InterfaceIndex
			MAX-ACCESS read-only
			STATUS current
			DESCRIPTION
				"The APS interface index."
			::= { hwRanApsProtectionEntry 4 }
		
		hwRanApsIfType OBJECT-TYPE
			SYNTAX INTEGER  
			{
			invalid(0),
			work(1),
			protect(2)
			}
			MAX-ACCESS read-create
			STATUS current
			DESCRIPTION
				"The APS interface type."
			::= { hwRanApsProtectionEntry 5 }
 		
		hwRanApsRestoreWaitTime  OBJECT-TYPE
			SYNTAX Integer32 (0..12)
			MAX-ACCESS read-create
			STATUS current
			DESCRIPTION
				"The APS restrore wait time.zero is no revert mode"
			::= { hwRanApsProtectionEntry 6 }	   
		hwRanApsProtectSwitch  OBJECT-TYPE
			SYNTAX INTEGER 
			{
			invalid(0),
			lock(1),
			force(2),
			manual(3),
			forceback(4),
			manualback(5)
			}
			MAX-ACCESS read-create
			STATUS current
			DESCRIPTION
				"The switch of APS protection."
			::= { hwRanApsProtectionEntry 7 }
		hwRanApsProtectMode  OBJECT-TYPE
			SYNTAX INTEGER
			{
			invalid(0),
			oneplusoneunidirection(1),
			oneplusonebidirection(2),
			onetooneunidirection(3),
			onetoonebidirection(4)
			}
			MAX-ACCESS read-create
			STATUS current
			DESCRIPTION
				"The protect mode of APS."
			::= { hwRanApsProtectionEntry 8 }
		hwRanApsWorkingIfStatus  OBJECT-TYPE
			SYNTAX INTEGER
			{
			active(1),
			inactive(2)
			}
			MAX-ACCESS read-only
			STATUS current
			DESCRIPTION
				"Status of the APS interface."
			::= { hwRanApsProtectionEntry 9 }
		hwRanApsIfPeerIp  OBJECT-TYPE
			SYNTAX IpAddress
			MAX-ACCESS read-create
			STATUS current
			DESCRIPTION
				"MC-APS peer ip."
			::= { hwRanApsProtectionEntry 10 }
		hwRanApsIfLocalIp  OBJECT-TYPE
			SYNTAX IpAddress
			MAX-ACCESS read-create
			STATUS current
			DESCRIPTION
				"MC-APS local ip."
			::= { hwRanApsProtectionEntry 11 }
		hwRanApsKeepaliveTimer  OBJECT-TYPE
			SYNTAX Integer32 (1..60)
			MAX-ACCESS read-create
			STATUS current
			DESCRIPTION
				"MC-APS keep a live timer."
			::= { hwRanApsProtectionEntry 12 }			
		hwRanApsHoldTimer  OBJECT-TYPE
			SYNTAX Integer32 (3..300)
			MAX-ACCESS read-create
			STATUS current
			DESCRIPTION
				"MC-APS hold timer."
			::= { hwRanApsProtectionEntry 13 }								
		hwRanApsIfName  OBJECT-TYPE
	    	SYNTAX      OCTET STRING (SIZE (1..64))
			MAX-ACCESS read-only
			STATUS current
			DESCRIPTION
				"Interface name."
			::= { hwRanApsProtectionEntry 14 }
		hwRanApsSystemId  OBJECT-TYPE
	    	SYNTAX PhysAddress
			MAX-ACCESS read-only
			STATUS current
			DESCRIPTION
				"The system ID of the APS. It is a physical address.."
			::= { hwRanApsProtectionEntry 15 }
		hwRanApsRowStatus  OBJECT-TYPE
			SYNTAX RowStatus
			MAX-ACCESS read-create
			STATUS current
			DESCRIPTION
				"Current operation status of the row."
			::= { hwRanApsProtectionEntry 16}
		hwRanApsTrackBfdName  OBJECT-TYPE
	    	SYNTAX      OCTET STRING (SIZE (0..15))
			MAX-ACCESS read-create
			STATUS current
			DESCRIPTION
				"The BFD session name to track, size 0 means not to track the BFD session."
			::= { hwRanApsProtectionEntry 17 }
		hwRanApsAuthenticateString OBJECT-TYPE
			SYNTAX OCTET STRING (SIZE (0..16|32|48))
			MAX-ACCESS read-create
			STATUS current
			DESCRIPTION
				"MC-APS authenticate string."
			::= { hwRanApsProtectionEntry 18 }
		hwRanApsSignalPriority  OBJECT-TYPE
			SYNTAX INTEGER 
			{
			highPriority(0),
			lowPriority(1)
			}
			MAX-ACCESS read-create
			STATUS current
			DESCRIPTION
				"The priority of APS signal, eg : Signal fail high priority, Signal fail low priority. The default value is high priority."
			::= { hwRanApsProtectionEntry 19 }
		hwRanApsAuthenticateType  OBJECT-TYPE
			SYNTAX INTEGER 
			{
			     invalid(0),
			     cipher(1),
			     simple(2),
                                                            hmac(3),
                                                            sha2(4)	    
			}
			MAX-ACCESS read-create
			STATUS current
			DESCRIPTION
				"This object indicates the encryption type of authenticate string."
			::= { hwRanApsProtectionEntry 20 }
		hwRanApsAntiReplay OBJECT-TYPE
			SYNTAX INTEGER
	                                     {
			    disable(0),
			    enable(1)
			}
			MAX-ACCESS read-create
			STATUS current
			DESCRIPTION
				"This object indicates the anti-replay function"
			::= { hwRanApsProtectionEntry 21 }

  -- ======================= APS group table =================================
		hwRanApsGroupTable OBJECT-TYPE
			SYNTAX SEQUENCE OF HwRanApsGroupEntry
			MAX-ACCESS not-accessible
			STATUS current
			DESCRIPTION
				"APS group table."
			::= { hwRanApsObjects 2 }	

		hwRanApsGroupEntry OBJECT-TYPE
			SYNTAX HwRanApsGroupEntry
			MAX-ACCESS not-accessible
			STATUS current
			DESCRIPTION
				"APS group table entry."
			INDEX { hwRanApsGroupId }
			::= { hwRanApsGroupTable 1 }
		
		HwRanApsGroupEntry ::=
			SEQUENCE { 
				hwRanApsGroupId
					Unsigned32,
				hwRanApsTableRowStatus
					RowStatus  
			 }
-- ==============================================================================			 
		hwRanApsGroupId OBJECT-TYPE
			SYNTAX Unsigned32  (1..192)
			MAX-ACCESS read-only
			STATUS current
			DESCRIPTION
				"The table's index that is APS protection group number from 1 to 192."
			::= { hwRanApsGroupEntry 1 }
 
 		hwRanApsTableRowStatus  OBJECT-TYPE
			SYNTAX RowStatus
			MAX-ACCESS read-create
			STATUS current
			DESCRIPTION
				"Current operation status of the row."
			::= { hwRanApsGroupEntry 2 }
 
-- ==================================================================================

 -- ======================= APS info table =================================
		hwRanApsInfoTable OBJECT-TYPE
			SYNTAX SEQUENCE OF HwRanApsInfoEntry
			MAX-ACCESS not-accessible
			STATUS current
			DESCRIPTION
				"APS group table."
			::= { hwRanApsObjects 3 }	

		hwRanApsInfoEntry OBJECT-TYPE
			SYNTAX HwRanApsInfoEntry
			MAX-ACCESS not-accessible
			STATUS current
			DESCRIPTION
				"APS group table entry."
			INDEX { hwRanApsInfoGroupId }
			::= { hwRanApsInfoTable 1 }
		
		HwRanApsInfoEntry ::=
			SEQUENCE { 
				hwRanApsInfoGroupId
					Unsigned32,
			    hwRanApsRemoteProtectMode
					INTEGER,   
				hwRanApsPgpInfo
					INTEGER,
				hwRanApsInfoRowStatus
					RowStatus  
			 }
-- ==============================================================================			 
		hwRanApsInfoGroupId OBJECT-TYPE
			SYNTAX Unsigned32  (1..192)
			MAX-ACCESS read-only
			STATUS current
			DESCRIPTION
				"The table's index that is APS protection group number from 1 to 192."
			::= { hwRanApsInfoEntry 1 }
 		hwRanApsRemoteProtectMode  OBJECT-TYPE
			SYNTAX INTEGER 			
			{
			invalid(0),
			oneplusoneunidirection(1),
			oneplusonebidirection(2),
			onetooneunidirection(3),
			onetoonebidirection(4)
			}  
			MAX-ACCESS read-only
			STATUS current
			DESCRIPTION
				"Remote APS mode."
			::= { hwRanApsInfoEntry 2 }						 
		hwRanApsPgpInfo  OBJECT-TYPE
			SYNTAX INTEGER 			
			{
			valid(0),
			apsgroupidmismatch(1),
			apsgroupversionmismatch(2)
			}  
			MAX-ACCESS read-only
			STATUS current
			DESCRIPTION
				"PGP information."
			::= { hwRanApsInfoEntry 3 } 
 		hwRanApsInfoRowStatus  OBJECT-TYPE
			SYNTAX RowStatus
			MAX-ACCESS read-create
			STATUS current
			DESCRIPTION
				"Current operation status of the row."
			::= { hwRanApsInfoEntry 4 }
 
 -- ======================= APS Mem table =================================
		hwRanApsMemTable OBJECT-TYPE
			SYNTAX SEQUENCE OF HwRanApsMemEntry
			MAX-ACCESS not-accessible
			STATUS current
			DESCRIPTION
				"APS member table."
			::= { hwRanApsObjects 4 }	
		hwRanApsMemEntry OBJECT-TYPE
			SYNTAX HwRanApsMemEntry
			MAX-ACCESS not-accessible
			STATUS current
			DESCRIPTION
				"APS group member entry."
			INDEX { hwRanApsMemIfIndex }
			::= { hwRanApsMemTable 1 }
		
		HwRanApsMemEntry ::=
			SEQUENCE {
				hwRanApsMemIfIndex
					InterfaceIndex,
				hwRanApsMemGroupId
					Unsigned32
			 }
-- ==============================================================================			 
		hwRanApsMemIfIndex OBJECT-TYPE
			SYNTAX InterfaceIndex
			MAX-ACCESS read-only
			STATUS current
			DESCRIPTION
				"The APS member interface index."
			::= { hwRanApsMemEntry 1 }
		hwRanApsMemGroupId OBJECT-TYPE
			SYNTAX Unsigned32  (0..192)
			MAX-ACCESS read-create
			STATUS current
			DESCRIPTION
				"The group id is 1 to 192,0 is delete aps group."
			::= { hwRanApsMemEntry 2 }

		
		-- 1.3.6.1.4.1.2011.5.25.200.2
		hwRanApsTraps OBJECT IDENTIFIER ::= { hwRanApsMIB 2 }

		
-- ==================================================================================
									
-- ==================================================================================
-- alarm
  
		hwRanApsFsmFail  NOTIFICATION-TYPE
			OBJECTS {hwRanApsIfIndex, hwRanApsIfName,hwRanApsProtectionGroupNum}
			STATUS current
			DESCRIPTION 
			"This object indicates that an alarm is generated when the LMSP state machine processing fails."
			::= { hwRanApsTraps 1}
	

		hwRanPgpPktError  NOTIFICATION-TYPE
			OBJECTS {hwRanApsIfIndex ,hwRanApsIfName,hwRanApsProtectionGroupNum,hwRanApsIfPeerIp,hwRanApsPgpInfo}
			STATUS current	
			DESCRIPTION 
			"This object indicates the PGP packet error."
			::= { hwRanApsTraps 2}  
	
		hwRanPgpKeepalivePktOvertime  NOTIFICATION-TYPE
			OBJECTS {hwRanApsIfIndex,hwRanApsIfName,hwRanApsProtectionGroupNum,hwRanApsIfPeerIp}
			STATUS current	
			DESCRIPTION 
			"This object indicates that an alarm is generated when PGP Keepalive packets time out."
			::= { hwRanApsTraps 3}  
	
		hwRanApsUniBidMismatch  NOTIFICATION-TYPE
			OBJECTS {hwRanApsIfIndex, hwRanApsIfName,hwRanApsProtectionGroupNum,hwRanApsProtectMode,hwRanApsRemoteProtectMode}
			STATUS current
			DESCRIPTION 
			"This object indicates that the APS modes configured between two NEs are inconsistent."
			::= { hwRanApsTraps 4}
                         
		hwRanApsK1K2Mismatch  NOTIFICATION-TYPE
			OBJECTS {hwRanApsIfIndex ,hwRanApsIfName, hwRanApsProtectionGroupNum}
			STATUS current	
			DESCRIPTION 
			"This object indicates that the received K1 and K2 bytes do not match the transmitted K1 and K2 bytes."
			::= { hwRanApsTraps 5}  
		
		hwRanApsK2Mismatch  NOTIFICATION-TYPE
			OBJECTS {hwRanApsIfIndex,hwRanApsIfName, hwRanApsProtectionGroupNum}
			STATUS current	
			DESCRIPTION 
			"This object indicates that an alarm is generated when the peer protection mode represented 
			by the K2 byte (the fifth byte in descending order) in the received packet is different from the local."
			::= { hwRanApsTraps 6} 
			
		hwRanApsProtectSwitchOver NOTIFICATION-TYPE
			OBJECTS {hwRanApsIfIndex,hwRanApsIfName ,hwRanApsIfType,hwRanApsProtectionGroupNum }
			STATUS current
			DESCRIPTION 
				"This object indicates that an LMSP protection switchover succeeds."
			::= { hwRanApsTraps 7 }
			
		hwRanApsProtectSwitchBackOver NOTIFICATION-TYPE
			OBJECTS {hwRanApsIfIndex,hwRanApsIfName,hwRanApsIfType,hwRanApsProtectionGroupNum}
			STATUS current
			DESCRIPTION 
				"This object indicates that an LMSP protection switchback succeeds."
			::= { hwRanApsTraps 8 }	
			
		hwRanApsInterfaceReady NOTIFICATION-TYPE
			OBJECTS {hwRanApsIfIndex,hwRanApsIfName,hwRanApsProtectionGroupNum}
			STATUS current
			DESCRIPTION 
				"This object indicates that an interface in an LMSP group becomes Up and begins to work as a protection interface."
			::= { hwRanApsTraps 9 }

		
		-- 1.3.6.1.4.1.2011.5.25.200.2.10
		hwRanApsUniBidMismatchResume NOTIFICATION-TYPE
			OBJECTS { hwRanApsIfIndex, hwRanApsIfName, hwRanApsProtectionGroupNum }
			STATUS current
			DESCRIPTION 
				"This object indicates that the LMSP working modes between two NEs are the same."
			::= { hwRanApsTraps 10 }

		
		-- 1.3.6.1.4.1.2011.5.25.200.2.11
		hwRanApsK2MismatchResume NOTIFICATION-TYPE
			OBJECTS { hwRanApsIfIndex, hwRanApsIfName, hwRanApsProtectionGroupNum }
			STATUS current
			DESCRIPTION 
				"This object indicates that the peer protection mode represented by the K2 byte (the fifth byte in descending order) in the received packet is the same as the local protection mode."
			::= { hwRanApsTraps 11 }

		
		-- 1.3.6.1.4.1.2011.5.25.200.2.12
		hwRanPgpKeepalivePktOvertimeResume NOTIFICATION-TYPE
			OBJECTS { hwRanApsIfIndex, hwRanApsIfName, hwRanApsProtectionGroupNum, hwRanApsIfPeerIp }
			STATUS current
			DESCRIPTION 
				"This object indicates that the alarm generated when PGP Keepalive packets timed out is cleared."
			::= { hwRanApsTraps 12 }

		
		-- 1.3.6.1.4.1.2011.5.25.200.2.13
		hwRanApsRevertMismatch  NOTIFICATION-TYPE
			OBJECTS {hwRanApsIfIndex, hwRanApsIfName, hwRanApsProtectionGroupNum}
			STATUS current
			DESCRIPTION
			"This object indicates that the LMSP switchback modes configured between two devices are inconsistent."
			::= { hwRanApsTraps 13} 

                -- 1.3.6.1.4.1.2011.5.25.200.2.14
		hwRanApsK1K2MisResume  NOTIFICATION-TYPE
			OBJECTS {hwRanApsIfIndex ,hwRanApsIfName, hwRanApsProtectionGroupNum}
			STATUS current	
			DESCRIPTION 
			"This object indicates that the received K1 and K2 bytes match the transmitted K1 and K2 bytes."
			::= { hwRanApsTraps 14}  			
			
		-- 1.3.6.1.4.1.2011.5.25.200.3
		hwRanApsConformance OBJECT IDENTIFIER ::= { hwRanApsMIB 3 }

		
		-- 1.3.6.1.4.1.2011.5.25.200.3.1
		hwRanApsCompliances OBJECT IDENTIFIER ::= { hwRanApsConformance 1 }

		

-- this module

		hwRanApsCompliance MODULE-COMPLIANCE
			STATUS current
			DESCRIPTION 
				"The compliance statement for entities that implement 
				extend APS on a router."
			MODULE -- this module
				MANDATORY-GROUPS {hwRanApsProtectionGroup,hwRanApsGroupGroup,hwRanApsInfoGroup,hwRanApsNotificationsGroup }
			::= { hwRanApsCompliances 1 }


		hwRanApsGroups OBJECT IDENTIFIER ::= { hwRanApsConformance 2 }
		
--   units of conformance 
		hwRanApsProtectionGroup OBJECT-GROUP
			OBJECTS {hwRanApsProGroupIdIndex,hwRanApsIfIndexIndex,hwRanApsProtectionGroupNum,hwRanApsIfIndex,hwRanApsIfType,hwRanApsRestoreWaitTime,hwRanApsProtectSwitch, hwRanApsProtectMode,
					hwRanApsWorkingIfStatus,hwRanApsIfPeerIp,hwRanApsIfLocalIp,hwRanApsKeepaliveTimer,hwRanApsHoldTimer,hwRanApsIfName,hwRanApsSystemId,hwRanApsRowStatus, hwRanApsTrackBfdName, hwRanApsAuthenticateString, hwRanApsSignalPriority, hwRanApsAuthenticateType }
			STATUS current
			DESCRIPTION 
				"This is a optional group of APS configuration information."
			::= { hwRanApsGroups 1 }
			
		hwRanApsGroupGroup OBJECT-GROUP
			OBJECTS {hwRanApsGroupId,hwRanApsTableRowStatus }
			STATUS current
			DESCRIPTION 
				"This is a optional group of APS group information."
			::= { hwRanApsGroups 2 }
		hwRanApsInfoGroup OBJECT-GROUP
			OBJECTS {hwRanApsInfoGroupId,hwRanApsRemoteProtectMode,hwRanApsPgpInfo,hwRanApsInfoRowStatus}
			STATUS current
			DESCRIPTION 
				"This is a optional group of APS information."
			::= { hwRanApsGroups 3 }
		hwRanApsNotificationsGroup NOTIFICATION-GROUP
			NOTIFICATIONS { hwRanApsFsmFail, hwRanPgpPktError, hwRanPgpKeepalivePktOvertime, hwRanApsUniBidMismatch, hwRanApsK1K2Mismatch, 
				hwRanApsK2Mismatch, hwRanApsProtectSwitchOver, hwRanApsProtectSwitchBackOver, hwRanApsInterfaceReady, hwRanApsUniBidMismatchResume, 
				hwRanApsK2MismatchResume, hwRanPgpKeepalivePktOvertimeResume, hwRanApsRevertMismatch, hwRanApsK1K2MisResume }
			STATUS current
			DESCRIPTION 
				"This is a optional group of information."
			::= { hwRanApsGroups 4 }
		hwRanApsMemGroup OBJECT-GROUP
			OBJECTS {hwRanApsMemIfIndex,hwRanApsMemGroupId}
			STATUS current
			DESCRIPTION 
				"This is a optional group of APS information."
			::= { hwRanApsGroups 5 }

		
END     
    
--
-- HUAWEI-RANAPS-MIB.mib
--

-- ===================================================================
-- Copyright (C) 2018 by HUAWEI TECHNOLOGIES. All rights reserved.
-- Description:  The mib is used for defining huawei's RF           
--               management in distributing mode MIB objects.
-- Reference:
-- Version: V1.07
-- ===================================================================
     
     
       HUAWEI-RFIPRETURN-MIB DEFINITIONS ::= BEGIN
       IMPORTS
           MODULE-IDENTITY, mib-2, OBJECT-TYPE, Counter32, Counter64,
           Unsigned32, Integer32, Gauge32, NOTIFICATION-TYPE, IpAddress
               FROM SNMPv2-SMI
           TruthValue, DateAndTime, RowStatus, MacAddress,TEXTUAL-CONVENTION, DisplayString
               FROM SNMPv2-TC
           ifIndex, InterfaceIndex, InterfaceIndexOrZero, ifAdminStatus, ifOperStatus
               FROM IF-MIB
           MODULE-COMPLIANCE, OBJECT-GROUP
               FROM SNMPv2-CONF
           SnmpAdminString
               FROM SNMP-FRAMEWORK-MIB
           OwnerString, EntryStatus
               FROM RMON-MIB
           huaweiUtility
               FROM HUAWEI-MIB
           hwFrameIndex, hwSlotIndex, hwPortIndex, hwConfigChangeIP
               FROM HUAWEI-DEVICE-MIB
           InetAddressType,InetAddress,InetAddressPrefixLength,InetPortNumber,InetAddressIPv6
               FROM INET-ADDRESS-MIB;
                 
   hwRfIpReturnMIB MODULE-IDENTITY
            LAST-UPDATED "201808230000Z"
            ORGANIZATION "Huawei Technologies Co.,Ltd."
			      CONTACT-INFO                                 
			             "Huawei Industrial Base         
			              Bantian, Longgang              
			              Shenzhen 518129                
			              People's Republic of China     
			              Website: http://www.huawei.com 
			              Email: support@huawei.com      
			             " 
            DESCRIPTION
                "The mib is used for defining huawei's RF management in distributing mode MIB objects.
                "
--  Revision history
	   REVISION     "201808230000Z" 
       DESCRIPTION  "V1.07, Modify the name of hwRfCableNdfChannelRfPower in table hwRfCableNdfChannelTable.
                            Modify the name of hwRfCableNdrChannelRfPower in table hwRfCableNdrChannelTable."

	   REVISION     "201808080000Z" 
       DESCRIPTION  "V1.06, Added the leaf hwRfCableNdrChannelRfPower." 

	   REVISION     "201804170000Z" 
       DESCRIPTION  "V1.05, Add the table of hwRfCableRfOutPortTable." 

	   REVISION     "201711200000Z" 
       DESCRIPTION  "V1.04, Obsoleted the table of hwRfTxIpReturnChannelTable and hwRfRxIpReturnChannelTable. 
       						Add the table of hwRfCableNdfChannelTable. 
                    		Add the table of hwRfCableNdrChannelTable. " 

       REVISION     "201609120000Z"
       DESCRIPTION  "V1.03, Modified the range of hwRfTxIpReturnChannelFrequency, hwRfTxIpReturnChannelFrequencyStatus in table hwRfTxIpReturnChannelTable."    
       
	   REVISION     "201607170000Z"
       DESCRIPTION  "V1.02, Deleted the leaf hwRfTxIpReturnChannelRfPower,hwRfTxIpReturnChannelModulationTech, hwRfTxIpReturnChannelBitRate,
       						hwRfTxIpReturnChannelModulationTechStatus,hwRfTxIpReturnChannelRfPowerStatus,hwRfTxIpReturnChannelBitRateStatus in table hwRfTxIpReturnChannelTable.
       				 		Modified the enumaration of hwRfTxIpReturnChannelFreqWidth,hwRfTxIpReturnChannelFreqWidthStatus in table hwRfTxIpReturnChannelTable.
       				 		Added the leaf hwRfTxIpReturnChannelGain,hwRfTxIpReturnChannelGainStatus in table hwRfTxIpReturnChannelTable.
                            Deleted the leaf hwRfRxIpReturnChannelModulationTech, hwRfRxIpReturnChannelBitRate,
                            hwRfRxIpReturnChannelModulationTechStatus,hwRfRxIpReturnChannelBitRateStatus in table hwRfRxIpReturnChannelTable.
       				 		Modified the enumaration of hwRfRxIpReturnChannelFreqWidth,hwRfRxIpReturnChannelFreqWidthStatus in table hwRfRxIpReturnChannelTable. 
       				 		Modified the range of leaf hwRfRxIpReturnChannelFrequency,hwRfRxIpReturnChannelFrequencyStatus in table hwRfRxIpReturnChannelTable. 
       				 		Modified the default value of leaf hwRfRxIpReturnChannelRfPower,hwRfRxIpReturnChannelRfPowerStatus in table hwRfRxIpReturnChannelTable."

	   REVISION     "201510260000Z"
       DESCRIPTION  "V1.01, Deleted the leaf hwRfTxIpReturnChannelAttenuation, hwRfTxIpReturnChannelAttenuationStatus in table hwRfTxIpReturnChannelTable.
       				 		Modified the enumaration of hwRfTxIpReturnChannelFreqWidth,hwRfTxIpReturnChannelFreqWidthStatus in table hwRfTxIpReturnChannelTable.
       				 		Added the leaf hwRfTxIpReturnChannelRfPower,hwRfTxIpReturnChannelModulationTech,hwRfTxIpReturnChannelBitRate,
                     		hwRfTxIpReturnChannelRfPowerStatus,hwRfTxIpReturnChannelModulationTechStatus,hwRfTxIpReturnChannelBitRateStatus in table hwRfTxIpReturnChannelTable.
                            Deleted the leaf hwRfRxIpReturnChannelAttenuation, hwRfRxIpReturnChannelAttenuationStatus in table hwRfRxIpReturnChannelTable.
       				 		Modified the enumaration of hwRfRxIpReturnChannelFreqWidth,hwRfRxIpReturnChannelFreqWidthStatus in table hwRfRxIpReturnChannelTable. 
       				 		Modified the range of leaf hwRfRxIpReturnChannelFrequency,hwRfRxIpReturnChannelFrequencyStatus in table hwRfRxIpReturnChannelTable.
       				 		Added the leaf hwRfRxIpReturnChannelRfPower,hwRfRxIpReturnChannelModulationTech,hwRfRxIpReturnChannelBitRate,
                     		hwRfRxIpReturnChannelRfPowerStatus,hwRfRxIpReturnChannelModulationTechStatus,hwRfRxIpReturnChannelBitRateStatus in table hwRfRxIpReturnChannelTable."

       REVISION     "201508111600Z" 
       DESCRIPTION  "V1.01, Add the table of hwRfTxIpReturnChannelTable. 
                    		Add the table of hwRfRxIpReturnChannelTable. " 
                    
       REVISION     "201508111600Z"
       DESCRIPTION  "V1.00, Initial version."
       ::= { huaweiUtility 182 }

   hwRfObjectMIB 	OBJECT IDENTIFIER ::= { hwRfIpReturnMIB 1 }

   hwRfObject 		OBJECT IDENTIFIER ::= { hwRfObjectMIB  1}

    -- Table hwRfTxIpReturnChannelTable Begin
    hwRfTxIpReturnChannelTable OBJECT-TYPE
          SYNTAX     SEQUENCE OF HwRfTxIpReturnChannelEntry
          MAX-ACCESS not-accessible
          STATUS     obsolete
          DESCRIPTION
               "
               This table describes the ip return attributes of tx channels.
               The index of this table are ifIndex and hwRfTxIpReturnChannelId.
               "
          ::= { hwRfObject 1 }

    hwRfTxIpReturnChannelEntry OBJECT-TYPE
          SYNTAX     HwRfTxIpReturnChannelEntry
          MAX-ACCESS not-accessible
          STATUS     obsolete
          DESCRIPTION
               "
               This table describes the ip return attributes of tx channels.
               The indexes of this table are ifIndex and hwRfTxIpReturnChannelId.
               "
          INDEX       { ifIndex, hwRfTxIpReturnChannelId }
          ::= { hwRfTxIpReturnChannelTable 1 }

    HwRfTxIpReturnChannelEntry ::=
          SEQUENCE {
                    hwRfTxIpReturnChannelId     					Integer32,
                    hwRfTxIpReturnChannelFrequency 					Integer32,
                    hwRfTxIpReturnChannelFreqWidth 					INTEGER,   
                    hwRfTxIpReturnChannelGain 						Integer32,
                    hwRfTxIpReturnChannelMode 						INTEGER, 
                    hwRfTxIpReturnChannelAdminStatus        		INTEGER,
                    hwRfTxIpReturnChannelFrequencyStatus 			Integer32,
                    hwRfTxIpReturnChannelFreqWidthStatus    		INTEGER, 
                    hwRfTxIpReturnChannelGainStatus					Integer32,  
                    hwRfTxIpReturnChannelModeStatus    				INTEGER,
                    hwRfTxIpReturnChannelOperStatus    				INTEGER,
		    		hwRfTxIpReturnChannelRowStatus     				RowStatus		
                   }

    hwRfTxIpReturnChannelId OBJECT-TYPE
          SYNTAX     Integer32(1)
          MAX-ACCESS not-accessible
          STATUS     obsolete
          DESCRIPTION
                "
                Indicates the channel id.
                "
              DEFVAL      { 1 }
          ::= { hwRfTxIpReturnChannelEntry 1 }

    hwRfTxIpReturnChannelFrequency OBJECT-TYPE
          SYNTAX      Integer32(-1|5000000..85000000)  
          UNITS   "Hz"
          MAX-ACCESS  read-write
          STATUS  obsolete
          DESCRIPTION
                "
                Indicates the channel frequency.   
                The adjustment accuracy is 0.1MHz.
                -1 represent invalid value.
                "
          ::= { hwRfTxIpReturnChannelEntry 2 }

    hwRfTxIpReturnChannelFreqWidth OBJECT-TYPE
          SYNTAX     INTEGER{hz400K(1),hz800K(2)}  
          MAX-ACCESS read-write
          STATUS     obsolete
          DESCRIPTION
                "
                Indicates the channel frequency bandwidth.
                Options:
                1. hz400K(1) - 400KHz     
                2. hz800K(2) - 800KHz   
                "
              DEFVAL      { 1 }
          ::= { hwRfTxIpReturnChannelEntry 3 }
          
    hwRfTxIpReturnChannelGain OBJECT-TYPE
          SYNTAX      Integer32(-200..200)  
          UNITS   "0.1dB"
          MAX-ACCESS  read-write
          STATUS  obsolete
          DESCRIPTION
                "
                Indicates the channel transmit gain.
                "  
              DEFVAL      { 0 }
          ::= { hwRfTxIpReturnChannelEntry 4 }
          
    hwRfTxIpReturnChannelMode OBJECT-TYPE
          SYNTAX     INTEGER{transponder(1)}
          MAX-ACCESS read-write
          STATUS     obsolete
          DESCRIPTION
                "
                Indicates the channel mode.
                Options:
                1. transponder(1) - transponder mode
                "
              DEFVAL      { 1 }
          ::= { hwRfTxIpReturnChannelEntry 5 }
			
    hwRfTxIpReturnChannelAdminStatus OBJECT-TYPE
          SYNTAX     INTEGER{disable(1),enable(2)}
          MAX-ACCESS read-write
          STATUS     obsolete
          DESCRIPTION
                "
                Indicates the administrative status of ip return tx channel.
                Options:
                1. disable(1) - disable ip return tx channel
                2. enable(2) - enable ip return tx channel
                "
              DEFVAL      { 1 }
          ::= { hwRfTxIpReturnChannelEntry 6 }

    hwRfTxIpReturnChannelFrequencyStatus OBJECT-TYPE
          SYNTAX     Integer32(-1|5000000..85000000) 
          UNITS   "Hz"
          MAX-ACCESS read-only
          STATUS     obsolete
          DESCRIPTION
                "
                Indicates the channel frequency. 
                The adjustment accuracy is 0.1MHz.
                -1 represent invalid value.
                "
          ::= { hwRfTxIpReturnChannelEntry 7 }

    hwRfTxIpReturnChannelFreqWidthStatus OBJECT-TYPE
          SYNTAX     INTEGER{hz400K(1),hz800K(2),invalid(-1)}  
          MAX-ACCESS read-only
          STATUS     obsolete
          DESCRIPTION
                "
                Indicates the channel frequency bandwidth.
                Options:
                1. hz400K(1) - 400KHz     
                2. hz800K(2) - 800KHz   
                3. invalid(-1) - invalid value      
                "
          ::= { hwRfTxIpReturnChannelEntry 8 }
            
    hwRfTxIpReturnChannelGainStatus OBJECT-TYPE
          SYNTAX     Integer32(-200..200|2147483647)  
          UNITS   "0.1dB"
          MAX-ACCESS read-only
          STATUS     obsolete
          DESCRIPTION
                "
                Indicates the channel transmit gain.  
                2147483647(0x7FFFFFFF) represent invalid value.
                "
          ::= { hwRfTxIpReturnChannelEntry 9 }      
          
    hwRfTxIpReturnChannelModeStatus OBJECT-TYPE
          SYNTAX     INTEGER{transponder(1),invalid(-1)}
          MAX-ACCESS read-only
          STATUS     obsolete
          DESCRIPTION
                "
                Indicates the channel mode.
                Options:
                1. transponder(1) - transponder mode
                2. invalid(-1) - invalid value
                "
          ::= { hwRfTxIpReturnChannelEntry 10 }

    hwRfTxIpReturnChannelOperStatus OBJECT-TYPE
          SYNTAX     INTEGER{down(1),up(2),invalid(-1)}
          MAX-ACCESS read-only
          STATUS     obsolete
          DESCRIPTION
                "
                Indicates the operational status of ip return tx channel .
                 Options:
                 1. down(1) - down status
                 2. up(2) - up status
                 3. invalid(-1) - invalid value
                "
          ::= { hwRfTxIpReturnChannelEntry 11 }

    hwRfTxIpReturnChannelRowStatus OBJECT-TYPE
          SYNTAX     RowStatus
          MAX-ACCESS read-create
          STATUS     obsolete
          DESCRIPTION
                "
                Indicates the row status to create or delete a channel ip return configuration.
                Options:
                1. active(1)      -indicates modify the specific ip return configuration.
                2. createAndGo(4) -indicates creating an ip return configuration.
                3. destroy(6)     -indicates deleting the specific ip return configuration.
                "
          ::= { hwRfTxIpReturnChannelEntry 12 } 
                
  -- Table hwRfTxIpReturnChannelTable End
  
  -- Table hwRfRxIpReturnChannelTable Begin
  
    hwRfRxIpReturnChannelTable OBJECT-TYPE
          SYNTAX     SEQUENCE OF HwRfRxIpReturnChannelEntry
          MAX-ACCESS not-accessible
          STATUS     obsolete
          DESCRIPTION
               "
               This table describes the ip return attributes of rx channels.
               The indexes of this table are ifIndex and hwRfRxIpReturnChannelId.
               "
          ::= { hwRfObject 2 }

    hwRfRxIpReturnChannelEntry OBJECT-TYPE
          SYNTAX     HwRfRxIpReturnChannelEntry
          MAX-ACCESS not-accessible
          STATUS     obsolete
          DESCRIPTION
               "
               This table describes the ip return attributes of rx channels.
               The indexes of this table are ifIndex and hwRfRxIpReturnChannelId.
               "
          INDEX       { ifIndex, hwRfRxIpReturnChannelId }
          ::= { hwRfRxIpReturnChannelTable 1 }

    HwRfRxIpReturnChannelEntry ::=
          SEQUENCE {
                    hwRfRxIpReturnChannelId     					Integer32,
                    hwRfRxIpReturnChannelFrequency 					Integer32,
                    hwRfRxIpReturnChannelFreqWidth 					INTEGER,  
                    hwRfRxIpReturnChannelRfPower 					Integer32,
                    hwRfRxIpReturnChannelMode 						INTEGER,
                    hwRfRxIpReturnChannelAdminStatus        		INTEGER,
                    hwRfRxIpReturnChannelFrequencyStatus 			Integer32,
                    hwRfRxIpReturnChannelFreqWidthStatus    		INTEGER,  
                    hwRfRxIpReturnChannelRfPowerStatus  			Integer32,  
                    hwRfRxIpReturnChannelModeStatus    				INTEGER,
                    hwRfRxIpReturnChannelOperStatus    				INTEGER,
		    		hwRfRxIpReturnChannelRowStatus     				RowStatus
                   }

    hwRfRxIpReturnChannelId OBJECT-TYPE
          SYNTAX     Integer32(1)
          MAX-ACCESS not-accessible
          STATUS     obsolete
          DESCRIPTION
                "
                Indicates the channel id.
                "
              DEFVAL      { 1 }
          ::= { hwRfRxIpReturnChannelEntry 1 }

    hwRfRxIpReturnChannelFrequency OBJECT-TYPE
          SYNTAX      Integer32(-1|54000000..204000000)  
          UNITS   "Hz"
          MAX-ACCESS  read-write
          STATUS  obsolete
          DESCRIPTION
                "
                Indicates the channel frequency.   
                The adjustment accuracy is 0.1MHz.
                -1 represent invalid value.
                "
          ::= { hwRfRxIpReturnChannelEntry 2 }

    hwRfRxIpReturnChannelFreqWidth OBJECT-TYPE
          SYNTAX     INTEGER{hz400K(1),hz800K(2)}
          MAX-ACCESS read-write
          STATUS     obsolete
          DESCRIPTION
                "
                Indicates the channel frequency bandwidth.
                Options:
                1. hz400K(1) - 400KHz     
                2. hz800K(2) - 800KHz       
                "
              DEFVAL      { 1 }
          ::= { hwRfRxIpReturnChannelEntry 3 }   
          
    hwRfRxIpReturnChannelRfPower OBJECT-TYPE
          SYNTAX      Integer32(-1|300..500)  
          UNITS   "0.1dBmV"
          MAX-ACCESS  read-write
          STATUS  obsolete
          DESCRIPTION
                "
                Indicates the channel received power.
                -1 represent invalid value.
                " 
              DEFVAL      { 400 }
          ::= { hwRfRxIpReturnChannelEntry 4 }

    hwRfRxIpReturnChannelMode OBJECT-TYPE
          SYNTAX     INTEGER{transponder(1)}
          MAX-ACCESS read-write
          STATUS     obsolete
          DESCRIPTION
                "                
                Indicates the channel mode.
                Option:
                1. transponder - transponder mode
                "
              DEFVAL      { 1 }
          ::= { hwRfRxIpReturnChannelEntry 5 }
          
    hwRfRxIpReturnChannelAdminStatus OBJECT-TYPE
          SYNTAX     INTEGER{disable(1),enable(2)}
          MAX-ACCESS read-write
          STATUS     obsolete
          DESCRIPTION
                "
                Indicates the administrative status of ip return rx channel.
                Options:
                1. disable(1) - disable ip return rx channel
                2. enable(2) - enable ip return rx channel
                "
              DEFVAL      { 1 }
          ::= { hwRfRxIpReturnChannelEntry 6 }

    hwRfRxIpReturnChannelFrequencyStatus OBJECT-TYPE
          SYNTAX     Integer32(-1|54000000..204000000)  
          UNITS   "Hz"
          MAX-ACCESS read-only
          STATUS     obsolete
          DESCRIPTION
                "
                Indicates the channel frequency.  
                The adjustment accuracy is 0.1MHz.
                -1 represent invalid value.
                "
          ::= { hwRfRxIpReturnChannelEntry 7 }

    hwRfRxIpReturnChannelFreqWidthStatus OBJECT-TYPE
          SYNTAX     INTEGER{hz400K(1),hz800K(2),invalid(-1)}
          MAX-ACCESS read-only
          STATUS     obsolete
          DESCRIPTION
                "
                Indicates the channel frequency bandwidth.
                Options:
                1. hz400K(1) - 400KHz     
                2. hz800K(2) - 800KHz       
                3. invalid(-1) - invalid value      
                "
          ::= { hwRfRxIpReturnChannelEntry 8 }
     
    hwRfRxIpReturnChannelRfPowerStatus OBJECT-TYPE
          SYNTAX     Integer32(-1|300..500)    
          UNITS   "0.1dBmV"
          MAX-ACCESS read-only
          STATUS     obsolete
          DESCRIPTION
                "
                Indicates the channel received power.
                -1 represent invalid value.
                "
          ::= { hwRfRxIpReturnChannelEntry 9 }

	hwRfRxIpReturnChannelModeStatus OBJECT-TYPE
          SYNTAX     INTEGER{transponder(1),invalid(-1)}
          MAX-ACCESS read-only
          STATUS     obsolete
          DESCRIPTION
                "
                Indicates the channel mode.
                Options:
                1. transponder - transponder mode
                2. invalid(-1) - invalid value
                "
          ::= { hwRfRxIpReturnChannelEntry 10 }
 
    hwRfRxIpReturnChannelOperStatus OBJECT-TYPE
          SYNTAX     INTEGER{down(1),up(2),invalid(-1)}
          MAX-ACCESS read-only
          STATUS     obsolete
          DESCRIPTION
                "
                Indicates the operational status of ip return rx channel .
                 Options:
                1. down(1) - down status
                2. up(2) - up status
                3. invalid(-1) - invalid value
                "
          ::= { hwRfRxIpReturnChannelEntry 11 }
		
    hwRfRxIpReturnChannelRowStatus OBJECT-TYPE
          SYNTAX     RowStatus
          MAX-ACCESS read-create
          STATUS     obsolete
          DESCRIPTION
                "
                Indicates the row status to create or delete a channel ip return configuration.
                Options:
                1. active(1)      -indicates modify the specific ip return configuration.
                2. createAndGo(4) -indicates creating an ip return configuration.
                3. destroy(6)     -indicates deleting the specific ip return configuration.
                "
          ::= { hwRfRxIpReturnChannelEntry 12 } 
          
  -- Table hwRfRxIpReturnChannelTable End
         
  -- Table hwRfCableNdfChannelTable  Begin
            
    hwRfCableNdfChannelTable OBJECT-TYPE
          SYNTAX     SEQUENCE OF HwRfCableNdfChannelEntry
          MAX-ACCESS not-accessible
          STATUS     current
          DESCRIPTION
               "
               This table describes the RF attributes of ndf channels.
               The index of this table  is  ifIndex of ndf channel interface.
               "
          ::= { hwRfObject 3 }

    hwRfCableNdfChannelEntry OBJECT-TYPE
          SYNTAX     HwRfCableNdfChannelEntry
          MAX-ACCESS not-accessible
          STATUS     current
          DESCRIPTION
               "
               This table describes the RF attributes of rx channels.
               The index of this table is ifIndex of ndf channel interface.
               "
          INDEX       { ifIndex }
          ::= { hwRfCableNdfChannelTable 1 }
                
    HwRfCableNdfChannelEntry ::=
          SEQUENCE {
                    hwRfCableNdfChannelChannelID        			Integer32,
                    hwRfCableNdfChannelFrequency                  	Integer32,
                    hwRfCableNdfChannelWidth                        INTEGER,
                    hwRfCableNdfChannelMaxRfPower                   Integer32,
                    hwRfCableNdfChannelAdminStatus                  INTEGER,
                    hwRfCableNdfChannelOperStatus                   INTEGER
                   }
    
    hwRfCableNdfChannelChannelID OBJECT-TYPE
          SYNTAX     Integer32
          MAX-ACCESS read-only
          STATUS     current
          DESCRIPTION
                "
                Indicates the ndf  channel id.
                "
          ::= { hwRfCableNdfChannelEntry 1 }

    hwRfCableNdfChannelFrequency OBJECT-TYPE
          SYNTAX     Integer32
          UNITS   "Hz"
          MAX-ACCESS  read-write
          STATUS  current
          DESCRIPTION
                "
                Indicates the ndf channel center frequency.      
                The frequency resolution is 10KHz.
                -1 represent invalid value.
                "
          ::= { hwRfCableNdfChannelEntry 2 }
           
    hwRfCableNdfChannelWidth OBJECT-TYPE
          SYNTAX     INTEGER{hz640K(1),hz1280K(2),hz2560K(3),hz5120K(4),hz25600K(5)}
          MAX-ACCESS read-write
          STATUS     current
          DESCRIPTION
                "
                Indicates the ndf channel frequency bandwidth.
                Options:
                1. hz640K(1)   - 640KHz     
                2. hz1280K(2)  - 1.28MHZ
                3. hz2560K(3)  - 2.560MHZ
                4. hz5120K(4)  - 5.120MHZ
                5. hz25600K(5) - 25.6MHZ
                6. invalid(-1) - invalid value  
                "   
              DEFVAL      { hz5120K }   
          ::= { hwRfCableNdfChannelEntry 3 } 
          
    hwRfCableNdfChannelMaxRfPower OBJECT-TYPE
          SYNTAX      Integer32  
          UNITS   "0.1dBmV"
          MAX-ACCESS  read-write
          STATUS  current
          DESCRIPTION
                "
                Indicates the channel maximum received power.
                2147483647(0x7FFFFFFF) represent invalid value.
                " 
              DEFVAL      { 300 }
          ::= { hwRfCableNdfChannelEntry 4 }     
          
    hwRfCableNdfChannelAdminStatus OBJECT-TYPE
          SYNTAX     INTEGER{disable(1),enable(2)}
          MAX-ACCESS read-write
          STATUS     current
          DESCRIPTION
                "
                Indicates the administrative status of ndf channel.
                 Options:
                1. disable(1) - disable ndf channel
                2. enable(2) - enable ndf channel
                " 
              DEFVAL      { 1 }
          ::= { hwRfCableNdfChannelEntry 5 }
          
    hwRfCableNdfChannelOperStatus OBJECT-TYPE
          SYNTAX     INTEGER{down(1),up(2),invalid(-1)}
          MAX-ACCESS read-only
          STATUS     current
          DESCRIPTION
                "
                Indicates the operational status of ndf channel.
                 Options:
                1. down(1) - down status
                2. up(2) - up status
                3. invalid(-1) - invalid value
                "
          ::= { hwRfCableNdfChannelEntry 6 }        
                 
  -- Table hwRfCableNdfChannelTable End
 
  -- Table hwRfCableNdrChannelTable  Begin
            
    hwRfCableNdrChannelTable OBJECT-TYPE
          SYNTAX     SEQUENCE OF HwRfCableNdrChannelEntry
          MAX-ACCESS not-accessible
          STATUS     current
          DESCRIPTION
               "
               This table describes the RF attributes of ndr channels.
               The index  of this table is ifIndex  of ndr channel interface.
               "
          ::= { hwRfObject 4 }

    hwRfCableNdrChannelEntry OBJECT-TYPE
          SYNTAX     HwRfCableNdrChannelEntry
          MAX-ACCESS not-accessible
          STATUS     current
          DESCRIPTION
               "
               This table describes the ip return attributes of ndr channels.
               The indexes of this table are ifIndex and hwRfCableNdrChannelChannelID.
               "
          INDEX       { ifIndex }
          ::= { hwRfCableNdrChannelTable 1 }

    HwRfCableNdrChannelEntry ::=
          SEQUENCE {
                    hwRfCableNdrChannelChannelID        			Integer32,
					hwRfCableNdrChannelFrequency                  	Integer32,
					hwRfCableNdrChannelWidth                        INTEGER,
					hwRfCableNdrChannelGain                         Integer32,
					hwRfCableNdrChannelAdminStatus                  INTEGER,
					hwRfCableNdrChannelOperStatus                   INTEGER,
                     hwRfCableNdrChannelInputRfPower                Integer32
                   }

    hwRfCableNdrChannelChannelID OBJECT-TYPE
          SYNTAX     Integer32
          MAX-ACCESS read-only
          STATUS     current
          DESCRIPTION
                "
                Indicates the ndr channel id.                
                "
          ::= { hwRfCableNdrChannelEntry 1 }

    hwRfCableNdrChannelFrequency OBJECT-TYPE
    	  SYNTAX     Integer32
          UNITS   "Hz"
          MAX-ACCESS  read-write
          STATUS  current
          DESCRIPTION
                "
                Indicates the ndr channel center frequency.   
                The  frequency resolution is 10KHz.
                -1 represent invalid value.
                "
          ::= { hwRfCableNdrChannelEntry 2 }

    hwRfCableNdrChannelWidth OBJECT-TYPE
          SYNTAX     INTEGER{hz640K(1),hz1280K(2),hz2560K(3),hz5120K(4)}
          MAX-ACCESS read-write
          STATUS     current
          DESCRIPTION
                "
                Indicates the ndr channel frequency bandwidth.
                Options:
                1. hz640K(1)   - 640KHz     
                2. hz1280K(2)  - 1.28MHZ
                3. hz2560K(3)  - 2.560MHZ
                4. hz5120K(4)  - 5.120MHZ
                5. invalid(-1) - invalid value  
                "   
              DEFVAL      { hz5120K }   
          ::= { hwRfCableNdrChannelEntry 3 } 
          
    hwRfCableNdrChannelGain OBJECT-TYPE         
          SYNTAX     Integer32
          UNITS   "0.1dB"
          MAX-ACCESS  read-write
          STATUS  current
          DESCRIPTION
                "
                Indicates the ndr channel gain .
                2147483647(0x7FFFFFFF) represent invalid value.
                " 
              DEFVAL      { 0 }
          ::= { hwRfCableNdrChannelEntry 4 }

    hwRfCableNdrChannelAdminStatus OBJECT-TYPE
          SYNTAX     INTEGER{disable(1),enable(2)}
          MAX-ACCESS read-write
          STATUS     current
          DESCRIPTION
                "
                Indicates the administrative status of ndr channel.
                Options:
                1. disable(1) - disable ndr channel
                2. enable(2) - enable ndr channel
                "
              DEFVAL      { 1 }
          ::= { hwRfCableNdrChannelEntry 5 }

    hwRfCableNdrChannelOperStatus OBJECT-TYPE
          SYNTAX     INTEGER{down(1),up(2),invalid(-1)}
          MAX-ACCESS read-only
          STATUS     current
          DESCRIPTION
                "
                Indicates the operational status of ndr channel.
                 Options:
                1. down(1) - down status
                2. up(2) - up status
                3. invalid(-1) - invalid value
                "
          ::= { hwRfCableNdrChannelEntry 6 }

    hwRfCableNdrChannelInputRfPower OBJECT-TYPE
          SYNTAX      Integer32  
          UNITS   "0.1dBmV"
          MAX-ACCESS  read-write
          STATUS  current
          DESCRIPTION
                "
                Indicates the channel input power.
                2147483647(0x7FFFFFFF) represent invalid value.
                " 
              DEFVAL      { 100 }
          ::= { hwRfCableNdrChannelEntry 7 }

  -- Table hwRfCableNdrChannelTable End 

  -- Table hwRfCableRfOutPortTable  Begin

     hwRfCableRfOutPortTable OBJECT-TYPE
          SYNTAX     SEQUENCE OF HwRfCableRfOutPortEntry
          MAX-ACCESS not-accessible
          STATUS     current
          DESCRIPTION
               "
               This table describes the gain of RF out port.
               The index of this table is ifIndex.
               "
          ::= { hwRfObject 5 }

    hwRfCableRfOutPortEntry OBJECT-TYPE
          SYNTAX     HwRfCableRfOutPortEntry
          MAX-ACCESS not-accessible
          STATUS     current
          DESCRIPTION
               "
               This table describes the ip return gain of RF out port.
               The index of this table is ifIndex.
               "
          INDEX       { ifIndex }
          ::= { hwRfCableRfOutPortTable 1 }

    HwRfCableRfOutPortEntry ::=
          SEQUENCE {
                     hwRfCableRfOutPortId                   Integer32,
                     hwRfCableRfOutPortGain                 Integer32
                   }

    hwRfCableRfOutPortId OBJECT-TYPE
          SYNTAX     Integer32
          MAX-ACCESS read-only
          STATUS     current
          DESCRIPTION
                "
                Indicates the RF out port id.
                "
          ::= { hwRfCableRfOutPortEntry 1 }

    hwRfCableRfOutPortGain OBJECT-TYPE         
          SYNTAX    Integer32
          UNITS     "0.1dB"
          MAX-ACCESS  read-write
          STATUS  current
          DESCRIPTION
                "
                Indicates the RF out port gain .
                2147483647(0x7FFFFFFF) represent invalid value.
                "
              DEFVAL      { 0 }
          ::= { hwRfCableRfOutPortEntry 2 }

  -- Table hwRfCableRfOutPortTable End

END

--
-- HUAWEI-RFIPRETURN-MIB.mib
--

--
-- HUAWEI-SECURITY-IPLINK-MIB.mib
-- MIB generated by MG-SOFT Visual MIB Builder Version 4.0 Build 341
-- Tuesday, August 19, 2014 at 18:02:02
--

--  =============================================================================
-- Copyright (C) 2012 by HUAWEI TECHNOLOGIES. All rights reserved.
--    
-- Description: The MIB is designed to get HRP information. 
-- Reference: Huawei Enterprise MIB
-- Version: V1.00
-- History: 
--          V1.00 The initial version created by Cao Jiancang 00005275. 
-- =============================================================================

	HUAWEI-SECURITY-IPLINK-MIB DEFINITIONS ::= BEGIN
 
		IMPORTS
			enterprises			
				FROM RFC1155-SMI			
			OBJECT-GROUP, MODULE-COMPLIANCE, NOTIFICATION-GROUP			
				FROM SNMPv2-CONF			
			OBJECT-TYPE, MODULE-IDENTITY, NOTIFICATION-TYPE			
				FROM SNMPv2-SMI;
	
	
		-- 1.3.6.1.4.1.2011.6.122.45
		hwIplink MODULE-IDENTITY 
			LAST-UPDATED "201203191933Z"		-- March 19, 2012 at 19:33 GMT
			ORGANIZATION 
				"Huawei Technologies Co.,Ltd."
			CONTACT-INFO 
				"Huawei Industrial Base
                                 Bantian, Longgang
                                 Shenzhen 518129
                                 People's Republic of China
                                 Website: http://www.huawei.com
                                 Email: support@huawei.com"
			DESCRIPTION 
				"
				V1.00
				The HUAWEI-SECURITY-IPLINK-MIB contains objects to manage the firewall IPLINK module.
				"
			--  Revision history
				 REVISION    "201203191933Z"
                                 DESCRIPTION "V1.00, completed the first draft."
			::= { hwSecurity 45 }

		
	
--
-- Node definitions
--
	
--  March 19, 2012 at 19:33 GMT
-- 
-- Node definitions
-- 
-- 1.3.6.1.4.1.2011
		-- 1.3.6.1.4.1.2011
		huawei OBJECT IDENTIFIER ::= { enterprises 2011 }

		
--  1.3.6.1.4.1.2011.6
		-- 1.3.6.1.4.1.2011.6
		huaweiUtility OBJECT IDENTIFIER ::= { huawei 6 }

		
--  1.3.6.1.4.1.2011.6.122
		-- 1.3.6.1.4.1.2011.6.122
		hwSecurity OBJECT IDENTIFIER ::= { huaweiUtility 122 }

		
		-- 1.3.6.1.4.1.2011.6.122.45.1
		hwIpLinkNotification OBJECT IDENTIFIER ::= { hwIplink 1 }

		
		-- 1.3.6.1.4.1.2011.6.122.45.1.1
		hwIpLinkTrapObjects OBJECT IDENTIFIER ::= { hwIpLinkNotification 1 }

		
--  ===============================================
-- TrapObject.
-- ===============================================
-- 1.3.6.1.4.1.2011.6.122.45.1.1.1
		-- 1.3.6.1.4.1.2011.6.122.45.1.1.1
		hwIpLinkName OBJECT-TYPE
			SYNTAX OCTET STRING
			MAX-ACCESS accessible-for-notify
			STATUS current
			DESCRIPTION
				"The ID of the IP-link"
			::= { hwIpLinkTrapObjects 1 }

		
--  1.3.6.1.4.1.2011.6.122.45.1.1.1
-- 1.3.6.1.4.1.2011.6.122.45.1.1.2	
		-- 1.3.6.1.4.1.2011.6.122.45.1.1.2
		hwIpLinkStatus OBJECT-TYPE
			SYNTAX OCTET STRING
			MAX-ACCESS accessible-for-notify
			STATUS current
			DESCRIPTION
				"The status of the IP-link."
			::= { hwIpLinkTrapObjects 2 }

		
		-- 1.3.6.1.4.1.2011.6.122.45.2
		hwIpLinkTraps OBJECT IDENTIFIER ::= { hwIplink 2 }

		
--  ===============================================
-- definition of traps.      
-- ===============================================                                
		-- 1.3.6.1.4.1.2011.6.122.45.2.1
		hwIpLinkUp NOTIFICATION-TYPE
			OBJECTS { hwIpLinkName, hwIpLinkStatus }
			STATUS current
			DESCRIPTION 
				"The IP-link changes to up"
			::= { hwIpLinkTraps 1 }

		
		-- 1.3.6.1.4.1.2011.6.122.45.2.2
		hwIpLinkDown NOTIFICATION-TYPE
			OBJECTS { hwIpLinkName, hwIpLinkStatus }
			STATUS current
			DESCRIPTION 
				"The IP-link changes to down"
			::= { hwIpLinkTraps 2 }

		
--   1.3.6.1.4.1.2011.6.122.68.3
-- 1.3.6.1.4.1.2011.6.122.68.3
		-- 1.3.6.1.4.1.2011.6.122.45.3
		hwIpLinkConformance OBJECT IDENTIFIER ::= { hwIplink 3 }

		
--   1.3.6.1.4.1.2011.6.122.68.3.1
-- 1.3.6.1.4.1.2011.6.122.68.3.1
		-- 1.3.6.1.4.1.2011.6.122.45.3.1
		hwIpLinkCompliances OBJECT IDENTIFIER ::= { hwIpLinkConformance 1 }

		
--   1.3.6.1.4.1.2011.6.122.68.3.1.1
-- this module
-- 1.3.6.1.4.1.2011.6.122.68.3.1.1
-- this module
		-- 1.3.6.1.4.1.2011.6.122.45.3.1.1
		hwIpLinkCompliance MODULE-COMPLIANCE
			STATUS current
			DESCRIPTION 
				"Description."
			MODULE -- this module
				MANDATORY-GROUPS { hwIpLinkObjectGroup, hwIpLinkTrapGroup }
			::= { hwIpLinkCompliances 1 }

		
--   1.3.6.1.4.1.2011.6.122.68.3.2
-- 1.3.6.1.4.1.2011.6.122.68.3.2
		-- 1.3.6.1.4.1.2011.6.122.45.3.2
		hwIpLinkMibGroups OBJECT IDENTIFIER ::= { hwIpLinkConformance 2 }

		
--   1.3.6.1.4.1.2011.6.122.68.3.2.1
-- 1.3.6.1.4.1.2011.6.122.68.3.2.1
		-- 1.3.6.1.4.1.2011.6.122.45.3.2.1
		hwIpLinkObjectGroup OBJECT-GROUP
			OBJECTS { hwIpLinkName, hwIpLinkStatus }
			STATUS current
			DESCRIPTION 
				"Description."
			::= { hwIpLinkMibGroups 1 }

		
--   1.3.6.1.4.1.2011.6.122.68.3.2.2
-- 1.3.6.1.4.1.2011.6.122.68.3.2.2
		-- 1.3.6.1.4.1.2011.6.122.45.3.2.2
		hwIpLinkTrapGroup NOTIFICATION-GROUP
			NOTIFICATIONS { hwIpLinkUp, hwIpLinkDown }
			STATUS current
			DESCRIPTION 
				"Description."
			::= { hwIpLinkMibGroups 2 }

		
	
	END

--
-- HUAWEI-SECURITY-IPLINK-MIB.mib
--

-- HUAWEI-SECURITY-L2TP-MIB
-- MIB generated by MG-SOFT Visual MIB Builder Version 3.0 Build 253
-- Friday, April 25, 2008 at 15:45:34
--

--  =================================================================
-- Copyright (C) 2003 by  HUAWEI TECHNOLOGIES. All rights reserved
-- 
-- Description: HUAWEI L2TP MIB, this mib will maintain the L2TP 
--              for datacomm product.  
-- Reference:
-- Version: V1.0
-- History:
-- hanzhankun,2008-08-27
-- shaoyu, 2008-09-16
-- =================================================================

	HUAWEI-SECURITY-L2TP-MIB DEFINITIONS ::= BEGIN
 
		IMPORTS
			enterprises			
				FROM RFC1155-SMI			
			OBJECT-GROUP, MODULE-COMPLIANCE, NOTIFICATION-GROUP			
				FROM SNMPv2-CONF			
			Unsigned32, IpAddress, Integer32, OBJECT-TYPE, MODULE-IDENTITY, NOTIFICATION-TYPE			
				FROM SNMPv2-SMI			
			TruthValue, RowStatus, DateAndTime, TimeInterval, TEXTUAL-CONVENTION			
				FROM SNMPv2-TC;
	
	
		hwL2tpMib MODULE-IDENTITY 
                LAST-UPDATED "200808271100Z"                -- January 17, 2008 at 11:00 GMT
			ORGANIZATION 
				"Huawei Technologies co.,Ltd."
			CONTACT-INFO 
				"
				R&D BeiJing, Huawei Technologies co.,Ltd.
				Huawei Bld.,NO.3 Xinxi Rd.,
				Shang-Di Information Industry Base,
				Hai-Dian District Beijing P.R. China
				Zip:100085
				Http://www.huawei.com
				E-mail:support@huawei.com
				"
            DESCRIPTION 
                "
                V1.00
                The HUAWEI-SECURITY-L2TP-MIB contains objects to manage the firewall L2TP module.
                "
			::= { hwSecurity 2 }
			
--
-- Node definitions
--
                -- 1.3.6.1.4.1.2011
                huawei OBJECT IDENTIFIER ::= { enterprises 2011 }
        
                -- 1.3.6.1.4.1.2011.6
                huaweiUtility OBJECT IDENTIFIER ::= { huawei 6 }
        
                -- 1.3.6.1.4.1.2011.6.122
                hwSecurity OBJECT IDENTIFIER ::= { huaweiUtility 122 }
                
                -- 1.3.6.1.4.1.2011.6.122.2
	        hwL2tpMibObjects OBJECT IDENTIFIER ::= { hwL2tpMib 1 }
		
		-- 1.3.6.1.4.1.2011.5.25.8.1.1
		hwL2tpEnableFlag OBJECT-TYPE
			SYNTAX TruthValue
			MAX-ACCESS read-write
			STATUS current
			DESCRIPTION
				"
				the tunnul function switch. the default value is false.
				1: true(on)
				2: false(off)
				"
			::= { hwL2tpMibObjects 1 }		
			
         
--L2TP Group 配置表     
                        
                hwL2tpGroupConfigTable OBJECT-TYPE
                        SYNTAX SEQUENCE OF HwL2tpGroupConfigEntry
                        MAX-ACCESS not-accessible
                        STATUS current
                        DESCRIPTION
                                "l2tp group configure."
                        ::= { hwL2tpMibObjects 2 }
                
                hwL2tpGroupConfigEntry OBJECT-TYPE
                        SYNTAX HwL2tpGroupConfigEntry
                        MAX-ACCESS not-accessible
                        STATUS current
                        DESCRIPTION
                                "."
                        INDEX { hwL2tpGroupindex }
                        ::= { hwL2tpGroupConfigTable 1 }
                
                HwL2tpGroupConfigEntry ::=
                        SEQUENCE { 
                                hwL2tpGroupindex
                                        Integer32,
                                hwL2tpTunnelNumber
                                        Integer32,
                                hwL2tpGroupFlag
                                        Integer32,
                                hwL2tpGroupAuthentication
                                        TruthValue,
                                hwL2tpGroupPassWord
                                        OCTET STRING,   
                                hwL2tpGroupAvpHidden
                                        TruthValue,
                                hwL2tpGroupName
                                        OCTET STRING,
                                hwL2tpGroupRemoteName
                                        OCTET STRING,
                                hwL2tpGroupRetransmit
                                        Integer32,
                                hwL2tpGroupTimeout
                                        TimeInterval,
                                hwL2tpGroupTimer
                                        TimeInterval,
                                hwL2tpGroupLnsIP1
                                        IpAddress,
                                hwL2tpGroupLnsIP2
                                        IpAddress,
                                hwL2tpGroupLnsIP3
                                        IpAddress,
                                hwL2tpGroupLnsIP4
                                        IpAddress,
                                hwL2tpGroupLnsIP5
                                        IpAddress,        
                                hwL2tpGroupForceChap
                                        TruthValue,
                                hwL2tpGroupForceLcp                
                                        TruthValue,
                                hwL2tpGroupVt
                                        Integer32,
                                hwL2tpGroupRowStatus
                                        RowStatus
                         }

                hwL2tpGroupindex OBJECT-TYPE
                        SYNTAX Integer32(1..1000)
                        MAX-ACCESS not-accessible
                        STATUS current
                        DESCRIPTION
                                "Number of l2tp-group."
                        ::= { hwL2tpGroupConfigEntry 1 }
                        
                hwL2tpTunnelNumber OBJECT-TYPE
                        SYNTAX Integer32(1..1000)
                        MAX-ACCESS read-write
                        STATUS current
                        DESCRIPTION
                                "L2tp tunnel number"
                        ::= { hwL2tpGroupConfigEntry 2 }        
                        
                hwL2tpGroupFlag OBJECT-TYPE
                        SYNTAX Integer32(0..2)
                        MAX-ACCESS read-only
                        STATUS current
                        DESCRIPTION
                                "L2tp group type identifier lac/lns. The default value is 0."
                        ::= { hwL2tpGroupConfigEntry 3 }
                
                hwL2tpGroupAuthentication OBJECT-TYPE
                        SYNTAX TruthValue
                        MAX-ACCESS read-write
                        STATUS current
                        DESCRIPTION
                                "Whether the tunnel enable authentication."
                        DEFVAL { true }
                        ::= { hwL2tpGroupConfigEntry 4 }
                        
                hwL2tpGroupPassWord OBJECT-TYPE
                        SYNTAX OCTET STRING (SIZE(0..16))
                        MAX-ACCESS read-write
                        STATUS current
                        DESCRIPTION
                                "L2tp group authentication password."
                        ::= { hwL2tpGroupConfigEntry 5 }
                
                hwL2tpGroupAvpHidden OBJECT-TYPE
                        SYNTAX TruthValue
                        MAX-ACCESS read-write
                        STATUS current
                        DESCRIPTION
                                "Whether the Avp hide."
                        DEFVAL { false }
                        ::= { hwL2tpGroupConfigEntry 6 }
                
                hwL2tpGroupName OBJECT-TYPE
                        SYNTAX OCTET STRING (SIZE(0..30))
                        MAX-ACCESS read-write
                        STATUS current
                        DESCRIPTION
                                "L2tp group name."
                        ::= { hwL2tpGroupConfigEntry 7 }
                        
                hwL2tpGroupRemoteName OBJECT-TYPE
                        SYNTAX OCTET STRING (SIZE(0..30))
                        MAX-ACCESS read-write
                        STATUS current
                        DESCRIPTION
                                "L2tp group peer's name."
                        ::= { hwL2tpGroupConfigEntry 8 }

                hwL2tpGroupRetransmit OBJECT-TYPE
                        SYNTAX Integer32(1..10)
                        MAX-ACCESS read-write
                        STATUS current
                        DESCRIPTION
                                "Retransmit of l2tp control packet."
                        ::= { hwL2tpGroupConfigEntry 9 }

                hwL2tpGroupTimeout OBJECT-TYPE
                        SYNTAX TimeInterval
                        MAX-ACCESS read-write
                        STATUS current
                        DESCRIPTION
                                "
                                Timeout of l2tp control packet."
                        ::= { hwL2tpGroupConfigEntry 10 }

                hwL2tpGroupTimer OBJECT-TYPE
                        SYNTAX TimeInterval
                        MAX-ACCESS read-write
                        STATUS current
                        DESCRIPTION
                                "
                                Hand shake timeout of l2tp group."
                        ::= { hwL2tpGroupConfigEntry 11 }
 
                hwL2tpGroupLnsIP1 OBJECT-TYPE
                        SYNTAX IpAddress
                        MAX-ACCESS read-write
                        STATUS current
                        DESCRIPTION
                                "Lns ip address1."
                        ::= { hwL2tpGroupConfigEntry 12 }
 
                hwL2tpGroupLnsIP2 OBJECT-TYPE
                        SYNTAX IpAddress
                        MAX-ACCESS read-write
                        STATUS current
                        DESCRIPTION
                                "Lns ip address2."
                        ::= { hwL2tpGroupConfigEntry 13 }
 
                hwL2tpGroupLnsIP3 OBJECT-TYPE
                        SYNTAX IpAddress
                        MAX-ACCESS read-write
                        STATUS current
                        DESCRIPTION
                                "Lns ip address3."
                        ::= { hwL2tpGroupConfigEntry 14 }
 
                hwL2tpGroupLnsIP4 OBJECT-TYPE
                        SYNTAX IpAddress
                        MAX-ACCESS read-write
                        STATUS current
                        DESCRIPTION
                                "Lns ip address4."
                        ::= { hwL2tpGroupConfigEntry 15 }
 
                hwL2tpGroupLnsIP5 OBJECT-TYPE
                        SYNTAX IpAddress
                        MAX-ACCESS read-write
                        STATUS current
                        DESCRIPTION
                                "Lns ip address5."
                        ::= { hwL2tpGroupConfigEntry 16 }       
                
                hwL2tpGroupForceChap OBJECT-TYPE
                        SYNTAX TruthValue
                        MAX-ACCESS read-write
                        STATUS current
                        DESCRIPTION
                                "Whether force chap."
                        ::= { hwL2tpGroupConfigEntry 17 }       
                        
                hwL2tpGroupForceLcp OBJECT-TYPE
                        SYNTAX TruthValue
                        MAX-ACCESS read-write
                        STATUS current
                        DESCRIPTION
                                "Whether force lcp renegotiate."
                        ::= { hwL2tpGroupConfigEntry 18 }
                        
                hwL2tpGroupVt OBJECT-TYPE
                        SYNTAX Integer32(0..1023|65535)
                        MAX-ACCESS read-write
                        STATUS current
                        DESCRIPTION
                                "Virtual template number."
                        ::= { hwL2tpGroupConfigEntry 19 }
                        
                hwL2tpGroupRowStatus OBJECT-TYPE
                        SYNTAX RowStatus
                        MAX-ACCESS read-write
                        STATUS current
                        DESCRIPTION
                                "                               
                                "
                        ::= { hwL2tpGroupConfigEntry 20}
                        
                        
-- L2TP Tunnel Configure Table
                hwL2tpTunnelTable OBJECT-TYPE
                        SYNTAX SEQUENCE OF HwL2tpTunnelEntry 
                        MAX-ACCESS not-accessible
                        STATUS current
                        DESCRIPTION
                                "This table specifies the monitoring attributes for
                                 Huawei L2TP tunnel."
                        ::= { hwL2tpMibObjects 3 }
                
                hwL2tpTunnelEntry OBJECT-TYPE
                        SYNTAX HwL2tpTunnelEntry 
                        MAX-ACCESS not-accessible
                        STATUS current
                        DESCRIPTION
                                "Each entry in the hwL2tpTunnelTable holds a set of monitoring
                                 parameters associated with an instance of l2tp tunnel."
                        INDEX { hwL2tpTunnelIndex}
                        ::= { hwL2tpTunnelTable 1 }
                
                HwL2tpTunnelEntry ::=
                        SEQUENCE { 
                                hwL2tpTunnelIndex
                                        Integer32,                                
                                hwL2tpTunnelLocalID                
                                        Integer32,
                                hwL2tpTunnelRemoteID
                                        Integer32,
                                hwL2tpTunnelRemoteName
                                        OCTET STRING,
                                hwL2tpTunnelRemoteIP
                                        IpAddress,
                                hwL2tpTunnelRemotePort
                                        Integer32,
                                hwL2tpTunnelSessionNum
                                        Integer32,
                                hwL2tpLnsGroupRowStatus
                                        RowStatus                                                                                                                                                       
                         }

                hwL2tpTunnelIndex OBJECT-TYPE
                        SYNTAX Integer32 (1..65535)
                        MAX-ACCESS not-accessible
                        STATUS current
                        DESCRIPTION
                                "A unique value for l2tp tunnel table.  Its value ranges
                                 between 0 and 65535 and may not be contigous."
                        ::= { hwL2tpTunnelEntry 1 }
                        
                hwL2tpTunnelLocalID OBJECT-TYPE
                        SYNTAX Integer32 (1..65535)
                        MAX-ACCESS read-only
                        STATUS current
                        DESCRIPTION
                                "L2tp tunnel local's id."
                        ::= { hwL2tpTunnelEntry 2 }
                
                hwL2tpTunnelRemoteID OBJECT-TYPE
                        SYNTAX Integer32 (1..65535)
                        MAX-ACCESS read-only
                        STATUS current
                        DESCRIPTION
                                "L2tp tunnel peer's id."      
                        ::= { hwL2tpTunnelEntry 3 }
                        
                hwL2tpTunnelRemoteName OBJECT-TYPE
                        SYNTAX OCTET STRING
                        MAX-ACCESS read-only
                        STATUS current
                        DESCRIPTION
                                "L2tp tunnel peer's name."       
                        ::= { hwL2tpTunnelEntry 4 }
                        
                hwL2tpTunnelRemoteIP OBJECT-TYPE
                        SYNTAX IpAddress
                        MAX-ACCESS read-only
                        STATUS current
                        DESCRIPTION
                                "L2tp tunnel peer's IP address."    
                        ::= { hwL2tpTunnelEntry 5 }
                        
                hwL2tpTunnelRemotePort OBJECT-TYPE
                        SYNTAX Integer32 (1..65535)
                        MAX-ACCESS read-only
                        STATUS current
                        DESCRIPTION
                                "L2tp tunnel peer's port number."        
                        ::= { hwL2tpTunnelEntry 6 }
                        
                hwL2tpTunnelSessionNum OBJECT-TYPE
                        SYNTAX Integer32 (1..65535)
                        MAX-ACCESS read-only
                        STATUS current
                        DESCRIPTION
                                "Number of l2tp tunnel's sessions"          
                        ::= { hwL2tpTunnelEntry 7 }
                        
                hwL2tpLnsGroupRowStatus OBJECT-TYPE
                        SYNTAX RowStatus
                        MAX-ACCESS read-write
                        STATUS current
                        DESCRIPTION
                                "                               
                                "
                        ::= { hwL2tpTunnelEntry 8}
                        
                        
--L2tp Session Table
 
                hwL2tpSessionTable OBJECT-TYPE
                        SYNTAX SEQUENCE OF HwL2tpSessionEntry
                        MAX-ACCESS not-accessible
                        STATUS current
                        DESCRIPTION
                                "This table specifies the monitoring attributes for
                                 Huawei l2tp session."
                        ::= { hwL2tpMibObjects 4 }
                
                hwL2tpSessionEntry OBJECT-TYPE
                        SYNTAX HwL2tpSessionEntry
                        MAX-ACCESS not-accessible
                        STATUS current
                        DESCRIPTION
                                "Each entry in the hwL2tpSessionTable holds a set of monitoring
                                 parameters associated with an instance of l2tp session."
                        INDEX { hwL2tpSessionIndex }
                        ::= { hwL2tpSessionTable 1 }
                
                HwL2tpSessionEntry ::=
                        SEQUENCE { 
                                hwL2tpSessionIndex
                                        Integer32,
                                hwL2tpSessionTunnelID
                                		Integer32,
                                hwL2tpSessionLocalSID
                                        Integer32,
                                hwL2tpSessionRemoteSID
                                        Integer32,
                                hwL2tpSessionUserName
                                        OCTET STRING,
                                hwL2tpSessionUserOnlineTime
                                	DateAndTime,
                                hwL2tpSessionState
                                        INTEGER,
                                hwL2tpSessionCallType
                                        INTEGER,
                                hwL2tpSessionSerialNumber
                                        Unsigned32                                                                                                                                                      
                         }

                   hwL2tpSessionIndex OBJECT-TYPE
                           SYNTAX          Integer32 (1..2147483647)
                           MAX-ACCESS      not-accessible
                           STATUS          current
                           DESCRIPTION
                              "This object identifies the session's associated
                               L2TP tunnel ifIndex value."
                           ::= { hwL2tpSessionEntry 1 }
                           
                   hwL2tpSessionTunnelID OBJECT-TYPE
                   	   SYNTAX          Integer32  (0..65535)
                           MAX-ACCESS      read-only
                           STATUS          current
                           DESCRIPTION
                              "This object contains the local assigned tunnel
                               identifier for this session. "
                           ::= { hwL2tpSessionEntry 2 }
                
                   hwL2tpSessionLocalSID OBJECT-TYPE
                           SYNTAX          Integer32 (1..65535)
                           MAX-ACCESS      read-only
                           STATUS          current
                           DESCRIPTION
                              "This object contains the local assigned session
                               identifier for this session."
                           ::= { hwL2tpSessionEntry 3 }
                
                   hwL2tpSessionRemoteSID OBJECT-TYPE
                           SYNTAX          Integer32  (0..65535)
                           MAX-ACCESS      read-only
                           STATUS          current
                           DESCRIPTION
                              "This object contains the remote assigned session
                               identifier for this session. When a session is
                               starting this value may be zero until the remote
                               tunnel endpoint has responded."
                           ::= { hwL2tpSessionEntry 4 }
                
                   hwL2tpSessionUserName OBJECT-TYPE
                           SYNTAX          OCTET STRING
                           MAX-ACCESS      read-only
                           STATUS          current
                           DESCRIPTION
                              "This object identifies the peer session name on
                               this interface. This is typically the login name
                               of the remote user. If the user name is unknown to
                               the local tunnel peer then this object will contain
                               a null string."
                           ::= { hwL2tpSessionEntry 5 }
                            
                   hwL2tpSessionUserOnlineTime OBJECT-TYPE
                           SYNTAX          DateAndTime
                           MAX-ACCESS      read-only
                           STATUS          current
                           DESCRIPTION
                              "This object identifies the peer user online time."
                           ::= { hwL2tpSessionEntry 6 }
                
                   hwL2tpSessionState   OBJECT-TYPE
                           SYNTAX          INTEGER {
                                               sessionIdle(1),
                                               sessionConnecting(2),
                                               sessionEstablished(3),
                                               sessionDisconnecting(4)
                                           }
                           MAX-ACCESS      read-only
                           STATUS          current
                           DESCRIPTION
                              "This object contains the current state of the
                               session."
                           ::= { hwL2tpSessionEntry 7 }
                
                   hwL2tpSessionCallType OBJECT-TYPE
                           SYNTAX          INTEGER {
                                               lacIncoming(1),
                                               lnsIncoming(2),
                                               lacOutgoing(3),
                                               lnsOutgoing(4)
                                           }
                           MAX-ACCESS      read-only
                           STATUS          current
                           DESCRIPTION
                              "This object indicates the type of call and the
                               role this tunnel peer is providing for this
                               session. For example, lacIncoming(1) indicates
                               that this tunnel peer is acting as a LAC and
                               generated a Incoming-Call-Request to the tunnel
                               peer (the LNS). Note that tunnel peers can be
                               both LAC and LNS simultaneously."
                           ::= { hwL2tpSessionEntry 8 }
                
                   hwL2tpSessionSerialNumber OBJECT-TYPE
                           SYNTAX          Unsigned32
                           MAX-ACCESS      read-only
                           STATUS          current
                           DESCRIPTION
                              "This object contains the serial number that has
                               been assigned to this  session."
                           ::= { hwL2tpSessionEntry 9 }
                        
-- ===============================================
-- L2tpTrapObject.
-- ===============================================
 
 		hwL2tpTrapObject OBJECT IDENTIFIER ::= { hwL2tpMibObjects 7 }
	        	        
	    	hwL2tpTunnelindex OBJECT-TYPE
			SYNTAX Integer32 (1..65535)
			MAX-ACCESS accessible-for-notify
			STATUS current
			DESCRIPTION
				"The L2tp tunnel index."
			::= { hwL2tpTrapObject 1 }
	        
	    	hwL2tpSessionindex OBJECT-TYPE
			SYNTAX Integer32 (1..2147483647)
			MAX-ACCESS accessible-for-notify
			STATUS current
			DESCRIPTION
				"The L2tp session index."
			::= { hwL2tpTrapObject 2 }
	        
	    	hwL2tpTunnelRemoteAddr OBJECT-TYPE
			SYNTAX IpAddress
			MAX-ACCESS accessible-for-notify
			STATUS current
			DESCRIPTION
				"The L2tp peer's address."
			::= { hwL2tpTrapObject 3 }

	    	hwL2tpTunnelUserName OBJECT-TYPE
			SYNTAX OCTET STRING
			MAX-ACCESS accessible-for-notify
			STATUS current
			DESCRIPTION
				"The L2tp peer's name."
			::= { hwL2tpTrapObject 4 }
			
		hwL2tpTunnelStartTime OBJECT-TYPE
			SYNTAX DateAndTime
			MAX-ACCESS accessible-for-notify
			STATUS current
			DESCRIPTION
				"The L2tp peer's online time."
			::= { hwL2tpTrapObject 5 }
                        
-- ===============================================
-- definition of traps.      
-- ===============================================

                hwL2tpTrap OBJECT IDENTIFIER ::= { hwL2tpMibObjects 8 }
                hwL2tpNotifications OBJECT IDENTIFIER ::= { hwL2tpTrap 1 }
                                
                hwL2tpSessionStart NOTIFICATION-TYPE
                OBJECTS { 
                          hwL2tpTunnelindex,                    
                          hwL2tpSessionindex,
                          hwL2tpTunnelRemoteAddr,
                          hwL2tpTunnelUserName,
                          hwL2tpTunnelStartTime
                        }
                STATUS     current
                DESCRIPTION
                               "This notification is generated when an L2tp 
                                Tunnel is created."
                ::= { hwL2tpNotifications 1 }
                
                hwL2tpSessionStop NOTIFICATION-TYPE
                OBJECTS {
                          hwL2tpTunnelindex,                    
                          hwL2tpSessionindex,
                          hwL2tpTunnelRemoteAddr,
                          hwL2tpTunnelUserName,
                          hwL2tpTunnelStartTime
                        }
                STATUS     current
                DESCRIPTION
                               "This notification is generated when an L2tp
                                Tunnel is deleted."
                ::= { hwL2tpNotifications 2 }
                
-- ===============================================
-- Conformance Information             
-- ===============================================

		hwL2tpMibConformance OBJECT IDENTIFIER ::= { hwL2tpMibObjects 10 }
		
		--hwL2tpMibCompliances OBJECT IDENTIFIER ::= { hwL2tpMibConformance 1 }
		
		hwL2tpMibGroups OBJECT IDENTIFIER ::= { hwL2tpMibConformance 2 }
		
		
-- ===============================================
-- Compliance Statements             
-- ===============================================	
	
        hwL2tpMibCompliances MODULE-COMPLIANCE
			 STATUS current
			 DESCRIPTION 
				" "
			 MODULE -- this module
			 MANDATORY-GROUPS 
				{ 
					hwL2tpGroupConfigTableGroup,
					hwL2tpTunnelTableGroup,
					hwL2tpSessionTableGroup,
					hwL2tpTrapObjectGroup,
					hwL2tpTrapGroup
				}
			::= { hwL2tpMibConformance 1 }
		     
		hwL2tpGroupConfigTableGroup OBJECT-GROUP
			OBJECTS { 
                                	hwL2tpTunnelNumber,
                                	hwL2tpGroupFlag,
                                	hwL2tpGroupAuthentication,
                                	hwL2tpGroupPassWord,   
                                	hwL2tpGroupAvpHidden,
                                	hwL2tpGroupName,
                                	hwL2tpGroupRemoteName,
                                	hwL2tpGroupRetransmit,
                                	hwL2tpGroupTimeout,
                                	hwL2tpGroupTimer,
                                	hwL2tpGroupLnsIP1,
                                	hwL2tpGroupLnsIP2,
                                	hwL2tpGroupLnsIP3,
                                	hwL2tpGroupLnsIP4,
                                	hwL2tpGroupLnsIP5,      
                                	hwL2tpGroupForceChap,
                                	hwL2tpGroupForceLcp,
                                	hwL2tpGroupVt,
                                	hwL2tpGroupRowStatus						
				}
			STATUS current
			DESCRIPTION 
				"l2tp group configure."
			::= { hwL2tpMibGroups 2 }			     
        
        	hwL2tpTunnelTableGroup OBJECT-GROUP
			OBJECTS {                                
                                	hwL2tpTunnelLocalID,
                                	hwL2tpTunnelRemoteID,
                                	hwL2tpTunnelRemoteName,
                                	hwL2tpTunnelRemoteIP,
                                	hwL2tpTunnelRemotePort,
                                	hwL2tpTunnelSessionNum,
                                	hwL2tpLnsGroupRowStatus      						
				}
			STATUS current
			DESCRIPTION 
				"This table specifies the monitoring attributes for
                                 Huawei L2TP tunnel."
			::= { hwL2tpMibGroups 3 }
			
		hwL2tpSessionTableGroup OBJECT-GROUP
			OBJECTS {                       
                                	hwL2tpSessionTunnelID,
                                	hwL2tpSessionLocalSID,
                                	hwL2tpSessionRemoteSID,
                                	hwL2tpSessionUserName,
                                	hwL2tpSessionUserOnlineTime,
                                	hwL2tpSessionState,
                                	hwL2tpSessionCallType,
                                	hwL2tpSessionSerialNumber        						
				}
			STATUS current
			DESCRIPTION 
				"This table specifies the monitoring attributes for
                                 Huawei l2tp session."
			::= { hwL2tpMibGroups 4 }
			
		hwL2tpTrapObjectGroup OBJECT-GROUP
			OBJECTS {                               
                                	hwL2tpTunnelindex,
                                	hwL2tpSessionindex,
                                	hwL2tpTunnelRemoteAddr,
                                	hwL2tpTunnelUserName,
                                	hwL2tpTunnelStartTime       						
				}
			STATUS current
			DESCRIPTION 
				"l2tp trap objects."
			::= { hwL2tpMibGroups 5 }
			
		hwL2tpTrapGroup NOTIFICATION-GROUP
			NOTIFICATIONS {                               
                                	hwL2tpSessionStart,
                                	hwL2tpSessionStop      						
				}
			STATUS current
			DESCRIPTION 
				"l2tp traps."
			::= { hwL2tpMibGroups 6 }
			
        END

--
-- HUAWEI-SECURITY-L2TP-MIB
--

-- =============================================================================                                                  
-- Copyright (C) 2021 by HUAWEI TECHNOLOGIES. All rights reserved.                                                                
--                                                                                                                                
-- Description:                                                                                                                   
-- Reference: Huawei Enterprise MIB                                                                                               
-- Version: V1.06                                                                                                                 
-- History:                                                                                                                       
--                                                               
-- =============================================================================                                                  
                                                                                                                                  
HUAWEI-SECURITY-NHRP-MIB DEFINITIONS ::= BEGIN                                                                                     
                                                                                                                                  
	IMPORTS                                                                                                                         
			huaweiUtility                                                                                                               
            FROM HUAWEI-MIB                                                                                                       
			OBJECT-GROUP, MODULE-COMPLIANCE, NOTIFICATION-GROUP                                                                         
        FROM SNMPv2-CONF                                                                                                          
		    Gauge32, IpAddress, OBJECT-TYPE, MODULE-IDENTITY, NOTIFICATION-TYPE,Integer32                                                       
			FROM SNMPv2-SMI                                                                                                             
    		enterprises			                                                                                                          
		    FROM RFC1155-SMI                                                                                                          
            DateAndTime			                                                                                                      
			FROM SNMPv2-TC;                                                                                                             
                                                                                                                                  
                                                                                                                                  
    hwNHRP MODULE-IDENTITY                                                                                                         
            LAST-UPDATED "202106280000Z"                                                  
            ORGANIZATION                                                                                                          
"Huawei Technologies Co.,Ltd."                                                                                                    
            CONTACT-INFO                                                                                                          
"Huawei Industrial Base                                                                                                           
  Bantian, Longgang                                                                                                               
   Shenzhen 518129                                                                                                                
   People's Republic of China                                                                                                     
   Website: http://www.huawei.com                                                                                                 
   Email: support@huawei.com                                                                                                      
 "                                
            DESCRIPTION 
                "Please provide the descritpion."

           REVISION "202106280000Z"
           DESCRIPTION  "Modify comment at 2021-06-28." 
           
           REVISION "202104300000Z"
           DESCRIPTION  "Modify comment at 2021-04-30." 

            REVISION    "201903082000Z" 
            DESCRIPTION " Modify hwNHRPHubDOWN"

            REVISION    "201902252000Z" 
            DESCRIPTION " Modify hwNHRPHubDOWN"

            REVISION    "201712232000Z" 
            DESCRIPTION " Add hwNHRPLocalPeerLimitReachAlarm and hwNHRPLocalPeerLimitResume"

            REVISION    "201712072000Z" 
            DESCRIPTION " Add hwNHRPDynPeerThresholdExceedAlarm and hwNHRPDynPeerThresholdExceedResume"

            REVISION    "201710272000Z" 
            DESCRIPTION " Add hwNHRPPeerThresholdExceedAlarm and hwNHRPPeerThresholdExceedResume"

            REVISION    "201506022000Z" 
            DESCRIPTION "V1.00, initial version."                 
                                                                                                                      
		        ::= { hwSecurity 73 }                                                                                                 
                                                                                                                                  
		                                                                                                                              
-- ===============================================                                                                                
-- Node definitions                                                                                                               
-- ===============================================                                                                                
	                                                                                                                                
	    	-- 1.3.6.1.4.1.2011                                                                                                       
		--huawei OBJECT IDENTIFIER ::= { enterprises 2011 }                                                                           
	                                                                                                                                
		-- 1.3.6.1.4.1.2011.6                                                                                                         
		--huaweiUtility OBJECT IDENTIFIER ::= { huawei 6 }                                                                            
	                                                                                                                                
		-- 1.3.6.1.4.1.2011.6.122                                                                                                     
		hwSecurity OBJECT IDENTIFIER ::= { huaweiUtility 122 }                                                                        
		                                                                                                                              
		                                                                                                                              
		hwNHRPNotification OBJECT IDENTIFIER ::= { hwNHRP 0 }                                                                           
		hwNHRPTrapObject OBJECT IDENTIFIER ::= { hwNHRPNotification 1 }                                                                 
		hwNHRPTraps OBJECT IDENTIFIER ::= { hwNHRPNotification 2 }                                                                      
                                                                                                                                  
                                                                                                                                  
-- ===============================================                                                                                
-- TrapObject.                                                                                                                    
-- ===============================================                                                                                
 	        	        		                                                                                                          
 		hwNHRPInterface  OBJECT-TYPE                                                                                                  
	        	SYNTAX OCTET STRING (SIZE (1..128))                                                                                   
	        	MAX-ACCESS accessible-for-notify                                                                                      
	        	STATUS current                                                                                                        
	        	DESCRIPTION                                                                                                           
	            		"the interface of the NHRP peer."                                                                                      
	        	::= { hwNHRPTrapObject 1 } 
	        	
	        hwNHRPProAddress  OBJECT-TYPE                                                                                                  
	        	SYNTAX OCTET STRING (SIZE (1..128))                                                                                   
	        	MAX-ACCESS accessible-for-notify                                                                                      
	        	STATUS current                                                                                                        
	        	DESCRIPTION                                                                                                           
	            		"the protocol address of the NHRP peer."                                                                                      
	        	::= { hwNHRPTrapObject 2 }
	        	
	    	hwNHRPProMask  OBJECT-TYPE                                                                                                  
	        	SYNTAX OCTET STRING (SIZE (1..128))                                                                                   
	        	MAX-ACCESS accessible-for-notify                                                                                      
	        	STATUS current                                                                                                        
	        	DESCRIPTION                                                                                                           
	            		"the mask of the protocol address."                                                                                      
	        	::= { hwNHRPTrapObject 3 }    		                                                                                            
	        	                                                                                                                      
	    	hwNHRPNextHop  OBJECT-TYPE                                                                                                  
	        	SYNTAX OCTET STRING (SIZE (1..128))                                                                                   
	        	MAX-ACCESS accessible-for-notify                                                                                      
	        	STATUS current                                                                                                        
	        	DESCRIPTION                                                                                                           
	            		"the next hop of the nhrp peer."                                                                                      
	        	::= { hwNHRPTrapObject 4 }                                                                                             
	        	                                                                                                                      
	        hwNHRPNbmaAddress  OBJECT-TYPE                                                                                                  
	        	SYNTAX OCTET STRING (SIZE (1..128))                                                                                   
	        	MAX-ACCESS accessible-for-notify                                                                                      
	        	STATUS current                                                                                                        
	        	DESCRIPTION                                                                                                           
	            		"the nbma address of the nhrp peer."                                                                                      
	        	::= { hwNHRPTrapObject 5 }
	        	
	        hwNHRPType  OBJECT-TYPE                                                                                                  
	        	SYNTAX OCTET STRING (SIZE (1..128))                                                                                   
	        	MAX-ACCESS accessible-for-notify                                                                                      
	        	STATUS current                                                                                                        
	        	DESCRIPTION                                                                                                           
	            		"the type of the nhrp peer."                                                                                      
	        	::= { hwNHRPTrapObject 6 }	        	                                                                                             

	        hwNHRPPeerDelReason  OBJECT-TYPE                                                                                                  
	        	SYNTAX OCTET STRING (SIZE (1..128))                                                                                     
	        	MAX-ACCESS accessible-for-notify                                                                                      
	        	STATUS current                                                                                                        
	        	DESCRIPTION                                                                                                           
	            		"the delete reason of the nhrp peer."                                                                                      
	        	::= { hwNHRPTrapObject 7 }

	        hwNHRPThrehold  OBJECT-TYPE                                                                                                  
	        	SYNTAX Integer32 (1..65535)                                                                                   
	        	MAX-ACCESS accessible-for-notify                                                                                      
	        	STATUS current                                                                                                        
	        	DESCRIPTION                                                                                                           
	            		"The object indicates the alarm threshold of NHRP peer."                                                                                      
	        	::= { hwNHRPTrapObject 8 }

	        hwNHRPPeerCnt  OBJECT-TYPE                                                                                                  
	        	SYNTAX Integer32 (1..65535)                                                                                   
	        	MAX-ACCESS accessible-for-notify                                                                                      
	        	STATUS current                                                                                                        
	        	DESCRIPTION                                                                                                           
	            		"The object indicates the number of NHRP peers."                                                                                      
	        	::= { hwNHRPTrapObject 9 }
	        	    	                                                                                                                	        		        		                                                                            
	        hwNHRPDynPeerThrehold  OBJECT-TYPE                                                                                                  
	        	SYNTAX Integer32 (1..65535)                                                                                   
	        	MAX-ACCESS accessible-for-notify                                                                                      
	        	STATUS current                                                                                                        
	        	DESCRIPTION                                                                                                           
	            		"The object indicates the alarm threshold of NHRP dynamic peer."                                                                                      
	        	::= { hwNHRPTrapObject 10 }
    
	        hwNHRPDynPeerCnt  OBJECT-TYPE                                                                                                  
	        	SYNTAX Integer32 (1..65535)                                                                                   
	        	MAX-ACCESS accessible-for-notify                                                                                      
	        	STATUS current                                                                                                        
	        	DESCRIPTION                                                                                                           
	            		"The object indicates the number of NHRP dynamic peer."                                                                                      
	        	::= { hwNHRPTrapObject 11 }
 
 	        hwNHRPLocalPeerLimit  OBJECT-TYPE                                                                                                  
	        	SYNTAX Integer32 (1..65535)                                                                                   
	        	MAX-ACCESS accessible-for-notify                                                                                      
	        	STATUS current                                                                                                        
	        	DESCRIPTION                                                                                                           
	            		"The object indicates the alarm limit of NHRP local peer."                                                                                      
	        	::= { hwNHRPTrapObject 12 }
    
	        hwNHRPLocalPeerCnt  OBJECT-TYPE                                                                                                  
	        	SYNTAX Integer32 (1..65535)                                                                                   
	        	MAX-ACCESS accessible-for-notify                                                                                      
	        	STATUS current                                                                                                        
	        	DESCRIPTION                                                                                                           
	            		"The object indicates the number of NHRP local peer."                                                                                      
	        	::= { hwNHRPTrapObject 13 }

	        hwNHRPHubDownReason  OBJECT-TYPE                                                                                                  
	        	SYNTAX OCTET STRING (SIZE (1..128))                                                                                     
	        	MAX-ACCESS accessible-for-notify                                                                                      
	        	STATUS current                                                                                                        
	        	DESCRIPTION                                                                                                           
	            		"the reason of the hub down."                                                                                      
	        	::= { hwNHRPTrapObject 14 }
  

-- ===============================================                                                                                
-- definition of traps.                                                                                                           
-- ===============================================                                                                                
	        hwNHRPPeerADD NOTIFICATION-TYPE                                                                                    
			OBJECTS {                                                                                                                   
				hwNHRPInterface,
				hwNHRPProAddress,
				hwNHRPProMask,
				hwNHRPNextHop,
				hwNHRPNbmaAddress,
				hwNHRPType																                                                                                                            
			        }                                                                                                                   
			STATUS     current                                                                                                          
			DESCRIPTION                                                                                                                 
			    "NHRP peer is added."                                                                 
			::= { hwNHRPTraps 1}                                                                                                         
			                                                                                                                            
		hwNHRPPeerDELETE NOTIFICATION-TYPE                                                                                       
			OBJECTS {                                                                                                                   
				hwNHRPInterface,
				hwNHRPProAddress,
				hwNHRPProMask,
				hwNHRPNextHop,
				hwNHRPNbmaAddress,
				hwNHRPType,
				hwNHRPPeerDelReason
				                                                                                                               
			        }                                                                                                                   
			STATUS     current                                                                                                          
			DESCRIPTION                                                                                                                 
			    "NHRP peer is deteled."                                                               
			::= { hwNHRPTraps 2}                                                                                                         
			                                                                                                                            
	        hwNHRPHubUP NOTIFICATION-TYPE                                                                                    
			OBJECTS {                                                                                                                   
				hwNHRPInterface,
				hwNHRPProAddress,
				hwNHRPProMask,
				hwNHRPNextHop,
				hwNHRPNbmaAddress,
				hwNHRPType                                                                                                          
		      		}                                                                                                                   
			STATUS     current                                                                                                          
			DESCRIPTION                                                                                                                 
			    "NHRP hub is up."                                                                 
			::= { hwNHRPTraps 3}                                                                                                         
                                                                                                                                  
	        hwNHRPHubDOWN NOTIFICATION-TYPE                                                                                   
			OBJECTS {                                                                                                                   
				hwNHRPInterface,
				hwNHRPProAddress,
				hwNHRPProMask,
				hwNHRPNextHop,
				hwNHRPNbmaAddress,    
                                                                             hwNHRPHubDownReason    
                                                                                                  
			        }                                                                                                                   
			STATUS     current                                                                                                          
			DESCRIPTION                                                                                                                 
			    "NHRP hub is down ."                                                               
			::= { hwNHRPTraps 4}

 	        hwNHRPPeerThresholdExceedAlarm NOTIFICATION-TYPE                                                                                   
			OBJECTS {                                                                                                                   
				hwNHRPThrehold,
				hwNHRPPeerCnt                                                                                                          
			        }                                                                                                                   
			STATUS     current                                                                                                          
			DESCRIPTION                                                                                                                 
			    "The number of NHRP peer reached the alarm threshold."  
			::= { hwNHRPTraps 5}                                                                                                        
                                                        
 	        hwNHRPPeerThresholdExceedResume NOTIFICATION-TYPE                                                                                   
			OBJECTS {                                                                                                                   
				hwNHRPThrehold,
				hwNHRPPeerCnt                                                                                                          
			        }                                                                                                                   
			STATUS     current                                                                                                          
			DESCRIPTION                                                                                                                 
			    "The number of NHRP peers fell below the alarm threshold."  
			::= { hwNHRPTraps 6}                                                                                     	        			                                                                                                                                                                                                                       
			                                                                                                                            
 	        hwNHRPDynPeerThresholdExceedAlarm NOTIFICATION-TYPE                                                                                   
			OBJECTS {                                                                                                                   
				hwNHRPDynPeerThrehold,
				hwNHRPDynPeerCnt                                                                                                          
			        }                                                                                                                   
			STATUS     current                                                                                                          
			DESCRIPTION                                                                                                                 
			    "The number of NHRP Dynamic peer reached the alarm threshold."  
			::= { hwNHRPTraps 7}                                                                                                        
                                                        
 	        hwNHRPDynPeerThresholdExceedResume NOTIFICATION-TYPE                                                                                   
			OBJECTS {                                                                                                                   
				hwNHRPDynPeerThrehold,
				hwNHRPDynPeerCnt                                                                                                          
				}                                                                                                                   
			STATUS     current                                                                                                          
			DESCRIPTION                                                                                                                 
			    "The number of NHRP Dynamic peers fell below the alarm threshold."  
			::= { hwNHRPTraps 8}
			
	        hwNHRPLocalPeerLimitReachAlarm NOTIFICATION-TYPE                                                                                   
			OBJECTS {                                                                                                                   
				hwNHRPLocalPeerLimit,
				hwNHRPLocalPeerCnt                                                                                                          
			        }                                                                                                                   
			STATUS     current                                                                                                          
			DESCRIPTION                                                                                                                 
			    "The number of NHRP Local peer reached the alarm limit."  
			::= { hwNHRPTraps 9}                                                                                                        
                                                        
 	        hwNHRPLocalPeerLimitResume NOTIFICATION-TYPE                                                                                   
			OBJECTS {                                                                                                                   
				hwNHRPLocalPeerLimit,
				hwNHRPLocalPeerCnt                                                                                                          
				}                                                                                                                   
			STATUS     current                                                                                                          
			DESCRIPTION                                                                                                                 
			    "The number of NHRP Local peers fell below the alarm limit."  
			::= { hwNHRPTraps 10}
	

--   Conformance information                                                                                                      
                                                                                                                                  
        hwNHRPMIBConformance OBJECT IDENTIFIER ::= { hwNHRP 4 }                                                                     
                                                                                                                                  
        hwNHRPMIBCompliances OBJECT IDENTIFIER ::= { hwNHRPMIBConformance 1 }                                                       
                                                                                                                                  
                                                                                                                                  
--  this module                                                                                                                   
                                                                                                                                  
       hwNHRPMIBCompliance MODULE-COMPLIANCE                                                                                       
            STATUS current                                                                                                        
            DESCRIPTION                                                                                                           
                "The compliance statement for devices running NHRP."                                                               
            MODULE -- this module                                                                                                 
                MANDATORY-GROUPS { hwNHRPTrapObjectGroup}                                                                            
            ::= { hwNHRPMIBCompliances 1 }                                                                                         
                                                                                                                                  
        hwNHRPMIBGroups OBJECT IDENTIFIER ::= { hwNHRPMIBConformance 2 }                                                            
                                                                                                                                  
        hwNHRPNotificationGroup NOTIFICATION-GROUP                                                                                 
            NOTIFICATIONS { hwNHRPPeerADD, hwNHRPPeerDELETE, hwNHRPHubUP, hwNHRPHubDOWN, hwNHRPPeerThresholdExceedAlarm,  hwNHRPPeerThresholdExceedResume, 
            				hwNHRPDynPeerThresholdExceedAlarm, hwNHRPDynPeerThresholdExceedResume, hwNHRPLocalPeerLimitReachAlarm, hwNHRPLocalPeerLimitResume}                                                                       
            STATUS current                                                                                                        
            DESCRIPTION                                                                                                           
                "A collection of notifications generated by                                                                       
                devices supporting this MIB."                                                                                     
            ::= { hwNHRPMIBGroups 1 }                                                                                              
                                                                                                                                  
        hwNHRPTrapObjectGroup OBJECT-GROUP                                                                                            
            OBJECTS { hwNHRPInterface, hwNHRPProAddress, hwNHRPProMask, hwNHRPNextHop, hwNHRPNbmaAddress,                               
                        hwNHRPType, hwNHRPPeerDelReason, hwNHRPThrehold, hwNHRPPeerCnt, hwNHRPDynPeerThrehold, hwNHRPDynPeerCnt, hwNHRPLocalPeerLimit, hwNHRPLocalPeerCnt,hwNHRPHubDownReason}                                                                          
            STATUS current                                                                                                        
            DESCRIPTION                                                                                                           
                "A collection of NHRP trap objects required to support                                                             
                management of devices."                                                                                           
            ::= { hwNHRPMIBGroups 2 }                                                                                              
    
    END

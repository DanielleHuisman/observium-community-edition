--==================================================================
-- Copyright (C) 2018 by  HUAWEI TECHNOLOGIES. All rights reserved.
-- 
-- Description: HUAWEI SPATIAL MULTICAST MIB
-- Reference:
-- Version: V2.04
-- History:     
--          V1.0 2010-02-17, publish
-- ==================================================================
-- ==================================================================
-- 
-- Varibles and types be imported
--
-- ==================================================================
HUAWEI-SMC-MIB DEFINITIONS ::= BEGIN
IMPORTS
    
    IpAddress, OBJECT-IDENTITY,
    MODULE-IDENTITY, OBJECT-TYPE, Integer32,Unsigned32,Counter64
        FROM SNMPv2-SMI  
    
    hwDatacomm      
        FROM HUAWEI-MIB  
                 
    OBJECT-GROUP, MODULE-COMPLIANCE, NOTIFICATION-GROUP            
        FROM SNMPv2-CONF 
        
    InetAddressPrefixLength, InetAddress, InetAddressType
        FROM INET-ADDRESS-MIB
    RowStatus    
        FROM SNMPv2-TC;                       
        
    hwSpMulticastMib OBJECT IDENTIFIER ::= { hwDatacomm 248 }
    
    hwSmc MODULE-IDENTITY
        LAST-UPDATED "201806110000Z"        
    ORGANIZATION 
        "Huawei Technologies Co.,Ltd."
    CONTACT-INFO 
        "Huawei Industrial Base
  Bantian, Longgang
   Shenzhen 518129
   People's Republic of China
   Website: http://www.huawei.com
   Email: support@huawei.com
 "
    DESCRIPTION
            "The SMC MIB module is defined to manage the spatial multicast function of Huawei Technologies co.,Ltd."
            REVISION  "201806110000Z"
            DESCRIPTION "Add Unsigned32 instead of COUNTER64"
            REVISION  "201609141058Z"
            DESCRIPTION "add  hwSmcChannelNum at 2016-09-14"
            REVISION  "201608311058Z"
            DESCRIPTION "add  hwSmcChannelBandMIBTable at 2016-08-31"
            REVISION  "201502061058Z"
            DESCRIPTION "delete hwSmcRowStatus OBJECT-TYPE for it is invalid at 2015-02-06"
            ::= { hwSpMulticastMib 1 }
    
-- ==================================================================
--
-- ======================= definition begin =========================
--
-- ==================================================================
           
hwSmcObjects OBJECT IDENTIFIER ::= { hwSmc 1 }             

                                     
hwSmcEnableStatus OBJECT-TYPE
    SYNTAX Integer32 (0..1)
    MAX-ACCESS read-write
    STATUS current
    DESCRIPTION "The value of this object identifies the status of the spatial multicast function status."
    ::= { hwSmcObjects  1 }      

hwSmcL3mcBandMIBTable OBJECT-TYPE
    SYNTAX SEQUENCE OF HwSmcL3mcBandMIBEntry
    MAX-ACCESS not-accessible
    STATUS current
    DESCRIPTION "The table contains basic information about the Layer 3 spatial multicast band configuration."
    ::= { hwSmcObjects  2 }
    
hwSmcL3mcBandMIBEntry OBJECT-TYPE
    SYNTAX HwSmcL3mcBandMIBEntry
    MAX-ACCESS not-accessible
    STATUS current
    DESCRIPTION "This object indicates entries of the Layer 3 spatial multicast band table. "
    INDEX   { hwSmcL3mcAddressType, hwSmcL3mcGrpAddress,
              hwSmcL3mcGrpAddressPrefixLength, hwSmcL3mcSrcAddress }
    ::= { hwSmcL3mcBandMIBTable 1}

HwSmcL3mcBandMIBEntry ::=
    SEQUENCE {                               
        hwSmcL3mcAddressType             InetAddressType,
        hwSmcL3mcGrpAddress              InetAddress,
        hwSmcL3mcGrpAddressPrefixLength  InetAddressPrefixLength,
        hwSmcL3mcSrcAddress              InetAddress,
        hwSmcL3mcBandwidth               Integer32,
        hwSmcL3mcRowStatus               RowStatus
    } 
    
hwSmcL3mcAddressType OBJECT-TYPE
    SYNTAX InetAddressType
    MAX-ACCESS not-accessible
    STATUS current
    DESCRIPTION "This object indicates the type of group and source IP for the Layer 3 spatial multicast band command."
    ::= { hwSmcL3mcBandMIBEntry 1 }

hwSmcL3mcGrpAddress OBJECT-TYPE
    SYNTAX InetAddress (SIZE (4|8|16|20))
    MAX-ACCESS not-accessible
    STATUS current
    DESCRIPTION "This object indicates the parameter of group IP for the Layer 3 spatial multicast band command."
    ::= { hwSmcL3mcBandMIBEntry 2 }

hwSmcL3mcGrpAddressPrefixLength OBJECT-TYPE
    SYNTAX InetAddressPrefixLength (4..128)
    MAX-ACCESS not-accessible
    STATUS current
    DESCRIPTION "The value of this object identifies the parameter of group IP mask for the Layer 3 spatial multicast band command. "
    ::= { hwSmcL3mcBandMIBEntry 3 }

hwSmcL3mcSrcAddress OBJECT-TYPE
    SYNTAX InetAddress (SIZE (4|8|16|20))
    MAX-ACCESS not-accessible
    STATUS current
    DESCRIPTION "This object indicates the parameter of source IP for the Layer 3 spatial multicast band command. "
    ::= { hwSmcL3mcBandMIBEntry 4 }

hwSmcL3mcBandwidth OBJECT-TYPE
    SYNTAX Integer32
    MAX-ACCESS read-write
    STATUS current
    DESCRIPTION "The value of this object identifies the parameter of current bandwdith for the Layer 3 spatial multicast band command. "
    ::= { hwSmcL3mcBandMIBEntry 5 }

hwSmcL3mcRowStatus OBJECT-TYPE
    SYNTAX RowStatus
    MAX-ACCESS read-create     
    STATUS current
    DESCRIPTION "This object indicates the row status of this table for creating and removing entries."
    ::= { hwSmcL3mcBandMIBEntry 6 }
                                                            
hwSmcL3mcVpnBandMIBTable OBJECT-TYPE
    SYNTAX SEQUENCE OF HwSmcL3mcVpnBandMIBEntry
    MAX-ACCESS not-accessible
    STATUS current
    DESCRIPTION "The table contains basic information about the Layer 3 VPN spatial multicast band configuration."
    ::= { hwSmcObjects  3 }
    
hwSmcL3mcVpnBandMIBEntry OBJECT-TYPE
    SYNTAX HwSmcL3mcVpnBandMIBEntry
    MAX-ACCESS not-accessible
    STATUS current
    DESCRIPTION "This object indicates entries of the Layer 3 spatial multicast band table. "
    INDEX   { hwSmcL3mcVpnVrfName, hwSmcL3mcVpnAddressType, hwSmcL3mcVpnGrpAddress,
              hwSmcL3mcVpnGrpAddressPrefixLength, hwSmcL3mcVpnSrcAddress }
    ::= { hwSmcL3mcVpnBandMIBTable 1}

HwSmcL3mcVpnBandMIBEntry ::=
    SEQUENCE {                               
        hwSmcL3mcVpnVrfName                 OCTET STRING,
        hwSmcL3mcVpnAddressType             InetAddressType,
        hwSmcL3mcVpnGrpAddress              InetAddress,
        hwSmcL3mcVpnGrpAddressPrefixLength  InetAddressPrefixLength,
        hwSmcL3mcVpnSrcAddress              InetAddress,
        hwSmcL3mcVpnBandwidth               Integer32,
        hwSmcL3mcVpnRowStatus               RowStatus
    } 
    
hwSmcL3mcVpnVrfName OBJECT-TYPE
    SYNTAX OCTET STRING (SIZE (1..31))
    MAX-ACCESS not-accessible
    STATUS current
    DESCRIPTION "This object indicates the parameter of VPN name for the Layer 3 spatial multicast band command."
    ::= { hwSmcL3mcVpnBandMIBEntry 1 }

hwSmcL3mcVpnAddressType OBJECT-TYPE
    SYNTAX InetAddressType
    MAX-ACCESS not-accessible
    STATUS current
    DESCRIPTION "This object indicates the type of group and source IP for the Layer 3 spatial multicast band command."
    ::= { hwSmcL3mcVpnBandMIBEntry 2 }

hwSmcL3mcVpnGrpAddress OBJECT-TYPE
    SYNTAX InetAddress (SIZE (4|8|16|20))
    MAX-ACCESS not-accessible
    STATUS current
    DESCRIPTION "This object indicates the parameter of group IP for the Layer 3 spatial multicast band command."
    ::= { hwSmcL3mcVpnBandMIBEntry 3 }

hwSmcL3mcVpnGrpAddressPrefixLength OBJECT-TYPE
    SYNTAX InetAddressPrefixLength (4..128)
    MAX-ACCESS not-accessible
    STATUS current
    DESCRIPTION "The value of this object identifies the parameter of group IP mask for the Layer 3 spatial multicast band command. "
    ::= { hwSmcL3mcVpnBandMIBEntry 4 }

hwSmcL3mcVpnSrcAddress OBJECT-TYPE
    SYNTAX InetAddress (SIZE (4|8|16|20))
    MAX-ACCESS not-accessible
    STATUS current
    DESCRIPTION "This object indicates the parameter of source IP for the Layer 3 spatial multicast band command. "
    ::= { hwSmcL3mcVpnBandMIBEntry 5 }

hwSmcL3mcVpnBandwidth OBJECT-TYPE
    SYNTAX Integer32
    MAX-ACCESS read-write
    STATUS current
    DESCRIPTION "The value of this object identifies the parameter of current bandwdith for the Layer 3 spatial multicast band command. "
    ::= { hwSmcL3mcVpnBandMIBEntry 6 }

hwSmcL3mcVpnRowStatus OBJECT-TYPE
    SYNTAX RowStatus
    MAX-ACCESS read-create     
    STATUS current
    DESCRIPTION "This object indicates the row status of this table for creating and removing entries."
    ::= { hwSmcL3mcVpnBandMIBEntry 7 }
            
hwSmcL2mcVlanBandMIBTable OBJECT-TYPE
    SYNTAX SEQUENCE OF HwSmcL2mcVlanBandMIBEntry
    MAX-ACCESS not-accessible
    STATUS current
    DESCRIPTION "The table contains basic information about the Layer 2 VLAN spatial multicast band configuration."
    ::= { hwSmcObjects  4 }              
    
hwSmcL2mcVlanBandMIBEntry OBJECT-TYPE
    SYNTAX HwSmcL2mcVlanBandMIBEntry
    MAX-ACCESS not-accessible
    STATUS current
    DESCRIPTION "This object indicates the entries of the Layer 2 VLAN spatial multicast band table. "
    INDEX   { hwSmcL2mcVlanId, hwSmcL2mcVlanAddressType, hwSmcL2mcVlanBroadcast,
              hwSmcL2mcVlanGrpAddress, hwSmcL2mcVlanGrpAddressPrefixLength,
              hwSmcL2mcVlanSrcAddress }
    ::= { hwSmcL2mcVlanBandMIBTable 1 }

HwSmcL2mcVlanBandMIBEntry ::=
    SEQUENCE {        
        hwSmcL2mcVlanId                      Integer32, 
        hwSmcL2mcVlanBroadcast               Integer32,
        hwSmcL2mcVlanAddressType             InetAddressType,
        hwSmcL2mcVlanGrpAddress              InetAddress,
        hwSmcL2mcVlanGrpAddressPrefixLength  InetAddressPrefixLength,
        hwSmcL2mcVlanSrcAddress              InetAddress,
        hwSmcL2mcVlanBandwidth               Integer32,
        hwSmcL2mcVlanRowStatus               RowStatus
    }                              
    
hwSmcL2mcVlanId OBJECT-TYPE
    SYNTAX Integer32 (1..4094)
    MAX-ACCESS not-accessible
    STATUS current
    DESCRIPTION "The value of this object identifies the parameter of VLAN ID for the Layer 2 VLAN spatial multicast command."
    ::= { hwSmcL2mcVlanBandMIBEntry 1 }  

hwSmcL2mcVlanBroadcast OBJECT-TYPE
    SYNTAX Integer32 (0..1)
    MAX-ACCESS not-accessible
    STATUS current
    DESCRIPTION "This object indicates the type of the Layer 2 VLAN spatial multicast band command.
                 0 - Multicast
                 1 - Broadcast."
    ::= { hwSmcL2mcVlanBandMIBEntry 2 }
    
hwSmcL2mcVlanAddressType OBJECT-TYPE
    SYNTAX InetAddressType
    MAX-ACCESS not-accessible
    STATUS current
    DESCRIPTION "This object indicates the type of group and source IP for the Layer 2 VLAN spatial multicast band command."
    ::= { hwSmcL2mcVlanBandMIBEntry 3 }

hwSmcL2mcVlanGrpAddress OBJECT-TYPE
    SYNTAX InetAddress (SIZE (4|8|16|20))
    MAX-ACCESS not-accessible
    STATUS current
    DESCRIPTION "This object indicates the parameter of group IP for the Layer 2 VLAN spatial multicast command."
    ::= { hwSmcL2mcVlanBandMIBEntry 4 }

hwSmcL2mcVlanGrpAddressPrefixLength OBJECT-TYPE
    SYNTAX InetAddressPrefixLength (4..128)
    MAX-ACCESS not-accessible
    STATUS current
    DESCRIPTION "The value of this object identifies the pamameter of group IP mask for the Layer 2 VLAN spatial multicast command."
    ::= { hwSmcL2mcVlanBandMIBEntry 5 }

hwSmcL2mcVlanSrcAddress OBJECT-TYPE
    SYNTAX InetAddress (SIZE (4|8|16|20))
    MAX-ACCESS not-accessible
    STATUS current
    DESCRIPTION "This object indicates the parameter of source IP for the Layer 2 VLAN spatial multicast command."
    ::= { hwSmcL2mcVlanBandMIBEntry 6 }

hwSmcL2mcVlanBandwidth OBJECT-TYPE
    SYNTAX Integer32
    MAX-ACCESS read-write
    STATUS current
    DESCRIPTION "The value of this object identifies the parameter of current bandwidth for a Layer 2 VLAN spatial multicast band command."
    ::= { hwSmcL2mcVlanBandMIBEntry 7 }   

hwSmcL2mcVlanRowStatus OBJECT-TYPE
    SYNTAX RowStatus
    MAX-ACCESS read-create
    STATUS current
    DESCRIPTION "This object indicates the row status of this table for creating and removing entries."
    ::= { hwSmcL2mcVlanBandMIBEntry 8 }

hwSmcL2mcVsiBandMIBTable OBJECT-TYPE
    SYNTAX SEQUENCE OF HwSmcL2mcVsiBandMIBEntry
    MAX-ACCESS not-accessible
    STATUS current
    DESCRIPTION "The table contains basic information about the Layer 2 Vsi spatial multicast band configuration."
    ::= { hwSmcObjects  5 }              
    
hwSmcL2mcVsiBandMIBEntry OBJECT-TYPE
    SYNTAX HwSmcL2mcVsiBandMIBEntry
    MAX-ACCESS not-accessible
    STATUS current
    DESCRIPTION "This object indicates the entries of the Layer 2 spatial multicast band table. "
    INDEX   { hwSmcL2mcVsiName, hwSmcL2mcVsiBroadcast, hwSmcL2mcVsiAddressType,
              hwSmcL2mcVsiGrpAddress, hwSmcL2mcVsiGrpAddressPrefixLength,
              hwSmcL2mcVsiSrcAddress }
    ::= { hwSmcL2mcVsiBandMIBTable 1 }

HwSmcL2mcVsiBandMIBEntry ::=
    SEQUENCE {        
        hwSmcL2mcVsiName                    OCTET STRING,
        hwSmcL2mcVsiBroadcast               Integer32, 
        hwSmcL2mcVsiAddressType             InetAddressType,
        hwSmcL2mcVsiGrpAddress              InetAddress,
        hwSmcL2mcVsiGrpAddressPrefixLength  InetAddressPrefixLength,
        hwSmcL2mcVsiSrcAddress              InetAddress,
        hwSmcL2mcVsiBandwidth               Integer32,
        hwSmcL2mcVsiRowStatus               RowStatus
    }                              
    
hwSmcL2mcVsiName OBJECT-TYPE
    SYNTAX OCTET STRING (SIZE(1..31))
    MAX-ACCESS not-accessible
    STATUS current
    DESCRIPTION "This object indicates the parameter of VSI name for the Layer 2 VSI spatial multicast command."
    ::= { hwSmcL2mcVsiBandMIBEntry 1 }

hwSmcL2mcVsiBroadcast OBJECT-TYPE
    SYNTAX Integer32 (0..1)
    MAX-ACCESS not-accessible
    STATUS current
    DESCRIPTION "This object indicates the type of the Layer 2 VSI spatial multicast band command.
                 0 - Multicast
                 1 - Broadcast."
    ::= { hwSmcL2mcVsiBandMIBEntry 2 }

hwSmcL2mcVsiAddressType OBJECT-TYPE
    SYNTAX InetAddressType
    MAX-ACCESS not-accessible
    STATUS current
    DESCRIPTION "This object indicates the type of group and source IP for the Layer 2 VSI spatial multicast band command."
    ::= { hwSmcL2mcVsiBandMIBEntry 3 }

hwSmcL2mcVsiGrpAddress OBJECT-TYPE
    SYNTAX InetAddress (SIZE (4|8|16|20))
    MAX-ACCESS not-accessible
    STATUS current
    DESCRIPTION "This object indicates the parameter of group IP for the Layer 2 VSI spatial multicast command."
    ::= { hwSmcL2mcVsiBandMIBEntry 4 }

hwSmcL2mcVsiGrpAddressPrefixLength OBJECT-TYPE
    SYNTAX InetAddressPrefixLength (4..128)
    MAX-ACCESS not-accessible
    STATUS current
    DESCRIPTION "The value of this object identifies the pamameter of group IP mask for the Layer 2 VSI spatial multicast command."
    ::= { hwSmcL2mcVsiBandMIBEntry 5 }

hwSmcL2mcVsiSrcAddress OBJECT-TYPE
    SYNTAX InetAddress (SIZE (4|8|16|20))
    MAX-ACCESS not-accessible
    STATUS current
    DESCRIPTION "This object indicates the parameter of source IP for the Layer 2 VSI spatial multicast command."
    ::= { hwSmcL2mcVsiBandMIBEntry 6 }

hwSmcL2mcVsiBandwidth OBJECT-TYPE
    SYNTAX Integer32
    MAX-ACCESS read-write
    STATUS current
    DESCRIPTION "The value of this object identifies the parameter of current bandwidth for a Layer 2 VSI spatial multicast band command."
    ::= { hwSmcL2mcVsiBandMIBEntry 7 }   

hwSmcL2mcVsiRowStatus OBJECT-TYPE
    SYNTAX RowStatus
    MAX-ACCESS read-create
    STATUS current
    DESCRIPTION "This object indicates the row status of this table for creating and removing entries."
    ::= { hwSmcL2mcVsiBandMIBEntry 8 }
       
hwSmcSlotMIBTable OBJECT-TYPE
    SYNTAX SEQUENCE OF HwSmcSlotMIBEntry
    MAX-ACCESS not-accessible
    STATUS current
    DESCRIPTION "The table contains the slot numbers that need to be enabled."
    ::= { hwSmcObjects  6 }    

hwSmcSlotMIBEntry OBJECT-TYPE
    SYNTAX HwSmcSlotMIBEntry
    MAX-ACCESS not-accessible
    STATUS current
    DESCRIPTION "This object indicates the entries of the Layer 2 spatial multicast band table."
    INDEX   { hwSmcSlot }
    ::= { hwSmcSlotMIBTable 1 }

HwSmcSlotMIBEntry ::=
    SEQUENCE {                
        hwSmcSlot          Integer32,
        hwSmcSlotRowStatus RowStatus
       }


hwSmcSlot OBJECT-TYPE
    SYNTAX Integer32 (1..256)
    MAX-ACCESS not-accessible
    STATUS current
    DESCRIPTION "The value of this parameters identifies the slot paramter for the spatial multicast slot enable command."
    ::= { hwSmcSlotMIBEntry 1 }

hwSmcSlotRowStatus OBJECT-TYPE
    SYNTAX RowStatus
    MAX-ACCESS read-create
    STATUS current
    DESCRIPTION "This object indicates the row status of this table for creating and removing entries.
                 The index specified when create an entry must be an available interface slot number."
    ::= { hwSmcSlotMIBEntry 2 }

hwL2mcCompatibleModeMIBTable OBJECT-TYPE
    SYNTAX SEQUENCE OF HwL2mcCompatibleModeMIBEntry
    MAX-ACCESS not-accessible
    STATUS current
    DESCRIPTION "The table contains the Layer 2 multicast compatible mode configuration. "
    ::= { hwSmcObjects  7 }              
    
hwL2mcCompatibleModeMIBEntry OBJECT-TYPE
    SYNTAX HwL2mcCompatibleModeMIBEntry
    MAX-ACCESS not-accessible
    STATUS current
    DESCRIPTION "This object indicates entries in the Layer 2 multicast compatible mode table. "
    INDEX   { hwL2mcVlanId, hwL2mcVsiName }
    ::= { hwL2mcCompatibleModeMIBTable 1 }

HwL2mcCompatibleModeMIBEntry ::=
    SEQUENCE {                
        hwL2mcVlanId           Integer32,
        hwL2mcVsiName          OCTET STRING,
        hwL2mcCompatibleMode   Integer32
    }

hwL2mcVlanId OBJECT-TYPE
    SYNTAX Integer32 (1..4095)
    MAX-ACCESS not-accessible
    STATUS current
    DESCRIPTION "The value of this object identifies a VLAN ID, the configuration index in a VLAN.
                 If a VSI is specified, the value is 4095. "
    ::= { hwL2mcCompatibleModeMIBEntry 1 }
    
hwL2mcVsiName OBJECT-TYPE
    SYNTAX OCTET STRING (SIZE(1..31))
    MAX-ACCESS not-accessible
    STATUS current
    DESCRIPTION "This object indicates the name of a VSI.
                 If a VLAN is specified, the value is 32. "
    ::= { hwL2mcCompatibleModeMIBEntry 2 }
    
hwL2mcCompatibleMode OBJECT-TYPE
    SYNTAX Integer32 (0..1)
    MAX-ACCESS read-write
    STATUS current
    DESCRIPTION "This object indicates that this VSI or VLAN is in compatible mode. "
    ::= { hwL2mcCompatibleModeMIBEntry 3 } 

hwSmcChannelBandMIBTable OBJECT-TYPE
    SYNTAX SEQUENCE OF HwSmcChannelBandMIBEntry
    MAX-ACCESS not-accessible
    STATUS current
    DESCRIPTION "The table contains the band of spatial multicast channel. "
    ::= { hwSmcObjects  8 }              
    
hwSmcChannelBandMIBEntry OBJECT-TYPE
    SYNTAX HwSmcChannelBandMIBEntry
    MAX-ACCESS not-accessible
    STATUS current
    DESCRIPTION "The table contains the band of spatial multicast channel. "
    INDEX   { hwSmcChannelBandChannelID }
    ::= { hwSmcChannelBandMIBTable 1 }

HwSmcChannelBandMIBEntry ::=
    SEQUENCE {                
        hwSmcChannelBandChannelID     Integer32,
        hwSmcChannelBandUsed          Counter64,
        hwSmcChannelBandNotUsed       Counter64
    }

hwSmcChannelBandChannelID OBJECT-TYPE
    SYNTAX Integer32 (0..1000)
    MAX-ACCESS read-only
    STATUS current
    DESCRIPTION "The index of spatial multicast channel ID. "
    ::= { hwSmcChannelBandMIBEntry 1 }
    
hwSmcChannelBandUsed OBJECT-TYPE
    SYNTAX Counter64
    MAX-ACCESS read-only
    STATUS current
    DESCRIPTION "This object indicates the used band of a specified spatial multicast channel. "
    ::= { hwSmcChannelBandMIBEntry 2 }
    
hwSmcChannelBandNotUsed OBJECT-TYPE
    SYNTAX Counter64
    MAX-ACCESS read-only
    STATUS current
    DESCRIPTION "This object indicates the residual band of a specified spatial multicast channel. "
    ::= { hwSmcChannelBandMIBEntry 3 }  

hwSmcChannelNum OBJECT-TYPE
    SYNTAX Integer32 (0..1000)
    MAX-ACCESS read-only
    STATUS current
    DESCRIPTION "This object indicates the total channel numbers of spatial multicast."
    ::= { hwSmcObjects  9 }   
hwSmcChannelBandMIBExtTable OBJECT-TYPE
    SYNTAX SEQUENCE OF HwSmcChannelBandMIBExtEntry
    MAX-ACCESS not-accessible
    STATUS current
    DESCRIPTION "The table contains the band of spatial multicast channel. "
    ::= { hwSmcObjects  10 }
hwSmcChannelBandMIBExtEntry OBJECT-TYPE
    SYNTAX HwSmcChannelBandMIBExtEntry
    MAX-ACCESS not-accessible
    STATUS current
    DESCRIPTION "The table contains the band of spatial multicast channel. "
    INDEX   { hwSmcChannelBandChannelIDExt }
    ::= { hwSmcChannelBandMIBExtTable 1 }
HwSmcChannelBandMIBExtEntry ::=
    SEQUENCE {                
        hwSmcChannelBandChannelIDExt     Integer32,
        hwSmcChannelBandUsedHighExt          Unsigned32,
        hwSmcChannelBandUsedLowExt          Unsigned32,
        hwSmcChannelBandNotUsedHighExt       Unsigned32,
        hwSmcChannelBandNotUsedLowExt       Unsigned32
    }
hwSmcChannelBandChannelIDExt OBJECT-TYPE
    SYNTAX Integer32 (0..1000)
    MAX-ACCESS read-only
    STATUS current
    DESCRIPTION "The index of spatial multicast channel ID. "
    ::= { hwSmcChannelBandMIBExtEntry 1 }
hwSmcChannelBandUsedHighExt OBJECT-TYPE
    SYNTAX Unsigned32
    MAX-ACCESS read-only
    STATUS current
    DESCRIPTION "This object indicates the used band of a specified spatial multicast channel. "
    ::= { hwSmcChannelBandMIBExtEntry 2 }
hwSmcChannelBandUsedLowExt OBJECT-TYPE
    SYNTAX Unsigned32
    MAX-ACCESS read-only
    STATUS current
    DESCRIPTION "This object indicates the used band of a specified spatial multicast channel. "
    ::= { hwSmcChannelBandMIBExtEntry 3 }
hwSmcChannelBandNotUsedHighExt OBJECT-TYPE
    SYNTAX Unsigned32
    MAX-ACCESS read-only
    STATUS current
    DESCRIPTION "This object indicates the residual band of a specified spatial multicast channel. "
    ::= { hwSmcChannelBandMIBExtEntry 4 }
hwSmcChannelBandNotUsedLowExt OBJECT-TYPE
    SYNTAX Unsigned32
    MAX-ACCESS read-only
    STATUS current
    DESCRIPTION "This object indicates the residual band of a specified spatial multicast channel. "
    ::= { hwSmcChannelBandMIBExtEntry 5 }      
hwSmcConformance OBJECT IDENTIFIER ::= { hwSmc 2 }

hwSmcCompliances OBJECT IDENTIFIER ::= { hwSmcConformance 1 }

hwSmcFullCompliance MODULE-COMPLIANCE
    STATUS current
    DESCRIPTION "This object indicates the compliance statement for systems supporting 
                  the HUAWEI-SMC-MIB."
    MODULE MANDATORY-GROUPS {hwSmcEnableGroup, hwSmcL3mcBandGroup, hwSmcL3mcVpnBandGroup,
        hwSmcL2mcVlanBandGroup, hwSmcL2mcVsiBandGroup, hwL2mcCompatibleModeGroup, hwSmcChannelBandGroup, hwSmcChannelNumGroup}
    ::= { hwSmcCompliances 1 }

hwSmcGroups OBJECT IDENTIFIER ::= { hwSmcConformance 2 }

hwSmcEnableGroup OBJECT-GROUP
    OBJECTS {
        hwSmcEnableStatus
    }
    STATUS current
    DESCRIPTION "This object group indicates whether the spatial multicast function is enabled."
    ::= { hwSmcGroups 1 }

hwSmcL3mcBandGroup OBJECT-GROUP
    OBJECTS {
        hwSmcL3mcBandwidth, hwSmcL3mcRowStatus 
    }
    STATUS current
    DESCRIPTION "This object group indicates the parameters for the Layer 3 spatial multicast band command."
    ::= { hwSmcGroups 2 }
    
hwSmcL3mcVpnBandGroup OBJECT-GROUP
    OBJECTS {
        hwSmcL3mcVpnBandwidth, hwSmcL3mcVpnRowStatus 
    }
    STATUS current
    DESCRIPTION "This object group indicates the parameters for the Layer 3 VPN spatial multicast band command."
    ::= { hwSmcGroups 3 }

hwSmcL2mcVlanBandGroup OBJECT-GROUP
    OBJECTS {
        hwSmcL2mcVlanBandwidth, hwSmcL2mcVlanRowStatus
    }
    STATUS current
    DESCRIPTION "This object group indicates the parameters for the Layer 2 spatial VLAN multicast band command."
    ::= { hwSmcGroups 4 }

hwSmcL2mcVsiBandGroup OBJECT-GROUP
    OBJECTS {
        hwSmcL2mcVsiBandwidth, hwSmcL2mcVsiRowStatus
    }
    STATUS current
    DESCRIPTION "This object group indicates the parameters for the Layer 2 spatial VSI multicast band command."
    ::= { hwSmcGroups 5 }

hwL2mcCompatibleModeGroup OBJECT-GROUP
    OBJECTS {
        hwL2mcCompatibleMode
    }
    STATUS current
    DESCRIPTION "This object indicates the VSI or VLAN in compatible mode."
    ::= { hwSmcGroups 6 }

hwSmcChannelBandGroup OBJECT-GROUP
    OBJECTS {
        hwSmcChannelBandChannelID, hwSmcChannelBandUsed, hwSmcChannelBandNotUsed
    }
    STATUS current
    DESCRIPTION "This object indicates the band of spatial multicast channel."
    ::= { hwSmcGroups 7 }
     
hwSmcChannelNumGroup  OBJECT-GROUP
   OBJECTS {
        hwSmcChannelNum
   }
   STATUS current
   DESCRIPTION "This object indicates the number of spatial multicast channel."
   ::= { hwSmcGroups 8 }
hwSmcChannelBandGroupExt OBJECT-GROUP
    OBJECTS {
        hwSmcChannelBandChannelIDExt, hwSmcChannelBandUsedHighExt,hwSmcChannelBandUsedLowExt, hwSmcChannelBandNotUsedHighExt, hwSmcChannelBandNotUsedLowExt
    }
    STATUS current
    DESCRIPTION "This object indicates the band of spatial multicast channel."
    ::= { hwSmcGroups 9 }
     
END

--
-- HUAWEI-STORAGE-SPACE-MIB.mib
-- MIB generated by MG-SOFT Visual MIB Builder Version 3.0 Build 253
-- Wednesday, May 25, 2016 at 11:41:14
--

--  HUAWEI-STORAGE-SPACE-MIB.mib
-- MIB generated by MG-SOFT Visual MIB Builder Version 3.0 Build 253
-- Tuesday, May 24, 2016 at 19:20:59
-- 
--  HUAWEI-STORAGE-SPACE-MIB.mib
-- MIB generated by MG-SOFT Visual MIB Builder Version 3.0 Build 253
-- Tuesday, April 05, 2016 at 11:03:12
-- 
--  HUAWEI-STORAGE-SPACE-MIB.mib
-- MIB generated by MG-SOFT Visual MIB Builder Version 3.0 Build 253
-- Friday, March 18, 2016 at 19:31:56
-- 
--  HUAWEI-STORAGE-SPACE-MIB.mib
-- MIB generated by MG-SOFT Visual MIB Builder Version 3.0 Build 253
-- Friday, March 11, 2016 at 15:20:03
-- 
--  HUAWEI-STORAGE-SPACE-MIB.mib
-- MIB generated by MG-SOFT Visual MIB Builder Version 3.0 Build 253
-- Tuesday, February 23, 2016 at 15:43:58
-- 
--  HUAWEI-STORAGE-SPACE-MIB.mib
-- MIB generated by MG-SOFT Visual MIB Builder Version 4.0 Build 347
-- Wednesday, October 15, 2014 at 11:21:02
-- 

	HUAWEI-STORAGE-SPACE-MIB DEFINITIONS ::= BEGIN
 
		IMPORTS
			OBJECT-GROUP, MODULE-COMPLIANCE			
				FROM SNMPv2-CONF			
			enterprises, Unsigned32, Counter64, OBJECT-TYPE, 
			MODULE-IDENTITY			
				FROM SNMPv2-SMI			
			TEXTUAL-CONVENTION			
				FROM SNMPv2-TC;
	
	
		hwStorage MODULE-IDENTITY 
			LAST-UPDATED "201603181930Z"		-- March 18, 2016 at 19:30 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"Description."
			REVISION "201304061354Z"		-- April 06, 2013 at 13:54 GMT
			DESCRIPTION
				" "
			::= { huaweistorage 4 }
		
	
--
-- Textual conventions
--
	
--  March 18, 2016 at 19:30 GMT
-- April 06, 2013 at 13:54 GMT
-- 
-- Textual conventions
-- 
--  March 18, 2016 at 19:30 GMT
-- April 06, 2013 at 13:54 GMT
-- 
-- Textual conventions
-- 
--  March 18, 2016 at 19:30 GMT
-- April 06, 2013 at 13:54 GMT
-- 
-- Textual conventions
-- 
--  August 11, 2010 at 12:39 GMT
-- April 06, 2013 at 13:54 GMT
-- 
-- Textual conventions
-- 
--  August 11, 2010 at 12:39 GMT
-- April 06, 2013 at 13:54 GMT
-- 
-- Textual conventions
-- 
--  August 11, 2010 at 12:39 GMT
-- April 06, 2013 at 13:54 GMT
-- 
-- Textual conventions
-- 
--  August 11, 2010 at 12:39 GMT
-- April 06, 2013 at 13:54 GMT
-- 
-- Textual conventions
-- 
		NodeCodeString ::= TEXTUAL-CONVENTION
			DISPLAY-HINT 
				"255a"
			STATUS current
			DESCRIPTION 
				"characters in length."
			SYNTAX OCTET STRING (SIZE (15..17))
			
	
--
-- Node definitions
--
	
--  Node definitions
-- 
-- Node definitions
-- 
-- Node definitions
-- 
-- Node definitions
-- 
-- Node definitions
-- 
-- Node definitions
-- 
-- Node definitions
-- 
-- 1.3.6.1.4.1.34774
-- 1.3.6.1.4.1.34774
-- 1.3.6.1.4.1.34774
-- 1.3.6.1.4.1.34774
-- 1.3.6.1.4.1.34774
		-- 1.3.6.1.4.1.34774
		huaweistorage OBJECT IDENTIFIER ::= { enterprises 34774 }
		
--      1.3.6.1.4.1.34774.4.1
-- 1.3.6.1.4.1.34774.4.1
-- 1.3.6.1.4.1.34774.4.1
-- 1.3.6.1.4.1.34774.4.1
-- 1.3.6.1.4.1.34774.4.1
		-- 1.3.6.1.4.1.34774.4.1
		hwISM OBJECT IDENTIFIER ::= { hwStorage 1 }
		
--      1.3.6.1.4.1.34774.4.1.23
-- 1.3.6.1.4.1.34774.4.1.23
-- 1.3.6.1.4.1.34774.4.1.23
-- 1.3.6.1.4.1.34774.4.1.23
-- 1.3.6.1.4.1.34774.4.1.23
		-- 1.3.6.1.4.1.34774.4.1.23
		hwStorageDevice OBJECT IDENTIFIER ::= { hwISM 23 }
		
--      1.3.6.1.4.1.34774.4.1.23.4
-- 1.3.6.1.4.1.34774.4.1.23.4
-- 1.3.6.1.4.1.34774.4.1.23.4
-- 1.3.6.1.4.1.34774.4.1.23.4
-- 1.3.6.1.4.1.34774.4.1.23.4
		-- 1.3.6.1.4.1.34774.4.1.23.4
		hwSpaceInfo OBJECT IDENTIFIER ::= { hwStorageDevice 4 }
		
--      1.3.6.1.4.1.34774.4.1.23.4.1
-- 1.3.6.1.4.1.34774.4.1.23.4.1
-- 1.3.6.1.4.1.34774.4.1.23.4.1
-- 1.3.6.1.4.1.34774.4.1.23.4.1
-- 1.3.6.1.4.1.34774.4.1.23.4.1
		-- 1.3.6.1.4.1.34774.4.1.23.4.1
		hwInfoDiskDomainTable OBJECT-TYPE
			SYNTAX SEQUENCE OF HwInfoDiskDomainEntry
			MAX-ACCESS not-accessible
			STATUS current
			DESCRIPTION
				" "
			::= { hwSpaceInfo 1 }
		
--      1.3.6.1.4.1.34774.4.1.23.4.1.1
-- 1.3.6.1.4.1.34774.4.1.23.4.1.1
-- 1.3.6.1.4.1.34774.4.1.23.4.1.1
-- 1.3.6.1.4.1.34774.4.1.23.4.1.1
-- 1.3.6.1.4.1.34774.4.1.23.4.1.1
		-- 1.3.6.1.4.1.34774.4.1.23.4.1.1
		hwInfoDiskDomainEntry OBJECT-TYPE
			SYNTAX HwInfoDiskDomainEntry
			MAX-ACCESS not-accessible
			STATUS current
			DESCRIPTION
				"  "
			INDEX { hwInfoDiskDomainID }
			::= { hwInfoDiskDomainTable 1 }
		
		HwInfoDiskDomainEntry ::=
			SEQUENCE { 
				hwInfoDiskDomainID
					OCTET STRING,
				hwInfoDiskDomainName
					OCTET STRING,
				hwInfoDiskDomainHealthStatus
					Unsigned32,
				hwInfoDiskDomainRunningStatus
					Unsigned32,
				hwInfoDiskDomainTotalCapacity
					Counter64,
				hwInfoDiskDomainFreeCapacity
					Counter64,
				hwInfoDiskDomainHotSpareCapacity
					Counter64,
				hwInfoDiskDomainUsedHotSpareCapacity
					Counter64
			 }

--      1.3.6.1.4.1.34774.4.1.23.4.1.1.1
-- 1.3.6.1.4.1.34774.4.1.23.4.1.1.1
-- 1.3.6.1.4.1.34774.4.1.23.4.1.1.1
-- 1.3.6.1.4.1.34774.4.1.23.4.1.1.1
-- 1.3.6.1.4.1.34774.4.1.23.4.1.1.1
		-- 1.3.6.1.4.1.34774.4.1.23.4.1.1.1
		hwInfoDiskDomainID OBJECT-TYPE
			SYNTAX OCTET STRING
			MAX-ACCESS read-only
			STATUS current
			DESCRIPTION
				"  "
			::= { hwInfoDiskDomainEntry 1 }
		
--      1.3.6.1.4.1.34774.4.1.23.4.1.1.2
-- 1.3.6.1.4.1.34774.4.1.23.4.1.1.2
-- 1.3.6.1.4.1.34774.4.1.23.4.1.1.2
-- 1.3.6.1.4.1.34774.4.1.23.4.1.1.2
-- 1.3.6.1.4.1.34774.4.1.23.4.1.1.2
		-- 1.3.6.1.4.1.34774.4.1.23.4.1.1.2
		hwInfoDiskDomainName OBJECT-TYPE
			SYNTAX OCTET STRING
			MAX-ACCESS read-only
			STATUS current
			DESCRIPTION
				"  "
			::= { hwInfoDiskDomainEntry 2 }
		
--      1.3.6.1.4.1.34774.4.1.23.4.1.1.3
-- 1.3.6.1.4.1.34774.4.1.23.4.1.1.3
-- 1.3.6.1.4.1.34774.4.1.23.4.1.1.3
-- 1.3.6.1.4.1.34774.4.1.23.4.1.1.3
-- 1.3.6.1.4.1.34774.4.1.23.4.1.1.3
		-- 1.3.6.1.4.1.34774.4.1.23.4.1.1.3
		hwInfoDiskDomainHealthStatus OBJECT-TYPE
			SYNTAX Unsigned32
			MAX-ACCESS read-only
			STATUS current
			DESCRIPTION
				"  "
			::= { hwInfoDiskDomainEntry 3 }
		
--      1.3.6.1.4.1.34774.4.1.23.4.1.1.4
-- 1.3.6.1.4.1.34774.4.1.23.4.1.1.4
-- 1.3.6.1.4.1.34774.4.1.23.4.1.1.4
-- 1.3.6.1.4.1.34774.4.1.23.4.1.1.4
-- 1.3.6.1.4.1.34774.4.1.23.4.1.1.4
		-- 1.3.6.1.4.1.34774.4.1.23.4.1.1.4
		hwInfoDiskDomainRunningStatus OBJECT-TYPE
			SYNTAX Unsigned32
			MAX-ACCESS read-only
			STATUS current
			DESCRIPTION
				"  "
			::= { hwInfoDiskDomainEntry 4 }
		
--      1.3.6.1.4.1.34774.4.1.23.4.1.1.5
-- 1.3.6.1.4.1.34774.4.1.23.4.1.1.5
-- 1.3.6.1.4.1.34774.4.1.23.4.1.1.5
-- 1.3.6.1.4.1.34774.4.1.23.4.1.1.5
-- 1.3.6.1.4.1.34774.4.1.23.4.1.1.5
		-- 1.3.6.1.4.1.34774.4.1.23.4.1.1.5
		hwInfoDiskDomainTotalCapacity OBJECT-TYPE
			SYNTAX Counter64
			MAX-ACCESS read-only
			STATUS current
			DESCRIPTION
				"  "
			::= { hwInfoDiskDomainEntry 5 }
		
--      1.3.6.1.4.1.34774.4.1.23.4.1.1.6
-- 1.3.6.1.4.1.34774.4.1.23.4.1.1.6
-- 1.3.6.1.4.1.34774.4.1.23.4.1.1.6
-- 1.3.6.1.4.1.34774.4.1.23.4.1.1.6
-- 1.3.6.1.4.1.34774.4.1.23.4.1.1.6
		-- 1.3.6.1.4.1.34774.4.1.23.4.1.1.6
		hwInfoDiskDomainFreeCapacity OBJECT-TYPE
			SYNTAX Counter64
			MAX-ACCESS read-only
			STATUS current
			DESCRIPTION
				"  "
			::= { hwInfoDiskDomainEntry 6 }
		
--      1.3.6.1.4.1.34774.4.1.23.4.1.1.7
-- 1.3.6.1.4.1.34774.4.1.23.4.1.1.7
-- 1.3.6.1.4.1.34774.4.1.23.4.1.1.7
-- 1.3.6.1.4.1.34774.4.1.23.4.1.1.7
-- 1.3.6.1.4.1.34774.4.1.23.4.1.1.7
		-- 1.3.6.1.4.1.34774.4.1.23.4.1.1.7
		hwInfoDiskDomainHotSpareCapacity OBJECT-TYPE
			SYNTAX Counter64
			MAX-ACCESS read-only
			STATUS current
			DESCRIPTION
				"  "
			::= { hwInfoDiskDomainEntry 7 }
		
--      1.3.6.1.4.1.34774.4.1.23.4.1.1.8
-- 1.3.6.1.4.1.34774.4.1.23.4.1.1.8
-- 1.3.6.1.4.1.34774.4.1.23.4.1.1.8
-- 1.3.6.1.4.1.34774.4.1.23.4.1.1.8
-- 1.3.6.1.4.1.34774.4.1.23.4.1.1.8
		-- 1.3.6.1.4.1.34774.4.1.23.4.1.1.8
		hwInfoDiskDomainUsedHotSpareCapacity OBJECT-TYPE
			SYNTAX Counter64
			MAX-ACCESS read-only
			STATUS current
			DESCRIPTION
				"  "
			::= { hwInfoDiskDomainEntry 8 }
		
--      1.3.6.1.4.1.34774.4.1.23.4.2
-- 1.3.6.1.4.1.34774.4.1.23.4.2
-- 1.3.6.1.4.1.34774.4.1.23.4.2
-- 1.3.6.1.4.1.34774.4.1.23.4.2
-- 1.3.6.1.4.1.34774.4.1.23.4.2
		-- 1.3.6.1.4.1.34774.4.1.23.4.2
		hwInfoStoragePoolTable OBJECT-TYPE
			SYNTAX SEQUENCE OF HwInfoStoragePoolEntry
			MAX-ACCESS not-accessible
			STATUS current
			DESCRIPTION
				"  "
			::= { hwSpaceInfo 2 }
		
--      1.3.6.1.4.1.34774.4.1.23.4.2.1
-- 1.3.6.1.4.1.34774.4.1.23.4.2.1
-- 1.3.6.1.4.1.34774.4.1.23.4.2.1
-- 1.3.6.1.4.1.34774.4.1.23.4.2.1
-- 1.3.6.1.4.1.34774.4.1.23.4.2.1
		-- 1.3.6.1.4.1.34774.4.1.23.4.2.1
		hwInfoStoragePoolEntry OBJECT-TYPE
			SYNTAX HwInfoStoragePoolEntry
			MAX-ACCESS not-accessible
			STATUS current
			DESCRIPTION
				"  "
			INDEX { hwInfoStoragePoolID }
			::= { hwInfoStoragePoolTable 1 }
		
		HwInfoStoragePoolEntry ::=
			SEQUENCE { 
				hwInfoStoragePoolID
					OCTET STRING,
				hwInfoStoragePoolName
					OCTET STRING,
				hwInfoStoragePoolDiskDomainID
					OCTET STRING,
				hwInfoStoragePoolDiskDomainName
					OCTET STRING,
				hwInfoStoragePoolHealthStatus
					Unsigned32,
				hwInfoStoragePoolRunningStatus
					Unsigned32,
				hwInfoStoragePoolTotalCapacity
					Counter64,
				hwInfoStoragePoolSubscribedCapacity
					Counter64,
				hwInfoStoragePoolFreeCapacity
					Counter64,
				hwInfoStoragePoolProtectionCapacity
					Counter64,
				hwInfoStoragePoolFullThreshold
					Unsigned32
			 }

--      1.3.6.1.4.1.34774.4.1.23.4.2.1.1
-- 1.3.6.1.4.1.34774.4.1.23.4.2.1.1
-- 1.3.6.1.4.1.34774.4.1.23.4.2.1.1
-- 1.3.6.1.4.1.34774.4.1.23.4.2.1.1
-- 1.3.6.1.4.1.34774.4.1.23.4.2.1.1
		-- 1.3.6.1.4.1.34774.4.1.23.4.2.1.1
		hwInfoStoragePoolID OBJECT-TYPE
			SYNTAX OCTET STRING
			MAX-ACCESS read-only
			STATUS current
			DESCRIPTION
				"  "
			::= { hwInfoStoragePoolEntry 1 }
		
--      1.3.6.1.4.1.34774.4.1.23.4.2.1.2
-- 1.3.6.1.4.1.34774.4.1.23.4.2.1.2
-- 1.3.6.1.4.1.34774.4.1.23.4.2.1.2
-- 1.3.6.1.4.1.34774.4.1.23.4.2.1.2
-- 1.3.6.1.4.1.34774.4.1.23.4.2.1.2
		-- 1.3.6.1.4.1.34774.4.1.23.4.2.1.2
		hwInfoStoragePoolName OBJECT-TYPE
			SYNTAX OCTET STRING
			MAX-ACCESS read-only
			STATUS current
			DESCRIPTION
				"  "
			::= { hwInfoStoragePoolEntry 2 }
		
--      1.3.6.1.4.1.34774.4.1.23.4.2.1.3
-- 1.3.6.1.4.1.34774.4.1.23.4.2.1.3
-- 1.3.6.1.4.1.34774.4.1.23.4.2.1.3
-- 1.3.6.1.4.1.34774.4.1.23.4.2.1.3
-- 1.3.6.1.4.1.34774.4.1.23.4.2.1.3
		-- 1.3.6.1.4.1.34774.4.1.23.4.2.1.3
		hwInfoStoragePoolDiskDomainID OBJECT-TYPE
			SYNTAX OCTET STRING
			MAX-ACCESS read-only
			STATUS current
			DESCRIPTION
				"  "
			::= { hwInfoStoragePoolEntry 3 }
		
--      1.3.6.1.4.1.34774.4.1.23.4.2.1.4
-- 1.3.6.1.4.1.34774.4.1.23.4.2.1.4
-- 1.3.6.1.4.1.34774.4.1.23.4.2.1.4
-- 1.3.6.1.4.1.34774.4.1.23.4.2.1.4
-- 1.3.6.1.4.1.34774.4.1.23.4.2.1.4
		-- 1.3.6.1.4.1.34774.4.1.23.4.2.1.4
		hwInfoStoragePoolDiskDomainName OBJECT-TYPE
			SYNTAX OCTET STRING
			MAX-ACCESS read-only
			STATUS current
			DESCRIPTION
				"  "
			::= { hwInfoStoragePoolEntry 4 }
		
--      1.3.6.1.4.1.34774.4.1.23.4.2.1.5
-- 1.3.6.1.4.1.34774.4.1.23.4.2.1.5
-- 1.3.6.1.4.1.34774.4.1.23.4.2.1.5
-- 1.3.6.1.4.1.34774.4.1.23.4.2.1.5
-- 1.3.6.1.4.1.34774.4.1.23.4.2.1.5
		-- 1.3.6.1.4.1.34774.4.1.23.4.2.1.5
		hwInfoStoragePoolHealthStatus OBJECT-TYPE
			SYNTAX Unsigned32
			MAX-ACCESS read-only
			STATUS current
			DESCRIPTION
				"  "
			::= { hwInfoStoragePoolEntry 5 }
		
--      1.3.6.1.4.1.34774.4.1.23.4.2.1.6
-- 1.3.6.1.4.1.34774.4.1.23.4.2.1.6
-- 1.3.6.1.4.1.34774.4.1.23.4.2.1.6
-- 1.3.6.1.4.1.34774.4.1.23.4.2.1.6
-- 1.3.6.1.4.1.34774.4.1.23.4.2.1.6
		-- 1.3.6.1.4.1.34774.4.1.23.4.2.1.6
		hwInfoStoragePoolRunningStatus OBJECT-TYPE
			SYNTAX Unsigned32
			MAX-ACCESS read-only
			STATUS current
			DESCRIPTION
				"  "
			::= { hwInfoStoragePoolEntry 6 }
		
--      1.3.6.1.4.1.34774.4.1.23.4.2.1.7
-- 1.3.6.1.4.1.34774.4.1.23.4.2.1.7
-- 1.3.6.1.4.1.34774.4.1.23.4.2.1.7
-- 1.3.6.1.4.1.34774.4.1.23.4.2.1.7
-- 1.3.6.1.4.1.34774.4.1.23.4.2.1.7
		-- 1.3.6.1.4.1.34774.4.1.23.4.2.1.7
		hwInfoStoragePoolTotalCapacity OBJECT-TYPE
			SYNTAX Counter64
			MAX-ACCESS read-only
			STATUS current
			DESCRIPTION
				"  "
			::= { hwInfoStoragePoolEntry 7 }
		
--      1.3.6.1.4.1.34774.4.1.23.4.2.1.8
-- 1.3.6.1.4.1.34774.4.1.23.4.2.1.8
-- 1.3.6.1.4.1.34774.4.1.23.4.2.1.8
-- 1.3.6.1.4.1.34774.4.1.23.4.2.1.8
-- 1.3.6.1.4.1.34774.4.1.23.4.2.1.8
		-- 1.3.6.1.4.1.34774.4.1.23.4.2.1.8
		hwInfoStoragePoolSubscribedCapacity OBJECT-TYPE
			SYNTAX Counter64
			MAX-ACCESS read-only
			STATUS current
			DESCRIPTION
				"  "
			::= { hwInfoStoragePoolEntry 8 }
		
--      1.3.6.1.4.1.34774.4.1.23.4.2.1.9
-- 1.3.6.1.4.1.34774.4.1.23.4.2.1.9
-- 1.3.6.1.4.1.34774.4.1.23.4.2.1.9
-- 1.3.6.1.4.1.34774.4.1.23.4.2.1.9
-- 1.3.6.1.4.1.34774.4.1.23.4.2.1.9
		-- 1.3.6.1.4.1.34774.4.1.23.4.2.1.9
		hwInfoStoragePoolFreeCapacity OBJECT-TYPE
			SYNTAX Counter64
			MAX-ACCESS read-only
			STATUS current
			DESCRIPTION
				"  "
			::= { hwInfoStoragePoolEntry 9 }
		
--      1.3.6.1.4.1.34774.4.1.23.4.2.1.9
-- 1.3.6.1.4.1.34774.4.1.23.4.2.1.9
-- 1.3.6.1.4.1.34774.4.1.23.4.2.1.9
-- 1.3.6.1.4.1.34774.4.1.23.4.2.1.9
-- 1.3.6.1.4.1.34774.4.1.23.4.2.1.9
		-- 1.3.6.1.4.1.34774.4.1.23.4.2.1.10
		hwInfoStoragePoolProtectionCapacity OBJECT-TYPE
			SYNTAX Counter64
			MAX-ACCESS read-only
			STATUS current
			DESCRIPTION
				"  "
			::= { hwInfoStoragePoolEntry 10 }
		
--      1.3.6.1.4.1.34774.4.1.23.4.2.1.14
-- 1.3.6.1.4.1.34774.4.1.23.4.2.1.14
-- 1.3.6.1.4.1.34774.4.1.23.4.2.1.14
-- 1.3.6.1.4.1.34774.4.1.23.4.2.1.14
-- 1.3.6.1.4.1.34774.4.1.23.4.2.1.14
		-- 1.3.6.1.4.1.34774.4.1.23.4.2.1.14
		hwInfoStoragePoolFullThreshold OBJECT-TYPE
			SYNTAX Unsigned32
			MAX-ACCESS read-only
			STATUS current
			DESCRIPTION
				"  "
			::= { hwInfoStoragePoolEntry 14 }
		
--      1.3.6.1.4.1.34774.4.1.23.4.4
-- 1.3.6.1.4.1.34774.4.1.23.4.4
-- 1.3.6.1.4.1.34774.4.1.23.4.4
-- 1.3.6.1.4.1.34774.4.1.23.4.4
-- 1.3.6.1.4.1.34774.4.1.23.4.4
		-- 1.3.6.1.4.1.34774.4.1.23.4.4
		hwInfoPortGroupTable OBJECT-TYPE
			SYNTAX SEQUENCE OF HwInfoPortGroupEntry
			MAX-ACCESS not-accessible
			STATUS current
			DESCRIPTION
				"  "
			::= { hwSpaceInfo 4 }
		
--      1.3.6.1.4.1.34774.4.1.23.4.4.1
-- 1.3.6.1.4.1.34774.4.1.23.4.4.1
-- 1.3.6.1.4.1.34774.4.1.23.4.4.1
-- 1.3.6.1.4.1.34774.4.1.23.4.4.1
-- 1.3.6.1.4.1.34774.4.1.23.4.4.1
		-- 1.3.6.1.4.1.34774.4.1.23.4.4.1
		hwInfoPortGroupEntry OBJECT-TYPE
			SYNTAX HwInfoPortGroupEntry
			MAX-ACCESS not-accessible
			STATUS current
			DESCRIPTION
				"  "
			INDEX { hwInfoPortGroupID }
			::= { hwInfoPortGroupTable 1 }
		
		HwInfoPortGroupEntry ::=
			SEQUENCE { 
				hwInfoPortGroupID
					OCTET STRING,
				hwInfoPortGroupName
					OCTET STRING,
				hwInfoPortGroupPortList
					OCTET STRING
			 }

--      1.3.6.1.4.1.34774.4.1.23.4.4.1.1
-- 1.3.6.1.4.1.34774.4.1.23.4.4.1.1
-- 1.3.6.1.4.1.34774.4.1.23.4.4.1.1
-- 1.3.6.1.4.1.34774.4.1.23.4.4.1.1
-- 1.3.6.1.4.1.34774.4.1.23.4.4.1.1
		-- 1.3.6.1.4.1.34774.4.1.23.4.4.1.1
		hwInfoPortGroupID OBJECT-TYPE
			SYNTAX OCTET STRING
			MAX-ACCESS read-only
			STATUS current
			DESCRIPTION
				"  "
			::= { hwInfoPortGroupEntry 1 }
		
--      1.3.6.1.4.1.34774.4.1.23.4.4.1.2
-- 1.3.6.1.4.1.34774.4.1.23.4.4.1.2
-- 1.3.6.1.4.1.34774.4.1.23.4.4.1.2
-- 1.3.6.1.4.1.34774.4.1.23.4.4.1.2
-- 1.3.6.1.4.1.34774.4.1.23.4.4.1.2
		-- 1.3.6.1.4.1.34774.4.1.23.4.4.1.2
		hwInfoPortGroupName OBJECT-TYPE
			SYNTAX OCTET STRING
			MAX-ACCESS read-only
			STATUS current
			DESCRIPTION
				"  "
			::= { hwInfoPortGroupEntry 2 }
		
--      1.3.6.1.4.1.34774.4.1.23.4.4.1.3
-- 1.3.6.1.4.1.34774.4.1.23.4.4.1.3
-- 1.3.6.1.4.1.34774.4.1.23.4.4.1.3
-- 1.3.6.1.4.1.34774.4.1.23.4.4.1.3
-- 1.3.6.1.4.1.34774.4.1.23.4.4.1.3
		-- 1.3.6.1.4.1.34774.4.1.23.4.4.1.3
		hwInfoPortGroupPortList OBJECT-TYPE
			SYNTAX OCTET STRING
			MAX-ACCESS read-only
			STATUS current
			DESCRIPTION
				"  "
			::= { hwInfoPortGroupEntry 3 }
		
--      1.3.6.1.4.1.34774.4.1.23.4.5
-- 1.3.6.1.4.1.34774.4.1.23.4.5
-- 1.3.6.1.4.1.34774.4.1.23.4.5
-- 1.3.6.1.4.1.34774.4.1.23.4.5
-- 1.3.6.1.4.1.34774.4.1.23.4.5
		-- 1.3.6.1.4.1.34774.4.1.23.4.5
		hwInfoHostTable OBJECT-TYPE
			SYNTAX SEQUENCE OF HwInfoHostEntry
			MAX-ACCESS not-accessible
			STATUS current
			DESCRIPTION
				"  "
			::= { hwSpaceInfo 5 }
		
--      1.3.6.1.4.1.34774.4.1.23.4.5.1
-- 1.3.6.1.4.1.34774.4.1.23.4.5.1
-- 1.3.6.1.4.1.34774.4.1.23.4.5.1
-- 1.3.6.1.4.1.34774.4.1.23.4.5.1
-- 1.3.6.1.4.1.34774.4.1.23.4.5.1
		-- 1.3.6.1.4.1.34774.4.1.23.4.5.1
		hwInfoHostEntry OBJECT-TYPE
			SYNTAX HwInfoHostEntry
			MAX-ACCESS not-accessible
			STATUS current
			DESCRIPTION
				"  "
			INDEX { hwInfoHostID }
			::= { hwInfoHostTable 1 }
		
		HwInfoHostEntry ::=
			SEQUENCE { 
				hwInfoHostID
					OCTET STRING,
				hwInfoHostName
					OCTET STRING,
				hwInfoHostLocation
					OCTET STRING,
				hwInfoHostHealthStatus
					Unsigned32,
				hwInfoHostRunningStatus
					Unsigned32,
				hwInfoHostOperatingSystem
					Unsigned32,
				hwInfoHostIPAddress
					OCTET STRING,
				hwInfoHostNetworkName
					OCTET STRING,
				hwInfoHostModel
					OCTET STRING
			 }

--      1.3.6.1.4.1.34774.4.1.23.4.5.1.1
-- 1.3.6.1.4.1.34774.4.1.23.4.5.1.1
-- 1.3.6.1.4.1.34774.4.1.23.4.5.1.1
-- 1.3.6.1.4.1.34774.4.1.23.4.5.1.1
-- 1.3.6.1.4.1.34774.4.1.23.4.5.1.1
		-- 1.3.6.1.4.1.34774.4.1.23.4.5.1.1
		hwInfoHostID OBJECT-TYPE
			SYNTAX OCTET STRING
			MAX-ACCESS read-only
			STATUS current
			DESCRIPTION
				"  "
			::= { hwInfoHostEntry 1 }
		
--      1.3.6.1.4.1.34774.4.1.23.4.5.1.2
-- 1.3.6.1.4.1.34774.4.1.23.4.5.1.2
-- 1.3.6.1.4.1.34774.4.1.23.4.5.1.2
-- 1.3.6.1.4.1.34774.4.1.23.4.5.1.2
-- 1.3.6.1.4.1.34774.4.1.23.4.5.1.2
		-- 1.3.6.1.4.1.34774.4.1.23.4.5.1.2
		hwInfoHostName OBJECT-TYPE
			SYNTAX OCTET STRING
			MAX-ACCESS read-only
			STATUS current
			DESCRIPTION
				"  "
			::= { hwInfoHostEntry 2 }
		
--      1.3.6.1.4.1.34774.4.1.23.4.5.1.3
-- 1.3.6.1.4.1.34774.4.1.23.4.5.1.3
-- 1.3.6.1.4.1.34774.4.1.23.4.5.1.3
-- 1.3.6.1.4.1.34774.4.1.23.4.5.1.3
-- 1.3.6.1.4.1.34774.4.1.23.4.5.1.3
		-- 1.3.6.1.4.1.34774.4.1.23.4.5.1.3
		hwInfoHostLocation OBJECT-TYPE
			SYNTAX OCTET STRING
			MAX-ACCESS read-only
			STATUS current
			DESCRIPTION
				"  "
			::= { hwInfoHostEntry 3 }
		
--      1.3.6.1.4.1.34774.4.1.23.4.5.1.4
-- 1.3.6.1.4.1.34774.4.1.23.4.5.1.4
-- 1.3.6.1.4.1.34774.4.1.23.4.5.1.4
-- 1.3.6.1.4.1.34774.4.1.23.4.5.1.4
-- 1.3.6.1.4.1.34774.4.1.23.4.5.1.4
		-- 1.3.6.1.4.1.34774.4.1.23.4.5.1.4
		hwInfoHostHealthStatus OBJECT-TYPE
			SYNTAX Unsigned32
			MAX-ACCESS read-only
			STATUS current
			DESCRIPTION
				"  "
			::= { hwInfoHostEntry 4 }
		
--      1.3.6.1.4.1.34774.4.1.23.4.5.1.5
-- 1.3.6.1.4.1.34774.4.1.23.4.5.1.5
-- 1.3.6.1.4.1.34774.4.1.23.4.5.1.5
-- 1.3.6.1.4.1.34774.4.1.23.4.5.1.5
-- 1.3.6.1.4.1.34774.4.1.23.4.5.1.5
		-- 1.3.6.1.4.1.34774.4.1.23.4.5.1.5
		hwInfoHostRunningStatus OBJECT-TYPE
			SYNTAX Unsigned32
			MAX-ACCESS read-only
			STATUS current
			DESCRIPTION
				"  "
			::= { hwInfoHostEntry 5 }
		
--      1.3.6.1.4.1.34774.4.1.23.4.5.1.6
-- 1.3.6.1.4.1.34774.4.1.23.4.5.1.6
-- 1.3.6.1.4.1.34774.4.1.23.4.5.1.6
-- 1.3.6.1.4.1.34774.4.1.23.4.5.1.6
-- 1.3.6.1.4.1.34774.4.1.23.4.5.1.6
		-- 1.3.6.1.4.1.34774.4.1.23.4.5.1.6
		hwInfoHostOperatingSystem OBJECT-TYPE
			SYNTAX Unsigned32
			MAX-ACCESS read-only
			STATUS current
			DESCRIPTION
				"  "
			::= { hwInfoHostEntry 6 }
		
--      1.3.6.1.4.1.34774.4.1.23.4.5.1.7
-- 1.3.6.1.4.1.34774.4.1.23.4.5.1.7
-- 1.3.6.1.4.1.34774.4.1.23.4.5.1.7
-- 1.3.6.1.4.1.34774.4.1.23.4.5.1.7
-- 1.3.6.1.4.1.34774.4.1.23.4.5.1.7
		-- 1.3.6.1.4.1.34774.4.1.23.4.5.1.7
		hwInfoHostIPAddress OBJECT-TYPE
			SYNTAX OCTET STRING
			MAX-ACCESS read-only
			STATUS current
			DESCRIPTION
				"  "
			::= { hwInfoHostEntry 7 }
		
--      1.3.6.1.4.1.34774.4.1.23.4.5.1.8
-- 1.3.6.1.4.1.34774.4.1.23.4.5.1.8
-- 1.3.6.1.4.1.34774.4.1.23.4.5.1.8
-- 1.3.6.1.4.1.34774.4.1.23.4.5.1.8
-- 1.3.6.1.4.1.34774.4.1.23.4.5.1.8
		-- 1.3.6.1.4.1.34774.4.1.23.4.5.1.8
		hwInfoHostNetworkName OBJECT-TYPE
			SYNTAX OCTET STRING
			MAX-ACCESS read-only
			STATUS current
			DESCRIPTION
				"  "
			::= { hwInfoHostEntry 8 }
		
--      1.3.6.1.4.1.34774.4.1.23.4.5.1.9
-- 1.3.6.1.4.1.34774.4.1.23.4.5.1.9
-- 1.3.6.1.4.1.34774.4.1.23.4.5.1.9
-- 1.3.6.1.4.1.34774.4.1.23.4.5.1.9
-- 1.3.6.1.4.1.34774.4.1.23.4.5.1.9
		-- 1.3.6.1.4.1.34774.4.1.23.4.5.1.9
		hwInfoHostModel OBJECT-TYPE
			SYNTAX OCTET STRING
			MAX-ACCESS read-only
			STATUS current
			DESCRIPTION
				"  "
			::= { hwInfoHostEntry 9 }
		
--      1.3.6.1.4.1.34774.4.1.23.4.6
-- 1.3.6.1.4.1.34774.4.1.23.4.6
-- 1.3.6.1.4.1.34774.4.1.23.4.6
-- 1.3.6.1.4.1.34774.4.1.23.4.6
-- 1.3.6.1.4.1.34774.4.1.23.4.6
		-- 1.3.6.1.4.1.34774.4.1.23.4.6
		hwInfoHostGroupTable OBJECT-TYPE
			SYNTAX SEQUENCE OF HwInfoHostGroupEntry
			MAX-ACCESS not-accessible
			STATUS current
			DESCRIPTION
				"  "
			::= { hwSpaceInfo 6 }
		
--      1.3.6.1.4.1.34774.4.1.23.4.6.1
-- 1.3.6.1.4.1.34774.4.1.23.4.6.1
-- 1.3.6.1.4.1.34774.4.1.23.4.6.1
-- 1.3.6.1.4.1.34774.4.1.23.4.6.1
-- 1.3.6.1.4.1.34774.4.1.23.4.6.1
		-- 1.3.6.1.4.1.34774.4.1.23.4.6.1
		hwInfoHostGroupEntry OBJECT-TYPE
			SYNTAX HwInfoHostGroupEntry
			MAX-ACCESS not-accessible
			STATUS current
			DESCRIPTION
				"  "
			INDEX { hwInfoHostGroupID }
			::= { hwInfoHostGroupTable 1 }
		
		HwInfoHostGroupEntry ::=
			SEQUENCE { 
				hwInfoHostGroupID
					OCTET STRING,
				hwInfoHostGroupName
					OCTET STRING,
				hwInfoHostGroupHostList
					OCTET STRING
			 }

--      1.3.6.1.4.1.34774.4.1.23.4.6.1.1
-- 1.3.6.1.4.1.34774.4.1.23.4.6.1.1
-- 1.3.6.1.4.1.34774.4.1.23.4.6.1.1
-- 1.3.6.1.4.1.34774.4.1.23.4.6.1.1
-- 1.3.6.1.4.1.34774.4.1.23.4.6.1.1
		-- 1.3.6.1.4.1.34774.4.1.23.4.6.1.1
		hwInfoHostGroupID OBJECT-TYPE
			SYNTAX OCTET STRING
			MAX-ACCESS read-only
			STATUS current
			DESCRIPTION
				"  "
			::= { hwInfoHostGroupEntry 1 }
		
--      1.3.6.1.4.1.34774.4.1.23.4.6.1.2
-- 1.3.6.1.4.1.34774.4.1.23.4.6.1.2
-- 1.3.6.1.4.1.34774.4.1.23.4.6.1.2
-- 1.3.6.1.4.1.34774.4.1.23.4.6.1.2
-- 1.3.6.1.4.1.34774.4.1.23.4.6.1.2
		-- 1.3.6.1.4.1.34774.4.1.23.4.6.1.2
		hwInfoHostGroupName OBJECT-TYPE
			SYNTAX OCTET STRING
			MAX-ACCESS read-only
			STATUS current
			DESCRIPTION
				"  "
			::= { hwInfoHostGroupEntry 2 }
		
--      1.3.6.1.4.1.34774.4.1.23.4.6.1.3
-- 1.3.6.1.4.1.34774.4.1.23.4.6.1.3
-- 1.3.6.1.4.1.34774.4.1.23.4.6.1.3
-- 1.3.6.1.4.1.34774.4.1.23.4.6.1.3
-- 1.3.6.1.4.1.34774.4.1.23.4.6.1.3
		-- 1.3.6.1.4.1.34774.4.1.23.4.6.1.3
		hwInfoHostGroupHostList OBJECT-TYPE
			SYNTAX OCTET STRING
			MAX-ACCESS read-only
			STATUS current
			DESCRIPTION
				"  "
			::= { hwInfoHostGroupEntry 3 }
		
--      1.3.6.1.4.1.34774.4.1.23.4.7
-- 1.3.6.1.4.1.34774.4.1.23.4.7
-- 1.3.6.1.4.1.34774.4.1.23.4.7
-- 1.3.6.1.4.1.34774.4.1.23.4.7
-- 1.3.6.1.4.1.34774.4.1.23.4.7
		-- 1.3.6.1.4.1.34774.4.1.23.4.7
		hwInfoLunGroupTable OBJECT-TYPE
			SYNTAX SEQUENCE OF HwInfoLunGroupEntry
			MAX-ACCESS not-accessible
			STATUS current
			DESCRIPTION
				"  "
			::= { hwSpaceInfo 7 }
		
--      1.3.6.1.4.1.34774.4.1.23.4.7.1
-- 1.3.6.1.4.1.34774.4.1.23.4.7.1
-- 1.3.6.1.4.1.34774.4.1.23.4.7.1
-- 1.3.6.1.4.1.34774.4.1.23.4.7.1
-- 1.3.6.1.4.1.34774.4.1.23.4.7.1
		-- 1.3.6.1.4.1.34774.4.1.23.4.7.1
		hwInfoLunGroupEntry OBJECT-TYPE
			SYNTAX HwInfoLunGroupEntry
			MAX-ACCESS not-accessible
			STATUS current
			DESCRIPTION
				"  "
			INDEX { hwInfoLunGroupID }
			::= { hwInfoLunGroupTable 1 }
		
		HwInfoLunGroupEntry ::=
			SEQUENCE { 
				hwInfoLunGroupID
					OCTET STRING,
				hwInfoLunGroupName
					OCTET STRING,
				hwInfoLunGroupLunList
					OCTET STRING
			 }

--      1.3.6.1.4.1.34774.4.1.23.4.7.1.1
-- 1.3.6.1.4.1.34774.4.1.23.4.7.1.1
-- 1.3.6.1.4.1.34774.4.1.23.4.7.1.1
-- 1.3.6.1.4.1.34774.4.1.23.4.7.1.1
-- 1.3.6.1.4.1.34774.4.1.23.4.7.1.1
		-- 1.3.6.1.4.1.34774.4.1.23.4.7.1.1
		hwInfoLunGroupID OBJECT-TYPE
			SYNTAX OCTET STRING
			MAX-ACCESS read-only
			STATUS current
			DESCRIPTION
				"  "
			::= { hwInfoLunGroupEntry 1 }
		
--      1.3.6.1.4.1.34774.4.1.23.4.7.1.2
-- 1.3.6.1.4.1.34774.4.1.23.4.7.1.2
-- 1.3.6.1.4.1.34774.4.1.23.4.7.1.2
-- 1.3.6.1.4.1.34774.4.1.23.4.7.1.2
-- 1.3.6.1.4.1.34774.4.1.23.4.7.1.2
		-- 1.3.6.1.4.1.34774.4.1.23.4.7.1.2
		hwInfoLunGroupName OBJECT-TYPE
			SYNTAX OCTET STRING
			MAX-ACCESS read-only
			STATUS current
			DESCRIPTION
				"  "
			::= { hwInfoLunGroupEntry 2 }
		
--      1.3.6.1.4.1.34774.4.1.23.4.7.1.3
-- 1.3.6.1.4.1.34774.4.1.23.4.7.1.3
-- 1.3.6.1.4.1.34774.4.1.23.4.7.1.3
-- 1.3.6.1.4.1.34774.4.1.23.4.7.1.3
-- 1.3.6.1.4.1.34774.4.1.23.4.7.1.3
		-- 1.3.6.1.4.1.34774.4.1.23.4.7.1.3
		hwInfoLunGroupLunList OBJECT-TYPE
			SYNTAX OCTET STRING
			MAX-ACCESS read-only
			STATUS current
			DESCRIPTION
				"  "
			::= { hwInfoLunGroupEntry 3 }
		
--      1.3.6.1.4.1.34774.4.1.23.4.8
-- 1.3.6.1.4.1.34774.4.1.23.4.8
-- 1.3.6.1.4.1.34774.4.1.23.4.8
-- 1.3.6.1.4.1.34774.4.1.23.4.8
-- 1.3.6.1.4.1.34774.4.1.23.4.8
		-- 1.3.6.1.4.1.34774.4.1.23.4.8
		hwInfoLunTable OBJECT-TYPE
			SYNTAX SEQUENCE OF HwInfoLunEntry
			MAX-ACCESS not-accessible
			STATUS current
			DESCRIPTION
				" "
			::= { hwSpaceInfo 8 }
		
--      1.3.6.1.4.1.34774.4.1.23.4.8.1
-- 1.3.6.1.4.1.34774.4.1.23.4.8.1
-- 1.3.6.1.4.1.34774.4.1.23.4.8.1
-- 1.3.6.1.4.1.34774.4.1.23.4.8.1
-- 1.3.6.1.4.1.34774.4.1.23.4.8.1
		-- 1.3.6.1.4.1.34774.4.1.23.4.8.1
		hwInfoLunEntry OBJECT-TYPE
			SYNTAX HwInfoLunEntry
			MAX-ACCESS not-accessible
			STATUS current
			DESCRIPTION
				"  "
			INDEX { hwInfoLunID }
			::= { hwInfoLunTable 1 }
		
		HwInfoLunEntry ::=
			SEQUENCE { 
				hwInfoLunID
					OCTET STRING,
				hwInfoLunName
					OCTET STRING,
				hwInfoLunPoolID
					OCTET STRING,
				hwInfoLunPoolName
					OCTET STRING,
				hwInfoLunCapacity
					Counter64,
				hwInfoLunSubscribedCapacity
					Counter64,
				hwInfoLunProtectionCapacity
					Counter64,
				hwInfoLunSectorSize
					Unsigned32,
				hwInfoLunHealthStatus
					Unsigned32,
				hwInfoLunRunningStatus
					Unsigned32,
				hwInfoLunType
					Unsigned32,
				hwInfoLunIOPriority
					Unsigned32,
				hwInfoLunWWN
					OCTET STRING,
				hwInfoLunExposedToInitiator
					Unsigned32,
				hwInfoLunWritePolicy
					Unsigned32,
				hwInfoLunRunningWritePolicy
					Unsigned32,
				hwInfoLunPrefetchPolicy
					Unsigned32,
				hwInfoLunPrefetchValue
					Unsigned32,
				hwInfoLunOwnerController
					OCTET STRING,
				hwInfoLunWorkController
					OCTET STRING,
				hwInfoLunIsAddToLunGroup
					Unsigned32,
				hwInfoLunDIFSwitch
					Unsigned32,
				hwInfoLunRemoteLUNWWN
					OCTET STRING,
				hwInfoLunUsageType
					Unsigned32
			 }

--      1.3.6.1.4.1.34774.4.1.23.4.8.1.1
-- 1.3.6.1.4.1.34774.4.1.23.4.8.1.1
-- 1.3.6.1.4.1.34774.4.1.23.4.8.1.1
-- 1.3.6.1.4.1.34774.4.1.23.4.8.1.1
-- 1.3.6.1.4.1.34774.4.1.23.4.8.1.1
		-- 1.3.6.1.4.1.34774.4.1.23.4.8.1.1
		hwInfoLunID OBJECT-TYPE
			SYNTAX OCTET STRING
			MAX-ACCESS read-only
			STATUS current
			DESCRIPTION
				"  "
			::= { hwInfoLunEntry 1 }
		
--      1.3.6.1.4.1.34774.4.1.23.4.8.1.2
-- 1.3.6.1.4.1.34774.4.1.23.4.8.1.2
-- 1.3.6.1.4.1.34774.4.1.23.4.8.1.2
-- 1.3.6.1.4.1.34774.4.1.23.4.8.1.2
-- 1.3.6.1.4.1.34774.4.1.23.4.8.1.2
		-- 1.3.6.1.4.1.34774.4.1.23.4.8.1.2
		hwInfoLunName OBJECT-TYPE
			SYNTAX OCTET STRING
			MAX-ACCESS read-only
			STATUS current
			DESCRIPTION
				"  "
			::= { hwInfoLunEntry 2 }
		
--      1.3.6.1.4.1.34774.4.1.23.4.8.1.3
-- 1.3.6.1.4.1.34774.4.1.23.4.8.1.3
-- 1.3.6.1.4.1.34774.4.1.23.4.8.1.3
-- 1.3.6.1.4.1.34774.4.1.23.4.8.1.3
-- 1.3.6.1.4.1.34774.4.1.23.4.8.1.3
		-- 1.3.6.1.4.1.34774.4.1.23.4.8.1.3
		hwInfoLunPoolID OBJECT-TYPE
			SYNTAX OCTET STRING
			MAX-ACCESS read-only
			STATUS current
			DESCRIPTION
				"  "
			::= { hwInfoLunEntry 3 }
		
--      1.3.6.1.4.1.34774.4.1.23.4.8.1.4
-- 1.3.6.1.4.1.34774.4.1.23.4.8.1.4
-- 1.3.6.1.4.1.34774.4.1.23.4.8.1.4
-- 1.3.6.1.4.1.34774.4.1.23.4.8.1.4
-- 1.3.6.1.4.1.34774.4.1.23.4.8.1.4
		-- 1.3.6.1.4.1.34774.4.1.23.4.8.1.4
		hwInfoLunPoolName OBJECT-TYPE
			SYNTAX OCTET STRING
			MAX-ACCESS read-only
			STATUS current
			DESCRIPTION
				"  "
			::= { hwInfoLunEntry 4 }
		
--      1.3.6.1.4.1.34774.4.1.23.4.8.1.5
-- 1.3.6.1.4.1.34774.4.1.23.4.8.1.5
-- 1.3.6.1.4.1.34774.4.1.23.4.8.1.5
-- 1.3.6.1.4.1.34774.4.1.23.4.8.1.5
-- 1.3.6.1.4.1.34774.4.1.23.4.8.1.5
		-- 1.3.6.1.4.1.34774.4.1.23.4.8.1.5
		hwInfoLunCapacity OBJECT-TYPE
			SYNTAX Counter64
			MAX-ACCESS read-only
			STATUS current
			DESCRIPTION
				"  "
			::= { hwInfoLunEntry 5 }
		
--      1.3.6.1.4.1.34774.4.1.23.4.8.1.6
-- 1.3.6.1.4.1.34774.4.1.23.4.8.1.6
-- 1.3.6.1.4.1.34774.4.1.23.4.8.1.6
-- 1.3.6.1.4.1.34774.4.1.23.4.8.1.6
-- 1.3.6.1.4.1.34774.4.1.23.4.8.1.6
		-- 1.3.6.1.4.1.34774.4.1.23.4.8.1.6
		hwInfoLunSubscribedCapacity OBJECT-TYPE
			SYNTAX Counter64
			MAX-ACCESS read-only
			STATUS current
			DESCRIPTION
				"  "
			::= { hwInfoLunEntry 6 }
		
--      1.3.6.1.4.1.34774.4.1.23.4.8.1.7
-- 1.3.6.1.4.1.34774.4.1.23.4.8.1.7
-- 1.3.6.1.4.1.34774.4.1.23.4.8.1.7
-- 1.3.6.1.4.1.34774.4.1.23.4.8.1.7
-- 1.3.6.1.4.1.34774.4.1.23.4.8.1.7
		-- 1.3.6.1.4.1.34774.4.1.23.4.8.1.7
		hwInfoLunProtectionCapacity OBJECT-TYPE
			SYNTAX Counter64
			MAX-ACCESS read-only
			STATUS current
			DESCRIPTION
				"  "
			::= { hwInfoLunEntry 7 }
		
--      1.3.6.1.4.1.34774.4.1.23.4.8.1.8
-- 1.3.6.1.4.1.34774.4.1.23.4.8.1.8
-- 1.3.6.1.4.1.34774.4.1.23.4.8.1.8
-- 1.3.6.1.4.1.34774.4.1.23.4.8.1.8
-- 1.3.6.1.4.1.34774.4.1.23.4.8.1.8
		-- 1.3.6.1.4.1.34774.4.1.23.4.8.1.8
		hwInfoLunSectorSize OBJECT-TYPE
			SYNTAX Unsigned32
			MAX-ACCESS read-only
			STATUS current
			DESCRIPTION
				"  "
			::= { hwInfoLunEntry 8 }
		
--      1.3.6.1.4.1.34774.4.1.23.4.8.1.9
-- 1.3.6.1.4.1.34774.4.1.23.4.8.1.9
-- 1.3.6.1.4.1.34774.4.1.23.4.8.1.9
-- 1.3.6.1.4.1.34774.4.1.23.4.8.1.9
-- 1.3.6.1.4.1.34774.4.1.23.4.8.1.9
		-- 1.3.6.1.4.1.34774.4.1.23.4.8.1.9
		hwInfoLunHealthStatus OBJECT-TYPE
			SYNTAX Unsigned32
			MAX-ACCESS read-only
			STATUS current
			DESCRIPTION
				"  "
			::= { hwInfoLunEntry 9 }
		
--      1.3.6.1.4.1.34774.4.1.23.4.8.1.10
-- 1.3.6.1.4.1.34774.4.1.23.4.8.1.10
-- 1.3.6.1.4.1.34774.4.1.23.4.8.1.10
-- 1.3.6.1.4.1.34774.4.1.23.4.8.1.10
-- 1.3.6.1.4.1.34774.4.1.23.4.8.1.10
		-- 1.3.6.1.4.1.34774.4.1.23.4.8.1.10
		hwInfoLunRunningStatus OBJECT-TYPE
			SYNTAX Unsigned32
			MAX-ACCESS read-only
			STATUS current
			DESCRIPTION
				"  "
			::= { hwInfoLunEntry 10 }
		
--      1.3.6.1.4.1.34774.4.1.23.4.8.1.11
-- 1.3.6.1.4.1.34774.4.1.23.4.8.1.11
-- 1.3.6.1.4.1.34774.4.1.23.4.8.1.11
-- 1.3.6.1.4.1.34774.4.1.23.4.8.1.11
-- 1.3.6.1.4.1.34774.4.1.23.4.8.1.11
		-- 1.3.6.1.4.1.34774.4.1.23.4.8.1.11
		hwInfoLunType OBJECT-TYPE
			SYNTAX Unsigned32
			MAX-ACCESS read-only
			STATUS current
			DESCRIPTION
				"  "
			::= { hwInfoLunEntry 11 }
		
--      1.3.6.1.4.1.34774.4.1.23.4.8.1.12
-- 1.3.6.1.4.1.34774.4.1.23.4.8.1.12
-- 1.3.6.1.4.1.34774.4.1.23.4.8.1.12
-- 1.3.6.1.4.1.34774.4.1.23.4.8.1.12
-- 1.3.6.1.4.1.34774.4.1.23.4.8.1.12
		-- 1.3.6.1.4.1.34774.4.1.23.4.8.1.12
		hwInfoLunIOPriority OBJECT-TYPE
			SYNTAX Unsigned32
			MAX-ACCESS read-only
			STATUS current
			DESCRIPTION
				"  "
			::= { hwInfoLunEntry 12 }
		
--      1.3.6.1.4.1.34774.4.1.23.4.8.1.13
-- 1.3.6.1.4.1.34774.4.1.23.4.8.1.13
-- 1.3.6.1.4.1.34774.4.1.23.4.8.1.13
-- 1.3.6.1.4.1.34774.4.1.23.4.8.1.13
-- 1.3.6.1.4.1.34774.4.1.23.4.8.1.13
		-- 1.3.6.1.4.1.34774.4.1.23.4.8.1.13
		hwInfoLunWWN OBJECT-TYPE
			SYNTAX OCTET STRING
			MAX-ACCESS read-only
			STATUS current
			DESCRIPTION
				"  "
			::= { hwInfoLunEntry 13 }
		
--      1.3.6.1.4.1.34774.4.1.23.4.8.1.14
-- 1.3.6.1.4.1.34774.4.1.23.4.8.1.14
-- 1.3.6.1.4.1.34774.4.1.23.4.8.1.14
-- 1.3.6.1.4.1.34774.4.1.23.4.8.1.14
-- 1.3.6.1.4.1.34774.4.1.23.4.8.1.14
		-- 1.3.6.1.4.1.34774.4.1.23.4.8.1.14
		hwInfoLunExposedToInitiator OBJECT-TYPE
			SYNTAX Unsigned32
			MAX-ACCESS read-only
			STATUS current
			DESCRIPTION
				"  "
			::= { hwInfoLunEntry 14 }
		
--      1.3.6.1.4.1.34774.4.1.23.4.8.1.15
-- 1.3.6.1.4.1.34774.4.1.23.4.8.1.15
-- 1.3.6.1.4.1.34774.4.1.23.4.8.1.15
-- 1.3.6.1.4.1.34774.4.1.23.4.8.1.15
-- 1.3.6.1.4.1.34774.4.1.23.4.8.1.15
		-- 1.3.6.1.4.1.34774.4.1.23.4.8.1.15
		hwInfoLunWritePolicy OBJECT-TYPE
			SYNTAX Unsigned32
			MAX-ACCESS read-only
			STATUS current
			DESCRIPTION
				"  "
			::= { hwInfoLunEntry 15 }
		
--      1.3.6.1.4.1.34774.4.1.23.4.8.1.16
-- 1.3.6.1.4.1.34774.4.1.23.4.8.1.16
-- 1.3.6.1.4.1.34774.4.1.23.4.8.1.16
-- 1.3.6.1.4.1.34774.4.1.23.4.8.1.16
-- 1.3.6.1.4.1.34774.4.1.23.4.8.1.16
		-- 1.3.6.1.4.1.34774.4.1.23.4.8.1.16
		hwInfoLunRunningWritePolicy OBJECT-TYPE
			SYNTAX Unsigned32
			MAX-ACCESS read-only
			STATUS current
			DESCRIPTION
				"  "
			::= { hwInfoLunEntry 16 }
		
--      1.3.6.1.4.1.34774.4.1.23.4.8.1.17
-- 1.3.6.1.4.1.34774.4.1.23.4.8.1.17
-- 1.3.6.1.4.1.34774.4.1.23.4.8.1.17
-- 1.3.6.1.4.1.34774.4.1.23.4.8.1.17
-- 1.3.6.1.4.1.34774.4.1.23.4.8.1.17
		-- 1.3.6.1.4.1.34774.4.1.23.4.8.1.17
		hwInfoLunPrefetchPolicy OBJECT-TYPE
			SYNTAX Unsigned32
			MAX-ACCESS read-only
			STATUS current
			DESCRIPTION
				"  "
			::= { hwInfoLunEntry 17 }
		
--      1.3.6.1.4.1.34774.4.1.23.4.8.1.20
-- 1.3.6.1.4.1.34774.4.1.23.4.8.1.20
-- 1.3.6.1.4.1.34774.4.1.23.4.8.1.20
-- 1.3.6.1.4.1.34774.4.1.23.4.8.1.20
-- 1.3.6.1.4.1.34774.4.1.23.4.8.1.20
		-- 1.3.6.1.4.1.34774.4.1.23.4.8.1.20
		hwInfoLunPrefetchValue OBJECT-TYPE
			SYNTAX Unsigned32
			MAX-ACCESS read-only
			STATUS current
			DESCRIPTION
				"  "
			::= { hwInfoLunEntry 20 }
		
--      1.3.6.1.4.1.34774.4.1.23.4.8.1.21
-- 1.3.6.1.4.1.34774.4.1.23.4.8.1.21
-- 1.3.6.1.4.1.34774.4.1.23.4.8.1.21
-- 1.3.6.1.4.1.34774.4.1.23.4.8.1.21
-- 1.3.6.1.4.1.34774.4.1.23.4.8.1.21
		-- 1.3.6.1.4.1.34774.4.1.23.4.8.1.21
		hwInfoLunOwnerController OBJECT-TYPE
			SYNTAX OCTET STRING
			MAX-ACCESS read-only
			STATUS current
			DESCRIPTION
				"  "
			::= { hwInfoLunEntry 21 }
		
--      1.3.6.1.4.1.34774.4.1.23.4.8.1.22
-- 1.3.6.1.4.1.34774.4.1.23.4.8.1.22
-- 1.3.6.1.4.1.34774.4.1.23.4.8.1.22
-- 1.3.6.1.4.1.34774.4.1.23.4.8.1.22
-- 1.3.6.1.4.1.34774.4.1.23.4.8.1.22
		-- 1.3.6.1.4.1.34774.4.1.23.4.8.1.22
		hwInfoLunWorkController OBJECT-TYPE
			SYNTAX OCTET STRING
			MAX-ACCESS read-only
			STATUS current
			DESCRIPTION
				"  "
			::= { hwInfoLunEntry 22 }
		
--      1.3.6.1.4.1.34774.4.1.23.4.8.1.25
-- 1.3.6.1.4.1.34774.4.1.23.4.8.1.25
-- 1.3.6.1.4.1.34774.4.1.23.4.8.1.25
-- 1.3.6.1.4.1.34774.4.1.23.4.8.1.25
-- 1.3.6.1.4.1.34774.4.1.23.4.8.1.25
		-- 1.3.6.1.4.1.34774.4.1.23.4.8.1.25
		hwInfoLunIsAddToLunGroup OBJECT-TYPE
			SYNTAX Unsigned32
			MAX-ACCESS read-only
			STATUS current
			DESCRIPTION
				"  "
			::= { hwInfoLunEntry 25 }
		
--      1.3.6.1.4.1.34774.4.1.23.4.8.1.26
-- 1.3.6.1.4.1.34774.4.1.23.4.8.1.26
-- 1.3.6.1.4.1.34774.4.1.23.4.8.1.26
-- 1.3.6.1.4.1.34774.4.1.23.4.8.1.26
-- 1.3.6.1.4.1.34774.4.1.23.4.8.1.26
		-- 1.3.6.1.4.1.34774.4.1.23.4.8.1.26
		hwInfoLunDIFSwitch OBJECT-TYPE
			SYNTAX Unsigned32
			MAX-ACCESS read-only
			STATUS current
			DESCRIPTION
				"  "
			::= { hwInfoLunEntry 26 }
		
--      1.3.6.1.4.1.34774.4.1.23.4.8.1.27
-- 1.3.6.1.4.1.34774.4.1.23.4.8.1.27
-- 1.3.6.1.4.1.34774.4.1.23.4.8.1.27
-- 1.3.6.1.4.1.34774.4.1.23.4.8.1.27
-- 1.3.6.1.4.1.34774.4.1.23.4.8.1.27
		-- 1.3.6.1.4.1.34774.4.1.23.4.8.1.27
		hwInfoLunRemoteLUNWWN OBJECT-TYPE
			SYNTAX OCTET STRING
			MAX-ACCESS read-only
			STATUS current
			DESCRIPTION
				"  "
			::= { hwInfoLunEntry 27 }
		
--      1.3.6.1.4.1.34774.4.1.23.4.8.1.28
-- 1.3.6.1.4.1.34774.4.1.23.4.8.1.28
-- 1.3.6.1.4.1.34774.4.1.23.4.8.1.28
-- 1.3.6.1.4.1.34774.4.1.23.4.8.1.28
-- 1.3.6.1.4.1.34774.4.1.23.4.8.1.28
		-- 1.3.6.1.4.1.34774.4.1.23.4.8.1.28
		hwInfoLunUsageType OBJECT-TYPE
			SYNTAX Unsigned32
			MAX-ACCESS read-only
			STATUS current
			DESCRIPTION
				"  "
			::= { hwInfoLunEntry 28 }
		
--      1.6
-- 1.6
-- 1.6
-- 1.6
-- 1.6
		-- 1.6
		isoConformance OBJECT IDENTIFIER ::= { iso 6 }
		
--      1.6.1
-- 1.6.1
-- 1.6.1
-- 1.6.1
-- 1.6.1
		-- 1.6.1
		isoGroups OBJECT IDENTIFIER ::= { isoConformance 1 }
		
--      1.6.1.1
-- 1.6.1.1
-- 1.6.1.1
-- 1.6.1.1
-- 1.6.1.1
		-- 1.6.1.1
		currentObjectGroup OBJECT-GROUP
			OBJECTS { hwInfoDiskDomainID, hwInfoDiskDomainName, hwInfoDiskDomainHealthStatus, hwInfoDiskDomainRunningStatus, hwInfoDiskDomainTotalCapacity, 
				hwInfoDiskDomainFreeCapacity, hwInfoDiskDomainHotSpareCapacity, hwInfoDiskDomainUsedHotSpareCapacity, hwInfoStoragePoolID, hwInfoStoragePoolName, 
				hwInfoStoragePoolDiskDomainID, hwInfoStoragePoolHealthStatus, hwInfoStoragePoolRunningStatus, hwInfoStoragePoolTotalCapacity, hwInfoStoragePoolSubscribedCapacity, 
				hwInfoStoragePoolFreeCapacity, hwInfoStoragePoolFullThreshold, hwInfoHostID, hwInfoHostName, hwInfoHostLocation, 
				hwInfoHostHealthStatus, hwInfoHostRunningStatus, hwInfoHostOperatingSystem, hwInfoHostIPAddress, hwInfoHostModel, 
				hwInfoHostNetworkName, hwInfoHostGroupID, hwInfoHostGroupName, hwInfoLunGroupID, hwInfoLunGroupName, 
				hwInfoLunID, hwInfoLunName, hwInfoLunPoolID, hwInfoLunPoolName, hwInfoLunCapacity, 
				hwInfoLunSubscribedCapacity, hwInfoLunProtectionCapacity, hwInfoLunSectorSize, hwInfoLunHealthStatus, hwInfoLunRunningStatus, 
				hwInfoLunType, hwInfoLunIOPriority, hwInfoLunWWN, hwInfoLunExposedToInitiator, hwInfoLunWritePolicy, 
				hwInfoLunRunningWritePolicy, hwInfoLunPrefetchPolicy, hwInfoLunPrefetchValue, hwInfoLunOwnerController, hwInfoLunWorkController, 
				hwInfoLunIsAddToLunGroup, hwInfoLunDIFSwitch, hwInfoLunRemoteLUNWWN, hwInfoStoragePoolDiskDomainName, hwInfoPortGroupID, 
				hwInfoPortGroupName, hwInfoPortGroupPortList, hwInfoHostGroupHostList, hwInfoLunGroupLunList, hwInfoLunUsageType, 
				hwInfoStoragePoolProtectionCapacity }
			STATUS current
			DESCRIPTION 
				"Enter the description of the created OBJECT-GROUP."
			::= { isoGroups 1 }
		
--      1.6.2
-- 1.6.2
-- 1.6.2
-- 1.6.2
-- 1.6.2
		-- 1.6.2
		isoCompliances OBJECT IDENTIFIER ::= { isoConformance 2 }
		
--       this module
-- 1.6.2.1
-- this module
-- 1.6.2.1
-- this module
-- 1.6.2.1
-- this module
-- 1.6.2.1
-- this module
-- 1.6.2.1
-- this module
		-- 1.6.2.1
		basicCompliance MODULE-COMPLIANCE
			STATUS current
			DESCRIPTION 
				"Enter the description of the created MODULE-COMPLIANCE."
			MODULE -- this module
				MANDATORY-GROUPS { currentObjectGroup }
			::= { isoCompliances 1 }
		
	
	END

--
-- HUAWEI-STORAGE-SPACE-MIB.mib
--

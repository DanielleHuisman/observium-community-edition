--
-- HUAWEI-SWITCH-SRV-RES-TRAP-MIB.mib
-- Copyright (C) 2014 by HUAWEI TECHNOLOGIES. All rights reserved
-- Thursday, Aug 6, 2014 at 19:22:20
-- Version: V1.01

    HUAWEI-SWITCH-SRV-RES-TRAP-MIB DEFINITIONS ::= BEGIN
 
        IMPORTS
            hwDatacomm            
                FROM HUAWEI-MIB            
            OBJECT-GROUP, MODULE-COMPLIANCE, NOTIFICATION-GROUP            
                FROM SNMPv2-CONF            
            Unsigned32, OBJECT-TYPE, MODULE-IDENTITY, NOTIFICATION-TYPE            
                FROM SNMPv2-SMI;
    
    
        hwSwitchSrvResTrapMIB MODULE-IDENTITY 
            LAST-UPDATED "201408060858Z"        --  July  31, 2014 at 19:22GMT
            ORGANIZATION 
                "Huawei Technologies Co.,Ltd."
            CONTACT-INFO 
                "Huawei Industrial Base
                  Bantian, Longgang
                   Shenzhen 518129
                   People's Republic of China
                   Website: http://www.huawei.com
                   Email: support@huawei.com
                 "
           DESCRIPTION 
           "The private mib file includes the alarm  
           information of fowarding engine resouce overload."

            REVISION "201408060858Z"        --  Aug  5, 2014 at 19:22GMT
            DESCRIPTION  
            " Version 1.00."

           REVISION "201411131432Z"        --  Nov  13, 2014 at 14:32GMT
            DESCRIPTION  
            " Version 1.01."


            ::= { hwDatacomm 334 }       
    
    
--
-- Node definitions
--
    
        hwSrvResTrapObject OBJECT IDENTIFIER ::= { hwSwitchSrvResTrapMIB 1 }

        hwSrvServiceId OBJECT-TYPE
            SYNTAX INTEGER
                {
                gvrpInterface(1),
                dldpInterface(2),
                igmpSnoopingQuerier(3),
                multicastUserVlan(4),
                portSecMac(5),
                stormControlInterface(6),
                sflowInterface(7)
                }
            MAX-ACCESS accessible-for-notify
            STATUS current
            DESCRIPTION
                "The ID of service."
            ::= { hwSrvResTrapObject 1 }

        hwSrvServiceDescr OBJECT-TYPE
            SYNTAX OCTET STRING(SIZE(0..256))
            MAX-ACCESS accessible-for-notify
            STATUS current
            DESCRIPTION
                "The description of service."
            ::= { hwSrvResTrapObject 2 }


        hwSrvRecommendThreshold OBJECT-TYPE
            SYNTAX  Unsigned32
            MAX-ACCESS accessible-for-notify
            STATUS current
            DESCRIPTION
                "The recommended threshold."
            ::= { hwSrvResTrapObject 3 }

        hwSrvServiceFailDescr OBJECT-TYPE
            SYNTAX OCTET STRING(SIZE(0..256))
            MAX-ACCESS accessible-for-notify
            STATUS current
            DESCRIPTION
                "The description of service failed."
            ::= { hwSrvResTrapObject 4 }


        hwSrvResTraps OBJECT IDENTIFIER ::= { hwSwitchSrvResTrapMIB 2 }
        
        hwSrvSeviceResTrap OBJECT IDENTIFIER ::= { hwSrvResTraps 1 }

        hwSrvServiceExceedThreshould NOTIFICATION-TYPE
            OBJECTS { hwSrvServiceId, hwSrvServiceDescr, hwSrvRecommendThreshold }
            STATUS current
            DESCRIPTION 
                "The service exceed the recommended threshold."
            ::= { hwSrvSeviceResTrap 1 }

        hwSrvServiceExceedThreshouldResume NOTIFICATION-TYPE
            OBJECTS { hwSrvServiceId, hwSrvServiceDescr, hwSrvRecommendThreshold }
            STATUS current
            DESCRIPTION 
                "The service fall below the recommended threshold."
            ::= { hwSrvSeviceResTrap 2 }

        hwSrvServiceConfigFailed NOTIFICATION-TYPE
            OBJECTS { hwSrvServiceId, hwSrvServiceDescr, hwSrvServiceFailDescr }
            STATUS current
            DESCRIPTION 
                "The service config failed."
            ::= { hwSrvSeviceResTrap 3 }


        -- 1.3.6.1.4.1.2011.5.25.227.3
        hwSrvResTrapConformance OBJECT IDENTIFIER ::= { hwSwitchSrvResTrapMIB 100 }
        
        -- 1.3.6.1.4.1.2011.5.25.227.3.1
        hwSrvResTrapCompliances OBJECT IDENTIFIER ::= { hwSrvResTrapConformance 1 }
        
        -- 1.3.6.1.4.1.2011.5.25.227.3.1.1
        hwSrvResTrapCompliance MODULE-COMPLIANCE
            STATUS current
            DESCRIPTION 
                "Compliance statement for agents that provide full support for hwSrvResTrapMIB."
            MODULE -- this module
                MANDATORY-GROUPS { hwSrvResObjectGroup, hwSrvResTrapGroup }
            ::= { hwSrvResTrapCompliances 1 }
        
        -- 1.3.6.1.4.1.2011.5.25.227.3.2
        hwSrvResTrapGroups OBJECT IDENTIFIER ::= { hwSrvResTrapConformance 2 }
        
        -- 1.3.6.1.4.1.2011.5.25.227.3.2.1
        hwSrvResObjectGroup OBJECT-GROUP
            OBJECTS { hwSrvServiceId, hwSrvServiceDescr, hwSrvRecommendThreshold, hwSrvServiceFailDescr }
            STATUS current
            DESCRIPTION 
                "Group for base trap objects."
            ::= { hwSrvResTrapGroups 1 }
        
        -- 1.3.6.1.4.1.2011.5.25.227.3.2.2
        hwSrvResTrapGroup NOTIFICATION-GROUP
            NOTIFICATIONS { hwSrvServiceExceedThreshould, hwSrvServiceExceedThreshouldResume, hwSrvServiceConfigFailed
            }
            STATUS current
            DESCRIPTION 
                "Group for all traps."
            ::= { hwSrvResTrapGroups 2 }
 
    
    END

--
-- HUAWEI-SRV-RES-TRAP-MIB.mib
--

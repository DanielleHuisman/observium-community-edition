-- =================================================================
-- Copyright (C) 2021 by  HUAWEI TECHNOLOGIES. All rights reserved
-- 
-- Description: HUAWEI TWAMP MIB. 
-- Reference:
-- Version:     V1.27
-- History:
--              V1.00 luzhihao 2014.6.7,publish
--              V1.01 maotiantian 2014.10.16, modify 
--              V1.02 maotiantian 2015.1.9, modify 
--              V1.03 huchao      2015.2.3, modify 
--              V1.04 lizhaohui      2015.5.30, modify 
--              V1.05 lizhaohui      2015.6.30, modify 
--              V1.06 lizhaohui      2015.7.28, modify 
--              V1.07 songyingjuan 2015.8.13, modify 
--              V1.08 yangjiannai 2016.4.18, modify
--              V1.09 yangjiannai 2016.7.11, modify  
--              V1.10 zongchao       2016.7.29, modify
--              V1.11 jizhiqing       2016.11.24, modify
--              V1.12 liweitao      2017.3.12, modify
--              V1.13 liweitao      2017.3.20, modify
--              V1.14 jizhiqing     2017.6.15, modify 
--              V1.17 xuhui         2018.8.15, modify  
--              V1.22 xuxin         2019.6.10, modify
--              V1.23 wuliujuan     2019.9.23, modify
--              V1.24 xulaijin      2020.9.28, modify
--              V1.25 huangjinqin   2020.12.28, modify
--              V1.26 xulaijin      2021.2.1, modify
--              V1.27 xulaijin      2020.2.2, modify
-- =================================================================

	HUAWEI-TWAMP-MIB DEFINITIONS ::= BEGIN
 
		IMPORTS
			hwDatacomm			
				FROM HUAWEI-MIB			
			InetAddressType, InetAddress
				FROM INET-ADDRESS-MIB			
			VlanIdOrNone			
				FROM Q-BRIDGE-MIB			
            ifIndex, InterfaceIndex, InterfaceIndexOrZero, ifDescr
                FROM IF-MIB
            OBJECT-GROUP, MODULE-COMPLIANCE, NOTIFICATION-GROUP		
				FROM SNMPv2-CONF			
			mib-2, Integer32, Gauge32, Counter64, OBJECT-TYPE, 
			MODULE-IDENTITY, NOTIFICATION-TYPE, Unsigned32			
				FROM SNMPv2-SMI			
			DisplayString, RowStatus, DateAndTime			
				FROM SNMPv2-TC;
	
		hwTwampMib MODULE-IDENTITY 
			LAST-UPDATED "202102021200Z"	
			ORGANIZATION 
				"Huawei Technologies Co.,Ltd."
			CONTACT-INFO 
				"Huawei Industrial Base
				Bantian, Longgang
				Shenzhen 518129
				People's Republic of China
				Website: http://www.huawei.com
				Email: support@huawei.com
     		"
            DESCRIPTION
    "HUAWEI TWAMP funcion."
	
			REVISION "202102021200Z"
              DESCRIPTION
    "Add session information of hwTwampTwoWayDelayExceed, hwTwampTwoWayDelayRecovery,
						        hwTwampTwoWayJitterExceed, hwTwampTwoWayJitterRecovery,
	                            hwTwampTwoWayLocExceed, hwTwampTwoWayLocRecovery,
						        hwTwampTwoWayLossRatioExceed, hwTwampTwoWayLossRatioRecovery,
						        hwTwampMemTwoWayDelayExceed, hwTwampMemTwoWayDelayRecovery,
						        hwTwampMemTwoWayJitterExceed, hwTwampMemTwoWayJitterRecovery,
                                hwTwampMemTwoWayLocExceed, hwTwampMemTwoWayLocRecovery,
						        hwTwampMemTwoWayLossRatioExceed, hwTwampMemTwoWayLossRatioRecovery for this mib."
 
            REVISION "202102011200Z"
              DESCRIPTION
    "Add hwTwampControlSessionNumExceed and hwTwampControlSessionNumRecovery nodes, and delete session information of 
	                            hwTwampTwoWayDelayExceed, hwTwampTwoWayDelayRecovery,
						        hwTwampTwoWayJitterExceed, hwTwampTwoWayJitterRecovery,
	                            hwTwampTwoWayLocExceed, hwTwampTwoWayLocRecovery,
						        hwTwampTwoWayLossRatioExceed, hwTwampTwoWayLossRatioRecovery,
						        hwTwampMemTwoWayDelayExceed, hwTwampMemTwoWayDelayRecovery,
						        hwTwampMemTwoWayJitterExceed, hwTwampMemTwoWayJitterRecovery,
                                hwTwampMemTwoWayLocExceed, hwTwampMemTwoWayLocRecovery,
						        hwTwampMemTwoWayLossRatioExceed, hwTwampMemTwoWayLossRatioRecovery node for this mib."

	
			REVISION "202012281022Z"
              DESCRIPTION
    "Add session information of hwTwampTwoWayDelayExceed, hwTwampTwoWayDelayRecovery,
						        hwTwampTwoWayJitterExceed, hwTwampTwoWayJitterRecovery,
	                            hwTwampTwoWayLocExceed, hwTwampTwoWayLocRecovery,
						        hwTwampTwoWayLossRatioExceed, hwTwampTwoWayLossRatioRecovery,
						        hwTwampMemTwoWayDelayExceed, hwTwampMemTwoWayDelayRecovery,
						        hwTwampMemTwoWayJitterExceed, hwTwampMemTwoWayJitterRecovery,
                                hwTwampMemTwoWayLocExceed, hwTwampMemTwoWayLocRecovery,
						        hwTwampMemTwoWayLossRatioExceed, hwTwampMemTwoWayLossRatioRecovery for this mib."

	        REVISION "202009281200Z"
             DESCRIPTION 
    "Add hwTwampMemTwoWayLossRatioExceed, hwTwampMemTwoWayLossRatioRecovery, 
         hwTwampMemTwoWayDelayExceed, hwTwampMemTwoWayDelayRecovery, 
         hwTwampMemTwoWayJitterExceed, hwTwampMemTwoWayJitterRecovery,
         hwTwampMemTwoWayLocExceed, hwTwampMemTwoWayLocRecovery,
         hwTwampResponderSessionNumExceed and hwTwampResponderSessionNumRecovery node for this mib."
		 
			 REVISION "201909231655Z"
                DESCRIPTION
    "Modify  hwTwampNotSupportServiceUnderIntf and hwTwampNotSupportServiceUnderIntfRecovery node for this mib ."

			 REVISION "201906101655Z"
              DESCRIPTION 
    "Add hwTwampSenderBindingIfIndex to node for this mib."

			 REVISION "201905291655Z"
              DESCRIPTION 
    "Add hwTwampNotSupportServiceUnderIntf and hwTwampNotSupportServiceUnderIntfRecovery node for this mib."

	         REVISION "201811231655Z"
              DESCRIPTION 
    "Modify  the min num of hwTwampSenderPadding nodes for this mib."

		     REVISION "201811061655Z" 
              DESCRIPTION 
    "Modify  the min num of hwTwampSenderPadding nodes for this mib."

		    REVISION "201808251426Z"	               
               DESCRIPTION 
	"Modify hwTwampResponderId range for this mib."

                          REVISION "201808151012Z" 
               DESCRIPTION 
	 "Add hwTwampSenderRegularAdminTable to node for this mib."

                                      REVISION "201711201419Z" 
               DESCRIPTION 
	 "Add hwTwampResponderAntiLoop to node for this mib."
                                        REVISION "201708171959Z" 
            DESCRIPTION 
                "Modify english description for this mib."
                                        REVISION "201706152047Z" 
			DESCRIPTION 
				"HUAWEI TWAMP funcion."
                                        REVISION "201703201655Z" 
            DESCRIPTION 
                "Change hwTwampResetStatisticsRowStatus to node for this mib."
                                        REVISION "201703121655Z" 
            DESCRIPTION 
                "Add hwTwampResetStatisticsTable, hwTwampResetStatisticsEntry and hwTwampResetStatisticsRowStatus node for this mib."
                                        REVISION "201611241726Z" 
            DESCRIPTION 
                "Add hwTwampSenderSessionNumExceed and hwTwampSenderSessionNumRecovery node for this mib."

                                        REVISION "201607291015Z" 
            DESCRIPTION 
                "Add hwTwampSenderMultiFlowEn node for this mib."

                                        REVISION "201607111655Z" 
            DESCRIPTION 
                "Modify  the description of hwTwampSenderTwoWayLossValue node for this mib."

                                        REVISION "201604181655Z" 
            DESCRIPTION 
                "Modify  the value range of hwTwampResponderSourceUDPPort, hwTwampResponderDestUDPPort, hwTwampSenderLocalUDPPort and hwTwampSenderRemoteUDPPort nodes for this mib."

		    REVISION "201508131655Z" 
            DESCRIPTION 
                "Modify  the description of hwTwampResponderDestUDPPort and hwTwampSenderRemoteUDPPort nodes for this mib."

		    REVISION "201507281655Z" 
            DESCRIPTION 
                "Modify  the datatype of hwTwampSenderPaddingType nodes for this mib."

		    REVISION "201506261655Z" 
            DESCRIPTION 
                "Add hwTwampSenderPaddingType hwTwampSenderTwoWayErrorCount hwTwampSenderTwoWayTotalErrorCount nodes for this mib."

		    REVISION "201505301655Z" 
            DESCRIPTION 
                "Add hwTwampSenderTwoWayTotalSentCount hwTwampSenderTwoWayTotalLossValue nodes for this mib.
				 Add interval00us for this mib."
				
	
                                           REVISION "201502031640Z" 
            DESCRIPTION 
                "Add hwTwampTwoWayLossAlarmTable hwTwampTwoWayDelayAlarmTable hwTwampTwoWayJitterAlarmTable nodes for this mib.
				 Add hwTwampTraps and hwTwampResponderIfIndex node for this mib.
				 Add four type alarm node for this mib."
				
		    REVISION "201501091658Z" 
            DESCRIPTION 
                "Add units for the hwTwampSenderPadding at 2015-01-09." 

            REVISION "201410161621Z"
		    DESCRIPTION
				"Modify description of hwTwampSenderAdminContinual at 2014-10-16.
                 Modify description of hwTwampSenderAdminDuration and hwTwampSenderAdminPacketCount at 2014-10-16."

            REVISION "201409251433Z"
		    DESCRIPTION
				"Add three nodes for this mib."

            REVISION "201409151606Z"
		    DESCRIPTION
				"Deleted the unnecessary default value."

			REVISION "201405131606Z"
			DESCRIPTION
				"Create file. on 2014-05-13."
                                                
			::= { hwTwamp 1 }

		
	
	
--
-- Node definitions
--
-- #############################################################################
-- 
--  OBJECT IDENTIFIER Statements
-- 
-- #############################################################################
-- 1.3.6.1.4.1.2011.5.25.333
		hwTwamp OBJECT IDENTIFIER ::= { hwDatacomm 333 }
		
--  OID is not approved
-- 1.3.6.1.4.1.2011.5.25.333.1.1
		hwTwampController OBJECT IDENTIFIER ::= { hwTwampMib 1 }
		
-- 1.3.6.1.4.1.2011.5.25.333.1.1.1
		hwTwampControllerClientEnable OBJECT-TYPE
			SYNTAX INTEGER
				{
				enable(1),
				disable(2)
				}
			MAX-ACCESS read-write
			STATUS current
			DESCRIPTION
				"The value of this object identifies whether the initiator client is enabled."
			::= { hwTwampController 1 }
		
-- 1.3.6.1.4.1.2011.5.25.333.1.1.2
		hwTwampControllerSenderEnable OBJECT-TYPE
			SYNTAX INTEGER
				{
				enable(1),
				disable(2)
				}
			MAX-ACCESS read-write
			STATUS current
			DESCRIPTION
				"The value of this object identifies whether the initiator sender is enabled."
			::= { hwTwampController 2 }
		
--             Controller test-session Node definitions
-- 1.3.6.1.4.1.2011.5.25.333.1.1.3
		hwTwampSenderTable OBJECT-TYPE
			SYNTAX SEQUENCE OF HwTwampSenderEntry
			MAX-ACCESS not-accessible
			STATUS current
			DESCRIPTION
				"This object indicates to create a TWAMP-light test instance table."
			::= { hwTwampController 3 }
		
-- 1.3.6.1.4.1.2011.5.25.333.1.1.3.1
		hwTwampSenderEntry OBJECT-TYPE
			SYNTAX HwTwampSenderEntry
			MAX-ACCESS not-accessible
			STATUS current
			DESCRIPTION
				"This object indicates to create a TWAMP-light test instance entry."
			INDEX { hwTwampSenderId }
			::= { hwTwampSenderTable 1 }
		
		HwTwampSenderEntry ::=
			SEQUENCE { 
				hwTwampSenderId
					Integer32,
				hwTwampSenderLocalIpAddressType
					InetAddressType,
				hwTwampSenderLocalIpAddress
					InetAddress,
				hwTwampSenderRemoteIpAddressType
					InetAddressType,
				hwTwampSenderRemoteIpAddress
					InetAddress,
				hwTwampSenderLocalUDPPort
					Integer32,
				hwTwampSenderRemoteUDPPort
					Integer32,
				hwTwampSenderVrfName
					DisplayString,
				hwTwampSenderDSCP
					Integer32,
				hwTwampSenderPadding
					Integer32,
				hwTwampSenderDescription
					DisplayString,
				hwTwampSenderRowStatus
					RowStatus,
				hwTwampSenderPaddingType
					Unsigned32,
				hwTwampSenderMultiFlowEn
				    INTEGER,
				hwTwampSenderBindingIfIndex
				    InterfaceIndexOrZero
			 }

-- 1.3.6.1.4.1.2011.5.25.333.1.1.3.1.1
		hwTwampSenderId OBJECT-TYPE
			SYNTAX Integer32 (1..8192)
			MAX-ACCESS not-accessible
			STATUS current
			DESCRIPTION
				"This object indicates the index of a TWAMP-light test instance."
			::= { hwTwampSenderEntry 1 }
		

-- 1.3.6.1.4.1.2011.5.25.333.1.1.3.1.2
		hwTwampSenderLocalIpAddressType OBJECT-TYPE
			SYNTAX InetAddressType
			MAX-ACCESS read-create
			STATUS current
			DESCRIPTION
				"This object indicates the sender's IP address type in a TWAMP-light test instance."
			::= { hwTwampSenderEntry 2 }
		
-- 1.3.6.1.4.1.2011.5.25.333.1.1.3.1.3
		hwTwampSenderLocalIpAddress OBJECT-TYPE
			SYNTAX InetAddress
			MAX-ACCESS read-create
			STATUS current
			DESCRIPTION
				"This object indicates the sender's IP address in a TWAMP-light test instance."
			::= { hwTwampSenderEntry 3 }
		
-- 1.3.6.1.4.1.2011.5.25.333.1.1.3.1.4
		hwTwampSenderRemoteIpAddressType OBJECT-TYPE
			SYNTAX InetAddressType
			MAX-ACCESS read-create
			STATUS current
			DESCRIPTION
				"This object indicates the reflector's IP address type in a TWAMP-light test instance."
			::= { hwTwampSenderEntry 4 }

-- 1.3.6.1.4.1.2011.5.25.333.1.1.3.1.5
		hwTwampSenderRemoteIpAddress OBJECT-TYPE
			SYNTAX InetAddress
			MAX-ACCESS read-create
			STATUS current
			DESCRIPTION
				"This object indicates the reflector's IP address in a TWAMP-light test instance."
			::= { hwTwampSenderEntry 5 }

-- 1.3.6.1.4.1.2011.5.25.333.1.1.3.1.6
		hwTwampSenderLocalUDPPort OBJECT-TYPE
			SYNTAX Integer32 (862..863 | 1025..65535)
			MAX-ACCESS read-create
			STATUS current
			DESCRIPTION
				"This object indicates the sender's UDP port of a TWAMP-light test instance."
			::= { hwTwampSenderEntry 6 }

-- 1.3.6.1.4.1.2011.5.25.333.1.1.3.1.7
		hwTwampSenderRemoteUDPPort OBJECT-TYPE
			SYNTAX Integer32 (862..863 | 1025..65535)
			MAX-ACCESS read-create
			STATUS current
			DESCRIPTION
				"This object indicates the reflector's UDP port of a TWAMP-light test instance."
			::= { hwTwampSenderEntry 7 }
		
-- 1.3.6.1.4.1.2011.5.25.333.1.1.3.1.8
		hwTwampSenderVrfName OBJECT-TYPE
			SYNTAX DisplayString (SIZE (0..31))
			MAX-ACCESS read-create
			STATUS current
			DESCRIPTION
				"This object indicates the VPN name of a TWAMP-light test instance."
			::= { hwTwampSenderEntry 8 }

-- 1.3.6.1.4.1.2011.5.25.333.1.1.3.1.9
		hwTwampSenderDSCP OBJECT-TYPE
			SYNTAX Integer32 (0..63)
			MAX-ACCESS read-create
			STATUS current
			DESCRIPTION
				"This object indicates the DSCP value of a TWAMP-light test instance."
			DEFVAL { 0 }
			::= { hwTwampSenderEntry 9 }
		
-- 1.3.6.1.4.1.2011.5.25.333.1.1.3.1.10
		hwTwampSenderPadding OBJECT-TYPE
			SYNTAX Integer32 (32..8500)
			UNITS "octets"
			MAX-ACCESS read-create
			STATUS current
			DESCRIPTION
				"This object indicates the padding value of a TWAMP-light test instance."
			DEFVAL { 128 }
			::= { hwTwampSenderEntry 10 }

-- 1.3.6.1.4.1.2011.5.25.333.1.1.3.1.11
		hwTwampSenderDescription OBJECT-TYPE
			SYNTAX DisplayString (SIZE (0 | 3..32))
			MAX-ACCESS read-create
			STATUS current
			DESCRIPTION
				"This object indicates the description of a TWAMP-light test instance."
			::= { hwTwampSenderEntry 11 }
		
-- 1.3.6.1.4.1.2011.5.25.333.1.1.1.1.99
		hwTwampSenderRowStatus OBJECT-TYPE
			SYNTAX RowStatus
			MAX-ACCESS read-create
			STATUS current
			DESCRIPTION
				"This object indicates the row status of this entry."
			::= { hwTwampSenderEntry 99 }

-- 1.3.6.1.4.1.2011.5.25.333.1.1.3.1.100
		hwTwampSenderPaddingType OBJECT-TYPE
			SYNTAX Unsigned32
			MAX-ACCESS read-create
			STATUS current
			DESCRIPTION
				"This object indicates the padding-type value of a TWAMP-light test instance."
			DEFVAL { 0 }
			::= { hwTwampSenderEntry 100 }

-- 1.3.6.1.4.1.2011.5.25.333.1.1.3.1.101
		hwTwampSenderMultiFlowEn OBJECT-TYPE
			SYNTAX INTEGER
				{
				enable(1),
				disable(0)
				}
			MAX-ACCESS read-create
			STATUS current
			DESCRIPTION
				"This object indicates the multi-flow enable flag of a TWAMP-light test instance."
			DEFVAL { disable }
			::= { hwTwampSenderEntry 101 }
			
-- 1.3.6.1.4.1.2011.5.25.333.1.1.3.1.102
		hwTwampSenderBindingIfIndex OBJECT-TYPE
			SYNTAX InterfaceIndexOrZero
			MAX-ACCESS read-create
			STATUS current
			DESCRIPTION
				"
				This object indicates the interface bound to the test session.
				"
			DEFVAL { 0 }
			::= { hwTwampSenderEntry 102 }

-- Controller test-session admin state Node definitions
-- 1.3.6.1.4.1.2011.5.25.333.1.1.4
		hwTwampSenderAdminTable OBJECT-TYPE
			SYNTAX SEQUENCE OF HwTwampSenderAdminEntry
			MAX-ACCESS not-accessible
			STATUS current
			DESCRIPTION
				"This object indicates to start a TWAMP-light test instance table."
			::= { hwTwampController 4 }

-- 1.3.6.1.4.1.2011.5.25.333.1.1.4.1
		hwTwampSenderAdminEntry OBJECT-TYPE
			SYNTAX HwTwampSenderAdminEntry
			MAX-ACCESS not-accessible
			STATUS current
			DESCRIPTION
				"This object indicates to start a TWAMP-light test instance entry."
			INDEX { hwTwampSenderId }
			::= { hwTwampSenderAdminTable 1 }
		
		HwTwampSenderAdminEntry ::=
			SEQUENCE { 
				hwTwampSenderAdminContinual
					INTEGER,
				hwTwampSenderAdminDuration
					Integer32,
				hwTwampSenderAdminPacketCount
					Integer32,
				hwTwampSenderAdminPeriod
					INTEGER,
				hwTwampSenderAdminTimeOut
					Integer32,
				hwTwampSenderAdminRowStatus
					RowStatus
			 }

-- 1.3.6.1.4.1.2011.5.25.333.1.1.4.1.1
		hwTwampSenderAdminContinual OBJECT-TYPE
			SYNTAX INTEGER
				{
				true(1),
				false(2)
				}
			MAX-ACCESS read-create
			STATUS current
			DESCRIPTION
				"This object indicates the continuous session."
			::= { hwTwampSenderAdminEntry 1 }
		
-- 1.3.6.1.4.1.2011.5.25.333.1.1.4.1.2
		hwTwampSenderAdminDuration OBJECT-TYPE
			SYNTAX Integer32 (0 | 60..300)
			UNITS "seconds"
			MAX-ACCESS read-create
			STATUS current
			DESCRIPTION
				"The value of this object identifies the session duration."
			::= { hwTwampSenderAdminEntry 2 }

-- 1.3.6.1.4.1.2011.5.25.333.1.1.4.1.3
		hwTwampSenderAdminPacketCount OBJECT-TYPE
			SYNTAX Integer32 (0 | 100..30000)
			MAX-ACCESS read-create
			STATUS current
			DESCRIPTION
				"The value of this object identifies the number of packets."

			::= { hwTwampSenderAdminEntry 3 }

-- 1.3.6.1.4.1.2011.5.25.333.1.1.4.1.4
		hwTwampSenderAdminPeriod OBJECT-TYPE
			SYNTAX INTEGER
				{
				interval10ms(1),
				interval100ms(2),
				interval1s(3),
				interval30s(4),
				interval100us(5)
				}
			MAX-ACCESS read-create
			STATUS current
			DESCRIPTION
				"The value of this object identifies the packet period."
			DEFVAL { interval100ms }
			::= { hwTwampSenderAdminEntry 4 }

-- 1.3.6.1.4.1.2011.5.25.333.1.1.4.1.5
		hwTwampSenderAdminTimeOut OBJECT-TYPE
			SYNTAX Integer32 (1..10)
			UNITS "seconds"
			MAX-ACCESS read-create
			STATUS current
			DESCRIPTION
				"The value of this object identifies the packet timeout period."
			DEFVAL { 5 }
			::= { hwTwampSenderAdminEntry 5 }
		
-- 1.3.6.1.4.1.2011.5.25.333.1.1.4.1.99
		hwTwampSenderAdminRowStatus OBJECT-TYPE
			SYNTAX RowStatus
			MAX-ACCESS read-create
			STATUS current
			DESCRIPTION
				"This object indicates the row status of this entry."
			::= { hwTwampSenderAdminEntry 99 }
		
-- Controller test-session operating state Node definitions
-- 1.3.6.1.4.1.2011.5.25.333.1.1.5
		hwTwampSenderOperTable OBJECT-TYPE
			SYNTAX SEQUENCE OF HwTwampSenderOperEntry
			MAX-ACCESS not-accessible
			STATUS current
			DESCRIPTION
				"This object indicates the running status table of a TWAMP-light test instance."
			::= { hwTwampController 5 }
		
-- 1.3.6.1.4.1.2011.5.25.333.1.1.5.1
		hwTwampSenderOperEntry OBJECT-TYPE
			SYNTAX HwTwampSenderOperEntry
			MAX-ACCESS not-accessible
			STATUS current
			DESCRIPTION
				"This object indicates the running status entry of a TWAMP-light test instance."
			INDEX { hwTwampSenderId }
			::= { hwTwampSenderOperTable 1 }
		
		HwTwampSenderOperEntry ::=
			SEQUENCE { 
				hwTwampSenderOperState
					INTEGER,
				hwTwampSenderOperType
					INTEGER,
				hwTwampSenderOperInactiveReason
					INTEGER,
				hwTwampSenderOperLastStartTime
					DateAndTime,
				hwTwampSenderOperLastStopTime
					DateAndTime,
				hwTwampSenderOperTxCount
					Counter64,
				hwTwampSenderOperRxCount
					Counter64,
				hwTwampSenderOperDiscardCount
					Counter64,
				hwTwampSenderOperSequence
					Gauge32
			 }

-- 1.3.6.1.4.1.2011.5.25.333.1.1.5.1.1
		hwTwampSenderOperState OBJECT-TYPE
			SYNTAX INTEGER
				{
				inactive(1),
				active(2)
				}
			MAX-ACCESS read-only
			STATUS current
			DESCRIPTION
				"This object indicates the running status of a TWAMP-light test instance."
			::= { hwTwampSenderOperEntry 1 }
		
-- 1.3.6.1.4.1.2011.5.25.333.1.1.5.1.2
		hwTwampSenderOperType OBJECT-TYPE
			SYNTAX INTEGER
				{
				continual(1),
				onDemand(2),
                                                                             regular(3)
				}
			MAX-ACCESS read-only
			STATUS current
			DESCRIPTION
				"This object indicates the operating type of a TWAMP-light test instance."
			::= { hwTwampSenderOperEntry 2 }

-- 1.3.6.1.4.1.2011.5.25.333.1.1.5.1.3
		hwTwampSenderOperInactiveReason OBJECT-TYPE
			SYNTAX INTEGER
				{
				notStart(1),
				absenceResource(2),
				boardFault(3),
				null(99)
				}
			MAX-ACCESS read-only
			STATUS current
			DESCRIPTION
				"This object indicates the reason why a TWAMP-light test instance is not started."
			::= { hwTwampSenderOperEntry 3 }
		


-- 1.3.6.1.4.1.2011.5.25.333.1.1.5.1.4
		hwTwampSenderOperLastStartTime OBJECT-TYPE
			SYNTAX DateAndTime
			MAX-ACCESS read-only
			STATUS current
			DESCRIPTION
				"This object indicates the latest time a TWAMP-light test instance started."
			::= { hwTwampSenderOperEntry 4 }
		
-- 1.3.6.1.4.1.2011.5.25.333.1.1.5.1.5
		hwTwampSenderOperLastStopTime OBJECT-TYPE
			SYNTAX DateAndTime
			MAX-ACCESS read-only
			STATUS current
			DESCRIPTION
				"This object indicates the latest time a TWAMP-light test instance stopped."
			::= { hwTwampSenderOperEntry 5 }
		
-- 1.3.6.1.4.1.2011.5.25.333.1.1.5.1.6
		hwTwampSenderOperTxCount OBJECT-TYPE
			SYNTAX Counter64
			MAX-ACCESS read-only
			STATUS current
			DESCRIPTION
				"This object indicates the number of packets that a TWAMP-light test instance sends."
			::= { hwTwampSenderOperEntry 6 }
		
-- 1.3.6.1.4.1.2011.5.25.333.1.1.5.1.7
		hwTwampSenderOperRxCount OBJECT-TYPE
			SYNTAX Counter64
			MAX-ACCESS read-only
			STATUS current
			DESCRIPTION
				"This object indicates the number of packets that a TWAMP-light test instance receives."
			::= { hwTwampSenderOperEntry 7 }
		
-- 1.3.6.1.4.1.2011.5.25.333.1.1.5.1.8
		hwTwampSenderOperDiscardCount OBJECT-TYPE
			SYNTAX Counter64
			MAX-ACCESS read-only
			STATUS current
			DESCRIPTION
				"This object indicates the number of packets that a TWAMP-light test instance drops."
			::= { hwTwampSenderOperEntry 8 }
		
-- 1.3.6.1.4.1.2011.5.25.333.1.1.5.1.9
		hwTwampSenderOperSequence OBJECT-TYPE
			SYNTAX Gauge32
			MAX-ACCESS read-only
			STATUS current
			DESCRIPTION
				"This object indicates the sequence number of a TWAMP-light test instance."
			::= { hwTwampSenderOperEntry 9 }
		
-- Controller test-session two-way delay measure Node definitions
-- 1.3.6.1.4.1.2011.5.25.333.1.1.6
		hwTwampSenderTwoWayDelayTable OBJECT-TYPE
			SYNTAX SEQUENCE OF HwTwampSenderTwoWayDelayEntry
			MAX-ACCESS not-accessible
			STATUS current
			DESCRIPTION
				"This object indicates a two-way delay measurement table."
			::= { hwTwampController 6 }
		
-- 1.3.6.1.4.1.2011.5.25.333.1.1.6.1
		hwTwampSenderTwoWayDelayEntry OBJECT-TYPE
			SYNTAX HwTwampSenderTwoWayDelayEntry
			MAX-ACCESS not-accessible
			STATUS current
			DESCRIPTION
				"This object indicates a two-way delay measurement entry."
			INDEX { hwTwampSenderId, hwTwampSenderTwoWayDelaySeq }
			::= { hwTwampSenderTwoWayDelayTable 1 }
		
		HwTwampSenderTwoWayDelayEntry ::=
			SEQUENCE { 
				hwTwampSenderTwoWayDelaySeq
					Gauge32,
				hwTwampSenderTwoWayDelayAvgValue
					Integer32,
				hwTwampSenderTwoWayDelayMaxValue
					Integer32,
				hwTwampSenderTwoWayDelayMinValue
					Integer32,
				hwTwampSenderTwoWayDelayAvgVariation
					Integer32,
				hwTwampSenderTwoWayDelayMaxVariation
					Integer32,
				hwTwampSenderTwoWayDelayMinVariation
					Integer32,
				hwTwampSenderTwoWayDelayTxAvgVariation
					Integer32,
				hwTwampSenderTwoWayDelayTxMaxVariation
					Integer32,
				hwTwampSenderTwoWayDelayTxMinVariation
					Integer32,
				hwTwampSenderTwoWayDelayRxAvgVariation
					Integer32,
				hwTwampSenderTwoWayDelayRxMaxVariation
					Integer32,
				hwTwampSenderTwoWayDelayRxMinVariation
					Integer32
			 }

-- 1.3.6.1.4.1.2011.5.25.333.1.1.6.1.1
		hwTwampSenderTwoWayDelaySeq OBJECT-TYPE
			SYNTAX Gauge32 (1..4294967295)
			MAX-ACCESS not-accessible
			STATUS current
			DESCRIPTION
				"This object indicates the sequence number of a two-way delay TWAMP-light test instance."
			::= { hwTwampSenderTwoWayDelayEntry 1 }
		
-- 1.3.6.1.4.1.2011.5.25.333.1.1.6.1.2
		hwTwampSenderTwoWayDelayAvgValue OBJECT-TYPE
			SYNTAX Integer32
			UNITS "microseconds"
			MAX-ACCESS read-only
			STATUS current
			DESCRIPTION
				"The value of this object identifies the average value of the dual-ended delay."
			::= { hwTwampSenderTwoWayDelayEntry 2 }

-- 1.3.6.1.4.1.2011.5.25.333.1.1.6.1.3
		hwTwampSenderTwoWayDelayMaxValue OBJECT-TYPE
			SYNTAX Integer32
			UNITS "microseconds"
			MAX-ACCESS read-only
			STATUS current
			DESCRIPTION
				"The value of this object identifies the maximum value of the dual-ended delay."
			::= { hwTwampSenderTwoWayDelayEntry 3 }
		
-- 1.3.6.1.4.1.2011.5.25.333.1.1.6.1.4
		hwTwampSenderTwoWayDelayMinValue OBJECT-TYPE
			SYNTAX Integer32
			UNITS "microseconds"
			MAX-ACCESS read-only
			STATUS current
			DESCRIPTION
				"The value of this object identifies the minimum value of the dual-ended delay."
			::= { hwTwampSenderTwoWayDelayEntry 4 }

-- 1.3.6.1.4.1.2011.5.25.333.1.1.6.1.5
		hwTwampSenderTwoWayDelayAvgVariation OBJECT-TYPE
			SYNTAX Integer32
			UNITS "microseconds"
			MAX-ACCESS read-only
			STATUS current
			DESCRIPTION
				"The value of this object identifies the average value of the dual-ended delay."
			::= { hwTwampSenderTwoWayDelayEntry 5 }
		
-- 1.3.6.1.4.1.2011.5.25.333.1.1.6.1.6
		hwTwampSenderTwoWayDelayMaxVariation OBJECT-TYPE
			SYNTAX Integer32
			UNITS "microseconds"
			MAX-ACCESS read-only
			STATUS current
			DESCRIPTION
				"The value of this object identifies the maximum dual-ended delay change."
			::= { hwTwampSenderTwoWayDelayEntry 6 }
		
-- 1.3.6.1.4.1.2011.5.25.333.1.1.6.1.7
		hwTwampSenderTwoWayDelayMinVariation OBJECT-TYPE
			SYNTAX Integer32
			UNITS "microseconds"
			MAX-ACCESS read-only
			STATUS current
			DESCRIPTION
				"The value of this object identifies the minimum dual-ended delay change."
			::= { hwTwampSenderTwoWayDelayEntry 7 }

-- 1.3.6.1.4.1.2011.5.25.333.1.1.6.1.8
		hwTwampSenderTwoWayDelayTxAvgVariation OBJECT-TYPE
			SYNTAX Integer32
			UNITS "microseconds"
			MAX-ACCESS read-only
			STATUS current
			DESCRIPTION
				"The value of this object identifies the average dual-ended delay change of the sender."
			::= { hwTwampSenderTwoWayDelayEntry 8 }

-- 1.3.6.1.4.1.2011.5.25.333.1.1.6.1.9
		hwTwampSenderTwoWayDelayTxMaxVariation OBJECT-TYPE
			SYNTAX Integer32
			UNITS "microseconds"
			MAX-ACCESS read-only
			STATUS current
			DESCRIPTION
				"The value of this object identifies the maximum dual-ended delay change of the sender."
			::= { hwTwampSenderTwoWayDelayEntry 9 }
		
-- 1.3.6.1.4.1.2011.5.25.333.1.1.6.1.10
		hwTwampSenderTwoWayDelayTxMinVariation OBJECT-TYPE
			SYNTAX Integer32
			UNITS "microseconds"
			MAX-ACCESS read-only
			STATUS current
			DESCRIPTION
				"The value of this object identifies the minimum dual-ended delay change of the sender."
			::= { hwTwampSenderTwoWayDelayEntry 10 }

-- 1.3.6.1.4.1.2011.5.25.333.1.1.6.1.11
		hwTwampSenderTwoWayDelayRxAvgVariation OBJECT-TYPE
			SYNTAX Integer32
			UNITS "microseconds"
			MAX-ACCESS read-only
			STATUS current
			DESCRIPTION
				"The value of this object identifies the average dual-ended delay change of the receiver."
			::= { hwTwampSenderTwoWayDelayEntry 11 }
		
-- 1.3.6.1.4.1.2011.5.25.333.1.1.6.1.12
		hwTwampSenderTwoWayDelayRxMaxVariation OBJECT-TYPE
			SYNTAX Integer32
			UNITS "microseconds"
			MAX-ACCESS read-only
			STATUS current
			DESCRIPTION
				"The value of this object identifies the maximum dual-ended delay change of the receiver."
			::= { hwTwampSenderTwoWayDelayEntry 12 }
		
-- 1.3.6.1.4.1.2011.5.25.333.1.1.6.1.13
		hwTwampSenderTwoWayDelayRxMinVariation OBJECT-TYPE
			SYNTAX Integer32
			UNITS "microseconds"
			MAX-ACCESS read-only
			STATUS current
			DESCRIPTION
				"The value of this object identifies the minimum dual-ended delay change of the receiver."
			::= { hwTwampSenderTwoWayDelayEntry 13 }
		
-- Controller test-session two-way loss measure Node definitions
-- 1.3.6.1.4.1.2011.5.25.333.1.1.7
		hwTwampSenderTwoWayLossTable OBJECT-TYPE
			SYNTAX SEQUENCE OF HwTwampSenderTwoWayLossEntry
			MAX-ACCESS not-accessible
			STATUS current
			DESCRIPTION
				"This object indicates a dual-ended packet loss measurement table."
			::= { hwTwampController 7 }
		
-- 1.3.6.1.4.1.2011.5.25.333.1.1.7.1
		hwTwampSenderTwoWayLossEntry OBJECT-TYPE
			SYNTAX HwTwampSenderTwoWayLossEntry
			MAX-ACCESS not-accessible
			STATUS current
			DESCRIPTION
				"This object indicates a dual-ended packet loss measurement entry."
			INDEX { hwTwampSenderId, hwTwampSenderTwoWayLossSeq }
			::= { hwTwampSenderTwoWayLossTable 1 }
		
		HwTwampSenderTwoWayLossEntry ::=
			SEQUENCE { 
				hwTwampSenderTwoWayLossSeq
					Gauge32,
				hwTwampSenderTwoWayLossValue
					Integer32,
				hwTwampSenderTwoWaySentCount
					Integer32,
				hwTwampSenderTwoWayTotalSentCount
					Unsigned32,
				hwTwampSenderTwoWayTotalLossValue
					Unsigned32,	
				hwTwampSenderTwoWayErrorCount
					Unsigned32,
				hwTwampSenderTwoWayTotalErrorCount
					Unsigned32						
			 }

-- 1.3.6.1.4.1.2011.5.25.333.1.1.7.1.1
		hwTwampSenderTwoWayLossSeq OBJECT-TYPE
			SYNTAX Gauge32 (1..4294967295)
			MAX-ACCESS not-accessible
			STATUS current
			DESCRIPTION
				"This object indicates the sequence number of a dual-ended packet loss measurement."
			::= { hwTwampSenderTwoWayLossEntry 1 }
		
-- 1.3.6.1.4.1.2011.5.25.333.1.1.7.1.2
		hwTwampSenderTwoWayLossValue OBJECT-TYPE
			SYNTAX Integer32
			MAX-ACCESS read-only
			STATUS current
			DESCRIPTION
				"This object indicates the number of lost packets in a dual-ended packet loss measurement."
			::= { hwTwampSenderTwoWayLossEntry 2 }
		
-- 1.3.6.1.4.1.2011.5.25.333.1.1.7.1.3
		hwTwampSenderTwoWaySentCount OBJECT-TYPE
			SYNTAX Integer32
			MAX-ACCESS read-only
			STATUS current
			DESCRIPTION
				"This object indicates the number of sent packets in a dual-ended packet loss measurement."
			::= { hwTwampSenderTwoWayLossEntry 3 }

-- 1.3.6.1.4.1.2011.5.25.333.1.1.7.1.4
		hwTwampSenderTwoWayTotalSentCount OBJECT-TYPE
			SYNTAX Unsigned32
			MAX-ACCESS read-only
			STATUS current
			DESCRIPTION
				"This object indicates the total number of sent packets in a dual-ended packet loss measurement."
			::= { hwTwampSenderTwoWayLossEntry 4 }
			
-- 1.3.6.1.4.1.2011.5.25.333.1.1.7.1.5
		hwTwampSenderTwoWayTotalLossValue OBJECT-TYPE
			SYNTAX Unsigned32
			MAX-ACCESS read-only
			STATUS current
			DESCRIPTION
				"This object indicates the total number of sent packets in a dual-ended packet loss measurement."
			::= { hwTwampSenderTwoWayLossEntry 5 }	

-- 1.3.6.1.4.1.2011.5.25.333.1.1.7.1.6
		hwTwampSenderTwoWayErrorCount OBJECT-TYPE
			SYNTAX Unsigned32
			MAX-ACCESS read-only
			STATUS current
			DESCRIPTION
				"This object indicates the number of sent packets in a dual-ended packet error measurement."
			::= { hwTwampSenderTwoWayLossEntry 6 }
			
-- 1.3.6.1.4.1.2011.5.25.333.1.1.7.1.7
		hwTwampSenderTwoWayTotalErrorCount OBJECT-TYPE
			SYNTAX Unsigned32
			MAX-ACCESS read-only
			STATUS current
			DESCRIPTION
				"This object indicates the total number of sent packets in a dual-ended packet error measurement."
			::= { hwTwampSenderTwoWayLossEntry 7 }	
					
-- Controller test-session loss statistics last sequence number Node definitions
-- 1.3.6.1.4.1.2011.5.25.333.1.1.8
		hwTwampSenderLossSeqNumberTable OBJECT-TYPE
			SYNTAX SEQUENCE OF HwTwampSenderLossSeqNumberEntry
			MAX-ACCESS not-accessible
			STATUS current
			DESCRIPTION
				"This object indicates the table for storing the sequence numbers of the latest packet loss sampling intervals."
			::= { hwTwampController 8 }
		
-- 1.3.6.1.4.1.2011.5.25.333.1.1.8.1
		hwTwampSenderLossSeqNumberEntry OBJECT-TYPE
			SYNTAX HwTwampSenderLossSeqNumberEntry
			MAX-ACCESS not-accessible
			STATUS current
			DESCRIPTION
				"This object indicates the entry for storing the sequence number of the latest packet loss sampling interval."
			INDEX { hwTwampSenderId }
			::= { hwTwampSenderLossSeqNumberTable 1 }
		
		HwTwampSenderLossSeqNumberEntry ::=
			SEQUENCE { 
				hwTwampSenderLossSeqNumberValue
					Gauge32
			 }

-- 1.3.6.1.4.1.2011.5.25.333.1.1.8.1.1
		hwTwampSenderLossSeqNumberValue OBJECT-TYPE
			SYNTAX Gauge32 (1..4294967295)
			MAX-ACCESS read-only
			STATUS current
			DESCRIPTION
				"This object indicates the sequence number of the latest packet loss sampling interval."
			::= { hwTwampSenderLossSeqNumberEntry 1 }
		
-- Controller test-session delay statistics last sequence number Node definitions
-- 1.3.6.1.4.1.2011.5.25.333.1.1.9
		hwTwampSenderDelaySeqNumberTable OBJECT-TYPE
			SYNTAX SEQUENCE OF HwTwampSenderDelaySeqNumberEntry
			MAX-ACCESS not-accessible
			STATUS current
			DESCRIPTION
				"This object indicates the table for storing the sequence numbers of the latest delay sampling intervals."
			::= { hwTwampController 9 }
		
-- 1.3.6.1.4.1.2011.5.25.333.1.1.9.1
		hwTwampSenderDelaySeqNumberEntry OBJECT-TYPE
			SYNTAX HwTwampSenderDelaySeqNumberEntry
			MAX-ACCESS not-accessible
			STATUS current
			DESCRIPTION
				"This object indicates the entry for storing the sequence number of the latest delay sampling interval."
			INDEX { hwTwampSenderId }
			::= { hwTwampSenderDelaySeqNumberTable 1 }
		
		HwTwampSenderDelaySeqNumberEntry ::=
			SEQUENCE { 
				hwTwampSenderDelaySeqNumberValue
					Gauge32
			 }

-- 1.3.6.1.4.1.2011.5.25.333.1.1.9.1.1
		hwTwampSenderDelaySeqNumberValue OBJECT-TYPE
			SYNTAX Gauge32 (1..4294967295)
			MAX-ACCESS read-only
			STATUS current
			DESCRIPTION
				"This object indicates the sequence number of the latest delay sampling interval."
			::= { hwTwampSenderDelaySeqNumberEntry 1 }

-- hwTwampTwoWayLossAlarmTable Node definitions
-- 1.3.6.1.4.1.2011.5.25.333.1.1.10
		hwTwampTwoWayLossAlarmTable OBJECT-TYPE
			SYNTAX SEQUENCE OF HwTwampTwoWayLossAlarmEntry
			MAX-ACCESS not-accessible
			STATUS current
			DESCRIPTION
				"This table is used to query whether the TWAMP two-way loss ratio value triggers alarms."
			::= { hwTwampController 10 }
		
-- 1.3.6.1.4.1.2011.5.25.333.1.1.10.1
		hwTwampTwoWayLossAlarmEntry OBJECT-TYPE
			SYNTAX HwTwampTwoWayLossAlarmEntry
			MAX-ACCESS not-accessible
			STATUS current
			DESCRIPTION
				"An entry in the table, containing information on the TWAMP two-way loss alarm entity."
			INDEX { hwTwampSenderId}
			::= { hwTwampTwoWayLossAlarmTable 1 }
		
		HwTwampTwoWayLossAlarmEntry ::=
			SEQUENCE {		
				      hwTwampTwoWayLossRatio
					  Integer32,
				      hwTwampTwoWayLossRatioUpperLimitThreshold
                      Integer32,
                      hwTwampTwoWayLossRatioLowerLimitThreshold
                      Integer32,       
        		      hwTwampTwoWayLossAlarmRowStatus
					  RowStatus
			        }

-- 1.3.6.1.4.1.2011.5.25.333.1.1.10.1.1
		hwTwampTwoWayLossRatio OBJECT-TYPE
			SYNTAX Integer32 (0..1000000)
			MAX-ACCESS accessible-for-notify
			STATUS current
			DESCRIPTION
				"The value of this object identifies the dual-ended packet loss rate."
			::= { hwTwampTwoWayLossAlarmEntry 1 }
		
-- 1.3.6.1.4.1.2011.5.25.333.1.1.10.1.2
		hwTwampTwoWayLossRatioUpperLimitThreshold OBJECT-TYPE
			SYNTAX Integer32 (2..999999)
			MAX-ACCESS read-create
			STATUS current
			DESCRIPTION
				"The value of this object identifies upper threshold of the dual-ended packet loss rate."
			::= { hwTwampTwoWayLossAlarmEntry 2 }
		
-- 1.3.6.1.4.1.2011.5.25.333.1.1.10.1.3
		hwTwampTwoWayLossRatioLowerLimitThreshold OBJECT-TYPE
			SYNTAX Integer32 (1..999998)
			MAX-ACCESS read-create
			STATUS current
			DESCRIPTION
				"The value of this object identifies lower threshold of the dual-ended packet loss rate."
			::= { hwTwampTwoWayLossAlarmEntry 3 }
			
-- 1.3.6.1.4.1.2011.5.25.333.1.1.10.1.99
		hwTwampTwoWayLossAlarmRowStatus OBJECT-TYPE
			SYNTAX RowStatus
			MAX-ACCESS read-create
			STATUS current
			DESCRIPTION
				"This object indicates the row status of this entry."
			::= { hwTwampTwoWayLossAlarmEntry 99 }

			
-- hwTwampTwoWayDelayAlarmTable Node definitions
-- 1.3.6.1.4.1.2011.5.25.333.1.1.11
		hwTwampTwoWayDelayAlarmTable OBJECT-TYPE
			SYNTAX SEQUENCE OF HwTwampTwoWayDelayAlarmEntry
			MAX-ACCESS not-accessible
			STATUS current
			DESCRIPTION
				"This table is used to query whether the TWAMP two-way delay value triggers alarms."
			::= { hwTwampController 11 }
		
-- 1.3.6.1.4.1.2011.5.25.333.1.1.11.1
		hwTwampTwoWayDelayAlarmEntry OBJECT-TYPE
			SYNTAX HwTwampTwoWayDelayAlarmEntry
			MAX-ACCESS not-accessible
			STATUS current
			DESCRIPTION
				"An entry in the table, containing information on the TWAMP two-way delay alarm entity."
			INDEX { hwTwampSenderId}
			::= { hwTwampTwoWayDelayAlarmTable 1 }
		
		HwTwampTwoWayDelayAlarmEntry ::=
			SEQUENCE {		
				      hwTwampTwoWayDelayValue
					  Integer32,
				      hwTwampTwoWayDelayValueUpperLimitThreshold
                      Integer32,
                      hwTwampTwoWayDelayValueLowerLimitThreshold				
                      Integer32,       
        		      hwTwampTwoWayDelayAlarmRowStatus
					  RowStatus
			        }

-- 1.3.6.1.4.1.2011.5.25.333.1.1.11.1.1
		hwTwampTwoWayDelayValue OBJECT-TYPE
			SYNTAX Integer32 (0..1000)
			UNITS "millisecond"
			MAX-ACCESS accessible-for-notify
			STATUS current
			DESCRIPTION
				"The value of this object identifies the dual-ended delay."
			::= { hwTwampTwoWayDelayAlarmEntry 1 }
		
-- 1.3.6.1.4.1.2011.5.25.333.1.1.11.1.2
		hwTwampTwoWayDelayValueUpperLimitThreshold OBJECT-TYPE
			SYNTAX Integer32 (2..1000)
			UNITS "millisecond"
			MAX-ACCESS read-create
			STATUS current
			DESCRIPTION
				"This object indicates the upper limit(ms) of the two-way ETH-DM."
			::= { hwTwampTwoWayDelayAlarmEntry 2 }
		
-- 1.3.6.1.4.1.2011.5.25.333.1.1.10.1.3
		hwTwampTwoWayDelayValueLowerLimitThreshold OBJECT-TYPE
			SYNTAX Integer32 (1..999)
			UNITS "millisecond"
			MAX-ACCESS read-create
			STATUS current
			DESCRIPTION
				"This object indicates the lower limit(ms) of the two-way ETH-DM."
			::= { hwTwampTwoWayDelayAlarmEntry 3 }

-- 1.3.6.1.4.1.2011.5.25.333.1.1.10.1.99
		hwTwampTwoWayDelayAlarmRowStatus OBJECT-TYPE
			SYNTAX RowStatus
			MAX-ACCESS read-create
			STATUS current
			DESCRIPTION
				"This object indicates the row status of this entry."
			::= { hwTwampTwoWayDelayAlarmEntry 99 }
			
-- hwTwampTwoWayJitterAlarmTable Node definitions
-- 1.3.6.1.4.1.2011.5.25.333.1.1.12
		hwTwampTwoWayJitterAlarmTable OBJECT-TYPE
			SYNTAX SEQUENCE OF HwTwampTwoWayJitterAlarmEntry
			MAX-ACCESS not-accessible
			STATUS current
			DESCRIPTION
				"This table is used to query whether the TWAMP two-way jitter value triggers alarms."
			::= { hwTwampController 12 }
		
-- 1.3.6.1.4.1.2011.5.25.333.1.1.12.1
		hwTwampTwoWayJitterAlarmEntry OBJECT-TYPE
			SYNTAX HwTwampTwoWayJitterAlarmEntry
			MAX-ACCESS not-accessible
			STATUS current
			DESCRIPTION
				"An entry in the table, containing information on the TWAMP two-way jitter alarm entity."
			INDEX { hwTwampSenderId}
			::= { hwTwampTwoWayJitterAlarmTable 1 }
		
		HwTwampTwoWayJitterAlarmEntry ::=
			SEQUENCE {		
				      hwTwampTwoWayJitterValue
					  Integer32,
				      hwTwampTwoWayJitterValueUpperLimitThreshold
                      Integer32,
                      hwTwampTwoWayJitterValueLowerLimitThreshold
                      Integer32,       
        		      hwTwampTwoWayJitterAlarmRowStatus
					  RowStatus			        
					  }

-- 1.3.6.1.4.1.2011.5.25.333.1.1.12.1.1
		hwTwampTwoWayJitterValue OBJECT-TYPE
			SYNTAX Integer32 (0..1000)
			UNITS "millisecond"
			MAX-ACCESS accessible-for-notify
			STATUS current
			DESCRIPTION
				"The value of this object identifies the dual-ended jitter."
			::= { hwTwampTwoWayJitterAlarmEntry 1 }
		
-- 1.3.6.1.4.1.2011.5.25.333.1.1.12.1.2
		hwTwampTwoWayJitterValueUpperLimitThreshold OBJECT-TYPE
			SYNTAX Integer32 (2..1000)
			UNITS "millisecond"
			MAX-ACCESS read-create
			STATUS current
			DESCRIPTION
				"This object indicates the upper limit(ms) of the two-way ETH-DM."
			::= { hwTwampTwoWayJitterAlarmEntry 2 }
		
-- 1.3.6.1.4.1.2011.5.25.333.1.1.12.1.3
		hwTwampTwoWayJitterValueLowerLimitThreshold OBJECT-TYPE
			SYNTAX Integer32 (1..999)
			UNITS "millisecond"
			MAX-ACCESS read-create
			STATUS current
			DESCRIPTION
				"This object indicates lower limit(ms) of the two-way ETH-DM."
			::= { hwTwampTwoWayJitterAlarmEntry 3 }
			
-- 1.3.6.1.4.1.2011.5.25.333.1.1.12.1.99
		hwTwampTwoWayJitterAlarmRowStatus OBJECT-TYPE
			SYNTAX RowStatus
			MAX-ACCESS read-create
			STATUS current
			DESCRIPTION
				"This object indicates the row status of this entry."
			::= { hwTwampTwoWayJitterAlarmEntry 99 }			

-- 1.3.6.1.4.1.2011.5.25.333.1.1.13
		hwTwampResetStatisticsTable OBJECT-TYPE
			SYNTAX SEQUENCE OF HwTwampResetStatisticsEntry
			MAX-ACCESS not-accessible
			STATUS current
			DESCRIPTION
				"This object indicates resetting the TWAMP-light test session statistics table."
			::= { hwTwampController 13 }
		
-- 1.3.6.1.4.1.2011.5.25.333.1.1.13.1
		hwTwampResetStatisticsEntry OBJECT-TYPE
			SYNTAX HwTwampResetStatisticsEntry
			MAX-ACCESS not-accessible
			STATUS current
			DESCRIPTION
				"This object indicates resetting the TWAMP-light test session statistics entry."
			INDEX { hwTwampSenderId }
			::= { hwTwampResetStatisticsTable 1 }
		
		HwTwampResetStatisticsEntry ::=
			SEQUENCE { 
				hwTwampResetStatistics
					INTEGER
			 }
			 
-- 1.3.6.1.4.1.2011.5.25.333.1.1.13.1.99
		hwTwampResetStatistics OBJECT-TYPE
			SYNTAX INTEGER
                {
                 single(1),
                 all(2)
                }
			MAX-ACCESS read-create
			STATUS current
			DESCRIPTION
				"This object indicates resetting the TWAMP-light test session statistics."
			::= { hwTwampResetStatisticsEntry 99 }				

			
-- Controller test-session regular  Node definitions
-- 1.3.6.1.4.1.2011.5.25.333.1.1.14
		hwTwampSenderRegularAdminTable OBJECT-TYPE
			SYNTAX SEQUENCE OF HwTwampSenderRegularAdminEntry
			MAX-ACCESS not-accessible
			STATUS current
			DESCRIPTION
				"This object indicates to start a TWAMP-light test instance table."
			::= { hwTwampController 14 }

-- 1.3.6.1.4.1.2011.5.25.333.1.1.14.1
		hwTwampSenderRegularAdminEntry OBJECT-TYPE
			SYNTAX HwTwampSenderRegularAdminEntry
			MAX-ACCESS not-accessible
			STATUS current
			DESCRIPTION
				"This object indicates to start a TWAMP-light test instance entry."
			INDEX { hwTwampSenderId }
			::= { hwTwampSenderRegularAdminTable 1 }
		
		HwTwampSenderRegularAdminEntry ::=
			SEQUENCE { 
				hwTwampSenderRegularTime
					Integer32,
				hwTwampSenderRegulaPacketCount
					Integer32,
				hwTwampSenderRegularTimeOut
					Integer32,
				hwTwampSenderRegularRowStatus
					RowStatus
			 }

-- 1.3.6.1.4.1.2011.5.25.333.1.1.14.1.1
		hwTwampSenderRegularTime OBJECT-TYPE
			SYNTAX Integer32 (10..60)
			UNITS "minutes"
			MAX-ACCESS read-create
			STATUS current
			DESCRIPTION
				"The value of this object identifies the packet timeout period."
			DEFVAL { 30 }
			::= { hwTwampSenderRegularAdminEntry 1 }
			
-- 1.3.6.1.4.1.2011.5.25.333.1.1.14.1.2
		hwTwampSenderRegulaPacketCount OBJECT-TYPE
			SYNTAX Integer32 (10..1000)
			MAX-ACCESS read-create
			STATUS current
			DESCRIPTION
				"The value of this object identifies the packet timeout period."
			DEFVAL { 100 }
			::= { hwTwampSenderRegularAdminEntry 2 }

-- 1.3.6.1.4.1.2011.5.25.333.1.1.14.1.3
		hwTwampSenderRegularTimeOut OBJECT-TYPE
			SYNTAX Integer32 (1..10)
			UNITS "seconds"
			MAX-ACCESS read-create
			STATUS current
			DESCRIPTION
				"The value of this object identifies the packet timeout period."
			DEFVAL { 5 }
			::= { hwTwampSenderRegularAdminEntry 3 }
		
-- 1.3.6.1.4.1.2011.5.25.333.1.1.14.1.99
		hwTwampSenderRegularRowStatus OBJECT-TYPE
			SYNTAX RowStatus
			MAX-ACCESS read-create
			STATUS current
			DESCRIPTION
				"This object indicates the row status of this entry."
			::= { hwTwampSenderRegularAdminEntry 99 }
			

-- hwTwampMemTwoWayLossAlarmTable Node definitions
-- 1.3.6.1.4.1.2011.5.25.333.1.1.15
		hwTwampMemTwoWayLossAlarmTable OBJECT-TYPE
			SYNTAX SEQUENCE OF HwTwampMemTwoWayLossAlarmEntry
			MAX-ACCESS not-accessible
			STATUS current
			DESCRIPTION
				"This table is used to query whether the TWAMP two-way loss ratio value triggers alarms."
			::= { hwTwampController 15 }
		
-- 1.3.6.1.4.1.2011.5.25.333.1.1.15.1
		hwTwampMemTwoWayLossAlarmEntry OBJECT-TYPE
			SYNTAX HwTwampMemTwoWayLossAlarmEntry
			MAX-ACCESS not-accessible
			STATUS current
			DESCRIPTION
				"An entry in the table, containing information on the TWAMP two-way loss alarm entity."
			INDEX { hwTwampSenderId, hwTwampSenderMember}
			::= { hwTwampMemTwoWayLossAlarmTable 1 }
		
		HwTwampMemTwoWayLossAlarmEntry ::=
			SEQUENCE {
				      hwTwampSenderMember
					  InterfaceIndex,
				      hwTwampSenderMemberName
					  OCTET STRING,
				      hwTwampMemTwoWayLossRatio
					  Integer32,
				      hwTwampMemTwoWayLossRatioUpperLimitThreshold
                      Integer32,
                      hwTwampMemTwoWayLossRatioLowerLimitThreshold
                      Integer32
			        }
					
-- 1.3.6.1.4.1.2011.5.25.333.1.1.15.1.1
		hwTwampSenderMember OBJECT-TYPE
			SYNTAX InterfaceIndex
			MAX-ACCESS not-accessible
			STATUS current
			DESCRIPTION
				"This object indicates the interface index of a two-way delay TWAMP-light test instance."
			::= { hwTwampMemTwoWayLossAlarmEntry 1 }

-- 1.3.6.1.4.1.2011.5.25.333.1.1.15.1.2
    hwTwampSenderMemberName OBJECT-TYPE 
        SYNTAX OCTET STRING(SIZE(0..64))
        MAX-ACCESS accessible-for-notify
        STATUS current
        DESCRIPTION
            "This object indicates the interface name of a two-way delay TWAMP-light test instance."     
        ::= { hwTwampMemTwoWayLossAlarmEntry 2 }
		
-- 1.3.6.1.4.1.2011.5.25.333.1.1.15.1.3
		hwTwampMemTwoWayLossRatio OBJECT-TYPE
			SYNTAX Integer32 (0..1000000)
			MAX-ACCESS accessible-for-notify
			STATUS current
			DESCRIPTION
				"The value of this object identifies the dual-ended packet loss rate."
			::= { hwTwampMemTwoWayLossAlarmEntry 3 }
		
-- 1.3.6.1.4.1.2011.5.25.333.1.1.15.1.4
		hwTwampMemTwoWayLossRatioUpperLimitThreshold OBJECT-TYPE
			SYNTAX Integer32 (2..999999)
			MAX-ACCESS accessible-for-notify
			STATUS current
			DESCRIPTION
				"The value of this object identifies upper threshold of the dual-ended packet loss rate."
			::= { hwTwampMemTwoWayLossAlarmEntry 4 }
		
-- 1.3.6.1.4.1.2011.5.25.333.1.1.15.1.5
		hwTwampMemTwoWayLossRatioLowerLimitThreshold OBJECT-TYPE
			SYNTAX Integer32 (1..999998)
			MAX-ACCESS accessible-for-notify
			STATUS current
			DESCRIPTION
				"The value of this object identifies lower threshold of the dual-ended packet loss rate."
			::= { hwTwampMemTwoWayLossAlarmEntry 5 }
			
			
-- hwTwampMemTwoWayDelayAlarmTable Node definitions
-- 1.3.6.1.4.1.2011.5.25.333.1.1.16
		hwTwampMemTwoWayDelayAlarmTable OBJECT-TYPE
			SYNTAX SEQUENCE OF HwTwampMemTwoWayDelayAlarmEntry
			MAX-ACCESS not-accessible
			STATUS current
			DESCRIPTION
				"This table is used to query whether the TWAMP two-way delay value triggers alarms."
			::= { hwTwampController 16 }
		
-- 1.3.6.1.4.1.2011.5.25.333.1.1.16.1
		hwTwampMemTwoWayDelayAlarmEntry OBJECT-TYPE
			SYNTAX HwTwampMemTwoWayDelayAlarmEntry
			MAX-ACCESS not-accessible
			STATUS current
			DESCRIPTION
				"An entry in the table, containing information on the TWAMP two-way delay alarm entity."
			INDEX { hwTwampSenderId, hwTwampSenderMember}
			::= { hwTwampMemTwoWayDelayAlarmTable 1 }
		
		HwTwampMemTwoWayDelayAlarmEntry ::=
			SEQUENCE {
					  hwTwampSenderMemberName
					  OCTET STRING,
				      hwTwampMemTwoWayDelayValue
					  Integer32,
				      hwTwampMemTwoWayDelayValueUpperLimitThreshold
                      Integer32,
                      hwTwampMemTwoWayDelayValueLowerLimitThreshold				
                      Integer32
			        }

-- 1.3.6.1.4.1.2011.5.25.333.1.1.16.1.1
		hwTwampMemTwoWayDelayValue OBJECT-TYPE
			SYNTAX Integer32 (0..1000)
			UNITS "millisecond"
			MAX-ACCESS accessible-for-notify
			STATUS current
			DESCRIPTION
				"The value of this object identifies the dual-ended delay."
			::= { hwTwampMemTwoWayDelayAlarmEntry 1 }
		
-- 1.3.6.1.4.1.2011.5.25.333.1.1.16.1.2
		hwTwampMemTwoWayDelayValueUpperLimitThreshold OBJECT-TYPE
			SYNTAX Integer32 (2..1000)
			UNITS "millisecond"
			MAX-ACCESS accessible-for-notify
			STATUS current
			DESCRIPTION
				"This object indicates the upper limit(ms) of the two-way ETH-DM."
			::= { hwTwampMemTwoWayDelayAlarmEntry 2 }
		
-- 1.3.6.1.4.1.2011.5.25.333.1.1.16.1.3
		hwTwampMemTwoWayDelayValueLowerLimitThreshold OBJECT-TYPE
			SYNTAX Integer32 (1..999)
			UNITS "millisecond"
			MAX-ACCESS accessible-for-notify
			STATUS current
			DESCRIPTION
				"This object indicates the lower limit(ms) of the two-way ETH-DM."
			::= { hwTwampMemTwoWayDelayAlarmEntry 3 }

			
-- hwTwampMemTwoWayJitterAlarmTable Node definitions
-- 1.3.6.1.4.1.2011.5.25.333.1.1.17
		hwTwampMemTwoWayJitterAlarmTable OBJECT-TYPE
			SYNTAX SEQUENCE OF HwTwampMemTwoWayJitterAlarmEntry
			MAX-ACCESS not-accessible
			STATUS current
			DESCRIPTION
				"This table is used to query whether the TWAMP two-way jitter value triggers alarms."
			::= { hwTwampController 17 }
		
-- 1.3.6.1.4.1.2011.5.25.333.1.1.17.1
		hwTwampMemTwoWayJitterAlarmEntry OBJECT-TYPE
			SYNTAX HwTwampMemTwoWayJitterAlarmEntry
			MAX-ACCESS not-accessible
			STATUS current
			DESCRIPTION
				"An entry in the table, containing information on the TWAMP two-way jitter alarm entity."
			INDEX { hwTwampSenderId, hwTwampSenderMember }
			::= { hwTwampMemTwoWayJitterAlarmTable 1 }
		
		HwTwampMemTwoWayJitterAlarmEntry ::=
			SEQUENCE {		
				      hwTwampSenderMemberName
					  OCTET STRING,
				      hwTwampMemTwoWayJitterValue
					  Integer32,
				      hwTwampMemTwoWayJitterValueUpperLimitThreshold
                      Integer32,
                      hwTwampMemTwoWayJitterValueLowerLimitThreshold
                      Integer32    
					  }

-- 1.3.6.1.4.1.2011.5.25.333.1.1.17.1.1
		hwTwampMemTwoWayJitterValue OBJECT-TYPE
			SYNTAX Integer32 (0..1000)
			UNITS "millisecond"
			MAX-ACCESS accessible-for-notify
			STATUS current
			DESCRIPTION
				"The value of this object identifies the dual-ended jitter."
			::= { hwTwampMemTwoWayJitterAlarmEntry 1 }
		
-- 1.3.6.1.4.1.2011.5.25.333.1.1.17.1.2
		hwTwampMemTwoWayJitterValueUpperLimitThreshold OBJECT-TYPE
			SYNTAX Integer32 (2..1000)
			UNITS "millisecond"
			MAX-ACCESS accessible-for-notify
			STATUS current
			DESCRIPTION
				"This object indicates the upper limit(ms) of the two-way ETH-DM."
			::= { hwTwampMemTwoWayJitterAlarmEntry 2 }
		
-- 1.3.6.1.4.1.2011.5.25.333.1.1.17.1.3
		hwTwampMemTwoWayJitterValueLowerLimitThreshold OBJECT-TYPE
			SYNTAX Integer32 (1..999)
			UNITS "millisecond"
			MAX-ACCESS accessible-for-notify
			STATUS current
			DESCRIPTION
				"This object indicates lower limit(ms) of the two-way ETH-DM."
			::= { hwTwampMemTwoWayJitterAlarmEntry 3 }

			
-- 1.3.6.1.4.1.2011.5.25.333.1.2
		hwTwampResponder OBJECT IDENTIFIER ::= { hwTwampMib 2 }
		
-- Respnder test Node definitions
-- 
-- 1.3.6.1.4.1.2011.5.25.333.1.2.1
		hwTwampResponderTable OBJECT-TYPE
			SYNTAX SEQUENCE OF HwTwampResponderEntry
			MAX-ACCESS not-accessible
			STATUS current
			DESCRIPTION
				"This object indicates the configuration table of TWAMP-light test instances on a reflector."
			::= { hwTwampResponder 1 }
		
-- 1.3.6.1.4.1.2011.5.25.333.1.2.1.1
		hwTwampResponderEntry OBJECT-TYPE
			SYNTAX HwTwampResponderEntry
			MAX-ACCESS not-accessible
			STATUS current
			DESCRIPTION
				"This object indicates the configuration entry of a TWAMP-light test instance on a reflector."
			INDEX { hwTwampResponderId }
			::= { hwTwampResponderTable 1 }
		
		HwTwampResponderEntry ::=
			SEQUENCE { 
				hwTwampResponderId
					Integer32,
				hwTwampResponderSourceIpAddressType
					InetAddressType,
				hwTwampResponderSourceIpAddress
					InetAddress,
				hwTwampResponderDestIpAddressType
					InetAddressType,
				hwTwampResponderDestIpAddress
					InetAddress,
				hwTwampResponderSourceUDPPort
					Integer32,
				hwTwampResponderDestUDPPort
					Integer32,
				hwTwampResponderPEVlan
					VlanIdOrNone,
				hwTwampResponderCEVlan
					VlanIdOrNone,
				hwTwampResponderVrfName
					DisplayString,
				hwTwampResponderIfIndex
				    InterfaceIndexOrZero,
				hwTwampResponderDescription
				    DisplayString,
				hwTwampResponderAntiLoop
				    INTEGER,
				hwTwampResponderRowStatus
					RowStatus
			 }

-- 1.3.6.1.4.1.2011.5.25.333.1.2.1.1.1
		hwTwampResponderId OBJECT-TYPE
			SYNTAX Integer32 (1..16384)
			MAX-ACCESS not-accessible
			STATUS current
			DESCRIPTION
				"This object indicates the index of a TWAMP-light test instance on the reflector. The value range of this object may vary because of different implementations."
			::= { hwTwampResponderEntry 1 }
		
-- 1.3.6.1.4.1.2011.5.25.333.1.2.1.1.2
		hwTwampResponderSourceIpAddressType OBJECT-TYPE
			SYNTAX InetAddressType
			MAX-ACCESS read-create
			STATUS current
			DESCRIPTION
				"This object indicates the sender's IP address type in a TWAMP-light test instance."
			::= { hwTwampResponderEntry 2 }

-- 1.3.6.1.4.1.2011.5.25.333.1.2.1.1.3
		hwTwampResponderSourceIpAddress OBJECT-TYPE
			SYNTAX InetAddress
			MAX-ACCESS read-create
			STATUS current
			DESCRIPTION
				"This object indicates the sender's IP address in a TWAMP-light test instance."
			::= { hwTwampResponderEntry 3 }

-- 1.3.6.1.4.1.2011.5.25.333.1.2.1.1.4
		hwTwampResponderDestIpAddressType OBJECT-TYPE
			SYNTAX InetAddressType
			MAX-ACCESS read-create
			STATUS current
			DESCRIPTION
				"This object indicates the reflector's IP address type in a TWAMP-light test instance."
			::= { hwTwampResponderEntry 4 }
-- 1.3.6.1.4.1.2011.5.25.333.1.2.1.1.5
		hwTwampResponderDestIpAddress OBJECT-TYPE
			SYNTAX InetAddress
			MAX-ACCESS read-create
			STATUS current
			DESCRIPTION
				"This object indicates the reflector's IP address in a TWAMP-light test instance."
			::= { hwTwampResponderEntry 5 }
-- 1.3.6.1.4.1.2011.5.25.333.1.2.1.1.6
		hwTwampResponderSourceUDPPort OBJECT-TYPE
			SYNTAX Integer32 (862..863 | 1025..65535)
			MAX-ACCESS read-create
			STATUS current
			DESCRIPTION
				"This object indicates the sender's UDP port in a TWAMP-light test instance."
			::= { hwTwampResponderEntry 6 }
		
-- 1.3.6.1.4.1.2011.5.25.333.1.2.1.1.7
		hwTwampResponderDestUDPPort OBJECT-TYPE
			SYNTAX Integer32 (862..863 | 1025..65535)
			MAX-ACCESS read-create
			STATUS current
			DESCRIPTION
				"This object indicates the reflector's UDP port in a TWAMP-light test instance."
			::= { hwTwampResponderEntry 7 }
		
-- 1.3.6.1.4.1.2011.5.25.333.1.2.1.1.8
		hwTwampResponderPEVlan OBJECT-TYPE
			SYNTAX VlanIdOrNone
			MAX-ACCESS read-create
			STATUS current
			DESCRIPTION
				"This object indicates the PE vlan in a TWAMP-light test instance."
			::= { hwTwampResponderEntry 8 }
-- 1.3.6.1.4.1.2011.5.25.333.1.2.1.1.9
		hwTwampResponderCEVlan OBJECT-TYPE
			SYNTAX VlanIdOrNone
			MAX-ACCESS read-create
			STATUS current
			DESCRIPTION
				"This object indicates the CE vlan in a TWAMP-light test instance."
			::= { hwTwampResponderEntry 9 }
-- 1.3.6.1.4.1.2011.5.25.333.1.2.1.1.10
		hwTwampResponderVrfName OBJECT-TYPE
			SYNTAX DisplayString (SIZE (0..31))
			MAX-ACCESS read-create
			STATUS current
			DESCRIPTION
				"This object indicates the VPN name of a TWAMP Light test instance."
			::= { hwTwampResponderEntry 10 }
-- 1.3.6.1.4.1.2011.5.25.333.1.2.1.1.11
        hwTwampResponderIfIndex OBJECT-TYPE
            SYNTAX InterfaceIndexOrZero
            MAX-ACCESS read-create
            STATUS current
            DESCRIPTION
                "
                This object indicates the interface index.
                "
            DEFVAL { 0 }
            ::= { hwTwampResponderEntry 11 }
-- 1.3.6.1.4.1.2011.5.25.333.1.2.1.1.12
		hwTwampResponderDescription OBJECT-TYPE
			SYNTAX DisplayString (SIZE (0 | 3..32))
			MAX-ACCESS read-create
			STATUS current
			DESCRIPTION
				"This object indicates the description of a TWAMP Light test instance."
			::= { hwTwampResponderEntry 12 }
-- 1.3.6.1.4.1.2011.5.25.333.1.2.1.1.13
		hwTwampResponderAntiLoop OBJECT-TYPE
			SYNTAX INTEGER
			    {
				enable(1),
				disable(0)
				}
			MAX-ACCESS read-create
			STATUS current
			DESCRIPTION
				"The extend flag for reflector to stop loop."
			::= { hwTwampResponderEntry 13 }
-- 1.3.6.1.4.1.2011.5.25.333.1.2.1.1.99
		hwTwampResponderRowStatus OBJECT-TYPE
			SYNTAX RowStatus
			MAX-ACCESS read-create
			STATUS current
			DESCRIPTION
				"This object indicates the row status of this entry."
			::= { hwTwampResponderEntry 99 }
			
-- 1.3.6.1.4.1.2011.5.25.333.1.2.2
		hwTwampResponderEnable OBJECT-TYPE
			SYNTAX INTEGER
				{
				enable(1),
				disable(2)
				}
			MAX-ACCESS read-write
			STATUS current
			DESCRIPTION
				"The value of this object identifies whether the reflector is enabled."
			::= { hwTwampResponder 2 }
-- 1.3.6.1.4.1.2011.5.25.333.1.2.3
		hwTwampResponderIDWithInterface OBJECT-TYPE
			SYNTAX Unsigned32
			MAX-ACCESS accessible-for-notify
			STATUS current
			DESCRIPTION
				"This object indicates the configuration table of TWAMP-light test instances on a reflector."
			::= { hwTwampResponder 3 }	
			
-- The consistency of mib
-- 1.3.6.1.4.1.2011.5.25.333.1.3
		hwTwampConformance OBJECT IDENTIFIER ::= { hwTwampMib 3 }
		
-- 1.3.6.1.4.1.2011.5.25.333.1.3.1
		hwTwampCompliances OBJECT IDENTIFIER ::= { hwTwampConformance 1 }
		
-- 1.3.6.1.4.1.2011.5.25.333.1.3.1.1
		hwTwampCompliance MODULE-COMPLIANCE
			STATUS current
			DESCRIPTION 
				"The compliance statement for systems supporting the HUAWEI-TWAMP-MIB."
			MODULE -- this module
				MANDATORY-GROUPS { hwTwampSenderObjectGroup, hwTwampSenderAdminObjectGroup }
			::= { hwTwampCompliances 1 }

-- 1.3.6.1.4.1.2011.5.25.333.1.3.2
		hwTwampGroups OBJECT IDENTIFIER ::= { hwTwampConformance 2 }

-- 1.3.6.1.4.1.2011.5.25.333.1.3.2.1
		hwTwampControllerObjectGroup OBJECT-GROUP
			OBJECTS { hwTwampControllerClientEnable, hwTwampControllerSenderEnable }
			STATUS current
			DESCRIPTION 
				"The hwTwampControllerObjectGroup group.."
			::= { hwTwampGroups 1 }
		
-- hwTwampSenderTestSessionLocalIpAddressType,

-- 1.3.6.1.4.1.2011.5.25.333.1.3.2.2
		hwTwampSenderObjectGroup OBJECT-GROUP
			OBJECTS { hwTwampSenderLocalIpAddressType, hwTwampSenderLocalIpAddress, hwTwampSenderRemoteIpAddressType, hwTwampSenderRemoteIpAddress, hwTwampSenderLocalUDPPort, 
				hwTwampSenderRemoteUDPPort, hwTwampSenderRowStatus }
			STATUS current
			DESCRIPTION 
				"The hwTwampSenderTestEntry group."
			::= { hwTwampGroups 2 }
			
-- 1.3.6.1.4.1.2011.5.25.333.1.3.2.3
		hwTwampSenderAdminObjectGroup OBJECT-GROUP
			OBJECTS { hwTwampSenderAdminContinual, hwTwampSenderAdminDuration, hwTwampSenderAdminRowStatus, hwTwampSenderAdminPacketCount }
			STATUS current
			DESCRIPTION 
				"The HwTwampSenderTestAdminStateEntry group."
			::= { hwTwampGroups 3 }
				
-- 1.3.6.1.4.1.2011.5.25.333.1.3.2.4
		hwTwampSenderLossSeqNumberGroup OBJECT-GROUP
			OBJECTS { hwTwampSenderLossSeqNumberValue }
			STATUS current
			DESCRIPTION 
				"The hwTwampSenderLossSeqNumberGroup group."
			::= { hwTwampGroups 4 }
		
-- 1.3.6.1.4.1.2011.5.25.333.1.3.2.5
		hwTwampSenderDelaySeqNumberGroup OBJECT-GROUP
			OBJECTS { hwTwampSenderDelaySeqNumberValue }
			STATUS current
			DESCRIPTION 
				"The hwTwampSenderDelaySeqNumberGroup group."
			::= { hwTwampGroups 5 }
--  1.3.6.1.4.1.2011.5.25.333.1.3.2.6
		hwTwampResponderObjectGroup OBJECT-GROUP
			OBJECTS { hwTwampResponderSourceIpAddressType, hwTwampResponderSourceIpAddress, hwTwampResponderSourceUDPPort, hwTwampResponderCEVlan, hwTwampResponderVrfName, hwTwampResponderIfIndex, hwTwampResponderDescription, hwTwampResponderAntiLoop, hwTwampResponderPEVlan, 
				hwTwampResponderDestIpAddress, hwTwampResponderDestIpAddressType, hwTwampResponderRowStatus, hwTwampResponderDestUDPPort, hwTwampResponderEnable }
			STATUS current
			DESCRIPTION 
				"The hwTwampResponderObjectGroup group."
			::= { hwTwampGroups 6 }
--  1.3.6.1.4.1.2011.5.25.333.1.3.2.7
		hwTwampTwoWayLossObjectGroup OBJECT-GROUP
			OBJECTS { hwTwampTwoWayLossRatio, hwTwampTwoWayLossRatioUpperLimitThreshold, hwTwampTwoWayLossRatioLowerLimitThreshold, hwTwampTwoWayLossAlarmRowStatus }
			STATUS current
			DESCRIPTION 
				"The hwTwampTwoWayLossObjectGroup group."
			::= { hwTwampGroups 7 }
--  1.3.6.1.4.1.2011.5.25.333.1.3.2.8
		hwTwampTwoWayDelayObjectGroup OBJECT-GROUP
			OBJECTS { hwTwampTwoWayDelayValue, hwTwampTwoWayDelayValueUpperLimitThreshold, hwTwampTwoWayDelayValueLowerLimitThreshold, hwTwampTwoWayDelayAlarmRowStatus }
			STATUS current
			DESCRIPTION 
				"The hwTwampTwoWayDelayObjectGroup group."
			::= { hwTwampGroups 8 }
--  1.3.6.1.4.1.2011.5.25.333.1.3.2.9
		hwTwampTwoWayJitterObjectGroup OBJECT-GROUP
			OBJECTS { hwTwampTwoWayJitterValue, hwTwampTwoWayJitterValueUpperLimitThreshold, hwTwampTwoWayJitterValueLowerLimitThreshold, hwTwampTwoWayJitterAlarmRowStatus }
			STATUS current
			DESCRIPTION 
				"The hwTwampTwoWayJitterObjectGroup group."
			::= { hwTwampGroups 9 }
--  1.3.6.1.4.1.2011.5.25.333.1.3.2.10
		hwTwampMemTwoWayLossObjectGroup OBJECT-GROUP
			OBJECTS { hwTwampSenderMemberName, hwTwampMemTwoWayLossRatio, hwTwampMemTwoWayLossRatioUpperLimitThreshold, hwTwampMemTwoWayLossRatioLowerLimitThreshold }
			STATUS current
			DESCRIPTION 
				"The hwTwampMemTwoWayLossObjectGroup group."
			::= { hwTwampGroups 10 }
--  1.3.6.1.4.1.2011.5.25.333.1.3.2.11
		hwTwampMemTwoWayDelayObjectGroup OBJECT-GROUP
			OBJECTS { hwTwampSenderMemberName, hwTwampMemTwoWayDelayValue, hwTwampMemTwoWayDelayValueUpperLimitThreshold, hwTwampMemTwoWayDelayValueLowerLimitThreshold }
			STATUS current
			DESCRIPTION 
				"The hwTwampMemTwoWayDelayObjectGroup group."
			::= { hwTwampGroups 11 }
--  1.3.6.1.4.1.2011.5.25.333.1.3.2.12
		hwTwampMemTwoWayJitterObjectGroup OBJECT-GROUP
			OBJECTS { hwTwampSenderMemberName, hwTwampMemTwoWayJitterValue, hwTwampMemTwoWayJitterValueUpperLimitThreshold, hwTwampMemTwoWayJitterValueLowerLimitThreshold }
			STATUS current
			DESCRIPTION 
				"The hwTwampMemTwoWayJitterObjectGroup group."
			::= { hwTwampGroups 12 }
-- 1.3.6.1.4.1.2011.5.25.333.1.3.2.99
		hwTwampNoMondatoryGroup OBJECT-GROUP
			OBJECTS { hwTwampSenderVrfName, hwTwampSenderDSCP, hwTwampSenderPadding, hwTwampSenderAdminPeriod, hwTwampSenderOperState, 
				hwTwampSenderOperInactiveReason, hwTwampSenderOperLastStartTime, hwTwampSenderOperLastStopTime, hwTwampSenderOperTxCount, hwTwampSenderOperRxCount, 
				hwTwampSenderOperDiscardCount, hwTwampSenderOperSequence, hwTwampSenderTwoWayDelayAvgValue, hwTwampSenderTwoWayDelayAvgVariation, hwTwampSenderTwoWayLossValue, 
				hwTwampSenderTwoWayDelayTxAvgVariation, hwTwampSenderTwoWayDelayRxAvgVariation, hwTwampSenderDescription, hwTwampSenderTwoWayDelayMaxValue, hwTwampSenderTwoWayDelayMinValue, 
				hwTwampSenderTwoWayDelayMaxVariation, hwTwampSenderTwoWayDelayMinVariation, hwTwampSenderTwoWayDelayTxMaxVariation, hwTwampSenderTwoWayDelayTxMinVariation, hwTwampSenderTwoWayDelayRxMaxVariation, 
				hwTwampSenderTwoWaySentCount, hwTwampSenderOperType, hwTwampSenderTwoWayDelayRxMinVariation, hwTwampSenderAdminTimeOut, hwTwampSenderTwoWayTotalSentCount, hwTwampSenderTwoWayTotalLossValue, hwTwampSenderPaddingType, hwTwampSenderTwoWayErrorCount, hwTwampSenderTwoWayTotalErrorCount, hwTwampSenderBindingIfIndex }
			STATUS current
			DESCRIPTION 
				"No Mandatory Group."
			::= { hwTwampGroups 99 }
	
-- 1.3.6.1.4.1.2011.5.25.333.1.3.3	
 hwTwampTrapGroups OBJECT IDENTIFIER ::= { hwTwampConformance 3 }
        
        hwTwampTrapsGroup NOTIFICATION-GROUP
            NOTIFICATIONS { hwTwampTwoWayLossRatioExceed, 
                                           hwTwampTwoWayLossRatioRecovery, 
                                           hwTwampTwoWayDelayExceed,
                                           hwTwampTwoWayDelayRecovery, 
                                           hwTwampTwoWayJitterExceed,
                                           hwTwampTwoWayJitterRecovery,
                                           hwTwampTwoWayLocExceed,
                                           hwTwampTwoWayLocRecovery,
                                           hwTwampSenderSessionNumExceed,
                                           hwTwampSenderSessionNumRecovery,
                                           hwTwampNotSupportServiceUnderIntf,
                                           hwTwampNotSupportServiceUnderIntfRecovery,
                                           hwTwampMemTwoWayLossRatioExceed, 
                                           hwTwampMemTwoWayLossRatioRecovery, 
                                           hwTwampMemTwoWayDelayExceed,
                                           hwTwampMemTwoWayDelayRecovery, 
                                           hwTwampMemTwoWayJitterExceed,
                                           hwTwampMemTwoWayJitterRecovery,
                                           hwTwampMemTwoWayLocExceed,
                                           hwTwampMemTwoWayLocRecovery,
                                           hwTwampResponderSessionNumExceed,
                                           hwTwampResponderSessionNumRecovery,
                                           hwTwampControlSessionNumExceed,
                                           hwTwampControlSessionNumRecovery}
            STATUS current
            DESCRIPTION 
                "The Group of Twamp twoway performance statistics Trap."
            ::= { hwTwampTrapGroups 1 }
        		
-- The consistency of mib
-- 1.3.6.1.4.1.2011.5.25.333.1.4
		hwTwampTraps OBJECT IDENTIFIER ::= { hwTwampMib 4 }		
		
--  ******************************************************************
-- NOTIFICATIONS (TRAPS)
-- These notifications will be sent to the management entity
-- *******************************************************************						
		hwTwampTwoWayLossRatioExceed NOTIFICATION-TYPE
		OBJECTS {
				 hwTwampTwoWayLossRatio, 
				 hwTwampTwoWayLossRatioUpperLimitThreshold, 
				 hwTwampTwoWayLossRatioLowerLimitThreshold,
				 hwTwampSenderLocalIpAddress,
				 hwTwampSenderRemoteIpAddress,
				 hwTwampSenderLocalUDPPort,
				 hwTwampSenderRemoteUDPPort,
				 hwTwampSenderVrfName
				 }
		STATUS current
		DESCRIPTION 
			"This object indicates that dual-ended packet loss rate exceeds the threshold."
		::= { hwTwampTraps 1 }
		
		hwTwampTwoWayLossRatioRecovery NOTIFICATION-TYPE
		OBJECTS {
				 hwTwampTwoWayLossRatio, 
				 hwTwampTwoWayLossRatioUpperLimitThreshold, 
				 hwTwampTwoWayLossRatioLowerLimitThreshold,
				 hwTwampSenderLocalIpAddress,
				 hwTwampSenderRemoteIpAddress,
				 hwTwampSenderLocalUDPPort,
				 hwTwampSenderRemoteUDPPort,
				 hwTwampSenderVrfName
				}
		STATUS current
		DESCRIPTION 
			"This object indicates that dual-ended packet loss rate restores."
		::= { hwTwampTraps 2 }
		
		hwTwampTwoWayDelayExceed NOTIFICATION-TYPE
		OBJECTS {
				 hwTwampTwoWayDelayValue,
				 hwTwampTwoWayDelayValueUpperLimitThreshold, 
				 hwTwampTwoWayDelayValueLowerLimitThreshold,
				 hwTwampSenderLocalIpAddress,
				 hwTwampSenderRemoteIpAddress,
				 hwTwampSenderLocalUDPPort,
				 hwTwampSenderRemoteUDPPort,
				 hwTwampSenderVrfName
				}
		STATUS current
		DESCRIPTION 
			"This object indicates that dual-ended delay exceeds the threshold."
		::= { hwTwampTraps 3 }
		
		hwTwampTwoWayDelayRecovery NOTIFICATION-TYPE
		OBJECTS {
				 hwTwampTwoWayDelayValue,
				 hwTwampTwoWayDelayValueUpperLimitThreshold, 
				 hwTwampTwoWayDelayValueLowerLimitThreshold,
				 hwTwampSenderLocalIpAddress,
				 hwTwampSenderRemoteIpAddress,
				 hwTwampSenderLocalUDPPort,
				 hwTwampSenderRemoteUDPPort,
				 hwTwampSenderVrfName
		        }
		STATUS current
		DESCRIPTION 
			"This object indicates that dual-ended delay restores."
		::= { hwTwampTraps 4 }
		
		hwTwampTwoWayJitterExceed NOTIFICATION-TYPE
		OBJECTS {
				 hwTwampTwoWayJitterValue,
				 hwTwampTwoWayJitterValueUpperLimitThreshold, 
				 hwTwampTwoWayJitterValueLowerLimitThreshold,
				 hwTwampSenderLocalIpAddress,
				 hwTwampSenderRemoteIpAddress,
				 hwTwampSenderLocalUDPPort,
				 hwTwampSenderRemoteUDPPort,
				 hwTwampSenderVrfName
		        }
		STATUS current
		DESCRIPTION 
			"This object indicates that dual-ended jitter exceeds the threshold."
		::= { hwTwampTraps 5 }
		
		hwTwampTwoWayJitterRecovery NOTIFICATION-TYPE
		OBJECTS {
				 hwTwampTwoWayJitterValue,
				 hwTwampTwoWayJitterValueUpperLimitThreshold, 
				 hwTwampTwoWayJitterValueLowerLimitThreshold,
				 hwTwampSenderLocalIpAddress,
				 hwTwampSenderRemoteIpAddress,
				 hwTwampSenderLocalUDPPort,
				 hwTwampSenderRemoteUDPPort,
				 hwTwampSenderVrfName
		        }
		STATUS current
		DESCRIPTION 
			"This object indicates that dual-ended jitter restores."
		::= { hwTwampTraps 6 }			

		hwTwampTwoWayLocExceed NOTIFICATION-TYPE
		OBJECTS {
				 hwTwampTwoWayLossRatio,
				 hwTwampSenderLocalIpAddress,
				 hwTwampSenderRemoteIpAddress,
				 hwTwampSenderLocalUDPPort,
				 hwTwampSenderRemoteUDPPort,
				 hwTwampSenderVrfName
				}
		STATUS current
		DESCRIPTION 
			"This object indicates that the connection between the two ends fails."
		::= { hwTwampTraps 7 }
		
		hwTwampTwoWayLocRecovery NOTIFICATION-TYPE
		OBJECTS {
				 hwTwampTwoWayLossRatio,
				 hwTwampSenderLocalIpAddress,
				 hwTwampSenderRemoteIpAddress,
				 hwTwampSenderLocalUDPPort,
				 hwTwampSenderRemoteUDPPort,
				 hwTwampSenderVrfName
				}
		STATUS current
		DESCRIPTION 
			"This object indicates that the connection between the two ends restores."
		::= { hwTwampTraps 8 }
		
		hwTwampSenderSessionNumExceed NOTIFICATION-TYPE
		STATUS current
		DESCRIPTION 
			"This object indicates that the number of sessions exceeds the threshold."
		::= { hwTwampTraps 9 }
		
		hwTwampSenderSessionNumRecovery NOTIFICATION-TYPE
		STATUS current
		DESCRIPTION 
			"This object indicates that the number of sessions restores."
		::= { hwTwampTraps 10 }

		hwTwampNotSupportServiceUnderIntf NOTIFICATION-TYPE
		OBJECTS {
				 hwTwampResponderIDWithInterface
				 }
		STATUS current
		DESCRIPTION
			"This object indicates that TWAMP does not support services on the bound interface."
		::= { hwTwampTraps 11 }
		
		hwTwampNotSupportServiceUnderIntfRecovery NOTIFICATION-TYPE
		OBJECTS {
				 hwTwampResponderIDWithInterface
				 }
		STATUS current
		DESCRIPTION
			"This object indicates that TWAMP does not support service alarm clearing on the bound interface."
		::= { hwTwampTraps 12 }
		
		hwTwampMemTwoWayLossRatioExceed NOTIFICATION-TYPE
		OBJECTS {
				 hwTwampSenderMemberName,
				 hwTwampMemTwoWayLossRatio, 
				 hwTwampMemTwoWayLossRatioUpperLimitThreshold, 
				 hwTwampMemTwoWayLossRatioLowerLimitThreshold,
				 hwTwampSenderLocalIpAddress,
				 hwTwampSenderRemoteIpAddress,
				 hwTwampSenderLocalUDPPort,
				 hwTwampSenderRemoteUDPPort,
				 hwTwampSenderVrfName
				 }
		STATUS current
		DESCRIPTION 
			"This object indicates that dual-ended packet loss rate exceeds the threshold."
		::= { hwTwampTraps 13 }
		
		hwTwampMemTwoWayLossRatioRecovery NOTIFICATION-TYPE
		OBJECTS {
				 hwTwampSenderMemberName,
				 hwTwampMemTwoWayLossRatio, 
				 hwTwampMemTwoWayLossRatioUpperLimitThreshold, 
				 hwTwampMemTwoWayLossRatioLowerLimitThreshold,
				 hwTwampSenderLocalIpAddress,
				 hwTwampSenderRemoteIpAddress,
				 hwTwampSenderLocalUDPPort,
				 hwTwampSenderRemoteUDPPort,
				 hwTwampSenderVrfName
				}
		STATUS current
		DESCRIPTION 
			"This object indicates that dual-ended packet loss rate restores."
		::= { hwTwampTraps 14 }
		
		hwTwampMemTwoWayDelayExceed NOTIFICATION-TYPE
		OBJECTS {
				 hwTwampSenderMemberName,
				 hwTwampMemTwoWayDelayValue,
				 hwTwampMemTwoWayDelayValueUpperLimitThreshold, 
				 hwTwampMemTwoWayDelayValueLowerLimitThreshold,
				 hwTwampSenderLocalIpAddress,
				 hwTwampSenderRemoteIpAddress,
				 hwTwampSenderLocalUDPPort,
				 hwTwampSenderRemoteUDPPort,
				 hwTwampSenderVrfName
				}
		STATUS current
		DESCRIPTION 
			"This object indicates that dual-ended delay exceeds the threshold."
		::= { hwTwampTraps 15 }
		
		hwTwampMemTwoWayDelayRecovery NOTIFICATION-TYPE
		OBJECTS {
				 hwTwampSenderMemberName,
				 hwTwampMemTwoWayDelayValue,
				 hwTwampMemTwoWayDelayValueUpperLimitThreshold, 
				 hwTwampMemTwoWayDelayValueLowerLimitThreshold,
				 hwTwampSenderLocalIpAddress,
				 hwTwampSenderRemoteIpAddress,
				 hwTwampSenderLocalUDPPort,
				 hwTwampSenderRemoteUDPPort,
				 hwTwampSenderVrfName
		        }
		STATUS current
		DESCRIPTION 
			"This object indicates that dual-ended delay restores."
		::= { hwTwampTraps 16 }
		
		hwTwampMemTwoWayJitterExceed NOTIFICATION-TYPE
		OBJECTS {
				 hwTwampSenderMemberName,
				 hwTwampMemTwoWayJitterValue,
				 hwTwampMemTwoWayJitterValueUpperLimitThreshold, 
				 hwTwampMemTwoWayJitterValueLowerLimitThreshold,
				 hwTwampSenderLocalIpAddress,
				 hwTwampSenderRemoteIpAddress,
				 hwTwampSenderLocalUDPPort,
				 hwTwampSenderRemoteUDPPort,
				 hwTwampSenderVrfName
		        }
		STATUS current
		DESCRIPTION 
			"This object indicates that dual-ended jitter exceeds the threshold."
		::= { hwTwampTraps 17 }
		
		hwTwampMemTwoWayJitterRecovery NOTIFICATION-TYPE
		OBJECTS {
				 hwTwampSenderMemberName,
				 hwTwampMemTwoWayJitterValue,
				 hwTwampMemTwoWayJitterValueUpperLimitThreshold, 
				 hwTwampMemTwoWayJitterValueLowerLimitThreshold,
				 hwTwampSenderLocalIpAddress,
				 hwTwampSenderRemoteIpAddress,
				 hwTwampSenderLocalUDPPort,
				 hwTwampSenderRemoteUDPPort,
				 hwTwampSenderVrfName
		        }
		STATUS current
		DESCRIPTION 
			"This object indicates that dual-ended jitter restores."
		::= { hwTwampTraps 18 }			

		hwTwampMemTwoWayLocExceed NOTIFICATION-TYPE
		OBJECTS {
				 hwTwampSenderMemberName,
				 hwTwampMemTwoWayLossRatio,
				 hwTwampSenderLocalIpAddress,
				 hwTwampSenderRemoteIpAddress,
				 hwTwampSenderLocalUDPPort,
				 hwTwampSenderRemoteUDPPort,
				 hwTwampSenderVrfName
				}
		STATUS current
		DESCRIPTION 
			"This object indicates that the connection between the two ends fails."
		::= { hwTwampTraps 19 }
		
		hwTwampMemTwoWayLocRecovery NOTIFICATION-TYPE
		OBJECTS {
				 hwTwampSenderMemberName,
				 hwTwampMemTwoWayLossRatio,
				 hwTwampSenderLocalIpAddress,
				 hwTwampSenderRemoteIpAddress,
				 hwTwampSenderLocalUDPPort,
				 hwTwampSenderRemoteUDPPort,
				 hwTwampSenderVrfName
				}
		STATUS current
		DESCRIPTION 
			"This object indicates that the connection between the two ends restores."
		::= { hwTwampTraps 20 }
		
		hwTwampResponderSessionNumExceed NOTIFICATION-TYPE
		STATUS current
		DESCRIPTION 
			"This object indicates that the number of sessions exceeds the threshold."
		::= { hwTwampTraps 21 }
		
		hwTwampResponderSessionNumRecovery NOTIFICATION-TYPE
		STATUS current
		DESCRIPTION 
			"This object indicates that the number of sessions restores."
		::= { hwTwampTraps 22 }
		hwTwampControlSessionNumExceed NOTIFICATION-TYPE
		STATUS current
		DESCRIPTION 
			"This object indicates that the number of TWAMP control sessions is out of device capability."
		::= { hwTwampTraps 23 }
		
		hwTwampControlSessionNumRecovery NOTIFICATION-TYPE
		STATUS current
		DESCRIPTION 
			"This object indicates that the number of TWAMP control sessions is under device capability."
		::= { hwTwampTraps 24 }
	END

--
-- HUAWEI-TWAMP-MIB.mib
--

-- ============================================================================
-- Copyright (C) 2018 by  HUAWEI TECHNOLOGIES. All rights reserved.
-- Description:  This mib is used for defining huawei's vectoring management MIB objects.
--               The MIB is used for vectoring, vectoring is a transmission method that
--               employs the coordination of line signals for reduction of crosstalk levels
--               and improvement of performance.
-- Reference:
-- Version: V1.33
--
-- ============================================================================

    HUAWEI-VECTOR-MIB DEFINITIONS ::= BEGIN

        IMPORTS
            enterprises, Integer32, Unsigned32, Gauge32, OBJECT-TYPE,
            MODULE-IDENTITY, OBJECT-IDENTITY, NOTIFICATION-TYPE
                FROM SNMPv2-SMI
            RowStatus, TruthValue, MacAddress, TEXTUAL-CONVENTION, DateAndTime
                FROM SNMPv2-TC
            huaweiUtility
                FROM HUAWEI-MIB
            ifIndex
                FROM IF-MIB
            hwFrameIndex, hwSlotIndex, hwPortIndex, hwConfigChangeIP
                FROM HUAWEI-DEVICE-MIB
            HwXdslDirection
                FROM   HUAWEI-XDSL-LINE-TC-MIB
            hwXdslRequestID, hwXdslPortFrequentRetrainControlTimes
                FROM   HUAWEI-XDSL-COMMON-MIB;

            hwVectoringMIB MODULE-IDENTITY
            LAST-UPDATED "201806260000Z"
            ORGANIZATION
                "Huawei Technologies Co.,Ltd."
            CONTACT-INFO
                         "Huawei Industrial Base
                          Bantian, Longgang
                          Shenzhen 518129
                          People's Republic of China
                          Website: http://www.huawei.com
                          Email: support@huawei.com
                         "
            DESCRIPTION
                "This mib is used for defining huawei's vectoring management MIB objects.
                 The MIB is used for vectoring, vectoring is a transmission method that
                 employs the coordination of line signals for reduction of crosstalk levels
                 and improvement of performance.
                "

            --  Revision history
            REVISION     "201806260000Z"
            DESCRIPTION  "V1.33, changes in this revision:
                          Add leaf node hwVectoringVpBoardMode in hwVectoringGlobalConfig.
                          Modify the ranges of the leaf node hwVectoringNlvFaultReason." 
 
            REVISION     "201805300000Z"
            DESCRIPTION  "V1.32, changes in this revision:
                          Modify the SYNTAX INTEGER and DESCRIPTION of hwVectoringBandplanType.
                          Add the definition of the table: hwVectoringNlvGlobalConfig 
                          Add the definition of the nodes: hwVectoringNlvSwitch, hwVectoringNlvMode, 
                          hwVectoringNlvSlotList, hwVectoringNlvClockSourceCfg, hwVectoringNlvFaultPolicy 
                          and hwVectoringNlvDescriptionCfg in hwVectoringNlvGlobalConfig.
                          Modify the ranges of the leaves hwVectoringCrosstalkCouplingMatrixPortLocationList.
                          Modify the ranges of the leaves hwVectoringNlvStatus, hwVectoringNlvPeerId.
                          Add leaf node: hwVectoringNlvDescription, hwVectoringNlvTimestamp, hwVectoringNlvGroupDslamList, 
                          hwVectoringNlvClockSource and hwVectoringNlvFaultReason in hwVectoringNlvTable. 
                          Add leaf node: hwVectoringNlvServiceFaultAlarmTrap, hwVectoringNlvServiceRecoveryTrap in hwVectoringAlarmTraps.
                          "
                          
            REVISION     "201802120000Z"
            DESCRIPTION  "V1.31, changes in this revision:
                          Add leaf node hwVectoringCpeWhiteListConfig.
                          Add leaf node hwVectoringCpeWhiteList."  
                          
	    REVISION     "201710300000Z"
            DESCRIPTION  "V1.30, changes in this revision:
                          Delete the table of hwVectoringAutoGroupingTable."   

	    REVISION     "201707200000Z"
            DESCRIPTION  "V1.29, changes in this revision:
                          Add leaf node hwVectoringFextCoefConfig in hwVectoringGlobalConfig."   

            REVISION     "201612220000Z"
            DESCRIPTION  "V1.28, changes in this revision:
                          Add leaf node hwVectoringGfastStartTone in hwVectoringGlobalConfig."   
                          
            REVISION     "201512120000Z"
            DESCRIPTION  "V1.27, changes in this revision:
                          Modify the DESCRIPTION of the leaves node 
                          hwVectoringSingleWireInterruptionAutoShaping.
                          "

            REVISION     "201512040000Z"
            DESCRIPTION  "V1.26, changes in this revision:
                          Modify the DESCRIPTION of the leaves node 
                          hwVectoringConfProfGfastFextCanelControlDs and hwVectoringConfProfGfastFextCanelControlUs.
                          "

            
            REVISION     "201511070000Z"
            DESCRIPTION  "V1.25, changes in this revision:
                          Add leaf node hwVectoringSingleWireInterruptionAutoShaping.
                          Add leaf node hwVectoringConfProfGfastFextCanelControlDs.
                          Add leaf node hwVectoringConfProfGfastFextCanelControlUs."

            REVISION     "201507080000Z"
            DESCRIPTION  "V1.24, changes in this revision:
                          Add leaf node hwVectoringLongLoopDectionConfig.
                          Add leaf node hwVectoringLongLoopInsertionLoss.
                          Add leaf node hwVectoringLongLoopPolicy.
                          Add leaf node hwVectoringLinkLongLoopControlState.
                          Add leaf node hwVectoringLinkLongLoopPolicyUsed.
                          Add leaf node hwVectoringLinkLongLoopControlRemove."
			  
            REVISION     "201506270000Z"
            DESCRIPTION  "V1.23, changes in this revision:
                          Modify the DESCRIPTION of the leaf: hwVectoringVpMode."
                          
            REVISION     "201506210000Z"
            DESCRIPTION  "V1.22, changes in this revision:
                          Modify the DESCRIPTION of the leaves: hwVectoringLegacyCpeReservedBand, hwVectoringLegacyCpeToneBlackoutBand,
                          hwVectoringProfLegacyCpeReservedBand, hwVectoringProfLegacyCpeToneBlackoutBand.
                          Add leaf node hwVectoringVpMode in hwVectoringGlobalConfig."
                          
            REVISION     "201505050000Z"
            DESCRIPTION  "V1.21, changes in this revision:
                          Modify the range and the invalid value of the leaf node: hwVectoringLinkVcePortIndex."
						  
            REVISION     "201504270000Z"
            DESCRIPTION  "V1.20, changes in this revision:
                          Modify the DESCRIPTION of the leaf node hwVectoringProfLegacyCpeReservedBand and hwVectoringProfLegacyCpeToneBlackoutBand."

            REVISION     "201503180000Z"
            DESCRIPTION  "V1.19, changes in this revision:
                          Modify the SYNTAX INTEGER and DESCRIPTION of hwVectoringLinkCPEType according to standard."
                          
            REVISION     "201501290000Z"
            DESCRIPTION  "V1.18, changes in this revision:
                          Modify the type name of hwVectoringCrosstalkCouplingMatrixDirection."

            REVISION     "201412010000Z"
            DESCRIPTION  "V1.17, changes in this revision:
                          Add leaf node hwxdsl2FrequentlyRetrainReachFurtherControlPolicy.
                          Modify the leaf hwvdsl2LegacyCpeActivatedAlarmTrap name to hwXdslLegacyCpeActivatedAlarmTrap.
                          Modify the leaf hwvdsl2FrequentlyRetrainTimesReachThresholdAlarmTrap  name to hwXdslFrequentlyRetrainTimesReachThresholdAlarmTrap .
                          Add parameter g.fast(6) in hwVectoringLinkCPEType .
                         "

            REVISION     "201411250000Z"
            DESCRIPTION  "V1.16, changes in this revision:
                          Add leaf node hwvdsl2FrequentlyRetrainReachFurtherControlThresholdAlarmTrap, hwxdsl2FrequentlyRetrainReachFurtherControlTime.
                         "
            REVISION     "201409090000Z"
            DESCRIPTION  "V1.15, changes in this revision:
                          Add leaf node hwVectoringLimitProfLineSpectrumProf, hwVectoringLimitProfUpboProf in hwVectoringGlobalConfig.
                          Add leaf node hwVectoringConfProfLimitProfLineSpectrumProf, hwVectoringConfProfLimitProfUpboProf in hwVectoringConfProfTable.
                         "

            REVISION     "201407250000Z"
            DESCRIPTION  "V1.14, changes in this revision:
                          Add leaf node hwVectoringErbDetectLevel, hwVectoringReinEsDropThresholdDuringJoin, hwVectoringReinEsDropThresholdDuringTrack in hwVectoringGlobalConfig.
                         "

            REVISION     "201406290000Z"
            DESCRIPTION  "V1.13, changes in this revision:
                          Add hwVectoringPortList.
        Modify the description of leaf hwVectoringLinkClearCoefficient
       "
            REVISION     "201406200000Z"
            DESCRIPTION  "V1.11, changes in this revision:
                          Add leaf node hwVectoringSingleWireInterruptionDectionMeltConfig in hwVectoringGlobalConfig.
                          Modify the description of the node hwVectoringGroupNotReqBandsUs, hwVectoringGroupNotReqBandsDs,
                          hwVectoringGroupProtectionOfNotReqBandsDs, hwVectoringGroupProtectionOfNotReqBandsUs, hwVectoringHistoryCoefficientClear,
                          hwVectoringVceRunInfoCollectTimes, hwVectoringVceRunInfoCollectInterval, hwVectoringVceRunInfoCollectAlgoParaVictimPort,
                          hwVectoringVceRunInfoCollectAlgoParaDisturberPort.
                          Add leaf node hwVectoringProfDisorderLeavingThreshold in hwVectoringConfProfTable.
                         "

            REVISION     "201405150000Z"
            DESCRIPTION  "V1.10, changes in this revision:
                          Add bandplan998ade17spe1(7) in hwVectoringBandplanType.
                          Modify the description of the node hwVectoringBandplanType.
                          Modify the description of the nodes:hwVectoringLinkCPEType.
                          Add hwVectoringSingleWireInterruptionDetectionConfig.
                          Add hwVectoringLegacyCpeActivationAlarmTrap and hwVectoringLegacyCpeActivationRecoveryTrap.
                          Add hwVectoringServiceFaultAlarmTrap and hwVectoringServiceRecoveryTrap.
                          Add hwVectoringSingleWireInterruptionAlarmTrap and hwVectoringSingleWireInterruptionRecoveryTrap.
                         "
            REVISION     "201404220000Z"
            DESCRIPTION  "V1.09, changes in this revision:
                          Modify the description of the node hwVectoringVceRunInfoCollectAlgoParaDisturberLocation.
                         "

            REVISION     "201404020000Z"
            DESCRIPTION  "V1.08, changes in this revision:
                          Add leaf node hwVectoringVceRunInfoCollectRequestId in hwVectoringVceRunInfoCollectTable.
                          Add the definition of the node: hwVectoringVceRunInfoCollectRequestId in hwVectoringVceRunInfoCollectTrap.
                          Add leaf node hwVectoringLinkClearCoefficient in hwVectoringPortTable.
                          Add leaf node hwVectoringHistoryCoefficientClear in hwVectoringFastJoinConfig.
                         "

            REVISION     "201403180000Z"
            DESCRIPTION  "V1.07, changes in this revision:
                          Add default value of the node hwVectoringVceRunInfoCollectAlgoParaDisturberLocation.
                          Add leaf node hwVectoringCableType, hwVectoringLegacyCpeRatio in hwVectoringGlobalConfig.
                          Add leaf node hwVectoringProfCableType, hwVectoringProfLegacyCpeRatio in hwVectoringConfProfTable.
                         "

            REVISION     "201402120000Z"
            DESCRIPTION  "V1.06, changes in this revision:
                          Modify the range of the leaf node: hwVectoringGroupLinkList, hwVectoringLinkVcePortIndex,
                          hwVectoringCrosstalkCouplingMatrixPortIfindexList, hwVectoringCrosstalkCouplingMatrixAverageMagnitudeList,
                          hwVectoringCrosstalkCouplingMatrixCancellationStatusList, hwVectoringCrosstalkCouplingMatrixPortLocationList.
                          Modify the description of the nodes:hwVectoringLinkCPEType.
                         "

            REVISION     "201312180000Z"
            DESCRIPTION  "V1.06, changes in this revision:
                          Add the definition of the table: hwVectoringVceRunInfoCollectTable.
                          Add hwVectoringVceRunInfoCollectTrap.
                          Add hwVectoringVceRunInfoCollectResult in hwVectoringTrapsVbOids.
                         "

            REVISION     "201311050000Z"
            DESCRIPTION  "V1.05, changes in this revision:
                          Add hwVectoringProfChangeTrap and hwVectoringProfIDChangeTrap.
                          Add hwVectoringProfOperType in hwVectoringTrapsVbOids.
                         "

            REVISION     "201307190000Z"
            DESCRIPTION  "V1.05, changes in this revision:
                          Add leaf node hwVectoringConfProfLimitProfDsDataRateProf to hwVectoringConfProfTable.
                          Add leaf node hwVectoringConfProfLimitProfUsDataRateProf to hwVectoringConfProfTable.
                          Add leaf node hwVectoringConfProfLimitProfChanProf to hwVectoringConfProfTable.
                          Add leaf node hwVectoringLimitProfDsDataRateProf to hwVectoringGlobalConfig.
                          Add leaf node hwVectoringLimitProfUsDataRateProf to hwVectoringGlobalConfig.
                          Add leaf node hwVectoringLimitProfChanProf to hwVectoringGlobalConfig.
                          Add leaf node hwVectoringLinkLegacyPolicyUsed to hwVectoringPortTable.
                          Add leaf node hwVectoringLinkFallbackStatus to hwVectoringPortTable.
                          Add leaf node hwVectoringJoinFdps to hwVectoringFastJoinConfig.
                          Modify the node hwVectoringLinkLegacyPolicyUsed, add the value -1 indicates invalid value.
                         "

            REVISION     "201307100000Z"
            DESCRIPTION  "V1.04, changes in this revision:
                          Add the definition of the table: hwVectoringNlvTable, hwVectoringXlinMonitorTable.
                          Add leaf node hwVectoringCrosstalkCouplingMatrixPortLocationList to hwVectoringCrosstalkCouplingMatrixTable.
                          Add leaf node hwVectoringXlinChangeTrap to hwVectoringCommonTrapsPrefix.
                          Add the definition of the nodes: hwVectoringProfLegacyCpeActivatePolicy, hwVectoringProfLegacyCpeReservedBand,
                          hwVectoringProfLegacyCpeToneBlackoutBand in hwVectoringConfProfTable.
                          Modify the node hwVectoringLinkBelongedVceId.
                          Modify the description of the nodes: hwVectoringSwitch, hwVectoringLegacyCpeReservedBand, hwVectoringLegacyCpeToneBlackoutBand, hwVectoringHistoryCoefficient.
                         "

            REVISION     "201301150000Z"
            DESCRIPTION  "V1.03, changes in this revision:
                          Add the definition of the nodes: hwVectoringReceivedESRecoverAlarmTrap, hwVectoringPSConfigAbnormalAlarmTrap,
                          hwVectoringPSConfigRecoverAlarmTrap in hwVectoringTraps.
                         "

            REVISION     "201208260000Z"
            DESCRIPTION  "V1.02, changes in this revision:
                          Add leaf node hwVectoringLegacyCpeReservedBand and hwVectoringLegacyCpeToneBlackoutBand.
                          Create table hwVectoringFastJoinConfig and hwVectoringCrosstalkCouplingMatrixTable.
                          Add leaf node hwVectoringGroupProtectionOfNotReqBandsDs and hwVectoringGroupProtectionOfNotReqBandsUs.
                          Add leaf node hwVectoringLinkCPEType to get the CPE type connected to the port.
                          Add leaf node hwVectoringGlobalConfigChangeTrap to notify the change vectoring global configuration.
                          Create table hwVectoringCommonTraps to fetch the vectoring traps.
                          Add leaf node hwVectoringGlobalConfigChangeTrap.
                          Add leaf node hwVectoringVictCoefAbnormalVariationAlarmTrap, hwVectoringDistCoefAbnormalVariationAlarmTrap,
                          hwVectoringReceivedESAbnormalAlarmTrap, hwvdsl2LegacyCpeActivatedAlarmTrap and hwvdsl2FrequentlyRetrainTimesReachThresholdAlarmTrap.
                          Modify the node hwVectoringGroupIndex, hwVectoringLinkBelongedVceId
                          and hwVectoringAutoGroupingGroupIndex.
                          Create table hwVectoringTrapsVbOids.
                          Add leaf node hwVectoringPortFrequentRetrainTimes.
                          delete unnecessary en dashes.
                          Add the definition of the table hwVectoringAutoGroupingTable,
                          hwVectoringCrosstalkCouplingMatrixTable, hwVectoringAlarmTraps.
                          add value forceFriendlyDsLimitUs(4) and forceFriendlyDsNoLimitUs(5) for hwVectoringLegacyCpeActivatePolicy and modify the description .
                         "

            REVISION     "201202150000Z"
            DESCRIPTION  "V1.01, changes in this revision:
                          Add the definition of the table: hwVectoringGroupTable, hwVectoringConfProfTable, hwVectoringPortTable.
                          Add the definition of the nodes: hwVectoringLegacyCpeActivatePolicy in hwVectoringGlobalConfig.
                          Add the definition of the nodes: hwVectoringLinkBandPlanCompatible in hwVectoringPortTable.
                          Add the definition of the nodes: hwVectoringBandplanType, hwVectoringUs0Type, hwVectoringAnnexALimitMask in hwVectoringGlobalConfig.
                         "

            REVISION     "201109010000Z"
            DESCRIPTION  "V1.00, initial version"

            ::= { huaweiUtility 171 }

--
-- Textual conventions
--

--
-- Vectoring table
--
    hwVectoringGlobalConfig OBJECT IDENTIFIER ::= { hwVectoringMIB 1 }

    hwVectoringSwitch OBJECT-TYPE
    SYNTAX INTEGER
    {
        enable(1),
        disable(2)
    }
    MAX-ACCESS  read-write
    STATUS      current
    DESCRIPTION
        "Enable/Disable the global vectoring configuration.
         Warning: this operation will reactivate all the VDSL ports supporting vectoring and may take several minutes.
         Default values:disable.
         Options:
         1. enable(1)  - Enables the global vectoring configuration
         2. disable(2) - Disables the global vectoring configuration
        "
    ::= { hwVectoringGlobalConfig 1 }

    hwVectoringLegacyCpeActivatePolicy OBJECT-TYPE
        SYNTAX INTEGER
        {
            noLimit(1),
            block(2),
            limit(3),
            forceFriendlyDsLimitUs(4),
            forceFriendlyDsNoLimitUs(5)
        }
        MAX-ACCESS  read-write
        STATUS      current
        DESCRIPTION
            "Vectoring legacy cpe activate policy.
             Default values:limit.
             Options:
             1. noLimit(1)                    - The legacy cpe is allowed to activated in G.993.2 operation mode
             2. block(2)                      - The legacy cpe is not allowed to activated in G.993.2 operation mode
             3. limit(3)                      - The legacy cpe is allowed to activated in G.993.2 operation mode,
                                                with PSD auto shaped to eliminate the self-FEXT to vectoring lines
             4. forceFriendlyDsLimitUs(4)     - Force friendly is used in the downstream direction, and PSD automatic
                                                shaping is used in the upstream direction
             5. forceFriendlyDsNoLimitUs(5)   - Force friendly is used in the downstream direction, and no restriction
                                                is set for the upstream direction
            "
        ::= { hwVectoringGlobalConfig 2 }

    hwVectoringBandplanType OBJECT-TYPE
        SYNTAX INTEGER
        {
            bandplanAnnexa(1),
            bandplanAnnexc(2),
            bandplan997e(3),
            bandplan998ade(4),
            bandplan998e(5),
            bandplanHPE(6),
            bandplan998ade17spe1(7),
            bandplanCN (8),
            bandplanCN1(9)
        }
        MAX-ACCESS  read-write
        STATUS      current
        DESCRIPTION
            "Vectoring global frequency plan types.
             Default values:bandplan998ade.
             Options:
             1. bandplanAnnexa(1)           - The frequency plan types for the vectoring feature is Annex A
             2. bandplanAnnexc(2)           - The frequency plan types for the vectoring feature is Annex C
             3. bandplan997e(3)             - The frequency plan types for the vectoring feature is 997E
             4. bandplan998ade(4)           - The frequency plan types for the vectoring feature is 998ADE
             5. bandplan998e(5)             - The frequency plan types for the vectoring feature is 998E
             6. bandplanHPE(6)              - The frequency plan types for the vectoring feature is HPE
             7. bandplan998ade17spe1(7)     - The frequency plan types for the vectoring feature is 998ADE17SPE-1
             8. bandplanCN (8)              - The frequency plan types for the vectoring feature is CN
             9. bandplanCN1(9)              - The frequency plan types for the vectoring feature is CN-1
            "
        ::= { hwVectoringGlobalConfig 3 }

    hwVectoringUs0Type OBJECT-TYPE
        SYNTAX INTEGER
        {
            us0TypeA(1),
            us0TypeB(2),
            us0TypeM(3),
            us0TypeN(4),
            invalidValue(-1)
        }
        MAX-ACCESS  read-write
        STATUS      current
        DESCRIPTION
            "Vectoring us0 type.
             Default values:us0TypeA.
             Options:
             1. us0TypeA(1)      - US0 type is US0-type A
             2. us0TypeB(2)      - US0 type is US0-type B
             3. us0TypeM(3)      - US0 type is US0-type M
             4. us0TypeN(4)      - US0 type is US0-type N/A
             5. invalidValue(-1) - US0 type return -1 when vectoring frequency plan types is Annex A/Annex C
            "
        ::= { hwVectoringGlobalConfig 4 }

    hwVectoringAnnexALimitMask OBJECT-TYPE
        SYNTAX INTEGER
        {
            d32(1),
            d48(2),
            d64(3),
            d128(4),
            invalidValue(-1)
        }
        MAX-ACCESS  read-write
        STATUS      current
        DESCRIPTION
            "AnnexA limit mask.
             Options:
             1. d32(1)          - AnnexA limit mask is D-32
             2. d48(2)          - AnnexA limit mask is D-48
             3. d64(3)          - AnnexA limit mask is D-64
             4. d128(4)         - AnnexA limit mask is D-128
             5. invalidValue(-1) - AnnexA limit mask return -1 when vectoring frequency plan types is not Annex A
            "
        ::= { hwVectoringGlobalConfig 5 }

    hwVectoringLegacyCpeReservedBand OBJECT-TYPE
        SYNTAX      OCTET STRING (SIZE(0..79))
        MAX-ACCESS  read-write
        STATUS      current
        DESCRIPTION
                        "This object is used to set the reserved band of a legacy CPE.
                         The PSD on the frequency band is not shaped and the frequency band can carry traffic.
                         This object takes effect when hwVectoringLegacyCpeActivatePolicy is set to limit.
                         Range of the subcarrier IDs: 0-8191. Two subcarriers are separated by a comma (,).
                         The format is: start subcarrier ID-end subcarrier ID.
                         The start subcarrier ID cannot be greater than the end subcarrier ID.
                         Only eight reserved band is supported, for example, 880-900,1000-1100.
                         The settings of hwVectoringLegacyCpeReservedBand and
                         hwVectoringLegacyCpeToneBlackoutBand cannot overlap with each other.
                        "
        ::= { hwVectoringGlobalConfig 6 }

    hwVectoringLegacyCpeToneBlackoutBand OBJECT-TYPE
        SYNTAX      OCTET STRING (SIZE(0..79))
        MAX-ACCESS  read-write
        STATUS      current
        DESCRIPTION
           "This object is used to set the blackout band of a legacy CPE.
            The blackout frequency band is disabled and cannot carry traffic.
            This object takes effect when hwVectoringLegacyCpeActivatePolicy is set to limit.
            Range of the subcarrier IDs: 0-8191. Two subcarriers are separated by a comma (,).
            The format is: start subcarrier ID-end subcarrier ID.
            The start subcarrier ID cannot be greater than the end subcarrier ID.
            Only eight tone blackout band is supported, for example, 1300-1320,1400-1500.
            The settings of hwVectoringLegacyCpeReservedBand and
            hwVectoringLegacyCpeToneBlackoutBand cannot overlap with each other.
            "
       ::= { hwVectoringGlobalConfig 7 }

    hwVectoringLimitProfDsDataRateProf OBJECT-TYPE
        SYNTAX      OCTET STRING (SIZE(0..128))
        MAX-ACCESS  read-write
        STATUS      current
        DESCRIPTION
           "The value of this object identifies the row in the XDSL Data Rate Configuration Profile Table,
            (hwVOPDataRateConfProfTable) that applies to vectoring link when the line is activated in non-vectoring mode(G.993.2).
            If the vectoring limit profile is unused, then the object is set to a zero length string.
           "
       ::= { hwVectoringGlobalConfig 8 }

    hwVectoringLimitProfUsDataRateProf OBJECT-TYPE
        SYNTAX      OCTET STRING (SIZE(0..128))
        MAX-ACCESS  read-write
        STATUS      current
        DESCRIPTION
           "The value of this object identifies the row in the XDSL Data Rate Configuration Profile Table,
            (hwVOPDataRateConfProfTable) that applies to vectoring link when the line is activated in non-vectoring mode(G.993.2).
            If the vectoring limit profile is unused, then the object is set to a zero length string.
           "
       ::= { hwVectoringGlobalConfig 9 }

    hwVectoringLimitProfChanProf OBJECT-TYPE
        SYNTAX      OCTET STRING (SIZE(0..32))
        MAX-ACCESS  read-write
        STATUS      current
        DESCRIPTION
           "The value of this object identifies the row in the VDSL2 Channel Configuration Profile Table,
            (Vdsl2ChanConfProfileTable) that applies to vectoring link when the line is activated in non-vectoring mode(G.993.2).
            If the vectoring limit profile is unused, then the object is set to a zero length string.
           "
       ::= { hwVectoringGlobalConfig 10 }

    hwVectoringSingleWireInterruptionDetectionConfig OBJECT-TYPE
        SYNTAX INTEGER
        {
            enable(1),
            disable(2)
        }
        MAX-ACCESS  read-write
        STATUS      current
        DESCRIPTION
            "Enable/Disable the vectoring single-wire interruption detection.
             Default values:disable.
             Options:
             1. enable(1)  - Enables the vectoring detection configuration
             2. disable(2) - Disables the vectoring detection configuration
            "
       ::= { hwVectoringGlobalConfig 11 }

    hwVectoringCableType OBJECT-TYPE
        SYNTAX INTEGER
        {
            atis(1),
            quad(2),
            paperInsulated(3),
            tp100(4),
            other(5)
        }
        MAX-ACCESS  read-write
        STATUS      current
        DESCRIPTION
            "Cable type.
             Default values: atis
             Options:
             1. atis(1)           - ATIS
             2. quad(2)           - Quad
             3. paperInsulated(3) - Paper Insulated
             4. tp100(4)          - TP100
             5. other(5)          - Other
            "
        ::= { hwVectoringGlobalConfig 12 }

    hwVectoringLegacyCpeRatio OBJECT-TYPE
        SYNTAX Unsigned32 (0..3)
        MAX-ACCESS  read-write
        STATUS      current
        DESCRIPTION
            "Legacy CPE ratio.
             Default values: 0
             Options:
             0: 1%~15%
             1: 15%~25%
             2: 25%~50%
             3: >50%
            "
        ::= { hwVectoringGlobalConfig 13 }

     hwVectoringSingleWireInterruptionDectionMeltConfig OBJECT-TYPE
        SYNTAX INTEGER
        {
            enable(1),
            disable(2)
        }
        MAX-ACCESS  read-write
        STATUS      current
        DESCRIPTION
            "Enable/Disable the vectoring melt detection.
             This parameter must be used together with hwVectoringSingleWireInterruptionDetectionConfig.
             This parameter is configurable only when hwVectoringSingleWireInterruptionDetectionConfig is enabled.
             Default values:disable.
             Options:
             1. enable(1)  - Enable melt detection for vectoring single wire interruption detection
             2. disable(2) - Disable melt detection for vectoring single wire interruption detection
            "
       ::= { hwVectoringGlobalConfig 14 }

    hwVectoringErbDetectLevel OBJECT-TYPE
        SYNTAX Unsigned32 (0..1)
        MAX-ACCESS  read-write
        STATUS      current
        DESCRIPTION
            "The level of detecting ERB(Errorcode Report Bloack) decide that how to judge the valid ERB.
             Default values: 0
             Options:
             0: ERB validity detection.
             1: ERB validity and ERB noise detection.
            "
        ::= { hwVectoringGlobalConfig 16 }

    hwVectoringReinEsDropThresholdDuringJoin OBJECT-TYPE
        SYNTAX Unsigned32 (0..100)
        MAX-ACCESS  read-write
        STATUS      current
        DESCRIPTION
            "In the joining, when the rate of dropped ES(Errorcode Sample) is larger than the threshold,
             this line's percode coef don't be calculated and updated.
             Default values: 75
            "
        ::= { hwVectoringGlobalConfig 17 }

    hwVectoringReinEsDropThresholdDuringTrack OBJECT-TYPE
        SYNTAX Unsigned32 (0..100)
        MAX-ACCESS  read-write
        STATUS      current
        DESCRIPTION
            "In the tracking, when the rate of dropped ES is larger than the threshold,
             this line's percode coef don't be calculated and updated.
             Default values: 7
            "
        ::= { hwVectoringGlobalConfig 18 }

    hwVectoringLimitProfLineSpectrumProf OBJECT-TYPE
        SYNTAX      OCTET STRING (SIZE(0..128))
        MAX-ACCESS  read-write
        STATUS      current
        DESCRIPTION
           "The value of this object identifies the row in the XDSL Line Spectrum Configuration Profile Table,
            (hwVOPLineSpectrumConfProfTable) that applies to vectoring link when the line is activated in non-vectoring mode(G.993.2).
            If the vectoring limit profile is unused, then the object is set to a zero length string.
           "
       ::= { hwVectoringGlobalConfig 19 }

    hwVectoringLimitProfUpboProf OBJECT-TYPE
        SYNTAX      OCTET STRING (SIZE(0..128))
        MAX-ACCESS  read-write
        STATUS      current
        DESCRIPTION
           "The value of this object identifies the row in the XDSL Upbo Configuration Profile Table,
            (hwVOPUPBOConfProfTable) that applies to vectoring link when the line is activated in non-vectoring mode(G.993.2).
            If the vectoring limit profile is unused, then the object is set to a zero length string.
           "
       ::= { hwVectoringGlobalConfig 20 }
       
   hwVectoringVpMode OBJECT-TYPE
        SYNTAX INTEGER    
        {
            mode192(1),
            mode384(2)
        }
        MAX-ACCESS  read-write
        STATUS      current
        DESCRIPTION
           "The value of this object identifies the vector vp-mode.
            Default values:mode384.
            Options:
             1. mode192(1) - The 192 mode of vectoring board
             2. mode384(2) - The 384 mode of vectoring board
           "
       ::= { hwVectoringGlobalConfig 21 }
       
	hwVectoringLongLoopDectionConfig OBJECT-TYPE
        SYNTAX INTEGER
        {
            disable(0),
            enable(1)
        }
        MAX-ACCESS  read-write
        STATUS      current
        DESCRIPTION
            "Enable/Disable the long loop detection.
             This parameter must be used together with hwVectoringLongLoopPolicy when it is enabled.
             Default values:disable.
             Options:
             1. disable(0)  - Disable long loop detection
             2. enable(1)   - Enable long loop detection
            "
       ::= { hwVectoringGlobalConfig 22 }
    
	hwVectoringLongLoopInsertionLoss OBJECT-TYPE
        SYNTAX Unsigned32 (20..40 | 4294967295)
        MAX-ACCESS  read-write
        STATUS      current
        DESCRIPTION
            "The value of this object identifies the long loop insertion loss.
             This parameter must be used together with hwVectoringLongLoopDectionConfig.
             This parameter is configurable only when hwVectoringLongLoopDectionConfig is enabled.
             Value 4294967295 means invalid value.
             Default values: 25 dB
            "
        ::= { hwVectoringGlobalConfig 23 }
		
	hwVectoringLongLoopPolicy OBJECT-TYPE
        SYNTAX INTEGER
        {
            nonVectoring(0),
            nonFextCanceling(1),
            invalidValue(-1)
        }
        MAX-ACCESS  read-write
        STATUS      current
        DESCRIPTION
            "The value of this object identifies the long loop policy.
             This parameter must be used together with hwVectoringLongLoopDectionConfig.
             This parameter is configurable only when hwVectoringLongLoopDectionConfig is enabled.
             Options:
             1. nonVectoring(0)       - Policy of non-vectoring. 
                                        If a vectoring port meets long line control requirements, 
                                        the vectoring port is considered as a legacy port during initialization.
             2. nonFextCanceling(1)   - Policy of non-fext-canceling.
                                        If a vectoring port meets long line control requirements, 
                                        the vectoring port does not perform crosstalk cancellation.
             3. invalidValue(-1)      - Invalid value, Default value, only read is supported. 
            "
       ::= { hwVectoringGlobalConfig 24 }
       
   	hwVectoringSingleWireInterruptionAutoShaping OBJECT-TYPE
        SYNTAX INTEGER
        {
            enable(1),
            disable(2)
        }
        MAX-ACCESS  read-write
        STATUS      current
        DESCRIPTION
            "Enable/Disable the global vectoring Single Wire Interruption Auto Shaping.
             This parameter must be used together with hwVectoringSingleWireInterruptionDetectionConfig.
             This parameter is configurable only when hwVectoringSingleWireInterruptionDetectionConfig is enabled.
             Default values:disable.
             Options:
             1. enable(1)  - Enable the auto shaping detection for vectoring single wire interruption detection.  
             2. disable(2) - Disable the auto shaping detection for vectoring single wire interruption detection.
            "
        ::= { hwVectoringGlobalConfig 25 }

    hwVectoringGfastStartTone OBJECT-TYPE
        SYNTAX      Unsigned32 (43..1023)
        MAX-ACCESS  read-write
        STATUS      current
        DESCRIPTION
            "It is the global start tone for G.fast lines. In a G.fast and 
             VDSL hybrid scenario, you can configure this parameter to set 
             the start tone of the frequency band used by G.fast lines. 
             Default values: 43
            "
        ::= { hwVectoringGlobalConfig 26 }

   	hwVectoringFextCoefConfig OBJECT-TYPE
        SYNTAX INTEGER
        {
            normal(1),
            premium(2)
        }
        MAX-ACCESS  read-write
        STATUS      current
        DESCRIPTION
            "The value of this object identifies whether the premium vectoring processing is enabled.
            Default values : normal.     
	    Options:
             1. normal(1) - The premium vectoring processing is disabled
             2. premium(2) - The premium vectoring processing is enabled    
            "
        ::= { hwVectoringGlobalConfig 27 }
        
    hwVectoringCpeWhiteListConfig OBJECT-TYPE
        SYNTAX INTEGER
        {
            enable(1),
            disable(2)
        }
        MAX-ACCESS  read-write
        STATUS      current
        DESCRIPTION
            "Enable/Disable the global vectoring cpe white list configuration.
             Default values: disable.
             Options:
             1. enable(1)  - Enable the global vectoring cpe white list configuration.  
             2. disable(2) - Disable the global vectoring cpe white list configuration.
            "
        ::= { hwVectoringGlobalConfig 28 }
    
    hwVectoringCpeWhiteList OBJECT-TYPE    
        SYNTAX      OCTET STRING (SIZE (0..64))
        MAX-ACCESS  read-write
        STATUS      current
        DESCRIPTION
            "This object defines the global vectoring cpe white list.
             This is a string of 4 bytes of values indicates the type of vectoring cpe.
             Default values: BDCMTRID. 
             the default value can not be deleted.
             If the vectoring cpe white list is unused, then the object is set to a zero length string."
        ::= { hwVectoringGlobalConfig 29 }
        
    hwVectoringVpBoardMode OBJECT-TYPE    
        SYNTAX INTEGER    
        {
            fast(1),
            vdsl(2)
        }
        MAX-ACCESS  read-write
        STATUS      current
        DESCRIPTION
           "The value of this object identifies the vector vp-board-mode.
            Default values:fast.
            Options:
             1. fast(1)   - The G.fast mode of vectoring board
             2. vdsl(2)   - The vdsl mode of vectoring board
           "
       ::= { hwVectoringGlobalConfig 30 }       
        
--       hwVectoringGroupTable
    hwVectoringGroupTable OBJECT-TYPE
        SYNTAX SEQUENCE OF HwVectoringGroupEntry
        MAX-ACCESS not-accessible
        STATUS current
        DESCRIPTION
            "The table hwVectoringGroupTable contains the vectoring group
             configuration.
             The index of this table is hwVectoringGroupIndex.
            "
        ::= { hwVectoringMIB 2 }

     hwVectoringGroupEntry OBJECT-TYPE
        SYNTAX HwVectoringGroupEntry
        MAX-ACCESS not-accessible
        STATUS current
        DESCRIPTION
             "The table hwVectoringGroupTable contains the vectoring group
             configuration.
             The index of this entry is hwVectoringGroupIndex.
            "
        INDEX { hwVectoringGroupIndex }
        ::= { hwVectoringGroupTable 1 }

    HwVectoringGroupEntry ::=
        SEQUENCE
            {
                hwVectoringGroupIndex                      Unsigned32,
                hwVectoringGroupNotReqBandsUs              OCTET STRING,
                hwVectoringGroupNotReqBandsDs              OCTET STRING,
                hwVectoringGroupLinkList                   OCTET STRING,
                hwVectoringGroupRowStatus                  RowStatus,
                hwVectoringGroupProtectionOfNotReqBandsDs  INTEGER,
                hwVectoringGroupProtectionOfNotReqBandsUs  INTEGER
            }

    hwVectoringGroupIndex OBJECT-TYPE
        SYNTAX      Unsigned32 (1..96)
        MAX-ACCESS  not-accessible
        STATUS      current
        DESCRIPTION
            "This object identifies a row in this table.
             The vectoring group 1 is the default group, can not add and delete.
            "
        ::= { hwVectoringGroupEntry 1 }

    hwVectoringGroupNotReqBandsUs OBJECT-TYPE
        SYNTAX      OCTET STRING (SIZE(0..79))
        MAX-ACCESS  read-create
        STATUS      current
        DESCRIPTION
          "This configuration parameter shall be an array of pairs of
           sub-carrier indices for uptream . Each pair represents the
           start and stop sub-carrier index of a frequency band in which
           FEXT cancellation is not required. Up to 8 frequency bands may
           be configured.
           for example :880-900,1000-1020.
           This parameter must be used together with hwVectoringGroupProtectionOfNotReqBandsUs.
           This parameter is configurable only when hwVectoringGroupProtectionOfNotReqBandsUs
     is enabled.
          "
        ::= { hwVectoringGroupEntry 2 }

    hwVectoringGroupNotReqBandsDs OBJECT-TYPE
        SYNTAX      OCTET STRING (SIZE(0..79))
        MAX-ACCESS  read-create
        STATUS      current
        DESCRIPTION
           "This configuration parameter shall be an array of pairs of
            sub-carrier indices for downstream . Each pair represents the
            start and stop sub-carrier index of a frequency band in which
            FEXT cancellation is not required. Up to 8 frequency bands may
            be configured.
            for example :1300-1320,1400-1450.
            This parameter must be used together with hwVectoringGroupProtectionOfNotReqBandsDs.
            This parameter is configurable only when hwVectoringGroupProtectionOfNotReqBandsDs
      is enabled.
           "
        ::= { hwVectoringGroupEntry 3 }

    hwVectoringGroupLinkList OBJECT-TYPE
        SYNTAX      OCTET STRING (SIZE (0..4096))
        MAX-ACCESS  read-create
        STATUS      current
        DESCRIPTION
            "This object defines the link list of the vectoring group.
             This is a string of 4 bytes of values indicates the port ifindex.
             It can contain as most as 1024 link."
        ::= { hwVectoringGroupEntry 4 }

    hwVectoringGroupRowStatus OBJECT-TYPE
        SYNTAX      RowStatus
        MAX-ACCESS  read-create
        STATUS      current
        DESCRIPTION
            "This object is used to create a new row or delete an existing row
             in this table.
            "
        ::= { hwVectoringGroupEntry 5 }

    hwVectoringGroupProtectionOfNotReqBandsDs OBJECT-TYPE
        SYNTAX INTEGER {
                           enable (1),
                           disable (2)
                       }
        MAX-ACCESS  read-create
        STATUS      current
        DESCRIPTION
                   "This object enable/disable the protection of vectoring
                    lines downstream.
        This parameter must be used together with hwVectoringGroupNotReqBandsDs.
                    hwVectoringGroupNotReqBandsDs cannot be null when this node is set to enable.
                    Options:
                    1. enable(1)- The protection of vectoring lines downstream
                                   is enabled
                    2. disable(2) - The protection of vectoring lines downstream
                                   is disabled
                   "
        DEFVAL       { disable }
        ::= { hwVectoringGroupEntry 6 }

    hwVectoringGroupProtectionOfNotReqBandsUs OBJECT-TYPE
        SYNTAX INTEGER {
                           enable (1),
                           disable (2)
                       }
        MAX-ACCESS  read-create
        STATUS      current
        DESCRIPTION
                   "This object enable/disable the protection of vectoring
                    lines upstream.
        This parameter must be used together with hwVectoringGroupNotReqBandsUs.
        hwVectoringGroupNotReqBandsUs cannot be null when this node is set to enable.
                    Options:
                    1. enable(1)- The protection of vectoring lines upstream
                                   is enabled
                    2. disable(2) - The protection of vectoring lines upstream
                                   is disabled
                   "
        DEFVAL       { disable }
        ::= { hwVectoringGroupEntry 7 }

--       hwVectoringConfProfTable
    hwVectoringConfProfTable OBJECT-TYPE
        SYNTAX SEQUENCE OF HwVectoringConfProfEntry
        MAX-ACCESS not-accessible
        STATUS current
        DESCRIPTION
            "The table hwVectoringConfProfTable contains the vectoring profile
             configuration.
             A default profile with an index of 'DEFVAL' will always exist and
             its parameters will be set to vendor-specific values, unless otherwise
             specified in this document.
             The index of this table is hwVectoringProfName."
        ::= { hwVectoringMIB 3 }

     hwVectoringConfProfEntry OBJECT-TYPE
        SYNTAX HwVectoringConfProfEntry
        MAX-ACCESS not-accessible
        STATUS current
        DESCRIPTION
             "The table hwVectoringConfProfTable contains the vectoring profile
              configuration.
              A default profile with an index of 'DEFVAL' will always exist and
              its parameters will be set to vendor-specific values, unless otherwise
              specified in this document.
              The index of this entry is hwVectoringProfName."
        INDEX { IMPLIED hwVectoringProfName }
        ::= { hwVectoringConfProfTable 1 }

    HwVectoringConfProfEntry ::=
        SEQUENCE
            {
                hwVectoringProfName                        OCTET STRING,
                hwVectoringEnableUs                        INTEGER,
                hwVectoringEnableDs                        INTEGER,
                hwVectoringProfRowStatus                   RowStatus,
                hwVectoringProfLegacyCpeActivatePolicy     INTEGER,
                hwVectoringProfLegacyCpeReservedBand       OCTET STRING,
                hwVectoringProfLegacyCpeToneBlackoutBand   OCTET STRING,
                hwVectoringConfProfLimitProfDsDataRateProf OCTET STRING,
                hwVectoringConfProfLimitProfUsDataRateProf OCTET STRING,
                hwVectoringConfProfLimitProfChanProf       OCTET STRING,
                hwVectoringConfVectoringModeCfg            Integer32,
                hwVectoringProfCableType                   INTEGER,
                hwVectoringProfLegacyCpeRatio              Unsigned32,
                hwVectoringProfDisorderLeavingThreshold    Unsigned32,
                hwVectoringConfProfLimitProfLineSpectrumProf  OCTET STRING,
                hwVectoringConfProfLimitProfUpboProf          OCTET STRING,
                hwVectoringConfProfGfastFextCanelControlDs    INTEGER,
                hwVectoringConfProfGfastFextCanelControlUs    INTEGER
            }

    hwVectoringProfName OBJECT-TYPE
        SYNTAX      OCTET STRING (SIZE(1..32))
        MAX-ACCESS  accessible-for-notify
        STATUS      current
        DESCRIPTION
            "This object identifies a row in this table."
        ::= { hwVectoringConfProfEntry 1 }

    hwVectoringEnableUs OBJECT-TYPE
        SYNTAX INTEGER
        {
            enable(1),
            disable(2)
        }
        MAX-ACCESS  read-create
        STATUS      current
        DESCRIPTION
            "Enable/Disable FEXT cancellation control upstream.
             Default values: enable.
             Options:
             1. enable(1)  - Enable FEXT cancellation in the upstream direction from all the other vectoring lines into the line in the vectoring group
             2. disable(2) - Disable FEXT cancellation in the upstream direction from all the other vectoring lines into the line in the vectoring group."
        DEFVAL       { enable }
        ::= { hwVectoringConfProfEntry 2 }

    hwVectoringEnableDs OBJECT-TYPE
        SYNTAX INTEGER
        {
            enable(1),
            disable(2)
        }
        MAX-ACCESS  read-create
        STATUS      current
        DESCRIPTION
            "Enable/Disable FEXT cancellation control downstream.
             Default values: enable.
             Options:
             1. enable(1)  - Enable FEXT cancellation in the downstream direction from all the other vectoring lines into the line in the vectoring group
             2. disable(2) - Disable FEXT cancellation in the downstream direction from all the other vectoring lines into the line in the vectoring group"
        DEFVAL       { enable }
        ::= { hwVectoringConfProfEntry 3 }

    hwVectoringProfRowStatus OBJECT-TYPE
        SYNTAX      RowStatus
        MAX-ACCESS  read-create
        STATUS      current
        DESCRIPTION
            "This object is used to create a new row or delete an existing row
             in this table. Before a profile can be deleted, it must be not
             referenced from all VDSL ports."
        ::= { hwVectoringConfProfEntry 4 }

    hwVectoringProfLegacyCpeActivatePolicy OBJECT-TYPE
        SYNTAX INTEGER
        {
            noLimit(1),
            block(2),
            limit(3),
            forceFriendlyDsLimitUs(4),
            forceFriendlyDsNoLimitUs(5),
            global(255)
        }
        MAX-ACCESS  read-write
        STATUS      current
        DESCRIPTION
            "Vectoring legacy cpe activate policy.
             Default values:global.
             Options:
             1. noLimit(1)                    - The legacy cpe is allowed to activated in G.993.2 operation mode
             2. block(2)                      - The legacy cpe is not allowed to activated in G.993.2 operation mode
             3. limit(3)                      - The legacy cpe is allowed to activated in G.993.2 operation mode,
                                                with PSD auto shaped to eliminate the self-FEXT to vectoring lines
             4. forceFriendlyDsLimitUs(4)     - Force friendly is used in the downstream direction, and PSD automatic
                                                shaping is used in the upstream direction
             5. forceFriendlyDsNoLimitUs(5)   - Force friendly is used in the downstream direction, and no restriction
                                                is set for the upstream direction
             6. global(255)                   - Use the global vectoring legacy CPE activation policy
            "
        ::= { hwVectoringConfProfEntry 5 }

    hwVectoringProfLegacyCpeReservedBand OBJECT-TYPE
        SYNTAX      OCTET STRING (SIZE(0..79))
        MAX-ACCESS  read-write
        STATUS      current
        DESCRIPTION
          "This object is used to set the reserved band of a legacy CPE.
           The PSD on the frequency band is not shaped and the frequency band can carry traffic.
           This object takes effect when hwVectoringProfLegacyCpeActivatePolicy is set to limit.
           Range of the subcarrier IDs: 0-8191. Two subcarriers are separated by a comma (,).
           The format is: start subcarrier ID-end subcarrier ID.
           The start subcarrier ID cannot be greater than the end subcarrier ID.
           Only eight reserved band is supported, for example, 880-900,1000-1100.
           The settings of hwVectoringProfLegacyCpeReservedBand and
           hwVectoringProfLegacyCpeToneBlackoutBand cannot overlap with each other.
           If the reserved band of a legacy CPE is not configured, then the object is set to a zero length string.
          "
        ::= { hwVectoringConfProfEntry 6 }

    hwVectoringProfLegacyCpeToneBlackoutBand OBJECT-TYPE
        SYNTAX      OCTET STRING (SIZE(0..79))
        MAX-ACCESS  read-write
        STATUS      current
        DESCRIPTION
           "This object is used to set the blackout band of a legacy CPE.
            The blackout frequency band is disabled and cannot carry traffic.
            This object takes effect when hwVectoringProfLegacyCpeActivatePolicy is set to limit.
            Range of the subcarrier IDs: 0-8191. Two subcarriers are separated by a comma (,).
            The format is: start subcarrier ID-end subcarrier ID.
            The start subcarrier ID cannot be greater than the end subcarrier ID.
            Only eight tone blackout band is supported, for example, 1300-1320,1400-1500.
            The settings of hwVectoringProfLegacyCpeReservedBand and
            hwVectoringProfLegacyCpeToneBlackoutBand cannot overlap with each other.
            If the blackout band of a legacy CPE is not configured, then the object is set to a zero length string.
            "
       ::= { hwVectoringConfProfEntry 7 }

    hwVectoringConfProfLimitProfDsDataRateProf OBJECT-TYPE
        SYNTAX      OCTET STRING (SIZE(0..128))
        MAX-ACCESS  read-write
        STATUS      current
        DESCRIPTION
           "The value of this object identifies the row in the XDSL Data Rate Configuration Profile Table,
            (hwVOPDataRateConfProfTable) that applies to vectoring link when the line is activated in non-vectoring mode(G.993.2).
            If the vectoring limit profile is unused, then the object is set to a zero length string.
           "
       ::= { hwVectoringConfProfEntry 8 }

    hwVectoringConfProfLimitProfUsDataRateProf OBJECT-TYPE
        SYNTAX      OCTET STRING (SIZE(0..128))
        MAX-ACCESS  read-write
        STATUS      current
        DESCRIPTION
           "The value of this object identifies the row in the XDSL Data Rate Configuration Profile Table,
            (hwVOPDataRateConfProfTable) that applies to vectoring link when the line is activated in non-vectoring mode(G.993.2).
            If the vectoring limit profile is unused, then the object is set to a zero length string.
           "
       ::= { hwVectoringConfProfEntry 9 }

    hwVectoringConfProfLimitProfChanProf OBJECT-TYPE
        SYNTAX      OCTET STRING (SIZE(0..32))
        MAX-ACCESS  read-write
        STATUS      current
        DESCRIPTION
           "The value of this object identifies the row in the VDSL2 Channel Configuration Profile Table,
            (Vdsl2ChanConfProfileTable) that applies to vectoring link when the line is activated in non-vectoring mode(G.993.2).
            If the vectoring limit profile is unused, then the object is set to a zero length string.
           "
       ::= { hwVectoringConfProfEntry 10 }

    hwVectoringConfVectoringModeCfg OBJECT-TYPE
        SYNTAX Integer32 (0..7)
        MAX-ACCESS  read-write
        STATUS      current
        DESCRIPTION
           "Indicates the access controlling of the type of friendly or vectoring cpe.
            Bit0 represent vectoring allowed or not allowed,0 represents not allowed,1 represents allowed.
            bit1 represent full-friendly allowed or not allowed,0 represents not allowed,1 represents allowed.
            bit2 represent friendly-ds allowed or not allowed,0 represents not allowed,1 represents allowed.
           "
       ::= { hwVectoringConfProfEntry 11 }

    hwVectoringProfCableType OBJECT-TYPE
        SYNTAX INTEGER
        {
            atis(1),
            quad(2),
            paperInsulated(3),
            tp100(4),
            other(5)
        }
        MAX-ACCESS  read-write
        STATUS      current
        DESCRIPTION
           "Cable type.
            Options:
            1. atis(1)           - ATIS
            2. quad(2)           - Quad
            3. paperInsulated(3) - Paper Insulated
            4. tp100(4)          - TP100
            5. other(5)          - Other
           "
       DEFVAL       { atis }
       ::= { hwVectoringConfProfEntry 12 }

    hwVectoringProfLegacyCpeRatio OBJECT-TYPE
        SYNTAX Unsigned32 (0..3)
        MAX-ACCESS  read-write
        STATUS      current
        DESCRIPTION
           "Legacy CPE ratio.
            Options:
            0: 1%~15%
            1: 15%~25%
            2: 25%~50%
            3: >50%
           "
       DEFVAL       { 0 }
       ::= { hwVectoringConfProfEntry 13 }

    hwVectoringProfDisorderLeavingThreshold OBJECT-TYPE
        SYNTAX Unsigned32 (0..40000)
        UNITS       "symbols"
        MAX-ACCESS  read-write
        STATUS      current
        DESCRIPTION
           "The time between observed loss of US signal and forced cutoff of the DS signal, expressed in DMT symbols.
           "
       DEFVAL       { 8 }
       ::= { hwVectoringConfProfEntry 14 }

    hwVectoringConfProfLimitProfLineSpectrumProf OBJECT-TYPE
        SYNTAX      OCTET STRING (SIZE(0..128))
        MAX-ACCESS  read-write
        STATUS      current
        DESCRIPTION
           "The value of this object identifies the row in the XDSL Line Spectrum Configuration Profile Table,
            (hwVOPLineSpectrumConfProfTable) that applies to vectoring link when the line is activated in non-vectoring mode(G.993.2).
            If the vectoring limit profile is unused, then the object is set to a zero length string.
           "
       ::= { hwVectoringConfProfEntry 15 }

    hwVectoringConfProfLimitProfUpboProf OBJECT-TYPE
        SYNTAX      OCTET STRING (SIZE(0..128))
        MAX-ACCESS  read-write
        STATUS      current
        DESCRIPTION
           "The value of this object identifies the row in the XDSL Upbo Configuration Profile Table,
            (hwVOPUPBOConfProfTable) that applies to vectoring link when the line is activated in non-vectoring mode(G.993.2).
            If the vectoring limit profile is unused, then the object is set to a zero length string.
           "
       ::= { hwVectoringConfProfEntry 16 }
   
   hwVectoringConfProfGfastFextCanelControlDs OBJECT-TYPE
        SYNTAX INTEGER
        {
            enable(1),
            disable(2)
        }
        MAX-ACCESS  read-write
        STATUS      current
        DESCRIPTION
           "Defines whether FEXT cancellation in the downstream direction from all the other vectoring lines into the G.fast line in the vectoring group is enabled or disabled.
            Options:
	        1. enable (1)   - Enable FEXT cancellation in the downstream direction from all the other vectoring lines into the G.fast line in the vectoring group.
            2. disable (2)  - Disable FEXT cancellation in the downstream direction from all the other vectoring lines into the G.fast line in the vectoring group.
           "
        DEFVAL       { enable }
       ::= { hwVectoringConfProfEntry 17 }
       
   hwVectoringConfProfGfastFextCanelControlUs OBJECT-TYPE
        SYNTAX INTEGER
        {
            enable(1),
            disable(2)
        }
        MAX-ACCESS  read-write
        STATUS      current
        DESCRIPTION
           "Defines whether FEXT cancellation in the upstream direction from all the other vectoring lines into the G.fast line in the vectoring group is enabled or disabled.
            Options:
	        1. enable (1)   - Enable FEXT cancellation in the upstream direction from all the other vectoring lines into the G.fast line in the vectoring group.
            2. disable (2)  - Disable FEXT cancellation in the upstream direction from all the other vectoring lines into the G.fast line in the vectoring group.
           " 
        DEFVAL       { enable }
       ::= { hwVectoringConfProfEntry 18 }

--       hwVectoringPortTable
    hwVectoringPortTable OBJECT-TYPE
        SYNTAX SEQUENCE OF HwVectoringPortEntry
        MAX-ACCESS not-accessible
        STATUS current
        DESCRIPTION
            "The table hwVectoringPortTable contains port configuration about vectoring.
             The index of this table is ifIndex.
            "
        ::= { hwVectoringMIB 4 }

     hwVectoringPortEntry OBJECT-TYPE
        SYNTAX HwVectoringPortEntry
        MAX-ACCESS not-accessible
        STATUS current
        DESCRIPTION
             "The table hwVectoringPortTable contains port configuration about vectoring.
              The index of this entry is ifIndex."
        INDEX { ifIndex }
        ::= { hwVectoringPortTable 1 }

    HwVectoringPortEntry ::=
        SEQUENCE
            {
                hwVectoringLinkCfgProf                      OCTET STRING,
                hwVectoringLinkBelongedVceId                Unsigned32,
                hwVectoringLinkVcePortIndex                 Unsigned32,
                hwVectoringLinkBandPlanCompatible           INTEGER,
                hwVectoringLinkCPEType                      INTEGER,
                hwVectoringLinkLegacyPolicyUsed             INTEGER,
                hwVectoringLinkFallbackStatus               INTEGER,
                hwVectoringLinkClearCoefficient             INTEGER,
                hwVectoringLinkLongLoopControlState         INTEGER,
                hwVectoringLinkLongLoopPolicyUsed           INTEGER,
                hwVectoringLinkLongLoopControlRemove        INTEGER
            }

    hwVectoringLinkCfgProf OBJECT-TYPE
        SYNTAX      OCTET STRING (SIZE(0..32))
        MAX-ACCESS  read-write
        STATUS      current
        DESCRIPTION
            "This object configures the vectoring link profile name.
            "
        ::= { hwVectoringPortEntry 1 }

    hwVectoringLinkBelongedVceId OBJECT-TYPE
        SYNTAX Unsigned32 (0..96)
        MAX-ACCESS  read-write
        STATUS      current
        DESCRIPTION
            "The VCE ID uniquely identifies the VCE that manages and controls
             the vectored group to which the line belongs. It consists of one
             octet and valid ranges are from 1 to 96. The special value 0 means
             the line is not in a vectored group."
        ::= { hwVectoringPortEntry 2 }

    hwVectoringLinkVcePortIndex OBJECT-TYPE
        SYNTAX Unsigned32 (0..1024 | 4294967295)
        MAX-ACCESS  read-only
        STATUS      current
        DESCRIPTION
            "The VCE port index is the physical index that uniquely identifies
             the VCE port to which the line is connected. It is an integer from
             0 to the maximum number of lines supported by the VCE. The special
             value 4294967295 means the VCE port index is not valid"
        ::= { hwVectoringPortEntry 3 }

    hwVectoringLinkBandPlanCompatible OBJECT-TYPE
         SYNTAX INTEGER
        {
            compatible(1),
            incompatible(2)
        }
        MAX-ACCESS read-only
        STATUS current
        DESCRIPTION
            "Options:
             1. compatible(1)   - The vectoring line configured band plan is compatible with the vectoring band configuration
             2. incompatible(2) - The vectoring line configured band plan is not compatible with the vectoring band configuration"
        ::= { hwVectoringPortEntry 4 }

    hwVectoringLinkCPEType  OBJECT-TYPE
        SYNTAX INTEGER
        {
            vectoring(1),
            fullFriendly(2),
            friendlyDs(3),
            legacyVdsl2(4),
            adsl(5),
            unknown(6),
            fast(7)
        }
        MAX-ACCESS read-only
        STATUS current
        DESCRIPTION
            "If the port is activated, it is the type of the activated CPE.
             If the port was activated but is not currently activated, it is the type of previsouly activated CPE connected to the port.
             If the CPE and CO connected to the port were trained but are not activated, it is the type of CPE identified during the training.
             If the port does not receive handshake requests from a CPE, the CPE type is unknown.
             Options:
             1. vectoring(1)     - The CPE type is vectoring
             2. fullFriendly(2)  - The CPE type is vectoring full friendly
             3. friendlyDs(3)    - The CPE type is vectoring friendly ds
             4. legacyVdsl2(4)   - The CPE type is vdsl2
             5. adsl(5)          - The CPE type is adsl/2/2+
             6. unknown(6)       - The CPE type is unknown
             7. fast(7)         - The CPE type is G.fast
            "
        ::= { hwVectoringPortEntry 5 }

    hwVectoringLinkLegacyPolicyUsed  OBJECT-TYPE
        SYNTAX INTEGER
        {
            noLimit(1),
            block(2),
            limit(3),
            forceFriendlyDsLimitUs(4),
            forceFriendlyDsNoLimitUs(5),
            invalidValue(-1)
        }
        MAX-ACCESS read-only
        STATUS current
        DESCRIPTION
            "Vectoring legacy cpe activate policy.
             Options:
             1. noLimit(1)                   - The legacy cpe is allowed to activated in G.993.2 operation mode
             2. block(2)                      - The legacy cpe is not allowed to activated in G.993.2 operation mode
             3. limit(3)                      - The legacy cpe is allowed to activated in G.993.2 operation mode,
                                                with PSD auto shaped to eliminate the self-FEXT to vectoring lines
             4. forceFriendlyDsLimitUs(4)     - Force friendly is used in the downstream direction, and PSD automatic
                                                shaping is used in the upstream direction
             5. forceFriendlyDsNoLimitUs(5)   - Force friendly is used in the downstream direction, and no restriction
                                                is set for the upstream direction
             6. invalidValue(-1)              - Invalid value
            "
        ::= { hwVectoringPortEntry 6 }

    hwVectoringLinkFallbackStatus  OBJECT-TYPE
        SYNTAX INTEGER
        {
            noFallback(1),
            fallback(2),
            noConfig(255)
        }
        MAX-ACCESS read-only
        STATUS current
        DESCRIPTION
            "Options:
             1. noFallback(1)        - The fall back configuration is not in use, or the line works in vectoring mode or ADSL mode(G.992.x operation mode)
             2. fallback(2)          - The fall back configuration is in use, and the line works in G.993.2 operation mode
             3. noConfig(255)        - The fall back configuration does not exist
            "
        ::= { hwVectoringPortEntry 7 }

    hwVectoringLinkClearCoefficient  OBJECT-TYPE
        SYNTAX INTEGER
        {
            clear(1),
            invalidValue(-1)

        }
        MAX-ACCESS  read-write
        STATUS      current
        DESCRIPTION
            "Clear current coefficient and history coefficient.
            Options:
            1. clear(1)           - Clear the current coefficient and history coefficient
            2. invalidValue(-1)   - Invalid value
            "
        ::= { hwVectoringPortEntry 8 }

    hwVectoringLinkLongLoopControlState  OBJECT-TYPE
        SYNTAX INTEGER
        {
            n(0),
            y(1),
            invalidValue(-1)
        }
        MAX-ACCESS  read-only
        STATUS      current
        DESCRIPTION
            "Indicates the long loop control state.
            Options:
            1. n(0)           - Long loop control state is off
            2. y(1)           - Long loop control state is on
            3. invalidValue(-1)   - Invalid value
            "
        ::= { hwVectoringPortEntry 9 }	
	
    hwVectoringLinkLongLoopPolicyUsed  OBJECT-TYPE
        SYNTAX INTEGER
        {
            nonVectoring(0),
            nonFextCanceling(1),
            invalidValue(-1)
        }
        MAX-ACCESS  read-only
        STATUS      current
        DESCRIPTION
            "Indicates the long loop policy used.
            Options:
            1. nonVectoring(0)                - Policy of non-vectoring.
                                                If a vectoring port meets long line control requirements, 
                                                the vectoring port is considered as a legacy port during initialization.
            2. nonFextCanceling(1)            - Policy of non-fext-canceling. 
                                                If a vectoring port meets long line control requirements, 
                                                the vectoring port does not perform crosstalk cancellation.
            3. invalidValue(-1)               - Invalid value
            "
        ::= { hwVectoringPortEntry 10 }	
		
	hwVectoringLinkLongLoopControlRemove  OBJECT-TYPE
        SYNTAX INTEGER
        {
            false(0),
            true(1)
        }
        MAX-ACCESS  read-write
        STATUS      current
        DESCRIPTION
            "Remove the current long loop control. 
 	        If it is set to true, the control status is removed, and the system returns false upon a reading request.
 	            Options: 
 	            1. false(0)        - The system returns false upon a reading request
 	            2. true(1)         - Remove the current long loop control
            "
        ::= { hwVectoringPortEntry 11 }		

--   hwVectoringCrosstalkCouplingMatrixTable
    hwVectoringCrosstalkCouplingMatrixTable OBJECT-TYPE
        SYNTAX SEQUENCE OF HwVectoringCrosstalkCouplingMatrixEntry
        MAX-ACCESS not-accessible
        STATUS current
        DESCRIPTION
            "The table hwVectoringCrosstalkCouplingMatrixTable contains information of vectoring
             crosstalk coupling matrix about a port in a vectoring group.
             The indexes of this table are ifIndex and hwVectoringCrosstalkCouplingMatrixDirection.
            "
        ::= { hwVectoringMIB 6 }

     hwVectoringCrosstalkCouplingMatrixEntry OBJECT-TYPE
        SYNTAX HwVectoringCrosstalkCouplingMatrixEntry
        MAX-ACCESS not-accessible
        STATUS current
        DESCRIPTION
             "The table hwVectoringCrosstalkCouplingMatrixTable contains information of vectoring
              crosstalk coupling matrix about a port in a vectoring group.
              The indexes of this entry are ifIndex and hwVectoringCrosstalkCouplingMatrixDirection.
             "
        INDEX {
          ifIndex,
          hwVectoringCrosstalkCouplingMatrixDirection
          }
        ::= { hwVectoringCrosstalkCouplingMatrixTable 1 }

    HwVectoringCrosstalkCouplingMatrixEntry ::=
        SEQUENCE
            {
                hwVectoringCrosstalkCouplingMatrixDirection                 HwXdslDirection,
                hwVectoringCrosstalkCoupingMatrixOperType                   INTEGER,
                hwVectoringCrosstalkCoupingMatrixOperResult                 INTEGER,
                hwVectoringCrosstalkCouplingMatrixPortIfindexList           OCTET STRING,
                hwVectoringCrosstalkCouplingMatrixAverageMagnitudeList      OCTET STRING,
                hwVectoringCrosstalkCouplingMatrixCancellationStatusList    OCTET STRING,
                hwVectoringCrosstalkCouplingMatrixPortLocationList          OCTET STRING
            }

    hwVectoringCrosstalkCouplingMatrixDirection OBJECT-TYPE
        SYNTAX      HwXdslDirection
        MAX-ACCESS  accessible-for-notify
        STATUS      current
        DESCRIPTION
            "The direction of the vectoring crosstalk coupling matrix
             either upstream or downstream.
            "
        ::= { hwVectoringCrosstalkCouplingMatrixEntry 1 }

    hwVectoringCrosstalkCoupingMatrixOperType OBJECT-TYPE
        SYNTAX      INTEGER
        {
        start(1),
        stop(2)
        }
        MAX-ACCESS  read-write
        STATUS      current
        DESCRIPTION
            "This object is used to start the vectoring crosstalk coupling matrix.
             Options:
             1. start(1)            - start the vectoring crosstalk coupling matrix
             2. stop(2)             - stop the vectoring crosstalk coupling matrix
            "
        ::= { hwVectoringCrosstalkCouplingMatrixEntry 2 }

    hwVectoringCrosstalkCoupingMatrixOperResult OBJECT-TYPE
        SYNTAX      INTEGER
        {
        normal(1),
        fail(2)
        }
        MAX-ACCESS  accessible-for-notify
        STATUS      current
        DESCRIPTION
            "This object identifies the crosstalk coupling matrix operation result.
             Options:
             1. normal(1)           - The crosstalk coupling matrix operation result is normal.
             2. fail(2)             - The crosstalk coupling matrix operation result is fail.
            "
        ::= { hwVectoringCrosstalkCouplingMatrixEntry 3 }

    hwVectoringCrosstalkCouplingMatrixPortIfindexList OBJECT-TYPE
        SYNTAX      OCTET STRING (SIZE (0..4096))
        MAX-ACCESS  read-only
        STATUS      current
        DESCRIPTION
            "Ifindex list of port that effect another port in the same vectoring group.
             This is a string of 4 bytes of values indicates the port ifindex.
            "
        ::= { hwVectoringCrosstalkCouplingMatrixEntry 4 }

    hwVectoringCrosstalkCouplingMatrixAverageMagnitudeList OBJECT-TYPE
        SYNTAX      OCTET STRING (SIZE (0..4096))
        MAX-ACCESS  read-only
        STATUS      current
        DESCRIPTION
            "In this matrix must be seen all vectoring subscribers with disturberline.
             This is a string of 4 bytes of values indicates the port average magnitude.
             The units is 0.1 dBm/Hz.
            "
        ::= { hwVectoringCrosstalkCouplingMatrixEntry 5 }

    hwVectoringCrosstalkCouplingMatrixCancellationStatusList OBJECT-TYPE
        SYNTAX      OCTET STRING (SIZE (0..1024))
        MAX-ACCESS  read-only
        STATUS      current
        DESCRIPTION
            "Indicates whether the impact on the port caused by a disturber port is canceled.
             The connected link of each port is 1 bit, and the connected link IDs
             of all the disturber ports form a character string.
             The byte value indicates:
             1. yes(1)            - counteract
             2. no(2)             - not counteract
             3. invalidValue(255)  - invalid value
            "
        ::= { hwVectoringCrosstalkCouplingMatrixEntry 6 }

    hwVectoringCrosstalkCouplingMatrixPortLocationList OBJECT-TYPE
        SYNTAX      OCTET STRING (SIZE (0..1024))
        MAX-ACCESS  read-only
        STATUS      current
        DESCRIPTION
            "Indicates the connected link ID list of the device
             where the disturber ports locate. The connected link of each port is 1 bit.
             The byte value indicates:
             1. local(0)            - Local device
             2. peer1(1)             - The first peer device
             3. peer2(2)             - The second peer device
             4. invalidValue(255)    - invalid value
            "
        ::= { hwVectoringCrosstalkCouplingMatrixEntry 7 }

--       hwVectoringBoardVectoringStateTable
    hwVectoringBoardVectoringStateTable OBJECT-TYPE
        SYNTAX SEQUENCE OF HwVectoringBoardVectoringStateEntry
        MAX-ACCESS not-accessible
        STATUS current
        DESCRIPTION
            "The table hwVectoringBoardVectoringStateTable contains the vectoring current running information.
             The indexes of this table are hwFrameIndex and hwSlotIndex.
            "
        ::= { hwVectoringMIB 7 }

     hwVectoringBoardVectoringStateEntry OBJECT-TYPE
        SYNTAX HwVectoringBoardVectoringStateEntry
        MAX-ACCESS not-accessible
        STATUS current
        DESCRIPTION
             "The table hwVectoringBoardVectoringStateTable contains the vectoring current running information.
             The indexes of this entry are hwFrameIndex and hwSlotIndex.
             "
        INDEX {
          hwFrameIndex,
          hwSlotIndex
          }
        ::= { hwVectoringBoardVectoringStateTable 1 }

    HwVectoringBoardVectoringStateEntry ::=
        SEQUENCE
            {
                hwVectoringVpVectoringInterfaceState        INTEGER,
                hwVectoringVdslVectoringInterfaceState      INTEGER,
                hwVectoringVdslVectoringSyncState           INTEGER
            }

    hwVectoringVpVectoringInterfaceState OBJECT-TYPE
        SYNTAX      INTEGER
        {
        down(1),
        up(2),
        invalidValue(-1)
        }
        MAX-ACCESS  read-only
        STATUS      current
        DESCRIPTION
            "The object indicates VCE vectoring interface state.
             Options:
             1. down(1)           - vectoring interface state is abnormal
             2. up(2)             - vectoring interface state is normal
             3. invalidValue(-1)  - invalid value
            "
        ::= { hwVectoringBoardVectoringStateEntry 1 }

    hwVectoringVdslVectoringInterfaceState OBJECT-TYPE
        SYNTAX      INTEGER
        {
        down(1),
        up(2),
        invalidValue(-1)
        }
        MAX-ACCESS  read-only
        STATUS      current
        DESCRIPTION
            "The object indicates VDSL vectoring interface state.
             Options:
             1. down(1)           - vectoring interface state is abnormal
             2. up(2)             - vectoring interface state is normal
             3. invalidValue(-1)  - invalid value
            "
        ::= { hwVectoringBoardVectoringStateEntry 2 }

    hwVectoringVdslVectoringSyncState OBJECT-TYPE
        SYNTAX      INTEGER
        {
        noSync(1),
        sync(2),
        invalidValue(-1)
        }
        MAX-ACCESS  read-only
        STATUS      current
        DESCRIPTION
            "The object indicates Sync state between VCE and VDSL vectoring interface.
             Options:
             1. noSync(1)         - communication between VCE and VDSL is abnormal
             2. sync(2)           - communication between VCE and VDSL is normal
             3. invalidValue(-1)  - invalid value
            "
        ::= { hwVectoringBoardVectoringStateEntry 3 }

-- Vectoring ALARM TRAP

    hwVectoringTraps OBJECT IDENTIFIER ::= { hwVectoringMIB 8 }
    hwVectoringAlarmTraps OBJECT IDENTIFIER  ::= { hwVectoringTraps 1 }
    hwVectoringAlarmTrapsPrefix OBJECT IDENTIFIER  ::= { hwVectoringAlarmTraps 1 }
    hwVectoringCommonTraps OBJECT IDENTIFIER  ::= { hwVectoringTraps 2 }
    hwVectoringCommonTrapsPrefix OBJECT IDENTIFIER  ::= { hwVectoringCommonTraps 1 }

    hwVectoringFaultAlarmTrap NOTIFICATION-TYPE
        OBJECTS
            {
            hwFrameIndex,
            hwSlotIndex
            }
        STATUS current
        DESCRIPTION
           "This notification indicates that the vectoring service on the board fails.
           "
        ::= { hwVectoringAlarmTrapsPrefix 1 }

    hwVectoringRecoveryAlarmTrap NOTIFICATION-TYPE
        OBJECTS
            {
            hwFrameIndex,
            hwSlotIndex
            }
        STATUS current
        DESCRIPTION
           "This notification indicates that the vectoring service on the board recovers.
           "
        ::= { hwVectoringAlarmTrapsPrefix 2 }

    hwVectoringVictCoefAbnormalVariationAlarmTrap NOTIFICATION-TYPE
        OBJECTS
            {
            hwFrameIndex,
            hwSlotIndex,
            hwPortIndex
            }
        STATUS current
        DESCRIPTION
           "This notification indicates that the port receives abnormal crosstalk from
            other ports."
        ::= { hwVectoringAlarmTrapsPrefix 3 }

    hwVectoringDistCoefAbnormalVariationAlarmTrap NOTIFICATION-TYPE
        OBJECTS
            {
            hwFrameIndex,
            hwSlotIndex,
            hwPortIndex
            }
        STATUS current
        DESCRIPTION
           "This notification indicates that the port causes abnormal crosstalk to
            other ports."
        ::= { hwVectoringAlarmTrapsPrefix 4 }

    hwVectoringReceivedESAbnormalAlarmTrap NOTIFICATION-TYPE
        OBJECTS
            {
            hwFrameIndex,
            hwSlotIndex,
            hwPortIndex
            }
        STATUS current
        DESCRIPTION
           "This notification indicates that the port receives abnormal error sample
            messages."
        ::= { hwVectoringAlarmTrapsPrefix 5 }

    hwXdslLegacyCpeActivatedAlarmTrap NOTIFICATION-TYPE
        OBJECTS
            {
            hwFrameIndex,
            hwSlotIndex,
            hwPortIndex,
            hwVectoringLinkCPEType,
            hwVectoringLegacyCpeActivatePolicy
            }
        STATUS current
        DESCRIPTION
           "This notification indicates that the port is activated in none-vectoring mode."
        ::= { hwVectoringAlarmTrapsPrefix 6 }

    hwXdslFrequentlyRetrainTimesReachThresholdAlarmTrap NOTIFICATION-TYPE
        OBJECTS
            {
            hwFrameIndex,
            hwSlotIndex,
            hwPortIndex,
            hwXdslPortFrequentRetrainControlTimes,
            hwVectoringPortFrequentRetrainTimes
            }
        STATUS current
        DESCRIPTION
           "This notification indicates that the port frequently retrain times in
            15 minutes reach the threshold."
        ::= { hwVectoringAlarmTrapsPrefix 7 }

    hwVectoringReceivedESRecoverAlarmTrap NOTIFICATION-TYPE
        OBJECTS
            {
            hwFrameIndex,
            hwSlotIndex,
            hwPortIndex
            }
        STATUS current
        DESCRIPTION
           "This notification indicates that the port error sample feedback recovers."
        ::= { hwVectoringAlarmTrapsPrefix 8 }


     hwVectoringPSConfigAbnormalAlarmTrap NOTIFICATION-TYPE
        OBJECTS
            {
            hwFrameIndex,
            hwSlotIndex,
            hwPortIndex
            }
        STATUS current
        DESCRIPTION
           "This notification indicates that port pilot sequence config abnormal messages."
        ::= { hwVectoringAlarmTrapsPrefix 9 }

     hwVectoringPSConfigRecoverAlarmTrap NOTIFICATION-TYPE
        OBJECTS
            {
            hwFrameIndex,
            hwSlotIndex,
            hwPortIndex
            }
        STATUS current
        DESCRIPTION
           "This notification indicates that the port pilot sequence config recovers."
        ::= { hwVectoringAlarmTrapsPrefix 10 }

     hwVectoringLegacyCpeActivationAlarmTrap NOTIFICATION-TYPE
        OBJECTS
            {
            hwFrameIndex,
            hwSlotIndex,
            hwPortIndex,
            hwVectoringLinkCPEType,
            hwVectoringLegacyCpeActivatePolicy
            }
        STATUS current
        DESCRIPTION
           "This notification indicates that the port is activated in none-vectoring mode."
        ::= { hwVectoringAlarmTrapsPrefix 11 }

     hwVectoringLegacyCpeActivationRecoveryTrap NOTIFICATION-TYPE
        OBJECTS
            {
            hwFrameIndex,
            hwSlotIndex,
            hwPortIndex
            }
        STATUS current
        DESCRIPTION
           "This notification indicates that the port is activated in vectoring mode."
        ::= { hwVectoringAlarmTrapsPrefix 12 }

      hwVectoringServiceFaultAlarmTrap NOTIFICATION-TYPE
        OBJECTS
            {
            hwFrameIndex,
            hwSlotIndex,
      hwVectoringPortList
            }
        STATUS current
        DESCRIPTION
           "This notification indicates that the vectoring service in the system fails."
        ::= { hwVectoringAlarmTrapsPrefix 13 }

      hwVectoringServiceRecoveryTrap NOTIFICATION-TYPE
        OBJECTS
            {
            hwFrameIndex,
            hwSlotIndex
            }
        STATUS current
        DESCRIPTION
           "This notification indicates that the vectoring service in the system recovers."
        ::= { hwVectoringAlarmTrapsPrefix 14 }

      hwVectoringSingleWireInterruptionAlarmTrap NOTIFICATION-TYPE
        OBJECTS
            {
            hwFrameIndex,
            hwSlotIndex,
            hwPortIndex
            }
        STATUS current
        DESCRIPTION
           "This notification indicates that the single-wire on the port is disconnected."
        ::= { hwVectoringAlarmTrapsPrefix 15 }

      hwVectoringSingleWireInterruptionRecoveryTrap NOTIFICATION-TYPE
        OBJECTS
            {
            hwFrameIndex,
            hwSlotIndex,
            hwPortIndex
            }
        STATUS current
        DESCRIPTION
           "This notification indicates that the single-wire on the port is re-connected."
        ::= { hwVectoringAlarmTrapsPrefix 16 }

    hwvdsl2FrequentlyRetrainReachFurtherControlThresholdAlarmTrap NOTIFICATION-TYPE
        OBJECTS
            {
            hwFrameIndex,
            hwSlotIndex,
            hwPortIndex,
            hwxdsl2FrequentlyRetrainReachFurtherControlTime,
            hwxdsl2FrequentlyRetrainReachFurtherControlPolicy
            }
        STATUS current
        DESCRIPTION
           "This notification indicates that the port frequent retrain times in the detect period reach the
            further control threshold."
        ::= { hwVectoringAlarmTrapsPrefix 17 }

    hwVectoringNlvServiceFaultAlarmTrap NOTIFICATION-TYPE
        OBJECTS
            {
            hwFrameIndex,
            hwSlotIndex,
            hwPortIndex,
            hwVectoringNlvDescription
            }
        STATUS current
        DESCRIPTION
           "This notification indicates that the node level vectoring service in the system fails."
        ::= { hwVectoringAlarmTrapsPrefix 18 }

    hwVectoringNlvServiceRecoveryTrap NOTIFICATION-TYPE
        OBJECTS
            {
            hwFrameIndex,
            hwSlotIndex,
            hwPortIndex,
            hwVectoringNlvDescription
            }
        STATUS current
        DESCRIPTION
           "This notification indicates that the node level vectoring service in the system recovers."
        ::= { hwVectoringAlarmTrapsPrefix 19 }

    hwVectoringGlobalConfigChangeTrap NOTIFICATION-TYPE
        OBJECTS
            {
            hwConfigChangeIP,
            hwVectoringSwitch,
            hwVectoringLegacyCpeActivatePolicy,
            hwVectoringBandplanType,
            hwVectoringUs0Type,
            hwVectoringAnnexALimitMask,
            hwVectoringLegacyCpeReservedBand,
            hwVectoringLegacyCpeToneBlackoutBand
            }
        STATUS current
        DESCRIPTION
           "This notification indicates that the vectoring global configuration is changed.
           "
        ::= { hwVectoringCommonTrapsPrefix 1 }

     hwVectoringCrosstalkCoupingMatrixOperResultTrap NOTIFICATION-TYPE
        OBJECTS
            {
            hwXdslRequestID,
            ifIndex,
            hwVectoringCrosstalkCouplingMatrixDirection,
            hwVectoringCrosstalkCoupingMatrixOperResult
            }
        STATUS current
        DESCRIPTION
           "This notification indicates that the vectoring crosstalk coupling matrix calculation result.
           "
        ::= { hwVectoringCommonTrapsPrefix 2 }

    hwVectoringXlinChangeTrap NOTIFICATION-TYPE
        OBJECTS
            {
            hwFrameIndex,
            hwSlotIndex
            }
        STATUS current
        DESCRIPTION
           "This notification indicates that the xlin is changed."
        ::= { hwVectoringCommonTrapsPrefix 3 }

    hwVectoringProfChangeTrap NOTIFICATION-TYPE
        OBJECTS
            {
            hwConfigChangeIP,
            hwVectoringProfOperType,
            hwVectoringProfName
            }
        STATUS current
        DESCRIPTION
           "This notification indicates that the vectoring profile configuration is changed."
        ::= { hwVectoringCommonTrapsPrefix 4 }

    hwVectoringProfIDChangeTrap NOTIFICATION-TYPE
        OBJECTS
            {
            hwConfigChangeIP,
            ifIndex,
            hwVectoringProfName
            }
        STATUS current
        DESCRIPTION
           "This notification indicates that the port's vectoring profile configuration is changed."
        ::= { hwVectoringCommonTrapsPrefix 5 }

   hwVectoringVceRunInfoCollectTrap NOTIFICATION-TYPE
        OBJECTS
           {
                hwFrameIndex,
                hwSlotIndex,
                hwVectoringVceRunInfoCollectResult,
                hwVectoringVceRunInfoCollectRequestId
           }
           STATUS current
           DESCRIPTION
                "
    This trap is generated when vectoring running information collection is complete.
    "
            ::= { hwVectoringCommonTrapsPrefix 6 }

-- hwVectoringFastJoinConfig

     hwVectoringFastJoinConfig OBJECT IDENTIFIER ::= { hwVectoringMIB 9 }

    hwVectoringGainPhase OBJECT-TYPE
        SYNTAX INTEGER
        {
            atInit(1),
            trigger(2),
            duringShowtime(3)
        }
        MAX-ACCESS  read-write
        STATUS      current
        DESCRIPTION
            "This object is used to set the mode for obtaining the vectoring
             gain during port activation. Default values:atInit.
             Options:
             1. atInit(1)         - The vectoring gain is obtained during port
                                    activation except board startup
             2. trigger(2)        - The vectoring gain is obtained in some condition
             3. duringShowtime(3) - The port is activated and then the vectoring
                                    gain is obtained during tracking
            "
        ::= { hwVectoringFastJoinConfig 1 }

    hwVectoringTriggerAfterBoardReset OBJECT-TYPE
        SYNTAX INTEGER
        {
            enable(1),
            disable(2),
            invalidValue(-1)
        }
        MAX-ACCESS  read-write
        STATUS      current
        DESCRIPTION
            "The vectoring gain is not obtained during port activation
             in board reset, but obtained during tracking in SRA.
             Default values:enable.
             Options:
             1. enable(1)         - Enables the vectoring gain achieved in showtime after board reset
             2. disable(2)        - Disables the vectoring gain achieved in showtime after board reset
             3. invalidValue(-1)  - invalid value
            "
        ::= { hwVectoringFastJoinConfig 2 }

    hwVectoringTriggerDuringBulkNum OBJECT-TYPE
       SYNTAX Unsigned32
        MAX-ACCESS  read-write
        STATUS      current
        DESCRIPTION
            "The vectoring gain achieved in showtime when the number of ports
             join in at a time exceeds the configured bulk init number. It
             ranges from 2 to 256. The invalid value  is 4294967295.
             Default values:64.
            "
        ::= { hwVectoringFastJoinConfig 3 }

    hwVectoringJoinMaxWaitTime OBJECT-TYPE
        SYNTAX Unsigned32 (0..60)
        UNITS       "seconds"
        MAX-ACCESS  read-write
        STATUS      current
        DESCRIPTION
            "This object is used to set the total time for a joined port
             to wait for other ports in the batch to join.
             Default values:15.
            "
        ::= { hwVectoringFastJoinConfig 4 }

    hwVectoringJoinGapWaitTime OBJECT-TYPE
        SYNTAX Unsigned32 (0..60)
        UNITS       "seconds"
        MAX-ACCESS  read-write
        STATUS      current
        DESCRIPTION
            "This object is used to set the interval for a joined port to wait
             for a single port in the batch to join.
             Default values:5.
            "
        ::= { hwVectoringFastJoinConfig 5 }

    hwVectoringTrackingPeriod OBJECT-TYPE
        SYNTAX Unsigned32 (0..240)
        UNITS       "minute"
        MAX-ACCESS  read-write
        STATUS      current
        DESCRIPTION
            "Vectoring tracking period. Default values:30.
            "
        ::= { hwVectoringFastJoinConfig 6 }

    hwVectoringHistoryCoefficient OBJECT-TYPE
        SYNTAX INTEGER
        {
            disable(1),
            upstream(2),
            downstream(3),
            both(4)
        }
        MAX-ACCESS  read-write
        STATUS      current
        DESCRIPTION
            "This object is used to set whether to use a historical coefficient.
             Default values:both.
             Options:
             1. disable(1)      - Indicates that a historical coefficient is not used
             2. upstream(2)     - Indicates that a historical coefficient is used in upstream direction
             3. downstream(3)   - Indicates that a historical coefficient is used in downstream direction
             4. both(4)         - Indicates that a historical coefficient is used in both upstream and downstream directions
             "
        ::= { hwVectoringFastJoinConfig 7 }

    hwVectoringJoinFdps OBJECT-TYPE
        SYNTAX INTEGER
        {
            disable(1),
            upstream(2),
            downstream(3),
            both(4)
        }
        MAX-ACCESS  read-write
        STATUS      current
        DESCRIPTION
            "The vectoring frequency dependent pilot sequence configuration.
            Default values:disable.
            Options:
            1. disable(1)    - Indicates that the frequency dependent pilot sequence (FDPS) is disabled
            2. upstream(2)   - Indicates that upstream frequency dependent pilot sequence (upstream FDPS) is enabled
            3. downstream(3) - Indicates that downstream frequency dependent pilot sequence (downstream FDPS) is enabled
            4. both(4)       - Indicates both downstream and upstream frequency dependent pilot sequence (FDPS) are enabled
            "
        ::= { hwVectoringFastJoinConfig 8 }

     hwVectoringHistoryCoefficientClear OBJECT-TYPE
        SYNTAX INTEGER
        {
            noClear(1),
            clearWhenWrong(2),
            clearAfterDle(3),
            invalidValue(-1)
        }
        MAX-ACCESS  read-write
        STATUS      current
        DESCRIPTION
            "The vectoring coefficient clear mode.
            Default values:noClear.
            Options:
            1. noClear(1)          - Do not clean up history coefficient
            2. clearWhenWrong(2)   - When detecting the wrong history coefficient, cleaning history coefficient
            3. clearAfterDle(3)    - When the port is deactivated, cleaning history coefficient
            4. invalidValue(-1)    - Invalid value
            "
        ::= { hwVectoringFastJoinConfig 9 }

-- hwVectoringTrapsVbOids
    hwVectoringTrapsVbOids OBJECT IDENTIFIER ::= { hwVectoringMIB 10 }

    hwVectoringPortFrequentRetrainTimes OBJECT-TYPE
        SYNTAX Unsigned32
        MAX-ACCESS accessible-for-notify
        STATUS current
        DESCRIPTION
            "The times that Xdsl port frequent retrain in 15 minutes.
                "
        ::= { hwVectoringTrapsVbOids 1}

    hwVectoringProfOperType OBJECT-TYPE
        SYNTAX INTEGER {
                       add(1),
                       modify(2),
                       delete(3)
                       }
        MAX-ACCESS accessible-for-notify
        STATUS current
        DESCRIPTION
                "Vectoring profile operate type.
                 Options:
                 1.add(1)    - Add a vectoring profile
                 2.modify(2) - Modify a vectoring profile
                 3.delete(3) - Delete a vectoring profile
                "
        ::= { hwVectoringTrapsVbOids 2}

    hwVectoringVceRunInfoCollectResult OBJECT-TYPE
        SYNTAX  INTEGER
                {
                noFail(0),
                memFull(1),
                otherCause(2)
                }
        MAX-ACCESS accessible-for-notify
        STATUS current
        DESCRIPTION
            "Indicates the status of vectoring running information collection.
             Options:
             1. noFail(0)     - Vectoring running information has been collected successfully.
             2. memFull(1)    - The memory for vectoring running information collection is used up.
             3. otherCause(2) - Other collection failure reasons.
            "
        ::= { hwVectoringTrapsVbOids 3 }

    hwVectoringPortList OBJECT-TYPE
        SYNTAX OCTET STRING (SIZE (0..2048))
        MAX-ACCESS accessible-for-notify
        STATUS current
        DESCRIPTION
            "This node is a list of ports activated in vectoring mode in the entire subrack.
             In the reported port list, first two bytes represent the number of boards that support port activation in vectoring mode.
             The format of each board is as follows:
             Two bytes represent the subrack ID.
             Two bytes represent the slot ID.
             16 bytes represent all port IDs of the entire board in format of bit mask.
             Port IDs are in ascending order from left to right. When the bit is 1, the port is activated in vectoring mode.
             When the bit is 0, the port is activated in non-vectoring modes.
       "
        ::= { hwVectoringTrapsVbOids 4}

    hwxdsl2FrequentlyRetrainReachFurtherControlTime  OBJECT-TYPE
        SYNTAX Unsigned32
        MAX-ACCESS accessible-for-notify
        STATUS current
        DESCRIPTION
            "The trigger time when the port frequent retrain times in the detect period reach the
             further control threshold."
        ::= { hwVectoringTrapsVbOids 5}

    hwxdsl2FrequentlyRetrainReachFurtherControlPolicy  OBJECT-TYPE
            SYNTAX OCTET STRING (SIZE (0..50))
            MAX-ACCESS  read-write
            STATUS      current
            DESCRIPTION
                "Further control policy for frequent retrain.
                 Values are as follows:
                 Permanent-lock: indicates that activation is permanently disabled in any mode.
                 Permanent-non-vectoring: indicates that activation is permanently disabled in vectoring mode.
                 -: indicates an invalid value.
                "
         ::= { hwVectoringTrapsVbOids 6}

--  hwVectoringNlvTable
    hwVectoringNlvTable OBJECT-TYPE
        SYNTAX SEQUENCE OF HwVectoringNlvEntry
        MAX-ACCESS not-accessible
        STATUS current
        DESCRIPTION
            "The table hwVectoringNlvTable contains status parameters of node level vectoring.
             The index of this table is hwVectoringNlvPeerId.
            "
        ::= { hwVectoringMIB 11 }

     hwVectoringNlvEntry OBJECT-TYPE
        SYNTAX HwVectoringNlvEntry
        MAX-ACCESS not-accessible
        STATUS current
        DESCRIPTION
             "The table hwVectoringNlvTable contains status parameters of node level vectoring.
              The index of this entry is hwVectoringNlvPeerId.
             "
        INDEX { hwVectoringNlvPeerId }
        ::= { hwVectoringNlvTable 1 }

    HwVectoringNlvEntry ::=
        SEQUENCE
            {
                hwVectoringNlvPeerId                   Unsigned32,
                hwVectoringNlvStatus                   BITS,
                hwVectoringNlvPeerEquipmentSysMac      MacAddress,
                hwVectoringNlvDescription              OCTET STRING,
                hwVectoringNlvTimestamp                DateAndTime,
                hwVectoringNlvGroupDslamList           OCTET STRING,
                hwVectoringNlvClockSource              INTEGER,
                hwVectoringNlvFaultReason              INTEGER
            }

    hwVectoringNlvPeerId OBJECT-TYPE
        SYNTAX      Unsigned32 (0..2)
        MAX-ACCESS  not-accessible
        STATUS      current
        DESCRIPTION
            "The value of this object identifies the node level vectoring peer equipment."
        ::= { hwVectoringNlvEntry 1 }

    hwVectoringNlvStatus  OBJECT-TYPE
        SYNTAX BITS {
            noDefect(0),
            datapathfault(1),
            managementpathfault(2),
            clocksyncfault(3),
            fault(4),
            disable(5)
        }

        MAX-ACCESS  read-only
        STATUS      current
        DESCRIPTION
            "Indicates current status of node level vectoring.
             This is a bit-map of possible conditions.  The various bit
             positions are:
             1. noDefect(0)            - This bit position positively reports that no defect exists
             2. datapathfault(1)       - The Vectoring Data Path Fault
             3. managementpathfault(2) - Vectoring Management Path Fault
             4. clocksyncfault(3)      - Clock Synchronization Failure
             5. fault(4)               - All types of the node level vectoring fault, including the vectoring data path fault,
                                         vectoring management path fault, clock synchronization failure and others fault
             6. disable(5)             - The node level vectoring function is disable
            "
        ::= { hwVectoringNlvEntry 2 }

    hwVectoringNlvPeerEquipmentSysMac OBJECT-TYPE
        SYNTAX      MacAddress
        MAX-ACCESS  read-only
        STATUS      current
        DESCRIPTION
            "A 6-octet read-only value carrying the individual MAC address of the node level vectoring peer equipment.
            "
        ::= { hwVectoringNlvEntry 3 }
        
    hwVectoringNlvDescription OBJECT-TYPE
        SYNTAX  OCTET STRING (SIZE(0..32))
        MAX-ACCESS  read-only
        STATUS      current
        DESCRIPTION
            "Indicates description information of the node level vectoring peer equipment.
            "
        ::= { hwVectoringNlvEntry 4 }
        
    hwVectoringNlvTimestamp OBJECT-TYPE
        SYNTAX      DateAndTime
        MAX-ACCESS  read-only
        STATUS      current
        DESCRIPTION
            "Indicates start time of the node level vectoring peer equipment.
            "
        ::= { hwVectoringNlvEntry 5 }
        
    hwVectoringNlvGroupDslamList OBJECT-TYPE
        SYNTAX  OCTET STRING (SIZE(0..128))
        MAX-ACCESS  read-only
        STATUS      current
        DESCRIPTION
            "Indicates infiniband port description information of the node level vectoring peer equipment.
            "
        ::= { hwVectoringNlvEntry 6 }
        
    hwVectoringNlvClockSource OBJECT-TYPE
        SYNTAX INTEGER
          {
              local(0),
              peer1(1),
              peer2(2)
          }
        MAX-ACCESS  read-only
        STATUS      current
        DESCRIPTION
            "Indicates clock source of the node level vectoring peer equipment.
             1. local(0)            - The local device clock is used as the clock source
             2. peer1(1)            - The first peer device clock is used as the clock source
             3. peer2(2)            - The second peer device clock is used as the clock source
            "
        ::= { hwVectoringNlvEntry 7 }
        
    hwVectoringNlvFaultReason OBJECT-TYPE
        SYNTAX INTEGER
          {
              normal(1),
              nlvConnectionFail(2),
              vectoringDisabled(3),
              nlvConfigurationInconsistent(4),
              synchronizationAbnormal(5),
              nlvDisabled(6)
          }
        MAX-ACCESS  read-only
        STATUS      current
        DESCRIPTION
            "Indicates the the reason of the node level vectoring fault.
             1. normal(1)                        - The node level vectoring is normal
             2. nlvConnectionFail(2)             - The node level vectoring fault reason is nlv connection fail
             3. vectoringDisabled(3)             - The node level vectoring fault reason is vectoring disabled
             4. nlvConfigurationInconsistent(4)  - The node level vectoring fault reason is nlv configuration inconsistent
             5. synchronizationAbnormal(5)       - The node level vectoring fault reason is synchronization abnormal
             6. nlvDisabled(6)                   - The node level vectoring fault reason is nlv disabled
            "
        ::= { hwVectoringNlvEntry 8 }

--  hwVectoringXlinMonitorTable
    hwVectoringXlinMonitorTable OBJECT IDENTIFIER ::= { hwVectoringMIB 12 }

    hwVectoringXlinMonitorEnable OBJECT-TYPE
          SYNTAX INTEGER
          {
              enable(1),
              disable(2)
          }
          MAX-ACCESS  read-write
          STATUS      current
          DESCRIPTION
              "Enable/Disable the vectoring xlin changing monitor functionality.
               Default values:disable.
               Options:
               1. enable(1)  - Enable the vectoring xlin changing monitor functionality
               2. disable(2) - Disable the vectoring xlin changing monitor functionality
              "
          ::= { hwVectoringXlinMonitorTable 1 }

--  hwVectoringVceRunInfoCollectTable
    hwVectoringVceRunInfoCollectTable OBJECT-TYPE
        SYNTAX SEQUENCE OF HwVectoringVceRunInfoCollectEntry
        MAX-ACCESS not-accessible
        STATUS current
        DESCRIPTION
                   "
                   Indicates the configuration of vectoring running information collection.
             The indexes of this table are hwFrameIndex and hwSlotIndex.
                   "
        ::= { hwVectoringMIB 13 }

    hwVectoringVceRunInfoCollectEntry OBJECT-TYPE
        SYNTAX HwVectoringVceRunInfoCollectEntry
        MAX-ACCESS not-accessible
        STATUS current
        DESCRIPTION
                   "
                   Indicates the configuration of vectoring running information collection.
             The indexes of this entry are hwFrameIndex and hwSlotIndex.
                   "
        INDEX{
                 hwFrameIndex,
                 hwSlotIndex
             }
        ::= { hwVectoringVceRunInfoCollectTable 1 }

    HwVectoringVceRunInfoCollectEntry ::=
        SEQUENCE{
            hwVectoringVceRunInfoCollectType        INTEGER,
            hwVectoringVceRunInfoCollectStart       INTEGER,
            hwVectoringVceRunInfoCollectState       INTEGER,
            hwVectoringVceRunInfoCollectTimes       Unsigned32,
            hwVectoringVceRunInfoCollectInterval    Unsigned32,
            hwVectoringVceRunInfoCollectCurrentTime               Unsigned32,
            hwVectoringVceRunInfoCollectAlgoParaVictimPort        Integer32,
            hwVectoringVceRunInfoCollectAlgoParaDisturberLocation INTEGER,
            hwVectoringVceRunInfoCollectAlgoParaDisturberPort     Integer32,
            hwVectoringVceRunInfoCollectRequestId                 Unsigned32
                }

    hwVectoringVceRunInfoCollectType OBJECT-TYPE
        SYNTAX INTEGER
                      {
                          crosstalkmatrix(1),
                          keyrecord(2),
                          couplingmatrix(3),
                          algorithmparameter(4),
                          invalid(-1)
                      }
        MAX-ACCESS  read-write
        STATUS      current
        DESCRIPTION
                   "
                   The leaf is used to set the vectoring running information collection type.
                   Options:
                   1. crosstalkmatrix(1)    - Collect information about crosstalk matrix for vectoring lines.
                   2. keyrecord(2)          - Collect key vectoring information.
                   3. couplingmatrix(3)     - Collect information about coupling matrix for vectoring lines.
                   4. algorithmparameter(4) - Collect information about algorithm parameter for vectoring lines.
                   5. invalid(-1)           - Invalid value.
                   "
        ::= { hwVectoringVceRunInfoCollectEntry 1 }

    hwVectoringVceRunInfoCollectStart OBJECT-TYPE
        SYNTAX INTEGER
                      {
                          start(1),
                          invalid(-1)
                      }
        MAX-ACCESS read-write
        STATUS     current
        DESCRIPTION
                   "
                    The leaf is used to start vectoring running information collection.
              Options:
              1. start(1)    - Start to collect vectoring running information.
              2. invalid(-1) - Invalid value.
             "
        ::= { hwVectoringVceRunInfoCollectEntry 2 }

    hwVectoringVceRunInfoCollectState OBJECT-TYPE
        SYNTAX INTEGER
                      {
                          nocollect(1),
                          collecting(2),
                          collected(3)
                      }
        MAX-ACCESS  read-only
        STATUS     current
        DESCRIPTION
                  "
                   Indicates the status of vectoring running information collection.
             Options:
                   1. nocollect(1)   - The collection does not start.
             2. collecting(2)  - The colleciton is running.
             3. collected(3)   - The collection completed.
                  "
        ::= { hwVectoringVceRunInfoCollectEntry 3 }

    hwVectoringVceRunInfoCollectTimes OBJECT-TYPE
        SYNTAX      Unsigned32 (1..5 | 4294967295)
        MAX-ACCESS  read-write
        STATUS      current
        DESCRIPTION
                "
                  Indicates vectoring running information collection times.
                  4294967295 represents invalid value.
                "
        ::= { hwVectoringVceRunInfoCollectEntry 4 }

   hwVectoringVceRunInfoCollectInterval OBJECT-TYPE
        SYNTAX      Unsigned32 (15..120 | 4294967295)
        UNITS       "minute"
        MAX-ACCESS  read-write
        STATUS      current
        DESCRIPTION
                "
                 Indicates the interval at which vectoring running information is collected.
                 4294967295 represents invalid value.
                "
        ::= { hwVectoringVceRunInfoCollectEntry 5 }

   hwVectoringVceRunInfoCollectCurrentTime OBJECT-TYPE
        SYNTAX      Unsigned32
        MAX-ACCESS  read-only
        STATUS      current
        DESCRIPTION
                "
                 Indicates the time at which vectoring running information is collected.
                "
        ::= { hwVectoringVceRunInfoCollectEntry 6 }

   hwVectoringVceRunInfoCollectAlgoParaVictimPort OBJECT-TYPE
        SYNTAX      Integer32
        MAX-ACCESS  read-write
        STATUS      current
        DESCRIPTION
                "
                 Indicates the ifindex of the victim port.
                 -1 represents invalid value.
                "
        ::= { hwVectoringVceRunInfoCollectEntry 7 }

   hwVectoringVceRunInfoCollectAlgoParaDisturberLocation OBJECT-TYPE
        SYNTAX INTEGER
                      {
                          local(1),
                          peer(2),
                          invalid(-1)
                      }
        MAX-ACCESS  read-write
        STATUS      current
        DESCRIPTION
                "Indicates the connected link ID list of the device where the disturber ports locate.
                 Options:
                  1. local(1)            - Local device
                  2. peer(2)             - Peer device
                  3. invalid(-1)         - Invalid value
                "
        DEFVAL  { local }
        ::= { hwVectoringVceRunInfoCollectEntry 8 }

   hwVectoringVceRunInfoCollectAlgoParaDisturberPort OBJECT-TYPE
        SYNTAX      Integer32
        MAX-ACCESS  read-write
        STATUS      current
        DESCRIPTION
                "
                 Indicates the ifindex of the disturber port.
                 -1 represents invalid value.
                "
        ::= { hwVectoringVceRunInfoCollectEntry 9 }

   hwVectoringVceRunInfoCollectRequestId OBJECT-TYPE
        SYNTAX      Unsigned32
        MAX-ACCESS  read-write
        STATUS      current
        DESCRIPTION
                "
                 The vce run info collect request ID, which identifies a collect request delivered by the NMS.
           An collect request ID can be any unsigned integer in the range of 0-4294967295.
           However, the IDs of different collect requests cannot duplicate.
           This object cannot be set independently.
           The value of 4294967295 indicates that request id is not specified.
                "
        ::= { hwVectoringVceRunInfoCollectEntry 10 }

--  hwVectoringVceRunInfoKeyRecordTable
    hwVectoringVceRunInfoKeyRecordTable OBJECT IDENTIFIER ::= { hwVectoringMIB 14 }

    hwVectoringVceRunInfoKeyRecordPortList OBJECT-TYPE
          SYNTAX  OCTET STRING (SIZE(0..128))
          MAX-ACCESS  read-write
          STATUS      current
          DESCRIPTION
              "Indicates the key record port list of vectoring run info.
              "
          ::= { hwVectoringVceRunInfoKeyRecordTable 1 }

    hwVectoringNlvGlobalConfig OBJECT IDENTIFIER ::= { hwVectoringMIB 15 }

    hwVectoringNlvSwitch OBJECT-TYPE
          SYNTAX INTEGER
          {
              enable(1),
              disable(2)
          }
          MAX-ACCESS  read-write
          STATUS      current
          DESCRIPTION
              "Enable/Disable the global node level vectoring configuration.
               Default values:enable.
               Options:
               1. enable(1)   - Enables the global node level vectoring configuration
               2. disable(2)  - Disables the global node level vectoring configuration
              "
          ::= { hwVectoringNlvGlobalConfig 1 }

    hwVectoringNlvMode OBJECT-TYPE
          SYNTAX Integer32 (1..2)
          MAX-ACCESS  read-write
          STATUS      current
          DESCRIPTION
              "It indicates in which node level vectoring mode the system works.
               Default values:1.
               Options:
               1.    - 2nlv, indicates that node level vectoring is supported on a maximum of 2 devices
               2.    - 3nlv, indicates that node level vectoring is supported on a maximum of 3 devices
              "
          ::= { hwVectoringNlvGlobalConfig 2 }

    hwVectoringNlvSlotList OBJECT-TYPE
          SYNTAX  OCTET STRING (SIZE(0..32))
          MAX-ACCESS  read-write
          STATUS      current
          DESCRIPTION
              "Indicates the slots that support vectoring in 3NLV mode. 
               This parameter is optional. If you configure this parameter, 
               configure two slots. After the 3NLV mode is selected, the slots 
               that support vectoring are set to slots 0/1 and 0/2 by default. 
               In this case, only slots 1 and 2 on a device support vectoring. 
               The ports on boards in slots 3 and 4 can be activated only after 
               being switched to the VDSL2 mode and the available frequency 
               bands are automatically limited to below 2.2 MHz.
              "
          ::= { hwVectoringNlvGlobalConfig 3 }

    hwVectoringNlvClockSourceCfg OBJECT-TYPE
          SYNTAX INTEGER
          {
              auto(1),
              local(2)
          }
          MAX-ACCESS  read-write
          STATUS      current
          DESCRIPTION
              "It is the configuration of an NLV clock source, which is used to 
               identify whether the current device is used as a clock output source.
               Default values:auto.
               Options:
               1. auto(1)      - Indicates that the clock source device is automatically 
                                 selected.Firstly, check whether ports on the NLV DSLAM are activated. 
                                 If a DSLAM has activated ports while others do not, 
                                 select this DSLAM as the clock source. If no DSLAM has activated ports, 
                                 determine the primary virtual path (VP) based on the values of the MAC addresses of these devices
               2. local(2)     - Indicates that the current device is used as the node level vectoring clock source
              "
            ::= { hwVectoringNlvGlobalConfig 4 } 

    hwVectoringNlvFaultPolicy OBJECT-TYPE
          SYNTAX INTEGER
          {
               auto(1),
               lock(2),
               nonVectoring(3),
               limit(4),
               slv(5)
          }
          MAX-ACCESS  read-write
          STATUS      current
          DESCRIPTION
              "It is an NLV fault handling policy, which is used to identify the vectoring fault handling policy used by the current device when an NLV fault occurs.
               Default values:auto.
               Options:
               1. auto(1)              - Indicates that the fault handling policy is decided by the vendor
               2. lock(2)              - Indicates that activation of the ports on the current device is not allowed
               3. nonVectoring(3)      - Indicates that VDSL2 boards are activated in non-vectoring mode
               4. limit(4)             - Is a VDSL2 fallback without vectoring and with spectrum occupation limited to 2.2 MHz
               5. slv(5)               - Rolls back to system level vectoring
              "
          ::= { hwVectoringNlvGlobalConfig 5 }

    hwVectoringNlvDescriptionCfg OBJECT-TYPE
          SYNTAX  OCTET STRING (SIZE(0..32))
          MAX-ACCESS  read-write
          STATUS      current
          DESCRIPTION
              "NLV description information, used to identify the node level vectoring device.
              "
          ::= { hwVectoringNlvGlobalConfig 6 }

    END
--
-- HUAWEI-VECTOR-MIB.mib
--

--  ==================================================================
-- Copyright (C) 2018 by  HUAWEI TECHNOLOGIES. All rights reserved.
-- 
-- Description: HUAWEI valued service managemnet MIB
-- Reference:
-- Version: V1.02
-- History:
-- <author>,  <date>,  <contents>
-- guanlinning   2015-03-09   create vsm mib
-- ==================================================================
-- ==================================================================

	HUAWEI-VSM-MIB DEFINITIONS ::= BEGIN
 
		IMPORTS
			hwDatacomm			
				FROM HUAWEI-MIB			
			Ipv6Address			
				FROM IPV6-TC			
			OBJECT-GROUP, MODULE-COMPLIANCE, NOTIFICATION-GROUP			
				FROM SNMPv2-CONF			
			TimeTicks, IpAddress, Integer32, Unsigned32, Counter64, 
            BITS, OBJECT-TYPE, MODULE-IDENTITY, NOTIFICATION-TYPE            
				FROM SNMPv2-SMI			
            DisplayString, TruthValue, TEXTUAL-CONVENTION            
				FROM SNMPv2-TC;
	
	
		hwVSMMIB MODULE-IDENTITY 
			LAST-UPDATED "201801131250Z"
			ORGANIZATION 
				 "Huawei Technologies Co.,Ltd."
			CONTACT-INFO 
				"Huawei Industrial Base
				  Bantian, Longgang
				   Shenzhen 518129
				   People's Republic of China
				   Website: http://www.huawei.com
				   Email: support@huawei.com
				 "
			DESCRIPTION 
				"The HUAWEI-VSM-MIB contains objects to manage the vsm function."
				
                                                                REVISION "201801131250Z"
                                                                DESCRIPTION
                                                                "modify description."
				
                                                                 REVISION
                                                                                        "201605280000Z"
                                                                  DESCRIPTION
                                                                                        "Change SlotID format."

                                                                  REVISION
                                                                                        "201503090000Z"
                                                                  DESCRIPTION
                                                                                        "Create vsm-mib."
			::= { hwDatacomm 341 }
		
	
--  Node definitions
		hwHTS OBJECT IDENTIFIER ::= { hwVSMMIB 1 }

		hwHTSObjiects OBJECT IDENTIFIER ::= { hwHTS 1 }
		
        hwHTSResourceTable OBJECT-TYPE
            SYNTAX SEQUENCE OF HwHTSResourceEntry
			MAX-ACCESS not-accessible
			STATUS current
			DESCRIPTION
				"This table provides information of hts resource."
			::= { hwHTSObjiects 1 }
		
        hwHTSResourceEntry OBJECT-TYPE
            SYNTAX HwHTSResourceEntry
			MAX-ACCESS not-accessible
			STATUS current
			DESCRIPTION
				"This entry provides information of hts resource."
            INDEX { hwHTSSlotId, hwHTSCpuId }
            ::= { hwHTSResourceTable 1 }
		
        HwHTSResourceEntry ::=
			SEQUENCE { 
                hwHTSSlotId
                    OCTET STRING,
                hwHTSCpuId
                    Integer32,
                hwHTSSessionNumber
                    Integer32,
                hwHTSSessionUsage
                    Integer32,
                hwHTSSessionThreshold
                    Integer32
			 }

        hwHTSSlotId OBJECT-TYPE
            SYNTAX OCTET STRING (SIZE (0..127))
			MAX-ACCESS accessible-for-notify
			STATUS current
			DESCRIPTION
				"This object indicates the slot index."
            ::= { hwHTSResourceEntry 1 }
		
        hwHTSCpuId OBJECT-TYPE
            SYNTAX Integer32 (0..3)
            MAX-ACCESS accessible-for-notify
            STATUS current
            DESCRIPTION
                "This object indicates the CPU index."
            ::= { hwHTSResourceEntry 2 }

        hwHTSSessionNumber OBJECT-TYPE
			SYNTAX Integer32
			MAX-ACCESS read-only
			STATUS current
			DESCRIPTION
				"This object indicates the number of HTS sessions."
            ::= { hwHTSResourceEntry 3 }

        hwHTSSessionUsage OBJECT-TYPE
			SYNTAX Integer32
			MAX-ACCESS read-only
			STATUS current
			DESCRIPTION
				"This object indicates the HTS session usage."
            ::= { hwHTSResourceEntry 4 }
        
        hwHTSSessionThreshold OBJECT-TYPE
			SYNTAX Integer32
			MAX-ACCESS read-only
			STATUS current
			DESCRIPTION
				"This object indicates the HTS session threshold."
            ::= { hwHTSResourceEntry 5 }          
            
		hwHTSTraps OBJECT IDENTIFIER ::= { hwHTS 2 } 
        
		hwHTSSessionThresholdAlarm NOTIFICATION-TYPE
			OBJECTS { hwHTSSessionUsage, hwHTSSessionThreshold }
			STATUS current
			DESCRIPTION 
				"This object indicates that an alarm is generated after the number of HTS sessions exceeds the threshold."
			::= { hwHTSTraps 1 }

		hwHTSSessionThresholdResumeAlarm NOTIFICATION-TYPE
			OBJECTS { hwHTSSessionUsage, hwHTSSessionThreshold }
			STATUS current
			DESCRIPTION 
				"This object indicates that the alarm generated after the number of HTS sessions exceeds the threshold is cleared."
			::= { hwHTSTraps 2 }

		hwHTSSessionExhaustAlarm NOTIFICATION-TYPE
			OBJECTS { hwHTSSessionNumber }
			STATUS current
			DESCRIPTION 
				"This object indicates that an HTS session exhaustion alarm is generated."
			::= { hwHTSTraps 3}

		hwHTSSessionExhaustResumeAlarm NOTIFICATION-TYPE
			OBJECTS { hwHTSSessionNumber }
			STATUS current
			DESCRIPTION 
				"This object indicates that the HTS session exhaustion alarm is cleared."
			::= { hwHTSTraps 4}
			
        hwHTSConformance OBJECT IDENTIFIER ::= { hwHTS 3 }

		hwHTSCompliances OBJECT IDENTIFIER ::= { hwHTSConformance 1 }
		
		hwHTSCompliance MODULE-COMPLIANCE
			STATUS current
			DESCRIPTION 
				"HTS compliance"
			MODULE -- this module
				MANDATORY-GROUPS { hwHTSSessionGroup, hwHTSTrapsGroup }
			::= { hwHTSCompliances 1 }
		
		hwHTSGroups OBJECT IDENTIFIER ::= { hwHTSConformance 2 }

		hwHTSSessionGroup OBJECT-GROUP
			OBJECTS {hwHTSSlotId, hwHTSCpuId, hwHTSSessionNumber, hwHTSSessionUsage, hwHTSSessionThreshold}
			STATUS current
			DESCRIPTION 
				"HTS session info group"
			::= { hwHTSGroups 1 }

		hwHTSTrapsGroup NOTIFICATION-GROUP
			NOTIFICATIONS {hwHTSSessionThresholdAlarm, hwHTSSessionThresholdResumeAlarm, hwHTSSessionExhaustAlarm, hwHTSSessionExhaustResumeAlarm}
			STATUS current
			DESCRIPTION 
				"HTS trap group"
			::= { hwHTSGroups 2 }
         
	END

--
-- HUAWEI-VSM-MIB.mib
--

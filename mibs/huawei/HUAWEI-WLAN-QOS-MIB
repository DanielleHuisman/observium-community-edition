-- Copyright (C) 2010 by HUAWEI TECHNOLOGIES. All rights reserved.
--
-- HUAWEI-WLAN-QOS-MIB.mib
-- MIB generated by MG-SOFT Visual MIB Builder Version 2.5 Build 225
-- Tuesday, February 19, 2013 at 18:37:25
--

	HUAWEI-WLAN-QOS-MIB DEFINITIONS ::= BEGIN

		IMPORTS 
			hwWlan			
				FROM HUAWEI-WLAN-MIB			
			OBJECT-GROUP, MODULE-COMPLIANCE			
				FROM SNMPv2-CONF			
			Integer32, Unsigned32, OBJECT-TYPE, MODULE-IDENTITY			
				FROM SNMPv2-SMI			
			RowStatus			
				FROM SNMPv2-TC;
	
	
		hwWlanQosManagement MODULE-IDENTITY
			LAST-UPDATED "201011100000Z"
			ORGANIZATION
				"Huawei Technologies Co.,Ltd."
			CONTACT-INFO
				"Huawei Industrial Base
				Bantian, Longgang
				Shenzhen 518129
				People's Republic of China
				Website: http://www.huawei.com
				Email: support@huawei.com
				"
			DESCRIPTION
				"Wlan QoS management."
			REVISION "201010121000Z"
			DESCRIPTION
				" V1.02, for the hwWlanTrafficProfileTable, change the 
				leaf nodes hwWlanClientLimitRate and hwWlanVAPLimitRate to 
				hwWlanClientUpLimitRate and hwWlanVAPUpLimitRate, add leaf nodes 
				hwWlanClientDownLimitRate and hwWlanClientDownLimitRate ."
			REVISION "201006011000Z"
			DESCRIPTION
				" V1.00, The first Draft."
			::= { hwWlan 5 }
		
	
		hwWlanWmmProfileTable OBJECT-TYPE
			SYNTAX SEQUENCE OF HwWlanWmmProfileEntry
			MAX-ACCESS not-accessible
			STATUS current
			DESCRIPTION
				"Wmm profile management table."
			::= { hwWlanQosManagement 1 }


		hwWlanWmmProfileEntry OBJECT-TYPE
			SYNTAX HwWlanWmmProfileEntry
			MAX-ACCESS not-accessible
			STATUS current
			DESCRIPTION
				"Wmm profile management entity."
			INDEX { hwWlanWmmProfileName }
			::= { hwWlanWmmProfileTable 1 }

		
		HwWlanWmmProfileEntry ::=
			SEQUENCE { 
				hwWlanWmmProfileName
					OCTET STRING,
				hwWlanWmmSwitch
					INTEGER,
				hwWlanWmmMandatorySwitch
					INTEGER,
				hwWlanWmmProfileRowStatus
					RowStatus,
				hwQAPEDCAVoiceECWmax
					Integer32,
				hwQAPEDCAVoiceECWmin
					Integer32,
				hwQAPEDCAVoiceAIFSN
					Integer32,
				hwQAPEDCAVoiceTXOPLimit
					Integer32,
				hwQAPEDCAVoiceACKPolicy
					INTEGER,
				hwQAPEDCAVideoECWmax
					Integer32,
				hwQAPEDCAVideoECWmin
					Integer32,
				hwQAPEDCAVideoAIFSN
					Integer32,
				hwQAPEDCAVideoTXOPLimit
					Integer32,
				hwQAPEDCAVideoACKPolicy
					INTEGER,
				hwQAPEDCABEECWmax
					Integer32,
				hwQAPEDCABEECWmin
					Integer32,
				hwQAPEDCABEAIFSN
					Integer32,
				hwQAPEDCABETXOPLimit
					Integer32,
				hwQAPEDCABEACKPolicy
					INTEGER,
				hwQAPEDCABKECWmax
					Integer32,
				hwQAPEDCABKECWmin
					Integer32,
				hwQAPEDCABKAIFSN
					Integer32,
				hwQAPEDCABKTXOPLimit
					Integer32,
				hwQAPEDCABKACKPolicy
					INTEGER,
				hwQClientEDCAVoiceECWmax
					Integer32,
				hwQClientEDCAVoiceECWmin
					Integer32,
				hwQClientEDCAVoiceAIFSN
					Integer32,
				hwQClientEDCAVoiceTXOPLimit
					Integer32,
				hwQClientEDCAVideoECWmax
					Integer32,
				hwQClientEDCAVideoECWmin
					Integer32,
				hwQClientEDCAVideoAIFSN
					Integer32,
				hwQClientEDCAVideoTXOPLimit
					Integer32,
				hwQClientEDCABEECWmax
					Integer32,
				hwQClientEDCABEECWmin
					Integer32,
				hwQClientEDCABEAIFSN
					Integer32,
				hwQClientEDCABETXOPLimit
					Integer32,
				hwQClientEDCABKECWmax
					Integer32,
				hwQClientEDCABKECWmin
					Integer32,
				hwQClientEDCABKAIFSN
					Integer32,
				hwQClientEDCABKTXOPLimit
					Integer32
			 }


		hwWlanWmmProfileName OBJECT-TYPE
			SYNTAX OCTET STRING (SIZE (1..31))
			MAX-ACCESS not-accessible
			STATUS current
			DESCRIPTION
				"Wmm profile name."
			::= { hwWlanWmmProfileEntry 1 }

		
		hwWlanWmmSwitch OBJECT-TYPE
			SYNTAX INTEGER
				{
				enable(1),
				disable(2)
				}
			MAX-ACCESS read-create
			STATUS current
			DESCRIPTION
				"The wmm switch."
			DEFVAL { 1 }
			::= { hwWlanWmmProfileEntry 2 }

		
		hwWlanWmmMandatorySwitch OBJECT-TYPE
			SYNTAX INTEGER
				{
				enable(1),
				disable(2)
				}
			MAX-ACCESS read-create
			STATUS current
			DESCRIPTION
				"The mandatory switch."
			DEFVAL { 2 }
			::= { hwWlanWmmProfileEntry 3 }


		hwWlanWmmProfileRowStatus OBJECT-TYPE
			SYNTAX RowStatus
			MAX-ACCESS read-write
			STATUS current
			DESCRIPTION
				"Row status.
				Add or delete a table item."
			::= { hwWlanWmmProfileEntry 4 }

		
		hwQAPEDCAVoiceECWmax OBJECT-TYPE
			SYNTAX Integer32 (0..15)
			MAX-ACCESS read-create
			STATUS current
			DESCRIPTION
				"Exponent form of CWmax. This attribute shall specify the value of ECWmax that shall be used by an AP for AC_VO."
			DEFVAL { 3 }
			::= { hwWlanWmmProfileEntry 5 }

		
		hwQAPEDCAVoiceECWmin OBJECT-TYPE
			SYNTAX Integer32 (0..15)
			MAX-ACCESS read-create
			STATUS current
			DESCRIPTION
				"Exponent form of CWmin. This attribute shall specify the value of ECWmin that shall be used by an AP for AC_VO."
			DEFVAL { 2 }
			::= { hwWlanWmmProfileEntry 6 }

		
		hwQAPEDCAVoiceAIFSN OBJECT-TYPE
			SYNTAX Integer32 (1..15)
			MAX-ACCESS read-create
			STATUS current
			DESCRIPTION
				"Arbitration Inter Frame Spacing Number. This attribute shall specify the value of AIFSN that shall be used by an AP for AC_VO."
			DEFVAL { 1 }
			::= { hwWlanWmmProfileEntry 7 }

		
		hwQAPEDCAVoiceTXOPLimit OBJECT-TYPE
			SYNTAX Integer32 (0..65535)
			MAX-ACCESS read-create
			STATUS current
			DESCRIPTION
				"Transmission Opportunity Limit. This attribute shall specify the value of TXOPLimit that shall be used by an AP for AC_VO."
			DEFVAL { 47 }
			::= { hwWlanWmmProfileEntry 8 }

		
		hwQAPEDCAVoiceACKPolicy OBJECT-TYPE
			SYNTAX INTEGER
				{
				normal(1),
				noack(2)
				}
			MAX-ACCESS read-create
			STATUS current
			DESCRIPTION
				"ACK policy. This attribute shall specify the policy of ACK that shall be used by an AP for AC_VO."
			DEFVAL { 1 }
			::= { hwWlanWmmProfileEntry 9 }

		
		hwQAPEDCAVideoECWmax OBJECT-TYPE
			SYNTAX Integer32 (0..15)
			MAX-ACCESS read-create
			STATUS current
			DESCRIPTION
				"Exponent form of CWmax. This attribute shall specify the value of ECWmax that shall be used by an AP for AC_VI."
			DEFVAL { 4 }
			::= { hwWlanWmmProfileEntry 10 }

		
		hwQAPEDCAVideoECWmin OBJECT-TYPE
			SYNTAX Integer32 (0..15)
			MAX-ACCESS read-create
			STATUS current
			DESCRIPTION
				"Exponent form of CWmin. This attribute shall specify the value of ECWmin that shall be used by an AP for AC_VI."
			DEFVAL { 3 }
			::= { hwWlanWmmProfileEntry 11 }

		
		hwQAPEDCAVideoAIFSN OBJECT-TYPE
			SYNTAX Integer32 (1..15)
			MAX-ACCESS read-create
			STATUS current
			DESCRIPTION
				"Arbitration Inter Frame Spacing Number. This attribute shall specify the value of AIFSN that shall be used by an AP for AC_VI."
			DEFVAL { 1 }
			::= { hwWlanWmmProfileEntry 12 }

		
		hwQAPEDCAVideoTXOPLimit OBJECT-TYPE
			SYNTAX Integer32 (0..65535)
			MAX-ACCESS read-create
			STATUS current
			DESCRIPTION
				"Transmission Opportunity Limit. This attribute shall specify the value of TXOPLimit that shall be used by an AP for AC_VI."
			DEFVAL { 94 }
			::= { hwWlanWmmProfileEntry 13 }

		
		hwQAPEDCAVideoACKPolicy OBJECT-TYPE
			SYNTAX INTEGER
				{
				normal(1),
				noack(2)
				}
			MAX-ACCESS read-create
			STATUS current
			DESCRIPTION
				"ACK policy. This attribute shall specify the policy of ACK that shall be used by an AP for AC_VI."
			DEFVAL { 1 }
			::= { hwWlanWmmProfileEntry 14 }

		
		hwQAPEDCABEECWmax OBJECT-TYPE
			SYNTAX Integer32 (0..15)
			MAX-ACCESS read-create
			STATUS current
			DESCRIPTION
				"Exponent form of CWmax. This attribute shall specify the value of ECWmax that shall be used by an AP for AC_BE."
			DEFVAL { 6 }
			::= { hwWlanWmmProfileEntry 15 }

		
		hwQAPEDCABEECWmin OBJECT-TYPE
			SYNTAX Integer32 (0..15)
			MAX-ACCESS read-create
			STATUS current
			DESCRIPTION
				"Exponent form of CWmin. This attribute shall specify the value of ECWmin that shall be used by an AP for AC_BE."
			DEFVAL { 4 }
			::= { hwWlanWmmProfileEntry 16 }

		
		hwQAPEDCABEAIFSN OBJECT-TYPE
			SYNTAX Integer32 (1..15)
			MAX-ACCESS read-create
			STATUS current
			DESCRIPTION
				"Arbitration Inter Frame Spacing Number. This attribute shall specify the value of AIFSN that shall be used by an AP for AC_BE."
			DEFVAL { 3 }
			::= { hwWlanWmmProfileEntry 17 }

		
		hwQAPEDCABETXOPLimit OBJECT-TYPE
			SYNTAX Integer32 (0..65535)
			MAX-ACCESS read-create
			STATUS current
			DESCRIPTION
				"Transmission Opportunity Limit. This attribute shall specify the value of TXOPLimit that shall be used by an AP for AC_BE."
			DEFVAL { 0 }
			::= { hwWlanWmmProfileEntry 18 }

		
		hwQAPEDCABEACKPolicy OBJECT-TYPE
			SYNTAX INTEGER
				{
				normal(1),
				noack(2)
				}
			MAX-ACCESS read-create
			STATUS current
			DESCRIPTION
				"ACK policy. This attribute shall specify the policy of ACK that shall be used by an AP for AC_BE."
			DEFVAL { 1 }
			::= { hwWlanWmmProfileEntry 19 }

		
		hwQAPEDCABKECWmax OBJECT-TYPE
			SYNTAX Integer32 (0..15)
			MAX-ACCESS read-create
			STATUS current
			DESCRIPTION
				"Exponent form of CWmax. This attribute shall specify the value of ECWmax that shall be used by an AP for AC_BK."
			DEFVAL { 10 }
			::= { hwWlanWmmProfileEntry 20 }

		
		hwQAPEDCABKECWmin OBJECT-TYPE
			SYNTAX Integer32 (0..15)
			MAX-ACCESS read-create
			STATUS current
			DESCRIPTION
				"Exponent form of CWmin. This attribute shall specify the value of ECWmin that shall be used by an AP for AC_BK."
			DEFVAL { 4 }
			::= { hwWlanWmmProfileEntry 21 }

		
		hwQAPEDCABKAIFSN OBJECT-TYPE
			SYNTAX Integer32 (1..15)
			MAX-ACCESS read-create
			STATUS current
			DESCRIPTION
				"Arbitration Inter Frame Spacing Number. This attribute shall specify the value of AIFSN that shall be used by an AP for AC_BK."
			DEFVAL { 7 }
			::= { hwWlanWmmProfileEntry 22 }

		
		hwQAPEDCABKTXOPLimit OBJECT-TYPE
			SYNTAX Integer32 (0..65535)
			MAX-ACCESS read-create
			STATUS current
			DESCRIPTION
				"Transmission Opportunity Limit. This attribute shall specify the value of TXOPLimit that shall be used by an AP for AC_BK."
			DEFVAL { 0 }
			::= { hwWlanWmmProfileEntry 23 }

		
		hwQAPEDCABKACKPolicy OBJECT-TYPE
			SYNTAX INTEGER
				{
				normal(1),
				noack(2)
				}
			MAX-ACCESS read-create
			STATUS current
			DESCRIPTION
				"ACK policy. This attribute shall specify the policy of ACK that shall be used by an AP for AC_BK."
			DEFVAL { 1 }
			::= { hwWlanWmmProfileEntry 24 }

		
		hwQClientEDCAVoiceECWmax OBJECT-TYPE
			SYNTAX Integer32 (0..15)
			MAX-ACCESS read-create
			STATUS current
			DESCRIPTION
				"Exponent form of CWmax. This attribute shall specify the value of ECWmax that shall be used by a STA for AC_VO."
			DEFVAL { 3 }
			::= { hwWlanWmmProfileEntry 25 }

		
		hwQClientEDCAVoiceECWmin OBJECT-TYPE
			SYNTAX Integer32 (0..15)
			MAX-ACCESS read-create
			STATUS current
			DESCRIPTION
				"Exponent form of CWmin. This attribute shall specify the value of ECWmin that shall be used by a STA for AC_VO."
			DEFVAL { 2 }
			::= { hwWlanWmmProfileEntry 26 }

		
		hwQClientEDCAVoiceAIFSN OBJECT-TYPE
			SYNTAX Integer32 (1..15)
			MAX-ACCESS read-create
			STATUS current
			DESCRIPTION
				"Arbitration Inter Frame Spacing Number. This attribute shall specify the value of AIFSN that shall be used by a STA for AC_VO."
			DEFVAL { 2 }
			::= { hwWlanWmmProfileEntry 27 }

		
		hwQClientEDCAVoiceTXOPLimit OBJECT-TYPE
			SYNTAX Integer32 (0..65535)
			MAX-ACCESS read-create
			STATUS current
			DESCRIPTION
				"Transmission Opportunity Limit. This attribute shall specify the value of TXOPLimit that shall be used by a STA for AC_VO."
			DEFVAL { 47 }
			::= { hwWlanWmmProfileEntry 28 }

		
		hwQClientEDCAVideoECWmax OBJECT-TYPE
			SYNTAX Integer32 (0..15)
			MAX-ACCESS read-create
			STATUS current
			DESCRIPTION
				"Exponent form of CWmax. This attribute shall specify the value of ECWmax that shall be used by a STA for AC_VI."
			DEFVAL { 4 }
			::= { hwWlanWmmProfileEntry 29 }

	
		hwQClientEDCAVideoECWmin OBJECT-TYPE
			SYNTAX Integer32 (0..15)
			MAX-ACCESS read-create
			STATUS current
			DESCRIPTION
				"Exponent form of CWmin. This attribute shall specify the value of ECWmin that shall be used by a STA for AC_VI."
			DEFVAL { 3 }
			::= { hwWlanWmmProfileEntry 30 }

		
		hwQClientEDCAVideoAIFSN OBJECT-TYPE
			SYNTAX Integer32 (1..15)
			MAX-ACCESS read-create
			STATUS current
			DESCRIPTION
				"Arbitration Inter Frame Spacing Number. This attribute shall specify the value of AIFSN that shall be used by a STA for AC_VI."
			DEFVAL { 2 }
			::= { hwWlanWmmProfileEntry 31 }

		
		hwQClientEDCAVideoTXOPLimit OBJECT-TYPE
			SYNTAX Integer32 (0..65535)
			MAX-ACCESS read-create
			STATUS current
			DESCRIPTION
				"Transmission Opportunity Limit. This attribute shall specify the value of TXOPLimit that shall be used by a STA for AC_VI."
			DEFVAL { 94 }
			::= { hwWlanWmmProfileEntry 32 }

		
		hwQClientEDCABEECWmax OBJECT-TYPE
			SYNTAX Integer32 (0..15)
			MAX-ACCESS read-create
			STATUS current
			DESCRIPTION
				"Exponent form of CWmax. This attribute shall specify the value of ECWmax that shall be used by a STA for AC_BE."
			DEFVAL { 10 }
			::= { hwWlanWmmProfileEntry 33 }

		
		hwQClientEDCABEECWmin OBJECT-TYPE
			SYNTAX Integer32 (0..15)
			MAX-ACCESS read-create
			STATUS current
			DESCRIPTION
				"Exponent form of CWmin. This attribute shall specify the value of ECWmin that shall be used by a STA for AC_BE."
			DEFVAL { 4 }
			::= { hwWlanWmmProfileEntry 34 }

		
		hwQClientEDCABEAIFSN OBJECT-TYPE
			SYNTAX Integer32 (1..15)
			MAX-ACCESS read-create
			STATUS current
			DESCRIPTION
				"Arbitration Inter Frame Spacing Number. This attribute shall specify the value of AIFSN that shall be used by a STA for AC_BE."
			DEFVAL { 3 }
			::= { hwWlanWmmProfileEntry 35 }

		
		hwQClientEDCABETXOPLimit OBJECT-TYPE
			SYNTAX Integer32 (0..65535)
			MAX-ACCESS read-create
			STATUS current
			DESCRIPTION
				"Transmission Opportunity Limit. This attribute shall specify the value of TXOPLimit that shall be used by a STA for AC_BE."
			DEFVAL { 0 }
			::= { hwWlanWmmProfileEntry 36 }

		
		hwQClientEDCABKECWmax OBJECT-TYPE
			SYNTAX Integer32 (0..15)
			MAX-ACCESS read-create
			STATUS current
			DESCRIPTION
				"Exponent form of CWmax. This attribute shall specify the value of ECWmax that shall be used by a STA for AC_BK."
			DEFVAL { 10 }
			::= { hwWlanWmmProfileEntry 37 }

		
		hwQClientEDCABKECWmin OBJECT-TYPE
			SYNTAX Integer32 (0..15)
			MAX-ACCESS read-create
			STATUS current
			DESCRIPTION
				"Exponent form of CWmin. This attribute shall specify the value of ECWmin that shall be used by a STA for AC_BK."
			DEFVAL { 4 }
			::= { hwWlanWmmProfileEntry 38 }

		
		hwQClientEDCABKAIFSN OBJECT-TYPE
			SYNTAX Integer32 (1..15)
			MAX-ACCESS read-create
			STATUS current
			DESCRIPTION
				"Arbitration Inter Frame Spacing Number. This attribute shall specify the value of AIFSN that shall be used by a STA for AC_BK."
			DEFVAL { 7 }
			::= { hwWlanWmmProfileEntry 39 }

		
		hwQClientEDCABKTXOPLimit OBJECT-TYPE
			SYNTAX Integer32 (0..65535)
			MAX-ACCESS read-create
			STATUS current
			DESCRIPTION
				"Transmission Opportunity Limit. This attribute shall specify the value of TXOPLimit that shall be used by a STA for AC_BK."
			DEFVAL { 0 }
			::= { hwWlanWmmProfileEntry 40 }


		hwWlanTrafficProfileTable OBJECT-TYPE
			SYNTAX SEQUENCE OF HwWlanTrafficProfileEntry
			MAX-ACCESS not-accessible
			STATUS current
			DESCRIPTION
				"Traffic profile management table."
			::= { hwWlanQosManagement 2 }



		hwWlanTrafficProfileEntry OBJECT-TYPE
			SYNTAX HwWlanTrafficProfileEntry
			MAX-ACCESS not-accessible
			STATUS current
			DESCRIPTION
				"Traffic profile management entity."
			INDEX { hwWlanTrafficProfileName }
			::= { hwWlanTrafficProfileTable 1 }

		
		HwWlanTrafficProfileEntry ::=
			SEQUENCE { 
				hwWlanTrafficProfileName
					OCTET STRING,
				hwWlanTrafficProfileRowStatus
					RowStatus,
				hwWlanClientUpLimitRate
					Unsigned32,
				hwWlanVAPUpLimitRate
					Unsigned32,
				hwWlan8021pMapMode
					INTEGER,
				hwWlan8021pSpecValue
					Integer32,
				hwWlanUP0Map8021p
					Integer32,
				hwWlanUP1Map8021p
					Integer32,
				hwWlanUP2Map8021p
					Integer32,
				hwWlanUP3Map8021p
					Integer32,
				hwWlanUP4Map8021p
					Integer32,
				hwWlanUP5Map8021p
					Integer32,
				hwWlanUP6Map8021p
					Integer32,
				hwWlanUP7Map8021p
					Integer32,
				hwWlan8021p0MapUPValue
					Integer32,
				hwWlan8021p1MapUPValue
					Integer32,
				hwWlan8021p2MapUPValue
					Integer32,
				hwWlan8021p3MapUPValue
					Integer32,
				hwWlan8021p4MapUPValue
					Integer32,
				hwWlan8021p5MapUPValue
					Integer32,
				hwWlan8021p6MapUPValue
					Integer32,
				hwWlan8021p7MapUPValue
					Integer32,
				hwWlanUpTunnelPriorityMapMode
					INTEGER,
				hwWlanUpTunnelPrioritySpecValue
					Integer32,
				hwWlanValue0MapUpTunnelPriority
					Integer32,
				hwWlanValue1MapUpTunnelPriority
					Integer32,
				hwWlanValue2MapUpTunnelPriority
					Integer32,
				hwWlanValue3MapUpTunnelPriority
					Integer32,
				hwWlanValue4MapUpTunnelPriority
					Integer32,
				hwWlanValue5MapUpTunnelPriority
					Integer32,
				hwWlanValue6MapUpTunnelPriority
					Integer32,
				hwWlanValue7MapUpTunnelPriority
					Integer32,
				hwWlanDownTunnelPriorityMapMode
					INTEGER,
				hwWlanDownTunnelPrioritySpecValue
					Integer32,
				hwWlanValue0MapDownTunnelPriority
					Integer32,
				hwWlanValue1MapDownTunnelPriority
					Integer32,
				hwWlanValue2MapDownTunnelPriority
					Integer32,
				hwWlanValue3MapDownTunnelPriority
					Integer32,
				hwWlanValue4MapDownTunnelPriority
					Integer32,
				hwWlanValue5MapDownTunnelPriority
					Integer32,
				hwWlanValue6MapDownTunnelPriority
					Integer32,
				hwWlanValue7MapDownTunnelPriority
					Integer32,
				hwWlanClientDownLimitRate
					Unsigned32,
				hwWlanVAPDownLimitRate
					Unsigned32,
				hwWlanTos0MapUPValue
					Integer32,
				hwWlanTos1MapUPValue
					Integer32,
				hwWlanTos2MapUPValue
					Integer32,
				hwWlanTos3MapUPValue
					Integer32,
				hwWlanTos4MapUPValue
					Integer32,
				hwWlanTos5MapUPValue
					Integer32,
				hwWlanTos6MapUPValue
					Integer32,
				hwWlanTos7MapUPValue
					Integer32
			 }


		hwWlanTrafficProfileName OBJECT-TYPE
			SYNTAX OCTET STRING (SIZE (1..31))
			MAX-ACCESS not-accessible
			STATUS current
			DESCRIPTION
				"Traffic profile name."
			::= { hwWlanTrafficProfileEntry 1 }

		
		hwWlanTrafficProfileRowStatus OBJECT-TYPE
			SYNTAX RowStatus
			MAX-ACCESS read-write
			STATUS current
			DESCRIPTION
				"Row status.
				Add or delete a table item."
			::= { hwWlanTrafficProfileEntry 2 }

		

		hwWlanClientUpLimitRate OBJECT-TYPE
			SYNTAX Unsigned32
			MAX-ACCESS read-create
			STATUS current
			DESCRIPTION
				"The up limit rate of client."
			::= { hwWlanTrafficProfileEntry 3 }

		
		hwWlanVAPUpLimitRate OBJECT-TYPE
			SYNTAX Unsigned32
			MAX-ACCESS read-create
			STATUS current
			DESCRIPTION
				"The up limit rate of VAP."
			::= { hwWlanTrafficProfileEntry 4 }


		hwWlan8021pMapMode OBJECT-TYPE
			SYNTAX INTEGER
				{
				designate(1),
				mapping(2)
				}
			MAX-ACCESS read-create
			STATUS current
			DESCRIPTION
				"The mapping mode of user-priority to 802.1p, supporting mapping and designate."
			::= { hwWlanTrafficProfileEntry 5 }


		hwWlan8021pSpecValue OBJECT-TYPE
			SYNTAX Integer32
			MAX-ACCESS read-create
			STATUS current
			DESCRIPTION
				"Designate the 802.1p priority value."
			DEFVAL { 0 }
			::= { hwWlanTrafficProfileEntry 6 }


		hwWlanUP0Map8021p OBJECT-TYPE
			SYNTAX Integer32
			MAX-ACCESS read-create
			STATUS current
			DESCRIPTION
				"The mapping 802.1p priority value from user-priority 0."
			DEFVAL { 0 }
			::= { hwWlanTrafficProfileEntry 7 }


		hwWlanUP1Map8021p OBJECT-TYPE
			SYNTAX Integer32
			MAX-ACCESS read-create
			STATUS current
			DESCRIPTION
				"The mapping 802.1p priority value from user-priority 1."
			DEFVAL { 1 }
			::= { hwWlanTrafficProfileEntry 8 }


		hwWlanUP2Map8021p OBJECT-TYPE
			SYNTAX Integer32
			MAX-ACCESS read-create
			STATUS current
			DESCRIPTION
				"The mapping 802.1p priority value from user-priority 2."
			DEFVAL { 2 }
			::= { hwWlanTrafficProfileEntry 9 }


		hwWlanUP3Map8021p OBJECT-TYPE
			SYNTAX Integer32
			MAX-ACCESS read-create
			STATUS current
			DESCRIPTION
				"The mapping 802.1p priority value from user-priority 3."
			DEFVAL { 3 }
			::= { hwWlanTrafficProfileEntry 10 }


		hwWlanUP4Map8021p OBJECT-TYPE
			SYNTAX Integer32
			MAX-ACCESS read-create
			STATUS current
			DESCRIPTION
				"The mapping 802.1p priority value from user-priority 4."
			DEFVAL { 4 }
			::= { hwWlanTrafficProfileEntry 11 }


		hwWlanUP5Map8021p OBJECT-TYPE
			SYNTAX Integer32
			MAX-ACCESS read-create
			STATUS current
			DESCRIPTION
				"The mapping 802.1p priority value from user-priority 5."
			DEFVAL { 5 }
			::= { hwWlanTrafficProfileEntry 12 }


		hwWlanUP6Map8021p OBJECT-TYPE
			SYNTAX Integer32
			MAX-ACCESS read-create
			STATUS current
			DESCRIPTION
				"The mapping 802.1p priority value from user-priority 6."
			DEFVAL { 6 }
			::= { hwWlanTrafficProfileEntry 13 }

		
		hwWlanUP7Map8021p OBJECT-TYPE
			SYNTAX Integer32
			MAX-ACCESS read-create
			STATUS current
			DESCRIPTION
				"The mapping 802.1p priority value from user-priority 7."
			DEFVAL { 7 }
			::= { hwWlanTrafficProfileEntry 14 }


		hwWlan8021p0MapUPValue OBJECT-TYPE
			SYNTAX Integer32 (0..7)
			MAX-ACCESS read-create
			STATUS current
			DESCRIPTION
				"The mapping user-priority value from 802.1p priority value 0."
			DEFVAL { 0 }
			::= { hwWlanTrafficProfileEntry 15 }


		hwWlan8021p1MapUPValue OBJECT-TYPE
			SYNTAX Integer32 (0..7)
			MAX-ACCESS read-create
			STATUS current
			DESCRIPTION
				"The mapping user-priority value from 802.1p priority value 1."
			DEFVAL { 1 }
			::= { hwWlanTrafficProfileEntry 16 }


		hwWlan8021p2MapUPValue OBJECT-TYPE
			SYNTAX Integer32 (0..7)
			MAX-ACCESS read-create
			STATUS current
			DESCRIPTION
				"The mapping user-priority value from 802.1p priority value 2."
			DEFVAL { 2 }
			::= { hwWlanTrafficProfileEntry 17 }


		hwWlan8021p3MapUPValue OBJECT-TYPE
			SYNTAX Integer32 (0..7)
			MAX-ACCESS read-create
			STATUS current
			DESCRIPTION
				"The mapping user-priority value from 802.1p priority value 3."
			DEFVAL { 3 }
			::= { hwWlanTrafficProfileEntry 18 }


		hwWlan8021p4MapUPValue OBJECT-TYPE
			SYNTAX Integer32 (0..7)
			MAX-ACCESS read-create
			STATUS current
			DESCRIPTION
				"The mapping user-priority value from 802.1p priority value 4."
			DEFVAL { 4 }
			::= { hwWlanTrafficProfileEntry 19 }


		hwWlan8021p5MapUPValue OBJECT-TYPE
			SYNTAX Integer32 (0..7)
			MAX-ACCESS read-create
			STATUS current
			DESCRIPTION
				"The mapping user-priority value from 802.1p priority value 5."
			DEFVAL { 5 }
			::= { hwWlanTrafficProfileEntry 20 }


		hwWlan8021p6MapUPValue OBJECT-TYPE
			SYNTAX Integer32 (0..7)
			MAX-ACCESS read-create
			STATUS current
			DESCRIPTION
				"The mapping user-priority value from 802.1p priority value 6."
			DEFVAL { 6 }
			::= { hwWlanTrafficProfileEntry 21 }


		hwWlan8021p7MapUPValue OBJECT-TYPE
			SYNTAX Integer32 (0..7)
			MAX-ACCESS read-create
			STATUS current
			DESCRIPTION
				"The mapping user-priority value from 802.1p priority value 7."
			DEFVAL { 7 }
			::= { hwWlanTrafficProfileEntry 22 }


		hwWlanUpTunnelPriorityMapMode OBJECT-TYPE
			SYNTAX INTEGER
				{
				specCOS(1),
				specDSCP(2),
				cos2cos(3),
				cos2dscp(4),
				dscp2cos(5),
				dscp2dscp(6)
				}
			MAX-ACCESS read-create
			STATUS current
			DESCRIPTION
				"The mapping mode to up tunnel priority, supporting specDSCP and specCOS and dscp2dscp and dscp2cos and cos2cos and cos2dscp."
			DEFVAL { 6 }
			::= { hwWlanTrafficProfileEntry 23 }

	
		hwWlanUpTunnelPrioritySpecValue OBJECT-TYPE
			SYNTAX Integer32
			MAX-ACCESS read-create
			STATUS current
			DESCRIPTION
				"Designate the up tunnel priority value."
			DEFVAL { 0 }
			::= { hwWlanTrafficProfileEntry 24 }


		hwWlanValue0MapUpTunnelPriority OBJECT-TYPE
			SYNTAX Integer32
			MAX-ACCESS read-create
			STATUS current
			DESCRIPTION
				"The mapping value of the up tunnel priority from priority value 0."
			DEFVAL { 0 }
			::= { hwWlanTrafficProfileEntry 25 }

	
		hwWlanValue1MapUpTunnelPriority OBJECT-TYPE
			SYNTAX Integer32
			MAX-ACCESS read-create
			STATUS current
			DESCRIPTION
				"The mapping value of the up tunnel priority from priority value 1."
			DEFVAL { 1 }
			::= { hwWlanTrafficProfileEntry 26 }

		
		hwWlanValue2MapUpTunnelPriority OBJECT-TYPE
			SYNTAX Integer32
			MAX-ACCESS read-create
			STATUS current
			DESCRIPTION
				"The mapping value of the up tunnel priority from priority value 2."
			DEFVAL { 2 }
			::= { hwWlanTrafficProfileEntry 27 }


		hwWlanValue3MapUpTunnelPriority OBJECT-TYPE
			SYNTAX Integer32
			MAX-ACCESS read-create
			STATUS current
			DESCRIPTION
				"The mapping value of the up tunnel priority from priority value 3."
			DEFVAL { 3 }
			::= { hwWlanTrafficProfileEntry 28 }

		
		hwWlanValue4MapUpTunnelPriority OBJECT-TYPE
			SYNTAX Integer32
			MAX-ACCESS read-create
			STATUS current
			DESCRIPTION
				"The mapping value of the up tunnel priority from priority value 4."
			DEFVAL { 4 }
			::= { hwWlanTrafficProfileEntry 29 }


		hwWlanValue5MapUpTunnelPriority OBJECT-TYPE
			SYNTAX Integer32
			MAX-ACCESS read-create
			STATUS current
			DESCRIPTION
				"The mapping value of the up tunnel priority from priority value 5."
			DEFVAL { 5 }
			::= { hwWlanTrafficProfileEntry 30 }


		hwWlanValue6MapUpTunnelPriority OBJECT-TYPE
			SYNTAX Integer32
			MAX-ACCESS read-create
			STATUS current
			DESCRIPTION
				"The mapping value of the up tunnel priority from priority value 6."
			DEFVAL { 6 }
			::= { hwWlanTrafficProfileEntry 31 }


		hwWlanValue7MapUpTunnelPriority OBJECT-TYPE
			SYNTAX Integer32
			MAX-ACCESS read-create
			STATUS current
			DESCRIPTION
				"The mapping value of the up tunnel priority from priority value 7."
			DEFVAL { 7 }
			::= { hwWlanTrafficProfileEntry 32 }
		
		
		hwWlanDownTunnelPriorityMapMode OBJECT-TYPE
			SYNTAX INTEGER
				{
				specCOS(1),
				specDSCP(2),
				cos2cos(3),
				cos2dscp(4),
				dscp2cos(5),
				dscp2dscp(6)
				}
			MAX-ACCESS read-create
			STATUS current
			DESCRIPTION
				"The mapping mode to down tunnel priority, supporting specDSCP and specCOS and dscp2dscp and dscp2cos and cos2cos and cos2dscp."
			DEFVAL { 6 }
			::= { hwWlanTrafficProfileEntry 33 }

		
		hwWlanDownTunnelPrioritySpecValue OBJECT-TYPE
			SYNTAX Integer32
			MAX-ACCESS read-create
			STATUS current
			DESCRIPTION
				"Designate the down tunnel priority value."
			DEFVAL { 0 }
			::= { hwWlanTrafficProfileEntry 34 }

	
		hwWlanValue0MapDownTunnelPriority OBJECT-TYPE
			SYNTAX Integer32
			MAX-ACCESS read-create
			STATUS current
			DESCRIPTION
				"The mapping value of the down tunnel priority from priority value 0."
			DEFVAL { 0 }
			::= { hwWlanTrafficProfileEntry 35 }

		
		hwWlanValue1MapDownTunnelPriority OBJECT-TYPE
			SYNTAX Integer32
			MAX-ACCESS read-create
			STATUS current
			DESCRIPTION
				"The mapping value of the down tunnel priority from priority value 1."
			DEFVAL { 1 }
			::= { hwWlanTrafficProfileEntry 36 }

		
		hwWlanValue2MapDownTunnelPriority OBJECT-TYPE
			SYNTAX Integer32
			MAX-ACCESS read-create
			STATUS current
			DESCRIPTION
				"The mapping value of the down tunnel priority from priority value 2."
			DEFVAL { 2 }
			::= { hwWlanTrafficProfileEntry 37 }

	
		hwWlanValue3MapDownTunnelPriority OBJECT-TYPE
			SYNTAX Integer32
			MAX-ACCESS read-create
			STATUS current
			DESCRIPTION
				"The mapping value of the down tunnel priority from priority value 3."
			DEFVAL { 7 }
			::= { hwWlanTrafficProfileEntry 38 }

	
		hwWlanValue4MapDownTunnelPriority OBJECT-TYPE
			SYNTAX Integer32
			MAX-ACCESS read-create
			STATUS current
			DESCRIPTION
				"The mapping value of the down tunnel priority from priority value 4."
			DEFVAL { 4 }
			::= { hwWlanTrafficProfileEntry 39 }

		
		hwWlanValue5MapDownTunnelPriority OBJECT-TYPE
			SYNTAX Integer32
			MAX-ACCESS read-create
			STATUS current
			DESCRIPTION
				"The mapping value of the down tunnel priority from priority value 5."
			DEFVAL { 5 }
			::= { hwWlanTrafficProfileEntry 40 }

		
		hwWlanValue6MapDownTunnelPriority OBJECT-TYPE
			SYNTAX Integer32
			MAX-ACCESS read-create
			STATUS current
			DESCRIPTION
				"The mapping value of the down tunnel priority from priority value 6."
			DEFVAL { 6 }
			::= { hwWlanTrafficProfileEntry 41 }

		
		hwWlanValue7MapDownTunnelPriority OBJECT-TYPE
			SYNTAX Integer32
			MAX-ACCESS read-create
			STATUS current
			DESCRIPTION
				"The mapping value of the down tunnel priority from priority value 7."
			DEFVAL { 7 }
			::= { hwWlanTrafficProfileEntry 42 }

		
		hwWlanClientDownLimitRate OBJECT-TYPE
			SYNTAX Unsigned32
			MAX-ACCESS read-create
			STATUS current
			DESCRIPTION
				"The down limit rate of client."
			::= { hwWlanTrafficProfileEntry 43 }

		
		hwWlanVAPDownLimitRate OBJECT-TYPE
			SYNTAX Unsigned32
			MAX-ACCESS read-create
			STATUS current
			DESCRIPTION
				"The down limit rate of VAP."
			::= { hwWlanTrafficProfileEntry 44 }


		hwWlanTos0MapUPValue OBJECT-TYPE
			SYNTAX Integer32 (0..7)
			MAX-ACCESS read-create
			STATUS current
			DESCRIPTION
				"The mapping user-priority value from tos priority value 0."
			DEFVAL { 0 }
			::= { hwWlanTrafficProfileEntry 45 }


		hwWlanTos1MapUPValue OBJECT-TYPE
			SYNTAX Integer32 (0..7)
			MAX-ACCESS read-create
			STATUS current
			DESCRIPTION
				"The mapping user-priority value from tos priority value 1."
			DEFVAL { 1 }
			::= { hwWlanTrafficProfileEntry 46 }


		hwWlanTos2MapUPValue OBJECT-TYPE
			SYNTAX Integer32 (0..7)
			MAX-ACCESS read-create
			STATUS current
			DESCRIPTION
				"The mapping user-priority value from tos priority value 2."
			DEFVAL { 2 }
			::= { hwWlanTrafficProfileEntry 47 }


		hwWlanTos3MapUPValue OBJECT-TYPE
			SYNTAX Integer32 (0..7)
			MAX-ACCESS read-create
			STATUS current
			DESCRIPTION
				"The mapping user-priority value from tos priority value 3."
			DEFVAL { 3 }
			::= { hwWlanTrafficProfileEntry 48 }


		hwWlanTos4MapUPValue OBJECT-TYPE
			SYNTAX Integer32 (0..7)
			MAX-ACCESS read-create
			STATUS current
			DESCRIPTION
				"The mapping user-priority value from tos priority value 4."
			DEFVAL { 4 }
			::= { hwWlanTrafficProfileEntry 49 }


		hwWlanTos5MapUPValue OBJECT-TYPE
			SYNTAX Integer32 (0..7)
			MAX-ACCESS read-create
			STATUS current
			DESCRIPTION
				"The mapping user-priority value from tos priority value 5."
			DEFVAL { 5 }
			::= { hwWlanTrafficProfileEntry 50 }


		hwWlanTos6MapUPValue OBJECT-TYPE
			SYNTAX Integer32 (0..7)
			MAX-ACCESS read-create
			STATUS current
			DESCRIPTION
				"The mapping user-priority value from tos priority value 6."
			DEFVAL { 6 }
			::= { hwWlanTrafficProfileEntry 51 }


		hwWlanTos7MapUPValue OBJECT-TYPE
			SYNTAX Integer32 (0..7)
			MAX-ACCESS read-create
			STATUS current
			DESCRIPTION
				"The mapping user-priority value from 802.1p priority value 7."
			DEFVAL { 7 }
			::= { hwWlanTrafficProfileEntry 52 }
    

		
		hwWlanBatchWmmProfileStartNumber OBJECT-TYPE
			SYNTAX Integer32 (0..32)
			MAX-ACCESS read-write
			STATUS current
			DESCRIPTION
				"The wmm-profile start number in batch operation. This node is used with node
				hwWlanBatchWmmProfileGetNumber, for example, hwWlanBatchWmmProfileStartNumber
				is set to one, and hwWlanBatchWmmProfileGetNumber is set to three, then get
				the node hwWlanBatchWmmProfileReturnNumber, hwWlanBatchWmmProfileName, that 
				means start from the first wmm-profile, get three	wmm-profile's name . if 
				it dose not exist three wmm-profile, the hwWlanBatchWmmProfileReturnNumber will 
				be the real wmm-profile number, otherwise, it is equal to hwWlanBatchWmmProfileGetNumber."
			::= { hwWlanQosManagement 3 }

		
		hwWlanBatchWmmProfileGetNumber OBJECT-TYPE
			SYNTAX Integer32 (0..32)
			MAX-ACCESS read-write
			STATUS current
			DESCRIPTION
				"The wmm-profile number that want to get in batch operation.This node is used 
				with node	hwWlanBatchWmmProfileStartNumber, for example, hwWlanBatchWmmProfileStartNumber
				is set to one, and hwWlanBatchWmmProfileGetNumber is set to three, then get
				the node hwWlanBatchWmmProfileReturnNumber, hwWlanBatchWmmProfileName, that 
				means start from the first wmm-profile, get three	wmm-profile's name . if 
				it dose not exist three wmm-profile, the hwWlanBatchWmmProfileReturnNumber will 
				be the real wmm-profile number, otherwise, it is equal to hwWlanBatchWmmProfileGetNumber."
			::= { hwWlanQosManagement 4 }

		
		hwWlanBatchWmmProfileReturnNumber OBJECT-TYPE
			SYNTAX Integer32
			MAX-ACCESS read-only
			STATUS current
			DESCRIPTION
				"The wmm-profile number get in batch operation."
			::= { hwWlanQosManagement 5 }

		
		hwWlanBatchWmmProfileName OBJECT-TYPE
			SYNTAX OCTET STRING
			MAX-ACCESS read-only
			STATUS current
			DESCRIPTION
				"The names of wmm-profiles which are determined by node hwWlanBatchWmmProfileStartNumber
				and node hwWlanBatchWmmProfileGetNumber.
				each wmm-profile name is divided by '?'."
			::= { hwWlanQosManagement 6 }

		
		hwWlanBatchTrafficProfileStartNumber OBJECT-TYPE
			SYNTAX Integer32 (0..32)
			MAX-ACCESS read-write
			STATUS current
			DESCRIPTION
				"The traffic-profile start number in batch operation. This node is used with node
				hwWlanBatchTrafficProfileGetNumber, for example, hwWlanBatchTrafficProfileStartNumber
				is set to one, and hwWlanBatchTrafficProfileGetNumber is set to three, then get
				the node hwWlanBatchTrafficProfileReturnNumber, hwWlanBatchTrafficProfileName, that 
				means start from the first traffic-profile, get three	traffic-profile's name . if 
				it dose not exist three traffic-profile, the hwWlanBatchTrafficProfileReturnNumber will 
				be the real traffic-profile number, otherwise, it is equal to hwWlanBatchTrafficProfileGetNumber."
			::= { hwWlanQosManagement 7 }

		
		hwWlanBatchTrafficProfileGetNumber OBJECT-TYPE
			SYNTAX Integer32 (0..32)
			MAX-ACCESS read-write
			STATUS current
			DESCRIPTION
				"The traffic-profile number that want to get in batch operation.This node is used 
				with node	hwWlanBatchTrafficProfileStartNumber, for example, hwWlanBatchTrafficProfileStartNumber
				is set to one, and hwWlanBatchTrafficProfileGetNumber is set to three, then get
				the node hwWlanBatchTrafficProfileReturnNumber, hwWlanBatchTrafficProfileName, that 
				means start from the first traffic-profile, get three	traffic-profile's name . if 
				it dose not exist three traffic-profile, the hwWlanBatchTrafficProfileReturnNumber will 
				be the real traffic-profile number, otherwise, it is equal to hwWlanBatchTrafficProfileGetNumber."
			::= { hwWlanQosManagement 8 }

		
		hwWlanBatchTrafficProfileReturnNumber OBJECT-TYPE
			SYNTAX Integer32
			MAX-ACCESS read-only
			STATUS current
			DESCRIPTION
				"The traffic-profile number get in batch operation."
			::= { hwWlanQosManagement 9 }

		
		hwWlanBatchTrafficProfileName OBJECT-TYPE
			SYNTAX OCTET STRING
			MAX-ACCESS read-only
			STATUS current
			DESCRIPTION
				"The names of traffic-profiles which are determined by node 
				hwWlanBatchTrafficProfileStartNumber and node hwWlanBatchTrafficProfileGetNumber.
				each traffic-profile name is divided by '?'."
			::= { hwWlanQosManagement 10 }
		
		hwWlanQosManagementObjects OBJECT IDENTIFIER ::= { hwWlanQosManagement 11 }
		
		hwWlanQosManagementConformance OBJECT IDENTIFIER ::= { hwWlanQosManagement 12 }
		
		hwWlanQosManagementCompliances OBJECT IDENTIFIER ::= { hwWlanQosManagementConformance 1 }
		
		hwWlanQosManagementCompliance MODULE-COMPLIANCE
			STATUS current
			DESCRIPTION 
			    "Description."
			MODULE -- this module
			    MANDATORY-GROUPS { hwWlanWmmProfileGroup, hwWlanTrafficProfileGroup, hwWlanQosManagementGroup }
			::= { hwWlanQosManagementCompliances 1 }
		
		hwWlanQosManagementObjectGroups OBJECT IDENTIFIER ::= { hwWlanQosManagementConformance 2 }
		
		hwWlanWmmProfileGroup OBJECT-GROUP
			OBJECTS { hwWlanWmmSwitch, hwWlanWmmMandatorySwitch, hwWlanWmmProfileRowStatus, hwQAPEDCAVoiceECWmax, hwQAPEDCAVoiceECWmin, 
				hwQAPEDCAVoiceAIFSN, hwQAPEDCAVoiceTXOPLimit, hwQAPEDCAVoiceACKPolicy, hwQAPEDCAVideoECWmax, hwQAPEDCAVideoECWmin, 
				hwQAPEDCAVideoAIFSN, hwQAPEDCAVideoTXOPLimit, hwQAPEDCAVideoACKPolicy, hwQAPEDCABEECWmax, hwQAPEDCABEECWmin, 
				hwQAPEDCABEAIFSN, hwQAPEDCABETXOPLimit, hwQAPEDCABEACKPolicy, hwQAPEDCABKECWmax, hwQAPEDCABKECWmin, 
				hwQAPEDCABKAIFSN, hwQAPEDCABKTXOPLimit, hwQAPEDCABKACKPolicy, hwQClientEDCAVoiceECWmax, hwQClientEDCAVoiceECWmin, 
				hwQClientEDCAVoiceAIFSN, hwQClientEDCAVoiceTXOPLimit, hwQClientEDCAVideoECWmax, hwQClientEDCAVideoECWmin, hwQClientEDCAVideoAIFSN, 
				hwQClientEDCAVideoTXOPLimit, hwQClientEDCABEECWmax, hwQClientEDCABEECWmin, hwQClientEDCABEAIFSN, hwQClientEDCABETXOPLimit, 
				hwQClientEDCABKECWmax, hwQClientEDCABKECWmin, hwQClientEDCABKAIFSN, hwQClientEDCABKTXOPLimit }
			STATUS current
			DESCRIPTION
				"Description."
			::= { hwWlanQosManagementObjectGroups 1 }
		
		hwWlanTrafficProfileGroup OBJECT-GROUP
			OBJECTS { hwWlanTrafficProfileRowStatus, hwWlanClientUpLimitRate, hwWlanVAPUpLimitRate, hwWlan8021pMapMode, hwWlan8021pSpecValue, 
				hwWlanUP0Map8021p, hwWlanUP1Map8021p, hwWlanUP2Map8021p, hwWlanUP3Map8021p, hwWlanUP4Map8021p, 
				hwWlanUP5Map8021p, hwWlanUP6Map8021p, hwWlanUP7Map8021p, hwWlan8021p0MapUPValue, hwWlan8021p1MapUPValue, 
				hwWlan8021p2MapUPValue, hwWlan8021p3MapUPValue, hwWlan8021p4MapUPValue, hwWlan8021p5MapUPValue, hwWlan8021p6MapUPValue, 
				hwWlan8021p7MapUPValue, hwWlanUpTunnelPriorityMapMode, hwWlanUpTunnelPrioritySpecValue, hwWlanValue0MapUpTunnelPriority, hwWlanValue1MapUpTunnelPriority, 
				hwWlanValue2MapUpTunnelPriority, hwWlanValue3MapUpTunnelPriority, hwWlanValue4MapUpTunnelPriority, hwWlanValue5MapUpTunnelPriority, hwWlanValue6MapUpTunnelPriority, 
				hwWlanValue7MapUpTunnelPriority, hwWlanDownTunnelPriorityMapMode, hwWlanDownTunnelPrioritySpecValue, hwWlanValue0MapDownTunnelPriority, hwWlanValue1MapDownTunnelPriority, 
				hwWlanValue2MapDownTunnelPriority, hwWlanValue3MapDownTunnelPriority, hwWlanValue4MapDownTunnelPriority, hwWlanValue5MapDownTunnelPriority, hwWlanValue6MapDownTunnelPriority, 
				hwWlanValue7MapDownTunnelPriority, hwWlanClientDownLimitRate, hwWlanVAPDownLimitRate, hwWlanTos0MapUPValue, hwWlanTos1MapUPValue, 
				hwWlanTos2MapUPValue, hwWlanTos3MapUPValue, hwWlanTos4MapUPValue, hwWlanTos5MapUPValue, hwWlanTos6MapUPValue, 
				hwWlanTos7MapUPValue }
			STATUS current
			DESCRIPTION
				"Description."
			::= { hwWlanQosManagementObjectGroups 2 }
		
		hwWlanQosManagementGroup OBJECT-GROUP
			OBJECTS { hwWlanBatchWmmProfileStartNumber, hwWlanBatchWmmProfileGetNumber, hwWlanBatchWmmProfileReturnNumber, hwWlanBatchWmmProfileName, hwWlanBatchTrafficProfileStartNumber, 
				hwWlanBatchTrafficProfileGetNumber, hwWlanBatchTrafficProfileReturnNumber, hwWlanBatchTrafficProfileName }
			STATUS current
			DESCRIPTION
				"Description."
			::= { hwWlanQosManagementObjectGroups 3 }
		
	
	END

--
-- HUAWEI-WLAN-QOS-MIB.mib
--

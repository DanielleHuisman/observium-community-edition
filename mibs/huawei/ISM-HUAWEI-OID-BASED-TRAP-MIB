--
-- ISM-HUAWEI-OID-BASED-TRAP-MIB.mib
-- MIB generated by MG-SOFT Visual MIB Builder Version 4.0 Build 347
-- Wednesday, March 02, 2016 at 22:48:04
--

--  ISM-HUAWEI-OID-BASED-TRAP-MIB.mib
-- MIB generated by MG-SOFT Visual MIB Builder Version 4.0 Build 347
-- Saturday, February 27, 2016 at 15:04:41
--
--  ISM-HUAWEI-MIB.mib
-- MIB generated by MG-SOFT Visual MIB Builder Version 4.0 Build 347
-- Thursday, March 27, 2014 at 11:36:30
--

    ISM-HUAWEI-OID-BASED-TRAP-MIB DEFINITIONS ::= BEGIN

        IMPORTS
            hwinfoFaultNotificationType, hwIsmReportingAlarmNodeCode, hwIsmReportingAlarmLocationInfo, hwIsmReportingAlarmRestoreAdvice, hwIsmReportingAlarmFaultTitle, 
            hwIsmReportingAlarmFaultType, hwIsmReportingAlarmFaultLevel, hwIsmReportingAlarmAlarmID, hwIsmReportingAlarmFaultTime, hwIsmReportingAlarmSerialNo, 
            hwIsmReportingAlarmAdditionInfo, hwIsmReportingAlarmFaultCategory, hwIsmReportingAlarmLocationAlarmID, isoConformance, basicCompliance  
                FROM ISM-HUAWEI-MIB     
            NOTIFICATION-GROUP  
                FROM SNMPv2-CONF    
            MODULE-IDENTITY, NOTIFICATION-TYPE  
                FROM SNMPv2-SMI;


--  1.3.6.1.4.1.2011.2.91.10.2.1.15
-- March 06, 2013 at 10:10 GMT
-- September 17, 2008 at 16:29 GMT
        -- 1.3.6.1.4.1.2011.2.91.10.2.1.1
        oidBasedTrap MODULE-IDENTITY 
            LAST-UPDATED "201303061010Z"        -- March 06, 2013 at 10:10 GMT
            ORGANIZATION 
                "Huawei Technologies Co.,Ltd."
            CONTACT-INFO 
                "Huawei Industrial Base
                Bantian, Longgang
                Shenzhen 518129
                People's Republic of China
                Website: http://www.huawei.com
                Email: support@huawei.com"
            DESCRIPTION 
                "Description."
            REVISION "200809171629Z"        -- September 17, 2008 at 16:29 GMT
            DESCRIPTION 
                "V1R1
                V1R2"
            ::= { hwinfoFaultNotificationType 1 }




--
-- Node definitions
--

        -- 1.3.6.1.4.1.2011.2.91.10.2.1.1.15
        storage OBJECT IDENTIFIER ::= { oidBasedTrap 15 }


        -- 1.3.6.1.4.1.2011.2.91.10.2.1.1.15.6
        port OBJECT IDENTIFIER ::= { storage 6 }


        -- 1.3.6.1.4.1.2011.2.91.10.2.1.1.15.6.9
        ethFCoEPortIsDisconnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "ETH/FCoE Port Link Down."
            ::= { port 9 }


        -- 1.3.6.1.4.1.2011.2.91.10.2.1.1.15.6.17
        portIsWorkingInHalfDuplexMode NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Network Port Is Working In Half-Duplex Mode."
            ::= { port 17 }


        -- 1.3.6.1.4.1.2011.2.91.10.2.1.1.15.6.20
        expPortHasTooManyBitErrors NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Port Has Too Many Bit Errors."
            ::= { port 20 }


        -- 1.3.6.1.4.1.2011.2.91.10.2.1.1.15.6.21
        hostPortHasTooManyBitErrors NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Host Port Has Too Many Bit Errors."
            ::= { port 21 }


        -- 1.3.6.1.4.1.2011.2.91.10.2.1.1.15.6.22
        pciePortIsPartiallyDamaged NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "PCIe Port Partially Damaged."
            ::= { port 22 }


        -- 1.3.6.1.4.1.2011.2.91.10.2.1.1.15.6.25
        pciePortIsDisconnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "PCIe Port Disconnected."
            ::= { port 25 }


        -- 1.3.6.1.4.1.2011.2.91.10.2.1.1.15.6.6
        expansionPortPartiallyDamaged NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Port Partially Damaged."
            ::= { port 6 }


        -- 1.3.6.1.4.1.2011.2.91.10.2.1.1.15.6.2
        expansionPortIsDisconnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Port Link Down."
            ::= { port 2 }


        -- 1.3.6.1.4.1.2011.2.91.10.2.1.1.15.6.29
        rateIsSmallerThanAllowedMaximum NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Port Negotiated Rate Is Smaller Than The Allowed Maximum."
            ::= { port 29 }


        -- 1.3.6.1.4.1.2011.2.91.10.2.1.1.15.6.15
        portNegotiatedRateNotToMaximum NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Negotiated Rate Of A Port Is Smaller Than The Allowed Maximum."
            ::= { port 15 }


        -- 1.3.6.1.4.1.2011.2.91.10.2.1.1.15.6.4
        hostPortIsDisconnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Host Port Link Down."
            ::= { port 4 }


        -- 1.3.6.1.4.1.2011.2.91.10.2.1.1.15.6.73
        manageNetworkPortIsDisconnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Management Network Port Is Disconnected."
            ::= { port 73 }


        -- 1.3.6.1.4.1.2011.2.91.10.2.1.1.15.6.16
        expansionPortIsolated NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Port Isolated."
            ::= { port 16 }


        -- 1.3.6.1.4.1.2011.2.91.10.2.1.1.15.6.11
        managementNetworkPortIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Management Network Port Is Faulty."
            ::= { port 11 }


        -- 1.3.6.1.4.1.2011.2.91.10.2.1.1.15.6.14
        pciePortIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "PCIe Port Is Faulty."
            ::= { port 14 }


        -- 1.3.6.1.4.1.2011.2.91.10.2.1.1.15.6.13
        hostPortIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Host Port Is Faulty."
            ::= { port 13 }


        -- 1.3.6.1.4.1.2011.2.91.10.2.1.1.15.6.12
        expansionPortIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Port Is Faulty."
            ::= { port 12 }


        -- 1.3.6.1.4.1.2011.2.91.10.2.1.1.15.10
        disk OBJECT IDENTIFIER ::= { storage 10 }


        -- 1.3.6.1.4.1.2011.2.91.10.2.1.1.15.10.269
        numberOfDisksExceedsUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Disks Exceeds The Upper Limit."
            ::= { disk 269 }


        -- 1.3.6.1.4.1.2011.2.91.10.2.1.1.15.10.259
        mixtureOfSATAAndNonSATADisks NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SATA Disks And Non-SATA Disks Mixed."
            ::= { disk 259 }


        -- 1.3.6.1.4.1.2011.2.91.10.2.1.1.15.10.91
        diskIsIsolated NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Hard Disk Is Isolated."
            ::= { disk 91 }


        -- 1.3.6.1.4.1.2011.2.91.10.2.1.1.15.10.95
        slowDiskResponse NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Slow Disk Response."
            ::= { disk 95 }


        -- 1.3.6.1.4.1.2011.2.91.10.2.1.1.15.10.155
        authenticationOfSEDAccessFails NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Authenticate Self-Encrypting Disk Access."
            ::= { disk 155 }


        -- 1.3.6.1.4.1.2011.2.91.10.2.1.1.15.10.8
        cofferDiskIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Coffer Disk Is Faulty."
            ::= { disk 8 }


        -- 1.3.6.1.4.1.2011.2.91.10.2.1.1.15.10.9
        cofferDiskFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Faulty Coffer."
            ::= { disk 9 }


        -- 1.3.6.1.4.1.2011.2.91.10.2.1.1.15.10.20
        diskInEngineMonitoringFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The System Failed To Monitor A Disk In The Controller Enclosure."
            ::= { disk 20 }


        -- 1.3.6.1.4.1.2011.2.91.10.2.1.1.15.10.21
        diskMonitoringFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The System Failed To Monitor A Disk In A Disk Enclosure."
            ::= { disk 21 }


        -- 1.3.6.1.4.1.2011.2.91.10.2.1.1.15.10.275
        diskModelIsIncompatible NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Incompatible Disk Model."
            ::= { disk 275 }


        -- 1.3.6.1.4.1.2011.2.91.10.2.1.1.15.10.274
        diskInSingleLinkState NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Is In Single Link State."
            ::= { disk 274 }


        -- 1.3.6.1.4.1.2011.2.91.10.2.1.1.15.10.273
        diskIsAboutToFail NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Is About To Fail."
            ::= { disk 273 }


        -- 1.3.6.1.4.1.2011.2.91.10.2.1.1.15.10.279
        cofferDiskModelIsIncompatible NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Coffer Disk Type Is Not Supported."
            ::= { disk 279 }


        -- 1.3.6.1.4.1.2011.2.91.10.2.1.1.15.10.4
        diskTemperatureExceedsUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Temperature Exceeds The Upper Limit."
            ::= { disk 4 }


        -- 1.3.6.1.4.1.2011.2.91.10.2.1.1.15.10.79
        cofferDiskInInccorrectSlot NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Coffer Disk Is Inserted Into An Incorrect Slot."
            ::= { disk 79 }


        -- 1.3.6.1.4.1.2011.2.91.10.2.1.1.15.10.132
        diskIsRejectedBySystem NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Disk Is Rejected By The System."
            ::= { disk 132 }


        -- 1.3.6.1.4.1.2011.2.91.10.2.1.1.15.10.10
        cofferDisksNotFound NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Coffer Disks Not Found."
            ::= { disk 10 }


        -- 1.3.6.1.4.1.2011.2.91.10.2.1.1.15.10.258
        authenticationOfSEDKeyFails NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Authenticate A Self-Encrypting Disk Key."
            ::= { disk 258 }


        -- 1.3.6.1.4.1.2011.2.91.10.2.1.1.15.10.271
        diskHardwareIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Is Faulty."
            ::= { disk 271 }


        -- 1.3.6.1.4.1.2011.2.91.10.2.1.1.15.10.272
        diskIsUnrecognizable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Unrecognizable Disk."
            ::= { disk 272 }


        -- 1.3.6.1.4.1.2011.2.91.10.2.1.1.15.10.149
        svpDiskIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SVP Disk Is Faulty."
            ::= { disk 149 }


        -- 1.3.6.1.4.1.2011.2.91.10.2.1.1.15.10.148
        svpDiskIsNotInserted NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SVP Disk Is Not Inserted."
            ::= { disk 148 }


        -- 1.3.6.1.4.1.2011.2.91.10.2.1.1.15.11
        lun OBJECT IDENTIFIER ::= { storage 11 }


        -- 1.3.6.1.4.1.2011.2.91.10.2.1.1.15.11.258
        externalLunTypeChanged NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "External LUN Is Changed To Command Device."
            ::= { lun 258 }


        -- 1.3.6.1.4.1.2011.2.91.10.2.1.1.15.11.268
        lunStartBgrTaskFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "LUN Start Bgr Task Failed."
            ::= { lun 268 }


        -- 1.3.6.1.4.1.2011.2.91.10.2.1.1.15.11.267
        localArrayRegPathToHeteroFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Register Paths From The Local Storage Array To Heterogeneous Storage Array."
            ::= { lun 267 }


        -- 1.3.6.1.4.1.2011.2.91.10.2.1.1.15.11.2
        theLUNHasMediumError NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "LUN Has A Medium Error."
            ::= { lun 2 }


        -- 1.3.6.1.4.1.2011.2.91.10.2.1.1.15.11.81
        theLUNLBAHasWarningMediumError NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "LUN Has A Medium Error."
            ::= { lun 81 }


        -- 1.3.6.1.4.1.2011.2.91.10.2.1.1.15.11.80
        theLUNLBAHasCriticalMediumError NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "LUN Has A Medium Error."
            ::= { lun 80 }


        -- 1.3.6.1.4.1.2011.2.91.10.2.1.1.15.11.269
        snapshotLUNIsFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Snapshot LUN Is Faulty."
            ::= { lun 269 }


        -- 1.3.6.1.4.1.2011.2.91.10.2.1.1.15.11.101
        externalLUNFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "External LUN Faulty."
            ::= { lun 101 }


        -- 1.3.6.1.4.1.2011.2.91.10.2.1.1.15.11.99
        externalLUNToOnlyOneController NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "External LUN Has Links To Only One Controller."
            ::= { lun 99 }


        -- 1.3.6.1.4.1.2011.2.91.10.2.1.1.15.11.264
        remoteLinkExceedUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of The Connected Remote Links Has Exceeded The Upper Limit ."
            ::= { lun 264 }


        -- 1.3.6.1.4.1.2011.2.91.10.2.1.1.15.11.265
        remoteArrayExceedUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of The Connected Remote Arrays Has Exceeded The Upper Limit."
            ::= { lun 265 }


        -- 1.3.6.1.4.1.2011.2.91.10.2.1.1.15.11.82
        incompatibleArrayConnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Incompatible Heterogeneous Array Connected To The System."
            ::= { lun 82 }


        -- 1.3.6.1.4.1.2011.2.91.10.2.1.1.15.11.270
        theLUNIsFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "LUN Is Faulty."
            ::= { lun 270 }


        -- 1.3.6.1.4.1.2011.2.91.10.2.1.1.15.11.98
        iscsiLinkFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "ISCSI Link Of Heterogeneous Array Faulty."
            ::= { lun 98 }


        -- 1.3.6.1.4.1.2011.2.91.10.2.1.1.15.11.97
        fcLinkFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "FC Link Of Heterogeneous Array Faulty."
            ::= { lun 97 }


        -- 1.3.6.1.4.1.2011.2.91.10.2.1.1.15.11.96
        iscsiLinkDisconnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "ISCSI Link Of Heterogeneous Array Disconnected."
            ::= { lun 96 }


        -- 1.3.6.1.4.1.2011.2.91.10.2.1.1.15.11.93
        fcLinkDisconnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "FC Link Of Heterogeneous Array Disconnected."
            ::= { lun 93 }


        -- 1.3.6.1.4.1.2011.2.91.10.2.1.1.15.11.1
        theLUNIsFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "LUN Is Faulty."
            ::= { lun 1 }


        -- 1.3.6.1.4.1.2011.2.91.10.2.1.1.15.11.61
        snapshotLUNIsFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Snapshot LUN Is Faulty."
            ::= { lun 61 }


        -- 1.3.6.1.4.1.2011.2.91.10.2.1.1.15.21
        host OBJECT IDENTIFIER ::= { storage 21 }


        -- 1.3.6.1.4.1.2011.2.91.10.2.1.1.15.21.25
        noRedundantConnectionToHost NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Host Is Not Redundantly Connected To Storage Arrays."
            ::= { host 25 }


        -- 1.3.6.1.4.1.2011.2.91.10.2.1.1.15.21.26
        aLinkToHostIsDown NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Link Between A Host And Storage Array Is Down."
            ::= { host 26 }


        -- 1.3.6.1.4.1.2011.2.91.10.2.1.1.15.21.29
        ultrapathIncompatibleWithStorage NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Ultrapath Incompatible With Storage Array Software."
            ::= { host 29 }


        -- 1.3.6.1.4.1.2011.2.91.10.2.1.1.15.23
        power OBJECT IDENTIFIER ::= { storage 23 }


        -- 1.3.6.1.4.1.2011.2.91.10.2.1.1.15.23.25
        powerModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Power Module Is Faulty."
            ::= { power 25 }


        -- 1.3.6.1.4.1.2011.2.91.10.2.1.1.15.23.5
        powerModuleInputIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Power Module Input Is Abnormal."
            ::= { power 5 }


        -- 1.3.6.1.4.1.2011.2.91.10.2.1.1.15.23.21
        powerModulesTypesDifferent NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Power Modules Of Different Types Are Used In A Disk Enclosure."
            ::= { power 21 }


        -- 1.3.6.1.4.1.2011.2.91.10.2.1.1.15.23.22
        diskEnclHasNoRePowerModule NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "A Disk Enclosure Does Not Have A Redundant Power Module."
            ::= { power 22 }


        -- 1.3.6.1.4.1.2011.2.91.10.2.1.1.15.23.24
        powerModuleIsIncompatible NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Power Module Type Is Mismatched."
            ::= { power 24 }


        -- 1.3.6.1.4.1.2011.2.91.10.2.1.1.15.23.23
        failedToMonitorAPowerModule NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The System Failed To Monitor A Power Module."
            ::= { power 23 }


        -- 1.3.6.1.4.1.2011.2.91.10.2.1.1.15.23.2
        powerModuleIsRemoved NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Power Module Is Removed."
            ::= { power 2 }


        -- 1.3.6.1.4.1.2011.2.91.10.2.1.1.15.23.3
        powerModuleFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Power Module Is Faulty."
            ::= { power 3 }


        -- 1.3.6.1.4.1.2011.2.91.10.2.1.1.15.23.20
        powerModuleHasNoInput NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Power Module Has No Input."
            ::= { power 20 }


        -- 1.3.6.1.4.1.2011.2.91.10.2.1.1.15.23.4
        powerModuleTempExceedsLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Power Module Temperature Exceeds The Upper Limit."
            ::= { power 4 }


        -- 1.3.6.1.4.1.2011.2.91.10.2.1.1.15.27
        snapshot OBJECT IDENTIFIER ::= { storage 27 }


        -- 1.3.6.1.4.1.2011.2.91.10.2.1.1.15.27.1
        snapshotStopAbnormally NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Snapshot Stops Abnormally."
            ::= { snapshot 1 }


        -- 1.3.6.1.4.1.2011.2.91.10.2.1.1.15.27.2
        snapshotUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Snapshot Unavailable."
            ::= { snapshot 2 }


        -- 1.3.6.1.4.1.2011.2.91.10.2.1.1.15.27.3
        failedToDisableTheSnapshot NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Disable The Snapshot."
            ::= { snapshot 3 }


        -- 1.3.6.1.4.1.2011.2.91.10.2.1.1.15.40
        filesystem OBJECT IDENTIFIER ::= { storage 40 }


        -- 1.3.6.1.4.1.2011.2.91.10.2.1.1.15.40.289
        fsObjectIsIsolated NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "An Object In File System Is Isolated."
            ::= { filesystem 289 }


        -- 1.3.6.1.4.1.2011.2.91.10.2.1.1.15.40.288
        fsRemainCapacityIsInsufficient NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Remaining Capacity In A File System Is Insufficient."
            ::= { filesystem 288 }


        -- 1.3.6.1.4.1.2011.2.91.10.2.1.1.15.40.290
        fileSystemExistMediumError NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Medium Errors In The File System."
            ::= { filesystem 290 }


        -- 1.3.6.1.4.1.2011.2.91.10.2.1.1.15.40.291
        fileOrDirExistMediumError NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Medium Errors In The File Or The Directory."
            ::= { filesystem 291 }


        -- 1.3.6.1.4.1.2011.2.91.10.2.1.1.15.40.287
        openedFilesNumAboutToExceedThres NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Opened Files On A Controller Is About To  Exceed The Upper Limit."
            ::= { filesystem 287 }


        -- 1.3.6.1.4.1.2011.2.91.10.2.1.1.15.40.282
        filesNumAboutToExceedThreshold NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Files In A File System Is About To Exceed The Upper Limit."
            ::= { filesystem 282 }


        -- 1.3.6.1.4.1.2011.2.91.10.2.1.1.15.40.284
        filesNumExceedLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Files In A File System Has Reached Or Exceeded The Upper Limit."
            ::= { filesystem 284 }


        -- 1.3.6.1.4.1.2011.2.91.10.2.1.1.15.40.286
        openedFilesNumExceedLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Opened Files On A Controller Has Reached Or Exceeded The Upper Limit."
            ::= { filesystem 286 }


        -- 1.3.6.1.4.1.2011.2.91.10.2.1.1.15.40.274
        filesNumAboutToExceedLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Files In A File System Is About To Exceed The Upper Limit."
            ::= { filesystem 274 }


        -- 1.3.6.1.4.1.2011.2.91.10.2.1.1.15.40.275
        dirFilesNumAboutToExceedLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Files In A Directory Of A File System Is About To Exceed The Upper Limit."
            ::= { filesystem 275 }


        -- 1.3.6.1.4.1.2011.2.91.10.2.1.1.15.40.278
        filesNumReachedOrExceededLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Files In A File System Has Reached Or Exceeded The Upper Limit."
            ::= { filesystem 278 }


        -- 1.3.6.1.4.1.2011.2.91.10.2.1.1.15.40.279
        dirFilesNumExceededLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Files In A Directory Of A File System Has Reached Or Exceeded The Upper Limit."
            ::= { filesystem 279 }


        -- 1.3.6.1.4.1.2011.2.91.10.2.1.1.15.40.280
        openedFilesNumExceededLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Opened Files On A Controller Has Reached Or Exceeded The Upper Limit."
            ::= { filesystem 280 }


        -- 1.3.6.1.4.1.2011.2.91.10.2.1.1.15.40.285
        subFilesNumToExceedLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Files Under A Directory Of A File System Has Reached Or Exceeded The Upper Limit."
            ::= { filesystem 285 }


        -- 1.3.6.1.4.1.2011.2.91.10.2.1.1.15.40.283
        subFilesNumAboutToExceedLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Files Under A Directory Of A File System Is About To Exceed The Upper Limit."
            ::= { filesystem 283 }


        -- 1.3.6.1.4.1.2011.2.91.10.2.1.1.15.40.116
        fileSystemMetadataIsDamaged NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "File System Metadata Corrupted."
            ::= { filesystem 116 }


        -- 1.3.6.1.4.1.2011.2.91.10.2.1.1.15.40.118
        fileOrDirDamagedInFs NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "File Or Directory Corrupted."
            ::= { filesystem 118 }


        -- 1.3.6.1.4.1.2011.2.91.10.2.1.1.15.40.69
        fileSystemIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "File System Is Faulty."
            ::= { filesystem 69 }


        -- 1.3.6.1.4.1.2011.2.91.10.2.1.1.15.40.117
        writeProtectionIsEnabledForFS NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "File System Under Write Protection."
            ::= { filesystem 117 }


        -- 1.3.6.1.4.1.2011.2.91.10.2.1.1.15.49
        event OBJECT IDENTIFIER ::= { storage 49 }


        -- 1.3.6.1.4.1.2011.2.91.10.2.1.1.15.49.4
        eventAmountReachUpLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Space That Stores Event Logs Is To Be Used Up."
            ::= { event 4 }


        -- 1.3.6.1.4.1.2011.2.91.10.2.1.1.15.201
        system OBJECT IDENTIFIER ::= { storage 201 }


        -- 1.3.6.1.4.1.2011.2.91.10.2.1.1.15.201.21
        controllerWriteCacheIsDisabled NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Controller Write Cache Is Disabled."
            ::= { system 21 }


        -- 1.3.6.1.4.1.2011.2.91.10.2.1.1.15.201.335
        dnsIsUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Management DNS Server Is Unavailable."
            ::= { system 335 }


        -- 1.3.6.1.4.1.2011.2.91.10.2.1.1.15.201.317
        ipaddrConflict NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "IP Address Conflict."
            ::= { system 317 }


        -- 1.3.6.1.4.1.2011.2.91.10.2.1.1.15.201.86
        onlyOneClusterLinkIsAvailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Only One Cluster Link Is Available."
            ::= { system 86 }


        -- 1.3.6.1.4.1.2011.2.91.10.2.1.1.15.201.6
        systemEnterSafeMode NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The System Has Entered Safe Mode."
            ::= { system 6 }


        -- 1.3.6.1.4.1.2011.2.91.10.2.1.1.15.202
        user OBJECT IDENTIFIER ::= { storage 202 }


        -- 1.3.6.1.4.1.2011.2.91.10.2.1.1.15.202.8
        userInfoNeedReview NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Super Administrator Needs To Review User Account Information."
            ::= { user 8 }


        -- 1.3.6.1.4.1.2011.2.91.10.2.1.1.15.202.15
        passwdOfUserHasExpired NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Password Of The User Has Expired."
            ::= { user 15 }


        -- 1.3.6.1.4.1.2011.2.91.10.2.1.1.15.202.14
        passwdOfUserIsAboutToExpire NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Password Of The User Is About To Expire."
            ::= { user 14 }


        -- 1.3.6.1.4.1.2011.2.91.10.2.1.1.15.202.17
        passwdOfUserHasExpired NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Password Of The User Has Expired."
            ::= { user 17 }


        -- 1.3.6.1.4.1.2011.2.91.10.2.1.1.15.202.16
        passwdOfUserIsAboutToExpire NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Password Of The User Is About To Expire ."
            ::= { user 16 }


        -- 1.3.6.1.4.1.2011.2.91.10.2.1.1.15.206
        enclosure OBJECT IDENTIFIER ::= { storage 206 }


        -- 1.3.6.1.4.1.2011.2.91.10.2.1.1.15.206.49
        enclosureIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Faults Occurred On An Enclosure."
            ::= { enclosure 49 }


        -- 1.3.6.1.4.1.2011.2.91.10.2.1.1.15.206.46
        failedToMonitorTheRearPanel NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The System Failed To Monitor The Rear Panel Of The Enclosure."
            ::= { enclosure 46 }


        -- 1.3.6.1.4.1.2011.2.91.10.2.1.1.15.206.43
        highDensityAreMixConnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "From An Expansion Port, Disk Enclosures And High-Density Disk Enclosures Are Mix-Connected."
            ::= { enclosure 43 }


        -- 1.3.6.1.4.1.2011.2.91.10.2.1.1.15.206.23
        numOfEnclOnExpPortExceedsLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Number Of Disk Enclosures Connected To An Expansion Port Exceeds The System Specification."
            ::= { enclosure 23 }


        -- 1.3.6.1.4.1.2011.2.91.10.2.1.1.15.206.4
        failedToIdentifyEnclosure NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Identify A Controller Enclosure Or Disk Enclosure."
            ::= { enclosure 4 }


        -- 1.3.6.1.4.1.2011.2.91.10.2.1.1.15.206.50
        enclosureIsUnrecognizable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Identify A Controller Enclosure Or Disk Enclosure."
            ::= { enclosure 50 }


        -- 1.3.6.1.4.1.2011.2.91.10.2.1.1.15.206.51
        enclosureCablingIsIncorrect NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Incorrect Configuration Disk Enclosure Cabling."
            ::= { enclosure 51 }


        -- 1.3.6.1.4.1.2011.2.91.10.2.1.1.15.206.20
        faultsOccurredOnEnclosure NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Faults Occurred On An Enclosure."
            ::= { enclosure 20 }


        -- 1.3.6.1.4.1.2011.2.91.10.2.1.1.15.206.5
        diskEnclTempExceedsUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Enclosure Temperature Exceeds The Upper Limit."
            ::= { enclosure 5 }


        -- 1.3.6.1.4.1.2011.2.91.10.2.1.1.15.206.7
        diskEnclTempIsBelowLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Engine Or Disk Enclosure Temperature Is Below The Lower Limit."
            ::= { enclosure 7 }


        -- 1.3.6.1.4.1.2011.2.91.10.2.1.1.15.206.8
        ctrlEnclTempExceedsUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Controller Enclosure Temperature Exceeds The Upper Limit."
            ::= { enclosure 8 }


        -- 1.3.6.1.4.1.2011.2.91.10.2.1.1.15.206.9
        ctrlEnclTempIsFarBeyondUpLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Controller Enclosure Temperature Is Far Beyond The Upper Limit."
            ::= { enclosure 9 }


        -- 1.3.6.1.4.1.2011.2.91.10.2.1.1.15.206.10
        diskEnclTempIsFarBeyondUpLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Enclosure Temperature Is Far Beyond The Upper Limit."
            ::= { enclosure 10 }


        -- 1.3.6.1.4.1.2011.2.91.10.2.1.1.15.206.52
        enclSpeedSmallerThanLoopSpeed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Disk Enclosure Speed Does Not Reach The Maximum Loop Speed."
            ::= { enclosure 52 }


        -- 1.3.6.1.4.1.2011.2.91.10.2.1.1.15.206.15
        anUnsupportedExpEnclConnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Controller Is Connected To An Unsupported Disk Enclosure."
            ::= { enclosure 15 }


        -- 1.3.6.1.4.1.2011.2.91.10.2.1.1.15.206.42
        diskEnclosureIsSingleLink NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Enclosure Is Working In Single Link State."
            ::= { enclosure 42 }


        -- 1.3.6.1.4.1.2011.2.91.10.2.1.1.15.206.1
        failedToMonitorADiskEnclosure NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Monitor A Disk Enclosure."
            ::= { enclosure 1 }


        -- 1.3.6.1.4.1.2011.2.91.10.2.1.1.15.207
        controller OBJECT IDENTIFIER ::= { storage 207 }


        -- 1.3.6.1.4.1.2011.2.91.10.2.1.1.15.207.20
        monitorControllerFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Monitor The Controller."
            ::= { controller 20 }


        -- 1.3.6.1.4.1.2011.2.91.10.2.1.1.15.207.5
        abnormalCommunicateBetweenCtrls NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Abnormal Communication Between Controllers."
            ::= { controller 5 }


        -- 1.3.6.1.4.1.2011.2.91.10.2.1.1.15.207.74
        controllerCannotBeMonitored NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Some Statuses Of A Controller Cannot Be Monitored."
            ::= { controller 74 }


        -- 1.3.6.1.4.1.2011.2.91.10.2.1.1.15.207.54
        controllerServicesAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Controller Services Are Abnormal."
            ::= { controller 54 }


        -- 1.3.6.1.4.1.2011.2.91.10.2.1.1.15.207.95
        controllerIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Controller Is Faulty."
            ::= { controller 95 }


        -- 1.3.6.1.4.1.2011.2.91.10.2.1.1.15.207.108
        bbuIsFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The BBU Module Of The Controller Is About To Expire."
            ::= { controller 108 }


        -- 1.3.6.1.4.1.2011.2.91.10.2.1.1.15.207.97
        ctrlAndMgtCommunicateLinkFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Communication Link Fault Among The Controller And Management Modules."
            ::= { controller 97 }


        -- 1.3.6.1.4.1.2011.2.91.10.2.1.1.15.207.104
        controllerIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Controller Is Faulty."
            ::= { controller 104 }


        -- 1.3.6.1.4.1.2011.2.91.10.2.1.1.15.207.105
        controllerIsOffline NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Controller Is Offline."
            ::= { controller 105 }


        -- 1.3.6.1.4.1.2011.2.91.10.2.1.1.15.207.23
        portIsIncorrectlyConnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Incorrect Connection Between A Controller Port And A Switch Port."
            ::= { controller 23 }


        -- 1.3.6.1.4.1.2011.2.91.10.2.1.1.15.207.6
        controllerIsRemoved NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Controller Is Removed."
            ::= { controller 6 }


        -- 1.3.6.1.4.1.2011.2.91.10.2.1.1.15.207.57
        theCoinBatteryIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Coin Battery Is Faulty."
            ::= { controller 57 }


        -- 1.3.6.1.4.1.2011.2.91.10.2.1.1.15.207.2
        ftpServiceIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The FTP Service Is Abnormal."
            ::= { controller 2 }


        -- 1.3.6.1.4.1.2011.2.91.10.2.1.1.15.207.11
        processCpuUsageIsTooHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Process CPU Usage Is Too High."
            ::= { controller 11 }


        -- 1.3.6.1.4.1.2011.2.91.10.2.1.1.15.207.1
        sshServiceIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The SSH Service Is Abnormal."
            ::= { controller 1 }


        -- 1.3.6.1.4.1.2011.2.91.10.2.1.1.15.207.98
        bbuIsFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Backup Power Module Of The Controller Is About To Expire ."
            ::= { controller 98 }


        -- 1.3.6.1.4.1.2011.2.91.10.2.1.1.15.207.9
        ntpSynchronizationIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "NTP Time Synchronization Is Abnormal."
            ::= { controller 9 }


        -- 1.3.6.1.4.1.2011.2.91.10.2.1.1.15.207.8
        excessiveFilesExistInADirectory NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Excessive Files Exist In A Directory."
            ::= { controller 8 }


        -- 1.3.6.1.4.1.2011.2.91.10.2.1.1.15.207.12
        processMemoryUsageIsTooHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Process Memory Usage Is Too High."
            ::= { controller 12 }


        -- 1.3.6.1.4.1.2011.2.91.10.2.1.1.15.207.7
        directoryIsOversized NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "A Directory Is Oversized."
            ::= { controller 7 }


        -- 1.3.6.1.4.1.2011.2.91.10.2.1.1.15.207.92
        openedFilesNumAboutToExceedLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Opened Files On A Controller Is About To Exceed The Upper Limit."
            ::= { controller 92 }


        -- 1.3.6.1.4.1.2011.2.91.10.2.1.1.15.207.94
        remainAvailableMemoryTooLow NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Remaining Available Memory Is Too Low."
            ::= { controller 94 }


        -- 1.3.6.1.4.1.2011.2.91.10.2.1.1.15.207.13
        cpuUsageTooHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "CPU Usage Is Too High."
            ::= { controller 13 }


        -- 1.3.6.1.4.1.2011.2.91.10.2.1.1.15.207.14
        memoryUsageTooHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Memory Usage Is Too High."
            ::= { controller 14 }


        -- 1.3.6.1.4.1.2011.2.91.10.2.1.1.15.207.100
        firmwareVersionIncompatible NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Firmware Version Of The Backup Power Module Of The Controller Incompatible With The Storage Array Software."
            ::= { controller 100 }


        -- 1.3.6.1.4.1.2011.2.91.10.2.1.1.15.207.10
        controllerNetStackIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Network Protocol Stack Of A Controller Is Abnormal."
            ::= { controller 10 }


        -- 1.3.6.1.4.1.2011.2.91.10.2.1.1.15.207.99
        bbuTempHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Temperature Of The Backup Power Module Of The Controller Exceeds The Upper Limit ."
            ::= { controller 99 }


        -- 1.3.6.1.4.1.2011.2.91.10.2.1.1.15.207.93
        cpuUsageIsTooHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "CPU Usage Is Too High."
            ::= { controller 93 }


        -- 1.3.6.1.4.1.2011.2.91.10.2.1.1.15.207.21
        monitorControllersFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Monitor Controllers Enclosure."
            ::= { controller 21 }


        -- 1.3.6.1.4.1.2011.2.91.10.2.1.1.15.207.96
        memoryCapacityIsNotSupported NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Incorrect Controller Memory Capacity."
            ::= { controller 96 }


        -- 1.3.6.1.4.1.2011.2.91.10.2.1.1.15.208
        expandboardmodule OBJECT IDENTIFIER ::= { storage 208 }


        -- 1.3.6.1.4.1.2011.2.91.10.2.1.1.15.208.24
        expansionModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Module Is Faulty."
            ::= { expandboardmodule 24 }


        -- 1.3.6.1.4.1.2011.2.91.10.2.1.1.15.208.23
        syncExpansionFirmwareFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Synchronize The Firmware Version Of An Expansion Module."
            ::= { expandboardmodule 23 }


        -- 1.3.6.1.4.1.2011.2.91.10.2.1.1.15.208.57
        sasExpansionModuleIncompatible NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Shared SAS  Expansion Module Firmware Is Incompatible With Storage Array Software."
            ::= { expandboardmodule 57 }


        -- 1.3.6.1.4.1.2011.2.91.10.2.1.1.15.208.41
        expansionModuleIncompatible NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Module Firmware Is Incompatible With Storage Array Software."
            ::= { expandboardmodule 41 }


        -- 1.3.6.1.4.1.2011.2.91.10.2.1.1.15.208.22
        expansionCableLinkError NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Module Is Incorrectly Cabled."
            ::= { expandboardmodule 22 }


        -- 1.3.6.1.4.1.2011.2.91.10.2.1.1.15.208.1
        expansionModuleIsRemoved NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Module Is Removed."
            ::= { expandboardmodule 1 }


        -- 1.3.6.1.4.1.2011.2.91.10.2.1.1.15.208.2
        expansionModuleIsNotInserted NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Module Is Not Inserted."
            ::= { expandboardmodule 2 }


        -- 1.3.6.1.4.1.2011.2.91.10.2.1.1.15.208.3
        expansionModuleFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Expansion Module Is Faulty."
            ::= { expandboardmodule 3 }


        -- 1.3.6.1.4.1.2011.2.91.10.2.1.1.15.208.20
        abnormalCommBetweenExpModules NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Abnormal Communication Between Expansion Modules."
            ::= { expandboardmodule 20 }


        -- 1.3.6.1.4.1.2011.2.91.10.2.1.1.15.209
        interfacemodule OBJECT IDENTIFIER ::= { storage 209 }


        -- 1.3.6.1.4.1.2011.2.91.10.2.1.1.15.209.5
        interfaceModuleIsRemoved NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Interface Module Is Removed."
            ::= { interfacemodule 5 }


        -- 1.3.6.1.4.1.2011.2.91.10.2.1.1.15.209.8
        interfaceModuleIsUnrecognizable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Interface Module Is Unrecognizable."
            ::= { interfacemodule 8 }


        -- 1.3.6.1.4.1.2011.2.91.10.2.1.1.15.209.10
        incorrectRemovalInterfaceModule NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Incorrect Removal Of Interface Module."
            ::= { interfacemodule 10 }


        -- 1.3.6.1.4.1.2011.2.91.10.2.1.1.15.209.9
        interfaceModuleTempExceedsLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Interface Module Temperature Exceeds The Upper Limit."
            ::= { interfacemodule 9 }


        -- 1.3.6.1.4.1.2011.2.91.10.2.1.1.15.209.30
        monitorInterfaceModuleFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Interface Module Cannot Be Monitored."
            ::= { interfacemodule 30 }


        -- 1.3.6.1.4.1.2011.2.91.10.2.1.1.15.209.66
        failedToMonitorTheInternalLink NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Monitor The Internal Link Of An Interface Module."
            ::= { interfacemodule 66 }


        -- 1.3.6.1.4.1.2011.2.91.10.2.1.1.15.209.62
        internalLinkofIntfModIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Internal Link Of Interface Module Is Faulty."
            ::= { interfacemodule 62 }


        -- 1.3.6.1.4.1.2011.2.91.10.2.1.1.15.209.65
        faultyInterfaceModuleComponent NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Faulty Interface Module Component."
            ::= { interfacemodule 65 }


        -- 1.3.6.1.4.1.2011.2.91.10.2.1.1.15.209.50
        managementModuleIncompatible NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Management Module Firmware Is Incompatible With Storage Array Software."
            ::= { interfacemodule 50 }


        -- 1.3.6.1.4.1.2011.2.91.10.2.1.1.15.209.35
        communicationIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Communication Link Fault Among Management Modules."
            ::= { interfacemodule 35 }


        -- 1.3.6.1.4.1.2011.2.91.10.2.1.1.15.209.40
        interfaceModuleIncompatible NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Interface Module Firmware Is Incompatible With Storage Array Software."
            ::= { interfacemodule 40 }


        -- 1.3.6.1.4.1.2011.2.91.10.2.1.1.15.209.60
        managementModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Management Module Is Faulty."
            ::= { interfacemodule 60 }


        -- 1.3.6.1.4.1.2011.2.91.10.2.1.1.15.209.59
        managementModuleIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Management Module Is Abnormal."
            ::= { interfacemodule 59 }


        -- 1.3.6.1.4.1.2011.2.91.10.2.1.1.15.209.56
        pcieChannelIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "PCIe Channel Between An Interface Module And A Controller Is Abnormal."
            ::= { interfacemodule 56 }


        -- 1.3.6.1.4.1.2011.2.91.10.2.1.1.15.209.19
        someStatusMonitoringFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Some Statuses Of A Management Module Cannot Be Monitored."
            ::= { interfacemodule 19 }


        -- 1.3.6.1.4.1.2011.2.91.10.2.1.1.15.209.61
        interfaceModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Interface Module Is Faulty."
            ::= { interfacemodule 61 }


        -- 1.3.6.1.4.1.2011.2.91.10.2.1.1.15.209.17
        pcieChannelIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The PCIe Channel Between An Interface Module And A Controller Is Abnormal."
            ::= { interfacemodule 17 }


        -- 1.3.6.1.4.1.2011.2.91.10.2.1.1.15.209.18
        slotDoesNotMatchInterfaceModule NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Interface Module Is Not Supported Or The Interface Module Is Inserted Into An Incorrect Slot ."
            ::= { interfacemodule 18 }


        -- 1.3.6.1.4.1.2011.2.91.10.2.1.1.15.210
        backuppowermodule OBJECT IDENTIFIER ::= { storage 210 }


        -- 1.3.6.1.4.1.2011.2.91.10.2.1.1.15.210.28
        bbuModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "BBU Module Is Faulty."
            ::= { backuppowermodule 28 }


        -- 1.3.6.1.4.1.2011.2.91.10.2.1.1.15.210.29
        bbuModuleLifeIsOvertime NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "BBU Module Reaches Its Expiration Date Or Is Aging."
            ::= { backuppowermodule 29 }


        -- 1.3.6.1.4.1.2011.2.91.10.2.1.1.15.210.30
        bbuModuleIsAboutToExpire NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "BBU Module Is About To Expire."
            ::= { backuppowermodule 30 }


        -- 1.3.6.1.4.1.2011.2.91.10.2.1.1.15.210.5
        bbuModuleTempExceedsLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "BBU Module Temperature Exceeds The Upper Limit."
            ::= { backuppowermodule 5 }


        -- 1.3.6.1.4.1.2011.2.91.10.2.1.1.15.210.20
        failedToMonitorABBUModule NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "BBU Module Cannot Be Monitored."
            ::= { backuppowermodule 20 }


        -- 1.3.6.1.4.1.2011.2.91.10.2.1.1.15.210.39
        bbuFirmwareIncompatible NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "BBU Firmware Is Incompatible With Storage Array Software."
            ::= { backuppowermodule 39 }


        -- 1.3.6.1.4.1.2011.2.91.10.2.1.1.15.210.4
        bbuModuleIsRemoved NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "BBU Module Is Removed."
            ::= { backuppowermodule 4 }


        -- 1.3.6.1.4.1.2011.2.91.10.2.1.1.15.210.25
        bbuModuleTypeDoesNotComply NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The BBU Type Does Not Comply With The System Specification."
            ::= { backuppowermodule 25 }


        -- 1.3.6.1.4.1.2011.2.91.10.2.1.1.15.210.27
        bbuModuleTempIsBelowLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "BBU Module Temperature Is Below The Lower Limit."
            ::= { backuppowermodule 27 }


        -- 1.3.6.1.4.1.2011.2.91.10.2.1.1.15.211
        fanmodule OBJECT IDENTIFIER ::= { storage 211 }


        -- 1.3.6.1.4.1.2011.2.91.10.2.1.1.15.211.3
        fanModuleIsRemoved NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Fan Module Is Removed."
            ::= { fanmodule 3 }


        -- 1.3.6.1.4.1.2011.2.91.10.2.1.1.15.211.21
        fanModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Fan Module Is Faulty."
            ::= { fanmodule 21 }


        -- 1.3.6.1.4.1.2011.2.91.10.2.1.1.15.216
        storagepool OBJECT IDENTIFIER ::= { storage 216 }


        -- 1.3.6.1.4.1.2011.2.91.10.2.1.1.15.216.291
        ckgMetadataHasFaults NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "CKG Metadata Of The Storage Pool Has Faults."
            ::= { storagepool 291 }


        -- 1.3.6.1.4.1.2011.2.91.10.2.1.1.15.216.86
        extentMetadataOfVolumeHasFaults NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Extent Metadata Of A Volume Has Faults."
            ::= { storagepool 86 }


        -- 1.3.6.1.4.1.2011.2.91.10.2.1.1.15.216.289
        usedCapacityReachAlarmThreshold NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Used Protection Capacity Reaches The Alarm Threshold."
            ::= { storagepool 289 }


        -- 1.3.6.1.4.1.2011.2.91.10.2.1.1.15.216.43
        availableSpaceInsufficient NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Available Space In The Storage Pool Is Insufficient."
            ::= { storagepool 43 }


        -- 1.3.6.1.4.1.2011.2.91.10.2.1.1.15.216.290
        smartTierUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SmartTier Unavailable."
            ::= { storagepool 290 }


        -- 1.3.6.1.4.1.2011.2.91.10.2.1.1.15.216.44
        availableSpaceUsedUp NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "No Available Space In The Storage Pool."
            ::= { storagepool 44 }


        -- 1.3.6.1.4.1.2011.2.91.10.2.1.1.15.216.288
        storagePoolCapacityShouldUseUp NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Storage Pool Capacity Is About To Be Used Up."
            ::= { storagepool 288 }


        -- 1.3.6.1.4.1.2011.2.91.10.2.1.1.15.216.281
        storagePoolCapacityNotEnough NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Storage Pool Remaining Capacity Is Insufficient."
            ::= { storagepool 281 }


        -- 1.3.6.1.4.1.2011.2.91.10.2.1.1.15.218
        smartcachepool OBJECT IDENTIFIER ::= { storage 218 }


        -- 1.3.6.1.4.1.2011.2.91.10.2.1.1.15.218.2
        smartCacheDiskIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "A Member Disk Of A SmartCache Pool Gets A Fault."
            ::= { smartcachepool 2 }


        -- 1.3.6.1.4.1.2011.2.91.10.2.1.1.15.219
        luncopy OBJECT IDENTIFIER ::= { storage 219 }


        -- 1.3.6.1.4.1.2011.2.91.10.2.1.1.15.219.2
        almCpyFullCopyFail NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Full LUN Copy Is Faulty."
            ::= { luncopy 2 }


        -- 1.3.6.1.4.1.2011.2.91.10.2.1.1.15.220
        clone OBJECT IDENTIFIER ::= { storage 220 }


        -- 1.3.6.1.4.1.2011.2.91.10.2.1.1.15.220.1
        almCLnPairInterrupt NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Clone Pair Is Abnormally Interrupted."
            ::= { clone 1 }


        -- 1.3.6.1.4.1.2011.2.91.10.2.1.1.15.220.3
        almClnPairFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Clone Pair Is Unavailable."
            ::= { clone 3 }


        -- 1.3.6.1.4.1.2011.2.91.10.2.1.1.15.221
        consistentgroup OBJECT IDENTIFIER ::= { storage 221 }


        -- 1.3.6.1.4.1.2011.2.91.10.2.1.1.15.221.4
        remoteReplicationCGAutoSplit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Remote Replication Consistency Group Is Automatically Split."
            ::= { consistentgroup 4 }


        -- 1.3.6.1.4.1.2011.2.91.10.2.1.1.15.221.2
        remoteReplicationCGIsUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Remote Replication Consistency Group Is Unavailable."
            ::= { consistentgroup 2 }


        -- 1.3.6.1.4.1.2011.2.91.10.2.1.1.15.221.1
        remoteReplicationCGIsInterrupted NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Remote Replication Consistency Group Is Disconnected."
            ::= { consistentgroup 1 }


        -- 1.3.6.1.4.1.2011.2.91.10.2.1.1.15.224
        remotedevice OBJECT IDENTIFIER ::= { storage 224 }


        -- 1.3.6.1.4.1.2011.2.91.10.2.1.1.15.224.20
        noBackupLinkForRep NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "No Backup Links Available."
            ::= { remotedevice 20 }


        -- 1.3.6.1.4.1.2011.2.91.10.2.1.1.15.224.1
        repLinkDown NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Replication Link Is Down."
            ::= { remotedevice 1 }


        -- 1.3.6.1.4.1.2011.2.91.10.2.1.1.15.232
        pciedataswitch OBJECT IDENTIFIER ::= { storage 232 }


        -- 1.3.6.1.4.1.2011.2.91.10.2.1.1.15.232.24
        switchFanModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Fan Module Is Faulty."
            ::= { pciedataswitch 24 }


        -- 1.3.6.1.4.1.2011.2.91.10.2.1.1.15.232.1
        powerSupplyOfSwitchIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Power Supply Of The Switch Is Faulty."
            ::= { pciedataswitch 1 }


        -- 1.3.6.1.4.1.2011.2.91.10.2.1.1.15.232.26
        switchPowerInputIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Input To The Switch Power Module Is Abnormal."
            ::= { pciedataswitch 26 }


        -- 1.3.6.1.4.1.2011.2.91.10.2.1.1.15.232.25
        switchFanModuleIsRemoved NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Fan Module Is Removed."
            ::= { pciedataswitch 25 }


        -- 1.3.6.1.4.1.2011.2.91.10.2.1.1.15.232.36
        negoRateSmallerThanTheMax NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Port Negotiated Rate Is Smaller Than The Allowed Maximum Rate."
            ::= { pciedataswitch 36 }


        -- 1.3.6.1.4.1.2011.2.91.10.2.1.1.15.232.34
        switchPortOpticalModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Port Optical Module Is Faulty."
            ::= { pciedataswitch 34 }


        -- 1.3.6.1.4.1.2011.2.91.10.2.1.1.15.232.43
        switchFailToMonitorPowModules NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Failed To Monitor Power Modules."
            ::= { pciedataswitch 43 }


        -- 1.3.6.1.4.1.2011.2.91.10.2.1.1.15.232.20
        switchIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Is Faulty."
            ::= { pciedataswitch 20 }


        -- 1.3.6.1.4.1.2011.2.91.10.2.1.1.15.232.22
        switchTempExceedsLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Temperature Exceeds The Upper Limit."
            ::= { pciedataswitch 22 }


        -- 1.3.6.1.4.1.2011.2.91.10.2.1.1.15.232.30
        switchManageNetworkPortIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Management Network Port Is Faulty."
            ::= { pciedataswitch 30 }


        -- 1.3.6.1.4.1.2011.2.91.10.2.1.1.15.232.27
        switchPowerModuleIsRemoved NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Power Module Is Removed."
            ::= { pciedataswitch 27 }


        -- 1.3.6.1.4.1.2011.2.91.10.2.1.1.15.232.21
        switchFailedToBeMonitored NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Failed To Be Monitored."
            ::= { pciedataswitch 21 }


        -- 1.3.6.1.4.1.2011.2.91.10.2.1.1.15.232.23
        switchTempIsBelowLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Temperature Is Below The Lower Limit."
            ::= { pciedataswitch 23 }


        -- 1.3.6.1.4.1.2011.2.91.10.2.1.1.15.232.31
        switchPortIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Port Is Faulty."
            ::= { pciedataswitch 31 }


        -- 1.3.6.1.4.1.2011.2.91.10.2.1.1.15.232.38
        linkToASwitchPortIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Link To A Switch Port Is Abnormal."
            ::= { pciedataswitch 38 }


        -- 1.3.6.1.4.1.2011.2.91.10.2.1.1.15.232.40
        dswEthPortIsDown NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Management Network Port Is Disconnected."
            ::= { pciedataswitch 40 }


        -- 1.3.6.1.4.1.2011.2.91.10.2.1.1.15.232.39
        failedToMonitorSwitchOpModule NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Switch Optical Module Cannot Be Monitored."
            ::= { pciedataswitch 39 }


        -- 1.3.6.1.4.1.2011.2.91.10.2.1.1.15.232.42
        switchFailToMonitorFanModules NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Switch Failed To Monitor Fan Modules."
            ::= { pciedataswitch 42 }


        -- 1.3.6.1.4.1.2011.2.91.10.2.1.1.15.234
        sfpopticaltransceiver OBJECT IDENTIFIER ::= { storage 234 }


        -- 1.3.6.1.4.1.2011.2.91.10.2.1.1.15.234.3
        portOpticalModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Port Optical Module Is Faulty."
            ::= { sfpopticaltransceiver 3 }


        -- 1.3.6.1.4.1.2011.2.91.10.2.1.1.15.234.5
        opticalModuleRateIsInconsistent NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Optical Module Rate Is Inconsistent With That Of Its Port."
            ::= { sfpopticaltransceiver 5 }


        -- 1.3.6.1.4.1.2011.2.91.10.2.1.1.15.234.24
        failedToMonitorOpOrEleModule NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The System Failed To Monitor An Optical Or Electrical Module."
            ::= { sfpopticaltransceiver 24 }


        -- 1.3.6.1.4.1.2011.2.91.10.2.1.1.15.234.20
        portLinkIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Abnormal Port Link."
            ::= { sfpopticaltransceiver 20 }


        -- 1.3.6.1.4.1.2011.2.91.10.2.1.1.15.234.21
        failedToMonitorAnOpticalModule NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Optical Module Cannot Be Monitored."
            ::= { sfpopticaltransceiver 21 }


        -- 1.3.6.1.4.1.2011.2.91.10.2.1.1.15.244
        license OBJECT IDENTIFIER ::= { storage 244 }


        -- 1.3.6.1.4.1.2011.2.91.10.2.1.1.15.244.1
        licenseIsAboutToExpire NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "License Is About To Expire."
            ::= { license 1 }


        -- 1.3.6.1.4.1.2011.2.91.10.2.1.1.15.244.2
        licenseHasExpired NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "License Has Expired."
            ::= { license 2 }


        -- 1.3.6.1.4.1.2011.2.91.10.2.1.1.15.244.6
        licenseIsInvalidWithStartDate NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Invalid License."
            ::= { license 6 }


        -- 1.3.6.1.4.1.2011.2.91.10.2.1.1.15.253
        lunmigrationtask OBJECT IDENTIFIER ::= { storage 253 }


        -- 1.3.6.1.4.1.2011.2.91.10.2.1.1.15.253.8
        almSmartMigrationErr NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SmartMigration Is Faulty."
            ::= { lunmigrationtask 8 }


        -- 1.3.6.1.4.1.2011.2.91.10.2.1.1.15.263
        replicationpair OBJECT IDENTIFIER ::= { storage 263 }


        -- 1.3.6.1.4.1.2011.2.91.10.2.1.1.15.263.58
        autoStartSynRemoteRepFails NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Remote Replication Failed To Synchronize Data Automatically."
            ::= { replicationpair 58 }


        -- 1.3.6.1.4.1.2011.2.91.10.2.1.1.15.263.56
        remoteReplicationIsInterrupted NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Remote Replication Is Interrupted."
            ::= { replicationpair 56 }


        -- 1.3.6.1.4.1.2011.2.91.10.2.1.1.15.263.57
        remoteReplicationIsInvalid NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Remote Replication Is Unavailable."
            ::= { replicationpair 57 }


        -- 1.3.6.1.4.1.2011.2.91.10.2.1.1.15.263.5
        autoStartSynRemoteRepCGFails NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Remote Replication Consistency Group Failed To Synchronize Data Automatically."
            ::= { replicationpair 5 }


        -- 1.3.6.1.4.1.2011.2.91.10.2.1.1.15.263.311
        remoteReplicationAutomaticSplit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Remote Replication Is Automatically Split."
            ::= { replicationpair 311 }


        -- 1.3.6.1.4.1.2011.2.91.10.2.1.1.15.263.274
        fsRemoteReplicationPairInvalid NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "A Remote Replication Is Unavailable."
            ::= { replicationpair 274 }


        -- 1.3.6.1.4.1.2011.2.91.10.2.1.1.15.263.275
        fsRemoteReplicationPairFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "A Remote Replication Is Abnormally Interrupted."
            ::= { replicationpair 275 }


        -- 1.3.6.1.4.1.2011.2.91.10.2.1.1.15.263.304
        fsRemoteReplicationAutoSyncFail NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "A Remote Replication Fails To Synchronize Data Automatically."
            ::= { replicationpair 304 }


        -- 1.3.6.1.4.1.2011.2.91.10.2.1.1.15.263.22
        failedRecoverRmReplication NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Recover The LUN Remote Replication Service At The Array End."
            ::= { replicationpair 22 }


        -- 1.3.6.1.4.1.2011.2.91.10.2.1.1.15.263.21
        addRemoteReplicationToCGFails NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Add Remote Replication To A Consistent Group."
            ::= { replicationpair 21 }


        -- 1.3.6.1.4.1.2011.2.91.10.2.1.1.15.266
        diskdomain OBJECT IDENTIFIER ::= { storage 266 }


        -- 1.3.6.1.4.1.2011.2.91.10.2.1.1.15.266.83
        diskDomainEnterSecureVideoState NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Domain Entering The SecureVideo State."
            ::= { diskdomain 83 }


        -- 1.3.6.1.4.1.2011.2.91.10.2.1.1.15.266.3
        diskDomainIsOffline NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Domain Is Offline."
            ::= { diskdomain 3 }


        -- 1.3.6.1.4.1.2011.2.91.10.2.1.1.15.266.2
        diskDomainFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Domain Is Faulty."
            ::= { diskdomain 2 }


        -- 1.3.6.1.4.1.2011.2.91.10.2.1.1.15.266.1
        diskDomainDegradation NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Disk Domain Is Degraded."
            ::= { diskdomain 1 }


        -- 1.3.6.1.4.1.2011.2.91.10.2.1.1.15.266.84
        backgroudTaskFailedToStart NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Background Task Of A Disk Domain Failed To Start."
            ::= { diskdomain 84 }


        -- 1.3.6.1.4.1.2011.2.91.10.2.1.1.15.266.6
        differentDiskType NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Inconsistent Disk Domain Disk Types."
            ::= { diskdomain 6 }


        -- 1.3.6.1.4.1.2011.2.91.10.2.1.1.15.266.5
        hotSpareCapacityInsufficient NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Hot Spare Capacity Of The Disk Domain Is Insufficient."
            ::= { diskdomain 5 }


        -- 1.3.6.1.4.1.2011.2.91.10.2.1.1.15.266.8
        diskIsRemovedFromDiskDomain NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "A Disk Is Removed From A Disk Domain."
            ::= { diskdomain 8 }


        -- 1.3.6.1.4.1.2011.2.91.10.2.1.1.15.266.32
        newDiskCapacityInsufficieny NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "A New Disk Fails To Be Added To The Disk Domain."
            ::= { diskdomain 32 }


        -- 1.3.6.1.4.1.2011.2.91.10.2.1.1.15.268
        cachepartition OBJECT IDENTIFIER ::= { storage 268 }


        -- 1.3.6.1.4.1.2011.2.91.10.2.1.1.15.268.11
        controllerWriteCacheDisabled NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Controller Write Cache Is Disabled."
            ::= { cachepartition 11 }


        -- 1.3.6.1.4.1.2011.2.91.10.2.1.1.15.268.12
        cachePartitionWriteCacheDisabled NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Write Cache For A Cache Partition Is Disabled."
            ::= { cachepartition 12 }


        -- 1.3.6.1.4.1.2011.2.91.10.2.1.1.15.269
        qos OBJECT IDENTIFIER ::= { storage 269 }


        -- 1.3.6.1.4.1.2011.2.91.10.2.1.1.15.269.67
        failReachSmartQoSObjective NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Reach The Control Objective Of SmartQoS."
            ::= { qos 67 }


        -- 1.3.6.1.4.1.2011.2.91.10.2.1.1.15.273
        smartcachepartition OBJECT IDENTIFIER ::= { storage 273 }


        -- 1.3.6.1.4.1.2011.2.91.10.2.1.1.15.273.1
        smartcacheIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SmartCache Function Is Unavailable."
            ::= { smartcachepartition 1 }


        -- 1.3.6.1.4.1.2011.2.91.10.2.1.1.15.285
        anti-virus OBJECT IDENTIFIER ::= { storage 285 }


        -- 1.3.6.1.4.1.2011.2.91.10.2.1.1.15.285.71
        antivirusServiceIsNotAvailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Antivirus Service Is Not Available."
            ::= { anti-virus 71 }


        -- 1.3.6.1.4.1.2011.2.91.10.2.1.1.15.285.68
        antivirusServerIsFault NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Antivirus Server Is Fault."
            ::= { anti-virus 68 }


        -- 1.3.6.1.4.1.2011.2.91.10.2.1.1.15.293
        hypervault OBJECT IDENTIFIER ::= { storage 293 }


        -- 1.3.6.1.4.1.2011.2.91.10.2.1.1.15.293.0
        hyperVaultJobCongestion NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "A HyperVault Job Is Congested."
            ::= { hypervault 0 }


        -- 1.3.6.1.4.1.2011.2.91.10.2.1.1.15.293.4
        hyperVaultScheduledTaskFailure NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "HyperVault Fails To Be Started As Scheduled."
            ::= { hypervault 4 }


        -- 1.3.6.1.4.1.2011.2.91.10.2.1.1.15.293.13
        hyperVaultCopiesReachUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of HyperVault Copies Reaches The Upper Limit ."
            ::= { hypervault 13 }


        -- 1.3.6.1.4.1.2011.2.91.10.2.1.1.15.293.2
        hyperVaultLinkIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Link To A Remote Device Is Down."
            ::= { hypervault 2 }


        -- 1.3.6.1.4.1.2011.2.91.10.2.1.1.15.293.3
        hyperVaultFileSystemFaults NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Owning File System Of A HyperVault Is Faulty."
            ::= { hypervault 3 }


        -- 1.3.6.1.4.1.2011.2.91.10.2.1.1.15.293.12
        hyperVaultPairInvalid NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Invalid HyperVault Pair."
            ::= { hypervault 12 }


        -- 1.3.6.1.4.1.2011.2.91.10.2.1.1.15.293.14
        hyperVaultInterruption NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "HyperVault Is Interrupted ."
            ::= { hypervault 14 }


        -- 1.3.6.1.4.1.2011.2.91.10.2.1.1.15.306
        assistantCoolingUnit OBJECT IDENTIFIER ::= { storage 306 }


        -- 1.3.6.1.4.1.2011.2.91.10.2.1.1.15.306.4
        assistCoolingUnitMonitorFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The System Failed To Monitor Assistant Cooling Unit."
            ::= { assistantCoolingUnit 4 }


        -- 1.3.6.1.4.1.2011.2.91.10.2.1.1.15.306.1
        assistantCoolingUnitNotPresent NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Assistant Cooling Unit Not Present."
            ::= { assistantCoolingUnit 1 }


        -- 1.3.6.1.4.1.2011.2.91.10.2.1.1.15.306.5
        coolingUnitIsUnrecognizable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Assistant Cooling Unit Is Unrecognizable."
            ::= { assistantCoolingUnit 5 }


        -- 1.3.6.1.4.1.2011.2.91.10.2.1.1.15.582
        svp OBJECT IDENTIFIER ::= { storage 582 }


        -- 1.3.6.1.4.1.2011.2.91.10.2.1.1.15.582.16
        svpCpuUsageIsTooHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The SVP CPU Usage Is Too High."
            ::= { svp 16 }


        -- 1.3.6.1.4.1.2011.2.91.10.2.1.1.15.582.6
        svpFanModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SVP Fan Module Is Faulty."
            ::= { svp 6 }


        -- 1.3.6.1.4.1.2011.2.91.10.2.1.1.15.582.2
        svpEnclosureTemperatureIsHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SVP Enclosure Temperature Is Too High."
            ::= { svp 2 }


        -- 1.3.6.1.4.1.2011.2.91.10.2.1.1.15.582.1
        svpCPUTemperatureIsHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SVP CPU Temperature Is Too High."
            ::= { svp 1 }


        -- 1.3.6.1.4.1.2011.2.91.10.2.1.1.15.582.0
        svpMainboardIsFaultyWithErrCode NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SVP Mainboard Is Faulty."
            ::= { svp 0 }


        -- 1.3.6.1.4.1.2011.2.91.10.2.1.1.15.582.10
        svpLUNDegrades NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SVP LUN Degrades."
            ::= { svp 10 }


        -- 1.3.6.1.4.1.2011.2.91.10.2.1.1.15.582.5
        svpPowerModuleIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SVP Power Module Is Faulty."
            ::= { svp 5 }


        -- 1.3.6.1.4.1.2011.2.91.10.2.1.1.15.582.4
        svpPowerModuleAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SVP Power Module Input Is Abnormal."
            ::= { svp 4 }


        -- 1.3.6.1.4.1.2011.2.91.10.2.1.1.15.582.20
        manageStorageEquipmentFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Manage The Storage Equipment."
            ::= { svp 20 }


        -- 1.3.6.1.4.1.2011.2.91.10.2.1.1.15.582.11
        manageSVPFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Manage The SVP."
            ::= { svp 11 }


        -- 1.3.6.1.4.1.2011.2.91.10.2.1.1.15.582.18
        svpProcessCpuUsageIsTooHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The CPU Usage Of An SVP Process Is Too High."
            ::= { svp 18 }


        -- 1.3.6.1.4.1.2011.2.91.10.2.1.1.15.582.17
        svpNtpSynchronizationIsAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "SVP NTP Time Synchronization Is Abnormal."
            ::= { svp 17 }


        -- 1.3.6.1.4.1.2011.2.91.10.2.1.1.15.582.19
        svpProcessMemoryUsageIsTooHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Memory Usage Of An SVP Process Is Too High."
            ::= { svp 19 }


        -- 1.3.6.1.4.1.2011.2.91.10.2.1.1.15.582.15
        svpDirectoryExcessiveFilesExist NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Excessive Files Exist In An SVP Directory."
            ::= { svp 15 }


        -- 1.3.6.1.4.1.2011.2.91.10.2.1.1.15.582.14
        svpDirectoryIsOversized NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "An SVP Directory Is Oversized."
            ::= { svp 14 }


        -- 1.3.6.1.4.1.2011.2.91.10.2.1.1.15.582.13
        svpMemoryUsageIsTooHigh NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The SVP Memory Usage Is Too High."
            ::= { svp 13 }


        -- 1.3.6.1.4.1.2011.2.91.10.2.1.1.15.583
        lunmirror OBJECT IDENTIFIER ::= { storage 583 }


        -- 1.3.6.1.4.1.2011.2.91.10.2.1.1.15.583.16
        almLunMirrorCopyErr NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Mirror Copy Is Abnormally Interrupted."
            ::= { lunmirror 16 }


        -- 1.3.6.1.4.1.2011.2.91.10.2.1.1.15.583.17
        almLunMirrorCopyUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Mirror Copy Is Unavailable."
            ::= { lunmirror 17 }


        -- 1.3.6.1.4.1.2011.2.91.10.2.1.1.15.815
        blockdevice OBJECT IDENTIFIER ::= { storage 815 }


        -- 1.3.6.1.4.1.2011.2.91.10.2.1.1.15.815.3
        blockDeviceIsFaulty NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Block Device Is Faulty."
            ::= { blockdevice 3 }


        -- 1.3.6.1.4.1.2011.2.91.10.2.1.1.15.818
        devicemanager OBJECT IDENTIFIER ::= { storage 818 }


        -- 1.3.6.1.4.1.2011.2.91.10.2.1.1.15.818.2
        caCertificateIsExpiring NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Certificate Of The DeviceManager Server Is Expiring."
            ::= { devicemanager 2 }


        -- 1.3.6.1.4.1.2011.2.91.10.2.1.1.15.818.3
        caCertificateHasExpired NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Certificate Of The DeviceManager Server Has Expired."
            ::= { devicemanager 3 }


        -- 1.3.6.1.4.1.2011.2.91.10.2.1.1.15.822
        systemreporter OBJECT IDENTIFIER ::= { storage 822 }


        -- 1.3.6.1.4.1.2011.2.91.10.2.1.1.15.822.29
        operationLogsExceedsUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Number Of Operation Logs Exceeds The Upper Limit."
            ::= { systemreporter 29 }


        -- 1.3.6.1.4.1.2011.2.91.10.2.1.1.15.822.30
        sshServiceUntrust NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The SSH Service Is Untrusted."
            ::= { systemreporter 30 }


        -- 1.3.6.1.4.1.2011.2.91.10.2.1.1.15.822.16
        majorUsageThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Usage Exceeded The Threshold."
            ::= { systemreporter 16 }


        -- 1.3.6.1.4.1.2011.2.91.10.2.1.1.15.822.8
        criticalAvgCpuUsageThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Average CPU Usage Exceeded The Threshold."
            ::= { systemreporter 8 }


        -- 1.3.6.1.4.1.2011.2.91.10.2.1.1.15.822.7
        warnTimeSinceLastSyncThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Time Since Last Synchronization Exceeded The Threshold."
            ::= { systemreporter 7 }


        -- 1.3.6.1.4.1.2011.2.91.10.2.1.1.15.822.11
        criticalAvgIORespThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Average I/O Response Time Exceeded The Threshold."
            ::= { systemreporter 11 }


        -- 1.3.6.1.4.1.2011.2.91.10.2.1.1.15.822.10
        criticalServiceTimeThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Service Time Exceeded The Threshold."
            ::= { systemreporter 10 }


        -- 1.3.6.1.4.1.2011.2.91.10.2.1.1.15.822.1
        warnAvgCpuUsageThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Average CPU Usage Exceeded The Threshold."
            ::= { systemreporter 1 }


        -- 1.3.6.1.4.1.2011.2.91.10.2.1.1.15.822.19
        majorMaxIORespTimeThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Maximum I/O Response Time Exceeded The Threshold."
            ::= { systemreporter 19 }


        -- 1.3.6.1.4.1.2011.2.91.10.2.1.1.15.822.18
        majorAvgIORespTimeThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Average I/O Response Time Exceeded The Threshold."
            ::= { systemreporter 18 }


        -- 1.3.6.1.4.1.2011.2.91.10.2.1.1.15.822.21
        majorTimeSinceSyncThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Time Since Last Synchronization Exceeded The Threshold."
            ::= { systemreporter 21 }


        -- 1.3.6.1.4.1.2011.2.91.10.2.1.1.15.822.6
        warnAvgCacheUsageThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Average Cache Usage Exceeded The Threshold."
            ::= { systemreporter 6 }


        -- 1.3.6.1.4.1.2011.2.91.10.2.1.1.15.822.4
        warnAvgIORespTimeThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Average I/O Response Time Exceeded The Threshold."
            ::= { systemreporter 4 }


        -- 1.3.6.1.4.1.2011.2.91.10.2.1.1.15.822.15
        majorAvgCpuUsageThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Average CPU Usage Exceeded The Threshold."
            ::= { systemreporter 15 }


        -- 1.3.6.1.4.1.2011.2.91.10.2.1.1.15.822.14
        criticalTimeSinceSyncThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Time Since Last Synchronization Exceeded The Threshold."
            ::= { systemreporter 14 }


        -- 1.3.6.1.4.1.2011.2.91.10.2.1.1.15.822.9
        criticalUsageThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Usage Exceeded The Threshold."
            ::= { systemreporter 9 }


        -- 1.3.6.1.4.1.2011.2.91.10.2.1.1.15.822.17
        majorServiceTimeThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Service Time Exceeded The Threshold."
            ::= { systemreporter 17 }


        -- 1.3.6.1.4.1.2011.2.91.10.2.1.1.15.822.13
        criticalAvgCacheUsageThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Average Cache Usage Exceeded The Threshold."
            ::= { systemreporter 13 }


        -- 1.3.6.1.4.1.2011.2.91.10.2.1.1.15.822.3
        warnServiceTimeThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Service Time Exceeded The Threshold."
            ::= { systemreporter 3 }


        -- 1.3.6.1.4.1.2011.2.91.10.2.1.1.15.822.12
        criticalMaxIORespThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Maximum I/O Response Time Exceeded The Threshold."
            ::= { systemreporter 12 }


        -- 1.3.6.1.4.1.2011.2.91.10.2.1.1.15.822.2
        warnUsageThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Usage Exceeded The Threshold."
            ::= { systemreporter 2 }


        -- 1.3.6.1.4.1.2011.2.91.10.2.1.1.15.822.5
        warnMaxIORespTimeThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Maximum I/O Response Time Exceeded The Threshold."
            ::= { systemreporter 5 }


        -- 1.3.6.1.4.1.2011.2.91.10.2.1.1.15.822.20
        majorAvgCacheUsageThreshAlarm NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Average Cache Usage Exceeded The Threshold."
            ::= { systemreporter 20 }


        -- 1.3.6.1.4.1.2011.2.91.10.2.1.1.15.823
        serverAgent OBJECT IDENTIFIER ::= { storage 823 }


        -- 1.3.6.1.4.1.2011.2.91.10.2.1.1.15.823.12
        serverLinkIsDown NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Server Link Is Down."
            ::= { serverAgent 12 }


        -- 1.3.6.1.4.1.2011.2.91.10.2.1.1.15.15361
        hypermetro OBJECT IDENTIFIER ::= { storage 15361 }


        -- 1.3.6.1.4.1.2011.2.91.10.2.1.1.15.15361.3
        hyperMetroIsInvalid NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Invalid HyperMetro Pair."
            ::= { hypermetro 3 }


        -- 1.3.6.1.4.1.2011.2.91.10.2.1.1.15.15361.1
        hyperMetroIsUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "HyperMetro Is Unavailable."
            ::= { hypermetro 1 }


        -- 1.3.6.1.4.1.2011.2.91.10.2.1.1.15.15361.4
        hyperMetroIsInterrupted NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "HyperMetro Pair Interrupted Unexpectedly."
            ::= { hypermetro 4 }


        -- 1.3.6.1.4.1.2011.2.91.10.2.1.1.15.15361.2
        hostIncorrectAccessForPair NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Host Has An Incorrect Access Permission."
            ::= { hypermetro 2 }


        -- 1.3.6.1.4.1.2011.2.91.10.2.1.1.15.15361.0
        hyperMetroIsDisconnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "HyperMetro Is Disconnected."
            ::= { hypermetro 0 }


        -- 1.3.6.1.4.1.2011.2.91.10.2.1.1.15.15361.7
        hyperMetroConfigInterrupt NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "HyperMetro Pair Configuration Is Abnormally Interrupted."
            ::= { hypermetro 7 }


        -- 1.3.6.1.4.1.2011.2.91.10.2.1.1.15.15361.8
        hyperMetroNasPairIsIsolated NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "One Storage Array Of A HyperMetro Pair Is Isolated ."
            ::= { hypermetro 8 }


        -- 1.3.6.1.4.1.2011.2.91.10.2.1.1.15.15362
        hypermetrodomain OBJECT IDENTIFIER ::= { storage 15362 }


        -- 1.3.6.1.4.1.2011.2.91.10.2.1.1.15.15362.0
        hyperMetroDomainIsUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "HyperMetro Domain Is Unavailable."
            ::= { hypermetrodomain 0 }


        -- 1.3.6.1.4.1.2011.2.91.10.2.1.1.15.15363
        quorumserver OBJECT IDENTIFIER ::= { storage 15363 }


        -- 1.3.6.1.4.1.2011.2.91.10.2.1.1.15.15363.0
        quorumServerDisconnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Arbitration Server Is Disconnected From Storage Arrays."
            ::= { quorumserver 0 }


        -- 1.3.6.1.4.1.2011.2.91.10.2.1.1.15.15364
        hypermetroconsistencygroup OBJECT IDENTIFIER ::= { storage 15364 }


        -- 1.3.6.1.4.1.2011.2.91.10.2.1.1.15.15364.3
        hostIncorrectAccessForGroup NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Host Has An Incorrect Access Permission."
            ::= { hypermetroconsistencygroup 3 }


        -- 1.3.6.1.4.1.2011.2.91.10.2.1.1.15.15364.2
        hyperMetroGroupIsUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "HyperMetro Consistency Group Is Unavailable."
            ::= { hypermetroconsistencygroup 2 }


        -- 1.3.6.1.4.1.2011.2.91.10.2.1.1.15.15364.1
        hyperMetroGroupIsDisconnected NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "HyperMetro Consistency Group Is Disconnected."
            ::= { hypermetroconsistencygroup 1 }


        -- 1.3.6.1.4.1.2011.2.91.10.2.1.1.15.15365
        quorumserverlink OBJECT IDENTIFIER ::= { storage 15365 }


        -- 1.3.6.1.4.1.2011.2.91.10.2.1.1.15.15365.0
        quorumLinkDown NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Quorum Server Link Is Down."
            ::= { quorumserverlink 0 }


        -- 1.3.6.1.4.1.2011.2.91.10.2.1.1.15.16446
        resourceuser OBJECT IDENTIFIER ::= { storage 16446 }


        -- 1.3.6.1.4.1.2011.2.91.10.2.1.1.15.16446.1
        pwdOfResUserIsAboutToExpire NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Password Of The Resource User Is About To Expire."
            ::= { resourceuser 1 }


        -- 1.3.6.1.4.1.2011.2.91.10.2.1.1.15.16446.4
        resUserHasBeenLocked NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Resource User Has Been Locked."
            ::= { resourceuser 4 }


        -- 1.3.6.1.4.1.2011.2.91.10.2.1.1.15.16446.2
        pwdOfResUserHasExpired NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Password Of The Resource User Has Expired."
            ::= { resourceuser 2 }


        -- 1.3.6.1.4.1.2011.2.91.10.2.1.1.15.16446.3
        resUserIsAboutToBeLocked NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Resource User Is About To Be Locked."
            ::= { resourceuser 3 }


        -- 1.3.6.1.4.1.2011.2.91.10.2.1.1.15.16450
        httpservice OBJECT IDENTIFIER ::= { storage 16450 }


        -- 1.3.6.1.4.1.2011.2.91.10.2.1.1.15.16450.1
        startHttpServiceFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Start The HTTP Service Failed."
            ::= { httpservice 1 }


        -- 1.3.6.1.4.1.2011.2.91.10.2.1.1.15.16451
        ftpservice OBJECT IDENTIFIER ::= { storage 16451 }


        -- 1.3.6.1.4.1.2011.2.91.10.2.1.1.15.16451.1
        startFtpServiceFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Start The FTP Service Failed."
            ::= { ftpservice 1 }


        -- 1.3.6.1.4.1.2011.2.91.10.2.1.1.15.16453
        cifsservice OBJECT IDENTIFIER ::= { storage 16453 }


        -- 1.3.6.1.4.1.2011.2.91.10.2.1.1.15.16453.44
        domainDNSServiceUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Domain DNS Service Is Unavailable."
            ::= { cifsservice 44 }


        -- 1.3.6.1.4.1.2011.2.91.10.2.1.1.15.16453.43
        adDomainServiceUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "AD Domain Service Is Unavailable."
            ::= { cifsservice 43 }


        -- 1.3.6.1.4.1.2011.2.91.10.2.1.1.15.16453.1
        auditLogFileSystemAbnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Audit Log File System Is Abnormal."
            ::= { cifsservice 1 }


        -- 1.3.6.1.4.1.2011.2.91.10.2.1.1.15.16453.2
        auditFSFreeCapacityNotEnough NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Available Capacity Of The Audit Log File System Is Insufficient."
            ::= { cifsservice 2 }


        -- 1.3.6.1.4.1.2011.2.91.10.2.1.1.15.16458
        filesystemquota OBJECT IDENTIFIER ::= { storage 16458 }


        -- 1.3.6.1.4.1.2011.2.91.10.2.1.1.15.16458.14
        fsUsedQuotaExceedsDirQuota NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Used Resource Of A File System Quota Exceeds The Soft Quota."
            ::= { filesystemquota 14 }


        -- 1.3.6.1.4.1.2011.2.91.10.2.1.1.15.16458.15
        fsUsedQuotaExceedsUsrGrpQuota NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Used Resource Of A File System Quota Exceeds The Soft Quota."
            ::= { filesystemquota 15 }


        -- 1.3.6.1.4.1.2011.2.91.10.2.1.1.15.16458.13
        fsUsedExceedUserOrGroupSoftQuota NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Used Resource Of A File System Quota Exceeds The Soft Quota."
            ::= { filesystemquota 13 }


        -- 1.3.6.1.4.1.2011.2.91.10.2.1.1.15.57350
        virtualmachine OBJECT IDENTIFIER ::= { storage 57350 }


        -- 1.3.6.1.4.1.2011.2.91.10.2.1.1.15.57350.104
        remainSpaceOfVMfsIsLower NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Remain Space Of The Virtual Machine File System Is Lower Than Threshold Percentage."
            ::= { virtualmachine 104 }


        -- 1.3.6.1.4.1.2011.2.91.10.2.1.1.15.57350.98
        ioErrorsOccurOnVirtualMachine NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Some Read/Write Errors Occur On A Virtual Machine."
            ::= { virtualmachine 98 }


        -- 1.3.6.1.4.1.2011.2.91.10.2.1.1.15.57350.118
        vmFailsShutDown NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "VM Fails To Be Correctly Shut Down Within The Specified Time During Array Power-Off."
            ::= { virtualmachine 118 }


        -- 1.3.6.1.4.1.2011.2.91.10.2.1.1.15.57350.1
        incompleteVirtualMachineCreation NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Incomplete Virtual Machine Creation."
            ::= { virtualmachine 1 }


        -- 1.3.6.1.4.1.2011.2.91.10.2.1.1.15.57350.100
        errorsOccurredOnHypervisor NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Errors Occurred On Hypervisor When Controlling Virtual Machine."
            ::= { virtualmachine 100 }


        -- 1.3.6.1.4.1.2011.2.91.10.2.1.1.15.57350.97
        virtualMachineIsSuspended NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Virtual Machine Is Suspended."
            ::= { virtualmachine 97 }


        -- 1.3.6.1.4.1.2011.2.91.10.2.1.1.15.57350.89
        virtualMachineCrashes NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Virtual Machine Crashes."
            ::= { virtualmachine 89 }


        -- 1.3.6.1.4.1.2011.2.91.10.2.1.1.15.57350.114
        failedToRestoreVirtualMachine NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Restore A Virtual Machine."
            ::= { virtualmachine 114 }


        -- 1.3.6.1.4.1.2011.2.91.10.2.1.1.15.57350.103
        initVMfileSystemFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Initiate The File System Of A Virtual Machine."
            ::= { virtualmachine 103 }


        -- 1.3.6.1.4.1.2011.2.91.10.2.1.1.15.57350.105
        fileSystemOfVMabnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "The Virtual Machine File System Is Abnormal."
            ::= { virtualmachine 105 }


        -- 1.3.6.1.4.1.2011.2.91.10.2.1.1.15.57350.116
        serviceOfVMabnormal NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "VM Service Is Abnormal."
            ::= { virtualmachine 116 }


        -- 1.3.6.1.4.1.2011.2.91.10.2.1.1.15.16452
        nfsservice OBJECT IDENTIFIER ::= { storage 16452 }


        -- 1.3.6.1.4.1.2011.2.91.10.2.1.1.15.16452.27
        obtainLDAPCertFileFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Obtain The LDAP Certificate File."
            ::= { nfsservice 27 }


        -- 1.3.6.1.4.1.2011.2.91.10.2.1.1.15.16452.25
        ldapServiceUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "LDAP Service Is Unavailable."
            ::= { nfsservice 25 }


        -- 1.3.6.1.4.1.2011.2.91.10.2.1.1.15.16452.24
        getLDAPCertificateFileFailed NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Failed To Get LDAP Certificate File And Restart The NFS Service."
            ::= { nfsservice 24 }


        -- 1.3.6.1.4.1.2011.2.91.10.2.1.1.15.16452.26
        nisServiceUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "NIS Service Is Unavailable."
            ::= { nfsservice 26 }


        -- 1.3.6.1.4.1.2011.2.91.10.2.1.1.15.16386
        protocolcluster OBJECT IDENTIFIER ::= { storage 16386 }


        -- 1.3.6.1.4.1.2011.2.91.10.2.1.1.15.16386.26
        cloneNFSShareReachLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "During File System Clone, The Number Of Copied NFS Share Reaches The Limit."
            ::= { protocolcluster 26 }


        -- 1.3.6.1.4.1.2011.2.91.10.2.1.1.15.16386.27
        cloneNFSPermissionReachLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "During File System Clone, The Number Of Copied NFS Share Permissions  Reaches The Limit."
            ::= { protocolcluster 27 }


        -- 1.3.6.1.4.1.2011.2.91.10.2.1.1.15.16386.2
        servicePortConflict NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "A Service Port Conflicts."
            ::= { protocolcluster 2 }


        -- 1.3.6.1.4.1.2011.2.91.10.2.1.1.15.16386.7
        phRecordReachUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of File Information Items To Be Backed Up Reaches The Upper Limit."
            ::= { protocolcluster 7 }


        -- 1.3.6.1.4.1.2011.2.91.10.2.1.1.15.16386.9
        smb1ShareNumReachUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Share Connections For SMB One Reaches The Upper Limit."
            ::= { protocolcluster 9 }


        -- 1.3.6.1.4.1.2011.2.91.10.2.1.1.15.16386.8
        smb2ShareNumReachUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of Share Connections For SMB Two Reaches The Upper Limit."
            ::= { protocolcluster 8 }


        -- 1.3.6.1.4.1.2011.2.91.10.2.1.1.15.16386.10
        fileLockNumReachUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of File Locks For NAS Reaches The Upper Limit."
            ::= { protocolcluster 10 }


        -- 1.3.6.1.4.1.2011.2.91.10.2.1.1.15.16386.5
        clientConnectionReachUpperLimit NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Number Of NAS Client Connections Of A Controller Reaches The Upper Limit."
            ::= { protocolcluster 5 }


        -- 1.3.6.1.4.1.2011.2.91.10.2.1.1.15.20480
        certificateManagement OBJECT IDENTIFIER ::= { storage 20480 }


        -- 1.3.6.1.4.1.2011.2.91.10.2.1.1.15.20480.2
        certificateWillExpireWithTime NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Certificate Is About To Expire."
            ::= { certificateManagement 2 }


        -- 1.3.6.1.4.1.2011.2.91.10.2.1.1.15.20480.1
        certificateExpiredWithDeadline NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Certificate Has Expired."
            ::= { certificateManagement 1 }


        -- 1.3.6.1.4.1.2011.2.91.10.2.1.1.15.20480.4
        tenantCertificateWillExpire NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Certificate Is About To Expire."
            ::= { certificateManagement 4 }


        -- 1.3.6.1.4.1.2011.2.91.10.2.1.1.15.20480.3
        tenantCertificateHasExpired NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Certificate Has Expired."
            ::= { certificateManagement 3 }


        -- 1.3.6.1.4.1.2011.2.91.10.2.1.1.15.15366
        hyperMetroVstorePair OBJECT IDENTIFIER ::= { storage 15366 }


        -- 1.3.6.1.4.1.2011.2.91.10.2.1.1.15.15366.1
        hostIncorrectAccessForVstorePair NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Hosts  Access Permissions For A HyperMetro VStore Pair Are Abnormal."
            ::= { hyperMetroVstorePair 1 }


        -- 1.3.6.1.4.1.2011.2.91.10.2.1.1.15.15366.3
        hyperMetroVstoreConfigInterrupt NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "HyperMetro VStore Pair Configuration Is Abnormally Interrupted."
            ::= { hyperMetroVstorePair 3 }


        -- 1.3.6.1.4.1.2011.2.91.10.2.1.1.15.15366.2
        vstorePairIsUnavailable NOTIFICATION-TYPE
            OBJECTS { hwIsmReportingAlarmNodeCode, hwIsmReportingAlarmLocationInfo, hwIsmReportingAlarmRestoreAdvice, hwIsmReportingAlarmFaultTitle, hwIsmReportingAlarmFaultType,
                hwIsmReportingAlarmFaultLevel, hwIsmReportingAlarmAlarmID, hwIsmReportingAlarmFaultTime, hwIsmReportingAlarmSerialNo, hwIsmReportingAlarmLocationAlarmID, 
                hwIsmReportingAlarmFaultCategory, hwIsmReportingAlarmAdditionInfo }
            STATUS current
            DESCRIPTION 
                "Invalid HyperMetro VStore Pair."
            ::= { hyperMetroVstorePair 2 }


--  1.6.1
        -- 1.6.1
        isoGroups OBJECT IDENTIFIER ::= { isoConformance 1 }


--  1.6.1.1
        -- 1.6.1.1
        currentNotificationGroup NOTIFICATION-GROUP
            NOTIFICATIONS { ethFCoEPortIsDisconnected, portIsWorkingInHalfDuplexMode, expPortHasTooManyBitErrors, hostPortHasTooManyBitErrors, pciePortIsPartiallyDamaged, pciePortIsDisconnected, expansionPortPartiallyDamaged, expansionPortIsDisconnected, rateIsSmallerThanAllowedMaximum, portNegotiatedRateNotToMaximum, hostPortIsDisconnected, manageNetworkPortIsDisconnected, expansionPortIsolated, managementNetworkPortIsFaulty, pciePortIsFaulty, hostPortIsFaulty, expansionPortIsFaulty, numberOfDisksExceedsUpperLimit, mixtureOfSATAAndNonSATADisks, diskIsIsolated, slowDiskResponse, authenticationOfSEDAccessFails, cofferDiskIsFaulty, cofferDiskFault, diskInEngineMonitoringFailed, diskMonitoringFailed, diskModelIsIncompatible, diskInSingleLinkState, diskIsAboutToFail, cofferDiskModelIsIncompatible, diskTemperatureExceedsUpperLimit, cofferDiskInInccorrectSlot, diskIsRejectedBySystem, cofferDisksNotFound, authenticationOfSEDKeyFails, diskHardwareIsFaulty,
                diskIsUnrecognizable, svpDiskIsFaulty, svpDiskIsNotInserted, externalLunTypeChanged, lunStartBgrTaskFailed, localArrayRegPathToHeteroFailed, theLUNHasMediumError, theLUNLBAHasWarningMediumError, theLUNLBAHasCriticalMediumError, snapshotLUNIsFault, externalLUNFault, externalLUNToOnlyOneController, remoteLinkExceedUpperLimit, remoteArrayExceedUpperLimit, incompatibleArrayConnected, theLUNIsFault, iscsiLinkFaulty, fcLinkFaulty, iscsiLinkDisconnected, fcLinkDisconnected, theLUNIsFault, snapshotLUNIsFault, noRedundantConnectionToHost, aLinkToHostIsDown, ultrapathIncompatibleWithStorage, powerModuleIsFaulty, powerModuleInputIsAbnormal, powerModulesTypesDifferent, diskEnclHasNoRePowerModule, powerModuleIsIncompatible, failedToMonitorAPowerModule, powerModuleIsRemoved, powerModuleFaulty, powerModuleHasNoInput, powerModuleTempExceedsLimit, snapshotStopAbnormally, snapshotUnavailable, failedToDisableTheSnapshot, fsObjectIsIsolated,
                fsRemainCapacityIsInsufficient, fileSystemExistMediumError, fileOrDirExistMediumError, openedFilesNumAboutToExceedThres, filesNumAboutToExceedThreshold, filesNumExceedLimit, openedFilesNumExceedLimit, filesNumAboutToExceedLimit, dirFilesNumAboutToExceedLimit, filesNumReachedOrExceededLimit, dirFilesNumExceededLimit, openedFilesNumExceededLimit, subFilesNumToExceedLimit, subFilesNumAboutToExceedLimit, fileSystemMetadataIsDamaged, fileOrDirDamagedInFs, fileSystemIsFaulty, writeProtectionIsEnabledForFS, eventAmountReachUpLimit, controllerWriteCacheIsDisabled, dnsIsUnavailable, ipaddrConflict, onlyOneClusterLinkIsAvailable, systemEnterSafeMode, userInfoNeedReview, passwdOfUserHasExpired, passwdOfUserIsAboutToExpire, passwdOfUserHasExpired, passwdOfUserIsAboutToExpire, enclosureIsFaulty, failedToMonitorTheRearPanel, highDensityAreMixConnected, numOfEnclOnExpPortExceedsLimit, failedToIdentifyEnclosure, enclosureIsUnrecognizable,
                enclosureCablingIsIncorrect, faultsOccurredOnEnclosure, diskEnclTempExceedsUpperLimit, diskEnclTempIsBelowLimit, ctrlEnclTempExceedsUpperLimit, ctrlEnclTempIsFarBeyondUpLimit, diskEnclTempIsFarBeyondUpLimit, enclSpeedSmallerThanLoopSpeed, anUnsupportedExpEnclConnected, diskEnclosureIsSingleLink, failedToMonitorADiskEnclosure, monitorControllerFailed, abnormalCommunicateBetweenCtrls, controllerCannotBeMonitored, controllerServicesAbnormal, controllerIsFaulty, bbuIsFault, ctrlAndMgtCommunicateLinkFault, controllerIsFaulty, controllerIsOffline, portIsIncorrectlyConnected, controllerIsRemoved, theCoinBatteryIsFaulty, ftpServiceIsAbnormal, processCpuUsageIsTooHigh, sshServiceIsAbnormal, bbuIsFault, ntpSynchronizationIsAbnormal, excessiveFilesExistInADirectory, processMemoryUsageIsTooHigh, directoryIsOversized, openedFilesNumAboutToExceedLimit, remainAvailableMemoryTooLow, cpuUsageTooHigh, memoryUsageTooHigh, firmwareVersionIncompatible,
                controllerNetStackIsAbnormal, bbuTempHigh, cpuUsageIsTooHigh, monitorControllersFailed, memoryCapacityIsNotSupported, expansionModuleIsFaulty, syncExpansionFirmwareFailed, sasExpansionModuleIncompatible, expansionModuleIncompatible, expansionCableLinkError, expansionModuleIsRemoved, expansionModuleIsNotInserted, expansionModuleFaulty, abnormalCommBetweenExpModules, interfaceModuleIsRemoved, interfaceModuleIsUnrecognizable, incorrectRemovalInterfaceModule, interfaceModuleTempExceedsLimit, monitorInterfaceModuleFailed, failedToMonitorTheInternalLink, internalLinkofIntfModIsFaulty, faultyInterfaceModuleComponent, managementModuleIncompatible, communicationIsFaulty, interfaceModuleIncompatible, managementModuleIsFaulty, managementModuleIsAbnormal, pcieChannelIsFaulty, someStatusMonitoringFailed, interfaceModuleIsFaulty, pcieChannelIsAbnormal, slotDoesNotMatchInterfaceModule, bbuModuleIsFaulty, bbuModuleLifeIsOvertime,
                bbuModuleIsAboutToExpire, bbuModuleTempExceedsLimit, failedToMonitorABBUModule, bbuFirmwareIncompatible, bbuModuleIsRemoved, bbuModuleTypeDoesNotComply, bbuModuleTempIsBelowLimit, fanModuleIsRemoved, fanModuleIsFaulty, ckgMetadataHasFaults, extentMetadataOfVolumeHasFaults, usedCapacityReachAlarmThreshold, availableSpaceInsufficient, smartTierUnavailable, availableSpaceUsedUp, storagePoolCapacityShouldUseUp, storagePoolCapacityNotEnough, smartCacheDiskIsFaulty, almCpyFullCopyFail, almCLnPairInterrupt, almClnPairFault, remoteReplicationCGAutoSplit, remoteReplicationCGIsUnavailable, remoteReplicationCGIsInterrupted, noBackupLinkForRep, repLinkDown, switchFanModuleIsFaulty, powerSupplyOfSwitchIsFaulty, switchPowerInputIsAbnormal, switchFanModuleIsRemoved, negoRateSmallerThanTheMax, switchPortOpticalModuleIsFaulty, switchFailToMonitorPowModules, switchIsFaulty, switchTempExceedsLimit, switchManageNetworkPortIsFaulty,
                switchPowerModuleIsRemoved, switchFailedToBeMonitored, switchTempIsBelowLimit, switchPortIsFaulty, linkToASwitchPortIsAbnormal, dswEthPortIsDown, failedToMonitorSwitchOpModule, switchFailToMonitorFanModules, portOpticalModuleIsFaulty, opticalModuleRateIsInconsistent, failedToMonitorOpOrEleModule, portLinkIsAbnormal, failedToMonitorAnOpticalModule, licenseIsAboutToExpire, licenseHasExpired, licenseIsInvalidWithStartDate, almSmartMigrationErr, autoStartSynRemoteRepFails, remoteReplicationIsInterrupted, remoteReplicationIsInvalid, autoStartSynRemoteRepCGFails, remoteReplicationAutomaticSplit, fsRemoteReplicationPairInvalid, fsRemoteReplicationPairFault, fsRemoteReplicationAutoSyncFail, failedRecoverRmReplication, addRemoteReplicationToCGFails, diskDomainEnterSecureVideoState, diskDomainIsOffline, diskDomainFault, diskDomainDegradation, backgroudTaskFailedToStart, differentDiskType, hotSpareCapacityInsufficient, diskIsRemovedFromDiskDomain,
                newDiskCapacityInsufficieny, controllerWriteCacheDisabled, cachePartitionWriteCacheDisabled, failReachSmartQoSObjective, smartcacheIsFaulty, antivirusServiceIsNotAvailable, antivirusServerIsFault, hyperVaultJobCongestion, hyperVaultScheduledTaskFailure, hyperVaultCopiesReachUpperLimit, hyperVaultLinkIsFaulty, hyperVaultFileSystemFaults, hyperVaultPairInvalid, hyperVaultInterruption, assistCoolingUnitMonitorFailed, assistantCoolingUnitNotPresent, coolingUnitIsUnrecognizable, svpCpuUsageIsTooHigh, svpFanModuleIsFaulty, svpEnclosureTemperatureIsHigh, svpCPUTemperatureIsHigh, svpMainboardIsFaultyWithErrCode, svpLUNDegrades, svpPowerModuleIsFaulty, svpPowerModuleAbnormal, manageStorageEquipmentFailed, manageSVPFailed, svpProcessCpuUsageIsTooHigh, svpNtpSynchronizationIsAbnormal, svpProcessMemoryUsageIsTooHigh, svpDirectoryExcessiveFilesExist, svpDirectoryIsOversized, svpMemoryUsageIsTooHigh, almLunMirrorCopyErr, almLunMirrorCopyUnavailable,
                blockDeviceIsFaulty, caCertificateIsExpiring, caCertificateHasExpired, operationLogsExceedsUpperLimit, sshServiceUntrust, majorUsageThreshAlarm, criticalAvgCpuUsageThreshAlarm, warnTimeSinceLastSyncThreshAlarm, criticalAvgIORespThreshAlarm, criticalServiceTimeThreshAlarm, warnAvgCpuUsageThreshAlarm, majorMaxIORespTimeThreshAlarm, majorAvgIORespTimeThreshAlarm, majorTimeSinceSyncThreshAlarm, warnAvgCacheUsageThreshAlarm, warnAvgIORespTimeThreshAlarm, majorAvgCpuUsageThreshAlarm, criticalTimeSinceSyncThreshAlarm, criticalUsageThreshAlarm, majorServiceTimeThreshAlarm, criticalAvgCacheUsageThreshAlarm, warnServiceTimeThreshAlarm, criticalMaxIORespThreshAlarm, warnUsageThreshAlarm, warnMaxIORespTimeThreshAlarm, majorAvgCacheUsageThreshAlarm, serverLinkIsDown, hyperMetroIsInvalid, hyperMetroIsUnavailable, hyperMetroIsInterrupted, hostIncorrectAccessForPair, hyperMetroIsDisconnected, hyperMetroConfigInterrupt, hyperMetroNasPairIsIsolated,
                hyperMetroDomainIsUnavailable, quorumServerDisconnected, hostIncorrectAccessForGroup, hyperMetroGroupIsUnavailable, hyperMetroGroupIsDisconnected, quorumLinkDown, pwdOfResUserIsAboutToExpire, resUserHasBeenLocked, pwdOfResUserHasExpired, resUserIsAboutToBeLocked, startHttpServiceFailed, startFtpServiceFailed, domainDNSServiceUnavailable, adDomainServiceUnavailable, auditLogFileSystemAbnormal, auditFSFreeCapacityNotEnough, fsUsedQuotaExceedsDirQuota, fsUsedQuotaExceedsUsrGrpQuota, fsUsedExceedUserOrGroupSoftQuota, remainSpaceOfVMfsIsLower, ioErrorsOccurOnVirtualMachine, vmFailsShutDown, incompleteVirtualMachineCreation, errorsOccurredOnHypervisor, virtualMachineIsSuspended, virtualMachineCrashes, failedToRestoreVirtualMachine, initVMfileSystemFailed, fileSystemOfVMabnormal, serviceOfVMabnormal, obtainLDAPCertFileFailed, ldapServiceUnavailable, getLDAPCertificateFileFailed, nisServiceUnavailable, cloneNFSShareReachLimit,
                cloneNFSPermissionReachLimit, servicePortConflict, phRecordReachUpperLimit, smb1ShareNumReachUpperLimit, smb2ShareNumReachUpperLimit, fileLockNumReachUpperLimit, clientConnectionReachUpperLimit, certificateWillExpireWithTime, certificateExpiredWithDeadline, tenantCertificateWillExpire, tenantCertificateHasExpired, hostIncorrectAccessForVstorePair, hyperMetroVstoreConfigInterrupt, vstorePairIsUnavailable }
            STATUS current
            DESCRIPTION 
                "Enter the description of the created NOTIFICATION-GROUP."
            ::= { isoGroups 1 }



    END

--
-- ISM-HUAWEI-OID-BASED-TRAP-MIB.mib
--

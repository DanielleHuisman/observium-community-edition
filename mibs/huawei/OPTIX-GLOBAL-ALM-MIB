--
-- OPTIX-ALM-MIB-NEW-G.mib
-- MIB generated by MG-SOFT Visual MIB Builder Version 3.0 Build 253
-- Tuesday, December 9, 2008 at 15:36:00
--

-- =================================================================
-- Copyright (C) 2006 by HUAWEI TECHNOLOGIES. All rights reserved
-- 
-- Description:This MIB describes the Alarm interface of Huawei SDH transmit
-- Reference:
-- Version: V1.00
-- History:
-- <author>, <date>,    <contents>
-- Liuzuming 2008-12-09
-- =================================================================
    OPTIX-GLOBAL-ALM-MIB DEFINITIONS ::= BEGIN
 
        IMPORTS
            DateAndTime          
                FROM SNMPv2-TC
            AlarmEventType, AlmDataNtfcnCdeType, AlmDataSrvEffType, ObjType
                FROM OPTIX-GLOBAL-TC-MIB            
            optixGlobalTrap, 
            rptEvtNumber, rptAlmName, rptEvtNtfcnCde, rptEvtState, rptEvtStartTime, rptEvtEndTime,
            rptEvtSrvEff, rptEvtObjType, rptEvtPara         
                FROM OPTIX-GLOBAL-TRAPS-MIB           
            OBJECT-GROUP, MODULE-COMPLIANCE            
                FROM SNMPv2-CONF            
        	optixCommonGlobal			
				FROM OPTIX-OID-MIB	
            Unsigned32, OBJECT-TYPE, MODULE-IDENTITY            
				FROM SNMPv2-SMI;

		optixGlobalAlarm MODULE-IDENTITY 
			LAST-UPDATED "200805240000Z"
			ORGANIZATION 
				"Huawei Technologies co.,Ltd."
			CONTACT-INFO 
				"R&D Building
				Huawei Technologies Co., Ltd.
				Bantian, Longgang District 
				Shenzhen, P. R. China
				http://www.huawei.com
				Zip:518129
				E-mail:support@huawei.com"
			DESCRIPTION 
				"Description."
			REVISION "200805240000Z"
			DESCRIPTION
				"The initial revision of this MIB module."
			::= { optixCommonGlobal 30 }   		
--
-- Node definitions,query current alm data or history alm data,
--
    
        -- 1.3.6.1.4.1.2011.2.25.3.40.30.10
        queryAlmData OBJECT IDENTIFIER ::= { optixGlobalAlarm 10 }  
               
-- -------------------------------------------------------------------------
--  Current Alarm Data Table 
-- -------------------------------------------------------------------------
        -- 1.3.6.1.4.1.2011.2.25.3.40.30.10.10
        curAlmDataTable OBJECT-TYPE
            SYNTAX SEQUENCE OF CurAlmDataEntry
            MAX-ACCESS not-accessible
            STATUS current
            DESCRIPTION
                "Current alarm data table."
            ::= { queryAlmData 10 }
			
		
	--  1.3.6.1.4.1.2011.2.25.3.40.40.40.13489
    almRmtDevPowerOff NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Remote device power-off alarm."
    ::= { trapsAlm 13489 }
	
--  1.3.6.1.4.1.2011.2.25.3.40.40.40.12584
    almInsertionLossHigh NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Excessive insertion loss between the TDC and RDC optical ports.The insertion loss between TDC and RDC does not match the gain."
    ::= { trapsAlm 12584 }

--  1.3.6.1.4.1.2011.2.25.3.40.40.40.12615
    almOtsTim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OTS trace identifier mismatch."
    ::= { trapsAlm 12615 }

--  1.3.6.1.4.1.2011.2.25.3.40.40.40.12616
    almOtsLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OTS loss of signal."
    ::= { trapsAlm 12616 }

--  1.3.6.1.4.1.2011.2.25.3.40.40.40.12617
    almOtsLosP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OTS loss of signal - Payload."
    ::= { trapsAlm 12617 }

--  1.3.6.1.4.1.2011.2.25.3.40.40.40.12618
    almOtsLosO NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OTS loss of signal - Overhead."
    ::= { trapsAlm 12618 }

--  1.3.6.1.4.1.2011.2.25.3.40.40.40.12619
    almOtsBdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OTS backward defect indication."
    ::= { trapsAlm 12619 }

--  1.3.6.1.4.1.2011.2.25.3.40.40.40.12620
    almOtsBdiP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OTS backward defect indication - Payload."
    ::= { trapsAlm 12620 }

--  1.3.6.1.4.1.2011.2.25.3.40.40.40.12621
    almOtsBdiO NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OTS backward defect indication - Overhead."
    ::= { trapsAlm 12621 }

--  1.3.6.1.4.1.2011.2.25.3.40.40.40.12622
    almOosLost NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Loss of OTM overhead signal."
    ::= { trapsAlm 12622 }

--  1.3.6.1.4.1.2011.2.25.3.40.40.40.12623
    almOmsLosP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OMS loss of signal - Payload."
    ::= { trapsAlm 12623 }

--  1.3.6.1.4.1.2011.2.25.3.40.40.40.12624
    almOmsSsf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Server signal fail at OMS layer."
    ::= { trapsAlm 12624 }

--  1.3.6.1.4.1.2011.2.25.3.40.40.40.12625
    almOmsSsfP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Server signal fail (payload) at OMS layer."
    ::= { trapsAlm 12625 }

--  1.3.6.1.4.1.2011.2.25.3.40.40.40.12626
    almOmsSsfO NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Server signal fail (overhead) at OMS layer."
    ::= { trapsAlm 12626 }

--  1.3.6.1.4.1.2011.2.25.3.40.40.40.12627
    almOmsFdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OMS forward defect indication."
    ::= { trapsAlm 12627 }

--  1.3.6.1.4.1.2011.2.25.3.40.40.40.12628
    almOmsFdiP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OMS forward defect indication - Payload."
    ::= { trapsAlm 12628 }

--  1.3.6.1.4.1.2011.2.25.3.40.40.40.12629
    almOmsFdiO NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OMS forward defect indication - Overhead."
    ::= { trapsAlm 12629 }

--  1.3.6.1.4.1.2011.2.25.3.40.40.40.12630
    almOmsBdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OMS backward defect indication."
    ::= { trapsAlm 12630 }

--  1.3.6.1.4.1.2011.2.25.3.40.40.40.12631
    almOmsBdiP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OMS backward defect indication - Payload."
    ::= { trapsAlm 12631 }

--  1.3.6.1.4.1.2011.2.25.3.40.40.40.12632
    almOmsBdiO NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OMS backward defect indication - Overhead."
    ::= { trapsAlm 12632 }

--  1.3.6.1.4.1.2011.2.25.3.40.40.40.12771
    almWavelenOver NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The wavelength drift over the threshold."
    ::= { trapsAlm 12771 }

--  1.3.6.1.4.1.2011.2.25.3.40.40.40.12779
    almOnePumpWork NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Only one pump card is working."
    ::= { trapsAlm 12779 }

--  1.3.6.1.4.1.2011.2.25.3.40.40.40.12780
    almPumpLinkUllageHigh NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Pump laser connection loss."
    ::= { trapsAlm 12780 }

--  1.3.6.1.4.1.2011.2.25.3.40.40.40.12784
    almPumpOffline NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The pump card is offline."
    ::= { trapsAlm 12784 }

--  1.3.6.1.4.1.2011.2.25.3.40.40.40.12840
    almPumpMisMatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The type of pump card does not match that of the board."
    ::= { trapsAlm 12840 }

--  1.3.6.1.4.1.2011.2.25.3.40.40.40.12878
    almApdTemHigh NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: APD temperature over upper threshold."
    ::= { trapsAlm 12878 }

--  1.3.6.1.4.1.2011.2.25.3.40.40.40.12879
    almApdTemLow NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: APD temperature below lower threshold."
    ::= { trapsAlm 12879 }

--  1.3.6.1.4.1.2011.2.25.3.40.40.40.12880
    almApdCoolAlm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: APD cooling current over threshold."
    ::= { trapsAlm 12880 }

--  1.3.6.1.4.1.2011.2.25.3.40.40.40.12995
    almOaHighGain NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OA gain is higher than standard level."
    ::= { trapsAlm 12995 }

--  1.3.6.1.4.1.2011.2.25.3.40.40.40.13052
    almLockpowMis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Mismatch of lock-power attribute."
    ::= { trapsAlm 13052 }


--  1.3.6.1.4.1.2011.2.25.3.40.40.40.13197
    almWaveAddAbn NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The actually accessed wavelengths on each optical interface can be obtained through the spectrum analysis module of the detect board.The wavelengths are then compared with the scanned wavelengths obtained during the defining.If there is a

wavelength that is not accessed,a wavelength drop alm is reported."
    ::= { trapsAlm 13197 }

--  1.3.6.1.4.1.2011.2.25.3.40.40.40.13198
    almWaveDropAbn NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The actually accessed wavelengths on each optical interface can be obtained through the spectrum analysis module of the detect board.The wavelengths are then compared with the scanned wavelengths obtained during the defining. If a new wavelength is detected,a wavelength add alm is reported."
    ::= { trapsAlm 13198 }

--  1.3.6.1.4.1.2011.2.25.3.40.40.40.13199
    almApeAdjustPend NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: APE adjustment is pending for operation."
    ::= { trapsAlm 13199 }

--  1.3.6.1.4.1.2011.2.25.3.40.40.40.13200
    almApeAdjustFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: APE adjustment fails."
    ::= { trapsAlm 13200 }

--  1.3.6.1.4.1.2011.2.25.3.40.40.40.13414
    almRlCriticalHi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: High return loss alarm - critical."
    ::= { trapsAlm 13414 }

--  1.3.6.1.4.1.2011.2.25.3.40.40.40.13415
    almRlCriticalLow NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Low return loss alarm - critical."
    ::= { trapsAlm 13415 }

--  1.3.6.1.4.1.2011.2.25.3.40.40.40.13483
    almFibertypeMis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Fiber type mismatch."
    ::= { trapsAlm 13483 }

--  1.3.6.1.4.1.2011.2.25.3.40.40.40.13504
    almAlsTriggered NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Automatic laser shutdown."
    ::= { trapsAlm 13504 }

--  1.3.6.1.4.1.2011.2.25.3.40.40.40.13534
    almAseNotCalibrate NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The alarm is generated when the amplified spontaneous emission (ASE) on the RAMAN board is not demarcated."
    ::= { trapsAlm 13534 }

--  1.3.6.1.4.1.2011.2.25.3.40.40.40.13541
    almDerivedPwrError NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Optical power exception alarm."
    ::= { trapsAlm 13541 }

--  1.3.6.1.4.1.2011.2.25.3.40.40.40.13715
    almLaserOpenFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: This alarm is reported when the laser fails to be turned on because the OTDR test results do not satisfy the requirements."
    ::= { trapsAlm 13715 }

--  1.3.6.1.4.1.2011.2.25.3.40.40.40.13720
    almOtsPmi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: When a local OTS-layer board detects that it has no transmit light or is faulty, it inserts an OTS_PMI signal downstream."
    ::= { trapsAlm 13720 }

--  1.3.6.1.4.1.2011.2.25.3.40.40.40.13721
    almOmsPmi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: When a local OMS-layer MUX board detects a fault, it inserts an OMS_PMI signal downstream."
    ::= { trapsAlm 13721 }

--  1.3.6.1.4.1.2011.2.25.3.40.40.40.13965
    almLsrKeyUnlock NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Front panel key unlocked."
    ::= { trapsAlm 13965 }

--  1.3.6.1.4.1.2011.2.25.3.40.40.40.13966
    almMcsSwitchBlocked NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: MCS switch blocked."
    ::= { trapsAlm 13966 }

--  1.3.6.1.4.1.2011.2.25.3.40.40.40.14001
    almOrpCriticalHi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Excessively high reflection power."
    ::= { trapsAlm 14001 }

--  1.3.6.1.4.1.2011.2.25.3.40.40.40.14009
    almFiberBreakPos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Fiber broken position indication."
    ::= { trapsAlm 14009 }

--  1.3.6.1.4.1.2011.2.25.3.40.40.40.14010
    almFiberAbnPos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Fiber abnormal position indication."
    ::= { trapsAlm 14010 }

--  1.3.6.1.4.1.2011.2.25.3.40.40.40.14011
    almFiberLossChg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Fiber loss changing indication."
    ::= { trapsAlm 14011 }

--  1.3.6.1.4.1.2011.2.25.3.40.40.40.14025
    almWavelenRepeated NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Repeated wavelengths found during wavelength locking configuration."
    ::= { trapsAlm 14025 }

--  1.3.6.1.4.1.2011.2.25.3.40.40.40.14037
    almSubcardComFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: This alarm is reported when the communication between the CPU module of the board and the subcard fails."
    ::= { trapsAlm 14037 }

--  1.3.6.1.4.1.2011.2.25.3.40.40.40.14038
    almSubcardMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: This alarm is reported when the subcard that is not supported is inserted to the board."
    ::= { trapsAlm 14038 }

--  1.3.6.1.4.1.2011.2.25.3.40.40.40.14039
    almSubcardOffline NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: This alarm is reported when the subcard of the board is offline or the subcard hardware is faulty."
    ::= { trapsAlm 14039 }

--  1.3.6.1.4.1.2011.2.25.3.40.40.40.14040
    almSubcardUpgradeFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: This alarm is reported when the subcard file of the board fails to be upgraded."
    ::= { trapsAlm 14040 }

--  1.3.6.1.4.1.2011.2.25.3.40.40.40.14050
    almSubcardTempOver NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Sub-card working temperature threshold-crossing."
    ::= { trapsAlm 14050 }

--  1.3.6.1.4.1.2011.2.25.3.40.40.40.14203
    almOtuWaveMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Wavelength configuration mismatch."
    ::= { trapsAlm 14203 }

--  1.3.6.1.4.1.2011.2.25.3.40.40.40.14270
    almIntraOtuWeak NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Poor intra-board 1+1 protection capability."
    ::= { trapsAlm 14270 }

--  1.3.6.1.4.1.2011.2.25.3.40.40.40.14320
    almChanPowerDiffOver NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The difference between the single-wavelength optical power on the working and protection channels exceeds the threshold."
    ::= { trapsAlm 14320 }

--  1.3.6.1.4.1.2011.2.25.3.40.40.40.14326
    almOpaVoaMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: VOA合波衰减和OPA保存的计算值不一样并且超过一定门限则上报此告警."
    ::= { trapsAlm 14326 }

--  1.3.6.1.4.1.2011.2.25.3.40.40.40.14339
    almOsnrDeg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OSNR degrade."
    ::= { trapsAlm 14339 }

--  1.3.6.1.4.1.2011.2.25.3.40.40.40.14340
    almOmsRouteStatusAbn NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Abnormal OMS route status."
    ::= { trapsAlm 14340 }

--  1.3.6.1.4.1.2011.2.25.3.40.40.40.42184
    almRmRlos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Loss of input reverse pump light."
    ::= { trapsAlm 42184 }



--  1.3.6.1.4.1.2011.2.25.3.40.40.40.14401
    almSubrackRingConnectWeak NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: SUBRACK_RING_CONNECT_WEAK."
    ::= { trapsAlm 14401 }
	
--  1.3.6.1.4.1.2011.2.25.3.40.40.40.14385
    almNebdOxcDif NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Optical cross-connect data inconsistency between the NE and boards."
    ::= { trapsAlm 14385 }
	
	--  1.3.6.1.4.1.2011.2.25.3.40.40.40.197
    almNestateInstall NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: NE in install state."
    ::= { trapsAlm 197 }

--  1.3.6.1.4.1.2011.2.25.3.40.40.40.215
    almNesfLost NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Loss of NE software."
    ::= { trapsAlm 215 }

--  1.3.6.1.4.1.2011.2.25.3.40.40.40.234
    almSncpFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: SNCP switching failure."
    ::= { trapsAlm 234 }

--  1.3.6.1.4.1.2011.2.25.3.40.40.40.270
    almModuleCoolcurOver NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Alarm of module cooling current threshold crossing."
    ::= { trapsAlm 270 }

--  1.3.6.1.4.1.2011.2.25.3.40.40.40.342
    almSccLoc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Loss of SCC clock source."
    ::= { trapsAlm 342 }

--  1.3.6.1.4.1.2011.2.25.3.40.40.40.420
    almAlmHangup NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: the orderwire phone is in the off-hook state for a long time."
    ::= { trapsAlm 420 }

--  1.3.6.1.4.1.2011.2.25.3.40.40.40.422
    almSccChange NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: SCC Change Alarm."
    ::= { trapsAlm 422 }

--  1.3.6.1.4.1.2011.2.25.3.40.40.40.440
    almHscUnavail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: HOT SWITCH CONTROL UNAVAILABLE."
    ::= { trapsAlm 440 }

--  1.3.6.1.4.1.2011.2.25.3.40.40.40.578
    almNodeidMm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Node Id Mismatch."
    ::= { trapsAlm 578 }

--  1.3.6.1.4.1.2011.2.25.3.40.40.40.600
    almMsApsIndiEx NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: MS Auto Protect Switch Indicator Expand."
    ::= { trapsAlm 600 }

--  1.3.6.1.4.1.2011.2.25.3.40.40.40.12644
    almDbRestoreFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Database restoration failed."
    ::= { trapsAlm 12644 }

--  1.3.6.1.4.1.2011.2.25.3.40.40.40.13133
    almAlcWaitAdjust NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ALC adjustment is pending for operation."
    ::= { trapsAlm 13133 }

--  1.3.6.1.4.1.2011.2.25.3.40.40.40.13134
    almAlcAdjustFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ALC adjustment fails."
    ::= { trapsAlm 13134 }

--  1.3.6.1.4.1.2011.2.25.3.40.40.40.13272
    almEthMisconnect NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: LAN cable for the link between shelves misconnects."
    ::= { trapsAlm 13272 }


--  1.3.6.1.4.1.2011.2.25.3.40.40.40.13437
    almEfiTypeMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Mismatch between the EFI board type and subrack type."
    ::= { trapsAlm 13437 }

--  1.3.6.1.4.1.2011.2.25.3.40.40.40.13513
    almNeipConfusion NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: NE IP address conflict."
    ::= { trapsAlm 13513 }

--  1.3.6.1.4.1.2011.2.25.3.40.40.40.13664
    almLcsShortageShelf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Lack of sufficient licenses or the number of license functions used exceeding the authorized number."
    ::= { trapsAlm 13664 }

--  1.3.6.1.4.1.2011.2.25.3.40.40.40.13763
    almShelfPowerUnconfig NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: This alarm is reported if the power consumption threshold of a subrack is not configured."
    ::= { trapsAlm 13763 }

--  1.3.6.1.4.1.2011.2.25.3.40.40.40.13947
    almSubrackExceed NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Number of slave subracks exceeding threshold."
    ::= { trapsAlm 13947 }

--  1.3.6.1.4.1.2011.2.25.3.40.40.40.13952
    almRackConflictScreen NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Subrack ID conflict isolation."
    ::= { trapsAlm 13952 }

--  1.3.6.1.4.1.2011.2.25.3.40.40.40.13982
    almBdSessionFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Session broken between NE and remote board."
    ::= { trapsAlm 13982 }

--  1.3.6.1.4.1.2011.2.25.3.40.40.40.14204
    almWclaAbnormal NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Abnormal optical power detected by WCLA."
    ::= { trapsAlm 14204 }

--  1.3.6.1.4.1.2011.2.25.3.40.40.40.14205
    almWclaAdjustFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: WCLA adjustment failure."
    ::= { trapsAlm 14205 }

--  1.3.6.1.4.1.2011.2.25.3.40.40.40.14327
    almXcsUpgradeInproc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Cross-upgrade in progress."
    ::= { trapsAlm 14327 }

--  1.3.6.1.4.1.2011.2.25.3.40.40.40.14328
    almXcsUpgradeFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Cross-upgrade failure."
    ::= { trapsAlm 14328 }

--  1.3.6.1.4.1.2011.2.25.3.40.40.40.14329
    almXcsUpgradeUncommit NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Cross-upgrade not committed."
    ::= { trapsAlm 14329 }

--  1.3.6.1.4.1.2011.2.25.3.40.40.40.14330
    almXcsDngradeInproc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Cross-downgrade in progress."
    ::= { trapsAlm 14330 }

--  1.3.6.1.4.1.2011.2.25.3.40.40.40.14331
    almXcsDngradeFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Cross-downgrade failure."
    ::= { trapsAlm 14331 }
	
--  1.3.6.1.4.1.2011.2.25.3.40.40.40.14379
    almOduflexLoa NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUFLEX_LOA."
    ::= { trapsAlm 14379 }

--  1.3.6.1.4.1.2011.2.25.3.40.40.40.14332
    almXcsRollbackInproc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Cross-rollback in progress."
    ::= { trapsAlm 14332 }

--  1.3.6.1.4.1.2011.2.25.3.40.40.40.14333
    almXcsRollbackFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Cross-rollback failure."
    ::= { trapsAlm 14333 }

--  1.3.6.1.4.1.2011.2.25.3.40.40.40.63625
    almNeidConflict NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: NEID_CONFLICT."
    ::= { trapsAlm 63625 }







--  1.3.6.1.4.1.2011.2.25.3.40.40.40.13008
    almArpMacMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The mac of static arp is mismatched."
    ::= { trapsAlm 13008 }










--  1.3.6.1.4.1.2011.2.25.3.40.40.40.14190
    almFpOffline NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Filler Panel Offline."
    ::= { trapsAlm 14190 }


        
        -- 1.3.6.1.4.1.2011.2.25.3.40.30.10.10.1
        curAlmDataEntry OBJECT-TYPE
            SYNTAX CurAlmDataEntry
            MAX-ACCESS not-accessible
            STATUS current
            DESCRIPTION
                "Current alarm data table."
            INDEX { curAlmNUM }
            ::= { curAlmDataTable 1 }
        
        CurAlmDataEntry ::=
            SEQUENCE { 
                curAlmNUM
                    INTEGER,                
                curAlmEID
                    AlarmEventType,
                curAlmSeverity
                    AlmDataNtfcnCdeType,
                curAlmState
                    INTEGER,
                curAlmStartTime
                    DateAndTime,
                curAlmEndTime
                    DateAndTime,
                curAlmSrvEff
                    AlmDataSrvEffType,
                curAlmObjType
                    ObjType,
                curAlmPara
                    OCTET STRING,  
             }
-- <NUM>  
-- <EID>                     
-- <SEVERITY>            
-- <STATE>          
-- <START-TIME>          
-- <END-TIME>  
-- <SRVEFF>
-- <OBJ-TYPE> 
-- <PARA>   
        -- 1.3.6.1.4.1.2011.2.25.3.40.30.10.10.1.1
        curAlmNUM OBJECT-TYPE
            SYNTAX INTEGER
            MAX-ACCESS read-only
            STATUS current
            DESCRIPTION
                "Alarm number."
            ::= { curAlmDataEntry 1 }        
        -- 1.3.6.1.4.1.2011.2.25.3.40.30.10.10.1.2
        curAlmEID OBJECT-TYPE
            SYNTAX AlarmEventType
            MAX-ACCESS read-only
            STATUS current
            DESCRIPTION
                "Alarm ID."
            ::= { curAlmDataEntry 2 }
        
        -- 1.3.6.1.4.1.2011.2.25.3.40.30.10.10.1.3
        curAlmSeverity OBJECT-TYPE
            SYNTAX AlmDataNtfcnCdeType
            MAX-ACCESS read-only
            STATUS current
            DESCRIPTION
                "The notification code of the retrieved alarm. 
                Only CR|MJ|MN|IG|NR will be represented here."
            ::= { curAlmDataEntry 3 } 
       
        -- 1.3.6.1.4.1.2011.2.25.3.40.30.10.10.1.4
        curAlmState OBJECT-TYPE
            SYNTAX INTEGER
            {
            start(1),
            end(3)
            }
            MAX-ACCESS read-only
            STATUS current
            DESCRIPTION
                "Alarm state."
            ::= { curAlmDataEntry 4 }
        
        -- 1.3.6.1.4.1.2011.2.25.3.40.30.10.10.1.5
        curAlmStartTime OBJECT-TYPE
            SYNTAX DateAndTime
            MAX-ACCESS read-only
            STATUS current
            DESCRIPTION
                "Alarm start time."
            ::= { curAlmDataEntry 5 } 
        
        -- 1.3.6.1.4.1.2011.2.25.3.40.30.10.10.1.6
        curAlmEndTime OBJECT-TYPE
            SYNTAX DateAndTime
            MAX-ACCESS read-only
            STATUS current
            DESCRIPTION
                "Alarm end time."
            ::= { curAlmDataEntry 6 }  
            
       -- 1.3.6.1.4.1.2011.2.25.3.20.60.10.10.1.7
        curAlmSrvEff OBJECT-TYPE
            SYNTAX AlmDataSrvEffType
            MAX-ACCESS read-only
            STATUS current
            DESCRIPTION
                "The notification code of the retrieved alarm. 
                Only SA|NSA will be represented here."
            ::= { curAlmDataEntry 7 }
             
        -- 1.3.6.1.4.1.2011.2.25.3.40.30.10.10.1.8
        curAlmObjType OBJECT-TYPE
            SYNTAX ObjType
            MAX-ACCESS read-only
            STATUS current
            DESCRIPTION
                "Alarm object type."
            ::= { curAlmDataEntry 8 }
        
        -- 1.3.6.1.4.1.2011.2.25.3.20.60.10.10.1.9
        curAlmPara OBJECT-TYPE
            SYNTAX OCTET STRING (SIZE (0..128))
            MAX-ACCESS read-only
            STATUS current
            DESCRIPTION
                "Alarm parameter."
            ::= { curAlmDataEntry 9 }
            
-- -------------------------------------------------------------------------
--  History Alarm Data Table 
-- -------------------------------------------------------------------------
        -- 1.3.6.1.4.1.2011.2.25.3.40.30.10.20
        hisAlmDataTable OBJECT-TYPE
            SYNTAX SEQUENCE OF HisAlmDataEntry
            MAX-ACCESS not-accessible
            STATUS current
            DESCRIPTION
                "History alarm data table."
            ::= { queryAlmData 20 }
        
        -- 1.3.6.1.4.1.2011.2.25.3.40.30.10.20.1
        hisAlmDataEntry OBJECT-TYPE
            SYNTAX HisAlmDataEntry
            MAX-ACCESS not-accessible
            STATUS current
            DESCRIPTION
                "History alarm data table."
            INDEX { hisAlmNUM }
            ::= { hisAlmDataTable 1 }
        
        HisAlmDataEntry ::=
            SEQUENCE { 
                hisAlmNUM
                    INTEGER,                
                hisAlmEID
                    AlarmEventType,
                hisAlmSeverity
                    AlmDataNtfcnCdeType,
                hisAlmState
                    INTEGER,
                hisAlmStartTime
                    DateAndTime,
                hisAlmEndTime
                    DateAndTime,
                hisAlmSrvEff
                    AlmDataSrvEffType,
                hisAlmObjType
                    ObjType,
                hisAlmPara
                    OCTET STRING,  
             }
-- <NUM>  
-- <EID>                     
-- <SEVERITY>            
-- <STATE>          
-- <START-TIME>          
-- <END-TIME>  
-- <SRVEFF>
-- <OBJ-TYPE> 
-- <PARA>   
        -- 1.3.6.1.4.1.2011.2.25.3.40.30.10.20.1.1
        hisAlmNUM OBJECT-TYPE
            SYNTAX INTEGER
            MAX-ACCESS read-only
            STATUS current
            DESCRIPTION
                "Alarm number."
            ::= { hisAlmDataEntry 1 }        
        -- 1.3.6.1.4.1.2011.2.25.3.40.30.10.20.1.2
        hisAlmEID OBJECT-TYPE
            SYNTAX AlarmEventType
            MAX-ACCESS read-only
            STATUS current
            DESCRIPTION
                "Alarm ID."
            ::= { hisAlmDataEntry 2 }
        
        -- 1.3.6.1.4.1.2011.2.25.3.40.30.10.20.1.3
        hisAlmSeverity OBJECT-TYPE
            SYNTAX AlmDataNtfcnCdeType
            MAX-ACCESS read-only
            STATUS current
            DESCRIPTION
                "The notification code of the retrieved alarm. 
                Only CR|MJ|MN|IG|NR will be represented here."
            ::= { hisAlmDataEntry 3 } 
       
        -- 1.3.6.1.4.1.2011.2.25.3.40.30.10.20.1.4
        hisAlmState OBJECT-TYPE
            SYNTAX INTEGER
            {
            start(1),
            end(3)
            }
            MAX-ACCESS read-only
            STATUS current
            DESCRIPTION
                "Alarm state."
            ::= { hisAlmDataEntry 4 }
        
        -- 1.3.6.1.4.1.2011.2.25.3.40.30.10.20.1.5
        hisAlmStartTime OBJECT-TYPE
            SYNTAX DateAndTime
            MAX-ACCESS read-only
            STATUS current
            DESCRIPTION
                "Alarm start time."
            ::= { hisAlmDataEntry 5 } 
        
        -- 1.3.6.1.4.1.2011.2.25.3.40.30.10.20.1.6
        hisAlmEndTime OBJECT-TYPE
            SYNTAX DateAndTime
            MAX-ACCESS read-only
            STATUS current
            DESCRIPTION
                "Alarm end time."
            ::= { hisAlmDataEntry 6 }  
            
       -- 1.3.6.1.4.1.2011.2.25.3.20.60.10.20.1.7
        hisAlmSrvEff OBJECT-TYPE
            SYNTAX AlmDataSrvEffType
            MAX-ACCESS read-only
            STATUS current
            DESCRIPTION
                "The notification code of the retrieved alarm. 
                Only SA|NSA will be represented here."
            ::= { hisAlmDataEntry 7 }
             
        -- 1.3.6.1.4.1.2011.2.25.3.40.30.10.20.1.8
        hisAlmObjType OBJECT-TYPE
            SYNTAX ObjType
            MAX-ACCESS read-only
            STATUS current
            DESCRIPTION
                "Alarm object type."
            ::= { hisAlmDataEntry 8 }
        
        -- 1.3.6.1.4.1.2011.2.25.3.20.60.10.20.1.9
        hisAlmPara OBJECT-TYPE
            SYNTAX OCTET STRING (SIZE (0..128))
            MAX-ACCESS read-only
            STATUS current
            DESCRIPTION
                "Alarm parameter."
            ::= { hisAlmDataEntry 9 }

-- Node definitions,
--  
	-- 1.3.6.1.4.1.2011.2.25.3.40.40.40       
        trapsAlm  OBJECT IDENTIFIER ::= { optixGlobalTrap 40 } 
--  1.3.6.1.4.1.2011.2.25.3.40.40.40.1
    almLos NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Loss of signal"
    ::= { trapsAlm  1}
	

--  1.3.6.1.4.1.2011.2.25.3.40.40.40.3
    almRLoc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of clock on receiving line"
    ::= { trapsAlm 3 }


--  1.3.6.1.4.1.2011.2.25.3.40.40.40.8
    almRLof NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of frame on receiving line"
    ::= { trapsAlm 8 }

	
--  1.3.6.1.4.1.2011.2.25.3.40.40.40.13882
    almInsertLossHigh NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Fiber fault due to excessive insertion losses."
    ::= { trapsAlm 13882 }

--  1.3.6.1.4.1.2011.2.25.3.40.40.40.13883
    almInsertLossMid NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Fiber fault due to high insertion losses."
    ::= { trapsAlm 13883 }

--  1.3.6.1.4.1.2011.2.25.3.40.40.40.14303
    almGneConnectFull NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Excessive gateway connections."
    ::= { trapsAlm 14303 }

--  1.3.6.1.4.1.2011.2.25.3.40.40.40.25
    almInPwrAbn NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The IN_PWR_ABN is an alarm indicating that the input optical power is asbnormal"
    ::= { trapsAlm 25 }

--  1.3.6.1.4.1.2011.2.25.3.40.40.40.33
    almMsAis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The MS_AIS is an indication alarm in the multiplex section"
    ::= { trapsAlm 33 }


--  1.3.6.1.4.1.2011.2.25.3.40.40.40.41
    almApsIndi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The APS_INDI is an alarm indicating the APS state"
    ::= { trapsAlm 41 }


--  1.3.6.1.4.1.2011.2.25.3.40.40.40.57
    almLsrNoFited NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The LSR_NO_FITED is an alarm indicating that the laser is not installed"
    ::= { trapsAlm 57 }


--  1.3.6.1.4.1.2011.2.25.3.40.40.40.68
    almPumTemAlm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Working temperature of the pump laser exceeds the threshold"
    ::= { trapsAlm 68 }

--  1.3.6.1.4.1.2011.2.25.3.40.40.40.69
    almPumBcmAlm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm occurs when the pump laser bias current of the optical amplifier unit crosses the threshold"
    ::= { trapsAlm 69 }




--  1.3.6.1.4.1.2011.2.25.3.40.40.40.87
    almJ0Mm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "When a line board has detected that the received J0 byte at the relevant optical interface is inconsistent with the J0 byte to be received, the J0_MM alarm is reported"
    ::= { trapsAlm 87 }




--  1.3.6.1.4.1.2011.2.25.3.40.40.40.100
    almLti NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The LTI is an alarm indicating the loss of synchronization source"
    ::= { trapsAlm 100 }

--  1.3.6.1.4.1.2011.2.25.3.40.40.40.101
    almSynBad NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The SYN_BAD is a synchronization source degrade alarm"
    ::= { trapsAlm 101 }



--  1.3.6.1.4.1.2011.2.25.3.40.40.40.261
    almLinkErr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm occurs when the Ethernet connection is incorrect and the port negotiation fails"
    ::= { trapsAlm 261 }

--  1.3.6.1.4.1.2011.2.25.3.40.40.40.262
    almWOffline NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The W_OFFLINE is an alarm indicating that the front panel of a board is out of position"
    ::= { trapsAlm 262 }

--  1.3.6.1.4.1.2011.2.25.3.40.40.40.263
    almOol NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The OOL is an alarm indicating that the phase-locked loop is out of lock"
    ::= { trapsAlm 263 }

--  1.3.6.1.4.1.2011.2.25.3.40.40.40.296
    almAlmAls NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ALM_ALS is an automatic laser shutdown (ALS) alarm"
    ::= { trapsAlm 296 }

--  1.3.6.1.4.1.2011.2.25.3.40.40.40.323
    almSumInpwrHi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The SUM_INPWR_HI is an alarm indicating that the combined input optical power of the laser of the colored optical module is over high"
    ::= { trapsAlm 323 }

--  1.3.6.1.4.1.2011.2.25.3.40.40.40.324
    almSumInpwrLow NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Sum input optical power is too low"
    ::= { trapsAlm 324 }

--  1.3.6.1.4.1.2011.2.25.3.40.40.40.327
    almOaLowGain NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The OA_LOW_GAIN is an alarm indicating that the gain of the optical amplifier declines"
    ::= { trapsAlm 327 }

--  1.3.6.1.4.1.2011.2.25.3.40.40.40.336
    almApsManualStop NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ALM_APS_MANU_STOP is an alarm indicating that the MSP protocol is manually stopped"
    ::= { trapsAlm 336 }

--  1.3.6.1.4.1.2011.2.25.3.40.40.40.377
    almBusErr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The BUS_ERR is a bus error alarm"
    ::= { trapsAlm 377 }




--  1.3.6.1.4.1.2011.2.25.3.40.40.40.26
    almOutPwrAbn NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The OUT_PWR_ABN is an alarm indicating that the output optical power is abnormal"
    ::= { trapsAlm 26 }

--  1.3.6.1.4.1.2011.2.25.3.40.40.40.42
    almApsFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The APS_FAIL is an indication alarm of APS protection switching failure"
    ::= { trapsAlm 42 }

--  1.3.6.1.4.1.2011.2.25.3.40.40.40.58
    almLsrBcmAlm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The LSR_BCM_ALM is an alarm indicating that the bias current of the laser crosses the threshold"
    ::= { trapsAlm 58 }

--  1.3.6.1.4.1.2011.2.25.3.40.40.40.60
    almLsrCoolAlm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The LSR_COOL_ALM is an alarm indicating that the cooling current of the laser crosses the threshold"
    ::= { trapsAlm 60 }




--  1.3.6.1.4.1.2011.2.25.3.40.40.40.111
    almSyncCLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm occurs when the clock source of a service board is lost in the priority table"
    ::= { trapsAlm 111 }


--  1.3.6.1.4.1.2011.2.25.3.40.40.40.166
    almTempAlarm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The temperature threshold crossing alarm"
    ::= { trapsAlm 166 }

--  1.3.6.1.4.1.2011.2.25.3.40.40.40.175
    almB1Sd NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The B1_SD is an alarm indicating that regenerator section B1 signals received over the line are degraded"
    ::= { trapsAlm 175 }

--  1.3.6.1.4.1.2011.2.25.3.40.40.40.180
    almK1K2M NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The K1_K2_M is an alarm indicating the mismatch between the K1 and K2 bytes"
    ::= { trapsAlm 180 }

--  1.3.6.1.4.1.2011.2.25.3.40.40.40.181
    almK2M NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The K2_M is an alarm of K2 byte mismatch"
    ::= { trapsAlm 181 }


--  1.3.6.1.4.1.2011.2.25.3.40.40.40.184
    almExtSyncLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The EXT_SYNC_LOS is an alarm indicating the loss of external clock source"
    ::= { trapsAlm 184 }

--  1.3.6.1.4.1.2011.2.25.3.40.40.40.186
    almMutLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The MUT_LOS is an alarm indicating that the coupled signals are lost"
    ::= { trapsAlm 186 }

--  1.3.6.1.4.1.2011.2.25.3.40.40.40.190
    almNoBdPara NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The NO_BD_PARA is an alarm indicating that the board parameters are not set"
    ::= { trapsAlm 190 }

--  1.3.6.1.4.1.2011.2.25.3.40.40.40.192
    almPumpCoolExc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Cool current of pump laser over threshold"
    ::= { trapsAlm 192 }

--  1.3.6.1.4.1.2011.2.25.3.40.40.40.193
    almS1SynChange NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The S1_SYN_CHANGE is an alarm indicating that, in the S1 byte mode, the clock source is switched"
    ::= { trapsAlm 193 }


--  1.3.6.1.4.1.2011.2.25.3.40.40.40.211
    almPowerDiffOver NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Power difference between optical monitoring active and standby crossed the threshold"
    ::= { trapsAlm 211 }
	
--  1.3.6.1.4.1.2011.2.25.3.40.40.40.13112
    almMemOver NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm indicates that the value of memory usage is too high,and it will report when the value of memory usage exceed the thresholds."
    ::= { trapsAlm 13112 }
	
--  1.3.6.1.4.1.2011.2.25.3.40.40.40.14147
    almDcncfgNotCommit NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The configured DCN subnet ID has not been committed."
    ::= { trapsAlm 14147 }

--  1.3.6.1.4.1.2011.2.25.3.40.40.40.63509
    almLaserShut NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The LASER_SHUT is an alarm indicating that the laser of the board is shut down"
    ::= { trapsAlm 63509 }

--  1.3.6.1.4.1.2011.2.25.3.40.40.40.63537
    almHardNonsupport NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the hardware does not support the configuration delivered by the SCC board or the total power of all boards is beyond the permitted range"
    ::= { trapsAlm 63537 }



--  1.3.6.1.4.1.2011.2.25.3.40.40.40.10
    almRsCrosstr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Regenerator section performance over threshold"
    ::= { trapsAlm 10 }

--  1.3.6.1.4.1.2011.2.25.3.40.40.40.12
    almB1Exc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The B1_EXC is an alarm indicating that the number of regenerator section B1 bit errors in the signals received over the line crosses the threshold"
    ::= { trapsAlm 12 }




	
--  1.3.6.1.4.1.2011.2.25.3.40.40.40.390
    almSyncLockoff NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The SYNC_LOCKOFF is an alarm indicating that the clock source in the priority list is locked"
    ::= { trapsAlm 390 }

--  1.3.6.1.4.1.2011.2.25.3.40.40.40.391
    almSyncFMSwitch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The SYNC_F_M_SWITCH is an alarm indicating the forced or manual switching state of a clock source"
    ::= { trapsAlm 391 }

--  1.3.6.1.4.1.2011.2.25.3.40.40.40.393
    almLaserModErr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The LASER_MOD_ERR is an alarm indicating mismatch of optical modules"
    ::= { trapsAlm 393 }

--  1.3.6.1.4.1.2011.2.25.3.40.40.40.12305
    almRelayAlarmCritical NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The RELAY_ALARM_CRITICAL is an alarm of critical alarm inputs"
    ::= { trapsAlm 12305 }

--  1.3.6.1.4.1.2011.2.25.3.40.40.40.12306
    almRelayAlarmMajor NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The RELAY_ALARM_MAJOR is an alarm of major alarm inputs"
    ::= { trapsAlm 12306 }

--  1.3.6.1.4.1.2011.2.25.3.40.40.40.12307
    almRelayAlarmMinor NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The RELAY_ALARM_MINOR is an alarm of minor alarm inputs"
    ::= { trapsAlm 12307 }

--  1.3.6.1.4.1.2011.2.25.3.40.40.40.12308
    almRelayAlarmIgnore NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The RELAY_ALARM_IGNORE is an alarm of warning alarm inputs"
    ::= { trapsAlm 12308 }

--  1.3.6.1.4.1.2011.2.25.3.40.40.40.12311
    almOtu1Lof NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of OTUk frame"
    ::= { trapsAlm 12311 }

--  1.3.6.1.4.1.2011.2.25.3.40.40.40.12312
    almOtu1Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTUk alarm indication signal"
    ::= { trapsAlm 12312 }

--  1.3.6.1.4.1.2011.2.25.3.40.40.40.12313
    almOtu1Lom NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of OTUk multiframe"
    ::= { trapsAlm 12313 }

--  1.3.6.1.4.1.2011.2.25.3.40.40.40.12323
    almOtu2Lof NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of OTUk frame"
    ::= { trapsAlm 12323 }

--  1.3.6.1.4.1.2011.2.25.3.40.40.40.12324
    almOtu2Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTUk alarm indication signal"
    ::= { trapsAlm 12324 }

--  1.3.6.1.4.1.2011.2.25.3.40.40.40.12325
    almOtu2Lom NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of OTUk multiframe"
    ::= { trapsAlm 12325 }

--  1.3.6.1.4.1.2011.2.25.3.40.40.40.12326
    almOtu2Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTUk TTI mismatch"
    ::= { trapsAlm 12326 }

--  1.3.6.1.4.1.2011.2.25.3.40.40.40.12327
    almOtu2Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTUk signal degraded alarm"
    ::= { trapsAlm 12327 }
--  1.3.6.1.4.1.2011.2.25.3.40.40.40.12328
    almOtu2Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTUk backward defect indication"
    ::= { trapsAlm 12328 }

--  1.3.6.1.4.1.2011.2.25.3.40.40.40.12329
    almOtu3Lof NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of OTUk frame"
    ::= { trapsAlm 12329 }

--  1.3.6.1.4.1.2011.2.25.3.40.40.40.12336
    almOdu1PmDeg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk PM signal degraded"
    ::= { trapsAlm 12336 }

--  1.3.6.1.4.1.2011.2.25.3.40.40.40.12337
    almOdu1PmBdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk PM backward defect indication"
    ::= { trapsAlm 12337 }

--  1.3.6.1.4.1.2011.2.25.3.40.40.40.12338
    almOdu1PmLck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU1 PM signal locked"
    ::= { trapsAlm 12338 }

--  1.3.6.1.4.1.2011.2.25.3.40.40.40.12339
    almOdu1PmOci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk PM open connection indication"
    ::= { trapsAlm 12339 }

--  1.3.6.1.4.1.2011.2.25.3.40.40.40.12340
    almOdu1PmAis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk PM alarm indication signal"
    ::= { trapsAlm 12340 }








--  1.3.6.1.4.1.2011.2.25.3.40.40.40.269
    almAdCheckFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "AD (analog to digital converter) self check failure alarm"
    ::= { trapsAlm 269 }

--  1.3.6.1.4.1.2011.2.25.3.40.40.40.333
    almClkNoTraceMode NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The CLK_NO_TRACE_MODE is an alarm indicating that the clock enters into a non-tracing running mode"
    ::= { trapsAlm 333 }

--  1.3.6.1.4.1.2011.2.25.3.40.40.40.364
    almLaserClosed NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The LASER_CLOSED is an alarm indicating that the laser on the line board is closed after the laser shutdown command is received"
    ::= { trapsAlm 364 }


--  1.3.6.1.4.1.2011.2.25.3.40.40.40.424
    almSlaveWorking NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The SLAVE_WORKING is an alarm indicating that the protection board is working"
    ::= { trapsAlm 424 }

--  1.3.6.1.4.1.2011.2.25.3.40.40.40.449
    almBiosStatus NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The BIOS_STATUS is an alarm indicating that the board cannot reach a normal software running status"
    ::= { trapsAlm 449 }

--  1.3.6.1.4.1.2011.2.25.3.40.40.40.591
    almSyncFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The SYNC_FAIL is an alarm indicating that the batch backup of the databases of the active and standby SCC boards fails"
    ::= { trapsAlm 591 }

--  1.3.6.1.4.1.2011.2.25.3.40.40.40.12303
    almSubrackIdMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The hardware subrack ID mismatches that saved in the NE software"
    ::= { trapsAlm 12303 }

--  1.3.6.1.4.1.2011.2.25.3.40.40.40.12314
    almOtu1Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTUk TTI mismatch"
    ::= { trapsAlm 12314 }

--  1.3.6.1.4.1.2011.2.25.3.40.40.40.12315
    almOtu1Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTUk signal degraded alarm"
    ::= { trapsAlm 12315 }

--  1.3.6.1.4.1.2011.2.25.3.40.40.40.12316
    almOtu1Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTUk backward defect indication"
    ::= { trapsAlm 12316 }

--  1.3.6.1.4.1.2011.2.25.3.40.40.40.12330
    almOtu3Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "12330"
    ::= { trapsAlm 12330 }

--  1.3.6.1.4.1.2011.2.25.3.40.40.40.12331
    almOtu3Lom NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "12331"
    ::= { trapsAlm 12331 }

--  1.3.6.1.4.1.2011.2.25.3.40.40.40.12332
    almOtu3Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "12332"
    ::= { trapsAlm 12332 }

--  1.3.6.1.4.1.2011.2.25.3.40.40.40.12333
    almOtu3Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "12333"
    ::= { trapsAlm 12333 }

--  1.3.6.1.4.1.2011.2.25.3.40.40.40.12334
    almOtu3Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "12334"
    ::= { trapsAlm 12334 }

--  1.3.6.1.4.1.2011.2.25.3.40.40.40.12335
    almOdu1PmTim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU1 PM section TTI mismatch"
    ::= { trapsAlm 12335 }

--  1.3.6.1.4.1.2011.2.25.3.40.40.40.12363
    almOdu1Tcm1Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12363 }

--  1.3.6.1.4.1.2011.2.25.3.40.40.40.12364
    almOdu1Tcm2Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12364 }

--  1.3.6.1.4.1.2011.2.25.3.40.40.40.12365
    almOdu1Tcm3Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12365 }

--  1.3.6.1.4.1.2011.2.25.3.40.40.40.12366
    almOdu1Tcm4Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12366 }

--  1.3.6.1.4.1.2011.2.25.3.40.40.40.12367
    almOdu1Tcm5Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12367 }

--  1.3.6.1.4.1.2011.2.25.3.40.40.40.14144
    almFiberMisconnect NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Fiber connections are incorrect"
    ::= { trapsAlm 14144 }

--  1.3.6.1.4.1.2011.2.25.3.40.40.40.12378
    almOdu1Tcm4Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12378 }

--  1.3.6.1.4.1.2011.2.25.3.40.40.40.12379
    almOdu1Tcm5Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12379 }

--  1.3.6.1.4.1.2011.2.25.3.40.40.40.12380
    almOdu1Tcm6Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12380 }

--  1.3.6.1.4.1.2011.2.25.3.40.40.40.12381
    almOdu1Tcm1Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12381 }

--  1.3.6.1.4.1.2011.2.25.3.40.40.40.12382
    almOdu1Tcm2Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12382 }

--  1.3.6.1.4.1.2011.2.25.3.40.40.40.12383
    almOdu1Tcm3Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12383 }

--  1.3.6.1.4.1.2011.2.25.3.40.40.40.12394
    almOdu1Tcm2Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12394 }

--  1.3.6.1.4.1.2011.2.25.3.40.40.40.12395
    almOdu1Tcm3Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12395 }

--  1.3.6.1.4.1.2011.2.25.3.40.40.40.12396
    almOdu1Tcm4Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12396 }

--  1.3.6.1.4.1.2011.2.25.3.40.40.40.12397
    almOdu1Tcm5Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12397 }

--  1.3.6.1.4.1.2011.2.25.3.40.40.40.12398
    almOdu1Tcm6Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12398 }

--  1.3.6.1.4.1.2011.2.25.3.40.40.40.12399
    almOdu1Tcm1Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12399 }

--  1.3.6.1.4.1.2011.2.25.3.40.40.40.12447
    almOdu2Tcm1Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12447 }

--  1.3.6.1.4.1.2011.2.25.3.40.40.40.12448
    almOdu2Tcm2Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12448 }

--  1.3.6.1.4.1.2011.2.25.3.40.40.40.12449
    almOdu2Tcm3Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12449 }

--  1.3.6.1.4.1.2011.2.25.3.40.40.40.12450
    almOdu2Tcm4Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12450 }

--  1.3.6.1.4.1.2011.2.25.3.40.40.40.12451
    almOdu2Tcm5Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12451 }

--  1.3.6.1.4.1.2011.2.25.3.40.40.40.12452
    almOdu2Tcm6Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12452 }

--  1.3.6.1.4.1.2011.2.25.3.40.40.40.12453
    almOdu2Tcm1Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12453 }

--  1.3.6.1.4.1.2011.2.25.3.40.40.40.12454
    almOdu2Tcm2Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12454 }

--  1.3.6.1.4.1.2011.2.25.3.40.40.40.12455
    almOdu2Tcm3Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12455 }

--  1.3.6.1.4.1.2011.2.25.3.40.40.40.12456
    almOdu2Tcm4Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12456 }

--  1.3.6.1.4.1.2011.2.25.3.40.40.40.12457
    almOdu2Tcm5Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12457 }

--  1.3.6.1.4.1.2011.2.25.3.40.40.40.12458
    almOdu2Tcm6Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12458 }

--  1.3.6.1.4.1.2011.2.25.3.40.40.40.12459
    almOdu2Tcm1Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12459 }

--  1.3.6.1.4.1.2011.2.25.3.40.40.40.12460
    almOdu2Tcm2Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12460 }

--  1.3.6.1.4.1.2011.2.25.3.40.40.40.12461
    almOdu2Tcm3Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12461 }

--  1.3.6.1.4.1.2011.2.25.3.40.40.40.12462
    almOdu2Tcm4Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12462 }

--  1.3.6.1.4.1.2011.2.25.3.40.40.40.12463
    almOdu2Tcm5Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12463 }

--  1.3.6.1.4.1.2011.2.25.3.40.40.40.12464
    almOdu2Tcm6Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12464 }

--  1.3.6.1.4.1.2011.2.25.3.40.40.40.12465
    almOdu2Tcm1Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12465 }

--  1.3.6.1.4.1.2011.2.25.3.40.40.40.12466
    almOdu2Tcm2Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12466 }

--  1.3.6.1.4.1.2011.2.25.3.40.40.40.12467
    almOdu2Tcm3Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12467 }

--  1.3.6.1.4.1.2011.2.25.3.40.40.40.12468
    almOdu2Tcm4Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12468 }

--  1.3.6.1.4.1.2011.2.25.3.40.40.40.12469
    almOdu2Tcm5Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12469 }

--  1.3.6.1.4.1.2011.2.25.3.40.40.40.12470
    almOdu2Tcm6Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12470 }

--  1.3.6.1.4.1.2011.2.25.3.40.40.40.12471
    almOdu2Tcm1Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12471 }

--  1.3.6.1.4.1.2011.2.25.3.40.40.40.12472
    almOdu2Tcm2Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12472 }

--  1.3.6.1.4.1.2011.2.25.3.40.40.40.12473
    almOdu2Tcm3Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12473 }

--  1.3.6.1.4.1.2011.2.25.3.40.40.40.12474
    almOdu2Tcm4Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12474 }

--  1.3.6.1.4.1.2011.2.25.3.40.40.40.12475
    almOdu2Tcm5Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12475 }

--  1.3.6.1.4.1.2011.2.25.3.40.40.40.12476
    almOdu2Tcm6Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12476 }

--  1.3.6.1.4.1.2011.2.25.3.40.40.40.12477
    almOdu2Tcm1Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12477 }

--  1.3.6.1.4.1.2011.2.25.3.40.40.40.12478
    almOdu2Tcm2Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12478 }

--  1.3.6.1.4.1.2011.2.25.3.40.40.40.12479
    almOdu2Tcm3Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12479 }

--  1.3.6.1.4.1.2011.2.25.3.40.40.40.12480
    almOdu2Tcm4Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12480 }

--  1.3.6.1.4.1.2011.2.25.3.40.40.40.12481
    almOdu2Tcm5Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12481 }

--  1.3.6.1.4.1.2011.2.25.3.40.40.40.12482
    almOdu2Tcm6Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12482 }

--  1.3.6.1.4.1.2011.2.25.3.40.40.40.12483
    almOdu2Tcm1Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12483 }

--  1.3.6.1.4.1.2011.2.25.3.40.40.40.12484
    almOdu2Tcm2Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12484 }

--  1.3.6.1.4.1.2011.2.25.3.40.40.40.12485
    almOdu2Tcm3Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12485 }

--  1.3.6.1.4.1.2011.2.25.3.40.40.40.12486
    almOdu2Tcm4Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12486 }

--  1.3.6.1.4.1.2011.2.25.3.40.40.40.12487
    almOdu2Tcm5Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12487 }

--  1.3.6.1.4.1.2011.2.25.3.40.40.40.12488
    almOdu2Tcm6Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12488 }

--  1.3.6.1.4.1.2011.2.25.3.40.40.40.12489
    almOdu3Tcm1Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM1_TIM"
    ::= { trapsAlm 12489 }

--  1.3.6.1.4.1.2011.2.25.3.40.40.40.12490
    almOdu3Tcm2Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM2_TIM"
    ::= { trapsAlm 12490 }

--  1.3.6.1.4.1.2011.2.25.3.40.40.40.12491
    almOdu3Tcm3Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM3_TIM"
    ::= { trapsAlm 12491 }

--  1.3.6.1.4.1.2011.2.25.3.40.40.40.12492
    almOdu3Tcm4Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM4_TIM"
    ::= { trapsAlm 12492 }

--  1.3.6.1.4.1.2011.2.25.3.40.40.40.12493
    almOdu3Tcm5Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM5_TIM"
    ::= { trapsAlm 12493 }

--  1.3.6.1.4.1.2011.2.25.3.40.40.40.12494
    almOdu3Tcm6Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM6_TIM"
    ::= { trapsAlm 12494 }

--  1.3.6.1.4.1.2011.2.25.3.40.40.40.12495
    almOdu3Tcm1Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM1_DEG"
    ::= { trapsAlm 12495 }

--  1.3.6.1.4.1.2011.2.25.3.40.40.40.12496
    almOdu3Tcm2Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM2_DEG"
    ::= { trapsAlm 12496 }

--  1.3.6.1.4.1.2011.2.25.3.40.40.40.12497
    almOdu3Tcm3Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM3_DEG"
    ::= { trapsAlm 12497 }

--  1.3.6.1.4.1.2011.2.25.3.40.40.40.12498
    almOdu3Tcm4Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM4_DEG"
    ::= { trapsAlm 12498 }

--  1.3.6.1.4.1.2011.2.25.3.40.40.40.12499
    almOdu3Tcm5Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM5_DEG"
    ::= { trapsAlm 12499 }

--  1.3.6.1.4.1.2011.2.25.3.40.40.40.12500
    almOdu3Tcm6Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM6_DEG"
    ::= { trapsAlm 12500 }

--  1.3.6.1.4.1.2011.2.25.3.40.40.40.12501
    almOdu3Tcm1Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM1_BDI"
    ::= { trapsAlm 12501 }

--  1.3.6.1.4.1.2011.2.25.3.40.40.40.12502
    almOdu3Tcm2Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM2_BDI"
    ::= { trapsAlm 12502 }

--  1.3.6.1.4.1.2011.2.25.3.40.40.40.12503
    almOdu3Tcm3Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM3_BDI"
    ::= { trapsAlm 12503 }
--  1.3.6.1.4.1.2011.2.25.3.40.40.40.12504
    almOdu3Tcm4Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM4_BDI"
    ::= { trapsAlm 12504 }

--  1.3.6.1.4.1.2011.2.25.3.40.40.40.12505
    almOdu3Tcm5Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM5_BDI"
    ::= { trapsAlm 12505 }

--  1.3.6.1.4.1.2011.2.25.3.40.40.40.12506
    almOdu3Tcm6Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM6_BDI"
    ::= { trapsAlm 12506 }

--  1.3.6.1.4.1.2011.2.25.3.40.40.40.12507
    almOdu3Tcm1Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM1_AIS"
    ::= { trapsAlm 12507 }

--  1.3.6.1.4.1.2011.2.25.3.40.40.40.12508
    almOdu3Tcm2Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM2_AIS"
    ::= { trapsAlm 12508 }

--  1.3.6.1.4.1.2011.2.25.3.40.40.40.12509
    almOdu3Tcm3Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM3_AIS"
    ::= { trapsAlm 12509 }

--  1.3.6.1.4.1.2011.2.25.3.40.40.40.12510
    almOdu3Tcm4Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM4_AIS"
    ::= { trapsAlm 12510 }

--  1.3.6.1.4.1.2011.2.25.3.40.40.40.12511
    almOdu3Tcm5Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM5_AIS"
    ::= { trapsAlm 12511 }

--  1.3.6.1.4.1.2011.2.25.3.40.40.40.12512
    almOdu3Tcm6Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM6_AIS"
    ::= { trapsAlm 12512 }

--  1.3.6.1.4.1.2011.2.25.3.40.40.40.12513
    almOdu3Tcm1Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM1_OCI"
    ::= { trapsAlm 12513 }

--  1.3.6.1.4.1.2011.2.25.3.40.40.40.12514
    almOdu3Tcm2Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM2_OCI"
    ::= { trapsAlm 12514 }

--  1.3.6.1.4.1.2011.2.25.3.40.40.40.12515
    almOdu3Tcm3Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM3_OCI"
    ::= { trapsAlm 12515 }

--  1.3.6.1.4.1.2011.2.25.3.40.40.40.12516
    almOdu3Tcm4Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM4_OCI"
    ::= { trapsAlm 12516 }

--  1.3.6.1.4.1.2011.2.25.3.40.40.40.12517
    almOdu3Tcm5Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM5_OCI"
    ::= { trapsAlm 12517 }

--  1.3.6.1.4.1.2011.2.25.3.40.40.40.12518
    almOdu3Tcm6Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM6_OCI"
    ::= { trapsAlm 12518 }

--  1.3.6.1.4.1.2011.2.25.3.40.40.40.12519
    almOdu3Tcm1Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM1_LCK"
    ::= { trapsAlm 12519 }

--  1.3.6.1.4.1.2011.2.25.3.40.40.40.12520
    almOdu3Tcm2Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM2_LCK"
    ::= { trapsAlm 12520 }

--  1.3.6.1.4.1.2011.2.25.3.40.40.40.12521
    almOdu3Tcm3Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM3_LCK"
    ::= { trapsAlm 12521 }

--  1.3.6.1.4.1.2011.2.25.3.40.40.40.12522
    almOdu3Tcm4Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM4_LCK"
    ::= { trapsAlm 12522 }

--  1.3.6.1.4.1.2011.2.25.3.40.40.40.12523
    almOdu3Tcm5Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM5_LCK"
    ::= { trapsAlm 12523 }

--  1.3.6.1.4.1.2011.2.25.3.40.40.40.12524
    almOdu3Tcm6Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM6_LCK"
    ::= { trapsAlm 12524 }

--  1.3.6.1.4.1.2011.2.25.3.40.40.40.12525
    almOdu3Tcm1Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM1_LTC"
    ::= { trapsAlm 12525 }

--  1.3.6.1.4.1.2011.2.25.3.40.40.40.12526
    almOdu3Tcm2Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM2_LTC"
    ::= { trapsAlm 12526 }

--  1.3.6.1.4.1.2011.2.25.3.40.40.40.12527
    almOdu3Tcm3Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM3_LTC"
    ::= { trapsAlm 12527 }

--  1.3.6.1.4.1.2011.2.25.3.40.40.40.12528
    almOdu3Tcm4Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM4_LTC"
    ::= { trapsAlm 12528 }

--  1.3.6.1.4.1.2011.2.25.3.40.40.40.12529
    almOdu3Tcm5Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM5_LTC"
    ::= { trapsAlm 12529 }

--  1.3.6.1.4.1.2011.2.25.3.40.40.40.12530
    almOdu3Tcm6Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3_TCM6_LTC"
    ::= { trapsAlm 12530 }

--  1.3.6.1.4.1.2011.2.25.3.40.40.40.12531
    almOpu1Plm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OPUk payload mismatch"
    ::= { trapsAlm 12531 }

--  1.3.6.1.4.1.2011.2.25.3.40.40.40.12537
    almOlpPs NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Optical line protection switching"
    ::= { trapsAlm 12537 }

--  1.3.6.1.4.1.2011.2.25.3.40.40.40.12539
    almIntraOtuPs NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Intra-OTU 1+1 protection switching"
    ::= { trapsAlm 12539 }

--  1.3.6.1.4.1.2011.2.25.3.40.40.40.12541
    almOduSncpPs NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU SNCP protection switching"
    ::= { trapsAlm 12541 }

--  1.3.6.1.4.1.2011.2.25.3.40.40.40.12634
    almOchOci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when the downstream interrupt site receives the OCI signals inserted after proactive signal interrupt occurs in optical cross-connections"
    ::= { trapsAlm 12634 }

--  1.3.6.1.4.1.2011.2.25.3.40.40.40.12635
    almOchSsf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when both OCH_SSF-P and OCH_SSF-O are generated"
    ::= { trapsAlm 12635 }

--  1.3.6.1.4.1.2011.2.25.3.40.40.40.12636
    almOchSsfP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when the load signals at the OMS layer are lost or the OMS layer receives FDI-P signals from the OCh layer in the upstream"
    ::= { trapsAlm 12636 }
--  1.3.6.1.4.1.2011.2.25.3.40.40.40.12637
    almOchSsfO NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when the overhead signals at the OMS layer are lost or the OMS layer receives FDI-O signals from the OCh layer in the upstream"
    ::= { trapsAlm 12637 }

--  1.3.6.1.4.1.2011.2.25.3.40.40.40.12638
    almOchFdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when both OCH_FDI-P and OCH_FDI-O are generated"
    ::= { trapsAlm 12638 }

--  1.3.6.1.4.1.2011.2.25.3.40.40.40.12639
    almOchFdiP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when the downstream receives the OCH_FDI-P overhead signals inserted by the OMS layer after the OMS layer detects load LOS"
    ::= { trapsAlm 12639 }

--  1.3.6.1.4.1.2011.2.25.3.40.40.40.12711
    almOtu1Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTU1 Server Signal Fail"
    ::= { trapsAlm 12711 }

--  1.3.6.1.4.1.2011.2.25.3.40.40.40.12712
    almOdu1PmSsf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU1 PM Server Signal Fail"
    ::= { trapsAlm 12712 }

--  1.3.6.1.4.1.2011.2.25.3.40.40.40.12713
    almOdu1Tcm1Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU1 TCM1 Server Signal Fail"
    ::= { trapsAlm 12713 }

--  1.3.6.1.4.1.2011.2.25.3.40.40.40.12714
    almOdu1Tcm2Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU1 TCM2 Server Signal Fail"
    ::= { trapsAlm 12714 }

--  1.3.6.1.4.1.2011.2.25.3.40.40.40.12715
    almOdu1Tcm3Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU1 TCM3 Server Signal Fail"
    ::= { trapsAlm 12715 }

--  1.3.6.1.4.1.2011.2.25.3.40.40.40.12716
    almOdu1Tcm4Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU1 TCM4 Server Signal Fail"
    ::= { trapsAlm 12716 }

--  1.3.6.1.4.1.2011.2.25.3.40.40.40.12717
    almOdu1Tcm5Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU1 TCM5 Server Signal Fail"
    ::= { trapsAlm 12717 }

--  1.3.6.1.4.1.2011.2.25.3.40.40.40.12718
    almOdu1Tcm6Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU1 TCM6 Server Signal Fail"
    ::= { trapsAlm 12718 }

--  1.3.6.1.4.1.2011.2.25.3.40.40.40.12727
    almOtu2Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTU2 Server Signal Fail"
    ::= { trapsAlm 12727 }

--  1.3.6.1.4.1.2011.2.25.3.40.40.40.12729
    almOdu2Tcm1Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU2 TCM1 Server Signal Fail"
    ::= { trapsAlm 12729 }

--  1.3.6.1.4.1.2011.2.25.3.40.40.40.12730
    almOdu2Tcm2Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU2 TCM2 Server Signal Fail"
    ::= { trapsAlm 12730 }

--  1.3.6.1.4.1.2011.2.25.3.40.40.40.12731
    almOdu2Tcm3Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU2 TCM3 Server Signal Fail"
    ::= { trapsAlm 12731 }

--  1.3.6.1.4.1.2011.2.25.3.40.40.40.12732
    almOdu2Tcm4Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU2 TCM4 Server Signal Fail"
    ::= { trapsAlm 12732 }

--  1.3.6.1.4.1.2011.2.25.3.40.40.40.12733
    almOdu2Tcm5Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU2 TCM5 Server Signal Fail"
    ::= { trapsAlm 12733 }

--  1.3.6.1.4.1.2011.2.25.3.40.40.40.12734
    almOdu2Tcm6Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU2 TCM6 Server Signal Fail"
    ::= { trapsAlm 12734 }

--  1.3.6.1.4.1.2011.2.25.3.40.40.40.12735
    almOtu3Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OTU3 Server Signal Fail"
    ::= { trapsAlm 12735 }

--  1.3.6.1.4.1.2011.2.25.3.40.40.40.12737
    almOdu3Tcm1Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3 TCM1 Server Signal Fail"
    ::= { trapsAlm 12737 }

--  1.3.6.1.4.1.2011.2.25.3.40.40.40.12738
    almOdu3Tcm2Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3 TCM2 Server Signal Fail"
    ::= { trapsAlm 12738 }

--  1.3.6.1.4.1.2011.2.25.3.40.40.40.12739
    almOdu3Tcm3Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3 TCM3 Server Signal Fail"
    ::= { trapsAlm 12739 }

--  1.3.6.1.4.1.2011.2.25.3.40.40.40.12740
    almOdu3Tcm4Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3 TCM4 Server Signal Fail"
    ::= { trapsAlm 12740 }

--  1.3.6.1.4.1.2011.2.25.3.40.40.40.12741
    almOdu3Tcm5Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3 TCM5 Server Signal Fail"
    ::= { trapsAlm 12741 }

--  1.3.6.1.4.1.2011.2.25.3.40.40.40.12742
    almOdu3Tcm6Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU3 TCM6 Server Signal Fail"
    ::= { trapsAlm 12742 }

--  1.3.6.1.4.1.2011.2.25.3.40.40.40.12745
    almDcmInsuff NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "DCM_INSUFF"
    ::= { trapsAlm 12745 }

--  1.3.6.1.4.1.2011.2.25.3.40.40.40.12778
    almQValueExc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The alarm is generated when the Q value is greater than the threshold"
    ::= { trapsAlm 12778 }

--  1.3.6.1.4.1.2011.2.25.3.40.40.40.12843
    almOscLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OSC_LOS"
    ::= { trapsAlm 12843 }

--  1.3.6.1.4.1.2011.2.25.3.40.40.40.12956
    almLSync NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of  codeword synchronization at coding layer in incoming signal so as to stop receiving data"
    ::= { trapsAlm 12956 }

--  1.3.6.1.4.1.2011.2.25.3.40.40.40.12963
    almTimeNoTraceMode NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Precision clock is now working in freerun mode"
    ::= { trapsAlm 12963 }

--  1.3.6.1.4.1.2011.2.25.3.40.40.40.12964
    almTimeLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The timing source severity level is lost"
    ::= { trapsAlm 12964 }

--  1.3.6.1.4.1.2011.2.25.3.40.40.40.12972
    almExtTimeLoc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The EXT_TIME_LOC is an alarm indicating that the board detects no clock signal from the external clock source but the external clock port is enabled"
    ::= { trapsAlm 12972 }

--  1.3.6.1.4.1.2011.2.25.3.40.40.40.13423
    almRxPowerAbnormal NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The optical module demultiplexes one signal into multiple channels of optical signals and transmits them at the same time"
    ::= { trapsAlm 13423 }

--  1.3.6.1.4.1.2011.2.25.3.40.40.40.13506
    almLaserCheckErr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm indicates that the current optical module has a write/read error"
    ::= { trapsAlm 13506 }

--  1.3.6.1.4.1.2011.2.25.3.40.40.40.12792
    almSyncDisable NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "SYNC_DISABLE"
    ::= { trapsAlm 12792 }

--  1.3.6.1.4.1.2011.2.25.3.40.40.40.13044
    almCpcNodeIdErr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "During the startup, when the node ID in the system parameter area is null or is different from the node ID saved in the database (if such a node ID exists in the database), the ASON software cannot be normally enabled and the alarm is reported"
    ::= { trapsAlm 13044 }

--  1.3.6.1.4.1.2011.2.25.3.40.40.40.13055
    almOdu0PmTim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 PM section TTI mismatch"
    ::= { trapsAlm 13055 }
--  1.3.6.1.4.1.2011.2.25.3.40.40.40.13066
    almOpu0Plm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OPU0 payload mismatch"
    ::= { trapsAlm 13066 }

--  1.3.6.1.4.1.2011.2.25.3.40.40.40.13070
    almServiceTypeExceedLicense NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The alarm indicates that the type of configured services exceeds the license limit"
    ::= { trapsAlm 13070 }

--  1.3.6.1.4.1.2011.2.25.3.40.40.40.13071
    almServiceCapacityExceedLicense NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The alarm indicates that the capacity of configured services exceeds the license limit"
    ::= { trapsAlm 13071 }

--  1.3.6.1.4.1.2011.2.25.3.40.40.40.13082
    almOpu0Csf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Client-side signals fail"
    ::= { trapsAlm 13082 }

--  1.3.6.1.4.1.2011.2.25.3.40.40.40.13083
    almOpu1Csf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Client-side signals fail"
    ::= { trapsAlm 13083 }

--  1.3.6.1.4.1.2011.2.25.3.40.40.40.13146
    almLcsDaysOfGrace NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The license has expired and is within the keepalive period of 60 days"
    ::= { trapsAlm 13146 }

--  1.3.6.1.4.1.2011.2.25.3.40.40.40.13194
    almPtpSourceSwitch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "When the ID of the Grandmaster source traced by the NE or the tracing port changes, this alarm is reported to remind the user of switchover of the IEEE 1588v2 tracing source"
    ::= { trapsAlm 13194 }

--  1.3.6.1.4.1.2011.2.25.3.40.40.40.13195
    almClkLockFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "When the frequency of an NE is synchronized from the upstream,the frequency lock status is locking"
    ::= { trapsAlm 13195 }

--  1.3.6.1.4.1.2011.2.25.3.40.40.40.13196
    almTimeLockFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "When the time of an NE is synchronized from the upstream,the time lock status is locking"
    ::= { trapsAlm 13196 }

--  1.3.6.1.4.1.2011.2.25.3.40.40.40.13210
    almOdu4Tcm2Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU4 TCM2 Server Signal Fail"
    ::= { trapsAlm 13210 }

--  1.3.6.1.4.1.2011.2.25.3.40.40.40.13211
    almOdu4Tcm3Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU4 TCM3 Server Signal Fail"
    ::= { trapsAlm 13211 }

--  1.3.6.1.4.1.2011.2.25.3.40.40.40.13212
    almOdu4Tcm4Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU4 TCM4 Server Signal Fail"
    ::= { trapsAlm 13212 }

--  1.3.6.1.4.1.2011.2.25.3.40.40.40.13213
    almOdu4Tcm5Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU4 TCM5 Server Signal Fail"
    ::= { trapsAlm 13213 }

--  1.3.6.1.4.1.2011.2.25.3.40.40.40.13214
    almOdu4Tcm6Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU4 TCM6 Server Signal Fail"
    ::= { trapsAlm 13214 }

--  1.3.6.1.4.1.2011.2.25.3.40.40.40.13216
    almOdu4Tcm1Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 13216 }

--  1.3.6.1.4.1.2011.2.25.3.40.40.40.13217
    almOdu4Tcm2Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 13217 }

--  1.3.6.1.4.1.2011.2.25.3.40.40.40.13218
    almOdu4Tcm3Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 13218 }

--  1.3.6.1.4.1.2011.2.25.3.40.40.40.13219
    almOdu4Tcm4Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 13219 }

--  1.3.6.1.4.1.2011.2.25.3.40.40.40.13220
    almOdu4Tcm5Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 13220 }

--  1.3.6.1.4.1.2011.2.25.3.40.40.40.13221
    almOdu4Tcm6Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 13221 }

--  1.3.6.1.4.1.2011.2.25.3.40.40.40.13223
    almOdu4Tcm1Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 13223 }

--  1.3.6.1.4.1.2011.2.25.3.40.40.40.13224
    almOdu4Tcm2Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 13224 }

--  1.3.6.1.4.1.2011.2.25.3.40.40.40.13225
    almOdu4Tcm3Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 13225 }

--  1.3.6.1.4.1.2011.2.25.3.40.40.40.13226
    almOdu4Tcm4Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 13226 }

--  1.3.6.1.4.1.2011.2.25.3.40.40.40.13227
    almOdu4Tcm5Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 13227 }

--  1.3.6.1.4.1.2011.2.25.3.40.40.40.13228
    almOdu4Tcm6Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 13228 }

--  1.3.6.1.4.1.2011.2.25.3.40.40.40.13230
    almOdu4Tcm1Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 13230 }

--  1.3.6.1.4.1.2011.2.25.3.40.40.40.13231
    almOdu4Tcm2Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 13231 }

--  1.3.6.1.4.1.2011.2.25.3.40.40.40.13232
    almOdu4Tcm3Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 13232 }

--  1.3.6.1.4.1.2011.2.25.3.40.40.40.13233
    almOdu4Tcm4Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 13233 }

--  1.3.6.1.4.1.2011.2.25.3.40.40.40.13234
    almOdu4Tcm5Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 13234 }

--  1.3.6.1.4.1.2011.2.25.3.40.40.40.13235
    almOdu4Tcm6Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 13235 }

--  1.3.6.1.4.1.2011.2.25.3.40.40.40.13236
    almOdu4Tcm1Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13236 }

--  1.3.6.1.4.1.2011.2.25.3.40.40.40.13237
    almOdu4Tcm2Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13237 }

--  1.3.6.1.4.1.2011.2.25.3.40.40.40.13238
    almOdu4Tcm3Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13238 }

--  1.3.6.1.4.1.2011.2.25.3.40.40.40.13239
    almOdu4Tcm4Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13239 }

--  1.3.6.1.4.1.2011.2.25.3.40.40.40.13240
    almOdu4Tcm5Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13240 }

--  1.3.6.1.4.1.2011.2.25.3.40.40.40.13241
    almOdu4Tcm6Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13241 }

--  1.3.6.1.4.1.2011.2.25.3.40.40.40.13243
    almOdu4Tcm1Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 13243 }

--  1.3.6.1.4.1.2011.2.25.3.40.40.40.13244
    almOdu4Tcm2Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 13244 }

--  1.3.6.1.4.1.2011.2.25.3.40.40.40.13245
    almOdu4Tcm3Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 13245 }

--  1.3.6.1.4.1.2011.2.25.3.40.40.40.13246
    almOdu4Tcm4Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 13246 }

--  1.3.6.1.4.1.2011.2.25.3.40.40.40.13247
    almOdu4Tcm5Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 13247 }

--  1.3.6.1.4.1.2011.2.25.3.40.40.40.13248
    almOdu4Tcm6Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 13248 }

--  1.3.6.1.4.1.2011.2.25.3.40.40.40.13250
    almOdu4Tcm1Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 13250 }

--  1.3.6.1.4.1.2011.2.25.3.40.40.40.13251
    almOdu4Tcm2Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 13251 }
--  1.3.6.1.4.1.2011.2.25.3.40.40.40.13252
    almOdu4Tcm3Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 13252 }

--  1.3.6.1.4.1.2011.2.25.3.40.40.40.13253
    almOdu4Tcm4Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 13253 }

--  1.3.6.1.4.1.2011.2.25.3.40.40.40.13254
    almOdu4Tcm5Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 13254 }

--  1.3.6.1.4.1.2011.2.25.3.40.40.40.13255
    almOdu4Tcm6Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 13255 }

--  1.3.6.1.4.1.2011.2.25.3.40.40.40.13264
    almOdu4Tcm1Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 13264 }

--  1.3.6.1.4.1.2011.2.25.3.40.40.40.13265
    almOdu4Tcm2Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 13265 }

--  1.3.6.1.4.1.2011.2.25.3.40.40.40.13266
    almOdu4Tcm3Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 13266 }

--  1.3.6.1.4.1.2011.2.25.3.40.40.40.13267
    almOdu4Tcm4Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 13267 }

--  1.3.6.1.4.1.2011.2.25.3.40.40.40.13268
    almOdu4Tcm5Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 13268 }

--  1.3.6.1.4.1.2011.2.25.3.40.40.40.13269
    almOdu4Tcm6Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 13269 }

--  1.3.6.1.4.1.2011.2.25.3.40.40.40.13310
    almOpuflexPlm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OPUk payload mismatch"
    ::= { trapsAlm 13310 }

--  1.3.6.1.4.1.2011.2.25.3.40.40.40.13311
    almOduflexPmSsf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODUFlex PM layer signals fail"
    ::= { trapsAlm 13311 }

--  1.3.6.1.4.1.2011.2.25.3.40.40.40.13322
    almOdu0Tcm1Ais  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk alarm indication signal"
    ::= { trapsAlm 13322 }

--  1.3.6.1.4.1.2011.2.25.3.40.40.40.13323
    almOdu0Tcm1Lck  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal locked"
    ::= { trapsAlm 13323 }

--  1.3.6.1.4.1.2011.2.25.3.40.40.40.13324
    almOdu0Tcm1Oci  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk open connection indication"
    ::= { trapsAlm 13324 }

--  1.3.6.1.4.1.2011.2.25.3.40.40.40.13325
    almOdu0Tcm1Ltc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13325 }

--  1.3.6.1.4.1.2011.2.25.3.40.40.40.13326
    almOdu0Tcm1Deg  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal degraded"
    ::= { trapsAlm 13326 }

--  1.3.6.1.4.1.2011.2.25.3.40.40.40.13327
    almOdu0Tcm1Exc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODU0 TCMk section exceeds the threshold"
    ::= { trapsAlm 13327 }

--  1.3.6.1.4.1.2011.2.25.3.40.40.40.13338
    almOdu0Tcm3Tim  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13338 }

--  1.3.6.1.4.1.2011.2.25.3.40.40.40.13339
    almOdu0Tcm3Bdi  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk backward defect indication"
    ::= { trapsAlm 13339 }

--  1.3.6.1.4.1.2011.2.25.3.40.40.40.13340
    almOdu0Tcm3Ais  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk alarm indication signal"
    ::= { trapsAlm 13340 }

--  1.3.6.1.4.1.2011.2.25.3.40.40.40.13341
    almOdu0Tcm3Lck  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal locked"
    ::= { trapsAlm 13341 }

--  1.3.6.1.4.1.2011.2.25.3.40.40.40.13342
    almOdu0Tcm3Oci  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk open connection indication"
    ::= { trapsAlm 13342 }

--  1.3.6.1.4.1.2011.2.25.3.40.40.40.13343
    almOdu0Tcm3Ltc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13343 }

--  1.3.6.1.4.1.2011.2.25.3.40.40.40.13354
    almOdu0Tcm4Exc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODU0 TCMk section exceeds the threshold"
    ::= { trapsAlm 13354 }

--  1.3.6.1.4.1.2011.2.25.3.40.40.40.13355
    almOdu0Tcm4Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODU0 TCMk layer signal failure alarm"
    ::= { trapsAlm 13355 }

--  1.3.6.1.4.1.2011.2.25.3.40.40.40.13356
    almOdu0Tcm5Tim  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13356 }

--  1.3.6.1.4.1.2011.2.25.3.40.40.40.13357
    almOdu0Tcm5Bdi  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk backward defect indication"
    ::= { trapsAlm 13357 }

--  1.3.6.1.4.1.2011.2.25.3.40.40.40.13358
    almOdu0Tcm5Ais  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk alarm indication signal"
    ::= { trapsAlm 13358 }

--  1.3.6.1.4.1.2011.2.25.3.40.40.40.13359
    almOdu0Tcm5Lck  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal locked"
    ::= { trapsAlm 13359 }

--  1.3.6.1.4.1.2011.2.25.3.40.40.40.13370
    almOdu0Tcm6Ltc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13370 }

--  1.3.6.1.4.1.2011.2.25.3.40.40.40.13371
    almOdu0Tcm6Deg  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal degraded"
    ::= { trapsAlm 13371 }

--  1.3.6.1.4.1.2011.2.25.3.40.40.40.13372
    almOdu0Tcm6Exc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODU0 TCMk section exceeds the threshold"
    ::= { trapsAlm 13372 }

--  1.3.6.1.4.1.2011.2.25.3.40.40.40.13373
    almOdu0Tcm6Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODU0 TCMk layer signal failure alarm"
    ::= { trapsAlm 13373 }

--  1.3.6.1.4.1.2011.2.25.3.40.40.40.13434
    almOpuflexCsf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Client-side signals fail"
    ::= { trapsAlm 13434 }

--  1.3.6.1.4.1.2011.2.25.3.40.40.40.13487
    almFopNr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "After transmitting an APS command request, the local end does not receive any RRs or APS command quests from the peer end within 1s"
    ::= { trapsAlm 13487 }

--  1.3.6.1.4.1.2011.2.25.3.40.40.40.13488
    almFopPr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Information in the received APS frame and the type of APS protection configured at the local end are inconsistent"
    ::= { trapsAlm 13488 }

--  1.3.6.1.4.1.2011.2.25.3.40.40.40.13542
    almNoBdPower NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm indicates that the board is not powered on"
    ::= { trapsAlm 13542 }

--  1.3.6.1.4.1.2011.2.25.3.40.40.40.13565
    almOduflexTcm4Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODUFLEX TCMk layer signal failure alarm"
    ::= { trapsAlm 13565 }

--  1.3.6.1.4.1.2011.2.25.3.40.40.40.13566
    almOduflexTcm4Exc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODUFLEX TCMk section exceeds the threshold"
    ::= { trapsAlm 13566 }

--  1.3.6.1.4.1.2011.2.25.3.40.40.40.13567
    almOduflexTcm4Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13567 }

--  1.3.6.1.4.1.2011.2.25.3.40.40.40.13578
    almOduflexTcm5Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13578 }

--  1.3.6.1.4.1.2011.2.25.3.40.40.40.13579
    almOduflexTcm5Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal degraded"
    ::= { trapsAlm 13579 }

--  1.3.6.1.4.1.2011.2.25.3.40.40.40.13580
    almOduflexTcm5Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13580 }

--  1.3.6.1.4.1.2011.2.25.3.40.40.40.13581
    almOduflexTcm5Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk backward defect indication"
    ::= { trapsAlm 13581 }

--  1.3.6.1.4.1.2011.2.25.3.40.40.40.13582
    almOduflexTcm5Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk alarm indication signal"
    ::= { trapsAlm 13582 }
--  1.3.6.1.4.1.2011.2.25.3.40.40.40.13583
    almOduflexTcm6Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13583 }

--  1.3.6.1.4.1.2011.2.25.3.40.40.40.13594
    almOduflexTcm3Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk alarm indication signal"
    ::= { trapsAlm 13594 }

--  1.3.6.1.4.1.2011.2.25.3.40.40.40.13595
    almOduflexTcm3Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal degraded"
    ::= { trapsAlm 13595 }

--  1.3.6.1.4.1.2011.2.25.3.40.40.40.13596
    almOduflexTcm3Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13596 }

--  1.3.6.1.4.1.2011.2.25.3.40.40.40.13597
    almOduflexTcm3Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk open connection indication"
    ::= { trapsAlm 13597 }

--  1.3.6.1.4.1.2011.2.25.3.40.40.40.13598
    almOduflexTcm3Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal locked"
    ::= { trapsAlm 13598 }

--  1.3.6.1.4.1.2011.2.25.3.40.40.40.13599
    almOduflexTcm3Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODUFLEX TCMk layer signal failure alarm"
    ::= { trapsAlm 13599 }

--  1.3.6.1.4.1.2011.2.25.3.40.40.40.13610
    almOduflexTcm1Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13610 }
	
--  1.3.6.1.4.1.2011.2.25.3.40.40.40.13611
    almOduflexTcm1Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk backward defect indication"
    ::= { trapsAlm 13611 }

--  1.3.6.1.4.1.2011.2.25.3.40.40.40.13612
    almOduflexTcm1Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk alarm indication signal"
    ::= { trapsAlm 13612 }

--  1.3.6.1.4.1.2011.2.25.3.40.40.40.13613
    almOduflexTcm1Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal locked"
    ::= { trapsAlm 13613 }

--  1.3.6.1.4.1.2011.2.25.3.40.40.40.13614
    almOduflexTcm1Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk backward defect indication"
    ::= { trapsAlm 13614 }

--  1.3.6.1.4.1.2011.2.25.3.40.40.40.13615
    almOduflexTcm1Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13615 }

--  1.3.6.1.4.1.2011.2.25.3.40.40.40.13690
    almCfpLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when no sigal is input to the receive end of the channel on the CFP module"
    ::= { trapsAlm 13690 }

--  1.3.6.1.4.1.2011.2.25.3.40.40.40.13693
    almPtpAnnounceLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the Slave port does not receive any Announce packet within the specified period"
    ::= { trapsAlm 13693 }

--  1.3.6.1.4.1.2011.2.25.3.40.40.40.13694
    almPtpSyncLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the Slave port does not receive any SYNC packet within the specified period"
    ::= { trapsAlm 13694 }

--  1.3.6.1.4.1.2011.2.25.3.40.40.40.13695
    almPtpDelayRespLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the port in P2P mode does not receive any Delay_RESP packet within the specified period"
    ::= { trapsAlm 13695 }

--  1.3.6.1.4.1.2011.2.25.3.40.40.40.13706
    almOchmLosP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The OCHM_LOS_P alarm is reported when an OTU board detects a LOS but no LOS or FDI, OCI alarm is preset at the upper layer"
    ::= { trapsAlm 13706 }

--  1.3.6.1.4.1.2011.2.25.3.40.40.40.13707
    almOchmOci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The OCHM_OCI alarm is actively inserted downstream during optical cross-connection configuration"
    ::= { trapsAlm 13707 }

--  1.3.6.1.4.1.2011.2.25.3.40.40.40.13708
    almOchmSsf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The OCHM_SSF alarm is reported when the OCHM_SSF-P and OCHM_SSF-O alarms are present at the same time and suppresses the latter two alarms"
    ::= { trapsAlm 13708 }

--  1.3.6.1.4.1.2011.2.25.3.40.40.40.13709
    almOchmSsfP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The OCHM_SSF_P alarm is reported when the signal payload at the OMS layer is lost or an OChM-layer FDI-P signal is transmitted from the upstream board/site"
    ::= { trapsAlm 13709 }
--  1.3.6.1.4.1.2011.2.25.3.40.40.40.13710
    almOchmSsfO NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The OCHM_SSF_O alarm is reported when the signal overhead at the OMS layer is lost or an OChM-layer FDI-O signal is transmitted from the upstream board/site"
    ::= { trapsAlm 13710 }

--  1.3.6.1.4.1.2011.2.25.3.40.40.40.13711
    almOchmFdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The OCHM_FDI alarm is reported when the OCHM_FDI-P and OCHM_FDI-O alarms are present at the same time and suppresses the latter two alarms"
    ::= { trapsAlm 13711 }

--  1.3.6.1.4.1.2011.2.25.3.40.40.40.13726
    almCfgDatasaveFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the configuration is saved to the database"
    ::= { trapsAlm 13726 }

--  1.3.6.1.4.1.2011.2.25.3.40.40.40.13727
    almCfgDatacheckFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The database will be checked during the NE running"
    ::= { trapsAlm 13727 }

--  1.3.6.1.4.1.2011.2.25.3.40.40.40.13951
    almLaserTypeMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The LASER_TYPE_MISMATCH alarm is an alarm indicating mismatch of optical module types"
    ::= { trapsAlm 13951 }

--  1.3.6.1.4.1.2011.2.25.3.40.40.40.13962
    almMpnOppositeCfgErr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The?MPN configuration of the peer NE is incorrect"
    ::= { trapsAlm 13962 }

--  1.3.6.1.4.1.2011.2.25.3.40.40.40.13963
    almMpnApsStop NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The?automatic switching protocol of MPN protection is stopped"
    ::= { trapsAlm 13963 }

--  1.3.6.1.4.1.2011.2.25.3.40.40.40.13964
    almXcpDegrade NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the external switching command that affects the automatic switching of cross-connect boards is delivered or the active or standby cross-connect board is faulty"
    ::= { trapsAlm 13964 }

--  1.3.6.1.4.1.2011.2.25.3.40.40.40.13978
    almLaserParaErr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The LSR_PARA_ERR alarm is an alarm indicating that the parameter stored in the optical module is missing or incorrect"
    ::= { trapsAlm 13978 }

--  1.3.6.1.4.1.2011.2.25.3.40.40.40.13987
    almAmbientTempFluct NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when the ambient temperature of the subrack is fluctuation over 15°"
    ::= { trapsAlm 13987 }

--  1.3.6.1.4.1.2011.2.25.3.40.40.40.14090
    almCpldUpdating NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The board CPLD is being upgraded"
    ::= { trapsAlm 14090 }

--  1.3.6.1.4.1.2011.2.25.3.40.40.40.14092
    almSdiCrcExc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the software detects that the number of bytes in SDI CRC error frames has exceeded the threshold"
    ::= { trapsAlm 14092 }

--  1.3.6.1.4.1.2011.2.25.3.40.40.40.14093
    almOduSncpNotHitless NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The alarm is reported when the ODU SNCP protection group loses hitless protection"
    ::= { trapsAlm 14093 }

--  1.3.6.1.4.1.2011.2.25.3.40.40.40.14142
    almPwrCurrentNoEqual NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Power output current unbalance"
    ::= { trapsAlm 14142 }

--  1.3.6.1.4.1.2011.2.25.3.40.40.40.14143
    almBdInMaintenance NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The board in the maintenance state will be isolated, and the maintenance personnel can perform maintenance operations"
    ::= { trapsAlm 14143 }

--  1.3.6.1.4.1.2011.2.25.3.40.40.40.41987
    almShelfWrongConnect NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The network cables between subracks are incorrectly connected (that is, the network cables are cross-connected)"
    ::= { trapsAlm 41987 }

--  1.3.6.1.4.1.2011.2.25.3.40.40.40.63635
    almThunderAlm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Thunder protection circuit failure alarm"
    ::= { trapsAlm 63635 }


	
--  1.3.6.1.4.1.2011.2.25.3.40.40.40.12341
    almOdu1Loflom NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk frame and multiframe"
    ::= { trapsAlm 12341 }

--  1.3.6.1.4.1.2011.2.25.3.40.40.40.12368
    almOdu1Tcm6Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn TTI mismatch"
    ::= { trapsAlm 12368 }

--  1.3.6.1.4.1.2011.2.25.3.40.40.40.12369
    almOdu1Tcm1Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12369 }

--  1.3.6.1.4.1.2011.2.25.3.40.40.40.12370
    almOdu1Tcm2Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12370 }

--  1.3.6.1.4.1.2011.2.25.3.40.40.40.12371
    almOdu1Tcm3Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12371 }

--  1.3.6.1.4.1.2011.2.25.3.40.40.40.12372
    almOdu1Tcm4Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12372 }

--  1.3.6.1.4.1.2011.2.25.3.40.40.40.12373
    almOdu1Tcm5Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12373 }

--  1.3.6.1.4.1.2011.2.25.3.40.40.40.12374
    almOdu1Tcm6Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal degraded"
    ::= { trapsAlm 12374 }

--  1.3.6.1.4.1.2011.2.25.3.40.40.40.12375
    almOdu1Tcm1Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12375 }

--  1.3.6.1.4.1.2011.2.25.3.40.40.40.12376
    almOdu1Tcm2Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12376 }

--  1.3.6.1.4.1.2011.2.25.3.40.40.40.12377
    almOdu1Tcm3Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn backward defect indication"
    ::= { trapsAlm 12377 }

--  1.3.6.1.4.1.2011.2.25.3.40.40.40.12384
    almOdu1Tcm4Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12384 }

--  1.3.6.1.4.1.2011.2.25.3.40.40.40.12385
    almOdu1Tcm5Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12385 }

--  1.3.6.1.4.1.2011.2.25.3.40.40.40.12386
    almOdu1Tcm6Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn alarm indication signal"
    ::= { trapsAlm 12386 }

--  1.3.6.1.4.1.2011.2.25.3.40.40.40.12387
    almOdu1Tcm1Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12387 }

--  1.3.6.1.4.1.2011.2.25.3.40.40.40.12388
    almOdu1Tcm2Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12388 }

--  1.3.6.1.4.1.2011.2.25.3.40.40.40.12389
    almOdu1Tcm3Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12389 }

--  1.3.6.1.4.1.2011.2.25.3.40.40.40.12390
    almOdu1Tcm4Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12390 }

--  1.3.6.1.4.1.2011.2.25.3.40.40.40.12391
    almOdu1Tcm5Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12391 }

--  1.3.6.1.4.1.2011.2.25.3.40.40.40.12392
    almOdu1Tcm6Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn open connection indication"
    ::= { trapsAlm 12392 }

--  1.3.6.1.4.1.2011.2.25.3.40.40.40.12393
    almOdu1Tcm1Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk TCMn signal locked"
    ::= { trapsAlm 12393 }

--  1.3.6.1.4.1.2011.2.25.3.40.40.40.12400
    almOdu1Tcm2Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12400 }

--  1.3.6.1.4.1.2011.2.25.3.40.40.40.12401
    almOdu1Tcm3Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12401 }
--  1.3.6.1.4.1.2011.2.25.3.40.40.40.12402
    almOdu1Tcm4Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12402 }

--  1.3.6.1.4.1.2011.2.25.3.40.40.40.12403
    almOdu1Tcm5Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12403 }

--  1.3.6.1.4.1.2011.2.25.3.40.40.40.12404
    almOdu1Tcm6Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 12404 }

--  1.3.6.1.4.1.2011.2.25.3.40.40.40.12596
    almOpaFailIndi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Automatic adjustment of power during optical cross-connection failed"
    ::= { trapsAlm 12596 }

--  1.3.6.1.4.1.2011.2.25.3.40.40.40.12633
    almOchLosP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "12633"
    ::= { trapsAlm 12633 }

--  1.3.6.1.4.1.2011.2.25.3.40.40.40.12640
    almOchFdiO NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when the downstream receives the OCH_FDI-O overhead signals inserted by the OMS layer after the OMS layer detects overhead LOS"
    ::= { trapsAlm 12640 }

--  1.3.6.1.4.1.2011.2.25.3.40.40.40.12641
    almOdukspPs NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "12641"
    ::= { trapsAlm 12641 }

--  1.3.6.1.4.1.2011.2.25.3.40.40.40.13154
    almOdcDoorOpen NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The cabinet door is open"
    ::= { trapsAlm 13154 }

--  1.3.6.1.4.1.2011.2.25.3.40.40.40.12914
    almSsmQlFailed NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "It must be able to configure a minimum SSM-QL related to the special port with SyncE timing input"
    ::= { trapsAlm 12914 }

--  1.3.6.1.4.1.2011.2.25.3.40.40.40.12917
    almSsmLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "If no valid SSM is received during 5 seconds, a Loss_Of_SSM defect is detected"
    ::= { trapsAlm 12917 }

--  1.3.6.1.4.1.2011.2.25.3.40.40.40.13056
    almOdu0PmDeg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "odu0 PM signal degraded"
    ::= { trapsAlm 13056 }

--  1.3.6.1.4.1.2011.2.25.3.40.40.40.13057
    almOdu0PmBdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "odu0 PM backward defect indication"
    ::= { trapsAlm 13057 }

--  1.3.6.1.4.1.2011.2.25.3.40.40.40.13058
    almOdu0PmLck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 PM signal locked"
    ::= { trapsAlm 13058 }

--  1.3.6.1.4.1.2011.2.25.3.40.40.40.13059
    almOdu0PmOci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk PM open connection indication"
    ::= { trapsAlm 13059 }

--  1.3.6.1.4.1.2011.2.25.3.40.40.40.13060
    almOdu0PmAis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUk PM alarm indication signal"
    ::= { trapsAlm 13060 }

--  1.3.6.1.4.1.2011.2.25.3.40.40.40.13061
    almOdu0Loflom NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk frame and multiframe"
    ::= { trapsAlm 13061 }

--  1.3.6.1.4.1.2011.2.25.3.40.40.40.13062
    almOdu0PmSsf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODU0 PM layer signal failure alarm"
    ::= { trapsAlm 13062 }

--  1.3.6.1.4.1.2011.2.25.3.40.40.40.13063
    almOpu1Msim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OPU1 multiplex structure indicator mismatch"
    ::= { trapsAlm 13063 }

--  1.3.6.1.4.1.2011.2.25.3.40.40.40.13079
    almShelfAreaPowerOver NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when the total power consumption of the boards of each partition of the subrack is higher or equal to the power consumption threshold for each partition"
    ::= { trapsAlm 13079 }

--  1.3.6.1.4.1.2011.2.25.3.40.40.40.13136
    almOdukspStaIndi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Indicates the state of the ODUk SPRing protection group"
    ::= { trapsAlm 13136 }

--  1.3.6.1.4.1.2011.2.25.3.40.40.40.13137
    almOlpStaIndi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Indicates the state of the optical line protection group"
    ::= { trapsAlm 13137 }

--  1.3.6.1.4.1.2011.2.25.3.40.40.40.13140
    almIntraOtuStaIndi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Indicates the state of the intra-OTU 1+1 optical channel protection group"
    ::= { trapsAlm 13140 }

--  1.3.6.1.4.1.2011.2.25.3.40.40.40.13142
    almOduSncpStaIndi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Indicates the state of the ODU SNCP protection group"
    ::= { trapsAlm 13142 }

--  1.3.6.1.4.1.2011.2.25.3.40.40.40.13144
    almLcsFileNotExist NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The system is under license control but a license file is not loaded onto the system"
    ::= { trapsAlm 13144 }

--  1.3.6.1.4.1.2011.2.25.3.40.40.40.13145
    almLcsExpired NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The license has expired and the keepalive period of 60 days has also elapsed"
    ::= { trapsAlm 13145 }

--  1.3.6.1.4.1.2011.2.25.3.40.40.40.13170
    almFeatureWithoutLicense NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "A license-controlled feature is used but a license for the feature is not installed"
    ::= { trapsAlm 13170 }

--  1.3.6.1.4.1.2011.2.25.3.40.40.40.13185
    almOscDeg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Signal degraded alarm"
    ::= { trapsAlm 13185 }

--  1.3.6.1.4.1.2011.2.25.3.40.40.40.13186
    almOscBdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Backward defect indication"
    ::= { trapsAlm 13186 }

--  1.3.6.1.4.1.2011.2.25.3.40.40.40.13188
    almPtpTimestampAbn NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "When the PTP (IEEE 1588v2) time stamp freezes, this alarm is reported"
    ::= { trapsAlm 13188 }

--  1.3.6.1.4.1.2011.2.25.3.40.40.40.13209
    almOdu4Tcm1Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU4 TCM1 Server Signal Fail"
    ::= { trapsAlm 13209 }
--  1.3.6.1.4.1.2011.2.25.3.40.40.40.13312
    almOduflexPmTim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFlex PM section TTI mismatch"
    ::= { trapsAlm 13312 }

--  1.3.6.1.4.1.2011.2.25.3.40.40.40.13313
    almOduflexPmDeg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFlex PM signal degraded"
    ::= { trapsAlm 13313 }

--  1.3.6.1.4.1.2011.2.25.3.40.40.40.13314
    almOduflexPmBdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFlex PM backward defect indication"
    ::= { trapsAlm 13314 }

--  1.3.6.1.4.1.2011.2.25.3.40.40.40.13315
    almOduflexPmLck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFlex PM signal locked"
    ::= { trapsAlm 13315 }

--  1.3.6.1.4.1.2011.2.25.3.40.40.40.13316
    almOduflexPmOci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFlex PM open connection indication"
    ::= { trapsAlm 13316 }

--  1.3.6.1.4.1.2011.2.25.3.40.40.40.13317
    almOduflexPmAis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFlex PM alarm indication signal"
    ::= { trapsAlm 13317 }

--  1.3.6.1.4.1.2011.2.25.3.40.40.40.13318
    almOduflexLoflom NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUFlex frame and multiframe"
    ::= { trapsAlm 13318 }

--  1.3.6.1.4.1.2011.2.25.3.40.40.40.13319
    almOduflexPmExc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODUFlex PM section exceeds the threshold"
    ::= { trapsAlm 13319 }

--  1.3.6.1.4.1.2011.2.25.3.40.40.40.13320
    almOdu0Tcm1Tim  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13320 }

--  1.3.6.1.4.1.2011.2.25.3.40.40.40.13321
    almOdu0Tcm1Bdi  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk backward defect indication"
    ::= { trapsAlm 13321 }

--  1.3.6.1.4.1.2011.2.25.3.40.40.40.13328
    almOdu0Tcm1Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODU0 TCMk layer signal failure alarm"
    ::= { trapsAlm 13328 }

--  1.3.6.1.4.1.2011.2.25.3.40.40.40.13329
    almOdu0Tcm2Tim  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13329 }

--  1.3.6.1.4.1.2011.2.25.3.40.40.40.13330
    almOdu0Tcm2Bdi  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCM1 backward defect indication"
    ::= { trapsAlm 13330 }
--  1.3.6.1.4.1.2011.2.25.3.40.40.40.13331
    almOdu0Tcm2Ais  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCM2 alarm indication signal"
    ::= { trapsAlm 13331 }

--  1.3.6.1.4.1.2011.2.25.3.40.40.40.13332
    almOdu0Tcm2Lck  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal locked"
    ::= { trapsAlm 13332 }

--  1.3.6.1.4.1.2011.2.25.3.40.40.40.13333
    almOdu0Tcm2Oci  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk open connection indication"
    ::= { trapsAlm 13333 }

--  1.3.6.1.4.1.2011.2.25.3.40.40.40.13334
    almOdu0Tcm2Ltc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13334 }

--  1.3.6.1.4.1.2011.2.25.3.40.40.40.13335
    almOdu0Tcm2Deg  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal degraded"
    ::= { trapsAlm 13335 }

--  1.3.6.1.4.1.2011.2.25.3.40.40.40.13336
    almOdu0Tcm2Exc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODU0 TCMk section exceeds the threshold"
    ::= { trapsAlm 13336 }

--  1.3.6.1.4.1.2011.2.25.3.40.40.40.13337
    almOdu0Tcm2Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODU0 TCMk layer signal failure alarm"
    ::= { trapsAlm 13337 }

--  1.3.6.1.4.1.2011.2.25.3.40.40.40.13344
    almOdu0Tcm3Deg  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal degraded"
    ::= { trapsAlm 13344 }

--  1.3.6.1.4.1.2011.2.25.3.40.40.40.13345
    almOdu0Tcm3Exc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODU0 TCMk section exceeds the threshold"
    ::= { trapsAlm 13345 }

--  1.3.6.1.4.1.2011.2.25.3.40.40.40.13346
    almOdu0Tcm3Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODU0 TCMk layer signal failure alarm"
    ::= { trapsAlm 13346 }

--  1.3.6.1.4.1.2011.2.25.3.40.40.40.13347
    almOdu0Tcm4Tim  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13347 }

--  1.3.6.1.4.1.2011.2.25.3.40.40.40.13348
    almOdu0Tcm4Bdi  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk backward defect indication"
    ::= { trapsAlm 13348 }

--  1.3.6.1.4.1.2011.2.25.3.40.40.40.13349
    almOdu0Tcm4Ais  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk alarm indication signal"
    ::= { trapsAlm 13349 }

--  1.3.6.1.4.1.2011.2.25.3.40.40.40.13350
    almOdu0Tcm4Lck  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal locked"
    ::= { trapsAlm 13350 }

--  1.3.6.1.4.1.2011.2.25.3.40.40.40.13351
    almOdu0Tcm4Oci  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk open connection indication"
    ::= { trapsAlm 13351 }
--  1.3.6.1.4.1.2011.2.25.3.40.40.40.13352
    almOdu0Tcm4Ltc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13352 }

--  1.3.6.1.4.1.2011.2.25.3.40.40.40.13353
    almOdu0Tcm4Deg  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal degraded"
    ::= { trapsAlm 13353 }

--  1.3.6.1.4.1.2011.2.25.3.40.40.40.13360
    almOdu0Tcm5Oci  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk open connection indication"
    ::= { trapsAlm 13360 }

--  1.3.6.1.4.1.2011.2.25.3.40.40.40.13361
    almOdu0Tcm5Ltc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13361 }

--  1.3.6.1.4.1.2011.2.25.3.40.40.40.13362
    almOdu0Tcm5Deg  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal degraded"
    ::= { trapsAlm 13362 }

--  1.3.6.1.4.1.2011.2.25.3.40.40.40.13363
    almOdu0Tcm5Exc  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODU0 TCMk section exceeds the threshold"
    ::= { trapsAlm 13363 }

--  1.3.6.1.4.1.2011.2.25.3.40.40.40.13364
    almOdu0Tcm5Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODU0 TCMk layer signal failure alarm"
    ::= { trapsAlm 13364 }

--  1.3.6.1.4.1.2011.2.25.3.40.40.40.13365
    almOdu0Tcm6Tim  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13365 }

--  1.3.6.1.4.1.2011.2.25.3.40.40.40.13366
    almOdu0Tcm6Bdi  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk backward defect indication"
    ::= { trapsAlm 13366 }

--  1.3.6.1.4.1.2011.2.25.3.40.40.40.13367
    almOdu0Tcm6Ais  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk alarm indication signal"
    ::= { trapsAlm 13367 }

--  1.3.6.1.4.1.2011.2.25.3.40.40.40.13368
    almOdu0Tcm6Lck  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk signal locked"
    ::= { trapsAlm 13368 }

--  1.3.6.1.4.1.2011.2.25.3.40.40.40.13369
    almOdu0Tcm6Oci  NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODU0 TCMk open connection indication"
    ::= { trapsAlm 13369 }

--  1.3.6.1.4.1.2011.2.25.3.40.40.40.13443
    almModuleRateMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The module does not support the speed-up mode"
    ::= { trapsAlm 13443 }

--  1.3.6.1.4.1.2011.2.25.3.40.40.40.13568
    almOduflexTcm4Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal degraded"
    ::= { trapsAlm 13568 }

--  1.3.6.1.4.1.2011.2.25.3.40.40.40.13569
    almOduflexTcm4Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal locked"
    ::= { trapsAlm 13569 }

--  1.3.6.1.4.1.2011.2.25.3.40.40.40.13570
    almOduflexTcm4Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk open connection indication"
    ::= { trapsAlm 13570 }

--  1.3.6.1.4.1.2011.2.25.3.40.40.40.13571
    almOduflexTcm4Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk backward defect indication"
    ::= { trapsAlm 13571 }

--  1.3.6.1.4.1.2011.2.25.3.40.40.40.13572
    almOduflexTcm4Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk alarm indication signal"
    ::= { trapsAlm 13572 }

--  1.3.6.1.4.1.2011.2.25.3.40.40.40.13573
    almOduflexTcm4Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13573 }

--  1.3.6.1.4.1.2011.2.25.3.40.40.40.13574
    almOduflexTcm5Exc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODUFLEX TCMk section exceeds the threshold"
    ::= { trapsAlm 13574 }

--  1.3.6.1.4.1.2011.2.25.3.40.40.40.13575
    almOduflexTcm5Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODUFLEX TCMk layer signal failure alarm"
    ::= { trapsAlm 13575 }

--  1.3.6.1.4.1.2011.2.25.3.40.40.40.13576
    almOduflexTcm5Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal locked"
    ::= { trapsAlm 13576 }
--  1.3.6.1.4.1.2011.2.25.3.40.40.40.14088
    almPatchMatchNoStart NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the system control board does not launch a board patch match for specific reasons"
    ::= { trapsAlm 14088 }

--  1.3.6.1.4.1.2011.2.25.3.40.40.40.14089
    almCpldNeedUpdate NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The board CPLD needs to be upgraded"
    ::= { trapsAlm 14089 }

--  1.3.6.1.4.1.2011.2.25.3.40.40.40.14102
    almDcnChannelBiterror NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The DCN_CHANNEL_BITERROR alarm indicates bit errors on the DCN channel, which may cause DCN communication interruption"
    ::= { trapsAlm 14102 }
--  1.3.6.1.4.1.2011.2.25.3.40.40.40.13953
    almOduSncpWeak NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the working and protection channels of a protection group are configured on the same OTU board, but it is not reported when ASON services are configured"
    ::= { trapsAlm 13953 }

--  1.3.6.1.4.1.2011.2.25.3.40.40.40.13961
    almMpnApsIndi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm indicates the status of an MPN protection group"
    ::= { trapsAlm 13961 }

--  1.3.6.1.4.1.2011.2.25.3.40.40.40.14081
    almSplitInstFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when a logical 5"
    ::= { trapsAlm 14081 }
--  1.3.6.1.4.1.2011.2.25.3.40.40.40.13925
    almBdRateMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Rate mismatching of a service board and cross-connect board"
    ::= { trapsAlm 13925 }

--  1.3.6.1.4.1.2011.2.25.3.40.40.40.13926
    almTpmSelfTestFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The TPM fails to test its hardware"
    ::= { trapsAlm 13926 }

--  1.3.6.1.4.1.2011.2.25.3.40.40.40.13927
    almTpmStmMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "TPM_STM_MISMATCH is reported when the measurement result is different from the benchmark"
    ::= { trapsAlm 13927 }
--  1.3.6.1.4.1.2011.2.25.3.40.40.40.13670
    almAmbientTempOver NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is generated when the ambient temperature of the subrack is too high or too low"
    ::= { trapsAlm 13670 }

--  1.3.6.1.4.1.2011.2.25.3.40.40.40.13671
    almOpu0Msim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OPU0 multiplex structure identifier mismatch"
    ::= { trapsAlm 13671 }

--  1.3.6.1.4.1.2011.2.25.3.40.40.40.13672
    almOpuflexMsim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OPUFLEX multiplex structure identifier mismatch"
    ::= { trapsAlm 13672 }

--  1.3.6.1.4.1.2011.2.25.3.40.40.40.13686
    almOpucnMsim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "OPUCn multiplex structure indicator mismatch"
    ::= { trapsAlm 13686 }

--  1.3.6.1.4.1.2011.2.25.3.40.40.40.13696
    almPtpPdelayRespLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the port in P2P mode does not receive any PDelay_RESP packet within the specified period"
    ::= { trapsAlm 13696 }

--  1.3.6.1.4.1.2011.2.25.3.40.40.40.13697
    almPtpClkclassFailed NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the CLOCKCLASS value received by a port exceeds the specified threshold"
    ::= { trapsAlm 13697 }

--  1.3.6.1.4.1.2011.2.25.3.40.40.40.13712
    almOchmFdiP NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "When a payload LOS is detected at the OMS layer, an OCHM_FDI-P signal is inserted downstream"
    ::= { trapsAlm 13712 }

--  1.3.6.1.4.1.2011.2.25.3.40.40.40.13713
    almOchmFdiO NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "When an overhead LOS is detected at the OMS layer, an OCHM_FDI-O signal is inserted downstream"
    ::= { trapsAlm 13713 }

--  1.3.6.1.4.1.2011.2.25.3.40.40.40.13714
    almSwdlBdWeakmatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "This alarm is reported when the software of boards on an NE weakly matches the NE software"
    ::= { trapsAlm 13714 }
--  1.3.6.1.4.1.2011.2.25.3.40.40.40.13616
    almOduflexTcm1Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal degraded"
    ::= { trapsAlm 13616 }

--  1.3.6.1.4.1.2011.2.25.3.40.40.40.13617
    almOduflexTcm1Exc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODUFLEX TCMk section exceeds the threshold"
    ::= { trapsAlm 13617 }

--  1.3.6.1.4.1.2011.2.25.3.40.40.40.13618
    almOduflexTcm1Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODUFLEX TCMk layer signal failure alarm"
    ::= { trapsAlm 13618 }

--  1.3.6.1.4.1.2011.2.25.3.40.40.40.13621
    almFopPm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The B bit values in the transmitted and received APS bytes are different"
    ::= { trapsAlm 13621 }

--  1.3.6.1.4.1.2011.2.25.3.40.40.40.13640
    almRLol NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of lane alignment on receiving line"
    ::= { trapsAlm 13640 }

--  1.3.6.1.4.1.2011.2.25.3.40.40.40.13657
    almBdBpxcMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The board access capability mismatches the cross-connect capacity of the backplane in the subrack"
    ::= { trapsAlm 13657 }
--  1.3.6.1.4.1.2011.2.25.3.40.40.40.13605
    almOduflexTcm2Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk backward defect indication"
    ::= { trapsAlm 13605 }

--  1.3.6.1.4.1.2011.2.25.3.40.40.40.13606
    almOduflexTcm2Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13606 }

--  1.3.6.1.4.1.2011.2.25.3.40.40.40.13607
    almOduflexTcm2Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal degraded"
    ::= { trapsAlm 13607 }

--  1.3.6.1.4.1.2011.2.25.3.40.40.40.13608
    almOduflexTcm2Exc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODUFLEX TCMk section exceeds the threshold"
    ::= { trapsAlm 13608 }

--  1.3.6.1.4.1.2011.2.25.3.40.40.40.13609
    almOduflexTcm2Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODUFLEX TCMk layer signal failure alarm"
    ::= { trapsAlm 13609 }
--  1.3.6.1.4.1.2011.2.25.3.40.40.40.13603
    almOduflexTcm2Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk alarm indication signal"
    ::= { trapsAlm 13603 }

--  1.3.6.1.4.1.2011.2.25.3.40.40.40.13604
    almOduflexTcm2Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal locked"
    ::= { trapsAlm 13604 }
	
--  1.3.6.1.4.1.2011.2.25.3.40.40.40.13602
    almOduflexTcm2Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk backward defect indication"
    ::= { trapsAlm 13602 }	

--  1.3.6.1.4.1.2011.2.25.3.40.40.40.13601
    almOduflexTcm2Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13601 }
--  1.3.6.1.4.1.2011.2.25.3.40.40.40.13577
    almOduflexTcm5Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk open connection indication"
    ::= { trapsAlm 13577 }

--  1.3.6.1.4.1.2011.2.25.3.40.40.40.13584
    almOduflexTcm6Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal locked"
    ::= { trapsAlm 13584 }

--  1.3.6.1.4.1.2011.2.25.3.40.40.40.13585
    almOduflexTcm6Oci NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk open connection indication"
    ::= { trapsAlm 13585 }

--  1.3.6.1.4.1.2011.2.25.3.40.40.40.13586
    almOduflexTcm6Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk backward defect indication"
    ::= { trapsAlm 13586 }

--  1.3.6.1.4.1.2011.2.25.3.40.40.40.13587
    almOduflexTcm6Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk alarm indication signal"
    ::= { trapsAlm 13587 }

--  1.3.6.1.4.1.2011.2.25.3.40.40.40.13588
    almOduflexTcm6Exc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODUFLEX TCMk section exceeds the threshold"
    ::= { trapsAlm 13588 }

--  1.3.6.1.4.1.2011.2.25.3.40.40.40.13589
    almOduflexTcm6Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The ODUFLEX TCMk layer signal failure alarm"
    ::= { trapsAlm 13589 }

--  1.3.6.1.4.1.2011.2.25.3.40.40.40.13590
    almOduflexTcm6Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Loss of ODUk TCMn serial connection"
    ::= { trapsAlm 13590 }


--  1.3.6.1.4.1.2011.2.25.3.40.40.40.13591
    almOduflexTcm6Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk signal degraded"
    ::= { trapsAlm 13591 }

--  1.3.6.1.4.1.2011.2.25.3.40.40.40.13592
    almOduflexTcm3Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Identifiers (API) in the input signals and the expected API"
    ::= { trapsAlm 13592 }

--  1.3.6.1.4.1.2011.2.25.3.40.40.40.13593
    almOduflexTcm3Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "ODUFLEX TCMk backward defect indication"
    ::= { trapsAlm 13593 }

--  1.3.6.1.4.1.2011.2.25.3.40.40.40.13600
    almOduflexTcm3Exc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "The number of BIP8 bit errors in the ODUFLEX TCMk section exceeds the threshold"
    ::= { trapsAlm 13600 }
	
--  1.3.6.1.4.1.2011.2.25.3.40.40.40.6
    almNoBdSoft NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: No board software"
    ::= { trapsAlm  6}
--  1.3.6.1.4.1.2011.2.25.3.40.40.40.9
    almTf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Laser transmission Failure"
    ::= { trapsAlm  9}
--  1.3.6.1.4.1.2011.2.25.3.40.40.40.28
    almTempOver NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Board working temperature over threshold"
    ::= { trapsAlm  28}

--  1.3.6.1.4.1.2011.2.25.3.40.40.40.29
    almTempHigh NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Laser temperature is too high"
    ::= { trapsAlm  29}

--  1.3.6.1.4.1.2011.2.25.3.40.40.40.30
    almTempLow NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Laser temperature is too low"
    ::= { trapsAlm  30}

--  1.3.6.1.4.1.2011.2.25.3.40.40.40.31
    almInPwrHigh NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Input optical power is too high"
    ::= { trapsAlm  31}

--  1.3.6.1.4.1.2011.2.25.3.40.40.40.32
    almInPwrLow NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Input optical power is too low"
    ::= { trapsAlm  32}
--  1.3.6.1.4.1.2011.2.25.3.40.40.40.56
    almLsrWillDie NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Laser will be out of work"
    ::= { trapsAlm  56}
--  1.3.6.1.4.1.2011.2.25.3.40.40.40.63
    almOutPwrHigh NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Output optical power too high"
    ::= { trapsAlm  63}

--  1.3.6.1.4.1.2011.2.25.3.40.40.40.64
    almOtuPwrLow NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Output optical power too low "
    ::= { trapsAlm  64}
--  1.3.6.1.4.1.2011.2.25.3.40.40.40.115
    almFanFail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Fan failure"
    ::= { trapsAlm  115}  
--  1.3.6.1.4.1.2011.2.25.3.40.40.40.119
    almBdStatus NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: board offline except main control board"
    ::= { trapsAlm  119}
--  1.3.6.1.4.1.2011.2.25.3.40.40.40.121
    almWrgBdType NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Wrong board type"
    ::= { trapsAlm  121}

--  1.3.6.1.4.1.2011.2.25.3.40.40.40.125
    almPwrFail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Power failure"
    ::= { trapsAlm  125}
--  1.3.6.1.4.1.2011.2.25.3.40.40.40.185
    almDBErr NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Data base error"
    ::= { trapsAlm  185}
--  1.3.6.1.4.1.2011.2.25.3.40.40.40.189
    almTd NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Laser transmitter degrade"
    ::= { trapsAlm  189}
--  1.3.6.1.4.1.2011.2.25.3.40.40.40.198
    almProtectMode NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Databases in protection mode"
    ::= { trapsAlm  198}

--  1.3.6.1.4.1.2011.2.25.3.40.40.40.199
    almCommFail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Inter-board communication failure"
    ::= { trapsAlm  199}

--  1.3.6.1.4.1.2011.2.25.3.40.40.40.200
    almSecuAlm NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Security alarm"
    ::= { trapsAlm  200}
--  1.3.6.1.4.1.2011.2.25.3.40.40.40.236
    almHardBad  NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm:  This alarm occurs when a hardware exception is detected "
    ::= { trapsAlm  236}

--  1.3.6.1.4.1.2011.2.25.3.40.40.40.240
    almLoopback NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Loopback"
    ::= { trapsAlm  240}

--  1.3.6.1.4.1.2011.2.25.3.40.40.40.256
    almFanCommFail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: The communication of fans fails"
    ::= { trapsAlm  256}
--  1.3.6.1.4.1.2011.2.25.3.40.40.40.335
    almBeffecExc NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Bit errors over threshold before FEC"
    ::= { trapsAlm  335}
--  1.3.6.1.4.1.2011.2.25.3.40.40.40.573
    almActiveTimeout NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Activation time out"
    ::= { trapsAlm  573}

--  1.3.6.1.4.1.2011.2.25.3.40.40.40.574
    almSwdlNepkgcheck NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Loss of file"
    ::= { trapsAlm  574}

--  1.3.6.1.4.1.2011.2.25.3.40.40.40.575
    almSwdlChgmngMismatch NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: NE software and the board software do not match"
    ::= { trapsAlm  575}

--  1.3.6.1.4.1.2011.2.25.3.40.40.40.584
    almBootRomBad NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: BOOTROM_CheckSum_Alarm"
    ::= { trapsAlm  584}
--  1.3.6.1.4.1.2011.2.25.3.40.40.40.606
    almLaserModuleMismatch NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Laser module is mismatch"
    ::= { trapsAlm  606}
--  1.3.6.1.4.1.2011.2.25.3.40.40.40.624
    almRtcFault NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: RTC time fail alarm"
    ::= { trapsAlm  624}

--  1.3.6.1.4.1.2011.2.25.3.40.40.40.625
    almBDNotInstalled NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Logic board not installed"
    ::= { trapsAlm  625}

--  1.3.6.1.4.1.2011.2.25.3.40.40.40.2569
    almSWDLPkgNoBDSoft NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: No board software in the software package"
    ::= { trapsAlm  2569}

--  1.3.6.1.4.1.2011.2.25.3.40.40.40.2570
    almRollBackFail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: NE rollback failed"
    ::= { trapsAlm  2570}

--  1.3.6.1.4.1.2011.2.25.3.40.40.40.2571
    almCommitFail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Commit failure"
    ::= { trapsAlm  2571}

--  1.3.6.1.4.1.2011.2.25.3.40.40.40.2572
    almSWDLInProcess NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Software downloading in process"
    ::= { trapsAlm  2572}

--  1.3.6.1.4.1.2011.2.25.3.40.40.40.2573
    almSwdlPkgverMisMatch NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Inconsistency of software package versions"
    ::= { trapsAlm  2573}

--  1.3.6.1.4.1.2011.2.25.3.40.40.40.2574
    almSwdlAutoMatchInh NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Automatic match inhibited"
    ::= { trapsAlm  2574}
--  1.3.6.1.4.1.2011.2.25.3.40.40.40.12302
    almShelfIdConflict NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Subrack ID conflict"
    ::= { trapsAlm  12302}
--  1.3.6.1.4.1.2011.2.25.3.40.40.40.12304
    almShelfLoop NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Subrack forming a loop"
    ::= { trapsAlm  12304}
--  1.3.6.1.4.1.2011.2.25.3.40.40.40.12309
    almSingleFanFail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Fan fault"
    ::= { trapsAlm  12309}
--  1.3.6.1.4.1.2011.2.25.3.40.40.40.12349
    almOdu2PMTim NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU2 PM trace identifier mismatch"
    ::= { trapsAlm  12349}

--  1.3.6.1.4.1.2011.2.25.3.40.40.40.12350
    almOdu2PMDeg NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU2 PM signal degrade alarm"
    ::= { trapsAlm  12350}

--  1.3.6.1.4.1.2011.2.25.3.40.40.40.12351
    almOdu2PMBdi NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU2 PM backward defect indication"
    ::= { trapsAlm  12351}

--  1.3.6.1.4.1.2011.2.25.3.40.40.40.12352
    almOdu2PMLck NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU2 PM locked defect"
    ::= { trapsAlm  12352}

--  1.3.6.1.4.1.2011.2.25.3.40.40.40.12353
    almOdu2PMOci NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU2 PM open connection indication"
    ::= { trapsAlm  12353}

--  1.3.6.1.4.1.2011.2.25.3.40.40.40.12354
    almOdu2PMAis NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU2 PM alarm indication signal"
    ::= { trapsAlm  12354}

--  1.3.6.1.4.1.2011.2.25.3.40.40.40.12355
    almOdu2Loflom NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU2 PM loss of frame and multi-frame"
    ::= { trapsAlm  12355}

--  1.3.6.1.4.1.2011.2.25.3.40.40.40.12356
    almOdu3PMTim NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU3 PM trace identifier mismatch"
    ::= { trapsAlm  12356}

--  1.3.6.1.4.1.2011.2.25.3.40.40.40.12357
    almOdu3PMDeg NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU3 PM signal degrade alarm"
    ::= { trapsAlm  12357}

--  1.3.6.1.4.1.2011.2.25.3.40.40.40.12358
    almOdu3PMBdi NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU3 PM backward defect indication"
    ::= { trapsAlm  12358}

--  1.3.6.1.4.1.2011.2.25.3.40.40.40.12359
    almOdu3PMLck NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU3 PM locked defect"
    ::= { trapsAlm  12359}

--  1.3.6.1.4.1.2011.2.25.3.40.40.40.12360
    almOdu3PMOci NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU3 PM open connection indication"
    ::= { trapsAlm  12360}

--  1.3.6.1.4.1.2011.2.25.3.40.40.40.12361
    almOdu3PMAis NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU3 PM alarm indication signal"
    ::= { trapsAlm  12361}

--  1.3.6.1.4.1.2011.2.25.3.40.40.40.13680
    almOducnPmAis NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "ODUCn PM alarm indication signal"
    ::= { trapsAlm  13680}

--  1.3.6.1.4.1.2011.2.25.3.40.40.40.13681
    almOducnPmSsf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "ODUCn PM Server Signal Fail"
    ::= { trapsAlm  13681}

--  1.3.6.1.4.1.2011.2.25.3.40.40.40.13682
    almOducnPmBdi NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "ODUCn PM backward defect indication"
    ::= { trapsAlm  13682}

--  1.3.6.1.4.1.2011.2.25.3.40.40.40.13683
    almOducnPmDeg NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "ODUCn PM section excessive BIP8 errors"
    ::= { trapsAlm  13683}

--  1.3.6.1.4.1.2011.2.25.3.40.40.40.13684
    almOducnPmTim NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "ODUCn PM trace identifier mismatch"
    ::= { trapsAlm  13684}

--  1.3.6.1.4.1.2011.2.25.3.40.40.40.299
    almRmonAlmInbadoctsOver NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Rmon Alm Inbadocts Over"
    ::= { trapsAlm  299}

--  1.3.6.1.4.1.2011.2.25.3.40.40.40.12532
--  1.3.6.1.4.1.2011.2.25.3.40.40.40.12533
    almOpu2Plm NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OPU2 payload label mismatch "
    ::= { trapsAlm  12533}

--  1.3.6.1.4.1.2011.2.25.3.40.40.40.12534
    almOpu2Msim NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OPU2 multiplex structure identifier mismatch"
    ::= { trapsAlm  12534}

--  1.3.6.1.4.1.2011.2.25.3.40.40.40.12535
    almOpu3Plm NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OPU3 payload label mismatch"
    ::= { trapsAlm  12535}

--  1.3.6.1.4.1.2011.2.25.3.40.40.40.12536
    almOpu3Msim NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OPU3 multiplex structure identifier mismatch"
    ::= { trapsAlm  12536}

--  1.3.6.1.4.1.2011.2.25.3.40.40.40.12540
    almClientPortPs NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Client-side 1+1 optical channel protection switching"
    ::= { trapsAlm  12540}

--  1.3.6.1.4.1.2011.2.25.3.40.40.40.12542
--  1.3.6.1.4.1.2011.2.25.3.40.40.40.12543
--  1.3.6.1.4.1.2011.2.25.3.40.40.40.12544
    almRemoteFault NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Remote fault"
    ::= { trapsAlm  12544}

--  1.3.6.1.4.1.2011.2.25.3.40.40.40.12545
    almLocalFault NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Local fault"
    ::= { trapsAlm  12545}

--  1.3.6.1.4.1.2011.2.25.3.40.40.40.12580
    almHardErr NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Hardware error "
    ::= { trapsAlm  12580}

--  1.3.6.1.4.1.2011.2.25.3.40.40.40.12581
    almElabelLost NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: No e-label."
    ::= { trapsAlm  12581}

--  1.3.6.1.4.1.2011.2.25.3.40.40.40.12582
    almLptActive NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: LPT switching occurred. "
    ::= { trapsAlm  12582}

--  1.3.6.1.4.1.2011.2.25.3.40.40.40.12595
    almClientPortNotStart NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: The alarm raises when the client-side 1+1 optical channel protection cannot start"
    ::= { trapsAlm  12595}

--  1.3.6.1.4.1.2011.2.25.3.40.40.40.12643
    almPrbsLss NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Loss of PRBS(Pseudo-Random Binary Sequence) signal"
    ::= { trapsAlm  12643}

--  1.3.6.1.4.1.2011.2.25.3.40.40.40.12728
    almOdu2PMSsf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU2 PM Server Signal Fail"
    ::= { trapsAlm  12728}

--  1.3.6.1.4.1.2011.2.25.3.40.40.40.12736
    almOdu3PMSsf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU3 PM Server Signal Fail"
    ::= { trapsAlm  12736}

--  1.3.6.1.4.1.2011.2.25.3.40.40.40.12790
    almPatchPkgErr NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Patch package file error"
    ::= { trapsAlm  12790}

--  1.3.6.1.4.1.2011.2.25.3.40.40.40.12884
    almStormCurQuenumOver NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Alarm Storm "
    ::= { trapsAlm  12884}

--  1.3.6.1.4.1.2011.2.25.3.40.40.40.12921
--  1.3.6.1.4.1.2011.2.25.3.40.40.40.12929
    almNullSend NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: NULL sending enable"
    ::= { trapsAlm  12929}

--  1.3.6.1.4.1.2011.2.25.3.40.40.40.12973
    almShelfTypeMismatch NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Subrack type mismatch"
    ::= { trapsAlm  12973}

--  1.3.6.1.4.1.2011.2.25.3.40.40.40.13047
    almPasswordneedchange NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: The default user's default password must be changed to reduce risks"
    ::= { trapsAlm  13047}

--  1.3.6.1.4.1.2011.2.25.3.40.40.40.13049
    almComexteccfull NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm:  Number of TCP connections between NEs running the automatically extended ECC protocol exceeding the system limit"
    ::= { trapsAlm  13049}	
    
--  1.3.6.1.4.1.2011.2.25.3.40.40.40.13051
    almWavedataMis NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: WAVEDATA_MIS"
    ::= { trapsAlm  13051}

--  1.3.6.1.4.1.2011.2.25.3.40.40.40.13139
    almClientPortStaIndi NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Client-side 1+1 optical channel protection status indication"
    ::= { trapsAlm  13139}

--  1.3.6.1.4.1.2011.2.25.3.40.40.40.13309
    almOpu2Csf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Client-side signals fail"
    ::= { trapsAlm  13309}

--  1.3.6.1.4.1.2011.2.25.3.40.40.40.13412
    almAlsActive NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: AlsActive"
    ::= { trapsAlm  13412}

--  1.3.6.1.4.1.2011.2.25.3.40.40.40.13419
    almBdLedTest NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Board LED Flash Test"
    ::= { trapsAlm  13419}

--  1.3.6.1.4.1.2011.2.25.3.40.40.40.13435
    almOpu3Csf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Client-side signals fail"
    ::= { trapsAlm  13435}

--  1.3.6.1.4.1.2011.2.25.3.40.40.40.13436
    almOpu4Csf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Client-side signals fail"
    ::= { trapsAlm  13436}

--  1.3.6.1.4.1.2011.2.25.3.40.40.40.13502
    almDbmsDelete NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: NE database deletion"
    ::= { trapsAlm  13502}

--  1.3.6.1.4.1.2011.2.25.3.40.40.40.13514
    almSslcertnoenc NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Certificate file of SSL is not encrypted"
    ::= { trapsAlm  13514}

-- 1.3.6.1.4.1.2011.2.25.3.40.40.40.13622
	almEthHiBer NOTIFICATION-TYPE
		OBJECTS { rptEvtNumber, rptAlmName, rptEvtNtfcnCde, rptEvtState, rptEvtStartTime, 
        rptEvtEndTime, rptEvtSrvEff, rptEvtObjType, rptEvtPara}
    STATUS current
    DESCRIPTION 
		"Trap of Alarm: 40GE/100GE BIP8 error threshold crossing."
	::= { trapsAlm 13622 }

-- 1.3.6.1.4.1.2011.2.25.3.40.40.40.13623
	almEthBip8Sd NOTIFICATION-TYPE
		OBJECTS { rptEvtNumber, rptAlmName, rptEvtNtfcnCde, rptEvtState, rptEvtStartTime, 
        rptEvtEndTime, rptEvtSrvEff, rptEvtObjType, rptEvtPara}
    STATUS current
    DESCRIPTION 
		"Trap of Alarm: 40GE/100GE signal degrade."
	::= { trapsAlm 13623 }

--  1.3.6.1.4.1.2011.2.25.3.40.40.40.13673
    almSwdlBdMatchFail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: The SWDL_BD_MATCH_FAIL is an alarm indicating that a board fails to match the board software."
    ::= { trapsAlm  13673} 

-- 1.3.6.1.4.1.2011.2.25.3.40.40.40.13735
	almSwdlBDNotMatch NOTIFICATION-TYPE
		OBJECTS { rptEvtNumber, rptAlmName, rptEvtNtfcnCde, rptEvtState, rptEvtStartTime, 
        rptEvtEndTime, rptEvtSrvEff, rptEvtObjType, rptEvtPara}
    STATUS current
    DESCRIPTION 
		"Trap of Alarm: Board software mismatched."
	::= { trapsAlm 13735 }

--  1.3.6.1.4.1.2011.2.25.3.40.40.40.63604
    almRemSf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Remote Singal Unequip"
    ::= { trapsAlm  63604}

--  1.3.6.1.4.1.2011.2.25.3.40.40.40.63605
    almRemSd NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Remote Singal Degrade Alarm Indication"
    ::= { trapsAlm  63605}

--  1.3.6.1.4.1.2011.2.25.3.40.40.40.63629
    almPortOffline NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Port module offline"
    ::= { trapsAlm  63629}

--  1.3.6.1.4.1.2011.2.25.3.40.40.40.63644
    almLaserModErrEx NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: almLaserModErrEx"
    ::= { trapsAlm  63644}

--  1.3.6.1.4.1.2011.2.25.3.40.40.40.13125
    almntpsyncfail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: NTP synchronization failure"
    ::= { trapsAlm  13125}

--  1.3.6.1.4.1.2011.2.25.3.40.40.40.12586
    almsyslogcommfail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Communication failure between NE and syslog server"
    ::= { trapsAlm  12586}

--  1.3.6.1.4.1.2011.2.25.3.40.40.40.13169
   almSecradiusfail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
       "Trap of Alarm: Illegal RADIUS login"
   ::= { trapsAlm 13169}

--  1.3.6.1.4.1.2011.2.25.3.40.40.40.13190
   almSwdlbdexclude NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
       "Trap of Alarm:Boards excluded from the software package upgrade"
   ::= { trapsAlm 13190}     

--  1.3.6.1.4.1.2011.2.25.3.40.40.40.12926
    almLanloc NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Ethernet communication failure. The alarm occurs when the external Ethernet communication and the network port fail"
    ::= { trapsAlm  12926}

--  1.3.6.1.4.1.2011.2.25.3.40.40.40.13201
    almotu4ssf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OTU4 Server Signal Fail"
    ::= { trapsAlm  13201}

--  1.3.6.1.4.1.2011.2.25.3.40.40.40.13202
    almotu4ais NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OTU4 alarm indication signal"
    ::= { trapsAlm  13202}

--  1.3.6.1.4.1.2011.2.25.3.40.40.40.13203
    almotu4lof NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Loss of OTU4 frame"
    ::= { trapsAlm  13203}

--  1.3.6.1.4.1.2011.2.25.3.40.40.40.13204
    almotu4lom NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Loss of OTU4 multiframe"
    ::= { trapsAlm  13204}

--  1.3.6.1.4.1.2011.2.25.3.40.40.40.13205
    almotu4Tim NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OTU4 trace identifier mismatch"
    ::= { trapsAlm  13205}

--  1.3.6.1.4.1.2011.2.25.3.40.40.40.13206
    almotu4Deg NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OTU4 signal degrade"
    ::= { trapsAlm  13206}

--  1.3.6.1.4.1.2011.2.25.3.40.40.40.13207
    almotu4Bdi NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OTU4 backward alarm indication"
    ::= { trapsAlm  13207}

--  1.3.6.1.4.1.2011.2.25.3.40.40.40.13208
    almOdu4PMSsf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU4 PM Server Signal Fail"
    ::= { trapsAlm  13208}      

--  1.3.6.1.4.1.2011.2.25.3.40.40.40.13215
    almOdu4PMAis NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU4 PM alarm indication signal"
    ::= { trapsAlm  13215}       

--  1.3.6.1.4.1.2011.2.25.3.40.40.40.13222
    almOdu4PMOci NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU4 PM open connection indication"
    ::= { trapsAlm  13222}       

--  1.3.6.1.4.1.2011.2.25.3.40.40.40.13229
    almOdu4PMLck NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU4 PM locked defect"
    ::= { trapsAlm  13229}             

--  1.3.6.1.4.1.2011.2.25.3.40.40.40.13242
    almOdu4PMTim NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU4 PM trace identifier mismatch"
    ::= { trapsAlm  13242}       

--  1.3.6.1.4.1.2011.2.25.3.40.40.40.13249
    almOdu4PMDeg NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU4 PM signal degrade alarm"
    ::= { trapsAlm  13249}      

--  1.3.6.1.4.1.2011.2.25.3.40.40.40.13263
    almOdu4PMBdi NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU4 PM backward defect indication"
    ::= { trapsAlm  13263}  

--  1.3.6.1.4.1.2011.2.25.3.40.40.40.13270
    almOpu4Plm NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OPU4 payload label mismatch"
    ::= { trapsAlm  13270}

--  1.3.6.1.4.1.2011.2.25.3.40.40.40.13271
    almOpu4Msim NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OPU4 multiplex structure identifier mismatch"
    ::= { trapsAlm  13271}  

--  1.3.6.1.4.1.2011.2.25.3.40.40.40.13273
    almSubrackCommPS NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Alarm of protection switching of inter-subrack communication. Subrack link auto switch"
    ::= { trapsAlm  13273}

--  1.3.6.1.4.1.2011.2.25.3.40.40.40.13275
    almodu4loflom  NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU4 frame and multiframes loss"
    ::= { trapsAlm  13275}

--  1.3.6.1.4.1.2011.2.25.3.40.40.40.13110
    almDcnsizeOver NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: number of NE in a DCN subnet exceeds the setting threshold"
    ::= { trapsAlm  13110}

--  1.3.6.1.4.1.2011.2.25.3.40.40.40.12362
    almOdu3Loflom NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: ODU3 PM loss of frame and multi-frame"
    ::= { trapsAlm  12362}

--  1.3.6.1.4.1.2011.2.25.3.40.40.40.12872
    almPatchChgSccNotMatch NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Patch inconsistency after the SCC board is replaced"
    ::= { trapsAlm  12872}

--  1.3.6.1.4.1.2011.2.25.3.40.40.40.13557
    almPatchBdExclude NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Exclusion of a patch package board"
    ::= { trapsAlm  13557}

--  1.3.6.1.4.1.2011.2.25.3.40.40.40.13558
    almPatchBdMatchFail NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Patch package matching failure"
    ::= { trapsAlm  13558}

--  1.3.6.1.4.1.2011.2.25.3.40.40.40.13744
    almPwdEncriptRisk NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: User password encryption mode risk"
    ::= { trapsAlm  13744}

--  1.3.6.1.4.1.2011.2.25.3.40.40.40.13880
    almSubrackPortCfgErr NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Configuration error of cascade ports on subrack"
    ::= { trapsAlm  13880}

-- 1.3.6.1.4.1.2011.2.25.3.40.40.40.13111
	almDcnLinkOver NOTIFICATION-TYPE
		OBJECTS { rptEvtNumber, rptAlmName, rptEvtNtfcnCde, rptEvtState, rptEvtStartTime, 
        rptEvtEndTime, rptEvtSrvEff, rptEvtObjType, rptEvtPara}
    STATUS current
    DESCRIPTION 
		"Trap of Alarm: DCNLINK_OVER."
	::= { trapsAlm 13111 }	

-- 1.3.6.1.4.1.2011.2.25.3.40.40.40.13759
	almSslCertDamaged NOTIFICATION-TYPE
		OBJECTS { rptEvtNumber, rptAlmName, rptEvtNtfcnCde, rptEvtState, rptEvtStartTime, 
        rptEvtEndTime, rptEvtSrvEff, rptEvtObjType, rptEvtPara}
    STATUS current
    DESCRIPTION 
		"Trap of Alarm: User-defined SSL certificate file damaged."
	::= { trapsAlm 13759 }

-- 1.3.6.1.4.1.2011.2.25.3.40.40.40.13779
	almSslCertToExpire NOTIFICATION-TYPE
		OBJECTS { rptEvtNumber, rptAlmName, rptEvtNtfcnCde, rptEvtState, rptEvtStartTime, 
        rptEvtEndTime, rptEvtSrvEff, rptEvtObjType, rptEvtPara}
    STATUS current
    DESCRIPTION 
		"Trap of Alarm: SSL certificate file is to expire."
	::= { trapsAlm 13779 }	

--  1.3.6.1.4.1.2011.2.25.3.40.40.40.13674
    almOtucnBdi NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OTUCn backward alarm indication"
    ::= { trapsAlm  13674}

--  1.3.6.1.4.1.2011.2.25.3.40.40.40.13675
    almOtucnDeg NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OTUCn signal degrade"
    ::= { trapsAlm  13675}

--  1.3.6.1.4.1.2011.2.25.3.40.40.40.13676
    almOtucnTim NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OTUCn trace identifier mismatch"
    ::= { trapsAlm  13676}

--  1.3.6.1.4.1.2011.2.25.3.40.40.40.13677
    almOtucnLom NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Loss of OTUCn multiframe"
    ::= { trapsAlm  13677}

--  1.3.6.1.4.1.2011.2.25.3.40.40.40.13678
    almOtucnLof NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: Loss of OTUCn frame"
    ::= { trapsAlm  13678}

--  1.3.6.1.4.1.2011.2.25.3.40.40.40.13679
    almOtucnSsf NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "Trap of Alarm: OTUCn Server Signal Fail"
    ::= { trapsAlm  13679}

--  1.3.6.1.4.1.2011.2.25.3.40.40.40.13685
    almOducnPlm NOTIFICATION-TYPE
    OBJECTS { rptEvtNumber, rptAlmName, 
        rptEvtNtfcnCde, rptEvtState, rptEvtStartTime, 
        rptEvtEndTime, rptEvtSrvEff, rptEvtObjType, rptEvtPara}
    STATUS current
    DESCRIPTION 
        "OPUCn payload label mismatch"
    ::= { trapsAlm  13685}

-- 1.3.6.1.4.1.2011.2.25.3.40.40.40.13687
	almEncAuthFail NOTIFICATION-TYPE
		OBJECTS { rptEvtNumber, rptAlmName, rptEvtNtfcnCde, rptEvtState, rptEvtStartTime, 
        rptEvtEndTime, rptEvtSrvEff, rptEvtObjType, rptEvtPara}
    STATUS current
    DESCRIPTION 
		"Device authentication at the source and sink fails "
	::= { trapsAlm 13687 }

-- 1.3.6.1.4.1.2011.2.25.3.40.40.40.13892
	almRxcfgWavedataMis NOTIFICATION-TYPE
		OBJECTS { rptEvtNumber, rptAlmName, rptEvtNtfcnCde, rptEvtState, rptEvtStartTime, 
        rptEvtEndTime, rptEvtSrvEff, rptEvtObjType, rptEvtPara}
    STATUS current
    DESCRIPTION 
		"RXCFG_WAVEDATA_MIS "
	::= { trapsAlm 13892 }

-- 1.3.6.1.4.1.2011.2.25.3.40.40.40.13923
	almOducnPmLck NOTIFICATION-TYPE
		OBJECTS { rptEvtNumber, rptAlmName, rptEvtNtfcnCde, rptEvtState, rptEvtStartTime, 
        rptEvtEndTime, rptEvtSrvEff, rptEvtObjType, rptEvtPara}
    STATUS current
    DESCRIPTION 
		"Trap of Alarm:ODUCN PM locked defect"
	::= { trapsAlm 13923 }	

--  1.3.6.1.4.1.2011.2.25.3.40.40.40.13543
    almInnerCommunMiscon NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Inner Communication Misconnect"
    ::= { trapsAlm 13543}

--  1.3.6.1.4.1.2011.2.25.3.40.40.40.13960
    almKmcKeySyncFail  NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: KMC_KEY_SYNC_FAIL. " 
    ::= { trapsAlm 13960}

--  1.3.6.1.4.1.2011.2.25.3.40.40.40.13983
    almInsuffcntMemSpac  NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Insufficient memory space. " 
    ::= { trapsAlm 13983}

--  1.3.6.1.4.1.2011.2.25.3.40.40.40.13984
    almInsuffcntFlshSpace  NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Insufficient flash space. " 
    ::= { trapsAlm 13984}

--  1.3.6.1.4.1.2011.2.25.3.40.40.40.13985
    almStorageFail  NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Storage error. " 
    ::= { trapsAlm 13985}

--  1.3.6.1.4.1.2011.2.25.3.40.40.40.13993
    almlaneoutpwrhigh  NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Excessively high output optical power on the sub-channel. " 
    ::= { trapsAlm 13993}

--  1.3.6.1.4.1.2011.2.25.3.40.40.40.13994
    almlaneoutpwrlow  NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Excessively low output optical power on the sub-channel. " 
    ::= { trapsAlm 13994}

--  1.3.6.1.4.1.2011.2.25.3.40.40.40.13995
    almlaneinpwrhigh  NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Excessively high input optical power on the sub-channel. " 
    ::= { trapsAlm 13995}

--  1.3.6.1.4.1.2011.2.25.3.40.40.40.13996
    almlaneinpwrlow  NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Excessively low input optical power on the sub-channel. " 
    ::= { trapsAlm 13996}

--  1.3.6.1.4.1.2011.2.25.3.40.40.40.13997
    almlanelos  NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Loss of signal on the sub-channel of module. " 
    ::= { trapsAlm 13997}


--  1.3.6.1.4.1.2011.2.25.3.40.40.40.13545
	almSubnetRTConflict NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: When network route to NMS port conflict with other direct DCN OSPF network route, and the latter‘s mask is longer than the former‘s, it may cause PC communication problem. When there are more than one conflict routes, report the one has the longest mask." 
    ::= { trapsAlm 13545}

--  1.3.6.1.4.1.2011.2.25.3.40.40.40.13716
	almOPU4LOOMFI NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Loss of OPU4 multiframe. The alarm is generated when the information about the upstream OPU4 multiframe head does not match the information about the downstream OPU4 multiframe." 
    ::= { trapsAlm 13716}
	
--  1.3.6.1.4.1.2011.2.25.3.40.40.40.13981
	almEncEMKInit NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: This alarm is generated when services are interrupted due to EMK initialization of encrypted services." 
    ::= { trapsAlm 13981}
	
--  1.3.6.1.4.1.2011.2.25.3.40.40.40.14041
	almPatchOPTimeout NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: The PATCH_OP_TIMEOUT is an alarm indicating that the duration for the patch package to be in the downloading or activation completion state exceeds the upper limit and the patch package needs to be manually processed." 
    ::= { trapsAlm 14041}
	
--  1.3.6.1.4.1.2011.2.25.3.40.40.40.14042
	almPatchInitFail NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: This alarm is generated when the patch initialization fails." 
    ::= { trapsAlm 14042}
	
--  1.3.6.1.4.1.2011.2.25.3.40.40.40.13967
    almFcAis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Fiber channel alarm indication signal, which indicates that an alarm is detected"
    ::= { trapsAlm 13967 }
	
	
	
--  1.3.6.1.4.1.2011.2.25.3.40.40.40.259
	almNebdXcDif NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Inconsistency between NE and board cross-connect matrix data." 
    ::= { trapsAlm 259}

	

	
	
--  1.3.6.1.4.1.2011.2.25.3.40.40.40.12794
	almMacFcsExc NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Bit error threshold-crossing detected at MAC layer." 
    ::= { trapsAlm 12794}
	
--  1.3.6.1.4.1.2011.2.25.3.40.40.40.12795
	almMacFcsSd NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Degrade threshold-crossing detected at MAC layer." 
    ::= { trapsAlm 12795}
	
--  1.3.6.1.4.1.2011.2.25.3.40.40.40.14029
	almBdFileNotActive NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: Board file not activated." 
    ::= { trapsAlm 14029}
	
--  1.3.6.1.4.1.2011.2.25.3.40.40.40.14096
	almClntSrvExceedLcs NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: The number of client-side services of a type exceeds the license limit." 
    ::= { trapsAlm 14096}
	
--  1.3.6.1.4.1.2011.2.25.3.40.40.40.14097
	almMacFcsNumSd NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: This alarm indicates signal degrade detected at the MAC layer based on the number of FCS packets." 
    ::= { trapsAlm 14097}

--  1.3.6.1.4.1.2011.2.25.3.40.40.40.14098
	almMacFcsNumExc NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: This alarm indicates bit error threshold-crossing detected at the MAC layer based on the number of FCS packets." 
    ::= { trapsAlm 14098}
	
--  1.3.6.1.4.1.2011.2.25.3.40.40.40.14181
	almSoftError NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: A soft error of failure occurs." 
    ::= { trapsAlm 14181}

--  1.3.6.1.4.1.2011.2.25.3.40.40.40.14178 
	almLsrSubmodOffline NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: The alarm is reported when a board detects that the submodule (optical module) is offline." 
    ::= { trapsAlm 14178}
	
--  1.3.6.1.4.1.2011.2.25.3.40.40.40.14179
	almLsrModFail NOTIFICATION-TYPE
    OBJECTS { rptEvtNumber,rptAlmName,rptEvtNtfcnCde,rptEvtState,rptEvtStartTime,rptEvtEndTime,rptEvtSrvEff,rptEvtObjType,rptEvtPara }
    STATUS current
    DESCRIPTION 
        "Trap of Alarm: The LSR_MOD_FAIL alarm indicates that the status of the module on a board is abnormal." 
    ::= { trapsAlm 14179}
	
	
	
	
	
	
	
	
--  1.3.6.1.4.1.2011.2.25.3.40.40.40.187
    almChanLos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Loss of single-wavelength signal."
    ::= { trapsAlm 187 }

--  1.3.6.1.4.1.2011.2.25.3.40.40.40.188
    almChanAdd NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: (CHAN_ADD)Addition of single-wavelength signal."
    ::= { trapsAlm 188 }

--  1.3.6.1.4.1.2011.2.25.3.40.40.40.224
    almCrcExc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: almCrcExc."
    ::= { trapsAlm 224 }


--  1.3.6.1.4.1.2011.2.25.3.40.40.40.295
    almPortswitchFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Optical switch transfer failure."
    ::= { trapsAlm 295 }

--  1.3.6.1.4.1.2011.2.25.3.40.40.40.432
    almModComFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Module Communicate Failure."
    ::= { trapsAlm 432 }

--  1.3.6.1.4.1.2011.2.25.3.40.40.40.441
    almAlmDataRlos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Ethernet Port Receive No Data."
    ::= { trapsAlm 441 }

--  1.3.6.1.4.1.2011.2.25.3.40.40.40.442
    almAlmDataTlos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Ethernet Port Transmit No Data."
    ::= { trapsAlm 442 }

--  1.3.6.1.4.1.2011.2.25.3.40.40.40.12842
    almMutTlos NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Loss of transmitted optical power."
    ::= { trapsAlm 12842 }

--  1.3.6.1.4.1.2011.2.25.3.40.40.40.12969
    almLaserHazardWarning NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Warning indication of the laser hazard
level."
    ::= { trapsAlm 12969 }

--  1.3.6.1.4.1.2011.2.25.3.40.40.40.13053
    almVoadataMis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Mismatch of attenuation attribute."
    ::= { trapsAlm 13053 }

--  1.3.6.1.4.1.2011.2.25.3.40.40.40.13054
    almGaindataMis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Mismatch of gain attribute."
    ::= { trapsAlm 13054 }

--  1.3.6.1.4.1.2011.2.25.3.40.40.40.13132
    almSpanLossHigh NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Span loss too high."
    ::= { trapsAlm 13132 }

--  1.3.6.1.4.1.2011.2.25.3.40.40.40.13280
    almSpanLossLow NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Span loss too low."
    ::= { trapsAlm 13280 }


--  1.3.6.1.4.1.2011.2.25.3.40.40.40.13629
    almSpanLossExceedEol NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Span fiber loss exceeding EOL."
    ::= { trapsAlm 13629 }

--  1.3.6.1.4.1.2011.2.25.3.40.40.40.13630
    almOmsPwrAdjFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OMS loss compensation adjustment failure."
    ::= { trapsAlm 13630 }

--  1.3.6.1.4.1.2011.2.25.3.40.40.40.13631
    almOmsLossAccumAbn NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Abnormal accumulated span loss."
    ::= { trapsAlm 13631 }

--  1.3.6.1.4.1.2011.2.25.3.40.40.40.13632
    almOaOutPwrAbn NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Abnormal optical power of the transmit-end OA."
    ::= { trapsAlm 13632 }

--  1.3.6.1.4.1.2011.2.25.3.40.40.40.13633
    almPwrUnbalanced NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Unbalanced optical power flatness."
    ::= { trapsAlm 13633 }

--  1.3.6.1.4.1.2011.2.25.3.40.40.40.13634
    almOsnrLossUnbalanced NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Unbalanced OSNR loss flatness."
    ::= { trapsAlm 13634 }

--  1.3.6.1.4.1.2011.2.25.3.40.40.40.13636
    almOmsLossMonFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OMS loss monitoring failure."
    ::= { trapsAlm 13636 }

--  1.3.6.1.4.1.2011.2.25.3.40.40.40.13649
    almSpanLossUpperGain NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Span loss upper than the gain compensation value."
    ::= { trapsAlm 13649 }

--  1.3.6.1.4.1.2011.2.25.3.40.40.40.13650
    almSpanLossLowerGain NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Span loss lower than the gain compensation value."
    ::= { trapsAlm 13650 }


--  1.3.6.1.4.1.2011.2.25.3.40.40.40.13931
    almChanPwrHigh NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Excessively High Channel Power."
    ::= { trapsAlm 13931 }


--  1.3.6.1.4.1.2011.2.25.3.40.40.40.14036
    almSpectraAnalyseFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: This alarm is reported when the board with the spectrum analysis capability fails to analyze spectrum."
    ::= { trapsAlm 14036 }


--  1.3.6.1.4.1.2011.2.25.3.40.40.40.14087
    almWorkparaMis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: This alarm is reported when the actual and configured working parameters of the board mismatch."
    ::= { trapsAlm 14087 }

--  1.3.6.1.4.1.2011.2.25.3.40.40.40.14145
    almInterBdwidthMism NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The inter-subrack bandwidth of the cluster is not matched.."
    ::= { trapsAlm 14145 }

--  1.3.6.1.4.1.2011.2.25.3.40.40.40.14146
    almInterBdwidthInsuf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The inter-subrack bandwidth of the cluster is insufficient.."
    ::= { trapsAlm 14146 }


--  1.3.6.1.4.1.2011.2.25.3.40.40.40.14174
    almApsStatusIndi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: APS status indication."
    ::= { trapsAlm 14174 }

--  1.3.6.1.4.1.2011.2.25.3.40.40.40.14180
    almSrvTypeMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: SRV_TYPE_MISMATCH."
    ::= { trapsAlm 14180 }

--  1.3.6.1.4.1.2011.2.25.3.40.40.40.14183
    almXcSrvErr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: XC_SRV_ERR."
    ::= { trapsAlm 14183 }

--  1.3.6.1.4.1.2011.2.25.3.40.40.40.14188
    almSwdlIncpkgFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Failure to load a dynamic incremental package."
    ::= { trapsAlm 14188 }

--  1.3.6.1.4.1.2011.2.25.3.40.40.40.14191
    almWaveBlocked NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Wavelength blocked."
    ::= { trapsAlm 14191 }

--  1.3.6.1.4.1.2011.2.25.3.40.40.40.14198
    almTsSyncFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: TS_SYNC_FAIL."
    ::= { trapsAlm 14198 }

--  1.3.6.1.4.1.2011.2.25.3.40.40.40.14206
    almClusterFiberlenDif NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Cluster fiber length difference."
    ::= { trapsAlm 14206 }

--  1.3.6.1.4.1.2011.2.25.3.40.40.40.14209
    almDpsStaIndi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Device protection status indication."
    ::= { trapsAlm 14209 }

--  1.3.6.1.4.1.2011.2.25.3.40.40.40.14212
    almOducnTcm1Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM1 Server Signal Fail."
    ::= { trapsAlm 14212 }

--  1.3.6.1.4.1.2011.2.25.3.40.40.40.14213
    almOducnTcm2Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM2 Server Signal Fail."
    ::= { trapsAlm 14213 }

--  1.3.6.1.4.1.2011.2.25.3.40.40.40.14214
    almOducnTcm3Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM3 Server Signal Fail."
    ::= { trapsAlm 14214 }

--  1.3.6.1.4.1.2011.2.25.3.40.40.40.14215
    almOducnTcm4Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM4 Server Signal Fail."
    ::= { trapsAlm 14215 }

--  1.3.6.1.4.1.2011.2.25.3.40.40.40.14216
    almOducnTcm5Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM5 Server Signal Fail."
    ::= { trapsAlm 14216 }

--  1.3.6.1.4.1.2011.2.25.3.40.40.40.14217
    almOducnTcm6Ssf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM6 Server Signal Fail."
    ::= { trapsAlm 14217 }

--  1.3.6.1.4.1.2011.2.25.3.40.40.40.14218
    almOducnTcm1Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM1 alarm indication signal."
    ::= { trapsAlm 14218 }

--  1.3.6.1.4.1.2011.2.25.3.40.40.40.14219
    almOducnTcm2Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM2 alarm indication signal."
    ::= { trapsAlm 14219 }

--  1.3.6.1.4.1.2011.2.25.3.40.40.40.14220
    almOducnTcm3Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM3 alarm indication signal."
    ::= { trapsAlm 14220 }

--  1.3.6.1.4.1.2011.2.25.3.40.40.40.14221
    almOducnTcm4Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM4 alarm indication signal."
    ::= { trapsAlm 14221 }

--  1.3.6.1.4.1.2011.2.25.3.40.40.40.14222
    almOducnTcm5Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM5 alarm indication signal."
    ::= { trapsAlm 14222 }

--  1.3.6.1.4.1.2011.2.25.3.40.40.40.14223
    almOducnTcm6Ais NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM6 alarm indication signal."
    ::= { trapsAlm 14223 }

--  1.3.6.1.4.1.2011.2.25.3.40.40.40.14224
    almOducnTcm1Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM1 locked defect."
    ::= { trapsAlm 14224 }

--  1.3.6.1.4.1.2011.2.25.3.40.40.40.14225
    almOducnTcm2Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM2 locked defect."
    ::= { trapsAlm 14225 }

--  1.3.6.1.4.1.2011.2.25.3.40.40.40.14226
    almOducnTcm3Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM3 locked defect."
    ::= { trapsAlm 14226 }

--  1.3.6.1.4.1.2011.2.25.3.40.40.40.14227
    almOducnTcm4Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM4 locked defect."
    ::= { trapsAlm 14227 }

--  1.3.6.1.4.1.2011.2.25.3.40.40.40.14228
    almOducnTcm5Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM5 locked defect."
    ::= { trapsAlm 14228 }

--  1.3.6.1.4.1.2011.2.25.3.40.40.40.14229
    almOducnTcm6Lck NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM6 locked defect."
    ::= { trapsAlm 14229 }

--  1.3.6.1.4.1.2011.2.25.3.40.40.40.14230
    almOducnTcm1Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM1 loss of tandem connection."
    ::= { trapsAlm 14230 }

--  1.3.6.1.4.1.2011.2.25.3.40.40.40.14231
    almOducnTcm2Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM2 loss of tandem connection."
    ::= { trapsAlm 14231 }

--  1.3.6.1.4.1.2011.2.25.3.40.40.40.14232
    almOducnTcm3Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM3 loss of tandem connection."
    ::= { trapsAlm 14232 }

--  1.3.6.1.4.1.2011.2.25.3.40.40.40.14233
    almOducnTcm4Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM4 loss of tandem connection."
    ::= { trapsAlm 14233 }

--  1.3.6.1.4.1.2011.2.25.3.40.40.40.14234
    almOducnTcm5Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM5 loss of tandem connection."
    ::= { trapsAlm 14234 }

--  1.3.6.1.4.1.2011.2.25.3.40.40.40.14235
    almOducnTcm6Ltc NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM6 loss of tandem connection."
    ::= { trapsAlm 14235 }

--  1.3.6.1.4.1.2011.2.25.3.40.40.40.14236
    almOducnTcm1Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM1 trace identifier mismatch."
    ::= { trapsAlm 14236 }

--  1.3.6.1.4.1.2011.2.25.3.40.40.40.14237
    almOducnTcm2Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM2 trace identifier mismatch."
    ::= { trapsAlm 14237 }

--  1.3.6.1.4.1.2011.2.25.3.40.40.40.14238
    almOducnTcm3Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM3 trace identifier mismatch."
    ::= { trapsAlm 14238 }

--  1.3.6.1.4.1.2011.2.25.3.40.40.40.14239
    almOducnTcm4Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM4 trace identifier mismatch."
    ::= { trapsAlm 14239 }

--  1.3.6.1.4.1.2011.2.25.3.40.40.40.14240
    almOducnTcm5Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM5 trace identifier mismatch."
    ::= { trapsAlm 14240 }

--  1.3.6.1.4.1.2011.2.25.3.40.40.40.14241
    almOducnTcm6Tim NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM6 trace identifier mismatch."
    ::= { trapsAlm 14241 }

--  1.3.6.1.4.1.2011.2.25.3.40.40.40.14242
    almOducnTcm1Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM1 signal degrade."
    ::= { trapsAlm 14242 }

--  1.3.6.1.4.1.2011.2.25.3.40.40.40.14243
    almOducnTcm2Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM2 signal degrade."
    ::= { trapsAlm 14243 }

--  1.3.6.1.4.1.2011.2.25.3.40.40.40.14244
    almOducnTcm3Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM3 signal degrade."
    ::= { trapsAlm 14244 }

--  1.3.6.1.4.1.2011.2.25.3.40.40.40.14245
    almOducnTcm4Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM4 signal degrade."
    ::= { trapsAlm 14245 }

--  1.3.6.1.4.1.2011.2.25.3.40.40.40.14246
    almOducnTcm5Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM5 signal degrade."
    ::= { trapsAlm 14246 }

--  1.3.6.1.4.1.2011.2.25.3.40.40.40.14247
    almOducnTcm6Deg NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM6 signal degrade."
    ::= { trapsAlm 14247 }

--  1.3.6.1.4.1.2011.2.25.3.40.40.40.14248
    almOducnTcm1Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM1 backward defect indication."
    ::= { trapsAlm 14248 }

--  1.3.6.1.4.1.2011.2.25.3.40.40.40.14249
    almOducnTcm2Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM2 backward defect indication."
    ::= { trapsAlm 14249 }

--  1.3.6.1.4.1.2011.2.25.3.40.40.40.14250
    almOducnTcm3Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM3 backward defect indication."
    ::= { trapsAlm 14250 }

--  1.3.6.1.4.1.2011.2.25.3.40.40.40.14251
    almOducnTcm4Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM4 backward defect indication."
    ::= { trapsAlm 14251 }

--  1.3.6.1.4.1.2011.2.25.3.40.40.40.14252
    almOducnTcm5Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM5 backward defect indication."
    ::= { trapsAlm 14252 }

--  1.3.6.1.4.1.2011.2.25.3.40.40.40.14253
    almOducnTcm6Bdi NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ODUCN TCM6 backward defect indication."
    ::= { trapsAlm 14253 }

--  1.3.6.1.4.1.2011.2.25.3.40.40.40.14255
    almDbUnsave NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Configuration persistency prohibited."
    ::= { trapsAlm 14255 }


--  1.3.6.1.4.1.2011.2.25.3.40.40.40.14271
    almBpOduLoflom NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Loss of ODU frames and multiframes from the backplane."
    ::= { trapsAlm 14271 }

--  1.3.6.1.4.1.2011.2.25.3.40.40.40.13746
    almProPktFlooding NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Protocol packet flooding attacks detected."
    ::= { trapsAlm 13746 }	
	
--  1.3.6.1.4.1.2011.2.25.3.40.40.40.13762
    almArpSpoof NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: ARP Spoof."
    ::= { trapsAlm 13762}	
	
--  1.3.6.1.4.1.2011.2.25.3.40.40.40.12585
    almModuleAdjustFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The optical module adjusting failed."
    ::= { trapsAlm 12585 }

--  1.3.6.1.4.1.2011.2.25.3.40.40.40.12606
    almModulefileUpdateFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The optical module program upgrade failed."
    ::= { trapsAlm 12606 }



--  1.3.6.1.4.1.2011.2.25.3.40.40.40.13635
    almIpaFault NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: IPA fault."
    ::= { trapsAlm 13635 }

--  1.3.6.1.4.1.2011.2.25.3.40.40.40.14152
    almIpaAbnormal NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: This alarm occurs when the IPA function is abnormal."
    ::= { trapsAlm 14152 }	
	
--  1.3.6.1.4.1.2011.2.25.3.40.40.40.271
    almModuleTempOver NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Module temperature exceeds the threshold."
    ::= { trapsAlm 271 }	

--  1.3.6.1.4.1.2011.2.25.3.40.40.40.14288
    almBdDcnLack NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Insufficient DCN bandwidth resources of the board."
    ::= { trapsAlm 14288 }
	
--  1.3.6.1.4.1.2011.2.25.3.40.40.40.13986
    almOscClkMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OSC clock mismatch."
    ::= { trapsAlm 13986 }

--  1.3.6.1.4.1.2011.2.25.3.40.40.40.14306
    almSysbusErr NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: SYSTEM BUS Error Alarm."
    ::= { trapsAlm 14306 }

--  1.3.6.1.4.1.2011.2.25.3.40.40.40.14334
    almBdTempFluct NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Fluctuation of working temperature over threshold."
    ::= { trapsAlm 14334 }

--  1.3.6.1.4.1.2011.2.25.3.40.40.40.14335
    almFanSpeedFluct NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Fluctuation of fan speed over threshold."
    ::= { trapsAlm 14335 }

	

--  1.3.6.1.4.1.2011.2.25.3.40.40.40.14373
    almDcnSubnetMixedUp NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: DCN_SUBNET_MIXED_UP."
    ::= { trapsAlm 14373 }
	


--  1.3.6.1.4.1.2011.2.25.3.40.40.40.13724
    almStdPtpOffsetOver NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: standard ptptime offset over."
    ::= { trapsAlm 13724 }

	
--  1.3.6.1.4.1.2011.2.25.3.40.40.40.14384
    almVersionFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: REVERSION_FAIL."
    ::= { trapsAlm 14384 }
	

--  1.3.6.1.4.1.2011.2.25.3.40.40.40.14395
    almClusterShelfIsolate NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Cluster Subrack Isolation."
    ::= { trapsAlm 14395 }    
    --  1.3.6.1.4.1.2011.2.25.3.40.40.40.87
    almJ0Mm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Section trace identifier mismatch."
    ::= { trapsAlm 87 }
    
--  1.3.6.1.4.1.2011.2.25.3.40.40.40.14322
    almSerialLogin NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Serial login alarm."
    ::= { trapsAlm 14322 }

--  1.3.6.1.4.1.2011.2.25.3.40.40.40.14323
    almSecuLogfailed NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: User login failed alarm."
    ::= { trapsAlm 14323 }	      
    
    --  1.3.6.1.4.1.2011.2.25.3.40.40.40.99
    almWRFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Reading or writing single chip register failed."
    ::= { trapsAlm 99 }

--  1.3.6.1.4.1.2011.2.25.3.40.40.40.12288
    almDlagProtectFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: DLAG protection failed."
    ::= { trapsAlm 12288 }

--  1.3.6.1.4.1.2011.2.25.3.40.40.40.14388
    almTelemetryCommFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Communication failure between NE and telemetry server."
    ::= { trapsAlm 14388 }

--  1.3.6.1.4.1.2011.2.25.3.40.40.40.14392
    almAlienWavelengthAccess NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Alien wavelength access."
    ::= { trapsAlm 14392 }

--  1.3.6.1.4.1.2011.2.25.3.40.40.40.14028
    almPortWllcfgRepeated NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Repeated wavelength locking configurations on OTU board optical ports."
    ::= { trapsAlm 14028 }

--  1.3.6.1.4.1.2011.2.25.3.40.40.40.14412
    almTbFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Trustworthiness module abnormality."
    ::= { trapsAlm 14412 }

--  1.3.6.1.4.1.2011.2.25.3.40.40.40.14429
    almOxcLicenseOwe NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Optical-layer license overconsumption alarm."
    ::= { trapsAlm 14429 }

--  1.3.6.1.4.1.2011.2.25.3.40.40.40.14430
    almOscPlm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OSC payload mismatch."
    ::= { trapsAlm 14430 }


--  1.3.6.1.4.1.2011.2.25.3.40.40.40.14445
    almFlexeRpf NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Remote PHY failure."
    ::= { trapsAlm 14445 }

--  1.3.6.1.4.1.2011.2.25.3.40.40.40.14446
    almFlexeLof NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: FlexE FAS loss."
    ::= { trapsAlm 14446 }

--  1.3.6.1.4.1.2011.2.25.3.40.40.40.14447
    almFlexeLom NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: FlexE MFAS loss."
    ::= { trapsAlm 14447 }

--  1.3.6.1.4.1.2011.2.25.3.40.40.40.14448
    almFlexeGidm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: FlexE Group ID mismatch."
    ::= { trapsAlm 14448 }

--  1.3.6.1.4.1.2011.2.25.3.40.40.40.14449
    almFlexeFmm NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: FlexE Group PHY ID mismatch."
    ::= { trapsAlm 14449 }

--  1.3.6.1.4.1.2011.2.25.3.40.40.40.14450
    almFlexeLol NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Deskew misalignment of multiple FlexE instances."
    ::= { trapsAlm 14450 }

--  1.3.6.1.4.1.2011.2.25.3.40.40.40.14451
    almModuleNotAuthenticated NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Module is not authenticated."
    ::= { trapsAlm 14451 }

--  1.3.6.1.4.1.2011.2.25.3.40.40.40.14435
    almServiceAutocrtFail NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Failure of automatic service creation."
    ::= { trapsAlm 14435 }

--  1.3.6.1.4.1.2011.2.25.3.40.40.40.14210
    almFibertypeNotConfig NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: The fiber type is not configured."
    ::= { trapsAlm 14210 }

--  1.3.6.1.4.1.2011.2.25.3.40.40.40.14457
    almEnhanceSwitchFar NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: OMS 1+1 protection switching alarm."
    ::= { trapsAlm 14457 }


--  1.3.6.1.4.1.2011.2.25.3.40.40.40.13090
    almCpuBusy NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: CPU BUSY."
    ::= { trapsAlm 13090 }

    
--  1.3.6.1.4.1.2011.2.25.3.40.40.40.14464
    almIpaAuxiliaryMis NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Missing of the IPA auxiliary detection board."
    ::= { trapsAlm 14464 }

--  1.3.6.1.4.1.2011.2.25.3.40.40.40.12856
    almTsCfgMismatch NOTIFICATION-TYPE
    OBJECTS { rptEvtNumber, rptAlmName,
        rptEvtNtfcnCde, rptEvtState, rptEvtStartTime,
        rptEvtEndTime, rptEvtSrvEff, rptEvtObjType, rptEvtPara}
    STATUS current
    DESCRIPTION
        "Trap of Alarm: Timeslot configuration mismatch."
    ::= { trapsAlm 12856 }

    END

--
-- OPTIX-SONET-ALM-MIB.mib
--

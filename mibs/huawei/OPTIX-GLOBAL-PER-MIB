--
-- OPTIX-SONET-PER-MIB.mib
-- MIB generated by MG-SOFT Visual MIB Builder Version 3.0 Build 253
-- Monday, March 06, 2006 at 10:26:16
--
            -- =================================================================
--  Copyright (C) 2006 by HUAWEI TECHNOLOGIES. All rights reserved
--  
--  Description:This MIB describes the Performance interface of Huawei SONET transmit
--  Reference:
--  Version: V1.00
--  History:
-- 	<author>,<date>,<contents>
-- =================================================================
-- 

	OPTIX-GLOBAL-PER-MIB DEFINITIONS ::= BEGIN
 
		IMPORTS  
			optixCommonGlobal			
				FROM OPTIX-OID-MIB			
			MOD2Type, PerformanceEventType, ValidflagType			
				FROM OPTIX-GLOBAL-TC-MIB			
			OBJECT-GROUP, MODULE-COMPLIANCE			
				FROM SNMPv2-CONF			
			Integer32, Unsigned32, OBJECT-TYPE, MODULE-IDENTITY			
				FROM SNMPv2-SMI			
			DateAndTime, DisplayString			
				FROM SNMPv2-TC;    
				
		optixGlobalPER MODULE-IDENTITY 
			LAST-UPDATED "200805240000Z"
			ORGANIZATION 
				"Huawei Technologies co.,Ltd."
			CONTACT-INFO 
				"R&D Building
				Huawei Technologies Co., Ltd.
				Bantian, Longgang District 
				Shenzhen, P. R. China
				http://www.huawei.com
				Zip:518129
				E-mail:support@huawei.com"
			DESCRIPTION 
				"Description."
			REVISION "200805240000Z"
			DESCRIPTION
				"The initial revision of this MIB module."
			::= { optixCommonGlobal 20 }  
	
	    perMonitorTime OBJECT IDENTIFIER ::= { optixGlobalPER 10 }	
--  -------------------------------------------------------------------------
-- Node Object Identity
-- -------------------------------------------------------------------------
--  Event report event(REP)
		-- 1.3.6.1.4.1.2011.2.25.3.10.20.10.10
		per15mMonitorTime OBJECT IDENTIFIER ::= { perMonitorTime 10 }
		
-- -------------------------------------------------------------------------
-- Date and time of PM 15 minutes(or one day) period beginning( or end)
-- -------------------------------------------------------------------------
		-- 1.3.6.1.4.1.2011.2.25.3.10.20.10.10.10
		per15mMonitorStartTime OBJECT-TYPE
			SYNTAX DateAndTime
			MAX-ACCESS read-write
			STATUS current
			DESCRIPTION
				"Start date and time of 15 minutes PM period.When system enter 
				the per15mMonitorStartTime,15 minutes PM starts.the 
				per15mMonitorStartTime should not ealier than current date and time,
				specially,when it is equal to 1990-00-00 00:00:00,15 minutes PM 
				starts immediately.reset the per15mMonitorStartTime will terminate
				current 15 minutes PM period.When system enter the per15mMonitorEndTime,
				the per15mMonitorStartTime will be reset to zero."
			::= { per15mMonitorTime 10 }
		
		-- 1.3.6.1.4.1.2011.2.25.3.10.20.10.10.20
		per15mMonitorEndTime OBJECT-TYPE
			SYNTAX DateAndTime
			MAX-ACCESS read-write
			STATUS current
			DESCRIPTION
				"End date and time of 15 minutes PM period.you need set the 
				per15mMonitorStartTime before set the per15mMonitorEndTime,and 
				per15mMonitorStartTime should earlier than the 
				per15mMonitorEndTime,specially,when the  per15mMonitorEndTime 
				is equal to 1990-00-00 00:00:00,15 minutes PM ends immediately.
				When system enter the per15mMonitorEndTime,the 
				per15mMonitorEndTime will be reset to zero."
			::= { per15mMonitorTime 20 }
		
--  date and time of 15 minutes PM period
		-- 1.3.6.1.4.1.2011.2.25.3.10.20.10.20
		per24hMonitorTime OBJECT IDENTIFIER ::= { perMonitorTime 20 }
		
		-- 1.3.6.1.4.1.2011.2.25.3.10.20.10.20.10
		per24hMonitorStartTime OBJECT-TYPE
			SYNTAX DateAndTime
			MAX-ACCESS read-write
			STATUS current
			DESCRIPTION
				"Start date and time of one day PM period.When system enter 
				the per24hMonitorStartTime,one day PM starts.the 
				per24hMonitorStartTime should not ealier than current date and time,
				specially,when it is equal to 1990-00-00 00:00:00,one day PM 
				starts immediately.reset the per24hMonitorStartTime will terminate
				current one day PM period.When system enter the per24hMonitorEndTime,
				the per24hMonitorStartTime will be reset to zero."
			::= { per24hMonitorTime 10 }
		
		-- 1.3.6.1.4.1.2011.2.25.3.10.20.10.20.20
		per24hMonitorEndTime OBJECT-TYPE
			SYNTAX DateAndTime
			MAX-ACCESS read-write
			STATUS current
			DESCRIPTION
				"End date and time of one day PM period.you need set the 
				per24hMonitorStartTime before set the per24hMonitorEndTime,and 
				per24hMonitorStartTime should earlier than the 
				per24hMonitorEndTime,specially,when the  per24hMonitorEndTime 
				is equal to 1990-00-00 00:00:00,one day PM ends immediately.
				When system enter the per24hMonitorEndTime,the 
				per24hMonitorEndTime will be reset to zero."
			::= { per24hMonitorTime 20 }            
		

		
	END
--
-- OPTIX-SONET-PER-MIB.mib
--

DATAPOWER-STATUS-MIB DEFINITIONS ::= BEGIN


-- Programmatically Generated; do not edit 

-- Licensed Materials - Property of IBM
-- IBM WebSphere DataPower Appliances
-- Copyright IBM Corporation 2007,2017. All Rights Reserved.
-- US Government Users Restricted Rights - Use, duplication or disclosure
-- restricted by GSA ADP Schedule Contract with IBM Corp.
      
IMPORTS
    enterprises, MODULE-IDENTITY, OBJECT-TYPE, 
    Integer32, IpAddress, Counter32, 
    Counter64, Gauge32, Unsigned32, 
    TimeTicks
        FROM SNMPv2-SMI
    TEXTUAL-CONVENTION, DisplayString, MacAddress, 
    TimeInterval, TimeStamp
        FROM SNMPv2-TC
    InetAddressType, InetAddress, InetAddressPrefixLength, 
    InetPortNumber
        FROM INET-ADDRESS-MIB
    dpConfigXMLManagerIndex, dpConfigLogTargetIndex, dpConfigSLMPolicyIndex, 
    dpConfigLoadBalancerGroupIndex, dpConfigCountMonitorIndex, dpConfigMessageTypeIndex, 
    dpConfigDurationMonitorIndex, dpConfigMQQMIndex, dpConfigWSGatewayIndex, 
    dpConfigTibcoEMSServerIndex, dpConfigWebSphereJMSServerIndex, dpConfigUDDISubscriptionIndex, 
    dpConfigWSRRSubscriptionIndex, dpConfigSQLDataSourceIndex, dpConfigXC10GridIndex, 
    dpConfigIMSConnectIndex, dpConfigZosNSSClientIndex, dpConfigWSRRSavedSearchSubscriptionIndex, 
    dpConfigIPMulticastIndex, dpConfigGatewayBaseIndex, dpConfigODRConnectorGroupIndex, 
    dpConfigSecureGatewayClientIndex, dpConfigWXSGridIndex
        FROM DATAPOWER-CONFIG-MIB;

dpStatusMIB MODULE-IDENTITY
    LAST-UPDATED "200701110000Z"
    ORGANIZATION "IBM Corporation"
    CONTACT-INFO "IBM Corporation, Application Integration and Middleware, DataPower SOA Appliances. Web:
    http://www-306.ibm.com/software/integration/datapower/support/ Email: csupport@us.ibm.com"
    DESCRIPTION "The MIB module for status monitoring of a DataPower XML device."
    REVISION "200701110000Z"
    DESCRIPTION "Updated"

    ::= { dpModules 1 }

IpNetworkAddress ::= TEXTUAL-CONVENTION
      DISPLAY-HINT "1d.1d.1d.1d/1d.1d.1d.1d"
      STATUS    current
      DESCRIPTION
              "An IP Network and mask"
      SYNTAX    OCTET STRING (SIZE(8))
          
DPTimeIntervalSeconds ::= TEXTUAL-CONVENTION
      STATUS   current
      DESCRIPTION
               "A unit of time expressed in seconds"
      SYNTAX   INTEGER
          
DPTimeIntervalMillis ::= TEXTUAL-CONVENTION
      STATUS   current
      DESCRIPTION
               "A unit of time expressed in milliseconds"
      SYNTAX   INTEGER
          
datapower OBJECT IDENTIFIER ::= { enterprises 14685 }

dpModules OBJECT IDENTIFIER ::= { datapower 2 }

dpManagement OBJECT IDENTIFIER ::= { datapower 3 }

dpStatus OBJECT IDENTIFIER ::= { dpManagement 1 }

--

dpStatusActiveUsersTable OBJECT-TYPE
    SYNTAX      SEQUENCE OF DPStatusActiveUsersEntry
    MAX-ACCESS  not-accessible
    STATUS      current
    DESCRIPTION
        "This is a list of all users currently logged into the device."

    ::= { dpStatus 1 }

dpStatusActiveUsersEntry OBJECT-TYPE
    SYNTAX      DPStatusActiveUsersEntry
    MAX-ACCESS  not-accessible
    STATUS      current
    DESCRIPTION "Table row."
    INDEX { dpStatusActiveUserssession }

    ::= { dpStatusActiveUsersTable 1 }

DPStatusActiveUsersEntry ::= SEQUENCE {
    dpStatusActiveUserssession    Unsigned32,
    dpStatusActiveUsersname    DisplayString,
    dpStatusActiveUsersconnection    INTEGER,
    dpStatusActiveUsersaddress    IpAddress,
    dpStatusActiveUserslogin    TimeStamp,
    dpStatusActiveUsersdomain    DisplayString
}

dpStatusActiveUserssession OBJECT-TYPE
    SYNTAX      Unsigned32
    MAX-ACCESS  read-only
    STATUS      current
    DESCRIPTION
        "A system-assigned session identifier."

    ::= { dpStatusActiveUsersEntry 1 }

dpStatusActiveUsersname OBJECT-TYPE
    SYNTAX      DisplayString
    MAX-ACCESS  read-only
    STATUS      current
    DESCRIPTION
        "Username presented during login."

    ::= { dpStatusActiveUsersEntry 2 }

dpStatusActiveUsersconnection OBJECT-TYPE
    SYNTAX      INTEGER { 
                        serial-port(1),
                        telnet(2),
                        secure-shell(3),
                        web-gui(4),
                        saml-artifact(5),
                        system(6),
                        rest-mgmt(7),
                        apic-gw-service(8)
                }
    MAX-ACCESS  read-only
    STATUS      current
    DESCRIPTION
        "The method used to connect to the device, such as web-gui (using a
        browser), cli (through telnet or ssh), or serial (via a serial cable)."

    ::= { dpStatusActiveUsersEntry 3 }

dpStatusActiveUsersaddress OBJECT-TYPE
    SYNTAX      IpAddress
    MAX-ACCESS  read-only
    STATUS      current
    DESCRIPTION
        "The IP address of the user's client machine. Not valid for serial
        connections."

    ::= { dpStatusActiveUsersEntry 4 }

dpStatusActiveUserslogin OBJECT-TYPE
    SYNTAX      TimeStamp
    MAX-ACCESS  read-only
    STATUS      current
    DESCRIPTION
        "Time of login."

    ::= { dpStatusActiveUsersEntry 5 }

dpStatusActiveUsersdomain OBJECT-TYPE
    SYNTAX      DisplayString
    MAX-ACCESS  read-only
    STATUS      current
    DESCRIPTION
        "Application domain for this user session."

    ::= { dpStatusActiveUsersEntry 6 }

--

dpStatusARPStatusTable OBJECT-TYPE
    SYNTAX      SEQUENCE OF DPStatusARPStatusEntry
    MAX-ACCESS  not-accessible
    STATUS      obsolete
    DESCRIPTION
        "Status of ARP translations on all interfaces, both Ethernet and VLAN. Only
        complete ARP entries are shown.
        Note: this is obsolete as of release 3.6.1"

    ::= { dpStatus 2 }

dpStatusARPStatusEntry OBJECT-TYPE
    SYNTAX      DPStatusARPStatusEntry
    MAX-ACCESS  not-accessible
    STATUS      obsolete
    DESCRIPTION "Table row."
    INDEX { dpStatusARPStatusIPAddress }

    ::= { dpStatusARPStatusTable 1 }

DPStatusARPStatusEntry ::= SEQUENCE {
    dpStatusARPStatusIPAddress    IpAddress,
    dpStatusARPStatusHardwareAddress    MacAddress,
    dpStatusARPStatusInterface    DisplayString,
    dpStatusARPStatusInterfaceType    INTEGER,
    dpStatusARPStatusVlanName    DisplayString
}

dpStatusARPStatusIPAddress OBJECT-TYPE
    SYNTAX      IpAddress
    MAX-ACCESS  read-only
    STATUS      obsolete
    DESCRIPTION
        "The IP address of the network interface node corresponding to the MAC
        address listed in this ARP entry."

    ::= { dpStatusARPStatusEntry 1 }

dpStatusARPStatusHardwareAddress OBJECT-TYPE
    SYNTAX      MacAddress
    MAX-ACCESS  read-only
    STATUS      obsolete
    DESCRIPTION
        "The MAC address of this network interface node."

    ::= { dpStatusARPStatusEntry 4 }

dpStatusARPStatusInterface OBJECT-TYPE
    SYNTAX      DisplayString
    MAX-ACCESS  read-only
    STATUS      obsolete
    DESCRIPTION
        "The device network interface (such as eth0, eth1) to which this ARP entry
        corresponds. If the entry is on a VLAN, this is the Ethernet interface
        that VLAN is on."

    ::= { dpStatusARPStatusEntry 6 }

dpStatusARPStatusInterfaceType OBJECT-TYPE
    SYNTAX      INTEGER { 
                        other(1),
                        ethernet(6),
                        tunnel(131),
                        vLAN(135),
                        aggregate(161)
                }
    MAX-ACCESS  read-only
    STATUS      obsolete
    DESCRIPTION
        "The type of the interface this ARP entry is on. Ethernet indicates that it
        is on the base Ethernet MAC interface. VLAN indicates that it is on an
        IEEE 802.1Q VLAN on top of the base Ethernet MAC interface."

    ::= { dpStatusARPStatusEntry 7 }

dpStatusARPStatusVlanName OBJECT-TYPE
    SYNTAX      DisplayString
    MAX-ACCESS  read-only
    STATUS      obsolete
    DESCRIPTION
        "If this ARP entry is on a VLAN, this is the name of that VLAN."

    ::= { dpStatusARPStatusEntry 8 }

dpStatusDateTimeStatus OBJECT IDENTIFIER ::= { dpStatus 3 }

dpStatusDateTimeStatustime OBJECT-TYPE
    SYNTAX      TimeStamp
    MAX-ACCESS  read-only
    STATUS      current
    DESCRIPTION
        "The current local time. This time is obtained from the timezone settings
        established on the Time Settings object and with the date and time
        settings set on the System Control page."

    ::= { dpStatusDateTimeStatus 1 }

dpStatusDateTimeStatusuptime OBJECT-TYPE
    SYNTAX      TimeInterval
    MAX-ACCESS  read-only
    STATUS      obsolete
    DESCRIPTION
        "The total amount of time the appliance has been up since the last reload
        or reboot. Note that a shutdown and reload resets this counter."

    ::= { dpStatusDateTimeStatus 2 }

dpStatusDateTimeStatustimezone OBJECT-TYPE
    SYNTAX      DisplayString
    MAX-ACCESS  read-only
    STATUS      current
    DESCRIPTION
        "The name of the time zone currently in effect, as set on the Time Settings
        page."

    ::= { dpStatusDateTimeStatus 3 }

dpStatusDateTimeStatustzspec OBJECT-TYPE
    SYNTAX      DisplayString
    MAX-ACCESS  read-only
    STATUS      current
    DESCRIPTION
        "The POSIX.1 timezone specification. See time settings for more
        information."

    ::= { dpStatusDateTimeStatus 4 }

dpStatusDateTimeStatusbootuptime OBJECT-TYPE
    SYNTAX      TimeInterval
    MAX-ACCESS  read-only
    STATUS      obsolete
    DESCRIPTION
        "The total amount of time in seconds since the last reboot. Note that this
        counter is reset by a shutdown and reboot , but not by a shutdown and
        reload ."

    ::= { dpStatusDateTimeStatus 5 }

dpStatusDateTimeStatusuptime2 OBJECT-TYPE
    SYNTAX      TimeTicks
    MAX-ACCESS  read-only
    STATUS      current
    DESCRIPTION
        "The total amount of time the appliance has been up since the last reload
        or reboot. Note that a shutdown and reload resets this counter."

    ::= { dpStatusDateTimeStatus 6 }

dpStatusDateTimeStatusbootuptime2 OBJECT-TYPE
    SYNTAX      TimeTicks
    MAX-ACCESS  read-only
    STATUS      current
    DESCRIPTION
        "The total amount of time in seconds since the last reboot. Note that this
        counter is reset by a shutdown and reboot , but not by a shutdown and
        reload ."

    ::= { dpStatusDateTimeStatus 7 }

dpStatusVersion OBJECT IDENTIFIER ::= { dpStatus 4 }

dpStatusVersionVersion OBJECT-TYPE
    SYNTAX      DisplayString
    MAX-ACCESS  read-only
    STATUS      obsolete
    DESCRIPTION "Note: this is obsoleted and is replaced by dpStatusFirmwareVersion as of release 3.6.0"

    ::= { dpStatusVersion 1 }

dpStatusVersionBuild OBJECT-TYPE
    SYNTAX      DisplayString
    MAX-ACCESS  read-only
    STATUS      obsolete
    DESCRIPTION "Note: this is obsoleted and is replaced by dpStatusFirmwareVersion as of release 3.6.0"

    ::= { dpStatusVersion 2 }

dpStatusVersionBuildDate OBJECT-TYPE
    SYNTAX      DisplayString
    MAX-ACCESS  read-only
    STATUS      obsolete
    DESCRIPTION "Note: this is obsoleted and is replaced by dpStatusFirmwareVersion as of release 3.6.0"

    ::= { dpStatusVersion 3 }

dpStatusVersionWatchdogBuild OBJECT-TYPE
    SYNTAX      DisplayString
    MAX-ACCESS  read-only
    STATUS      obsolete
    DESCRIPTION "Note: this is obsoleted and is replaced by dpStatusFirmwareVersion as of release 3.6.0"

    ::= { dpStatusVersion 4 }

dpStatusVersionInstalledDPOS OBJECT-TYPE
    SYNTAX      DisplayString
    MAX-ACCESS  read-only
    STATUS      obsolete
    DESCRIPTION "Note: this is obsoleted and is replaced by dpStatusFirmwareVersion as of release 3.6.0"

    ::= { dpStatusVersion 5 }

dpStatusVersionRunningDPOS OBJECT-TYPE
    SYNTAX      DisplayString
    MAX-ACCESS  read-only
    STATUS      obsolete
    DESCRIPTION "Note: this is obsoleted and is replaced by dpStatusFirmwareVersion as of release 3.6.0"

    ::= { dpStatusVersion 6 }

dpStatusVersionLibraryMQ OBJECT-TYPE
    SYNTAX      DisplayString
    MAX-ACCESS  read-only
    STATUS      obsolete
    DESCRIPTION "Note: this is obsoleted and is replaced by dpStatusFirmwareVersion as of release 3.6.0"

    ::= { dpStatusVersion 7 }

dpStatusVersionLibraryTAM OBJECT-TYPE
    SYNTAX      DisplayString
    MAX-ACCESS  read-only
    STATUS      obsolete
    DESCRIPTION "Note: this is obsoleted and is replaced by dpStatusFirmwareVersion as of release 3.6.0"

    ::= { dpStatusVersion 8 }

dpStatusVersionCoprocVersion OBJECT-TYPE
    SYNTAX      DisplayString
    MAX-ACCESS  read-only
    STATUS      obsolete
    DESCRIPTION "Note: this is obsoleted and is replaced by dpStatusFirmwareVersion as of release 3.6.0"

    ::= { dpStatusVersion 9 }

dpStatusVersionLibraryReserved OBJECT-TYPE
    SYNTAX      DisplayString
    MAX-ACCESS  read-only
    STATUS      obsolete
    DESCRIPTION "Note: this is obsoleted and is replaced by dpStatusFirmwareVersion as of release 3.6.0"

    ::= { dpStatusVersion 10 }

dpStatusVersionLibraryODBC OBJECT-TYPE
    SYNTAX      DisplayString
    MAX-ACCESS  read-only
    STATUS      obsolete
    DESCRIPTION "Note: this is obsoleted and is replaced by dpStatusFirmwareVersion as of release 3.6.0"

    ::= { dpStatusVersion 11 }

dpStatusVersionLibraryTibco OBJECT-TYPE
    SYNTAX      DisplayString
    MAX-ACCESS  read-only
    STATUS      obsolete
    DESCRIPTION "Note: this is obsoleted and is replaced by dpStatusFirmwareVersion as of release 3.6.0"

    ::= { dpStatusVersion 12 }

dpStatusVersionLibraryXMS OBJECT-TYPE
    SYNTAX      DisplayString
    MAX-ACCESS  read-only
    STATUS      obsolete
    DESCRIPTION "Note: this is obsoleted and is replaced by dpStatusFirmwareVersion as of release 3.6.0"

    ::= { dpStatusVersion 13 }

dpStatusVersionSerial OBJECT-TYPE
    SYNTAX      DisplayString
    MAX-ACCESS  read-only
    STATUS      obsolete
    DESCRIPTION "Note: this is obsoleted and is replaced by dpStatusFirmwareVersion as of release 3.6.0"

    ::= { dpStatusVersion 14 }

dpStatusVersionXMLAccelerator OBJECT-TYPE
    SYNTAX      DisplayString
    MAX-ACCESS  read-only
    STATUS      obsolete
    DESCRIPTION "Note: this is obsoleted and is replaced by dpStatusFirmwareVersion as of release 3.6.0"

    ::= { dpStatusVersion 15 }

dpStatusMemoryStatus OBJECT IDENTIFIER ::= { dpStatus 5 }

dpStatusMemoryStatusUsage OBJECT-TYPE
    SYNTAX      Unsigned32
    UNITS       "%"
    MAX-ACCESS  read-only
    STATUS      current
    DESCRIPTION
        "The instantaneous memory usage as a percentage of the total memory."

    ::= { dpStatusMemoryStatus 1 }

dpStatusMemoryStatusTotalMemory OBJECT-TYPE
    SYNTAX      Unsigned32
    UNITS       "kilobytes"
    MAX-ACCESS  read-only
    STATUS      current
    DESCRIPTION
        "The total memory of the system in kilobytes. The total memory equals the
        amount of installed memory minus the amount of reserved memory."

    ::= { dpStatusMemoryStatus 2 }

dpStatusMemoryStatusUsedMemory OBJECT-TYPE
    SYNTAX      Unsigned32
    UNITS       "kilobytes"
    MAX-ACCESS  read-only
    STATUS      current
    DESCRIPTION
        "The amount of memory that is currently in use. The used memory equals the
        amount of total memory minus the amount of free memory. The used memory
        does not include any hold memory."

    ::= { dpStatusMemoryStatus 3 }

dpStatusMemoryStatusFreeMemory OBJECT-TYPE
    SYNTAX      Unsigned32
    UNITS       "kilobytes"
    MAX-ACCESS  read-only
    STATUS      current
    DESCRIPTION
        "The amount of memory that is currently not in use and is therefore
        available. The free memory value includes any hold memory that is not
        currently in use."

    ::= { dpStatusMemoryStatus 4 }

dpStatusMemoryStatusReqMemory OBJECT-TYPE
    SYNTAX      Unsigned32
    UNITS       "kilobytes"
    MAX-ACCESS  read-only
    STATUS      current
    DESCRIPTION
        "The amount of memory that has been requested. Requested memory is not
        reported as used memory until the memory is actually in use."

    ::= { dpStatusMemoryStatus 5 }

dpStatusMemoryStatusXG4Usage OBJECT-TYPE
    SYNTAX      Unsigned32
    UNITS       "%"
    MAX-ACCESS  read-only
    STATUS      current
    DESCRIPTION
        "If an XML accelerator is available, the percentage of memory that is
        off-loaded to the XML accelerator."

    ::= { dpStatusMemoryStatus 6 }

dpStatusMemoryStatusHoldMemory OBJECT-TYPE
    SYNTAX      Unsigned32
    UNITS       "kilobytes"
    MAX-ACCESS  read-only
    STATUS      current
    DESCRIPTION
        "The amount of memory that is reserved by the appliance itself."

    ::= { dpStatusMemoryStatus 7 }

dpStatusMemoryStatusReservedMemory OBJECT-TYPE
    SYNTAX      Unsigned32
    UNITS       "kilobytes"
    MAX-ACCESS  read-only
    STATUS      current
    DESCRIPTION
        "The reserved memory equals the amount of installed memory minus the amount
        of total memory."

    ::= { dpStatusMemoryStatus 8 }

dpStatusMemoryStatusInstalledMemory OBJECT-TYPE
    SYNTAX      Unsigned32
    UNITS       "kilobytes"
    MAX-ACCESS  read-only
    STATUS      current
    DESCRIPTION
        "The amount of physical memory in the appliance."

    ::= { dpStatusMemoryStatus 9 }

--

dpStatusRoutingStatusTable OBJECT-TYPE
    SYNTAX      SEQUENCE OF DPStatusRoutingStatusEntry
    MAX-ACCESS  not-accessible
    STATUS      obsolete
    DESCRIPTION
        "This table describes all the static IP routes on the system. This table
        was deprecated because it could not support VLANs.
        Note: this is obsoleted and is replaced by dpStatusRoutingStatus2 as of release 3.6.1"

    ::= { dpStatus 6 }

dpStatusRoutingStatusEntry OBJECT-TYPE
    SYNTAX      DPStatusRoutingStatusEntry
    MAX-ACCESS  not-accessible
    STATUS      obsolete
    DESCRIPTION "Table row."
    INDEX { dpStatusRoutingStatusDestination, dpStatusRoutingStatusInterface }

    ::= { dpStatusRoutingStatusTable 1 }

DPStatusRoutingStatusEntry ::= SEQUENCE {
    dpStatusRoutingStatusDestination    IpNetworkAddress,
    dpStatusRoutingStatusInterface    INTEGER,
    dpStatusRoutingStatusGateway    IpAddress,
    dpStatusRoutingStatusMetric    Unsigned32
}

dpStatusRoutingStatusDestination OBJECT-TYPE
    SYNTAX      IpNetworkAddress
    MAX-ACCESS  read-only
    STATUS      obsolete
    DESCRIPTION
        "The IP subnet that is the destination of this route."

    ::= { dpStatusRoutingStatusEntry 1 }

dpStatusRoutingStatusInterface OBJECT-TYPE
    SYNTAX      INTEGER { 
                        eth0(1),
                        eth1(2),
                        eth2(3),
                        eth3(4),
                        mgt0(5),
                        eth4(6),
                        eth5(8),
                        eth6(9),
                        eth7(10),
                        eth8(11),
                        eth9(12),
                        eth10(13),
                        tun(14),
                        mgt1(15),
                        eth11(16),
                        eth12(17),
                        eth13(18),
                        eth14(19),
                        eth15(20),
                        eth16(21),
                        eth17(22),
                        eth20(23),
                        eth21(24),
                        eth22(25),
                        eth23(26),
                        eth24(27),
                        eth25(28),
                        eth26(29),
                        eth27(30),
                        eth30(31),
                        eth31(32),
                        eth32(33),
                        eth33(34)
                }
    MAX-ACCESS  read-only
    STATUS      obsolete
    DESCRIPTION
        "The Ethernet interface this route is via."

    ::= { dpStatusRoutingStatusEntry 2 }

dpStatusRoutingStatusGateway OBJECT-TYPE
    SYNTAX      IpAddress
    MAX-ACCESS  read-only
    STATUS      obsolete
    DESCRIPTION
        "The next hop gateway that traffic using this route is sent to. If the next
        hop is 0.0.0.0, then the route is via the interface (no next-hop router)."

    ::= { dpStatusRoutingStatusEntry 3 }

dpStatusRoutingStatusMetric OBJECT-TYPE
    SYNTAX      Unsigned32
    MAX-ACCESS  read-only
    STATUS      obsolete
    DESCRIPTION
        "The metric for this route. Typically configured in units of hops, but it
        is really user-selected. Given ultiple routes with the same destination,
        the one with the lowest metric is used."

    ::= { dpStatusRoutingStatusEntry 4 }

--

dpStatusStylesheetStatusTable OBJECT-TYPE
    SYNTAX      SEQUENCE OF DPStatusStylesheetStatusEntry
    MAX-ACCESS  not-accessible
    STATUS      deprecated
    DESCRIPTION "Note: this is obsoleted and is replaced by dpStatusStylesheetStatusSimpleIndex as of release
    3.5.1"

    ::= { dpStatus 7 }

dpStatusStylesheetStatusEntry OBJECT-TYPE
    SYNTAX      DPStatusStylesheetStatusEntry
    MAX-ACCESS  not-accessible
    STATUS      deprecated
    DESCRIPTION "Table row."
    INDEX { dpConfigXMLManagerIndex, dpStatusStylesheetStatusOutputMode, IMPLIED dpStatusStylesheetStatusURL }

    ::= { dpStatusStylesheetStatusTable 1 }

DPStatusStylesheetStatusEntry ::= SEQUENCE {
    dpStatusStylesheetStatusXMLManager    DisplayString,
    dpStatusStylesheetStatusOutputMode    INTEGER,
    dpStatusStylesheetStatusURL    DisplayString,
    dpStatusStylesheetStatusCompileOptions    DisplayString,
    dpStatusStylesheetStatusStatus    INTEGER,
    dpStatusStylesheetStatusCompileSpeed    DPTimeIntervalMillis,
    dpStatusStylesheetStatusRefreshInterval    DPTimeIntervalSeconds,
    dpStatusStylesheetStatusFlushable    INTEGER,
    dpStatusStylesheetStatusLastRefresh    TimeStamp,
    dpStatusStylesheetStatusMessage    DisplayString,
    dpStatusStylesheetStatusLog    DisplayString,
    dpStatusStylesheetStatusXG4Enabled    INTEGER,
    dpStatusStylesheetStatusXG4Size    Unsigned32
}

dpStatusStylesheetStatusXMLManager OBJECT-TYPE
    SYNTAX      DisplayString
    MAX-ACCESS  read-only
    STATUS      deprecated
    DESCRIPTION "No description yet."

    ::= { dpStatusStylesheetStatusEntry 1 }

dpStatusStylesheetStatusOutputMode OBJECT-TYPE
    SYNTAX      INTEGER { 
                        general(1),
                        stream(2),
                        context(3),
                        events(4)
                }
    MAX-ACCESS  read-only
    STATUS      deprecated
    DESCRIPTION "No description yet."

    ::= { dpStatusStylesheetStatusEntry 2 }

dpStatusStylesheetStatusURL OBJECT-TYPE
    SYNTAX      DisplayString
    MAX-ACCESS  read-only
    STATUS      deprecated
    DESCRIPTION "No description yet."

    ::= { dpStatusStylesheetStatusEntry 3 }

dpStatusStylesheetStatusCompileOptions OBJECT-TYPE
    SYNTAX      DisplayString
    MAX-ACCESS  read-only
    STATUS      deprecated
    DESCRIPTION "No description yet."

    ::= { dpStatusStylesheetStatusEntry 4 }

dpStatusStylesheetStatusStatus OBJECT-TYPE
    SYNTAX      INTEGER { 
                        ready(1),
                        pending(2),
                        bad(3),
                        expired(4)
                }
    MAX-ACCESS  read-only
    STATUS      deprecated
    DESCRIPTION "No description yet."

    ::= { dpStatusStylesheetStatusEntry 5 }

dpStatusStylesheetStatusCompileSpeed OBJECT-TYPE
    SYNTAX      DPTimeIntervalMillis
    UNITS       "msec"
    MAX-ACCESS  read-only
    STATUS      deprecated
    DESCRIPTION "No description yet."

    ::= { dpStatusStylesheetStatusEntry 6 }

dpStatusStylesheetStatusRefreshInterval OBJECT-TYPE
    SYNTAX      DPTimeIntervalSeconds
    UNITS       "sec"
    MAX-ACCESS  read-only
    STATUS      deprecated
    DESCRIPTION "No description yet."

    ::= { dpStatusStylesheetStatusEntry 7 }

dpStatusStylesheetStatusFlushable OBJECT-TYPE
    SYNTAX      INTEGER { 
                        on(1),
                        off(2)
                }
    MAX-ACCESS  read-only
    STATUS      deprecated
    DESCRIPTION "No description yet."

    ::= { dpStatusStylesheetStatusEntry 8 }

dpStatusStylesheetStatusLastRefresh OBJECT-TYPE
    SYNTAX      TimeStamp
    MAX-ACCESS  read-only
    STATUS      deprecated
    DESCRIPTION "No description yet."

    ::= { dpStatusStylesheetStatusEntry 9 }

dpStatusStylesheetStatusMessage OBJECT-TYPE
    SYNTAX      DisplayString
    MAX-ACCESS  read-only
    STATUS      deprecated
    DESCRIPTION "No description yet."

    ::= { dpStatusStylesheetStatusEntry 10 }

dpStatusStylesheetStatusLog OBJECT-TYPE
    SYNTAX      DisplayString
    MAX-ACCESS  read-only
    STATUS      deprecated
    DESCRIPTION "No description yet."

    ::= { dpStatusStylesheetStatusEntry 11 }

dpStatusStylesheetStatusXG4Enabled OBJECT-TYPE
    SYNTAX      INTEGER { 
                        on(1),
                        off(2)
                }
    MAX-ACCESS  read-only
    STATUS      deprecated
    DESCRIPTION "No description yet."

    ::= { dpStatusStylesheetStatusEntry 12 }

dpStatusStylesheetStatusXG4Size OBJECT-TYPE
    SYNTAX      Unsigned32
    UNITS       "%"
    MAX-ACCESS  read-only
    STATUS      deprecated
    DESCRIPTION "No description yet."

    ::= { dpStatusStylesheetStatusEntry 13 }

--

dpStatusStylesheetCachingSummaryTable OBJECT-TYPE
    SYNTAX      SEQUENCE OF DPStatusStylesheetCachingSummaryEntry
    MAX-ACCESS  not-accessible
    STATUS      current
    DESCRIPTION
        "The current status of the stylesheet cache. The cache contains a copy of
        all style sheets or WSDL files compiled within the refresh time, total
        count limit, or total cache size."

    ::= { dpStatus 8 }

dpStatusStylesheetCachingSummaryEntry OBJECT-TYPE
    SYNTAX      DPStatusStylesheetCachingSummaryEntry
    MAX-ACCESS  not-accessible
    STATUS      current
    DESCRIPTION "Table row."
    INDEX { IMPLIED dpConfigXMLManagerIndex }

    ::= { dpStatusStylesheetCachingSummaryTable 1 }

DPStatusStylesheetCachingSummaryEntry ::= SEQUENCE {
    dpStatusStylesheetCachingSummaryXMLManager    DisplayString,
    dpStatusStylesheetCachingSummaryCacheSize    Unsigned32,
    dpStatusStylesheetCachingSummaryCacheCount    Unsigned32,
    dpStatusStylesheetCachingSummaryReadyCount    Unsigned32,
    dpStatusStylesheetCachingSummaryPendingCount    Unsigned32,
    dpStatusStylesheetCachingSummaryBadCount    Unsigned32,
    dpStatusStylesheetCachingSummaryDupCount    Unsigned32,
    dpStatusStylesheetCachingSummaryCacheKBCount    Unsigned32
}

dpStatusStylesheetCachingSummaryXMLManager OBJECT-TYPE
    SYNTAX      DisplayString
    MAX-ACCESS  read-only
    STATUS      current
    DESCRIPTION
        "The name of the XML manager that is managing the style sheets. More than
        one service can use an XML manager."

    ::= { dpStatusStylesheetCachingSummaryEntry 1 }

dpStatusStylesheetCachingSummaryCacheSize OBJECT-TYPE
    SYNTAX      Unsigned32
    MAX-ACCESS  read-only
    STATUS      current
    DESCRIPTION
        "The maximum number of style sheets that can be added to the cache."

    ::= { dpStatusStylesheetCachingSummaryEntry 2 }

dpStatusStylesheetCachingSummaryCacheCount OBJECT-TYPE
    SYNTAX      Unsigned32
    MAX-ACCESS  read-only
    STATUS      current
    DESCRIPTION
        "The number of style sheets in the cache."

    ::= { dpStatusStylesheetCachingSummaryEntry 3 }

dpStatusStylesheetCachingSummaryReadyCount OBJECT-TYPE
    SYNTAX      Unsigned32
    MAX-ACCESS  read-only
    STATUS      current
    DESCRIPTION
        "The number of style sheets in the cache that are available for use."

    ::= { dpStatusStylesheetCachingSummaryEntry 4 }

dpStatusStylesheetCachingSummaryPendingCount OBJECT-TYPE
    SYNTAX      Unsigned32
    MAX-ACCESS  read-only
    STATUS      current
    DESCRIPTION
        "The number of style sheets in the cache that are pending compilation."

    ::= { dpStatusStylesheetCachingSummaryEntry 5 }

dpStatusStylesheetCachingSummaryBadCount OBJECT-TYPE
    SYNTAX      Unsigned32
    MAX-ACCESS  read-only
    STATUS      current
    DESCRIPTION
        "The number of style sheets in cache that the appliance encountered
        compilation errors for use during run time. When errors occur, the style
        sheet is cached and marked as bad. Flush these style sheets from the cache
        to prevent runtime errors."

    ::= { dpStatusStylesheetCachingSummaryEntry 6 }

dpStatusStylesheetCachingSummaryDupCount OBJECT-TYPE
    SYNTAX      Unsigned32
    MAX-ACCESS  read-only
    STATUS      current
    DESCRIPTION
        "The number of requests to compile a style sheet that is already cached."

    ::= { dpStatusStylesheetCachingSummaryEntry 7 }

dpStatusStylesheetCachingSummaryCacheKBCount OBJECT-TYPE
    SYNTAX      Unsigned32
    UNITS       "KB"
    MAX-ACCESS  read-only
    STATUS      current
    DESCRIPTION
        "The total amount of memory that cached style sheets use."

    ::= { dpStatusStylesheetCachingSummaryEntry 8 }

--

dpStatusEthernetInterfaceStatusTable OBJECT-TYPE
    SYNTAX      SEQUENCE OF DPStatusEthernetInterfaceStatusEntry
    MAX-ACCESS  not-accessible
    STATUS      deprecated
    DESCRIPTION
        "This table provides the status of all Ethernet network interfaces on the
        appliance."

    ::= { dpStatus 10 }

dpStatusEthernetInterfaceStatusEntry OBJECT-TYPE
    SYNTAX      DPStatusEthernetInterfaceStatusEntry
    MAX-ACCESS  not-accessible
    STATUS      deprecated
    DESCRIPTION "Table row."
    INDEX { dpStatusEthernetInterfaceStatusName }

    ::= { dpStatusEthernetInterfaceStatusTable 1 }

DPStatusEthernetInterfaceStatusEntry ::= SEQUENCE {
    dpStatusEthernetInterfaceStatusName    INTEGER,
    dpStatusEthernetInterfaceStatusIP    IpNetworkAddress,
    dpStatusEthernetInterfaceStatusMACAddress    MacAddress,
    dpStatusEthernetInterfaceStatusStatus    INTEGER,
    dpStatusEthernetInterfaceStatusNegotiate    INTEGER,
    dpStatusEthernetInterfaceStatusMode    INTEGER,
    dpStatusEthernetInterfaceStatusMTU    Unsigned32,
    dpStatusEthernetInterfaceStatusRxKbytes    Counter32,
    dpStatusEthernetInterfaceStatusRxPackets    Counter32,
    dpStatusEthernetInterfaceStatusRxErrors    Counter32,
    dpStatusEthernetInterfaceStatusRxDrops    Counter32,
    dpStatusEthernetInterfaceStatusTxKbytes    Counter32,
    dpStatusEthernetInterfaceStatusTxPackets    Counter32,
    dpStatusEthernetInterfaceStatusTxErrors    Counter32,
    dpStatusEthernetInterfaceStatusTxDrops    Counter32,
    dpStatusEthernetInterfaceStatusCollisions    Counter32,
    dpStatusEthernetInterfaceStatusRxHCBytes    Counter64,
    dpStatusEthernetInterfaceStatusRxHCPackets    Counter64,
    dpStatusEthernetInterfaceStatusRxErrors2    Counter32,
    dpStatusEthernetInterfaceStatusRxDrops2    Counter32,
    dpStatusEthernetInterfaceStatusTxHCBytes    Counter64,
    dpStatusEthernetInterfaceStatusTxHCPackets    Counter64,
    dpStatusEthernetInterfaceStatusTxErrors2    Counter32,
    dpStatusEthernetInterfaceStatusTxDrops2    Counter32,
    dpStatusEthernetInterfaceStatusCollisions2    Counter32,
    dpStatusEthernetInterfaceStatusFlowControlNegotiation    INTEGER,
    dpStatusEthernetInterfaceStatusFlowControlStatus    INTEGER
}

dpStatusEthernetInterfaceStatusName OBJECT-TYPE
    SYNTAX      INTEGER { 
                        eth0(1),
                        eth1(2),
                        eth2(3),
                        eth3(4),
                        mgt0(5),
                        eth4(6),
                        eth5(8),
                        eth6(9),
                        eth7(10),
                        eth8(11),
                        eth9(12),
                        eth10(13),
                        tun(14),
                        mgt1(15),
                        eth11(16),
                        eth12(17),
                        eth13(18),
                        eth14(19),
                        eth15(20),
                        eth16(21),
                        eth17(22),
                        eth20(23),
                        eth21(24),
                        eth22(25),
                        eth23(26),
                        eth24(27),
                        eth25(28),
                        eth26(29),
                        eth27(30),
                        eth30(31),
                        eth31(32),
                        eth32(33),
                        eth33(34)
                }
    MAX-ACCESS  read-only
    STATUS      deprecated
    DESCRIPTION
        "The name of the Ethernet interface."

    ::= { dpStatusEthernetInterfaceStatusEntry 1 }

dpStatusEthernetInterfaceStatusIP OBJECT-TYPE
    SYNTAX      IpNetworkAddress
    MAX-ACCESS  read-only
    STATUS      deprecated
    DESCRIPTION
        "The IP address for the interface."

    ::= { dpStatusEthernetInterfaceStatusEntry 2 }

dpStatusEthernetInterfaceStatusMACAddress OBJECT-TYPE
    SYNTAX      MacAddress
    MAX-ACCESS  read-only
    STATUS      deprecated
    DESCRIPTION
        "The working physical address of the Ethernet interface. The default value
        is programmed in the Ethernet hardware. Interfaces configured for standby
        mode use a configured physical address."

    ::= { dpStatusEthernetInterfaceStatusEntry 3 }

dpStatusEthernetInterfaceStatusStatus OBJECT-TYPE
    SYNTAX      INTEGER { 
                        ok(1),
                        no-link(2)
                }
    MAX-ACCESS  read-only
    STATUS      deprecated
    DESCRIPTION
        "The current link state of the interface."

    ::= { dpStatusEthernetInterfaceStatusEntry 4 }

dpStatusEthernetInterfaceStatusNegotiate OBJECT-TYPE
    SYNTAX      INTEGER { 
                        no(1),
                        auto(2),
                        failed(3),
                        restarted(4)
                }
    MAX-ACCESS  read-only
    STATUS      deprecated
    DESCRIPTION
        "The current Ethernet negotiation status of the interface."

    ::= { dpStatusEthernetInterfaceStatusEntry 5 }

dpStatusEthernetInterfaceStatusMode OBJECT-TYPE
    SYNTAX      INTEGER { 
                        dr10BASE-T-HD(0),
                        dr10BASE-T-FD(256),
                        dr100BASE-TX-HD(8192),
                        dr100BASE-TX-FD(8448),
                        dr1000BASE-T-FD(65535),
                        dr1000BASE-KX(65536),
                        dr10GBASE-KX4(131072),
                        dr40GBASE-CR4(262144),
                        none(524288)
                }
    MAX-ACCESS  read-only
    STATUS      deprecated
    DESCRIPTION
        "The actual fixed, configured, or negotiated Ethernet PHY mode of the
        interface. The value includes the speed and the duplex mode."

    ::= { dpStatusEthernetInterfaceStatusEntry 6 }

dpStatusEthernetInterfaceStatusMTU OBJECT-TYPE
    SYNTAX      Unsigned32
    MAX-ACCESS  read-only
    STATUS      deprecated
    DESCRIPTION
        "The current Maximum Transmission Unit (MTU) for the interface."

    ::= { dpStatusEthernetInterfaceStatusEntry 7 }

dpStatusEthernetInterfaceStatusRxKbytes OBJECT-TYPE
    SYNTAX      Counter32
    MAX-ACCESS  read-only
    STATUS      deprecated
    DESCRIPTION
        "The number of kilobytes of traffic that the interface received. Obsoleted
        in release 5.0.0.0 due to incompatible SNMP changes in release 4.0.1.0.
        When read via SNMP, the value type improperly returns Counter64 from
        release 4.0.1.0 to release 4.0.1.7 and from release 4.0.2.0 to release
        4.0.2.3."

    ::= { dpStatusEthernetInterfaceStatusEntry 8 }

dpStatusEthernetInterfaceStatusRxPackets OBJECT-TYPE
    SYNTAX      Counter32
    MAX-ACCESS  read-only
    STATUS      deprecated
    DESCRIPTION
        "The number of packets that the interface received. Obsoleted in release
        5.0.0.0 due to incompatible SNMP changes in release 4.0.1.0. When read via
        SNMP, the value type improperly returns Counter64 from release 4.0.1.0 to
        release 4.0.1.7 and from release 4.0.2.0 to release 4.0.2.3."

    ::= { dpStatusEthernetInterfaceStatusEntry 9 }

dpStatusEthernetInterfaceStatusRxErrors OBJECT-TYPE
    SYNTAX      Counter32
    MAX-ACCESS  read-only
    STATUS      deprecated
    DESCRIPTION
        "The number of errors that the interface encountered during reception.
        Obsoleted in release 5.0.0.0 due to incompatible SNMP changes in release
        4.0.1.0. When read via SNMP, the value type improperly returns Counter64
        from release 4.0.1.0 to release 4.0.1.7 and from release 4.0.2.0 to
        release 4.0.2.3."

    ::= { dpStatusEthernetInterfaceStatusEntry 10 }

dpStatusEthernetInterfaceStatusRxDrops OBJECT-TYPE
    SYNTAX      Counter32
    MAX-ACCESS  read-only
    STATUS      deprecated
    DESCRIPTION
        "The number of received packets that the interface dropped. Obsoleted in
        release 5.0.0.0 due to incompatible SNMP changes in release 4.0.1.0. When
        read via SNMP, the value type improperly returns Counter64 from release
        4.0.1.0 to release 4.0.1.7 and from release 4.0.2.0 to release 4.0.2.3."

    ::= { dpStatusEthernetInterfaceStatusEntry 11 }

dpStatusEthernetInterfaceStatusTxKbytes OBJECT-TYPE
    SYNTAX      Counter32
    MAX-ACCESS  read-only
    STATUS      deprecated
    DESCRIPTION
        "The number of kilobytes of traffic that the interface transmitted.
        Obsoleted in release 5.0.0.0 due to incompatible SNMP changes in release
        4.0.1.0. When read via SNMP, the value type improperly returns Counter64
        from release 4.0.1.0 to release 4.0.1.7 and from release 4.0.2.0 to
        release 4.0.2.3."

    ::= { dpStatusEthernetInterfaceStatusEntry 12 }

dpStatusEthernetInterfaceStatusTxPackets OBJECT-TYPE
    SYNTAX      Counter32
    MAX-ACCESS  read-only
    STATUS      deprecated
    DESCRIPTION
        "The number of packets that the interface transmitted. Obsoleted in release
        5.0.0.0 due to incompatible SNMP changes in release 4.0.1.0. When read via
        SNMP, the value type improperly returns Counter64 from release 4.0.1.0 to
        release 4.0.1.7 and from release 4.0.2.0 to release 4.0.2.3."

    ::= { dpStatusEthernetInterfaceStatusEntry 13 }

dpStatusEthernetInterfaceStatusTxErrors OBJECT-TYPE
    SYNTAX      Counter32
    MAX-ACCESS  read-only
    STATUS      deprecated
    DESCRIPTION
        "The number of errors that the interface encountered during transmission.
        When read via SNMP, Obsoleted in release 5.0.0.0 due to incompatible SNMP
        changes in release 4.0.1.0. Obsoleted in release 5.0.0.0 due to
        incompatible SNMP changes in release 4.0.1.0. When read via SNMP, the
        value type improperly returns Counter64 from release 4.0.1.0 to release
        4.0.1.7 and from release 4.0.2.0 to release 4.0.2.3."

    ::= { dpStatusEthernetInterfaceStatusEntry 14 }

dpStatusEthernetInterfaceStatusTxDrops OBJECT-TYPE
    SYNTAX      Counter32
    MAX-ACCESS  read-only
    STATUS      deprecated
    DESCRIPTION
        "The number of packets that the interface dropped during transmission.
        Obsoleted in release 5.0.0.0 due to incompatible SNMP changes in release
        4.0.1.0. When read via SNMP, the value type improperly returns Counter64
        from release 4.0.1.0 to release 4.0.1.7 and from release 4.0.2.0 to
        release 4.0.2.3."

    ::= { dpStatusEthernetInterfaceStatusEntry 15 }

dpStatusEthernetInterfaceStatusCollisions OBJECT-TYPE
    SYNTAX      Counter32
    MAX-ACCESS  read-only
    STATUS      deprecated
    DESCRIPTION
        "The number of collisions on the interface. Obsoleted in release 5.0.0.0
        due to incompatible SNMP changes in release 4.0.1.0. When read via SNMP,
        the value type improperly returns Counter64 from release 4.0.1.0 to
        release 4.0.1.7 and from release 4.0.2.0 to release 4.0.2.3."

    ::= { dpStatusEthernetInterfaceStatusEntry 16 }

dpStatusEthernetInterfaceStatusRxHCBytes OBJECT-TYPE
    SYNTAX      Counter64
    MAX-ACCESS  read-only
    STATUS      deprecated
    DESCRIPTION
        "The number of bytes of traffic that the interface received."

    ::= { dpStatusEthernetInterfaceStatusEntry 17 }

dpStatusEthernetInterfaceStatusRxHCPackets OBJECT-TYPE
    SYNTAX      Counter64
    MAX-ACCESS  read-only
    STATUS      deprecated
    DESCRIPTION
        "The number of packets that the interface received."

    ::= { dpStatusEthernetInterfaceStatusEntry 18 }

dpStatusEthernetInterfaceStatusRxErrors2 OBJECT-TYPE
    SYNTAX      Counter32
    MAX-ACCESS  read-only
    STATUS      deprecated
    DESCRIPTION
        "The number of errors that the interface encountered during reception."

    ::= { dpStatusEthernetInterfaceStatusEntry 19 }

dpStatusEthernetInterfaceStatusRxDrops2 OBJECT-TYPE
    SYNTAX      Counter32
    MAX-ACCESS  read-only
    STATUS      deprecated
    DESCRIPTION
        "The number of received packets that the interface dropped."

    ::= { dpStatusEthernetInterfaceStatusEntry 20 }

dpStatusEthernetInterfaceStatusTxHCBytes OBJECT-TYPE
    SYNTAX      Counter64
    MAX-ACCESS  read-only
    STATUS      deprecated
    DESCRIPTION
        "The number of bytes of traffic that the interface transmitted."

    ::= { dpStatusEthernetInterfaceStatusEntry 21 }

dpStatusEthernetInterfaceStatusTxHCPackets OBJECT-TYPE
    SYNTAX      Counter64
    MAX-ACCESS  read-only
    STATUS      deprecated
    DESCRIPTION
        "The number of packets that the interface transmitted."

    ::= { dpStatusEthernetInterfaceStatusEntry 22 }

dpStatusEthernetInterfaceStatusTxErrors2 OBJECT-TYPE
    SYNTAX      Counter32
    MAX-ACCESS  read-only
    STATUS      deprecated
    DESCRIPTION
        "The number of errors that the interface encountered during transmission."

    ::= { dpStatusEthernetInterfaceStatusEntry 23 }

dpStatusEthernetInterfaceStatusTxDrops2 OBJECT-TYPE
    SYNTAX      Counter32
    MAX-ACCESS  read-only
    STATUS      deprecated
    DESCRIPTION
        "The number of packets that the interface dropped during transmission."

    ::= { dpStatusEthernetInterfaceStatusEntry 24 }

dpStatusEthernetInterfaceStatusCollisions2 OBJECT-TYPE
    SYNTAX      Counter32
    MAX-ACCESS  read-only
    STATUS      deprecated
    DESCRIPTION
        "The number of collisions on the interface."

    ::= { dpStatusEthernetInterfaceStatusEntry 25 }

dpStatusEthernetInterfaceStatusFlowControlNegotiation OBJECT-TYPE
    SYNTAX      INTEGER { 
                        no(1),
                        auto(2),
                        unknown(3)
                }
    MAX-ACCESS  read-only
    STATUS      deprecated
    DESCRIPTION
        "Specifies whether IEEE 802.3x Ethernet PAUSE frame autonegotiation been
        performed on this interface."

    ::= { dpStatusEthernetInterfaceStatusEntry 26 }

dpStatusEthernetInterfaceStatusFlowControlStatus OBJECT-TYPE
    SYNTAX      INTEGER { 
                        disabled(1),
                        tx(2),
                        rx(3),
                        full(4),
                        unknown(5)
                }
    MAX-ACCESS  read-only
    STATUS      deprecated
    DESCRIPTION
        "Status of IEEE 802.3x Ethernet flow control using PAUSE frames, as
        configured or auto-negotiated on this interface."

    ::= { dpStatusEthernetInterfaceStatusEntry 27 }

--

dpStatusTCPTableTable OBJECT-TYPE
    SYNTAX      SEQUENCE OF DPStatusTCPTableEntry
    MAX-ACCESS  not-accessible
    STATUS      current
    DESCRIPTION
        "This table describes all TCP connections on the system. Active connections
        and listeners are included. For listeners that are related to router
        configuration objects, the table indicates with what object the listener
        is associated."

    ::= { dpStatus 11 }

dpStatusTCPTableEntry OBJECT-TYPE
    SYNTAX      DPStatusTCPTableEntry
    MAX-ACCESS  not-accessible
    STATUS      current
    DESCRIPTION "Table row."
    INDEX { dpStatusTCPTablelocalIP, dpStatusTCPTablelocalPort, dpStatusTCPTableremoteIP, dpStatusTCPTableremotePort }

    ::= { dpStatusTCPTableTable 1 }

DPStatusTCPTableEntry ::= SEQUENCE {
    dpStatusTCPTablelocalIP    IpAddress,
    dpStatusTCPTablelocalPort    Unsigned32,
    dpStatusTCPTableremoteIP    IpAddress,
    dpStatusTCPTableremotePort    Unsigned32,
    dpStatusTCPTablestate    INTEGER,
    dpStatusTCPTableserviceDomain    DisplayString,
    dpStatusTCPTableserviceClass    INTEGER,
    dpStatusTCPTableserviceName    DisplayString
}

dpStatusTCPTablelocalIP OBJECT-TYPE
    SYNTAX      IpAddress
    MAX-ACCESS  read-only
    STATUS      current
    DESCRIPTION
        "The local IP address of this TCP connection. For connections in the listen
        state, an IP address of 0.0.0.0 means that connections will be accepted at
        any IP address of the system. A specific IP address indicates that
        connections will only be accepted at that IP address."

    ::= { dpStatusTCPTableEntry 1 }

dpStatusTCPTablelocalPort OBJECT-TYPE
    SYNTAX      Unsigned32 (0..65535)
    MAX-ACCESS  read-only
    STATUS      current
    DESCRIPTION
        "The local TCP port number of this TCP connection."

    ::= { dpStatusTCPTableEntry 2 }

dpStatusTCPTableremoteIP OBJECT-TYPE
    SYNTAX      IpAddress
    MAX-ACCESS  read-only
    STATUS      current
    DESCRIPTION
        "The remote IP address of this TCP connection. The value is 0.0.0.0 for
        connections in the listen state. The value is a specific IP address for
        established connections."

    ::= { dpStatusTCPTableEntry 3 }

dpStatusTCPTableremotePort OBJECT-TYPE
    SYNTAX      Unsigned32 (0..65535)
    MAX-ACCESS  read-only
    STATUS      current
    DESCRIPTION
        "The remote TCP port number of this TCP connection."

    ::= { dpStatusTCPTableEntry 4 }

dpStatusTCPTablestate OBJECT-TYPE
    SYNTAX      INTEGER { 
                        established(1),
                        syn-sent(2),
                        syn-received(3),
                        fin-wait-1(4),
                        fin-wait-2(5),
                        time-wait(6),
                        closed(7),
                        close-wait(8),
                        last-ack(9),
                        listen(10),
                        closing(11)
                }
    MAX-ACCESS  read-only
    STATUS      current
    DESCRIPTION
        "The state of the TCP connection as defined in RFC 793."

    ::= { dpStatusTCPTableEntry 5 }

dpStatusTCPTableserviceDomain OBJECT-TYPE
    SYNTAX      DisplayString
    MAX-ACCESS  read-only
    STATUS      current
    DESCRIPTION
        "For TCP connections that were created by a configuration object this value
        indicates the domain that the configuration object that created the
        listener is in. Only applies to connections in the listen state."

    ::= { dpStatusTCPTableEntry 8 }

dpStatusTCPTableserviceClass OBJECT-TYPE
    SYNTAX      INTEGER { 
                        configBase(0),
                        dNSNameService(1),
                        ethernetInterface(2),
                        cRLFetch(3),
                        hTTPService(4),
                        statistics(5),
                        traceTarget(6),
                        nTPService(7),
                        throttler(8),
                        stylePolicy(9),
                        hTTPUserAgent(10),
                        tCPProxyService(12),
                        uRLMap(13),
                        uRLRefreshPolicy(14),
                        user(15),
                        networkSettings(16),
                        xMLManager(17),
                        mQQM(18),
                        xSLProxyService(19),
                        mQGW(20),
                        sSLProxyService(21),
                        stylePolicyRule(22),
                        errorReportSettings(23),
                        iPInterface(25),
                        matching(26),
                        systemSettings(27),
                        sNMPSettings(28),
                        rADIUSSettings(29),
                        userGroup(30),
                        shellAlias(31),
                        xSLCoprocService(32),
                        telnetService(33),
                        cryptoSSKey(34),
                        messageMonitor(35),
                        uRLRewritePolicy(36),
                        sSLProxyProfile(37),
                        hTTPProxyService(38),
                        service(39),
                        cryptoFWCred(41),
                        xMLFirewallService(42),
                        cryptoKey(43),
                        cryptoCertificate(44),
                        cryptoIdentCred(45),
                        cryptoValCred(46),
                        cryptoProfile(47),
                        logTarget(48),
                        sSHService(49),
                        crypto(50),
                        webGUI(51),
                        eventlog(52),
                        accessControl(53),
                        messageFlowControl(54),
                        mQConfiguration(55),
                        deviceSettings(56),
                        deviceManagementService(57),
                        networkConfiguration(58),
                        logLabel(59),
                        mgmtInterface(60),
                        messageMatching(61),
                        messageType(62),
                        countMonitor(63),
                        durationMonitor(64),
                        filterAction(65),
                        hTTPInputConversionMap(66),
                        compileOptionsPolicy(68),
                        xPathRoutingMap(69),
                        schemaExceptionMap(70),
                        reserved71(71),
                        documentCryptoMap(72),
                        tAM(73),
                        domain(74),
                        timeSettings(75),
                        dynamicXMLContentMap(77),
                        dynamicStylesheet(78),
                        dynamicSchema(79),
                        accessControlList(80),
                        importPackage(81),
                        mQhost(82),
                        mQproxy(83),
                        loadBalancerGroup(84),
                        rBMSettings(85),
                        includeConfig(86),
                        certMonitor(87),
                        hostAlias(88),
                        aAAPolicy(91),
                        stylePolicyAction(92),
                        cryptoKerberosKDC(93),
                        webServiceMonitor(94),
                        wSGateway(95),
                        stylePolicyRuleBase(96),
                        wSStylePolicyRule(97),
                        wSStylePolicy(98),
                        webServicesAgent(99),
                        gatewayBase(100),
                        multiProtocolGateway(101),
                        sourceProtocolHandler(102),
                        hTTPSourceProtocolHandler(103),
                        hTTPSSourceProtocolHandler(104),
                        mQSourceProtocolHandler(105),
                        xTCProtocolHandler(106),
                        cryptoKerberosKeytab(109),
                        statelessTCPSourceProtocolHandler(110),
                        sLMCredClass(111),
                        sLMRsrcClass(112),
                        sLMSchedule(113),
                        sLMAction(114),
                        sLMPolicy(115),
                        peerGroup(116),
                        reserved117(117),
                        tFIMEndpoint(118),
                        xmltrace(120),
                        nFSClientSettings(121),
                        wSEndpointRewritePolicy(122),
                        sQLDataSource(124),
                        nFSStaticMount(125),
                        nFSDynamicMounts(126),
                        webAppErrorHandlingPolicy(127),
                        simpleCountMonitor(128),
                        nameValueProfile(129),
                        webAppResponse(130),
                        webAppRequest(131),
                        webAppFW(132),
                        appSecurityPolicy(133),
                        uDDIRegistry(134),
                        webAppSessionPolicy(135),
                        jMSServer(136),
                        tibcoEMSServer(137),
                        tibcoEMSSourceProtocolHandler(138),
                        xACMLPDP(139),
                        jMSSourceProtocolHandler(140),
                        webSphereJMSServer(141),
                        webSphereJMSSourceProtocolHandler(142),
                        processingMetadata(143),
                        mTOMPolicy(144),
                        fTPServerSourceProtocolHandler(145),
                        filePollerSourceProtocolHandler(146),
                        nFSFilePollerSourceProtocolHandler(147),
                        fTPFilePollerSourceProtocolHandler(148),
                        fTPQuoteCommands(149),
                        mQQMBase(150),
                        mQQMGroup(151),
                        wSRRServer(152),
                        wSRRSubscription(153),
                        webServiceSubscription(154),
                        uDDISubscription(155),
                        vLANInterface(156),
                        conformancePolicy(157),
                        sOAPHeaderDisposition(158),
                        policyAttachments(159),
                        policyParameters(160),
                        iMSConnect(161),
                        iMSConnectSourceProtocolHandler(162),
                        lDAPSearchParameters(163),
                        configDeploymentPolicy(164),
                        compactFlash(165),
                        raidVolume(166),
                        iScsiInitiatorConfig(167),
                        lLMSourceProtocolHandler(168),
                        tRVSourceProtocolHandler(169),
                        iScsiHBAConfig(170),
                        iScsiTargetConfig(171),
                        iScsiVolumeConfig(172),
                        iScsiChapConfig(173),
                        zosNSSClient(174),
                        sSHServerSourceProtocolHandler(175),
                        fTPDemonSourceProtocolHandler(176),
                        aS3SourceProtocolHandler(177),
                        aS2SourceProtocolHandler(178),
                        b2BXPathRoutingPolicy(179),
                        lLMInstance(180),
                        lLMMulticastReceive(181),
                        lLMMulticastTransmit(182),
                        lLMUnicast(183),
                        lLMMulticastTierGroup(184),
                        lLMRoute(186),
                        lLMPolicy(187),
                        fibreChannelHBA(188),
                        fibreChannelTarget(189),
                        fibreChannelVolume(190),
                        webB2BViewer(192),
                        b2BPersistence(193),
                        b2BProfileGroup(194),
                        b2BGateway(195),
                        b2BProfile(196),
                        wCCService(197),
                        formsLoginPolicy(198),
                        tRVPolicy(199),
                        tRVRoute(200),
                        tRVTransport(201),
                        lLMPolicyBase(202),
                        lLMRouteBase(203),
                        pOPPollerSourceProtocolHandlerBase(204),
                        aS1PollerSourceProtocolHandler(205),
                        pOPPollerSourceProtocolHandler(206),
                        sMTPServerConnection(207),
                        xM70Persistence(208),
                        wSRRSavedSearchSubscription(209),
                        eBMS2SourceProtocolHandler(210),
                        sAMLAttributes(211),
                        sSHClientProfile(212),
                        sFTPFilePollerSourceProtocolHandler(213),
                        zHybridTargetControlService(214),
                        multipathService(215),
                        clusterService(216),
                        secureCloudConnector(217),
                        iPMILanChannel(218),
                        iPMIUser(219),
                        b2BCPACollaboration(220),
                        mQFTESourceProtocolHandler(221),
                        b2BCPA(222),
                        b2BCPASenderSetting(223),
                        b2BCPAReceiverSetting(224),
                        oAuthSupportedClient(225),
                        oAuthSupportedClientGroup(226),
                        sSLSNIServerProfile(227),
                        xC10Grid(235),
                        runtimeSettings(246),
                        sQLRuntimeSettings(247),
                        webApplicationGateway(248),
                        interopService(249),
                        oDRConnectorGroup(250),
                        oDR(251),
                        sSLClientProfile(253),
                        sSLServerProfile(254),
                        sSLSNIMapping(256),
                        webTokenService(266),
                        messageContentFilters(267),
                        mCFBase(268),
                        mCFHttpHeader(269),
                        mCFXPath(270),
                        mCFHttpURL(271),
                        mCFHttpMethod(272),
                        iMSCalloutSourceProtocolHandler(273),
                        pattern(274),
                        mCFCustomRule(275),
                        aS2ProxySourceProtocolHandler(277),
                        luna(278),
                        lunaPartition(279),
                        configSequence(280),
                        lunaHAGroup(285),
                        lunaHASettings(286),
                        wAXHNProxy(300),
                        hNApplication(301),
                        cloudGatewayService(302),
                        cloudConnectorService(303),
                        jSONSettings(308),
                        iPMulticast(309),
                        deploymentPolicyParametersBinding(310),
                        lDAPConnectionPool(311),
                        mPGWErrorHandlingPolicy(312),
                        mPGWErrorAction(313),
                        language(314),
                        domainAvailability(315),
                        generatedPolicy(316),
                        passwordMap(320),
                        aAAJWTValidator(321),
                        aAAJWTGenerator(322),
                        linkAggregation(333),
                        cookieAttributePolicy(334),
                        iSAMReverseProxy(335),
                        iSAMReverseProxyJunction(336),
                        iSAMRuntime(337),
                        passwordAlias(338),
                        auditLog(340),
                        jWERecipient(345),
                        jOSESignatureIdentifier(346),
                        jWSSignature(347),
                        jWEHeader(348),
                        jOSERecipientIdentifier(349),
                        secureGatewayClient(350),
                        cacheGrid(351),
                        wXSGrid(352),
                        domainSettings(353),
                        mQAUI(354),
                        gWScriptSettings(358),
                        aPICollection(359),
                        aPIGateway(360),
                        aPIDefinition(361),
                        aPIPath(362),
                        aPIOperation(363),
                        aPIPlan(364),
                        aPISecurityDefinition(365),
                        aPISecurityAPIKey(366),
                        aPISecurityOAuth(368),
                        aPISecurityRequirement(369),
                        controlList(370),
                        aPILDAPRegistry(371),
                        aPIRule(372),
                        aPISecurityOAuthReq(373),
                        gWSRemoteDebug(374),
                        mQAUIMFT(375),
                        assemblyActionUserSecurity(376),
                        aPISecurityBasicAuth(377),
                        aPISchema(378),
                        aPIUserRegistry(379),
                        aPIAuthURLRegistry(380),
                        assemblyActionClientSecurity(381),
                        restMgmtInterface(400),
                        secureBackupMode(402),
                        aPIConnectGatewayService(403),
                        standaloneStandbyControlInterface(450),
                        standaloneStandbyControl(451),
                        tenant(452),
                        socialLoginPolicy(455),
                        eBMS3SourceProtocolHandler(456),
                        dFDLSettings(460),
                        parseSettings(461),
                        accessProfile(462),
                        iLMTScanner(500),
                        quotaEnforcementServer(504),
                        sSHServerProfile(505),
                        quotaEnforcementMatchClass(506),
                        quotaEnforcementGroupClass(507),
                        quotaEnforcementAlgorithm(508),
                        quotaEnforcementSchedule(509),
                        sSHDomainClientProfile(510),
                        quotaEnforcementPolicyGroup(511),
                        quotaEnforcementPolicyBase(512),
                        quotaEnforcementAction(513),
                        quotaEnforcementPolicy(514),
                        gatewayPeering(526),
                        stylePolicyActionBase(600),
                        assemblyActionBase(601),
                        assemblyAction(602),
                        assemblyLogic(603),
                        aPIExecute(605),
                        aPIResult(607),
                        assemblyLogicSwitch(609),
                        assembly(610),
                        assemblyActionInvoke(611),
                        assemblyActionSetVar(612),
                        assemblyActionThrow(613),
                        aPIRouting(614),
                        aPISecurity(615),
                        aPIRateLimit(616),
                        assemblyActionXml2Json(617),
                        aPIAction(618),
                        assemblyActionXSLT(619),
                        assemblyActionGatewayScript(620),
                        aPIClientIdentification(621),
                        assemblyActionMap(622),
                        assemblyActionJWTValidate(623),
                        assemblyActionParse(624),
                        aPICORS(625),
                        operationRateLimit(626),
                        analyticsEndpoint(627),
                        assemblyActionJWTGenerate(628),
                        assemblyActionJson2Xml(629),
                        assemblyActionOAuth(630),
                        oAuthProviderSettings(640),
                        aPISecurityTokenManager(641),
                        assemblyActionValidate(642),
                        aPIDebugProbe(643),
                        aPIApplicationType(644),
                        assemblyFunction(645),
                        assemblyActionFunctionCall(646),
                        gatewayPeeringManager(648),
                        assemblyActionLog(649),
                        assemblyActionRateLimit(650),
                        assemblyActionRedact(651),
                        productInsights(850)
                }
    MAX-ACCESS  read-only
    STATUS      current
    DESCRIPTION
        "The type of configuration object that created the listener. For all
        connections not in the listen state this value will be configBase."

    ::= { dpStatusTCPTableEntry 9 }

dpStatusTCPTableserviceName OBJECT-TYPE
    SYNTAX      DisplayString
    MAX-ACCESS  read-only
    STATUS      current
    DESCRIPTION
        "The name of the configuration object that created the listener. Only
        applies to TCP connections in the listen state."

    ::= { dpStatusTCPTableEntry 10 }

dpStatusTCPSummary OBJECT IDENTIFIER ::= { dpStatus 12 }

dpStatusTCPSummaryestablished OBJECT-TYPE
    SYNTAX      Counter32
    MAX-ACCESS  read-only
    STATUS      current
    DESCRIPTION
        "The number of TCP connections in the established state. Connections in
        this state have completed all handshakes and can transfer data in either
        direction."

    ::= { dpStatusTCPSummary 1 }

dpStatusTCPSummarysynsent OBJECT-TYPE
    SYNTAX      Counter32
    MAX-ACCESS  read-only
    STATUS      current
    DESCRIPTION
        "The number of TCP connections in the syn-sent state. Connections in this
        state are waiting for a matching connection request after sending a
        connection request."

    ::= { dpStatusTCPSummary 2 }

dpStatusTCPSummarysynreceived OBJECT-TYPE
    SYNTAX      Counter32
    MAX-ACCESS  read-only
    STATUS      current
    DESCRIPTION
        "The number of TCP connections in the syn-received state. Connections in
        this state are waiting for a confirming connection request acknowledgment
        after both receiving and sending a connection request."

    ::= { dpStatusTCPSummary 3 }

dpStatusTCPSummaryfinwait1 OBJECT-TYPE
    SYNTAX      Counter32
    MAX-ACCESS  read-only
    STATUS      current
    DESCRIPTION
        "The number of TCP connections in the fin-wait-1 state. Connections in this
        state are waiting for a connection termination request from the remote TCP
        or an acknowledgment of the connection termination request previously
        sent."

    ::= { dpStatusTCPSummary 4 }

dpStatusTCPSummaryfinwait2 OBJECT-TYPE
    SYNTAX      Counter32
    MAX-ACCESS  read-only
    STATUS      current
    DESCRIPTION
        "The number of TCP connections in the fin-wait-2 state. Connections in this
        state are waiting for a connection termination request from the remote
        TCP."

    ::= { dpStatusTCPSummary 5 }

dpStatusTCPSummarytimewait OBJECT-TYPE
    SYNTAX      Counter32
    MAX-ACCESS  read-only
    STATUS      current
    DESCRIPTION
        "The number of TCP connections in the time-wait state. Connections in this
        state are waiting for enough time to pass to be sure that the remote TCP
        received the acknowledgment of its connection termination request."

    ::= { dpStatusTCPSummary 6 }

dpStatusTCPSummaryclosed OBJECT-TYPE
    SYNTAX      Counter32
    MAX-ACCESS  read-only
    STATUS      current
    DESCRIPTION
        "The number of TCP connections in the closed state. This state represents
        no connection state at all."

    ::= { dpStatusTCPSummary 7 }

dpStatusTCPSummaryclosewait OBJECT-TYPE
    SYNTAX      Counter32
    MAX-ACCESS  read-only
    STATUS      current
    DESCRIPTION
        "The number of TCP connections in the close-wait state. Connections in this
        state are waiting for a connection termination request from the local
        user."

    ::= { dpStatusTCPSummary 8 }

dpStatusTCPSummarylastack OBJECT-TYPE
    SYNTAX      Counter32
    MAX-ACCESS  read-only
    STATUS      current
    DESCRIPTION
        "The number of TCP connections in the last-ack state. Connections in this
        state are waiting for an acknowledgment of the connection termination
        request previously sent to the remote TCP (which includes an
        acknowledgment of its connection termination request)."

    ::= { dpStatusTCPSummary 9 }

dpStatusTCPSummarylisten OBJECT-TYPE
    SYNTAX      Counter32
    MAX-ACCESS  read-only
    STATUS      current
    DESCRIPTION
        "The number of TCP connections in the listen state. Connections in the
        listen state are waiting for a connection request from any remote TCP and
        port."

    ::= { dpStatusTCPSummary 10 }

dpStatusTCPSummaryclosing OBJECT-TYPE
    SYNTAX      Counter32
    MAX-ACCESS  read-only
    STATUS      current
    DESCRIPTION
        "The number of TCP connections in the closing state. Connections in this
        state are waiting for a connection termination request acknowledgment from
        the remote TCP."

    ::= { dpStatusTCPSummary 11 }

dpStatusConnectionsAccepted OBJECT IDENTIFIER ::= { dpStatus 13 }

dpStatusConnectionsAcceptedtenSeconds OBJECT-TYPE
    SYNTAX      Counter32
    MAX-ACCESS  read-only
    STATUS      current
    DESCRIPTION
        "The number of connections accepted in the previous 10 seconds."

    ::= { dpStatusConnectionsAccepted 1 }

dpStatusConnectionsAcceptedoneMinute OBJECT-TYPE
    SYNTAX      Counter32
    MAX-ACCESS  read-only
    STATUS      current
    DESCRIPTION
        "The number of connections accepted in the previous minute."

    ::= { dpStatusConnectionsAccepted 2 }

dpStatusConnectionsAcceptedtenMinutes OBJECT-TYPE
    SYNTAX      Counter32
    MAX-ACCESS  read-only
    STATUS      current
    DESCRIPTION
        "The number of connections accepted in the previous 10 minutes."

    ::= { dpStatusConnectionsAccepted 3 }

dpStatusConnectionsAcceptedoneHour OBJECT-TYPE
    SYNTAX      Counter32
    MAX-ACCESS  read-only
    STATUS      current
    DESCRIPTION
        "The number of connections accepted in the previous hour."

    ::= { dpStatusConnectionsAccepted 4 }

dpStatusConnectionsAcceptedoneDay OBJECT-TYPE
    SYNTAX      Counter32
    MAX-ACCESS  read-only
    STATUS      current
    DESCRIPTION
        "The number of connections accepted in the previous 24 hours."

    ::= { dpStatusConnectionsAccepted 5 }

dpStatusCPUUsage OBJECT IDENTIFIER ::= { dpStatus 14 }

dpStatusCPUUsagetenSeconds OBJECT-TYPE
    SYNTAX      Unsigned32
    UNITS       "%"
    MAX-ACCESS  read-only
    STATUS      current
    DESCRIPTION
        "The average CPU usage over the the previous 10 seconds."

    ::= { dpStatusCPUUsage 1 }

dpStatusCPUUsageoneMinute OBJECT-TYPE
    SYNTAX      Unsigned32
    UNITS       "%"
    MAX-ACCESS  read-only
    STATUS      current
    DESCRIPTION
        "The average CPU usage over the the previous minute."

    ::= { dpStatusCPUUsage 2 }

dpStatusCPUUsagetenMinutes OBJECT-TYPE
    SYNTAX      Unsigned32
    UNITS       "%"
    MAX-ACCESS  read-only
    STATUS      current
    DESCRIPTION
        "The average CPU usage over the the previous 10 minutes."

    ::= { dpStatusCPUUsage 3 }

dpStatusCPUUsageoneHour OBJECT-TYPE
    SYNTAX      Unsigned32
    UNITS       "%"
    MAX-ACCESS  read-only
    STATUS      current
    DESCRIPTION
        "The average CPU usage over the the previous hour."

    ::= { dpStatusCPUUsage 4 }

dpStatusCPUUsageoneDay OBJECT-TYPE
    SYNTAX      Unsigned32
    UNITS       "%"
    MAX-ACCESS  read-only
    STATUS      current
    DESCRIPTION
        "The average CPU usage over the the previous day."

    ::= { dpStatusCPUUsage 5 }

--

dpStatusStylesheetExecutionsTable OBJECT-TYPE
    SYNTAX      SEQUENCE OF DPStatusStylesheetExecutionsEntry
    MAX-ACCESS  not-accessible
    STATUS      obsolete
    DESCRIPTION
        "Stylesheet execution counts
        Note: this is obsoleted and is replaced by dpStatusStylesheetExecutionsSimpleIndex as of release
    3.5.1"

    ::= { dpStatus 15 }

dpStatusStylesheetExecutionsEntry OBJECT-TYPE
    SYNTAX      DPStatusStylesheetExecutionsEntry
    MAX-ACCESS  not-accessible
    STATUS      obsolete
    DESCRIPTION "Table row."
    INDEX { dpConfigXMLManagerIndex, dpStatusStylesheetExecutionsOutputMode, IMPLIED dpStatusStylesheetExecutionsURL }

    ::= { dpStatusStylesheetExecutionsTable 1 }

DPStatusStylesheetExecutionsEntry ::= SEQUENCE {
    dpStatusStylesheetExecutionsXMLManager    DisplayString,
    dpStatusStylesheetExecutionsOutputMode    INTEGER,
    dpStatusStylesheetExecutionsURL    DisplayString,
    dpStatusStylesheetExecutionstenSeconds    Counter32,
    dpStatusStylesheetExecutionsoneMinute    Counter32,
    dpStatusStylesheetExecutionstenMinutes    Counter32,
    dpStatusStylesheetExecutionsoneHour    Counter32,
    dpStatusStylesheetExecutionsoneDay    Counter32
}

dpStatusStylesheetExecutionsXMLManager OBJECT-TYPE
    SYNTAX      DisplayString
    MAX-ACCESS  read-only
    STATUS      obsolete
    DESCRIPTION "No description yet."

    ::= { dpStatusStylesheetExecutionsEntry 1 }

dpStatusStylesheetExecutionsOutputMode OBJECT-TYPE
    SYNTAX      INTEGER { 
                        general(1),
                        stream(2),
                        context(3),
                        events(4)
                }
    MAX-ACCESS  read-only
    STATUS      obsolete
    DESCRIPTION "No description yet."

    ::= { dpStatusStylesheetExecutionsEntry 2 }

dpStatusStylesheetExecutionsURL OBJECT-TYPE
    SYNTAX      DisplayString
    MAX-ACCESS  read-only
    STATUS      obsolete
    DESCRIPTION "No description yet."

    ::= { dpStatusStylesheetExecutionsEntry 3 }

dpStatusStylesheetExecutionstenSeconds OBJECT-TYPE
    SYNTAX      Counter32
    MAX-ACCESS  read-only
    STATUS      obsolete
    DESCRIPTION "No description yet."

    ::= { dpStatusStylesheetExecutionsEntry 4 }

dpStatusStylesheetExecutionsoneMinute OBJECT-TYPE
    SYNTAX      Counter32
    MAX-ACCESS  read-only
    STATUS      obsolete
    DESCRIPTION "No description yet."

    ::= { dpStatusStylesheetExecutionsEntry 5 }

dpStatusStylesheetExecutionstenMinutes OBJECT-TYPE
    SYNTAX      Counter32
    MAX-ACCESS  read-only
    STATUS      obsolete
    DESCRIPTION "No description yet."

    ::= { dpStatusStylesheetExecutionsEntry 6 }

dpStatusStylesheetExecutionsoneHour OBJECT-TYPE
    SYNTAX      Counter32
    MAX-ACCESS  read-only
    STATUS      obsolete
    DESCRIPTION "No description yet."

    ::= { dpStatusStylesheetExecutionsEntry 7 }

dpStatusStylesheetExecutionsoneDay OBJECT-TYPE
    SYNTAX      Counter32
    MAX-ACCESS  read-only
    STATUS      obsolete
    DESCRIPTION "No description yet."

    ::= { dpStatusStylesheetExecutionsEntry 8 }

--

dpStatusStylesheetMeanExecutionTimeTable OBJECT-TYPE
    SYNTAX      SEQUENCE OF DPStatusStylesheetMeanExecutionTimeEntry
    MAX-ACCESS  not-accessible
    STATUS      obsolete
    DESCRIPTION
        "Stylesheet mean execution times
        Note: this is obsoleted and is replaced by dpStatusStylesheetMeanExecutionTimeSimpleIndex as of release
    3.5.1"

    ::= { dpStatus 16 }

dpStatusStylesheetMeanExecutionTimeEntry OBJECT-TYPE
    SYNTAX      DPStatusStylesheetMeanExecutionTimeEntry
    MAX-ACCESS  not-accessible
    STATUS      obsolete
    DESCRIPTION "Table row."
    INDEX { dpConfigXMLManagerIndex, dpStatusStylesheetMeanExecutionTimeOutputMode, IMPLIED dpStatusStylesheetMeanExecutionTimeURL }

    ::= { dpStatusStylesheetMeanExecutionTimeTable 1 }

DPStatusStylesheetMeanExecutionTimeEntry ::= SEQUENCE {
    dpStatusStylesheetMeanExecutionTimeXMLManager    DisplayString,
    dpStatusStylesheetMeanExecutionTimeOutputMode    INTEGER,
    dpStatusStylesheetMeanExecutionTimeURL    DisplayString,
    dpStatusStylesheetMeanExecutionTimetenSeconds    Counter32,
    dpStatusStylesheetMeanExecutionTimeoneMinute    Counter32,
    dpStatusStylesheetMeanExecutionTimetenMinutes    Counter32,
    dpStatusStylesheetMeanExecutionTimeoneHour    Counter32,
    dpStatusStylesheetMeanExecutionTimeoneDay    Counter32
}

dpStatusStylesheetMeanExecutionTimeXMLManager OBJECT-TYPE
    SYNTAX      DisplayString
    MAX-ACCESS  read-only
    STATUS      obsolete
    DESCRIPTION "No description yet."

    ::= { dpStatusStylesheetMeanExecutionTimeEntry 1 }

dpStatusStylesheetMeanExecutionTimeOutputMode OBJECT-TYPE
    SYNTAX      INTEGER { 
                        general(1),
                        stream(2),
                        context(3),
                        events(4)
                }
    MAX-ACCESS  read-only
    STATUS      obsolete
    DESCRIPTION "No description yet."

    ::= { dpStatusStylesheetMeanExecutionTimeEntry 2 }

dpStatusStylesheetMeanExecutionTimeURL OBJECT-TYPE
    SYNTAX      DisplayString
    MAX-ACCESS  read-only
    STATUS      obsolete
    DESCRIPTION "No description yet."

    ::= { dpStatusStylesheetMeanExecutionTimeEntry 3 }

dpStatusStylesheetMeanExecutionTimetenSeconds OBJECT-TYPE
    SYNTAX      Counter32
    UNITS       "msec"
    MAX-ACCESS  read-only
    STATUS      obsolete
    DESCRIPTION "No description yet."

    ::= { dpStatusStylesheetMeanExecutionTimeEntry 4 }

dpStatusStylesheetMeanExecutionTimeoneMinute OBJECT-TYPE
    SYNTAX      Counter32
    UNITS       "msec"
    MAX-ACCESS  read-only
    STATUS      obsolete
    DESCRIPTION "No description yet."

    ::= { dpStatusStylesheetMeanExecutionTimeEntry 5 }

dpStatusStylesheetMeanExecutionTimetenMinutes OBJECT-TYPE
    SYNTAX      Counter32
    UNITS       "msec"
    MAX-ACCESS  read-only
    STATUS      obsolete
    DESCRIPTION "No description yet."

    ::= { dpStatusStylesheetMeanExecutionTimeEntry 6 }

dpStatusStylesheetMeanExecutionTimeoneHour OBJECT-TYPE
    SYNTAX      Counter32
    UNITS       "msec"
    MAX-ACCESS  read-only
    STATUS      obsolete
    DESCRIPTION "No description yet."

    ::= { dpStatusStylesheetMeanExecutionTimeEntry 7 }

dpStatusStylesheetMeanExecutionTimeoneDay OBJECT-TYPE
    SYNTAX      Counter32
    UNITS       "msec"
    MAX-ACCESS  read-only
    STATUS      obsolete
    DESCRIPTION "No description yet."

    ::= { dpStatusStylesheetMeanExecutionTimeEntry 8 }

--

dpStatusStandbyStatusTable OBJECT-TYPE
    SYNTAX      SEQUENCE OF DPStatusStandbyStatusEntry
    MAX-ACCESS  not-accessible
    STATUS      obsolete
    DESCRIPTION
        "Status of standby control protocol on Ethernet interfaces or VLANs on top
        of Ethernet interfaces.
        Note: this is obsoleted and is replaced by dpStatusStandbyStatus2 as of release 5.0.0"

    ::= { dpStatus 23 }

dpStatusStandbyStatusEntry OBJECT-TYPE
    SYNTAX      DPStatusStandbyStatusEntry
    MAX-ACCESS  not-accessible
    STATUS      obsolete
    DESCRIPTION "Table row."
    INDEX { dpStatusStandbyStatusName }

    ::= { dpStatusStandbyStatusTable 1 }

DPStatusStandbyStatusEntry ::= SEQUENCE {
    dpStatusStandbyStatusName    INTEGER,
    dpStatusStandbyStatusGroup    Unsigned32,
    dpStatusStandbyStatusIP    IpAddress,
    dpStatusStandbyStatusPriority    Unsigned32,
    dpStatusStandbyStatusMode    INTEGER,
    dpStatusStandbyStatusPreempt    INTEGER,
    dpStatusStandbyStatusGroupLeader    IpAddress,
    dpStatusStandbyStatusInterfaceType    INTEGER,
    dpStatusStandbyStatusVlanName    DisplayString,
    dpStatusStandbyStatusSelfBalance    INTEGER,
    dpStatusStandbyStatusDistAlg    INTEGER
}

dpStatusStandbyStatusName OBJECT-TYPE
    SYNTAX      INTEGER { 
                        eth0(1),
                        eth1(2),
                        eth2(3),
                        eth3(4),
                        mgt0(5),
                        eth4(6),
                        eth5(8),
                        eth6(9),
                        eth7(10),
                        eth8(11),
                        eth9(12),
                        eth10(13),
                        tun(14),
                        mgt1(15),
                        eth11(16),
                        eth12(17),
                        eth13(18),
                        eth14(19),
                        eth15(20),
                        eth16(21),
                        eth17(22),
                        eth20(23),
                        eth21(24),
                        eth22(25),
                        eth23(26),
                        eth24(27),
                        eth25(28),
                        eth26(29),
                        eth27(30),
                        eth30(31),
                        eth31(32),
                        eth32(33),
                        eth33(34)
                }
    MAX-ACCESS  read-only
    STATUS      obsolete
    DESCRIPTION
        "The physical Ethernet interface assigned to standby"

    ::= { dpStatusStandbyStatusEntry 1 }

dpStatusStandbyStatusGroup OBJECT-TYPE
    SYNTAX      Unsigned32 (0..65535)
    MAX-ACCESS  read-only
    STATUS      obsolete
    DESCRIPTION
        "An integer used to identify a standby group; allowable identifiers are in
        the range 1 through 255."

    ::= { dpStatusStandbyStatusEntry 2 }

dpStatusStandbyStatusIP OBJECT-TYPE
    SYNTAX      IpAddress
    MAX-ACCESS  read-only
    STATUS      obsolete
    DESCRIPTION
        "The virtual IP address managed by this group, which will be active on one
        member of the group at any given time. This is the address external
        clients use to contact the group."

    ::= { dpStatusStandbyStatusEntry 3 }

dpStatusStandbyStatusPriority OBJECT-TYPE
    SYNTAX      Unsigned32 (0..65535)
    MAX-ACCESS  read-only
    STATUS      obsolete
    DESCRIPTION
        "The priority value (an integer within the range 100 through 255, with a
        default of 100) determines the device's eligibility for the active role.
        The device within the standby group with the highest assigned priority
        assumes the active role."

    ::= { dpStatusStandbyStatusEntry 4 }

dpStatusStandbyStatusMode OBJECT-TYPE
    SYNTAX      INTEGER { 
                        active(1),
                        standby(2)
                }
    MAX-ACCESS  read-only
    STATUS      obsolete
    DESCRIPTION
        "The current state of this member of this standby control group. If it is
        active, this member is the one receiving traffic for the group's IP
        address. If it is standby, some other member of the group is active."

    ::= { dpStatusStandbyStatusEntry 5 }

dpStatusStandbyStatusPreempt OBJECT-TYPE
    SYNTAX      INTEGER { 
                        on(1),
                        off(2)
                }
    MAX-ACCESS  read-only
    STATUS      obsolete
    DESCRIPTION
        "With preempt mode enabled, a previously active (rather than standby)
        device regains its active status provided it has a high enough priority
        when returned to service following a failure. With preempt mode disabled
        (the default state), a previously active device assumes the standby role
        when returned to service following a failure."

    ::= { dpStatusStandbyStatusEntry 6 }

dpStatusStandbyStatusGroupLeader OBJECT-TYPE
    SYNTAX      IpAddress
    MAX-ACCESS  read-only
    STATUS      obsolete
    DESCRIPTION
        "The address or host name of the machine in the group that currently
        responds to the virtual IP address"

    ::= { dpStatusStandbyStatusEntry 7 }

dpStatusStandbyStatusInterfaceType OBJECT-TYPE
    SYNTAX      INTEGER { 
                        other(1),
                        ethernet(6),
                        tunnel(131),
                        vLAN(135),
                        aggregate(161)
                }
    MAX-ACCESS  read-only
    STATUS      obsolete
    DESCRIPTION
        "The type of the interface this standby control is on. This may be Ethernet
        or VLAN."

    ::= { dpStatusStandbyStatusEntry 8 }

dpStatusStandbyStatusVlanName OBJECT-TYPE
    SYNTAX      DisplayString
    MAX-ACCESS  read-only
    STATUS      obsolete
    DESCRIPTION
        "If this standby control is on a VLAN, the name of that VLAN."

    ::= { dpStatusStandbyStatusEntry 9 }

dpStatusStandbyStatusSelfBalance OBJECT-TYPE
    SYNTAX      INTEGER { 
                        on(1),
                        off(2)
                }
    MAX-ACCESS  read-only
    STATUS      obsolete
    DESCRIPTION
        "With self-balancing enabled, the active device distributes incoming
        requests across all members of the standby group with the self-balancing
        feature enabled."

    ::= { dpStatusStandbyStatusEntry 10 }

dpStatusStandbyStatusDistAlg OBJECT-TYPE
    SYNTAX      INTEGER { 
                        wlc(1),
                        rr(2)
                }
    MAX-ACCESS  read-only
    STATUS      obsolete
    DESCRIPTION
        "The active device uses chosen algorithm to distribute connections to
        members of the standby group with the self-balancing feature enabled. All
        members in the standby group must use the same algorithm."

    ::= { dpStatusStandbyStatusEntry 11 }

--

dpStatusReceiveKbpsThroughputTable OBJECT-TYPE
    SYNTAX      SEQUENCE OF DPStatusReceiveKbpsThroughputEntry
    MAX-ACCESS  not-accessible
    STATUS      obsolete
    DESCRIPTION
        "Receive throughput in kbits/sec for all physical Ethernet interfaces. For
        physical and VLAN interfaces, see drStatusNetworkRecieveDataThroughput.
        Note: this is obsoleted and is replaced by dpStatusNetworkReceiveDataThroughput as of release
    3.6.1"

    ::= { dpStatus 24 }

dpStatusReceiveKbpsThroughputEntry OBJECT-TYPE
    SYNTAX      DPStatusReceiveKbpsThroughputEntry
    MAX-ACCESS  not-accessible
    STATUS      obsolete
    DESCRIPTION "Table row."
    INDEX { dpStatusReceiveKbpsThroughputInterface }

    ::= { dpStatusReceiveKbpsThroughputTable 1 }

DPStatusReceiveKbpsThroughputEntry ::= SEQUENCE {
    dpStatusReceiveKbpsThroughputInterface    INTEGER,
    dpStatusReceiveKbpsThroughputtenSeconds    Unsigned32,
    dpStatusReceiveKbpsThroughputoneMinute    Unsigned32,
    dpStatusReceiveKbpsThroughputtenMinutes    Unsigned32,
    dpStatusReceiveKbpsThroughputoneHour    Unsigned32,
    dpStatusReceiveKbpsThroughputoneDay    Unsigned32
}

dpStatusReceiveKbpsThroughputInterface OBJECT-TYPE
    SYNTAX      INTEGER { 
                        eth0(1),
                        eth1(2),
                        eth2(3),
                        eth3(4),
                        mgt0(5),
                        eth4(6),
                        eth5(8),
                        eth6(9),
                        eth7(10),
                        eth8(11),
                        eth9(12),
                        eth10(13),
                        tun(14),
                        mgt1(15),
                        eth11(16),
                        eth12(17),
                        eth13(18),
                        eth14(19),
                        eth15(20),
                        eth16(21),
                        eth17(22),
                        eth20(23),
                        eth21(24),
                        eth22(25),
                        eth23(26),
                        eth24(27),
                        eth25(28),
                        eth26(29),
                        eth27(30),
                        eth30(31),
                        eth31(32),
                        eth32(33),
                        eth33(34)
                }
    MAX-ACCESS  read-only
    STATUS      obsolete
    DESCRIPTION "No description yet."

    ::= { dpStatusReceiveKbpsThroughputEntry 1 }

dpStatusReceiveKbpsThroughputtenSeconds OBJECT-TYPE
    SYNTAX      Unsigned32
    UNITS       "kbits/sec"
    MAX-ACCESS  read-only
    STATUS      obsolete
    DESCRIPTION "No description yet."

    ::= { dpStatusReceiveKbpsThroughputEntry 2 }

dpStatusReceiveKbpsThroughputoneMinute OBJECT-TYPE
    SYNTAX      Unsigned32
    UNITS       "kbits/sec"
    MAX-ACCESS  read-only
    STATUS      obsolete
    DESCRIPTION "No description yet."

    ::= { dpStatusReceiveKbpsThroughputEntry 3 }

dpStatusReceiveKbpsThroughputtenMinutes OBJECT-TYPE
    SYNTAX      Unsigned32
    UNITS       "kbits/sec"
    MAX-ACCESS  read-only
    STATUS      obsolete
    DESCRIPTION "No description yet."

    ::= { dpStatusReceiveKbpsThroughputEntry 4 }

dpStatusReceiveKbpsThroughputoneHour OBJECT-TYPE
    SYNTAX      Unsigned32
    UNITS       "kbits/sec"
    MAX-ACCESS  read-only
    STATUS      obsolete
    DESCRIPTION "No description yet."

    ::= { dpStatusReceiveKbpsThroughputEntry 5 }

dpStatusReceiveKbpsThroughputoneDay OBJECT-TYPE
    SYNTAX      Unsigned32
    UNITS       "kbits/sec"
    MAX-ACCESS  read-only
    STATUS      obsolete
    DESCRIPTION "No description yet."

    ::= { dpStatusReceiveKbpsThroughputEntry 6 }

--

dpStatusReceivePacketThroughputTable OBJECT-TYPE
    SYNTAX      SEQUENCE OF DPStatusReceivePacketThroughputEntry
    MAX-ACCESS  not-accessible
    STATUS      obsolete
    DESCRIPTION
        "Receive throughput in packets/sec for all physical Ethernet interfaces.
        For physical and VLAN interfaces, see
        drStatusNetworkRecievePacketThroughput.
        Note: this is obsoleted and is replaced by dpStatusNetworkReceivePacketThroughput as of release
    3.6.1"

    ::= { dpStatus 25 }

dpStatusReceivePacketThroughputEntry OBJECT-TYPE
    SYNTAX      DPStatusReceivePacketThroughputEntry
    MAX-ACCESS  not-accessible
    STATUS      obsolete
    DESCRIPTION "Table row."
    INDEX { dpStatusReceivePacketThroughputInterface }

    ::= { dpStatusReceivePacketThroughputTable 1 }

DPStatusReceivePacketThroughputEntry ::= SEQUENCE {
    dpStatusReceivePacketThroughputInterface    INTEGER,
    dpStatusReceivePacketThroughputtenSeconds    Unsigned32,
    dpStatusReceivePacketThroughputoneMinute    Unsigned32,
    dpStatusReceivePacketThroughputtenMinutes    Unsigned32,
    dpStatusReceivePacketThroughputoneHour    Unsigned32,
    dpStatusReceivePacketThroughputoneDay    Unsigned32
}

dpStatusReceivePacketThroughputInterface OBJECT-TYPE
    SYNTAX      INTEGER { 
                        eth0(1),
                        eth1(2),
                        eth2(3),
                        eth3(4),
                        mgt0(5),
                        eth4(6),
                        eth5(8),
                        eth6(9),
                        eth7(10),
                        eth8(11),
                        eth9(12),
                        eth10(13),
                        tun(14),
                        mgt1(15),
                        eth11(16),
                        eth12(17),
                        eth13(18),
                        eth14(19),
                        eth15(20),
                        eth16(21),
                        eth17(22),
                        eth20(23),
                        eth21(24),
                        eth22(25),
                        eth23(26),
                        eth24(27),
                        eth25(28),
                        eth26(29),
                        eth27(30),
                        eth30(31),
                        eth31(32),
                        eth32(33),
                        eth33(34)
                }
    MAX-ACCESS  read-only
    STATUS      obsolete
    DESCRIPTION "No description yet."

    ::= { dpStatusReceivePacketThroughputEntry 1 }

dpStatusReceivePacketThroughputtenSeconds OBJECT-TYPE
    SYNTAX      Unsigned32
    UNITS       "packets/sec"
    MAX-ACCESS  read-only
    STATUS      obsolete
    DESCRIPTION "No description yet."

    ::= { dpStatusReceivePacketThroughputEntry 2 }

dpStatusReceivePacketThroughputoneMinute OBJECT-TYPE
    SYNTAX      Unsigned32
    UNITS       "packets/sec"
    MAX-ACCESS  read-only
    STATUS      obsolete
    DESCRIPTION "No description yet."

    ::= { dpStatusReceivePacketThroughputEntry 3 }

dpStatusReceivePacketThroughputtenMinutes OBJECT-TYPE
    SYNTAX      Unsigned32
    UNITS       "packets/sec"
    MAX-ACCESS  read-only
    STATUS      obsolete
    DESCRIPTION "No description yet."

    ::= { dpStatusReceivePacketThroughputEntry 4 }

dpStatusReceivePacketThroughputoneHour OBJECT-TYPE
    SYNTAX      Unsigned32
    UNITS       "packets/sec"
    MAX-ACCESS  read-only
    STATUS      obsolete
    DESCRIPTION "No description yet."

    ::= { dpStatusReceivePacketThroughputEntry 5 }

dpStatusReceivePacketThroughputoneDay OBJECT-TYPE
    SYNTAX      Unsigned32
    UNITS       "packets/sec"
    MAX-ACCESS  read-only
    STATUS      obsolete
    DESCRIPTION "No description yet."

    ::= { dpStatusReceivePacketThroughputEntry 6 }

--

dpStatusTransmitKbpsThroughputTable OBJECT-TYPE
    SYNTAX      SEQUENCE OF DPStatusTransmitKbpsThroughputEntry
    MAX-ACCESS  not-accessible
    STATUS      obsolete
    DESCRIPTION
        "Transmit throughput in kbits/sec for all physical Ethernet interfaces. For
        physical and VLAN interfaces, see drStatusNetworkTransmitDataThroughput.
        Note: this is obsoleted and is replaced by dpStatusNetworkTransmitDataThroughput as of release
    3.6.1"

    ::= { dpStatus 26 }

dpStatusTransmitKbpsThroughputEntry OBJECT-TYPE
    SYNTAX      DPStatusTransmitKbpsThroughputEntry
    MAX-ACCESS  not-accessible
    STATUS      obsolete
    DESCRIPTION "Table row."
    INDEX { dpStatusTransmitKbpsThroughputInterface }

    ::= { dpStatusTransmitKbpsThroughputTable 1 }

DPStatusTransmitKbpsThroughputEntry ::= SEQUENCE {
    dpStatusTransmitKbpsThroughputInterface    INTEGER,
    dpStatusTransmitKbpsThroughputtenSeconds    Unsigned32,
    dpStatusTransmitKbpsThroughputoneMinute    Unsigned32,
    dpStatusTransmitKbpsThroughputtenMinutes    Unsigned32,
    dpStatusTransmitKbpsThroughputoneHour    Unsigned32,
    dpStatusTransmitKbpsThroughputoneDay    Unsigned32
}

dpStatusTransmitKbpsThroughputInterface OBJECT-TYPE
    SYNTAX      INTEGER { 
                        eth0(1),
                        eth1(2),
                        eth2(3),
                        eth3(4),
                        mgt0(5),
                        eth4(6),
                        eth5(8),
                        eth6(9),
                        eth7(10),
                        eth8(11),
                        eth9(12),
                        eth10(13),
                        tun(14),
                        mgt1(15),
                        eth11(16),
                        eth12(17),
                        eth13(18),
                        eth14(19),
                        eth15(20),
                        eth16(21),
                        eth17(22),
                        eth20(23),
                        eth21(24),
                        eth22(25),
                        eth23(26),
                        eth24(27),
                        eth25(28),
                        eth26(29),
                        eth27(30),
                        eth30(31),
                        eth31(32),
                        eth32(33),
                        eth33(34)
                }
    MAX-ACCESS  read-only
    STATUS      obsolete
    DESCRIPTION "No description yet."

    ::= { dpStatusTransmitKbpsThroughputEntry 1 }

dpStatusTransmitKbpsThroughputtenSeconds OBJECT-TYPE
    SYNTAX      Unsigned32
    UNITS       "kbits/sec"
    MAX-ACCESS  read-only
    STATUS      obsolete
    DESCRIPTION "No description yet."

    ::= { dpStatusTransmitKbpsThroughputEntry 2 }

dpStatusTransmitKbpsThroughputoneMinute OBJECT-TYPE
    SYNTAX      Unsigned32
    UNITS       "kbits/sec"
    MAX-ACCESS  read-only
    STATUS      obsolete
    DESCRIPTION "No description yet."

    ::= { dpStatusTransmitKbpsThroughputEntry 3 }

dpStatusTransmitKbpsThroughputtenMinutes OBJECT-TYPE
    SYNTAX      Unsigned32
    UNITS       "kbits/sec"
    MAX-ACCESS  read-only
    STATUS      obsolete
    DESCRIPTION "No description yet."

    ::= { dpStatusTransmitKbpsThroughputEntry 4 }

dpStatusTransmitKbpsThroughputoneHour OBJECT-TYPE
    SYNTAX      Unsigned32
    UNITS       "kbits/sec"
    MAX-ACCESS  read-only
    STATUS      obsolete
    DESCRIPTION "No description yet."

    ::= { dpStatusTransmitKbpsThroughputEntry 5 }

dpStatusTransmitKbpsThroughputoneDay OBJECT-TYPE
    SYNTAX      Unsigned32
    UNITS       "kbits/sec"
    MAX-ACCESS  read-only
    STATUS      obsolete
    DESCRIPTION "No description yet."

    ::= { dpStatusTransmitKbpsThroughputEntry 6 }

--

dpStatusTransmitPacketThroughputTable OBJECT-TYPE
    SYNTAX      SEQUENCE OF DPStatusTransmitPacketThroughputEntry
    MAX-ACCESS  not-accessible
    STATUS      obsolete
    DESCRIPTION
        "Transmit throughput in packets/sec for all physical Ethernet interfaces.
        For physical and VLAN interfaces, see
        drStatusNetworkTransmitPacketThroughput.
        Note: this is obsoleted and is replaced by dpStatusNetworkTransmitPacketThroughput as of release
    3.6.0"

    ::= { dpStatus 27 }

dpStatusTransmitPacketThroughputEntry OBJECT-TYPE
    SYNTAX      DPStatusTransmitPacketThroughputEntry
    MAX-ACCESS  not-accessible
    STATUS      obsolete
    DESCRIPTION "Table row."
    INDEX { dpStatusTransmitPacketThroughputInterface }

    ::= { dpStatusTransmitPacketThroughputTable 1 }

DPStatusTransmitPacketThroughputEntry ::= SEQUENCE {
    dpStatusTransmitPacketThroughputInterface    INTEGER,
    dpStatusTransmitPacketThroughputtenSeconds    Unsigned32,
    dpStatusTransmitPacketThroughputoneMinute    Unsigned32,
    dpStatusTransmitPacketThroughputtenMinutes    Unsigned32,
    dpStatusTransmitPacketThroughputoneHour    Unsigned32,
    dpStatusTransmitPacketThroughputoneDay    Unsigned32
}

dpStatusTransmitPacketThroughputInterface OBJECT-TYPE
    SYNTAX      INTEGER { 
                        eth0(1),
                        eth1(2),
                        eth2(3),
                        eth3(4),
                        mgt0(5),
                        eth4(6),
                        eth5(8),
                        eth6(9),
                        eth7(10),
                        eth8(11),
                        eth9(12),
                        eth10(13),
                        tun(14),
                        mgt1(15),
                        eth11(16),
                        eth12(17),
                        eth13(18),
                        eth14(19),
                        eth15(20),
                        eth16(21),
                        eth17(22),
                        eth20(23),
                        eth21(24),
                        eth22(25),
                        eth23(26),
                        eth24(27),
                        eth25(28),
                        eth26(29),
                        eth27(30),
                        eth30(31),
                        eth31(32),
                        eth32(33),
                        eth33(34)
                }
    MAX-ACCESS  read-only
    STATUS      obsolete
    DESCRIPTION "No description yet."

    ::= { dpStatusTransmitPacketThroughputEntry 1 }

dpStatusTransmitPacketThroughputtenSeconds OBJECT-TYPE
    SYNTAX      Unsigned32
    UNITS       "packets/sec"
    MAX-ACCESS  read-only
    STATUS      obsolete
    DESCRIPTION "No description yet."

    ::= { dpStatusTransmitPacketThroughputEntry 2 }

dpStatusTransmitPacketThroughputoneMinute OBJECT-TYPE
    SYNTAX      Unsigned32
    UNITS       "packets/sec"
    MAX-ACCESS  read-only
    STATUS      obsolete
    DESCRIPTION "No description yet."

    ::= { dpStatusTransmitPacketThroughputEntry 3 }

dpStatusTransmitPacketThroughputtenMinutes OBJECT-TYPE
    SYNTAX      Unsigned32
    UNITS       "packets/sec"
    MAX-ACCESS  read-only
    STATUS      obsolete
    DESCRIPTION "No description yet."

    ::= { dpStatusTransmitPacketThroughputEntry 4 }

dpStatusTransmitPacketThroughputoneHour OBJECT-TYPE
    SYNTAX      Unsigned32
    UNITS       "packets/sec"
    MAX-ACCESS  read-only
    STATUS      obsolete
    DESCRIPTION "No description yet."

    ::= { dpStatusTransmitPacketThroughputEntry 5 }

dpStatusTransmitPacketThroughputoneDay OBJECT-TYPE
    SYNTAX      Unsigned32
    UNITS       "packets/sec"
    MAX-ACCESS  read-only
    STATUS      obsolete
    DESCRIPTION "No description yet."

    ::= { dpStatusTransmitPacketThroughputEntry 6 }

--

dpStatusLogTargetStatusTable OBJECT-TYPE
    SYNTAX      SEQUENCE OF DPStatusLogTargetStatusEntry
    MAX-ACCESS  not-accessible
    STATUS      current
    DESCRIPTION
        "This table gives the status for each log target in the domain."

    ::= { dpStatus 28 }

dpStatusLogTargetStatusEntry OBJECT-TYPE
    SYNTAX      DPStatusLogTargetStatusEntry
    MAX-ACCESS  not-accessible
    STATUS      current
    DESCRIPTION "Table row."
    INDEX { IMPLIED dpConfigLogTargetIndex }

    ::= { dpStatusLogTargetStatusTable 1 }

DPStatusLogTargetStatusEntry ::= SEQUENCE {
    dpStatusLogTargetStatusLogTarget    DisplayString,
    dpStatusLogTargetStatusStatus    INTEGER,
    dpStatusLogTargetStatusEventsProcessed    Counter32,
    dpStatusLogTargetStatusEventsDropped    Counter32,
    dpStatusLogTargetStatusEventsPending    Counter32,
    dpStatusLogTargetStatusErrorInfo    DisplayString,
    dpStatusLogTargetStatusRequestedMemory    Unsigned32
}

dpStatusLogTargetStatusLogTarget OBJECT-TYPE
    SYNTAX      DisplayString
    MAX-ACCESS  read-only
    STATUS      current
    DESCRIPTION
        "Name of the log target."

    ::= { dpStatusLogTargetStatusEntry 1 }

dpStatusLogTargetStatusStatus OBJECT-TYPE
    SYNTAX      INTEGER { 
                        active(1),
                        warning(2),
                        failure(3),
                        suspended(4)
                }
    MAX-ACCESS  read-only
    STATUS      current
    DESCRIPTION
        "The status of the log target. When the status indicates an error, check
        the error information column."

    ::= { dpStatusLogTargetStatusEntry 2 }

dpStatusLogTargetStatusEventsProcessed OBJECT-TYPE
    SYNTAX      Counter32
    MAX-ACCESS  read-only
    STATUS      current
    DESCRIPTION
        "The number of events that this log target processed."

    ::= { dpStatusLogTargetStatusEntry 3 }

dpStatusLogTargetStatusEventsDropped OBJECT-TYPE
    SYNTAX      Counter32
    MAX-ACCESS  read-only
    STATUS      current
    DESCRIPTION
        "The number of events that this log target dropped because there are too
        many pending events."

    ::= { dpStatusLogTargetStatusEntry 4 }

dpStatusLogTargetStatusEventsPending OBJECT-TYPE
    SYNTAX      Counter32
    MAX-ACCESS  read-only
    STATUS      current
    DESCRIPTION
        "The number of pending events for this log target. These events are waiting
        to be stored at the destination."

    ::= { dpStatusLogTargetStatusEntry 5 }

dpStatusLogTargetStatusErrorInfo OBJECT-TYPE
    SYNTAX      DisplayString
    MAX-ACCESS  read-only
    STATUS      current
    DESCRIPTION
        "Error information about the status for the log target."

    ::= { dpStatusLogTargetStatusEntry 6 }

dpStatusLogTargetStatusRequestedMemory OBJECT-TYPE
    SYNTAX      Unsigned32
    UNITS       "KB"
    MAX-ACCESS  read-only
    STATUS      current
    DESCRIPTION
        "The requested memory for this log target. This measurement represents the
        high watermark of memory requested."

    ::= { dpStatusLogTargetStatusEntry 7 }

dpStatusFilesystemStatus OBJECT IDENTIFIER ::= { dpStatus 29 }

dpStatusFilesystemStatusFreeEncrypted OBJECT-TYPE
    SYNTAX      Unsigned32
    UNITS       "Mbytes"
    MAX-ACCESS  read-only
    STATUS      current
    DESCRIPTION
        "Free, or unused and available, encrypted storage space on the device. All
        files placed in encrypted storage are automatically encrypted for security
        by the device."

    ::= { dpStatusFilesystemStatus 1 }

dpStatusFilesystemStatusTotalEncrypted OBJECT-TYPE
    SYNTAX      Unsigned32
    UNITS       "Mbytes"
    MAX-ACCESS  read-only
    STATUS      current
    DESCRIPTION
        "Total encrypted storage space on the device (the maximum capacity). All
        files placed in encrypted storage are automatically encrypted for security
        by the device."

    ::= { dpStatusFilesystemStatus 2 }

dpStatusFilesystemStatusFreeUnencrypted OBJECT-TYPE
    SYNTAX      Unsigned32
    UNITS       "Mbytes"
    MAX-ACCESS  read-only
    STATUS      obsolete
    DESCRIPTION
        "Free, or unused and available, unencrypted storage space on the device.
        All files placed in unencrypted storage are not encrypted for security by
        the device."

    ::= { dpStatusFilesystemStatus 3 }

dpStatusFilesystemStatusTotalUnencrypted OBJECT-TYPE
    SYNTAX      Unsigned32
    UNITS       "Mbytes"
    MAX-ACCESS  read-only
    STATUS      obsolete
    DESCRIPTION
        "Total unencrypted storage space on the device. All files placed in
        unencrypted storage are not encrypted for security by the device."

    ::= { dpStatusFilesystemStatus 4 }

dpStatusFilesystemStatusFreeTemporary OBJECT-TYPE
    SYNTAX      Unsigned32
    UNITS       "Mbytes"
    MAX-ACCESS  read-only
    STATUS      current
    DESCRIPTION
        "Free, or unused and available, temporary storage space on the device. The
        device uses temporary storage for processing, logging and debugging."

    ::= { dpStatusFilesystemStatus 5 }

dpStatusFilesystemStatusTotalTemporary OBJECT-TYPE
    SYNTAX      Unsigned32
    UNITS       "Mbytes"
    MAX-ACCESS  read-only
    STATUS      current
    DESCRIPTION
        "Total temporary storage space on the device. The device uses temporary
        storage for processing, logging and debugging."

    ::= { dpStatusFilesystemStatus 6 }

dpStatusFilesystemStatusFreeInternal OBJECT-TYPE
    SYNTAX      Unsigned32
    UNITS       "Mbytes"
    MAX-ACCESS  read-only
    STATUS      current
    DESCRIPTION
        "Free, or unused and available, internal storage space on the device. The
        device uses internal storage for import, export, firmware upgrades and
        debug captures."

    ::= { dpStatusFilesystemStatus 7 }

dpStatusFilesystemStatusTotalInternal OBJECT-TYPE
    SYNTAX      Unsigned32
    UNITS       "Mbytes"
    MAX-ACCESS  read-only
    STATUS      current
    DESCRIPTION
        "Total internal storage space on the device. The device uses internal
        storage for import, export, firmware upgrades and debug captures."

    ::= { dpStatusFilesystemStatus 8 }

--

dpStatusHTTPConnectionsTable OBJECT-TYPE
    SYNTAX      SEQUENCE OF DPStatusHTTPConnectionsEntry
    MAX-ACCESS  not-accessible
    STATUS      current
    DESCRIPTION
        "HTTP connection statistics"

    ::= { dpStatus 30 }

dpStatusHTTPConnectionsEntry OBJECT-TYPE
    SYNTAX      DPStatusHTTPConnectionsEntry
    MAX-ACCESS  not-accessible
    STATUS      current
    DESCRIPTION "Table row."
    INDEX { IMPLIED dpConfigXMLManagerIndex }

    ::= { dpStatusHTTPConnectionsTable 1 }

DPStatusHTTPConnectionsEntry ::= SEQUENCE {
    dpStatusHTTPConnectionsXMLManager    DisplayString,
    dpStatusHTTPConnectionsreqTenSec    Counter32,
    dpStatusHTTPConnectionsreqOneMin    Counter32,
    dpStatusHTTPConnectionsreqTenMin    Counter32,
    dpStatusHTTPConnectionsreqOneHr    Counter32,
    dpStatusHTTPConnectionsreqOneDay    Counter32,
    dpStatusHTTPConnectionsreuseTenSec    Counter32,
    dpStatusHTTPConnectionsreuseOneMin    Counter32,
    dpStatusHTTPConnectionsreuseTenMin    Counter32,
    dpStatusHTTPConnectionsreuseOneHr    Counter32,
    dpStatusHTTPConnectionsreuseOneDay    Counter32,
    dpStatusHTTPConnectionscreateTenSec    Counter32,
    dpStatusHTTPConnectionscreateOneMin    Counter32,
    dpStatusHTTPConnectionscreateTenMin    Counter32,
    dpStatusHTTPConnectionscreateOneHr    Counter32,
    dpStatusHTTPConnectionscreateOneDay    Counter32,
    dpStatusHTTPConnectionsreturnTenSec    Counter32,
    dpStatusHTTPConnectionsreturnOneMin    Counter32,
    dpStatusHTTPConnectionsreturnTenMin    Counter32,
    dpStatusHTTPConnectionsreturnOneHr    Counter32,
    dpStatusHTTPConnectionsreturnOneDay    Counter32,
    dpStatusHTTPConnectionsofferTenSec    Counter32,
    dpStatusHTTPConnectionsofferOneMin    Counter32,
    dpStatusHTTPConnectionsofferTenMin    Counter32,
    dpStatusHTTPConnectionsofferOneHr    Counter32,
    dpStatusHTTPConnectionsofferOneDay    Counter32,
    dpStatusHTTPConnectionsdestroyTenSec    Counter32,
    dpStatusHTTPConnectionsdestroyOneMin    Counter32,
    dpStatusHTTPConnectionsdestroyTenMin    Counter32,
    dpStatusHTTPConnectionsdestroyOneHr    Counter32,
    dpStatusHTTPConnectionsdestroyOneDay    Counter32
}

dpStatusHTTPConnectionsXMLManager OBJECT-TYPE
    SYNTAX      DisplayString
    MAX-ACCESS  read-only
    STATUS      current
    DESCRIPTION
        "The XML manager for the HTTP connection."

    ::= { dpStatusHTTPConnectionsEntry 1 }

dpStatusHTTPConnectionsreqTenSec OBJECT-TYPE
    SYNTAX      Counter32
    MAX-ACCESS  read-only
    STATUS      current
    DESCRIPTION
        "Number of requests in the previous 10 seconds."

    ::= { dpStatusHTTPConnectionsEntry 2 }

dpStatusHTTPConnectionsreqOneMin OBJECT-TYPE
    SYNTAX      Counter32
    MAX-ACCESS  read-only
    STATUS      current
    DESCRIPTION
        "Number of requests in the previous minute."

    ::= { dpStatusHTTPConnectionsEntry 3 }

dpStatusHTTPConnectionsreqTenMin OBJECT-TYPE
    SYNTAX      Counter32
    MAX-ACCESS  read-only
    STATUS      current
    DESCRIPTION
        "Number of requests in the previous 10 minutes."

    ::= { dpStatusHTTPConnectionsEntry 4 }

dpStatusHTTPConnectionsreqOneHr OBJECT-TYPE
    SYNTAX      Counter32
    MAX-ACCESS  read-only
    STATUS      current
    DESCRIPTION
        "Number of requests in the previous hour."

    ::= { dpStatusHTTPConnectionsEntry 5 }

dpStatusHTTPConnectionsreqOneDay OBJECT-TYPE
    SYNTAX      Counter32
    MAX-ACCESS  read-only
    STATUS      current
    DESCRIPTION
        "Number of requests in the previous day."

    ::= { dpStatusHTTPConnectionsEntry 6 }

dpStatusHTTPConnectionsreuseTenSec OBJECT-TYPE
    SYNTAX      Counter32
    MAX-ACCESS  read-only
    STATUS      current
    DESCRIPTION
        "Number of reused connections in the previous 10 seconds."

    ::= { dpStatusHTTPConnectionsEntry 7 }

dpStatusHTTPConnectionsreuseOneMin OBJECT-TYPE
    SYNTAX      Counter32
    MAX-ACCESS  read-only
    STATUS      current
    DESCRIPTION
        "Number of reused connections in the previous minute."

    ::= { dpStatusHTTPConnectionsEntry 8 }

dpStatusHTTPConnectionsreuseTenMin OBJECT-TYPE
    SYNTAX      Counter32
    MAX-ACCESS  read-only
    STATUS      current
    DESCRIPTION
        "Number of reused connections in the previous 10 minutes."

    ::= { dpStatusHTTPConnectionsEntry 9 }

dpStatusHTTPConnectionsreuseOneHr OBJECT-TYPE
    SYNTAX      Counter32
    MAX-ACCESS  read-only
    STATUS      current
    DESCRIPTION
        "Number of reused connections in the previous hour."

    ::= { dpStatusHTTPConnectionsEntry 10 }

dpStatusHTTPConnectionsreuseOneDay OBJECT-TYPE
    SYNTAX      Counter32
    MAX-ACCESS  read-only
    STATUS      current
    DESCRIPTION
        "Number of reused connections in the previous day."

    ::= { dpStatusHTTPConnectionsEntry 11 }

dpStatusHTTPConnectionscreateTenSec OBJECT-TYPE
    SYNTAX      Counter32
    MAX-ACCESS  read-only
    STATUS      current
    DESCRIPTION
        "Number of connections created in the previous 10 seconds."

    ::= { dpStatusHTTPConnectionsEntry 12 }

dpStatusHTTPConnectionscreateOneMin OBJECT-TYPE
    SYNTAX      Counter32
    MAX-ACCESS  read-only
    STATUS      current
    DESCRIPTION
        "Number of connections created in the previous minute."

    ::= { dpStatusHTTPConnectionsEntry 13 }

dpStatusHTTPConnectionscreateTenMin OBJECT-TYPE
    SYNTAX      Counter32
    MAX-ACCESS  read-only
    STATUS      current
    DESCRIPTION
        "Number of connections created in the previous 10 minutes."

    ::= { dpStatusHTTPConnectionsEntry 14 }

dpStatusHTTPConnectionscreateOneHr OBJECT-TYPE
    SYNTAX      Counter32
    MAX-ACCESS  read-only
    STATUS      current
    DESCRIPTION
        "Number of connections created in the previous hour."

    ::= { dpStatusHTTPConnectionsEntry 15 }

dpStatusHTTPConnectionscreateOneDay OBJECT-TYPE
    SYNTAX      Counter32
    MAX-ACCESS  read-only
    STATUS      current
    DESCRIPTION
        "Number of connections created in the previous day."

    ::= { dpStatusHTTPConnectionsEntry 16 }

dpStatusHTTPConnectionsreturnTenSec OBJECT-TYPE
    SYNTAX      Counter32
    MAX-ACCESS  read-only
    STATUS      current
    DESCRIPTION
        "Number of returns in the previous 10 seconds."

    ::= { dpStatusHTTPConnectionsEntry 17 }

dpStatusHTTPConnectionsreturnOneMin OBJECT-TYPE
    SYNTAX      Counter32
    MAX-ACCESS  read-only
    STATUS      current
    DESCRIPTION
        "Number of returns in the previous minute."

    ::= { dpStatusHTTPConnectionsEntry 18 }

dpStatusHTTPConnectionsreturnTenMin OBJECT-TYPE
    SYNTAX      Counter32
    MAX-ACCESS  read-only
    STATUS      current
    DESCRIPTION
        "Number of returns in the previous 10 minutes."

    ::= { dpStatusHTTPConnectionsEntry 19 }

dpStatusHTTPConnectionsreturnOneHr OBJECT-TYPE
    SYNTAX      Counter32
    MAX-ACCESS  read-only
    STATUS      current
    DESCRIPTION
        "Number of returns in the previous hour."

    ::= { dpStatusHTTPConnectionsEntry 20 }

dpStatusHTTPConnectionsreturnOneDay OBJECT-TYPE
    SYNTAX      Counter32
    MAX-ACCESS  read-only
    STATUS      current
    DESCRIPTION
        "Number of returns in the previous day."

    ::= { dpStatusHTTPConnectionsEntry 21 }

dpStatusHTTPConnectionsofferTenSec OBJECT-TYPE
    SYNTAX      Counter32
    MAX-ACCESS  read-only
    STATUS      current
    DESCRIPTION
        "Number of connections offered in the previous 10 seconds."

    ::= { dpStatusHTTPConnectionsEntry 22 }

dpStatusHTTPConnectionsofferOneMin OBJECT-TYPE
    SYNTAX      Counter32
    MAX-ACCESS  read-only
    STATUS      current
    DESCRIPTION
        "Number of connections offered in the previous 10 seconds."

    ::= { dpStatusHTTPConnectionsEntry 23 }

dpStatusHTTPConnectionsofferTenMin OBJECT-TYPE
    SYNTAX      Counter32
    MAX-ACCESS  read-only
    STATUS      current
    DESCRIPTION
        "Number of connections offered in the previous 10 seconds."

    ::= { dpStatusHTTPConnectionsEntry 24 }

dpStatusHTTPConnectionsofferOneHr OBJECT-TYPE
    SYNTAX      Counter32
    MAX-ACCESS  read-only
    STATUS      current
    DESCRIPTION
        "Number of connections offered in the previous 10 seconds."

    ::= { dpStatusHTTPConnectionsEntry 25 }

dpStatusHTTPConnectionsofferOneDay OBJECT-TYPE
    SYNTAX      Counter32
    MAX-ACCESS  read-only
    STATUS      current
    DESCRIPTION
        "Number of connections offered in the previous 10 seconds."

    ::= { dpStatusHTTPConnectionsEntry 26 }

dpStatusHTTPConnectionsdestroyTenSec OBJECT-TYPE
    SYNTAX      Counter32
    MAX-ACCESS  read-only
    STATUS      current
    DESCRIPTION
        "Number of connections destroyed in the previous 10 seconds."

    ::= { dpStatusHTTPConnectionsEntry 27 }

dpStatusHTTPConnectionsdestroyOneMin OBJECT-TYPE
    SYNTAX      Counter32
    MAX-ACCESS  read-only
    STATUS      current
    DESCRIPTION
        "Number of connections destroyed in the previous minute."

    ::= { dpStatusHTTPConnectionsEntry 28 }

dpStatusHTTPConnectionsdestroyTenMin OBJECT-TYPE
    SYNTAX      Counter32
    MAX-ACCESS  read-only
    STATUS      current
    DESCRIPTION
        "Number of connections destroyed in the previous 10 minutes."

    ::= { dpStatusHTTPConnectionsEntry 29 }

dpStatusHTTPConnectionsdestroyOneHr OBJECT-TYPE
    SYNTAX      Counter32
    MAX-ACCESS  read-only
    STATUS      current
    DESCRIPTION
        "Number of connections destroyed in the previous hour."

    ::= { dpStatusHTTPConnectionsEntry 30 }

dpStatusHTTPConnectionsdestroyOneDay OBJECT-TYPE
    SYNTAX      Counter32
    MAX-ACCESS  read-only
    STATUS      current
    DESCRIPTION
        "Number of connections destroyed in the previous day."

    ::= { dpStatusHTTPConnectionsEntry 31 }

--

dpStatusDomainStatusTable OBJECT-TYPE
    SYNTAX      SEQUENCE OF DPStatusDomainStatusEntry
    MAX-ACCESS  not-accessible
    STATUS      current
    DESCRIPTION
        "Information about the status of the domain. The data includes whether
        there are unsaved changes and whether any debugging option has been
        enabled."

    ::= { dpStatus 31 }

dpStatusDomainStatusEntry OBJECT-TYPE
    SYNTAX      DPStatusDomainStatusEntry
    MAX-ACCESS  not-accessible
    STATUS      current
    DESCRIPTION "Table row."
    INDEX { IMPLIED dpStatusDomainStatusDomain }

    ::= { dpStatusDomainStatusTable 1 }

DPStatusDomainStatusEntry ::= SEQUENCE {
    dpStatusDomainStatusDomain    DisplayString,
    dpStatusDomainStatusSaveNeeded    INTEGER,
    dpStatusDomainStatusTraceEnabled    INTEGER,
    dpStatusDomainStatusDebugEnabled    INTEGER,
    dpStatusDomainStatusProbeEnabled    INTEGER,
    dpStatusDomainStatusDiagEnabled    INTEGER,
    dpStatusDomainStatusCurrentCommand    DisplayString,
    dpStatusDomainStatusQuiesceState    DisplayString,
    dpStatusDomainStatusInterfaceState    INTEGER,
    dpStatusDomainStatusFailsafeMode    INTEGER
}

dpStatusDomainStatusDomain OBJECT-TYPE
    SYNTAX      DisplayString
    MAX-ACCESS  read-only
    STATUS      current
    DESCRIPTION
        "The name of the domain."

    ::= { dpStatusDomainStatusEntry 1 }

dpStatusDomainStatusSaveNeeded OBJECT-TYPE
    SYNTAX      INTEGER { 
                        on(1),
                        off(2)
                }
    MAX-ACCESS  read-only
    STATUS      current
    DESCRIPTION
        "Indicates whether the domain contains unsaved changes."

    ::= { dpStatusDomainStatusEntry 2 }

dpStatusDomainStatusTraceEnabled OBJECT-TYPE
    SYNTAX      INTEGER { 
                        on(1),
                        off(2)
                }
    MAX-ACCESS  read-only
    STATUS      current
    DESCRIPTION
        "Indicates whether the XML File Capture utility is enabled. This utility
        can only be enabled in the default domain."

    ::= { dpStatusDomainStatusEntry 3 }

dpStatusDomainStatusDebugEnabled OBJECT-TYPE
    SYNTAX      INTEGER { 
                        on(1),
                        off(2)
                }
    MAX-ACCESS  read-only
    STATUS      current
    DESCRIPTION
        "Indicates whether the domain is employing debug logging level. At this
        level many messages are written to the log, which impacts performance."

    ::= { dpStatusDomainStatusEntry 4 }

dpStatusDomainStatusProbeEnabled OBJECT-TYPE
    SYNTAX      INTEGER { 
                        on(1),
                        off(2)
                }
    MAX-ACCESS  read-only
    STATUS      current
    DESCRIPTION
        "Indicates whether a service in the domain has the probe enabled."

    ::= { dpStatusDomainStatusEntry 5 }

dpStatusDomainStatusDiagEnabled OBJECT-TYPE
    SYNTAX      INTEGER { 
                        on(1),
                        off(2)
                }
    MAX-ACCESS  read-only
    STATUS      current
    DESCRIPTION
        "Indicates whether diagnostic tracing is enabled. Note that diagnostic
        tracing applies to all domains."

    ::= { dpStatusDomainStatusEntry 6 }

dpStatusDomainStatusCurrentCommand OBJECT-TYPE
    SYNTAX      DisplayString
    MAX-ACCESS  read-only
    STATUS      current
    DESCRIPTION
        "Provides a list of commands that are currently running on the domain. Use
        this column to confirm whether long-running commands have completed.
        Possible values are: no value - there are no commands running on the
        domain. no domain - an Application Domain object is being deleted. restart
        domain - the domain is being restored to a state defined in a saved
        configuration file. reset domain - objects in the domain configuration are
        being deleted. write memswitch - the configuration is being saved.
        import-execute - importing an Import Package object. exec - a
        configuration script is running. domain - the domain is being created.
        backup - an archive of configuration data is being generated. save
        chkpoint - a checkpoint configuration file is being generated. test schema
        - an XML file is being tested against a schema. umount - a file system is
        being unmounted. configuring - the domain is being configured.
        secure-backup - the domain is being securely backed up. secure-restore -
        the domain is being restored from a secure backup."

    ::= { dpStatusDomainStatusEntry 7 }

dpStatusDomainStatusQuiesceState OBJECT-TYPE
    SYNTAX      DisplayString
    MAX-ACCESS  read-only
    STATUS      current
    DESCRIPTION
        "Indicates the quiesce state of the domain. Individually quiesced services
        within a domain are not reported here. Possible values are: #b#Quiesce not
        in progress#/b# - this is the default status if the system is not
        quiesced. This will also be the status if individual services within the
        domain have been quiesced but the domain has not been quiesced.
        #b#Stopping new connections#/b# - the domain is being quiesced. Note that
        this state is only briefly active. #b#Waiting for persistent connections
        to complete#/b# - the domain is waiting for existing connections to
        complete before entering the Quiesced state. Note that a timeout value is
        associated with the quiesce domain request. If the timeout value is
        reached before the existing connections complete then the domain will be
        forced into the Quiesced state. #b#Waiting for services to stop#/b# The
        domain is waiting for all the services and protocols to reach an
        operational state of down . #b#Quiesced#/b# - the domain is quiesced. The
        operational states of the domain and its services are down . If the entire
        device is quiesced: all domains are in the Quiesced state, all non-default
        domains have an operational state of down , and new services in all
        non-default domains will not accept requests. #b#Unquiesce started#/b# -
        the domain has begun to start up from a quiesced state. #b#Unquiesce
        done#/b# - the domain is up and running after being quiesced. After a
        brief time this state will change to Quiesce not in progress .
        #b#Error#/b# - there has been an error. Report this error to IBM support.
        #b#Unknown quiesce state#/b# - An internal has occurred, report this to
        IBM support."

    ::= { dpStatusDomainStatusEntry 8 }

dpStatusDomainStatusInterfaceState OBJECT-TYPE
    SYNTAX      INTEGER { 
                        ok(1),
                        linkErrors(2),
                        vlanErrors(3),
                        aggErrors(4),
                        linkVlanErrors(5),
                        linkAggErrors(6),
                        vlanAggErrors(7),
                        allErrors(8)
                }
    MAX-ACCESS  read-only
    STATUS      current
    DESCRIPTION
        "Indicates the state of the networking interfaces of the appliance which
        affects all domains. Connections to only management interfaces is
        permitted when networking has an invalid configuration. Any values that
        indicate errors are present means the appliance is in this state and the
        value gives an indication as to which networking objects require
        attention. Possible values are:"

    ::= { dpStatusDomainStatusEntry 9 }

dpStatusDomainStatusFailsafeMode OBJECT-TYPE
    SYNTAX      INTEGER { 
                        none(1),
                        management(2),
                        console(3)
                }
    MAX-ACCESS  read-only
    STATUS      current
    DESCRIPTION
        "Indicates the failsafe startup mode of the appliance. Failsafe modes are
        entered after the appliance unexpectedly restarts one or more times. Until
        you correct the problem, the appliance cannot accept and process client
        requests. Contact IBM support. Possible values are:"

    ::= { dpStatusDomainStatusEntry 10 }

--

dpStatusSSHTrustedHostStatusTable OBJECT-TYPE
    SYNTAX      SEQUENCE OF DPStatusSSHTrustedHostStatusEntry
    MAX-ACCESS  not-accessible
    STATUS      current
    DESCRIPTION
        "SSH known host table"

    ::= { dpStatus 32 }

dpStatusSSHTrustedHostStatusEntry OBJECT-TYPE
    SYNTAX      DPStatusSSHTrustedHostStatusEntry
    MAX-ACCESS  not-accessible
    STATUS      current
    DESCRIPTION "Table row."
    INDEX { IMPLIED dpStatusSSHTrustedHostStatusHost }

    ::= { dpStatusSSHTrustedHostStatusTable 1 }

DPStatusSSHTrustedHostStatusEntry ::= SEQUENCE {
    dpStatusSSHTrustedHostStatusHost    DisplayString,
    dpStatusSSHTrustedHostStatusType    DisplayString
}

dpStatusSSHTrustedHostStatusHost OBJECT-TYPE
    SYNTAX      DisplayString
    MAX-ACCESS  read-only
    STATUS      current
    DESCRIPTION
        "The hostname of the peer."

    ::= { dpStatusSSHTrustedHostStatusEntry 1 }

dpStatusSSHTrustedHostStatusType OBJECT-TYPE
    SYNTAX      DisplayString
    MAX-ACCESS  read-only
    STATUS      current
    DESCRIPTION
        "The key type recorded for peer."

    ::= { dpStatusSSHTrustedHostStatusEntry 2 }

--

dpStatusSLMPeeringStatusTable OBJECT-TYPE
    SYNTAX      SEQUENCE OF DPStatusSLMPeeringStatusEntry
    MAX-ACCESS  not-accessible
    STATUS      current
    DESCRIPTION
        "Counts of traffic exchange with SLM peers"

    ::= { dpStatus 33 }

dpStatusSLMPeeringStatusEntry OBJECT-TYPE
    SYNTAX      DPStatusSLMPeeringStatusEntry
    MAX-ACCESS  not-accessible
    STATUS      current
    DESCRIPTION "Table row."
    INDEX { dpConfigSLMPolicyIndex, dpStatusSLMPeeringStatusPeer }

    ::= { dpStatusSLMPeeringStatusTable 1 }

DPStatusSLMPeeringStatusEntry ::= SEQUENCE {
    dpStatusSLMPeeringStatusSLMPolicy    DisplayString,
    dpStatusSLMPeeringStatusPeer    IpAddress,
    dpStatusSLMPeeringStatusStarted    TimeStamp,
    dpStatusSLMPeeringStatusUpdated    TimeStamp,
    dpStatusSLMPeeringStatusCount    Counter32
}

dpStatusSLMPeeringStatusSLMPolicy OBJECT-TYPE
    SYNTAX      DisplayString
    MAX-ACCESS  read-only
    STATUS      current
    DESCRIPTION "No description yet."

    ::= { dpStatusSLMPeeringStatusEntry 1 }

dpStatusSLMPeeringStatusPeer OBJECT-TYPE
    SYNTAX      IpAddress
    MAX-ACCESS  read-only
    STATUS      current
    DESCRIPTION "No description yet."

    ::= { dpStatusSLMPeeringStatusEntry 2 }

dpStatusSLMPeeringStatusStarted OBJECT-TYPE
    SYNTAX      TimeStamp
    MAX-ACCESS  read-only
    STATUS      current
    DESCRIPTION "No description yet."

    ::= { dpStatusSLMPeeringStatusEntry 3 }

dpStatusSLMPeeringStatusUpdated OBJECT-TYPE
    SYNTAX      TimeStamp
    MAX-ACCESS  read-only
    STATUS      current
    DESCRIPTION "No description yet."

    ::= { dpStatusSLMPeeringStatusEntry 4 }

dpStatusSLMPeeringStatusCount OBJECT-TYPE
    SYNTAX      Counter32
    MAX-ACCESS  read-only
    STATUS      current
    DESCRIPTION "No description yet."

    ::= { dpStatusSLMPeeringStatusEntry 5 }

dpStatusCryptoEngineStatus OBJECT IDENTIFIER ::= { dpStatus 34 }

dpStatusCryptoEngineStatusEngineType OBJECT-TYPE
    SYNTAX      INTEGER { 
                        standard(1),
                        hardware1(2),
                        hardware2(3),
                        hsm1(4),
                        hsm2(5),
                        hsm3(6),
                        hardware3(7)
                }
    MAX-ACCESS  read-only
    STATUS      deprecated
    DESCRIPTION
        "The hardware type that is installed. Type 2 is a pure accelerator. HSM,
        which is a module for secure storage of private keys, also performs
        on-board cryptographic operations."

    ::= { dpStatusCryptoEngineStatus 1 }

dpStatusCryptoEngineStatusEngineStatus OBJECT-TYPE
    SYNTAX      DisplayString
    MAX-ACCESS  read-only
    STATUS      deprecated
    DESCRIPTION
        "A status message from the accelerator. If the message is 'HSM is
        uninitialized', you must initialize the HSM into one of the two FIPS 140-2
        levels before you can use it."

    ::= { dpStatusCryptoEngineStatus 2 }

dpStatusCryptoEngineStatusFIPSLevel OBJECT-TYPE
    SYNTAX      INTEGER { 
                        notApplicable(1),
                        uninitialized(2),
                        dr2(3),
                        dr3(4)
                }
    MAX-ACCESS  read-only
    STATUS      deprecated
    DESCRIPTION
        "This information is applicable only to an appliance that has an HSM
        attached. Not initialized applies if the status message is 'HSM is
        uninitialized'. Levels 2 and 3 refer to the FIPS 140-2 level to which the
        HSM is initialized."

    ::= { dpStatusCryptoEngineStatus 3 }

dpStatusCryptoEngineStatusFIPSRole OBJECT-TYPE
    SYNTAX      INTEGER { 
                        notApplicable(1),
                        user(2),
                        officer(3)
                }
    MAX-ACCESS  read-only
    STATUS      deprecated
    DESCRIPTION
        "This information is applicable only to an appliance that has an HSM
        attached. The HSM role that the appliance has assumed. Appliances with an
        HSM of type hsm1 never assume the role of Crypto Officer. Appliances with
        an HSM of type hsm2 need to assume the role of Crypto Officer in order to
        execute KWK cloning. All other operations require the role of Crypto User."

    ::= { dpStatusCryptoEngineStatus 4 }

dpStatusCryptoEngineStatusDisableAmount OBJECT-TYPE
    SYNTAX      INTEGER { 
                        none(1),
                        all(2),
                        rsa(3)
                }
    MAX-ACCESS  read-only
    STATUS      deprecated
    DESCRIPTION
        "Parts of the cryptographic hardware functionality may be be disabled
        either at user request or by entering certain crypto modes. This field
        shows what cryptographic hardware functionality is currently disabled."

    ::= { dpStatusCryptoEngineStatus 5 }

--

dpStatusLoadBalancerStatusTable OBJECT-TYPE
    SYNTAX      SEQUENCE OF DPStatusLoadBalancerStatusEntry
    MAX-ACCESS  not-accessible
    STATUS      obsolete
    DESCRIPTION
        "Deprecated due to indexing problems (port property not indexed).
        Note: this is obsoleted and is replaced by dpStatusLoadBalancerStatus2 as of release 3.7.1"

    ::= { dpStatus 35 }

dpStatusLoadBalancerStatusEntry OBJECT-TYPE
    SYNTAX      DPStatusLoadBalancerStatusEntry
    MAX-ACCESS  not-accessible
    STATUS      obsolete
    DESCRIPTION "Table row."
    INDEX { dpConfigLoadBalancerGroupIndex, IMPLIED dpStatusLoadBalancerStatusServer }

    ::= { dpStatusLoadBalancerStatusTable 1 }

DPStatusLoadBalancerStatusEntry ::= SEQUENCE {
    dpStatusLoadBalancerStatusGroup    DisplayString,
    dpStatusLoadBalancerStatusServer    DisplayString,
    dpStatusLoadBalancerStatusPort    Unsigned32,
    dpStatusLoadBalancerStatusHealth    INTEGER
}

dpStatusLoadBalancerStatusGroup OBJECT-TYPE
    SYNTAX      DisplayString
    MAX-ACCESS  read-only
    STATUS      obsolete
    DESCRIPTION "No description yet."

    ::= { dpStatusLoadBalancerStatusEntry 1 }

dpStatusLoadBalancerStatusServer OBJECT-TYPE
    SYNTAX      DisplayString
    MAX-ACCESS  read-only
    STATUS      obsolete
    DESCRIPTION "No description yet."

    ::= { dpStatusLoadBalancerStatusEntry 2 }

dpStatusLoadBalancerStatusPort OBJECT-TYPE
    SYNTAX      Unsigned32
    MAX-ACCESS  read-only
    STATUS      obsolete
    DESCRIPTION "No description yet."

    ::= { dpStatusLoadBalancerStatusEntry 3 }

dpStatusLoadBalancerStatusHealth OBJECT-TYPE
    SYNTAX      INTEGER { 
                        up(1),
                        softdown(2),
                        down(3)
                }
    MAX-ACCESS  read-only
    STATUS      obsolete
    DESCRIPTION "No description yet."

    ::= { dpStatusLoadBalancerStatusEntry 4 }

--

dpStatusDocumentCachingSummaryTable OBJECT-TYPE
    SYNTAX      SEQUENCE OF DPStatusDocumentCachingSummaryEntry
    MAX-ACCESS  not-accessible
    STATUS      current
    DESCRIPTION
        "A report of the processed documents cached by the device. Document caching
        improves execution times."

    ::= { dpStatus 36 }

dpStatusDocumentCachingSummaryEntry OBJECT-TYPE
    SYNTAX      DPStatusDocumentCachingSummaryEntry
    MAX-ACCESS  not-accessible
    STATUS      current
    DESCRIPTION "Table row."
    INDEX { IMPLIED dpConfigXMLManagerIndex }

    ::= { dpStatusDocumentCachingSummaryTable 1 }

DPStatusDocumentCachingSummaryEntry ::= SEQUENCE {
    dpStatusDocumentCachingSummaryXMLManager    DisplayString,
    dpStatusDocumentCachingSummaryCacheCount    Unsigned32,
    dpStatusDocumentCachingSummaryDocCount    Unsigned32,
    dpStatusDocumentCachingSummaryCacheSize    Unsigned32,
    dpStatusDocumentCachingSummaryByteCount    Unsigned32,
    dpStatusDocumentCachingSummaryCacheSizeKiB    Unsigned32,
    dpStatusDocumentCachingSummaryKiByteCount    Gauge32,
    dpStatusDocumentCachingSummaryExpiredCount    Unsigned32
}

dpStatusDocumentCachingSummaryXMLManager OBJECT-TYPE
    SYNTAX      DisplayString
    MAX-ACCESS  read-only
    STATUS      current
    DESCRIPTION
        "The name of the XML manager that cached the document. Any single XML
        manager may be used by many services."

    ::= { dpStatusDocumentCachingSummaryEntry 1 }

dpStatusDocumentCachingSummaryCacheCount OBJECT-TYPE
    SYNTAX      Unsigned32
    MAX-ACCESS  read-only
    STATUS      current
    DESCRIPTION
        "The maximum number of documents allowed in the cache. When this number is
        reached, the oldest document is replaced with any new document."

    ::= { dpStatusDocumentCachingSummaryEntry 2 }

dpStatusDocumentCachingSummaryDocCount OBJECT-TYPE
    SYNTAX      Unsigned32
    MAX-ACCESS  read-only
    STATUS      current
    DESCRIPTION
        "The number of documents in the cache."

    ::= { dpStatusDocumentCachingSummaryEntry 3 }

dpStatusDocumentCachingSummaryCacheSize OBJECT-TYPE
    SYNTAX      Unsigned32
    MAX-ACCESS  read-only
    STATUS      obsolete
    DESCRIPTION
        "The maximum size in bytes of the cache."

    ::= { dpStatusDocumentCachingSummaryEntry 4 }

dpStatusDocumentCachingSummaryByteCount OBJECT-TYPE
    SYNTAX      Unsigned32
    MAX-ACCESS  read-only
    STATUS      obsolete
    DESCRIPTION
        "The number of bytes used in the cache."

    ::= { dpStatusDocumentCachingSummaryEntry 5 }

dpStatusDocumentCachingSummaryCacheSizeKiB OBJECT-TYPE
    SYNTAX      Unsigned32
    UNITS       "kibibytes"
    MAX-ACCESS  read-only
    STATUS      current
    DESCRIPTION
        "The maximum size in kibibytes of the cache."

    ::= { dpStatusDocumentCachingSummaryEntry 6 }

dpStatusDocumentCachingSummaryKiByteCount OBJECT-TYPE
    SYNTAX      Gauge32
    UNITS       "kibibytes"
    MAX-ACCESS  read-only
    STATUS      current
    DESCRIPTION
        "The number of kibibytes used in the cache."

    ::= { dpStatusDocumentCachingSummaryEntry 7 }

dpStatusDocumentCachingSummaryExpiredCount OBJECT-TYPE
    SYNTAX      Unsigned32
    MAX-ACCESS  read-only
    STATUS      current
    DESCRIPTION
        "The number of expired documents in the cache."

    ::= { dpStatusDocumentCachingSummaryEntry 8 }

--

dpStatusDocumentStatusTable OBJECT-TYPE
    SYNTAX      SEQUENCE OF DPStatusDocumentStatusEntry
    MAX-ACCESS  not-accessible
    STATUS      obsolete
    DESCRIPTION
        "Displays status information about documents in the document cache.
        Note: this is obsoleted and is replaced by dpStatusDocumentStatusSimpleIndex as of release
    3.5.1"

    ::= { dpStatus 37 }

dpStatusDocumentStatusEntry OBJECT-TYPE
    SYNTAX      DPStatusDocumentStatusEntry
    MAX-ACCESS  not-accessible
    STATUS      obsolete
    DESCRIPTION "Table row."
    INDEX { dpConfigXMLManagerIndex, IMPLIED dpStatusDocumentStatusURL }

    ::= { dpStatusDocumentStatusTable 1 }

DPStatusDocumentStatusEntry ::= SEQUENCE {
    dpStatusDocumentStatusXMLManager    DisplayString,
    dpStatusDocumentStatusURL    DisplayString,
    dpStatusDocumentStatusExpiry    DisplayString
}

dpStatusDocumentStatusXMLManager OBJECT-TYPE
    SYNTAX      DisplayString
    MAX-ACCESS  read-only
    STATUS      obsolete
    DESCRIPTION
        "The name of the XML manager that cached the document. XML managers may be
        used by multiple services."

    ::= { dpStatusDocumentStatusEntry 1 }

dpStatusDocumentStatusURL OBJECT-TYPE
    SYNTAX      DisplayString
    MAX-ACCESS  read-only
    STATUS      obsolete
    DESCRIPTION
        "Location of the cached document."

    ::= { dpStatusDocumentStatusEntry 2 }

dpStatusDocumentStatusExpiry OBJECT-TYPE
    SYNTAX      DisplayString
    MAX-ACCESS  read-only
    STATUS      obsolete
    DESCRIPTION
        "Date and time at which this document will expire from the cache."

    ::= { dpStatusDocumentStatusEntry 3 }

--

dpStatusB2BTransactionLogTable OBJECT-TYPE
    SYNTAX      SEQUENCE OF DPStatusB2BTransactionLogEntry
    MAX-ACCESS  not-accessible
    STATUS      obsolete
    DESCRIPTION
        "B2B transaction log reports
        Note: this is obsolete as of release 6.0.0.0"

    ::= { dpStatus 38 }

dpStatusB2BTransactionLogEntry OBJECT-TYPE
    SYNTAX      DPStatusB2BTransactionLogEntry
    MAX-ACCESS  not-accessible
    STATUS      obsolete
    DESCRIPTION "Table row."
    INDEX { dpStatusB2BTransactionLogTransactionSetID, dpStatusB2BTransactionLogTransactionID, dpStatusB2BTransactionLogGatewayName, IMPLIED dpStatusB2BTransactionLogDomain }

    ::= { dpStatusB2BTransactionLogTable 1 }

DPStatusB2BTransactionLogEntry ::= SEQUENCE {
    dpStatusB2BTransactionLogTransactionSetID    DisplayString,
    dpStatusB2BTransactionLogTransactionID    DisplayString,
    dpStatusB2BTransactionLogGatewayName    DisplayString,
    dpStatusB2BTransactionLogDomain    DisplayString,
    dpStatusB2BTransactionLogSenderID    DisplayString,
    dpStatusB2BTransactionLogSenderName    DisplayString,
    dpStatusB2BTransactionLogReceiverID    DisplayString,
    dpStatusB2BTransactionLogReceiverName    DisplayString,
    dpStatusB2BTransactionLogInboundURL    DisplayString,
    dpStatusB2BTransactionLogOutboundURL    DisplayString,
    dpStatusB2BTransactionLogInputTime    DisplayString,
    dpStatusB2BTransactionLogBeginMessageRetry    DisplayString,
    dpStatusB2BTransactionLogProcessingCompleted    DisplayString,
    dpStatusB2BTransactionLogResultCode    DisplayString,
    dpStatusB2BTransactionLogMDNType    DisplayString,
    dpStatusB2BTransactionLogMDNStatus    DisplayString,
    dpStatusB2BTransactionLogOutputTime    DisplayString,
    dpStatusB2BTransactionLogMDNSent    DisplayString,
    dpStatusB2BTransactionLogMDNReceived    DisplayString,
    dpStatusB2BTransactionLogMessageIDHeader    DisplayString,
    dpStatusB2BTransactionLogContentTypeHeader    DisplayString,
    dpStatusB2BTransactionLogASFromHeader    DisplayString,
    dpStatusB2BTransactionLogASToHeader    DisplayString,
    dpStatusB2BTransactionLogDateHeader    DisplayString,
    dpStatusB2BTransactionLogDispositionHeader    DisplayString,
    dpStatusB2BTransactionLogDispositionOptionsHeader    DisplayString,
    dpStatusB2BTransactionLogContentLengthHeader    DisplayString,
    dpStatusB2BTransactionLogContentDispositionHeader    DisplayString,
    dpStatusB2BTransactionLogOriginalMessageIDHeader    DisplayString,
    dpStatusB2BTransactionLogASVersion    DisplayString,
    dpStatusB2BTransactionLogIsInbound    DisplayString,
    dpStatusB2BTransactionLogSubjectHeader    DisplayString,
    dpStatusB2BTransactionLogDocumentID    DisplayString,
    dpStatusB2BTransactionLogDocumentType    DisplayString,
    dpStatusB2BTransactionLogMessageDisposition    DisplayString,
    dpStatusB2BTransactionLogFilesCreatedBitMask    DisplayString,
    dpStatusB2BTransactionLogIntegrationID    DisplayString,
    dpStatusB2BTransactionLogMaxResend    DisplayString,
    dpStatusB2BTransactionLogResendStatus    DisplayString,
    dpStatusB2BTransactionLogResendCount    DisplayString,
    dpStatusB2BTransactionLogEBMSMessageID    DisplayString,
    dpStatusB2BTransactionLogEBMSRefToMessageID    DisplayString,
    dpStatusB2BTransactionLogEBMSCPAID    DisplayString,
    dpStatusB2BTransactionLogEBMSFromPartyID    DisplayString,
    dpStatusB2BTransactionLogEBMSToPartyID    DisplayString,
    dpStatusB2BTransactionLogEBMSFromRole    DisplayString,
    dpStatusB2BTransactionLogEBMSToRole    DisplayString,
    dpStatusB2BTransactionLogEBMSConversationID    DisplayString,
    dpStatusB2BTransactionLogEBMSService    DisplayString,
    dpStatusB2BTransactionLogEBMSServiceType    DisplayString,
    dpStatusB2BTransactionLogEBMSAction    DisplayString,
    dpStatusB2BTransactionLogEBMSTimeToPersist    DisplayString,
    dpStatusB2BTransactionLogEBMSSyncReplyMode    DisplayString,
    dpStatusB2BTransactionLogEBMSDuplicateElimination    DisplayString,
    dpStatusB2BTransactionLogEBMSAckRequested    DisplayString,
    dpStatusB2BTransactionLogTransType    DisplayString
}

dpStatusB2BTransactionLogTransactionSetID OBJECT-TYPE
    SYNTAX      DisplayString
    MAX-ACCESS  read-only
    STATUS      obsolete
    DESCRIPTION
        "A system-assigned identifier that is common within same-transaction
        events."

    ::= { dpStatusB2BTransactionLogEntry 1 }

dpStatusB2BTransactionLogTransactionID OBJECT-TYPE
    SYNTAX      DisplayString
    MAX-ACCESS  read-only
    STATUS      obsolete
    DESCRIPTION
        "A system-assigned identifier."

    ::= { dpStatusB2BTransactionLogEntry 2 }

dpStatusB2BTransactionLogGatewayName OBJECT-TYPE
    SYNTAX      DisplayString
    MAX-ACCESS  read-only
    STATUS      obsolete
    DESCRIPTION
        "Name of B2B Gateway."

    ::= { dpStatusB2BTransactionLogEntry 3 }

dpStatusB2BTransactionLogDomain OBJECT-TYPE
    SYNTAX      DisplayString
    MAX-ACCESS  read-only
    STATUS      obsolete
    DESCRIPTION
        "Name of domain."

    ::= { dpStatusB2BTransactionLogEntry 4 }

dpStatusB2BTransactionLogSenderID OBJECT-TYPE
    SYNTAX      DisplayString
    MAX-ACCESS  read-only
    STATUS      obsolete
    DESCRIPTION
        "ID of B2B message sender."

    ::= { dpStatusB2BTransactionLogEntry 5 }

dpStatusB2BTransactionLogSenderName OBJECT-TYPE
    SYNTAX      DisplayString
    MAX-ACCESS  read-only
    STATUS      obsolete
    DESCRIPTION
        "Name of B2B message sender."

    ::= { dpStatusB2BTransactionLogEntry 6 }

dpStatusB2BTransactionLogReceiverID OBJECT-TYPE
    SYNTAX      DisplayString
    MAX-ACCESS  read-only
    STATUS      obsolete
    DESCRIPTION
        "ID of B2B message receiver."

    ::= { dpStatusB2BTransactionLogEntry 7 }

dpStatusB2BTransactionLogReceiverName OBJECT-TYPE
    SYNTAX      DisplayString
    MAX-ACCESS  read-only
    STATUS      obsolete
    DESCRIPTION
        "Name of B2B message receiver."

    ::= { dpStatusB2BTransactionLogEntry 8 }

dpStatusB2BTransactionLogInboundURL OBJECT-TYPE
    SYNTAX      DisplayString
    MAX-ACCESS  read-only
    STATUS      obsolete
    DESCRIPTION
        "URL of in-bound message request."

    ::= { dpStatusB2BTransactionLogEntry 9 }

dpStatusB2BTransactionLogOutboundURL OBJECT-TYPE
    SYNTAX      DisplayString
    MAX-ACCESS  read-only
    STATUS      obsolete
    DESCRIPTION
        "URL of out-bound message request."

    ::= { dpStatusB2BTransactionLogEntry 10 }

dpStatusB2BTransactionLogInputTime OBJECT-TYPE
    SYNTAX      DisplayString
    MAX-ACCESS  read-only
    STATUS      obsolete
    DESCRIPTION
        "Time message received."

    ::= { dpStatusB2BTransactionLogEntry 11 }

dpStatusB2BTransactionLogBeginMessageRetry OBJECT-TYPE
    SYNTAX      DisplayString
    MAX-ACCESS  read-only
    STATUS      obsolete
    DESCRIPTION
        "Time message retry."

    ::= { dpStatusB2BTransactionLogEntry 12 }

dpStatusB2BTransactionLogProcessingCompleted OBJECT-TYPE
    SYNTAX      DisplayString
    MAX-ACCESS  read-only
    STATUS      obsolete
    DESCRIPTION
        "Time processing complete."

    ::= { dpStatusB2BTransactionLogEntry 13 }

dpStatusB2BTransactionLogResultCode OBJECT-TYPE
    SYNTAX      DisplayString
    MAX-ACCESS  read-only
    STATUS      obsolete
    DESCRIPTION
        "Processing result code."

    ::= { dpStatusB2BTransactionLogEntry 14 }

dpStatusB2BTransactionLogMDNType OBJECT-TYPE
    SYNTAX      DisplayString
    MAX-ACCESS  read-only
    STATUS      obsolete
    DESCRIPTION
        "If an mdn was associated with this transaction, indicates if it was
        synchronous or asynchronous"

    ::= { dpStatusB2BTransactionLogEntry 15 }

dpStatusB2BTransactionLogMDNStatus OBJECT-TYPE
    SYNTAX      DisplayString
    MAX-ACCESS  read-only
    STATUS      obsolete
    DESCRIPTION
        "Status of MDN message."

    ::= { dpStatusB2BTransactionLogEntry 16 }

dpStatusB2BTransactionLogOutputTime OBJECT-TYPE
    SYNTAX      DisplayString
    MAX-ACCESS  read-only
    STATUS      obsolete
    DESCRIPTION
        "Time message was sent out-bound."

    ::= { dpStatusB2BTransactionLogEntry 17 }

dpStatusB2BTransactionLogMDNSent OBJECT-TYPE
    SYNTAX      DisplayString
    MAX-ACCESS  read-only
    STATUS      obsolete
    DESCRIPTION
        "Time MDN was sent."

    ::= { dpStatusB2BTransactionLogEntry 18 }

dpStatusB2BTransactionLogMDNReceived OBJECT-TYPE
    SYNTAX      DisplayString
    MAX-ACCESS  read-only
    STATUS      obsolete
    DESCRIPTION
        "Time MDN was received."

    ::= { dpStatusB2BTransactionLogEntry 19 }

dpStatusB2BTransactionLogMessageIDHeader OBJECT-TYPE
    SYNTAX      DisplayString
    MAX-ACCESS  read-only
    STATUS      obsolete
    DESCRIPTION
        "ID of message header."

    ::= { dpStatusB2BTransactionLogEntry 20 }

dpStatusB2BTransactionLogContentTypeHeader OBJECT-TYPE
    SYNTAX      DisplayString
    MAX-ACCESS  read-only
    STATUS      obsolete
    DESCRIPTION
        "Type of content header."

    ::= { dpStatusB2BTransactionLogEntry 21 }

dpStatusB2BTransactionLogASFromHeader OBJECT-TYPE
    SYNTAX      DisplayString
    MAX-ACCESS  read-only
    STATUS      obsolete
    DESCRIPTION
        "'From' message header information."

    ::= { dpStatusB2BTransactionLogEntry 22 }

dpStatusB2BTransactionLogASToHeader OBJECT-TYPE
    SYNTAX      DisplayString
    MAX-ACCESS  read-only
    STATUS      obsolete
    DESCRIPTION
        "'To' message header information."

    ::= { dpStatusB2BTransactionLogEntry 23 }

dpStatusB2BTransactionLogDateHeader OBJECT-TYPE
    SYNTAX      DisplayString
    MAX-ACCESS  read-only
    STATUS      obsolete
    DESCRIPTION
        "Date in message header."

    ::= { dpStatusB2BTransactionLogEntry 24 }

dpStatusB2BTransactionLogDispositionHeader OBJECT-TYPE
    SYNTAX      DisplayString
    MAX-ACCESS  read-only
    STATUS      obsolete
    DESCRIPTION
        "Disposition header information."

    ::= { dpStatusB2BTransactionLogEntry 25 }

dpStatusB2BTransactionLogDispositionOptionsHeader OBJECT-TYPE
    SYNTAX      DisplayString
    MAX-ACCESS  read-only
    STATUS      obsolete
    DESCRIPTION
        "Disposition options header information."

    ::= { dpStatusB2BTransactionLogEntry 26 }

dpStatusB2BTransactionLogContentLengthHeader OBJECT-TYPE
    SYNTAX      DisplayString
    MAX-ACCESS  read-only
    STATUS      obsolete
    DESCRIPTION
        "Header content length."

    ::= { dpStatusB2BTransactionLogEntry 27 }

dpStatusB2BTransactionLogContentDispositionHeader OBJECT-TYPE
    SYNTAX      DisplayString
    MAX-ACCESS  read-only
    STATUS      obsolete
    DESCRIPTION
        "Header content disposition."

    ::= { dpStatusB2BTransactionLogEntry 28 }

dpStatusB2BTransactionLogOriginalMessageIDHeader OBJECT-TYPE
    SYNTAX      DisplayString
    MAX-ACCESS  read-only
    STATUS      obsolete
    DESCRIPTION
        "Original message ID header."

    ::= { dpStatusB2BTransactionLogEntry 29 }

dpStatusB2BTransactionLogASVersion OBJECT-TYPE
    SYNTAX      DisplayString
    MAX-ACCESS  read-only
    STATUS      obsolete
    DESCRIPTION
        "Version of AS protocol."

    ::= { dpStatusB2BTransactionLogEntry 30 }

dpStatusB2BTransactionLogIsInbound OBJECT-TYPE
    SYNTAX      DisplayString
    MAX-ACCESS  read-only
    STATUS      obsolete
    DESCRIPTION
        "Flag whether transaction is inbound."

    ::= { dpStatusB2BTransactionLogEntry 31 }

dpStatusB2BTransactionLogSubjectHeader OBJECT-TYPE
    SYNTAX      DisplayString
    MAX-ACCESS  read-only
    STATUS      obsolete
    DESCRIPTION
        "Subject header content."

    ::= { dpStatusB2BTransactionLogEntry 32 }

dpStatusB2BTransactionLogDocumentID OBJECT-TYPE
    SYNTAX      DisplayString
    MAX-ACCESS  read-only
    STATUS      obsolete
    DESCRIPTION
        "ID of message document."

    ::= { dpStatusB2BTransactionLogEntry 33 }

dpStatusB2BTransactionLogDocumentType OBJECT-TYPE
    SYNTAX      DisplayString
    MAX-ACCESS  read-only
    STATUS      obsolete
    DESCRIPTION
        "Type of message document."

    ::= { dpStatusB2BTransactionLogEntry 34 }

dpStatusB2BTransactionLogMessageDisposition OBJECT-TYPE
    SYNTAX      DisplayString
    MAX-ACCESS  read-only
    STATUS      obsolete
    DESCRIPTION
        "Disposition of transaction message."

    ::= { dpStatusB2BTransactionLogEntry 35 }

dpStatusB2BTransactionLogFilesCreatedBitMask OBJECT-TYPE
    SYNTAX      DisplayString
    MAX-ACCESS  read-only
    STATUS      obsolete
    DESCRIPTION
        "Files created BitMask"

    ::= { dpStatusB2BTransactionLogEntry 40 }

dpStatusB2BTransactionLogIntegrationID OBJECT-TYPE
    SYNTAX      DisplayString
    MAX-ACCESS  read-only
    STATUS      obsolete
    DESCRIPTION
        "The ID used to correlate the transactions between this appliance and the
        backend systems"

    ::= { dpStatusB2BTransactionLogEntry 41 }

dpStatusB2BTransactionLogMaxResend OBJECT-TYPE
    SYNTAX      DisplayString
    MAX-ACCESS  read-only
    STATUS      obsolete
    DESCRIPTION
        "MaxResend"

    ::= { dpStatusB2BTransactionLogEntry 42 }

dpStatusB2BTransactionLogResendStatus OBJECT-TYPE
    SYNTAX      DisplayString
    MAX-ACCESS  read-only
    STATUS      obsolete
    DESCRIPTION
        "This shows the status of the last manual resend at transport layer"

    ::= { dpStatusB2BTransactionLogEntry 43 }

dpStatusB2BTransactionLogResendCount OBJECT-TYPE
    SYNTAX      DisplayString
    MAX-ACCESS  read-only
    STATUS      obsolete
    DESCRIPTION
        "The number of times the resend button has been pressed"

    ::= { dpStatusB2BTransactionLogEntry 44 }

dpStatusB2BTransactionLogEBMSMessageID OBJECT-TYPE
    SYNTAX      DisplayString
    MAX-ACCESS  read-only
    STATUS      obsolete
    DESCRIPTION "No description yet."

    ::= { dpStatusB2BTransactionLogEntry 45 }

dpStatusB2BTransactionLogEBMSRefToMessageID OBJECT-TYPE
    SYNTAX      DisplayString
    MAX-ACCESS  read-only
    STATUS      obsolete
    DESCRIPTION "No description yet."

    ::= { dpStatusB2BTransactionLogEntry 46 }

dpStatusB2BTransactionLogEBMSCPAID OBJECT-TYPE
    SYNTAX      DisplayString
    MAX-ACCESS  read-only
    STATUS      obsolete
    DESCRIPTION "No description yet."

    ::= { dpStatusB2BTransactionLogEntry 47 }

dpStatusB2BTransactionLogEBMSFromPartyID OBJECT-TYPE
    SYNTAX      DisplayString
    MAX-ACCESS  read-only
    STATUS      obsolete
    DESCRIPTION "No description yet."

    ::= { dpStatusB2BTransactionLogEntry 48 }

dpStatusB2BTransactionLogEBMSToPartyID OBJECT-TYPE
    SYNTAX      DisplayString
    MAX-ACCESS  read-only
    STATUS      obsolete
    DESCRIPTION "No description yet."

    ::= { dpStatusB2BTransactionLogEntry 49 }

dpStatusB2BTransactionLogEBMSFromRole OBJECT-TYPE
    SYNTAX      DisplayString
    MAX-ACCESS  read-only
    STATUS      obsolete
    DESCRIPTION "No description yet."

    ::= { dpStatusB2BTransactionLogEntry 50 }

dpStatusB2BTransactionLogEBMSToRole OBJECT-TYPE
    SYNTAX      DisplayString
    MAX-ACCESS  read-only
    STATUS      obsolete
    DESCRIPTION "No description yet."

    ::= { dpStatusB2BTransactionLogEntry 51 }

dpStatusB2BTransactionLogEBMSConversationID OBJECT-TYPE
    SYNTAX      DisplayString
    MAX-ACCESS  read-only
    STATUS      obsolete
    DESCRIPTION "No description yet."

    ::= { dpStatusB2BTransactionLogEntry 52 }

dpStatusB2BTransactionLogEBMSService OBJECT-TYPE
    SYNTAX      DisplayString
    MAX-ACCESS  read-only
    STATUS      obsolete
    DESCRIPTION "No description yet."

    ::= { dpStatusB2BTransactionLogEntry 53 }

dpStatusB2BTransactionLogEBMSServiceType OBJECT-TYPE
    SYNTAX      DisplayString
    MAX-ACCESS  read-only
    STATUS      obsolete
    DESCRIPTION "No description yet."

    ::= { dpStatusB2BTransactionLogEntry 54 }

dpStatusB2BTransactionLogEBMSAction OBJECT-TYPE
    SYNTAX      DisplayString
    MAX-ACCESS  read-only
    STATUS      obsolete
    DESCRIPTION "No description yet."

    ::= { dpStatusB2BTransactionLogEntry 55 }

dpStatusB2BTransactionLogEBMSTimeToPersist OBJECT-TYPE
    SYNTAX      DisplayString
    MAX-ACCESS  read-only
    STATUS      obsolete
    DESCRIPTION "No description yet."

    ::= { dpStatusB2BTransactionLogEntry 57 }

dpStatusB2BTransactionLogEBMSSyncReplyMode OBJECT-TYPE
    SYNTAX      DisplayString
    MAX-ACCESS  read-only
    STATUS      obsolete
    DESCRIPTION "No description yet."

    ::= { dpStatusB2BTransactionLogEntry 58 }

dpStatusB2BTransactionLogEBMSDuplicateElimination OBJECT-TYPE
    SYNTAX      DisplayString
    MAX-ACCESS  read-only
    STATUS      obsolete
    DESCRIPTION "No description yet."

    ::= { dpStatusB2BTransactionLogEntry 59 }

dpStatusB2BTransactionLogEBMSAckRequested OBJECT-TYPE
    SYNTAX      DisplayString
    MAX-ACCESS  read-only
    STATUS      obsolete
    DESCRIPTION "No description yet."

    ::= { dpStatusB2BTransactionLogEntry 60 }

dpStatusB2BTransactionLogTransType OBJECT-TYPE
    SYNTAX      DisplayString
    MAX-ACCESS  read-only
    STATUS      obsolete
    DESCRIPTION "No description yet."

    ::= { dpStatusB2BTransactionLogEntry 63 }

--

dpStatusB2BMessageArchiveStatusTable OBJECT-TYPE
    SYNTAX      SEQUENCE OF DPStatusB2BMessageArchiveStatusEntry
    MAX-ACCESS  not-accessible
    STATUS      current
    DESCRIPTION
        "Displays the status of the expiration operation for each B2B gateway in
        the domain."

    ::= { dpStatus 39 }

dpStatusB2BMessageArchiveStatusEntry OBJECT-TYPE
    SYNTAX      DPStatusB2BMessageArchiveStatusEntry
    MAX-ACCESS  not-accessible
    STATUS      current
    DESCRIPTION "Table row."
    INDEX { IMPLIED dpStatusB2BMessageArchiveStatusGatewayName }

    ::= { dpStatusB2BMessageArchiveStatusTable 1 }

DPStatusB2BMessageArchiveStatusEntry ::= SEQUENCE {
    dpStatusB2BMessageArchiveStatusGatewayName    DisplayString,
    dpStatusB2BMessageArchiveStatusOperationMode    DisplayString,
    dpStatusB2BMessageArchiveStatusTrigger    DisplayString,
    dpStatusB2BMessageArchiveStatusStartTime    TimeStamp,
    dpStatusB2BMessageArchiveStatusEndTime    TimeStamp,
    dpStatusB2BMessageArchiveStatusStatus    DisplayString,
    dpStatusB2BMessageArchiveStatusRecordsProcessed    DisplayString,
    dpStatusB2BMessageArchiveStatusFilesProcessed    DisplayString
}

dpStatusB2BMessageArchiveStatusGatewayName OBJECT-TYPE
    SYNTAX      DisplayString
    MAX-ACCESS  read-only
    STATUS      current
    DESCRIPTION
        "Lists the name of each instance of the B2B Gateway object in the current
        domain."

    ::= { dpStatusB2BMessageArchiveStatusEntry 1 }

dpStatusB2BMessageArchiveStatusOperationMode OBJECT-TYPE
    SYNTAX      DisplayString
    MAX-ACCESS  read-only
    STATUS      current
    DESCRIPTION
        "Lists the type of operation last performed for the specific gateway. The
        value can be Archive & Purge or Purge Only ."

    ::= { dpStatusB2BMessageArchiveStatusEntry 2 }

dpStatusB2BMessageArchiveStatusTrigger OBJECT-TYPE
    SYNTAX      DisplayString
    MAX-ACCESS  read-only
    STATUS      current
    DESCRIPTION
        "Lists whether the system or an administrator triggered the operation. If
        by the system, the value is Auto followed by the criteria for the trigger
        (date or size). If by an administrator, the value is Manual ."

    ::= { dpStatusB2BMessageArchiveStatusEntry 3 }

dpStatusB2BMessageArchiveStatusStartTime OBJECT-TYPE
    SYNTAX      TimeStamp
    MAX-ACCESS  read-only
    STATUS      current
    DESCRIPTION
        "Lists the timestamp when the operation started; for example, Thu Mar 12
        12:58:59 2009 . If value is populated when requested. If no operation
        previously requested, lists N/A ."

    ::= { dpStatusB2BMessageArchiveStatusEntry 4 }

dpStatusB2BMessageArchiveStatusEndTime OBJECT-TYPE
    SYNTAX      TimeStamp
    MAX-ACCESS  read-only
    STATUS      current
    DESCRIPTION
        "Lists the timestamp when the operation finished; for example, Thu Mar 12
        13:01:12 2009 . If value is populated when requested. If no operation
        previously requested, lists N/A ."

    ::= { dpStatusB2BMessageArchiveStatusEntry 5 }

dpStatusB2BMessageArchiveStatusStatus OBJECT-TYPE
    SYNTAX      DisplayString
    MAX-ACCESS  read-only
    STATUS      current
    DESCRIPTION
        "Lists the status of the operation, which can be one of the following
        values: Completed -- The operation completed successfully. The operation
        is complete when the values in the #b#Records Processed#/b# and #b#File
        Processed#/b# columns report 100%. Processing -- The operation is
        currently processing. Failed ( code ): ' reason ' -- The operation failed
        for the reason defined by the code."

    ::= { dpStatusB2BMessageArchiveStatusEntry 6 }

dpStatusB2BMessageArchiveStatusRecordsProcessed OBJECT-TYPE
    SYNTAX      DisplayString
    MAX-ACCESS  read-only
    STATUS      current
    DESCRIPTION
        "Lists the number of records processed by the operation. The value is
        percentage complete and records processed; for example, 17% (50 of 300) ."

    ::= { dpStatusB2BMessageArchiveStatusEntry 7 }

dpStatusB2BMessageArchiveStatusFilesProcessed OBJECT-TYPE
    SYNTAX      DisplayString
    MAX-ACCESS  read-only
    STATUS      current
    DESCRIPTION
        "Lists the amount of file data processed by the operation. The value is
        percentage complete and kilobytes processed; for example, 6% (300KB of
        5000KB) ."

    ::= { dpStatusB2BMessageArchiveStatusEntry 8 }

dpStatusSystemUsage OBJECT IDENTIFIER ::= { dpStatus 52 }

dpStatusSystemUsageInterval OBJECT-TYPE
    SYNTAX      DPTimeIntervalMillis
    UNITS       "msec"
    MAX-ACCESS  read-only
    STATUS      current
    DESCRIPTION
        "The device collects and displays load statistics over the interval,
        expressed in milliseconds, given here."

    ::= { dpStatusSystemUsage 1 }

dpStatusSystemUsageLoad OBJECT-TYPE
    SYNTAX      Unsigned32
    UNITS       "%"
    MAX-ACCESS  read-only
    STATUS      current
    DESCRIPTION
        "The percentage of total load on the device during the measurement
        interval. A load above 90 indicates the device is at or near load
        capacity."

    ::= { dpStatusSystemUsage 2 }

dpStatusSystemUsageWorkList OBJECT-TYPE
    SYNTAX      Unsigned32
    MAX-ACCESS  read-only
    STATUS      current
    DESCRIPTION
        "The number of pending messages in queue for processing by the device.
        Pending messages may include such activities as off-box logging and
        stylesheet or WSDL retrieval from remote locations."

    ::= { dpStatusSystemUsage 3 }

--

dpStatusHTTPTransactionsTable OBJECT-TYPE
    SYNTAX      SEQUENCE OF DPStatusHTTPTransactionsEntry
    MAX-ACCESS  not-accessible
    STATUS      obsolete
    DESCRIPTION
        "Transaction rate
        Note: this is obsoleted and is replaced by dpStatusHTTPTransactions2 as of release 3.7.3"

    ::= { dpStatus 53 }

dpStatusHTTPTransactionsEntry OBJECT-TYPE
    SYNTAX      DPStatusHTTPTransactionsEntry
    MAX-ACCESS  not-accessible
    STATUS      obsolete
    DESCRIPTION "Table row."
    INDEX { IMPLIED dpStatusHTTPTransactionsproxy }

    ::= { dpStatusHTTPTransactionsTable 1 }

DPStatusHTTPTransactionsEntry ::= SEQUENCE {
    dpStatusHTTPTransactionsproxy    DisplayString,
    dpStatusHTTPTransactionstenSeconds    Unsigned32,
    dpStatusHTTPTransactionsoneMinute    Unsigned32,
    dpStatusHTTPTransactionstenMinutes    Unsigned32,
    dpStatusHTTPTransactionsoneHour    Unsigned32,
    dpStatusHTTPTransactionsoneDay    Unsigned32
}

dpStatusHTTPTransactionsproxy OBJECT-TYPE
    SYNTAX      DisplayString
    MAX-ACCESS  read-only
    STATUS      obsolete
    DESCRIPTION "No description yet."

    ::= { dpStatusHTTPTransactionsEntry 1 }

dpStatusHTTPTransactionstenSeconds OBJECT-TYPE
    SYNTAX      Unsigned32
    UNITS       "tps"
    MAX-ACCESS  read-only
    STATUS      obsolete
    DESCRIPTION "No description yet."

    ::= { dpStatusHTTPTransactionsEntry 2 }

dpStatusHTTPTransactionsoneMinute OBJECT-TYPE
    SYNTAX      Unsigned32
    UNITS       "tps"
    MAX-ACCESS  read-only
    STATUS      obsolete
    DESCRIPTION "No description yet."

    ::= { dpStatusHTTPTransactionsEntry 3 }

dpStatusHTTPTransactionstenMinutes OBJECT-TYPE
    SYNTAX      Unsigned32
    UNITS       "tps"
    MAX-ACCESS  read-only
    STATUS      obsolete
    DESCRIPTION "No description yet."

    ::= { dpStatusHTTPTransactionsEntry 4 }

dpStatusHTTPTransactionsoneHour OBJECT-TYPE
    SYNTAX      Unsigned32
    UNITS       "tps"
    MAX-ACCESS  read-only
    STATUS      obsolete
    DESCRIPTION "No description yet."

    ::= { dpStatusHTTPTransactionsEntry 5 }

dpStatusHTTPTransactionsoneDay OBJECT-TYPE
    SYNTAX      Unsigned32
    UNITS       "tps"
    MAX-ACCESS  read-only
    STATUS      obsolete
    DESCRIPTION "No description yet."

    ::= { dpStatusHTTPTransactionsEntry 6 }

--

dpStatusHTTPMeanTransactionTimeTable OBJECT-TYPE
    SYNTAX      SEQUENCE OF DPStatusHTTPMeanTransactionTimeEntry
    MAX-ACCESS  not-accessible
    STATUS      obsolete
    DESCRIPTION
        "Mean transaction times
        Note: this is obsoleted and is replaced by dpStatusHTTPMeanTransactionTime2 as of release
    3.7.3"

    ::= { dpStatus 54 }

dpStatusHTTPMeanTransactionTimeEntry OBJECT-TYPE
    SYNTAX      DPStatusHTTPMeanTransactionTimeEntry
    MAX-ACCESS  not-accessible
    STATUS      obsolete
    DESCRIPTION "Table row."
    INDEX { IMPLIED dpStatusHTTPMeanTransactionTimeproxy }

    ::= { dpStatusHTTPMeanTransactionTimeTable 1 }

DPStatusHTTPMeanTransactionTimeEntry ::= SEQUENCE {
    dpStatusHTTPMeanTransactionTimeproxy    DisplayString,
    dpStatusHTTPMeanTransactionTimetenSeconds    Counter32,
    dpStatusHTTPMeanTransactionTimeoneMinute    Counter32,
    dpStatusHTTPMeanTransactionTimetenMinutes    Counter32,
    dpStatusHTTPMeanTransactionTimeoneHour    Counter32,
    dpStatusHTTPMeanTransactionTimeoneDay    Counter32
}

dpStatusHTTPMeanTransactionTimeproxy OBJECT-TYPE
    SYNTAX      DisplayString
    MAX-ACCESS  read-only
    STATUS      obsolete
    DESCRIPTION "No description yet."

    ::= { dpStatusHTTPMeanTransactionTimeEntry 1 }

dpStatusHTTPMeanTransactionTimetenSeconds OBJECT-TYPE
    SYNTAX      Counter32
    UNITS       "msec"
    MAX-ACCESS  read-only
    STATUS      obsolete
    DESCRIPTION
        "The mean transaction time over the last 10 seconds."

    ::= { dpStatusHTTPMeanTransactionTimeEntry 2 }

dpStatusHTTPMeanTransactionTimeoneMinute OBJECT-TYPE
    SYNTAX      Counter32
    UNITS       "msec"
    MAX-ACCESS  read-only
    STATUS      obsolete
    DESCRIPTION
        "The mean transaction time over the last minute."

    ::= { dpStatusHTTPMeanTransactionTimeEntry 3 }

dpStatusHTTPMeanTransactionTimetenMinutes OBJECT-TYPE
    SYNTAX      Counter32
    UNITS       "msec"
    MAX-ACCESS  read-only
    STATUS      obsolete
    DESCRIPTION
        "The mean transaction time over the last 10 minutes."

    ::= { dpStatusHTTPMeanTransactionTimeEntry 4 }

dpStatusHTTPMeanTransactionTimeoneHour OBJECT-TYPE
    SYNTAX      Counter32
    UNITS       "msec"
    MAX-ACCESS  read-only
    STATUS      obsolete
    DESCRIPTION
        "The mean transaction time over the last hour."

    ::= { dpStatusHTTPMeanTransactionTimeEntry 5 }

dpStatusHTTPMeanTransactionTimeoneDay OBJECT-TYPE
    SYNTAX      Counter32
    UNITS       "msec"
    MAX-ACCESS  read-only
    STATUS      obsolete
    DESCRIPTION
        "The mean transaction time over the last day."

    ::= { dpStatusHTTPMeanTransactionTimeEntry 6 }

dpStatusEnvironmentalSensors OBJECT IDENTIFIER ::= { dpStatus 55 }

dpStatusEnvironmentalSensorssystemTemp OBJECT-TYPE
    SYNTAX      Unsigned32 (0..65535)
    UNITS       "C"
    MAX-ACCESS  read-only
    STATUS      current
    DESCRIPTION "No description yet."

    ::= { dpStatusEnvironmentalSensors 1 }

dpStatusEnvironmentalSensorscpu1Temp OBJECT-TYPE
    SYNTAX      Unsigned32 (0..65535)
    UNITS       "C"
    MAX-ACCESS  read-only
    STATUS      current
    DESCRIPTION "No description yet."

    ::= { dpStatusEnvironmentalSensors 2 }

dpStatusEnvironmentalSensorscpu2Temp OBJECT-TYPE
    SYNTAX      Unsigned32 (0..65535)
    UNITS       "C"
    MAX-ACCESS  read-only
    STATUS      current
    DESCRIPTION "No description yet."

    ::= { dpStatusEnvironmentalSensors 3 }

dpStatusEnvironmentalSensorscpu1rpm OBJECT-TYPE
    SYNTAX      Unsigned32 (0..65535)
    UNITS       "RPM"
    MAX-ACCESS  read-only
    STATUS      current
    DESCRIPTION "No description yet."

    ::= { dpStatusEnvironmentalSensors 4 }

dpStatusEnvironmentalSensorscpu2rpm OBJECT-TYPE
    SYNTAX      Unsigned32 (0..65535)
    UNITS       "RPM"
    MAX-ACCESS  read-only
    STATUS      current
    DESCRIPTION "No description yet."

    ::= { dpStatusEnvironmentalSensors 5 }

dpStatusEnvironmentalSensorschassis1rpm OBJECT-TYPE
    SYNTAX      Unsigned32 (0..65535)
    UNITS       "RPM"
    MAX-ACCESS  read-only
    STATUS      current
    DESCRIPTION "No description yet."

    ::= { dpStatusEnvironmentalSensors 6 }

dpStatusEnvironmentalSensorschassis2rpm OBJECT-TYPE
    SYNTAX      Unsigned32 (0..65535)
    UNITS       "RPM"
    MAX-ACCESS  read-only
    STATUS      current
    DESCRIPTION "No description yet."

    ::= { dpStatusEnvironmentalSensors 7 }

dpStatusEnvironmentalSensorschassis3rpm OBJECT-TYPE
    SYNTAX      Unsigned32 (0..65535)
    UNITS       "RPM"
    MAX-ACCESS  read-only
    STATUS      current
    DESCRIPTION "No description yet."

    ::= { dpStatusEnvironmentalSensors 8 }

dpStatusEnvironmentalSensorscaseopen OBJECT-TYPE
    SYNTAX      INTEGER { 
                        yes(1),
                        no(2)
                }
    MAX-ACCESS  read-only
    STATUS      current
    DESCRIPTION "No description yet."

    ::= { dpStatusEnvironmentalSensors 9 }

dpStatusEnvironmentalSensorsvolt33 OBJECT-TYPE
    SYNTAX      DisplayString
    UNITS       "V"
    MAX-ACCESS  read-only
    STATUS      current
    DESCRIPTION "No description yet."

    ::= { dpStatusEnvironmentalSensors 10 }

dpStatusEnvironmentalSensorsvolt5 OBJECT-TYPE
    SYNTAX      DisplayString
    UNITS       "V"
    MAX-ACCESS  read-only
    STATUS      current
    DESCRIPTION "No description yet."

    ::= { dpStatusEnvironmentalSensors 11 }

dpStatusEnvironmentalSensorsvolt12 OBJECT-TYPE
    SYNTAX      DisplayString
    UNITS       "V"
    MAX-ACCESS  read-only
    STATUS      current
    DESCRIPTION "No description yet."

    ::= { dpStatusEnvironmentalSensors 12 }

dpStatusEnvironmentalSensorspowersupply OBJECT-TYPE
    SYNTAX      INTEGER { 
                        ok(1),
                        power-1-failure(2),
                        power-2-failure(3),
                        power-1-ac-lost(4),
                        power-2-ac-lost(5)
                }
    MAX-ACCESS  read-only
    STATUS      current
    DESCRIPTION "No description yet."

    ::= { dpStatusEnvironmentalSensors 13 }

dpStatusEnvironmentalSensorsbatteryinstalldate OBJECT-TYPE
    SYNTAX      DisplayString
    MAX-ACCESS  read-only
    STATUS      current
    DESCRIPTION "No description yet."

    ::= { dpStatusEnvironmentalSensors 14 }

dpStatusEnvironmentalSensorscheckintrusion OBJECT-TYPE
    SYNTAX      INTEGER { 
                        yes(1),
                        no(2)
                }
    MAX-ACCESS  read-only
    STATUS      current
    DESCRIPTION "No description yet."

    ::= { dpStatusEnvironmentalSensors 15 }

--

dpStatusMessageCountsTable OBJECT-TYPE
    SYNTAX      SEQUENCE OF DPStatusMessageCountsEntry
    MAX-ACCESS  not-accessible
    STATUS      current
    DESCRIPTION
        "Message count monitor."

    ::= { dpStatus 56 }

dpStatusMessageCountsEntry OBJECT-TYPE
    SYNTAX      DPStatusMessageCountsEntry
    MAX-ACCESS  not-accessible
    STATUS      current
    DESCRIPTION "Table row."
    INDEX { IMPLIED dpConfigCountMonitorIndex }

    ::= { dpStatusMessageCountsTable 1 }

DPStatusMessageCountsEntry ::= SEQUENCE {
    dpStatusMessageCountsMonitor    DisplayString,
    dpStatusMessageCountsType    DisplayString,
    dpStatusMessageCountsMeasure    INTEGER,
    dpStatusMessageCountstenSeconds    Counter32,
    dpStatusMessageCountsoneMinute    Counter32,
    dpStatusMessageCountstenMinutes    Counter32,
    dpStatusMessageCountsoneHour    Counter32,
    dpStatusMessageCountsoneDay    Counter32,
    dpStatusMessageCountsTotal    Counter32
}

dpStatusMessageCountsMonitor OBJECT-TYPE
    SYNTAX      DisplayString
    MAX-ACCESS  read-only
    STATUS      current
    DESCRIPTION
        "Name of the message count monitor."

    ::= { dpStatusMessageCountsEntry 1 }

dpStatusMessageCountsType OBJECT-TYPE
    SYNTAX      DisplayString
    MAX-ACCESS  read-only
    STATUS      current
    DESCRIPTION
        "The target message class for this count monitor."

    ::= { dpStatusMessageCountsEntry 2 }

dpStatusMessageCountsMeasure OBJECT-TYPE
    SYNTAX      INTEGER { 
                        requests(1),
                        responses(2),
                        xpath(3),
                        errors(4)
                }
    MAX-ACCESS  read-only
    STATUS      current
    DESCRIPTION
        "Specifies the circumstances under which this count monitor increments."

    ::= { dpStatusMessageCountsEntry 3 }

dpStatusMessageCountstenSeconds OBJECT-TYPE
    SYNTAX      Counter32
    MAX-ACCESS  read-only
    STATUS      current
    DESCRIPTION
        "Messages counted over the previous 10 seconds."

    ::= { dpStatusMessageCountsEntry 4 }

dpStatusMessageCountsoneMinute OBJECT-TYPE
    SYNTAX      Counter32
    MAX-ACCESS  read-only
    STATUS      current
    DESCRIPTION
        "Messages counted over the previous minute."

    ::= { dpStatusMessageCountsEntry 5 }

dpStatusMessageCountstenMinutes OBJECT-TYPE
    SYNTAX      Counter32
    MAX-ACCESS  read-only
    STATUS      current
    DESCRIPTION
        "Messages counted over the previous 10 minutes."

    ::= { dpStatusMessageCountsEntry 6 }

dpStatusMessageCountsoneHour OBJECT-TYPE
    SYNTAX      Counter32
    MAX-ACCESS  read-only
    STATUS      current
    DESCRIPTION
        "Messages counted over the previous hour."

    ::= { dpStatusMessageCountsEntry 7 }

dpStatusMessageCountsoneDay OBJECT-TYPE
    SYNTAX      Counter32
    MAX-ACCESS  read-only
    STATUS      current
    DESCRIPTION
        "Messages counted over the previous day."

    ::= { dpStatusMessageCountsEntry 8 }

dpStatusMessageCountsTotal OBJECT-TYPE
    SYNTAX      Counter32
    MAX-ACCESS  read-only
    STATUS      current
    DESCRIPTION
        "Total number of messages counted by this monitor."

    ::= { dpStatusMessageCountsEntry 9 }

--

dpStatusMessageCountFiltersTable OBJECT-TYPE
    SYNTAX      SEQUENCE OF DPStatusMessageCountFiltersEntry
    MAX-ACCESS  not-accessible
    STATUS      current
    DESCRIPTION
        "Message monitor count filters information."

    ::= { dpStatus 57 }

dpStatusMessageCountFiltersEntry OBJECT-TYPE
    SYNTAX      DPStatusMessageCountFiltersEntry
    MAX-ACCESS  not-accessible
    STATUS      current
    DESCRIPTION "Table row."
    INDEX { dpConfigCountMonitorIndex, dpStatusMessageCountFiltersSource, IMPLIED dpStatusMessageCountFiltersFilter }

    ::= { dpStatusMessageCountFiltersTable 1 }

DPStatusMessageCountFiltersEntry ::= SEQUENCE {
    dpStatusMessageCountFiltersMonitor    DisplayString,
    dpStatusMessageCountFiltersSource    IpAddress,
    dpStatusMessageCountFiltersFilter    DisplayString,
    dpStatusMessageCountFiltersTotal    Counter32,
    dpStatusMessageCountFiltersHits    Counter32
}

dpStatusMessageCountFiltersMonitor OBJECT-TYPE
    SYNTAX      DisplayString
    MAX-ACCESS  read-only
    STATUS      current
    DESCRIPTION
        "The name of the Count Monitor activated."

    ::= { dpStatusMessageCountFiltersEntry 1 }

dpStatusMessageCountFiltersSource OBJECT-TYPE
    SYNTAX      IpAddress
    MAX-ACCESS  read-only
    STATUS      current
    DESCRIPTION
        "The IP address assigned to the DP device that received the message. An
        address of 0.0.0.0 indicates any or all interfaces."

    ::= { dpStatusMessageCountFiltersEntry 4 }

dpStatusMessageCountFiltersFilter OBJECT-TYPE
    SYNTAX      DisplayString
    MAX-ACCESS  read-only
    STATUS      current
    DESCRIPTION
        "This is the name of the Filter Action object invoked by this Count
        Monitor."

    ::= { dpStatusMessageCountFiltersEntry 5 }

dpStatusMessageCountFiltersTotal OBJECT-TYPE
    SYNTAX      Counter32
    MAX-ACCESS  read-only
    STATUS      current
    DESCRIPTION
        "The total number of messages processed by the monitor. This may be larger
        than the value in the Filter hits column."

    ::= { dpStatusMessageCountFiltersEntry 6 }

dpStatusMessageCountFiltersHits OBJECT-TYPE
    SYNTAX      Counter32
    MAX-ACCESS  read-only
    STATUS      current
    DESCRIPTION
        "The number of messages processed by the monitor that activated the listed
        Filter Action."

    ::= { dpStatusMessageCountFiltersEntry 7 }

--

dpStatusMessageDurationsTable OBJECT-TYPE
    SYNTAX      SEQUENCE OF DPStatusMessageDurationsEntry
    MAX-ACCESS  not-accessible
    STATUS      current
    DESCRIPTION
        "Message monitor durations"

    ::= { dpStatus 58 }

dpStatusMessageDurationsEntry OBJECT-TYPE
    SYNTAX      DPStatusMessageDurationsEntry
    MAX-ACCESS  not-accessible
    STATUS      current
    DESCRIPTION "Table row."
    INDEX { IMPLIED dpConfigDurationMonitorIndex }

    ::= { dpStatusMessageDurationsTable 1 }

DPStatusMessageDurationsEntry ::= SEQUENCE {
    dpStatusMessageDurationsMonitor    DisplayString,
    dpStatusMessageDurationsType    DisplayString,
    dpStatusMessageDurationsMeasure    INTEGER,
    dpStatusMessageDurationsCount    Counter32,
    dpStatusMessageDurationsMinimum    DPTimeIntervalMillis,
    dpStatusMessageDurationsMaximum    DPTimeIntervalMillis,
    dpStatusMessageDurationsAverage    DPTimeIntervalMillis,
    dpStatusMessageDurationstenSeconds    Counter32,
    dpStatusMessageDurationsoneMinute    Counter32,
    dpStatusMessageDurationstenMinutes    Counter32,
    dpStatusMessageDurationsoneHour    Counter32,
    dpStatusMessageDurationsoneDay    Counter32
}

dpStatusMessageDurationsMonitor OBJECT-TYPE
    SYNTAX      DisplayString
    MAX-ACCESS  read-only
    STATUS      current
    DESCRIPTION
        "Name of the duration monitor."

    ::= { dpStatusMessageDurationsEntry 1 }

dpStatusMessageDurationsType OBJECT-TYPE
    SYNTAX      DisplayString
    MAX-ACCESS  read-only
    STATUS      current
    DESCRIPTION
        "The target message class for the duration monitor."

    ::= { dpStatusMessageDurationsEntry 2 }

dpStatusMessageDurationsMeasure OBJECT-TYPE
    SYNTAX      INTEGER { 
                        messages(1),
                        requests(2),
                        server(3),
                        responses(4)
                }
    MAX-ACCESS  read-only
    STATUS      current
    DESCRIPTION
        "The portion of the client-to-server roundtrip of interest to this duration
        monitor."

    ::= { dpStatusMessageDurationsEntry 3 }

dpStatusMessageDurationsCount OBJECT-TYPE
    SYNTAX      Counter32
    MAX-ACCESS  read-only
    STATUS      current
    DESCRIPTION
        "The number of times that this duration monitor has been activated."

    ::= { dpStatusMessageDurationsEntry 4 }

dpStatusMessageDurationsMinimum OBJECT-TYPE
    SYNTAX      DPTimeIntervalMillis
    UNITS       "ms"
    MAX-ACCESS  read-only
    STATUS      current
    DESCRIPTION
        "The shortest transaction time recorded by this duration monitor for
        transactions of the specified type and message class."

    ::= { dpStatusMessageDurationsEntry 5 }

dpStatusMessageDurationsMaximum OBJECT-TYPE
    SYNTAX      DPTimeIntervalMillis
    UNITS       "ms"
    MAX-ACCESS  read-only
    STATUS      current
    DESCRIPTION
        "The longest transaction time recorded by this duration monitor for
        transactions of the specified type and message class."

    ::= { dpStatusMessageDurationsEntry 6 }

dpStatusMessageDurationsAverage OBJECT-TYPE
    SYNTAX      DPTimeIntervalMillis
    UNITS       "ms"
    MAX-ACCESS  read-only
    STATUS      current
    DESCRIPTION
        "The average transaction time recorded by this duration monitor for
        transactions of the specified type and message class."

    ::= { dpStatusMessageDurationsEntry 7 }

dpStatusMessageDurationstenSeconds OBJECT-TYPE
    SYNTAX      Counter32
    UNITS       "ms"
    MAX-ACCESS  read-only
    STATUS      current
    DESCRIPTION
        "The average transaction time recorded by this duration monitor for
        transactions of the specified type and message class over the previous 10
        seconds."

    ::= { dpStatusMessageDurationsEntry 8 }

dpStatusMessageDurationsoneMinute OBJECT-TYPE
    SYNTAX      Counter32
    UNITS       "ms"
    MAX-ACCESS  read-only
    STATUS      current
    DESCRIPTION
        "The average transaction time recorded by this duration monitor for
        transactions of the specified type and message class over the previous
        minute."

    ::= { dpStatusMessageDurationsEntry 9 }

dpStatusMessageDurationstenMinutes OBJECT-TYPE
    SYNTAX      Counter32
    UNITS       "ms"
    MAX-ACCESS  read-only
    STATUS      current
    DESCRIPTION
        "The average transaction time recorded by this duration monitor for
        transactions of the specified type and message class over the previous 10
        minutes."

    ::= { dpStatusMessageDurationsEntry 10 }

dpStatusMessageDurationsoneHour OBJECT-TYPE
    SYNTAX      Counter32
    UNITS       "ms"
    MAX-ACCESS  read-only
    STATUS      current
    DESCRIPTION
        "The average transaction time recorded by this duration monitor for
        transactions of the specified type and message class over the previous
        hour."

    ::= { dpStatusMessageDurationsEntry 11 }

dpStatusMessageDurationsoneDay OBJECT-TYPE
    SYNTAX      Counter32
    UNITS       "ms"
    MAX-ACCESS  read-only
    STATUS      current
    DESCRIPTION
        "The average transaction time recorded by this duration monitor for
        transactions of the specified type and message class over the previous
        day."

    ::= { dpStatusMessageDurationsEntry 12 }

--

dpStatusMessageDurationFiltersTable OBJECT-TYPE
    SYNTAX      SEQUENCE OF DPStatusMessageDurationFiltersEntry
    MAX-ACCESS  not-accessible
    STATUS      current
    DESCRIPTION
        "Message monitor duration filters"

    ::= { dpStatus 59 }

dpStatusMessageDurationFiltersEntry OBJECT-TYPE
    SYNTAX      DPStatusMessageDurationFiltersEntry
    MAX-ACCESS  not-accessible
    STATUS      current
    DESCRIPTION "Table row."
    INDEX { dpConfigDurationMonitorIndex, IMPLIED dpStatusMessageDurationFiltersFilter }

    ::= { dpStatusMessageDurationFiltersTable 1 }

DPStatusMessageDurationFiltersEntry ::= SEQUENCE {
    dpStatusMessageDurationFiltersMonitor    DisplayString,
    dpStatusMessageDurationFiltersFilter    DisplayString,
    dpStatusMessageDurationFiltersTotal    Counter32,
    dpStatusMessageDurationFiltersHits    Counter32
}

dpStatusMessageDurationFiltersMonitor OBJECT-TYPE
    SYNTAX      DisplayString
    MAX-ACCESS  read-only
    STATUS      current
    DESCRIPTION
        "The name of the duration monitor."

    ::= { dpStatusMessageDurationFiltersEntry 1 }

dpStatusMessageDurationFiltersFilter OBJECT-TYPE
    SYNTAX      DisplayString
    MAX-ACCESS  read-only
    STATUS      current
    DESCRIPTION
        "This is the name of the Filter Action object invoked by the listed
        duration monitor."

    ::= { dpStatusMessageDurationFiltersEntry 4 }

dpStatusMessageDurationFiltersTotal OBJECT-TYPE
    SYNTAX      Counter32
    MAX-ACCESS  read-only
    STATUS      current
    DESCRIPTION
        "The total number of messages processed by the monitor. This may be larger
        than the value in the Filter hits column."

    ::= { dpStatusMessageDurationFiltersEntry 5 }

dpStatusMessageDurationFiltersHits OBJECT-TYPE
    SYNTAX      Counter32
    MAX-ACCESS  read-only
    STATUS      current
    DESCRIPTION
        "The number of messages processed by the monitor that activated the listed
        Filter Action."

    ::= { dpStatusMessageDurationFiltersEntry 6 }

--

dpStatusMessageSourcesTable OBJECT-TYPE
    SYNTAX      SEQUENCE OF DPStatusMessageSourcesEntry
    MAX-ACCESS  not-accessible
    STATUS      current
    DESCRIPTION
        "Message monitor sources"

    ::= { dpStatus 66 }

dpStatusMessageSourcesEntry OBJECT-TYPE
    SYNTAX      DPStatusMessageSourcesEntry
    MAX-ACCESS  not-accessible
    STATUS      current
    DESCRIPTION "Table row."
    INDEX { dpConfigCountMonitorIndex, dpStatusMessageSourcesSource }

    ::= { dpStatusMessageSourcesTable 1 }

DPStatusMessageSourcesEntry ::= SEQUENCE {
    dpStatusMessageSourcesMonitor    DisplayString,
    dpStatusMessageSourcesSource    IpAddress,
    dpStatusMessageSourcesTotal    Unsigned32,
    dpStatusMessageSourcesLast    TimeStamp
}

dpStatusMessageSourcesMonitor OBJECT-TYPE
    SYNTAX      DisplayString
    MAX-ACCESS  read-only
    STATUS      current
    DESCRIPTION
        "Name of the monitor."

    ::= { dpStatusMessageSourcesEntry 1 }

dpStatusMessageSourcesSource OBJECT-TYPE
    SYNTAX      IpAddress
    MAX-ACCESS  read-only
    STATUS      current
    DESCRIPTION
        "The IP address assigned to the DP device that received the message. An
        address of 0.0.0.0 indicates any or all interfaces."

    ::= { dpStatusMessageSourcesEntry 2 }

dpStatusMessageSourcesTotal OBJECT-TYPE
    SYNTAX      Unsigned32
    MAX-ACCESS  read-only
    STATUS      current
    DESCRIPTION
        "Total number of messages counted by this monitor."

    ::= { dpStatusMessageSourcesEntry 3 }

dpStatusMessageSourcesLast OBJECT-TYPE
    SYNTAX      TimeStamp
    MAX-ACCESS  read-only
    STATUS      current
    DESCRIPTION
        "The last time that this monitor was incremented"

    ::= { dpStatusMessageSourcesEntry 4 }

--

dpStatusStylesheetProfilesTable OBJECT-TYPE
    SYNTAX      SEQUENCE OF DPStatusStylesheetProfilesEntry
    MAX-ACCESS  not-accessible
    STATUS      obsolete
    DESCRIPTION
        "Profiling of the Execution Time for a Stylesheet
        Note: this is obsoleted and is replaced by dpStatusStylesheetProfilesSimpleIndex as of release
    3.5.1"

    ::= { dpStatus 67 }

dpStatusStylesheetProfilesEntry OBJECT-TYPE
    SYNTAX      DPStatusStylesheetProfilesEntry
    MAX-ACCESS  not-accessible
    STATUS      obsolete
    DESCRIPTION "Table row."
    INDEX { dpConfigXMLManagerIndex, dpStatusStylesheetProfilesOutputMode, IMPLIED dpStatusStylesheetProfilesURL }

    ::= { dpStatusStylesheetProfilesTable 1 }

DPStatusStylesheetProfilesEntry ::= SEQUENCE {
    dpStatusStylesheetProfilesXMLManager    DisplayString,
    dpStatusStylesheetProfilesOutputMode    INTEGER,
    dpStatusStylesheetProfilesURL    DisplayString,
    dpStatusStylesheetProfilesName    DisplayString,
    dpStatusStylesheetProfilesLocation    DisplayString,
    dpStatusStylesheetProfilesCount    Counter32,
    dpStatusStylesheetProfilesType    DisplayString,
    dpStatusStylesheetProfilesTotalTimeMS    Unsigned32
}

dpStatusStylesheetProfilesXMLManager OBJECT-TYPE
    SYNTAX      DisplayString
    MAX-ACCESS  read-only
    STATUS      obsolete
    DESCRIPTION "No description yet."

    ::= { dpStatusStylesheetProfilesEntry 1 }

dpStatusStylesheetProfilesOutputMode OBJECT-TYPE
    SYNTAX      INTEGER { 
                        general(1),
                        stream(2),
                        context(3),
                        events(4)
                }
    MAX-ACCESS  read-only
    STATUS      obsolete
    DESCRIPTION "No description yet."

    ::= { dpStatusStylesheetProfilesEntry 2 }

dpStatusStylesheetProfilesURL OBJECT-TYPE
    SYNTAX      DisplayString
    MAX-ACCESS  read-only
    STATUS      obsolete
    DESCRIPTION "No description yet."

    ::= { dpStatusStylesheetProfilesEntry 3 }

dpStatusStylesheetProfilesName OBJECT-TYPE
    SYNTAX      DisplayString
    MAX-ACCESS  read-only
    STATUS      obsolete
    DESCRIPTION "No description yet."

    ::= { dpStatusStylesheetProfilesEntry 5 }

dpStatusStylesheetProfilesLocation OBJECT-TYPE
    SYNTAX      DisplayString
    MAX-ACCESS  read-only
    STATUS      obsolete
    DESCRIPTION "No description yet."

    ::= { dpStatusStylesheetProfilesEntry 6 }

dpStatusStylesheetProfilesCount OBJECT-TYPE
    SYNTAX      Counter32
    MAX-ACCESS  read-only
    STATUS      obsolete
    DESCRIPTION "No description yet."

    ::= { dpStatusStylesheetProfilesEntry 8 }

dpStatusStylesheetProfilesType OBJECT-TYPE
    SYNTAX      DisplayString
    MAX-ACCESS  read-only
    STATUS      obsolete
    DESCRIPTION "No description yet."

    ::= { dpStatusStylesheetProfilesEntry 9 }

dpStatusStylesheetProfilesTotalTimeMS OBJECT-TYPE
    SYNTAX      Unsigned32
    MAX-ACCESS  read-only
    STATUS      obsolete
    DESCRIPTION "No description yet."

    ::= { dpStatusStylesheetProfilesEntry 10 }

--

dpStatusObjectStatusTable OBJECT-TYPE
    SYNTAX      SEQUENCE OF DPStatusObjectStatusEntry
    MAX-ACCESS  not-accessible
    STATUS      current
    DESCRIPTION
        "Configuration object operational state"

    ::= { dpStatus 80 }

dpStatusObjectStatusEntry OBJECT-TYPE
    SYNTAX      DPStatusObjectStatusEntry
    MAX-ACCESS  not-accessible
    STATUS      current
    DESCRIPTION "Table row."
    INDEX { dpStatusObjectStatusClass, IMPLIED dpStatusObjectStatusName }

    ::= { dpStatusObjectStatusTable 1 }

DPStatusObjectStatusEntry ::= SEQUENCE {
    dpStatusObjectStatusClass    INTEGER,
    dpStatusObjectStatusOpState    INTEGER,
    dpStatusObjectStatusAdminState    INTEGER,
    dpStatusObjectStatusName    DisplayString,
    dpStatusObjectStatusEventCode    DisplayString,
    dpStatusObjectStatusErrorCode    DisplayString,
    dpStatusObjectStatusConfigState    INTEGER
}

dpStatusObjectStatusClass OBJECT-TYPE
    SYNTAX      INTEGER { 
                        configBase(0),
                        dNSNameService(1),
                        ethernetInterface(2),
                        cRLFetch(3),
                        hTTPService(4),
                        statistics(5),
                        traceTarget(6),
                        nTPService(7),
                        throttler(8),
                        stylePolicy(9),
                        hTTPUserAgent(10),
                        tCPProxyService(12),
                        uRLMap(13),
                        uRLRefreshPolicy(14),
                        user(15),
                        networkSettings(16),
                        xMLManager(17),
                        mQQM(18),
                        xSLProxyService(19),
                        mQGW(20),
                        sSLProxyService(21),
                        stylePolicyRule(22),
                        errorReportSettings(23),
                        iPInterface(25),
                        matching(26),
                        systemSettings(27),
                        sNMPSettings(28),
                        rADIUSSettings(29),
                        userGroup(30),
                        shellAlias(31),
                        xSLCoprocService(32),
                        telnetService(33),
                        cryptoSSKey(34),
                        messageMonitor(35),
                        uRLRewritePolicy(36),
                        sSLProxyProfile(37),
                        hTTPProxyService(38),
                        service(39),
                        cryptoFWCred(41),
                        xMLFirewallService(42),
                        cryptoKey(43),
                        cryptoCertificate(44),
                        cryptoIdentCred(45),
                        cryptoValCred(46),
                        cryptoProfile(47),
                        logTarget(48),
                        sSHService(49),
                        crypto(50),
                        webGUI(51),
                        eventlog(52),
                        accessControl(53),
                        messageFlowControl(54),
                        mQConfiguration(55),
                        deviceSettings(56),
                        deviceManagementService(57),
                        networkConfiguration(58),
                        logLabel(59),
                        mgmtInterface(60),
                        messageMatching(61),
                        messageType(62),
                        countMonitor(63),
                        durationMonitor(64),
                        filterAction(65),
                        hTTPInputConversionMap(66),
                        compileOptionsPolicy(68),
                        xPathRoutingMap(69),
                        schemaExceptionMap(70),
                        reserved71(71),
                        documentCryptoMap(72),
                        tAM(73),
                        domain(74),
                        timeSettings(75),
                        dynamicXMLContentMap(77),
                        dynamicStylesheet(78),
                        dynamicSchema(79),
                        accessControlList(80),
                        importPackage(81),
                        mQhost(82),
                        mQproxy(83),
                        loadBalancerGroup(84),
                        rBMSettings(85),
                        includeConfig(86),
                        certMonitor(87),
                        hostAlias(88),
                        aAAPolicy(91),
                        stylePolicyAction(92),
                        cryptoKerberosKDC(93),
                        webServiceMonitor(94),
                        wSGateway(95),
                        stylePolicyRuleBase(96),
                        wSStylePolicyRule(97),
                        wSStylePolicy(98),
                        webServicesAgent(99),
                        gatewayBase(100),
                        multiProtocolGateway(101),
                        sourceProtocolHandler(102),
                        hTTPSourceProtocolHandler(103),
                        hTTPSSourceProtocolHandler(104),
                        mQSourceProtocolHandler(105),
                        xTCProtocolHandler(106),
                        cryptoKerberosKeytab(109),
                        statelessTCPSourceProtocolHandler(110),
                        sLMCredClass(111),
                        sLMRsrcClass(112),
                        sLMSchedule(113),
                        sLMAction(114),
                        sLMPolicy(115),
                        peerGroup(116),
                        reserved117(117),
                        tFIMEndpoint(118),
                        xmltrace(120),
                        nFSClientSettings(121),
                        wSEndpointRewritePolicy(122),
                        sQLDataSource(124),
                        nFSStaticMount(125),
                        nFSDynamicMounts(126),
                        webAppErrorHandlingPolicy(127),
                        simpleCountMonitor(128),
                        nameValueProfile(129),
                        webAppResponse(130),
                        webAppRequest(131),
                        webAppFW(132),
                        appSecurityPolicy(133),
                        uDDIRegistry(134),
                        webAppSessionPolicy(135),
                        jMSServer(136),
                        tibcoEMSServer(137),
                        tibcoEMSSourceProtocolHandler(138),
                        xACMLPDP(139),
                        jMSSourceProtocolHandler(140),
                        webSphereJMSServer(141),
                        webSphereJMSSourceProtocolHandler(142),
                        processingMetadata(143),
                        mTOMPolicy(144),
                        fTPServerSourceProtocolHandler(145),
                        filePollerSourceProtocolHandler(146),
                        nFSFilePollerSourceProtocolHandler(147),
                        fTPFilePollerSourceProtocolHandler(148),
                        fTPQuoteCommands(149),
                        mQQMBase(150),
                        mQQMGroup(151),
                        wSRRServer(152),
                        wSRRSubscription(153),
                        webServiceSubscription(154),
                        uDDISubscription(155),
                        vLANInterface(156),
                        conformancePolicy(157),
                        sOAPHeaderDisposition(158),
                        policyAttachments(159),
                        policyParameters(160),
                        iMSConnect(161),
                        iMSConnectSourceProtocolHandler(162),
                        lDAPSearchParameters(163),
                        configDeploymentPolicy(164),
                        compactFlash(165),
                        raidVolume(166),
                        iScsiInitiatorConfig(167),
                        lLMSourceProtocolHandler(168),
                        tRVSourceProtocolHandler(169),
                        iScsiHBAConfig(170),
                        iScsiTargetConfig(171),
                        iScsiVolumeConfig(172),
                        iScsiChapConfig(173),
                        zosNSSClient(174),
                        sSHServerSourceProtocolHandler(175),
                        fTPDemonSourceProtocolHandler(176),
                        aS3SourceProtocolHandler(177),
                        aS2SourceProtocolHandler(178),
                        b2BXPathRoutingPolicy(179),
                        lLMInstance(180),
                        lLMMulticastReceive(181),
                        lLMMulticastTransmit(182),
                        lLMUnicast(183),
                        lLMMulticastTierGroup(184),
                        lLMRoute(186),
                        lLMPolicy(187),
                        fibreChannelHBA(188),
                        fibreChannelTarget(189),
                        fibreChannelVolume(190),
                        webB2BViewer(192),
                        b2BPersistence(193),
                        b2BProfileGroup(194),
                        b2BGateway(195),
                        b2BProfile(196),
                        wCCService(197),
                        formsLoginPolicy(198),
                        tRVPolicy(199),
                        tRVRoute(200),
                        tRVTransport(201),
                        lLMPolicyBase(202),
                        lLMRouteBase(203),
                        pOPPollerSourceProtocolHandlerBase(204),
                        aS1PollerSourceProtocolHandler(205),
                        pOPPollerSourceProtocolHandler(206),
                        sMTPServerConnection(207),
                        xM70Persistence(208),
                        wSRRSavedSearchSubscription(209),
                        eBMS2SourceProtocolHandler(210),
                        sAMLAttributes(211),
                        sSHClientProfile(212),
                        sFTPFilePollerSourceProtocolHandler(213),
                        zHybridTargetControlService(214),
                        multipathService(215),
                        clusterService(216),
                        secureCloudConnector(217),
                        iPMILanChannel(218),
                        iPMIUser(219),
                        b2BCPACollaboration(220),
                        mQFTESourceProtocolHandler(221),
                        b2BCPA(222),
                        b2BCPASenderSetting(223),
                        b2BCPAReceiverSetting(224),
                        oAuthSupportedClient(225),
                        oAuthSupportedClientGroup(226),
                        sSLSNIServerProfile(227),
                        xC10Grid(235),
                        runtimeSettings(246),
                        sQLRuntimeSettings(247),
                        webApplicationGateway(248),
                        interopService(249),
                        oDRConnectorGroup(250),
                        oDR(251),
                        sSLClientProfile(253),
                        sSLServerProfile(254),
                        sSLSNIMapping(256),
                        webTokenService(266),
                        messageContentFilters(267),
                        mCFBase(268),
                        mCFHttpHeader(269),
                        mCFXPath(270),
                        mCFHttpURL(271),
                        mCFHttpMethod(272),
                        iMSCalloutSourceProtocolHandler(273),
                        pattern(274),
                        mCFCustomRule(275),
                        aS2ProxySourceProtocolHandler(277),
                        luna(278),
                        lunaPartition(279),
                        configSequence(280),
                        lunaHAGroup(285),
                        lunaHASettings(286),
                        wAXHNProxy(300),
                        hNApplication(301),
                        cloudGatewayService(302),
                        cloudConnectorService(303),
                        jSONSettings(308),
                        iPMulticast(309),
                        deploymentPolicyParametersBinding(310),
                        lDAPConnectionPool(311),
                        mPGWErrorHandlingPolicy(312),
                        mPGWErrorAction(313),
                        language(314),
                        domainAvailability(315),
                        generatedPolicy(316),
                        passwordMap(320),
                        aAAJWTValidator(321),
                        aAAJWTGenerator(322),
                        linkAggregation(333),
                        cookieAttributePolicy(334),
                        iSAMReverseProxy(335),
                        iSAMReverseProxyJunction(336),
                        iSAMRuntime(337),
                        passwordAlias(338),
                        auditLog(340),
                        jWERecipient(345),
                        jOSESignatureIdentifier(346),
                        jWSSignature(347),
                        jWEHeader(348),
                        jOSERecipientIdentifier(349),
                        secureGatewayClient(350),
                        cacheGrid(351),
                        wXSGrid(352),
                        domainSettings(353),
                        mQAUI(354),
                        gWScriptSettings(358),
                        aPICollection(359),
                        aPIGateway(360),
                        aPIDefinition(361),
                        aPIPath(362),
                        aPIOperation(363),
                        aPIPlan(364),
                        aPISecurityDefinition(365),
                        aPISecurityAPIKey(366),
                        aPISecurityOAuth(368),
                        aPISecurityRequirement(369),
                        controlList(370),
                        aPILDAPRegistry(371),
                        aPIRule(372),
                        aPISecurityOAuthReq(373),
                        gWSRemoteDebug(374),
                        mQAUIMFT(375),
                        assemblyActionUserSecurity(376),
                        aPISecurityBasicAuth(377),
                        aPISchema(378),
                        aPIUserRegistry(379),
                        aPIAuthURLRegistry(380),
                        assemblyActionClientSecurity(381),
                        restMgmtInterface(400),
                        secureBackupMode(402),
                        aPIConnectGatewayService(403),
                        standaloneStandbyControlInterface(450),
                        standaloneStandbyControl(451),
                        tenant(452),
                        socialLoginPolicy(455),
                        eBMS3SourceProtocolHandler(456),
                        dFDLSettings(460),
                        parseSettings(461),
                        accessProfile(462),
                        iLMTScanner(500),
                        quotaEnforcementServer(504),
                        sSHServerProfile(505),
                        quotaEnforcementMatchClass(506),
                        quotaEnforcementGroupClass(507),
                        quotaEnforcementAlgorithm(508),
                        quotaEnforcementSchedule(509),
                        sSHDomainClientProfile(510),
                        quotaEnforcementPolicyGroup(511),
                        quotaEnforcementPolicyBase(512),
                        quotaEnforcementAction(513),
                        quotaEnforcementPolicy(514),
                        gatewayPeering(526),
                        stylePolicyActionBase(600),
                        assemblyActionBase(601),
                        assemblyAction(602),
                        assemblyLogic(603),
                        aPIExecute(605),
                        aPIResult(607),
                        assemblyLogicSwitch(609),
                        assembly(610),
                        assemblyActionInvoke(611),
                        assemblyActionSetVar(612),
                        assemblyActionThrow(613),
                        aPIRouting(614),
                        aPISecurity(615),
                        aPIRateLimit(616),
                        assemblyActionXml2Json(617),
                        aPIAction(618),
                        assemblyActionXSLT(619),
                        assemblyActionGatewayScript(620),
                        aPIClientIdentification(621),
                        assemblyActionMap(622),
                        assemblyActionJWTValidate(623),
                        assemblyActionParse(624),
                        aPICORS(625),
                        operationRateLimit(626),
                        analyticsEndpoint(627),
                        assemblyActionJWTGenerate(628),
                        assemblyActionJson2Xml(629),
                        assemblyActionOAuth(630),
                        oAuthProviderSettings(640),
                        aPISecurityTokenManager(641),
                        assemblyActionValidate(642),
                        aPIDebugProbe(643),
                        aPIApplicationType(644),
                        assemblyFunction(645),
                        assemblyActionFunctionCall(646),
                        gatewayPeeringManager(648),
                        assemblyActionLog(649),
                        assemblyActionRateLimit(650),
                        assemblyActionRedact(651),
                        productInsights(850)
                }
    MAX-ACCESS  read-only
    STATUS      current
    DESCRIPTION "No description yet."

    ::= { dpStatusObjectStatusEntry 1 }

dpStatusObjectStatusOpState OBJECT-TYPE
    SYNTAX      INTEGER { 
                        up(1),
                        down(2)
                }
    MAX-ACCESS  read-only
    STATUS      current
    DESCRIPTION "No description yet."

    ::= { dpStatusObjectStatusEntry 2 }

dpStatusObjectStatusAdminState OBJECT-TYPE
    SYNTAX      INTEGER { 
                        enabled(1),
                        disabled(2)
                }
    MAX-ACCESS  read-only
    STATUS      current
    DESCRIPTION "No description yet."

    ::= { dpStatusObjectStatusEntry 3 }

dpStatusObjectStatusName OBJECT-TYPE
    SYNTAX      DisplayString
    MAX-ACCESS  read-only
    STATUS      current
    DESCRIPTION "No description yet."

    ::= { dpStatusObjectStatusEntry 4 }

dpStatusObjectStatusEventCode OBJECT-TYPE
    SYNTAX      DisplayString
    MAX-ACCESS  read-only
    STATUS      current
    DESCRIPTION "No description yet."

    ::= { dpStatusObjectStatusEntry 5 }

dpStatusObjectStatusErrorCode OBJECT-TYPE
    SYNTAX      DisplayString
    MAX-ACCESS  read-only
    STATUS      current
    DESCRIPTION "No description yet."

    ::= { dpStatusObjectStatusEntry 6 }

dpStatusObjectStatusConfigState OBJECT-TYPE
    SYNTAX      INTEGER { 
                        invalid(1),
                        saved(2),
                        new(3),
                        modified(4),
                        deleted(5),
                        external(6)
                }
    MAX-ACCESS  read-only
    STATUS      current
    DESCRIPTION "No description yet."

    ::= { dpStatusObjectStatusEntry 7 }

--

dpStatusLicenseStatusTable OBJECT-TYPE
    SYNTAX      SEQUENCE OF DPStatusLicenseStatusEntry
    MAX-ACCESS  not-accessible
    STATUS      current
    DESCRIPTION
        "This provider displays information about available and enabled features.
        Some features are available because of the type of appliance, but some
        must be purchased to be enabled."

    ::= { dpStatus 81 }

dpStatusLicenseStatusEntry OBJECT-TYPE
    SYNTAX      DPStatusLicenseStatusEntry
    MAX-ACCESS  not-accessible
    STATUS      current
    DESCRIPTION "Table row."
    INDEX { dpStatusLicenseStatusFeature }

    ::= { dpStatusLicenseStatusTable 1 }

DPStatusLicenseStatusEntry ::= SEQUENCE {
    dpStatusLicenseStatusFeature    INTEGER,
    dpStatusLicenseStatusEnabled    INTEGER,
    dpStatusLicenseStatusAvailable    INTEGER
}

dpStatusLicenseStatusFeature OBJECT-TYPE
    SYNTAX      INTEGER { 
                        mQ(1),
                        tAM(2),
                        dataGlue(3),
                        jAXP-API(4),
                        hSM(5),
                        pKCS7-SMIME(6),
                        reserved(7),
                        sQL-ODBC(8),
                        tibco-EMS(9),
                        webSphere-JMS(10),
                        xG4(11),
                        compact-Flash(12),
                        raidVolume(13),
                        iSCSI(14),
                        locateLED(15),
                        appOpt(16),
                        tibco-RV(17),
                        fibreChannel(18),
                        iPMI(19),
                        dCO(20),
                        raidVolumeMpt(21),
                        raidVolumeSr(22),
                        intrusionDetection(23),
                        iPMI-LAN(24),
                        zBX(25),
                        iPv6(26),
                        realHardware(27),
                        virtual(28),
                        realRaid(29),
                        reserved2(30),
                        language(31),
                        sNMPEngineIDOptions(32),
                        dCO-Oracle(33),
                        raidVolumeMpt2Sas(34),
                        b2B(35),
                        iMS(36),
                        iSAMProxy(37),
                        dFDL(38),
                        iDG(39),
                        iMQA(40),
                        raidFSModify(41),
                        tenant(42)
                }
    MAX-ACCESS  read-only
    STATUS      current
    DESCRIPTION
        "The name of the feature."

    ::= { dpStatusLicenseStatusEntry 1 }

dpStatusLicenseStatusEnabled OBJECT-TYPE
    SYNTAX      INTEGER { 
                        yes(0),
                        no(1),
                        eRROR(2)
                }
    MAX-ACCESS  read-only
    STATUS      current
    DESCRIPTION
        "The enabled status of this feature."

    ::= { dpStatusLicenseStatusEntry 2 }

dpStatusLicenseStatusAvailable OBJECT-TYPE
    SYNTAX      INTEGER { 
                        yes(0),
                        no(1)
                }
    MAX-ACCESS  read-only
    STATUS      current
    DESCRIPTION
        "Even though it is licensed, the availability of this feature. A feature is
        unavailable when the installed firmware image does not include the code to
        support the feature."

    ::= { dpStatusLicenseStatusEntry 3 }

--

dpStatusMQStatusTable OBJECT-TYPE
    SYNTAX      SEQUENCE OF DPStatusMQStatusEntry
    MAX-ACCESS  not-accessible
    STATUS      obsolete
    DESCRIPTION
        "Status of the IBM MQ service.
        Note: this is obsolete as of release 5.0.0"

    ::= { dpStatus 82 }

dpStatusMQStatusEntry OBJECT-TYPE
    SYNTAX      DPStatusMQStatusEntry
    MAX-ACCESS  not-accessible
    STATUS      obsolete
    DESCRIPTION "Table row."
    INDEX { dpStatusMQStatusServiceType, IMPLIED dpStatusMQStatusServiceName }

    ::= { dpStatusMQStatusTable 1 }

DPStatusMQStatusEntry ::= SEQUENCE {
    dpStatusMQStatusServiceType    INTEGER,
    dpStatusMQStatusServiceName    DisplayString,
    dpStatusMQStatusReceivedMessages    Counter32,
    dpStatusMQStatusSentMessages    Counter32,
    dpStatusMQStatusReceiveFaults    Counter32,
    dpStatusMQStatusSendFaults    Counter32,
    dpStatusMQStatusRequestLatency    Unsigned32,
    dpStatusMQStatusResponseLatency    Unsigned32,
    dpStatusMQStatusRoundTripLatency    Unsigned32
}

dpStatusMQStatusServiceType OBJECT-TYPE
    SYNTAX      INTEGER { 
                        mQgateway(1),
                        mQhost(2),
                        mQproxy(3)
                }
    MAX-ACCESS  read-only
    STATUS      obsolete
    DESCRIPTION
        "The type of IBM MQ service."

    ::= { dpStatusMQStatusEntry 1 }

dpStatusMQStatusServiceName OBJECT-TYPE
    SYNTAX      DisplayString
    MAX-ACCESS  read-only
    STATUS      obsolete
    DESCRIPTION
        "The type of IBM MQ service."

    ::= { dpStatusMQStatusEntry 2 }

dpStatusMQStatusReceivedMessages OBJECT-TYPE
    SYNTAX      Counter32
    MAX-ACCESS  read-only
    STATUS      obsolete
    DESCRIPTION
        "Messages received by this IBM MQ service."

    ::= { dpStatusMQStatusEntry 3 }

dpStatusMQStatusSentMessages OBJECT-TYPE
    SYNTAX      Counter32
    MAX-ACCESS  read-only
    STATUS      obsolete
    DESCRIPTION
        "Messages sent by this IBM MQ service."

    ::= { dpStatusMQStatusEntry 4 }

dpStatusMQStatusReceiveFaults OBJECT-TYPE
    SYNTAX      Counter32
    MAX-ACCESS  read-only
    STATUS      obsolete
    DESCRIPTION
        "Messages received with faults by this IBM MQ service."

    ::= { dpStatusMQStatusEntry 5 }

dpStatusMQStatusSendFaults OBJECT-TYPE
    SYNTAX      Counter32
    MAX-ACCESS  read-only
    STATUS      obsolete
    DESCRIPTION
        "Messages sent with faults by this IBM MQ service."

    ::= { dpStatusMQStatusEntry 6 }

dpStatusMQStatusRequestLatency OBJECT-TYPE
    SYNTAX      Unsigned32
    UNITS       "sec"
    MAX-ACCESS  read-only
    STATUS      obsolete
    DESCRIPTION
        "The time taken for requests to reach the IBM MQ service form the DataPower
        appliance."

    ::= { dpStatusMQStatusEntry 7 }

dpStatusMQStatusResponseLatency OBJECT-TYPE
    SYNTAX      Unsigned32
    UNITS       "sec"
    MAX-ACCESS  read-only
    STATUS      obsolete
    DESCRIPTION
        "The time taken for responses to reach the DataPower appliance form the IBM
        MQ service."

    ::= { dpStatusMQStatusEntry 8 }

dpStatusMQStatusRoundTripLatency OBJECT-TYPE
    SYNTAX      Unsigned32
    UNITS       "sec"
    MAX-ACCESS  read-only
    STATUS      obsolete
    DESCRIPTION
        "The round-trip time for communications with the IBM MQ service."

    ::= { dpStatusMQStatusEntry 9 }

--

dpStatusDNSNameServerStatusTable OBJECT-TYPE
    SYNTAX      SEQUENCE OF DPStatusDNSNameServerStatusEntry
    MAX-ACCESS  not-accessible
    STATUS      obsolete
    DESCRIPTION "Note: this is obsoleted and is replaced by dpStatusDNSNameServerStatus2 as of release 3.8.1"

    ::= { dpStatus 83 }

dpStatusDNSNameServerStatusEntry OBJECT-TYPE
    SYNTAX      DPStatusDNSNameServerStatusEntry
    MAX-ACCESS  not-accessible
    STATUS      obsolete
    DESCRIPTION "Table row."
    INDEX { dpStatusDNSNameServerStatusIPAddress }

    ::= { dpStatusDNSNameServerStatusTable 1 }

DPStatusDNSNameServerStatusEntry ::= SEQUENCE {
    dpStatusDNSNameServerStatusIPAddress    IpAddress,
    dpStatusDNSNameServerStatusUDPPort    Unsigned32,
    dpStatusDNSNameServerStatusTCPPort    Unsigned32,
    dpStatusDNSNameServerStatusMaxRetries    Unsigned32
}

dpStatusDNSNameServerStatusIPAddress OBJECT-TYPE
    SYNTAX      IpAddress
    MAX-ACCESS  read-only
    STATUS      obsolete
    DESCRIPTION
        "The numeric IP address for any DNS server that is configured for use on
        this appliance."

    ::= { dpStatusDNSNameServerStatusEntry 1 }

dpStatusDNSNameServerStatusUDPPort OBJECT-TYPE
    SYNTAX      Unsigned32 (0..65535)
    MAX-ACCESS  read-only
    STATUS      obsolete
    DESCRIPTION
        "The UDP port number of the DNS server. (The default DNS UDP port is 53.)
        When the load balancing algorithm is first alive, this value is ignored."

    ::= { dpStatusDNSNameServerStatusEntry 2 }

dpStatusDNSNameServerStatusTCPPort OBJECT-TYPE
    SYNTAX      Unsigned32 (0..65535)
    MAX-ACCESS  read-only
    STATUS      obsolete
    DESCRIPTION
        "The TCP port number of the DNS server. (The default DNS TCP port is also
        53.) When the load balancing algorithm is first alive, this value is
        ignored."

    ::= { dpStatusDNSNameServerStatusEntry 3 }

dpStatusDNSNameServerStatusMaxRetries OBJECT-TYPE
    SYNTAX      Unsigned32
    MAX-ACCESS  read-only
    STATUS      obsolete
    DESCRIPTION
        "The maximum number of lookup requests that are sent to a given DNS name
        server before a connection failure is reported. However, if the load
        balancing algorithm is first alive, the individual host uses the top-level
        retry setting from DNS settings."

    ::= { dpStatusDNSNameServerStatusEntry 4 }

--

dpStatusDNSSearchDomainStatusTable OBJECT-TYPE
    SYNTAX      SEQUENCE OF DPStatusDNSSearchDomainStatusEntry
    MAX-ACCESS  not-accessible
    STATUS      current
    DESCRIPTION "Table."

    ::= { dpStatus 84 }

dpStatusDNSSearchDomainStatusEntry OBJECT-TYPE
    SYNTAX      DPStatusDNSSearchDomainStatusEntry
    MAX-ACCESS  not-accessible
    STATUS      current
    DESCRIPTION "Table row."
    INDEX { IMPLIED dpStatusDNSSearchDomainStatusSearchDomain }

    ::= { dpStatusDNSSearchDomainStatusTable 1 }

DPStatusDNSSearchDomainStatusEntry ::= SEQUENCE {
    dpStatusDNSSearchDomainStatusSearchDomain    DisplayString
}

dpStatusDNSSearchDomainStatusSearchDomain OBJECT-TYPE
    SYNTAX      DisplayString
    MAX-ACCESS  read-only
    STATUS      current
    DESCRIPTION
        "A list of configured and acquired domain names. The list is used if a
        partial host name is submitted to the DNS service. Each domain name is
        appended to the partial host name, and a DNS host name lookup is attempted
        for the host.domain pair until a name lookup succeeds or until the list is
        exhausted."

    ::= { dpStatusDNSSearchDomainStatusEntry 1 }

--

dpStatusDNSStaticHostStatusTable OBJECT-TYPE
    SYNTAX      SEQUENCE OF DPStatusDNSStaticHostStatusEntry
    MAX-ACCESS  not-accessible
    STATUS      current
    DESCRIPTION
        "A list of configured static hosts."

    ::= { dpStatus 85 }

dpStatusDNSStaticHostStatusEntry OBJECT-TYPE
    SYNTAX      DPStatusDNSStaticHostStatusEntry
    MAX-ACCESS  not-accessible
    STATUS      current
    DESCRIPTION "Table row."
    INDEX { IMPLIED dpStatusDNSStaticHostStatusHostname }

    ::= { dpStatusDNSStaticHostStatusTable 1 }

DPStatusDNSStaticHostStatusEntry ::= SEQUENCE {
    dpStatusDNSStaticHostStatusHostname    DisplayString,
    dpStatusDNSStaticHostStatusIPAddress    IpAddress,
    dpStatusDNSStaticHostStatusType    INTEGER
}

dpStatusDNSStaticHostStatusHostname OBJECT-TYPE
    SYNTAX      DisplayString
    MAX-ACCESS  read-only
    STATUS      current
    DESCRIPTION
        "The host name that represents a DNS static host or a host alias."

    ::= { dpStatusDNSStaticHostStatusEntry 1 }

dpStatusDNSStaticHostStatusIPAddress OBJECT-TYPE
    SYNTAX      IpAddress
    MAX-ACCESS  read-only
    STATUS      current
    DESCRIPTION
        "The IP address that corresponds to the given host name."

    ::= { dpStatusDNSStaticHostStatusEntry 2 }

dpStatusDNSStaticHostStatusType OBJECT-TYPE
    SYNTAX      INTEGER { 
                        static(1),
                        alias(2)
                }
    MAX-ACCESS  read-only
    STATUS      current
    DESCRIPTION
        "The type of configured host entry."

    ::= { dpStatusDNSStaticHostStatusEntry 3 }

dpStatusNTPRefreshStatus OBJECT IDENTIFIER ::= { dpStatus 86 }

dpStatusNTPRefreshStatusLastRefreshIndex OBJECT-TYPE
    SYNTAX      IpAddress
    MAX-ACCESS  read-only
    STATUS      current
    DESCRIPTION
        "IP address of the last server contacted as an NTP server."

    ::= { dpStatusNTPRefreshStatus 1 }

dpStatusNTPRefreshStatusLastRefreshResult OBJECT-TYPE
    SYNTAX      DisplayString
    MAX-ACCESS  read-only
    STATUS      current
    DESCRIPTION
        "Result of the last server contact."

    ::= { dpStatusNTPRefreshStatus 2 }

dpStatusNTPRefreshStatusLastRefreshTime OBJECT-TYPE
    SYNTAX      TimeStamp
    MAX-ACCESS  read-only
    STATUS      current
    DESCRIPTION
        "Time after the last refresh."

    ::= { dpStatusNTPRefreshStatus 3 }

dpStatusNTPRefreshStatusTime OBJECT-TYPE
    SYNTAX      TimeStamp
    MAX-ACCESS  read-only
    STATUS      current
    DESCRIPTION
        "The current local time. This time is obtained from the timezone settings
        established on the Time Settings object and with the date and time
        settings set on the System Control page."

    ::= { dpStatusNTPRefreshStatus 4 }

--

dpStatusHSMKeyStatusTable OBJECT-TYPE
    SYNTAX      SEQUENCE OF DPStatusHSMKeyStatusEntry
    MAX-ACCESS  not-accessible
    STATUS      current
    DESCRIPTION
        "List of keys in the HSM."

    ::= { dpStatus 87 }

dpStatusHSMKeyStatusEntry OBJECT-TYPE
    SYNTAX      DPStatusHSMKeyStatusEntry
    MAX-ACCESS  not-accessible
    STATUS      current
    DESCRIPTION "Table row."
    INDEX { dpStatusHSMKeyStatusKeyHandle, dpStatusHSMKeyStatusKeyType }

    ::= { dpStatusHSMKeyStatusTable 1 }

DPStatusHSMKeyStatusEntry ::= SEQUENCE {
    dpStatusHSMKeyStatusKeyHandle    DisplayString,
    dpStatusHSMKeyStatusKeyType    INTEGER,
    dpStatusHSMKeyStatusKeyLabel    DisplayString,
    dpStatusHSMKeyStatusBitLength    Unsigned32,
    dpStatusHSMKeyStatusExportable    INTEGER
}

dpStatusHSMKeyStatusKeyHandle OBJECT-TYPE
    SYNTAX      DisplayString
    MAX-ACCESS  read-only
    STATUS      current
    DESCRIPTION
        "Handle provided for this key."

    ::= { dpStatusHSMKeyStatusEntry 1 }

dpStatusHSMKeyStatusKeyType OBJECT-TYPE
    SYNTAX      INTEGER { 
                        private(1),
                        public(2),
                        secret(3)
                }
    MAX-ACCESS  read-only
    STATUS      current
    DESCRIPTION
        "Type of key."

    ::= { dpStatusHSMKeyStatusEntry 2 }

dpStatusHSMKeyStatusKeyLabel OBJECT-TYPE
    SYNTAX      DisplayString
    MAX-ACCESS  read-only
    STATUS      current
    DESCRIPTION
        "URL of the key."

    ::= { dpStatusHSMKeyStatusEntry 3 }

dpStatusHSMKeyStatusBitLength OBJECT-TYPE
    SYNTAX      Unsigned32
    MAX-ACCESS  read-only
    STATUS      current
    DESCRIPTION
        "Bit length used by this key."

    ::= { dpStatusHSMKeyStatusEntry 4 }

dpStatusHSMKeyStatusExportable OBJECT-TYPE
    SYNTAX      INTEGER { 
                        on(1),
                        off(2)
                }
    MAX-ACCESS  read-only
    STATUS      current
    DESCRIPTION
        "Identifies whether this key can be exported."

    ::= { dpStatusHSMKeyStatusEntry 5 }

--

dpStatusMQQMstatusTable OBJECT-TYPE
    SYNTAX      SEQUENCE OF DPStatusMQQMstatusEntry
    MAX-ACCESS  not-accessible
    STATUS      current
    DESCRIPTION
        "IBM MQ queue manager status."

    ::= { dpStatus 88 }

dpStatusMQQMstatusEntry OBJECT-TYPE
    SYNTAX      DPStatusMQQMstatusEntry
    MAX-ACCESS  not-accessible
    STATUS      current
    DESCRIPTION "Table row."
    INDEX { IMPLIED dpConfigMQQMIndex }

    ::= { dpStatusMQQMstatusTable 1 }

DPStatusMQQMstatusEntry ::= SEQUENCE {
    dpStatusMQQMstatusQueueManager    DisplayString,
    dpStatusMQQMstatusReceivedMessages    Unsigned32,
    dpStatusMQQMstatusSentMessages    Unsigned32,
    dpStatusMQQMstatusReceiveFaults    Unsigned32,
    dpStatusMQQMstatusSendFaults    Unsigned32
}

dpStatusMQQMstatusQueueManager OBJECT-TYPE
    SYNTAX      DisplayString
    MAX-ACCESS  read-only
    STATUS      current
    DESCRIPTION
        "IBM MQ queue manager name."

    ::= { dpStatusMQQMstatusEntry 1 }

dpStatusMQQMstatusReceivedMessages OBJECT-TYPE
    SYNTAX      Unsigned32
    MAX-ACCESS  read-only
    STATUS      current
    DESCRIPTION
        "Number of messages received by this IBM MQ queue manager."

    ::= { dpStatusMQQMstatusEntry 2 }

dpStatusMQQMstatusSentMessages OBJECT-TYPE
    SYNTAX      Unsigned32
    MAX-ACCESS  read-only
    STATUS      current
    DESCRIPTION
        "Number of messages sent by this IBM MQ queue manager."

    ::= { dpStatusMQQMstatusEntry 3 }

dpStatusMQQMstatusReceiveFaults OBJECT-TYPE
    SYNTAX      Unsigned32
    MAX-ACCESS  read-only
    STATUS      current
    DESCRIPTION
        "Number of messages received with faults."

    ::= { dpStatusMQQMstatusEntry 4 }

dpStatusMQQMstatusSendFaults OBJECT-TYPE
    SYNTAX      Unsigned32
    MAX-ACCESS  read-only
    STATUS      current
    DESCRIPTION
        "Number of messages sent with faults."

    ::= { dpStatusMQQMstatusEntry 5 }

--

dpStatusWSWSDLStatusTable OBJECT-TYPE
    SYNTAX      SEQUENCE OF DPStatusWSWSDLStatusEntry
    MAX-ACCESS  not-accessible
    STATUS      obsolete
    DESCRIPTION "Note: this is obsoleted and is replaced by dpStatusWSWSDLStatusSimpleIndex as of release 3.5.1"

    ::= { dpStatus 89 }

dpStatusWSWSDLStatusEntry OBJECT-TYPE
    SYNTAX      DPStatusWSWSDLStatusEntry
    MAX-ACCESS  not-accessible
    STATUS      obsolete
    DESCRIPTION "Table row."
    INDEX { dpConfigWSGatewayIndex, IMPLIED dpStatusWSWSDLStatusWSDLSourceLocation }

    ::= { dpStatusWSWSDLStatusTable 1 }

DPStatusWSWSDLStatusEntry ::= SEQUENCE {
    dpStatusWSWSDLStatusWSGateway    DisplayString,
    dpStatusWSWSDLStatusWSDLSourceLocation    DisplayString,
    dpStatusWSWSDLStatusStatus    INTEGER,
    dpStatusWSWSDLStatusRefreshInterval    DPTimeIntervalSeconds,
    dpStatusWSWSDLStatusLastRefresh    TimeStamp,
    dpStatusWSWSDLStatusLog    DisplayString
}

dpStatusWSWSDLStatusWSGateway OBJECT-TYPE
    SYNTAX      DisplayString
    MAX-ACCESS  read-only
    STATUS      obsolete
    DESCRIPTION "No description yet."

    ::= { dpStatusWSWSDLStatusEntry 1 }

dpStatusWSWSDLStatusWSDLSourceLocation OBJECT-TYPE
    SYNTAX      DisplayString
    MAX-ACCESS  read-only
    STATUS      obsolete
    DESCRIPTION "No description yet."

    ::= { dpStatusWSWSDLStatusEntry 2 }

dpStatusWSWSDLStatusStatus OBJECT-TYPE
    SYNTAX      INTEGER { 
                        processing(1),
                        okay(2),
                        warning(3),
                        error(4)
                }
    MAX-ACCESS  read-only
    STATUS      obsolete
    DESCRIPTION "No description yet."

    ::= { dpStatusWSWSDLStatusEntry 3 }

dpStatusWSWSDLStatusRefreshInterval OBJECT-TYPE
    SYNTAX      DPTimeIntervalSeconds
    UNITS       "sec"
    MAX-ACCESS  read-only
    STATUS      obsolete
    DESCRIPTION "No description yet."

    ::= { dpStatusWSWSDLStatusEntry 4 }

dpStatusWSWSDLStatusLastRefresh OBJECT-TYPE
    SYNTAX      TimeStamp
    MAX-ACCESS  read-only
    STATUS      obsolete
    DESCRIPTION "No description yet."

    ::= { dpStatusWSWSDLStatusEntry 5 }

dpStatusWSWSDLStatusLog OBJECT-TYPE
    SYNTAX      DisplayString
    MAX-ACCESS  read-only
    STATUS      obsolete
    DESCRIPTION "No description yet."

    ::= { dpStatusWSWSDLStatusEntry 6 }

--

dpStatusWSOperationsStatusTable OBJECT-TYPE
    SYNTAX      SEQUENCE OF DPStatusWSOperationsStatusEntry
    MAX-ACCESS  not-accessible
    STATUS      obsolete
    DESCRIPTION "Note: this is obsoleted and is replaced by dpStatusWSOperationsStatusSimpleIndex as of release
    3.6.1"

    ::= { dpStatus 90 }

dpStatusWSOperationsStatusEntry OBJECT-TYPE
    SYNTAX      DPStatusWSOperationsStatusEntry
    MAX-ACCESS  not-accessible
    STATUS      obsolete
    DESCRIPTION "Table row."
    INDEX { dpConfigWSGatewayIndex, dpStatusWSOperationsStatusInterface, dpStatusWSOperationsStatusPort, dpStatusWSOperationsStatusURL, dpStatusWSOperationsStatusSOAPAction, IMPLIED dpStatusWSOperationsStatusSOAPBody }

    ::= { dpStatusWSOperationsStatusTable 1 }

DPStatusWSOperationsStatusEntry ::= SEQUENCE {
    dpStatusWSOperationsStatusWSGateway    DisplayString,
    dpStatusWSOperationsStatusInterface    IpAddress,
    dpStatusWSOperationsStatusPort    Unsigned32,
    dpStatusWSOperationsStatusURL    DisplayString,
    dpStatusWSOperationsStatusSOAPAction    DisplayString,
    dpStatusWSOperationsStatusSOAPBody    DisplayString,
    dpStatusWSOperationsStatusStatus    INTEGER,
    dpStatusWSOperationsStatusRemoteURL    DisplayString
}

dpStatusWSOperationsStatusWSGateway OBJECT-TYPE
    SYNTAX      DisplayString
    MAX-ACCESS  read-only
    STATUS      obsolete
    DESCRIPTION "No description yet."

    ::= { dpStatusWSOperationsStatusEntry 1 }

dpStatusWSOperationsStatusInterface OBJECT-TYPE
    SYNTAX      IpAddress
    MAX-ACCESS  read-only
    STATUS      obsolete
    DESCRIPTION "No description yet."

    ::= { dpStatusWSOperationsStatusEntry 2 }

dpStatusWSOperationsStatusPort OBJECT-TYPE
    SYNTAX      Unsigned32 (0..65535)
    MAX-ACCESS  read-only
    STATUS      obsolete
    DESCRIPTION "No description yet."

    ::= { dpStatusWSOperationsStatusEntry 3 }

dpStatusWSOperationsStatusURL OBJECT-TYPE
    SYNTAX      DisplayString
    MAX-ACCESS  read-only
    STATUS      obsolete
    DESCRIPTION "No description yet."

    ::= { dpStatusWSOperationsStatusEntry 4 }

dpStatusWSOperationsStatusSOAPAction OBJECT-TYPE
    SYNTAX      DisplayString
    MAX-ACCESS  read-only
    STATUS      obsolete
    DESCRIPTION "No description yet."

    ::= { dpStatusWSOperationsStatusEntry 5 }

dpStatusWSOperationsStatusSOAPBody OBJECT-TYPE
    SYNTAX      DisplayString
    MAX-ACCESS  read-only
    STATUS      obsolete
    DESCRIPTION "No description yet."

    ::= { dpStatusWSOperationsStatusEntry 6 }

dpStatusWSOperationsStatusStatus OBJECT-TYPE
    SYNTAX      INTEGER { 
                        registered(1),
                        unregistered(2),
                        registrationError(3)
                }
    MAX-ACCESS  read-only
    STATUS      obsolete
    DESCRIPTION "No description yet."

    ::= { dpStatusWSOperationsStatusEntry 7 }

dpStatusWSOperationsStatusRemoteURL OBJECT-TYPE
    SYNTAX      DisplayString
    MAX-ACCESS  read-only
    STATUS      obsolete
    DESCRIPTION "No description yet."

    ::= { dpStatusWSOperationsStatusEntry 8 }

dpStatusWSMAgentStatus OBJECT IDENTIFIER ::= { dpStatus 91 }

dpStatusWSMAgentStatusSpoolerCount OBJECT-TYPE
    SYNTAX      Unsigned32
    MAX-ACCESS  read-only
    STATUS      current
    DESCRIPTION
        "The total number of active subscribers for this Application Domain."

    ::= { dpStatusWSMAgentStatus 1 }

dpStatusWSMAgentStatusPolledSpoolers OBJECT-TYPE
    SYNTAX      Unsigned32
    MAX-ACCESS  read-only
    STATUS      current
    DESCRIPTION
        "The total number of Push mode subscribers for this Application Domain."

    ::= { dpStatusWSMAgentStatus 2 }

dpStatusWSMAgentStatusRecordsSeen OBJECT-TYPE
    SYNTAX      Unsigned32
    MAX-ACCESS  read-only
    STATUS      current
    DESCRIPTION
        "The total number of messages successfully enqueued since the WSM Agent was
        restarted."

    ::= { dpStatusWSMAgentStatus 3 }

dpStatusWSMAgentStatusRecordsLost OBJECT-TYPE
    SYNTAX      Unsigned32
    MAX-ACCESS  read-only
    STATUS      current
    DESCRIPTION
        "The total number of messages dropped due to resource constraints since the
        WSM Agent was restarted."

    ::= { dpStatusWSMAgentStatus 4 }

dpStatusWSMAgentStatusPendingRecords OBJECT-TYPE
    SYNTAX      Unsigned32
    MAX-ACCESS  read-only
    STATUS      current
    DESCRIPTION
        "The total number of messages currently in the queue for transactions which
        have not completed. This number is normally very low, and is approximately
        a product of the current transaction rate and external latency."

    ::= { dpStatusWSMAgentStatus 5 }

dpStatusWSMAgentStatusCompleteRecords OBJECT-TYPE
    SYNTAX      Unsigned32
    MAX-ACCESS  read-only
    STATUS      current
    DESCRIPTION
        "The total number of messages currently in the queue for completed
        transactions. This number is approximately a product of the current
        transaction rate and subscriber polling interval."

    ::= { dpStatusWSMAgentStatus 6 }

dpStatusWSMAgentStatusMemoryUsedKB OBJECT-TYPE
    SYNTAX      Unsigned32
    UNITS       "kbytes"
    MAX-ACCESS  read-only
    STATUS      current
    DESCRIPTION
        "The amount of memory (in kilobytes) used by this Agent for transaction
        records and buffered messages. This number is compared to the configured
        Max Memory property of the Agent to limit resource usage."

    ::= { dpStatusWSMAgentStatus 7 }

dpStatusWSMAgentStatusMediationEnforcementMetrics OBJECT-TYPE
    SYNTAX      INTEGER { 
                        on(1),
                        off(2)
                }
    MAX-ACCESS  read-only
    STATUS      current
    DESCRIPTION
        "Mediation enforcement metrics"

    ::= { dpStatusWSMAgentStatus 8 }

--

dpStatusWSMAgentSpoolersTable OBJECT-TYPE
    SYNTAX      SEQUENCE OF DPStatusWSMAgentSpoolersEntry
    MAX-ACCESS  not-accessible
    STATUS      current
    DESCRIPTION "Table."

    ::= { dpStatus 92 }

dpStatusWSMAgentSpoolersEntry OBJECT-TYPE
    SYNTAX      DPStatusWSMAgentSpoolersEntry
    MAX-ACCESS  not-accessible
    STATUS      current
    DESCRIPTION "Table row."
    INDEX { dpStatusWSMAgentSpoolersIndex }

    ::= { dpStatusWSMAgentSpoolersTable 1 }

DPStatusWSMAgentSpoolersEntry ::= SEQUENCE {
    dpStatusWSMAgentSpoolersIndex    Unsigned32,
    dpStatusWSMAgentSpoolersContext    DisplayString,
    dpStatusWSMAgentSpoolersProtocol    DisplayString,
    dpStatusWSMAgentSpoolersSubProtocol    DisplayString,
    dpStatusWSMAgentSpoolersPollInterval    DPTimeIntervalSeconds,
    dpStatusWSMAgentSpoolersRecords    Unsigned32,
    dpStatusWSMAgentSpoolersLastReadIndex    Unsigned32,
    dpStatusWSMAgentSpoolersLastAckedIndex    Unsigned32,
    dpStatusWSMAgentSpoolersLastReadTime    TimeStamp,
    dpStatusWSMAgentSpoolersLastAckTime    TimeStamp
}

dpStatusWSMAgentSpoolersIndex OBJECT-TYPE
    SYNTAX      Unsigned32
    MAX-ACCESS  read-only
    STATUS      current
    DESCRIPTION
        "An identifier for this Subscriber, unique since the WSM Agent started."

    ::= { dpStatusWSMAgentSpoolersEntry 1 }

dpStatusWSMAgentSpoolersContext OBJECT-TYPE
    SYNTAX      DisplayString
    MAX-ACCESS  read-only
    STATUS      current
    DESCRIPTION
        "The identifying string provided by the Subscriber; not always meaningful
        to a human reader."

    ::= { dpStatusWSMAgentSpoolersEntry 2 }

dpStatusWSMAgentSpoolersProtocol OBJECT-TYPE
    SYNTAX      DisplayString
    MAX-ACCESS  read-only
    STATUS      current
    DESCRIPTION
        "Identifies which protocol the Subscriber is using."

    ::= { dpStatusWSMAgentSpoolersEntry 3 }

dpStatusWSMAgentSpoolersSubProtocol OBJECT-TYPE
    SYNTAX      DisplayString
    MAX-ACCESS  read-only
    STATUS      current
    DESCRIPTION
        "Identifies which variant protocol the Subscriber is using."

    ::= { dpStatusWSMAgentSpoolersEntry 4 }

dpStatusWSMAgentSpoolersPollInterval OBJECT-TYPE
    SYNTAX      DPTimeIntervalSeconds
    UNITS       "ms"
    MAX-ACCESS  read-only
    STATUS      current
    DESCRIPTION
        "For Push mode Subscribers, the maximum interval between notifications."

    ::= { dpStatusWSMAgentSpoolersEntry 5 }

dpStatusWSMAgentSpoolersRecords OBJECT-TYPE
    SYNTAX      Unsigned32
    MAX-ACCESS  read-only
    STATUS      current
    DESCRIPTION
        "Number of messages on the queue which have not yet been successfully
        acknowledged by the subscriber."

    ::= { dpStatusWSMAgentSpoolersEntry 6 }

dpStatusWSMAgentSpoolersLastReadIndex OBJECT-TYPE
    SYNTAX      Unsigned32
    MAX-ACCESS  read-only
    STATUS      current
    DESCRIPTION
        "The transaction ID of the last record read by the subscriber."

    ::= { dpStatusWSMAgentSpoolersEntry 7 }

dpStatusWSMAgentSpoolersLastAckedIndex OBJECT-TYPE
    SYNTAX      Unsigned32
    MAX-ACCESS  read-only
    STATUS      current
    DESCRIPTION
        "The transaction ID of the last record successfully acknowledged by the
        subscriber."

    ::= { dpStatusWSMAgentSpoolersEntry 8 }

dpStatusWSMAgentSpoolersLastReadTime OBJECT-TYPE
    SYNTAX      TimeStamp
    MAX-ACCESS  read-only
    STATUS      current
    DESCRIPTION
        "Timestamp of the last Read event for this subscriber."

    ::= { dpStatusWSMAgentSpoolersEntry 9 }

dpStatusWSMAgentSpoolersLastAckTime OBJECT-TYPE
    SYNTAX      TimeStamp
    MAX-ACCESS  read-only
    STATUS      current
    DESCRIPTION
        "Timestamp of the last Ack event for this subscriber."

    ::= { dpStatusWSMAgentSpoolersEntry 10 }

--

dpStatusNFSMountStatusTable OBJECT-TYPE
    SYNTAX      SEQUENCE OF DPStatusNFSMountStatusEntry
    MAX-ACCESS  not-accessible
    STATUS      current
    DESCRIPTION "Table."

    ::= { dpStatus 93 }

dpStatusNFSMountStatusEntry OBJECT-TYPE
    SYNTAX      DPStatusNFSMountStatusEntry
    MAX-ACCESS  not-accessible
    STATUS      current
    DESCRIPTION "Table row."
    INDEX { dpStatusNFSMountStatusType, IMPLIED dpStatusNFSMountStatusName }

    ::= { dpStatusNFSMountStatusTable 1 }

DPStatusNFSMountStatusEntry ::= SEQUENCE {
    dpStatusNFSMountStatusType    INTEGER,
    dpStatusNFSMountStatusName    DisplayString,
    dpStatusNFSMountStatusRemote    DisplayString,
    dpStatusNFSMountStatusState    INTEGER,
    dpStatusNFSMountStatusVersion    Unsigned32,
    dpStatusNFSMountStatusAddress    IpAddress,
    dpStatusNFSMountStatusTransport    INTEGER,
    dpStatusNFSMountStatusPort    Unsigned32,
    dpStatusNFSMountStatusFilesRead    Counter32,
    dpStatusNFSMountStatusFilesWritten    Counter32,
    dpStatusNFSMountStatusFilesOpen    Unsigned32
}

dpStatusNFSMountStatusType OBJECT-TYPE
    SYNTAX      INTEGER { 
                        staticURL(1),
                        dynamicURL(2)
                }
    MAX-ACCESS  read-only
    STATUS      current
    DESCRIPTION
        "The type of mount service this NFS mount provides."

    ::= { dpStatusNFSMountStatusEntry 1 }

dpStatusNFSMountStatusName OBJECT-TYPE
    SYNTAX      DisplayString
    MAX-ACCESS  read-only
    STATUS      current
    DESCRIPTION
        "The configuration identifier for this NFS mount."

    ::= { dpStatusNFSMountStatusEntry 2 }

dpStatusNFSMountStatusRemote OBJECT-TYPE
    SYNTAX      DisplayString
    MAX-ACCESS  read-only
    STATUS      current
    DESCRIPTION
        "The remote NFS mount point for this mount."

    ::= { dpStatusNFSMountStatusEntry 3 }

dpStatusNFSMountStatusState OBJECT-TYPE
    SYNTAX      INTEGER { 
                        new(1),
                        mounting(2),
                        up(3),
                        down(4),
                        unmounting(5),
                        unmountingForRemount(6),
                        unmounted(7),
                        defective(8)
                }
    MAX-ACCESS  read-only
    STATUS      current
    DESCRIPTION
        "The state of this NFS mount. If the state is up, Files can be opened over
        this mount."

    ::= { dpStatusNFSMountStatusEntry 4 }

dpStatusNFSMountStatusVersion OBJECT-TYPE
    SYNTAX      Unsigned32
    MAX-ACCESS  read-only
    STATUS      current
    DESCRIPTION
        "The version of the NFS protocol being used for this mount."

    ::= { dpStatusNFSMountStatusEntry 5 }

dpStatusNFSMountStatusAddress OBJECT-TYPE
    SYNTAX      IpAddress
    MAX-ACCESS  read-only
    STATUS      current
    DESCRIPTION
        "The IP address of the interface of the NFS server that NFS RPC traffic is
        being sent to, or was last sent to."

    ::= { dpStatusNFSMountStatusEntry 6 }

dpStatusNFSMountStatusTransport OBJECT-TYPE
    SYNTAX      INTEGER { 
                        tcp(1),
                        udp(2)
                }
    MAX-ACCESS  read-only
    STATUS      current
    DESCRIPTION
        "The transport protocol being used under the RPC protocol for this NFS
        mount."

    ::= { dpStatusNFSMountStatusEntry 7 }

dpStatusNFSMountStatusPort OBJECT-TYPE
    SYNTAX      Unsigned32
    MAX-ACCESS  read-only
    STATUS      current
    DESCRIPTION
        "The UDP or TCP port number that RPC data for this NFS mount is sent to."

    ::= { dpStatusNFSMountStatusEntry 8 }

dpStatusNFSMountStatusFilesRead OBJECT-TYPE
    SYNTAX      Counter32
    MAX-ACCESS  read-only
    STATUS      current
    DESCRIPTION
        "The number of files that were opened for reading over this NFS mount."

    ::= { dpStatusNFSMountStatusEntry 9 }

dpStatusNFSMountStatusFilesWritten OBJECT-TYPE
    SYNTAX      Counter32
    MAX-ACCESS  read-only
    STATUS      current
    DESCRIPTION
        "The number of files that were opened for write (create) over this NFS
        mount."

    ::= { dpStatusNFSMountStatusEntry 10 }

dpStatusNFSMountStatusFilesOpen OBJECT-TYPE
    SYNTAX      Unsigned32
    MAX-ACCESS  read-only
    STATUS      current
    DESCRIPTION
        "The number of files that are currently open for read or write (create)
        over this NFS mount."

    ::= { dpStatusNFSMountStatusEntry 11 }

dpStatusSNMPStatus OBJECT IDENTIFIER ::= { dpStatus 94 }

dpStatusSNMPStatusEngineID OBJECT-TYPE
    SYNTAX      DisplayString
    MAX-ACCESS  read-only
    STATUS      current
    DESCRIPTION
        "The engineID for the local SNMPv3 engine."

    ::= { dpStatusSNMPStatus 1 }

dpStatusSNMPStatusEngineBoots OBJECT-TYPE
    SYNTAX      Unsigned32
    MAX-ACCESS  read-only
    STATUS      current
    DESCRIPTION
        "The number of reboots for the local SNMPv3 engine."

    ::= { dpStatusSNMPStatus 2 }

--

dpStatusWebAppFwAcceptedTable OBJECT-TYPE
    SYNTAX      SEQUENCE OF DPStatusWebAppFwAcceptedEntry
    MAX-ACCESS  not-accessible
    STATUS      current
    DESCRIPTION
        "The number of approvals by the Web Application Firewall."

    ::= { dpStatus 95 }

dpStatusWebAppFwAcceptedEntry OBJECT-TYPE
    SYNTAX      DPStatusWebAppFwAcceptedEntry
    MAX-ACCESS  not-accessible
    STATUS      current
    DESCRIPTION "Table row."
    INDEX { IMPLIED dpStatusWebAppFwAcceptedfirewall }

    ::= { dpStatusWebAppFwAcceptedTable 1 }

DPStatusWebAppFwAcceptedEntry ::= SEQUENCE {
    dpStatusWebAppFwAcceptedfirewall    DisplayString,
    dpStatusWebAppFwAcceptedtenSeconds    Counter32,
    dpStatusWebAppFwAcceptedoneMinute    Counter32,
    dpStatusWebAppFwAcceptedtenMinutes    Counter32,
    dpStatusWebAppFwAcceptedoneHour    Counter32,
    dpStatusWebAppFwAcceptedoneDay    Counter32
}

dpStatusWebAppFwAcceptedfirewall OBJECT-TYPE
    SYNTAX      DisplayString
    MAX-ACCESS  read-only
    STATUS      current
    DESCRIPTION
        "Firewall"

    ::= { dpStatusWebAppFwAcceptedEntry 1 }

dpStatusWebAppFwAcceptedtenSeconds OBJECT-TYPE
    SYNTAX      Counter32
    MAX-ACCESS  read-only
    STATUS      current
    DESCRIPTION
        "Number of approvals in the previous 10 seconds."

    ::= { dpStatusWebAppFwAcceptedEntry 2 }

dpStatusWebAppFwAcceptedoneMinute OBJECT-TYPE
    SYNTAX      Counter32
    MAX-ACCESS  read-only
    STATUS      current
    DESCRIPTION
        "Number of approvals in the previous minute."

    ::= { dpStatusWebAppFwAcceptedEntry 3 }

dpStatusWebAppFwAcceptedtenMinutes OBJECT-TYPE
    SYNTAX      Counter32
    MAX-ACCESS  read-only
    STATUS      current
    DESCRIPTION
        "Number of approvals in the previous 10 minutes."

    ::= { dpStatusWebAppFwAcceptedEntry 4 }

dpStatusWebAppFwAcceptedoneHour OBJECT-TYPE
    SYNTAX      Counter32
    MAX-ACCESS  read-only
    STATUS      current
    DESCRIPTION
        "Number of approvals in the previous hour."

    ::= { dpStatusWebAppFwAcceptedEntry 5 }

dpStatusWebAppFwAcceptedoneDay OBJECT-TYPE
    SYNTAX      Counter32
    MAX-ACCESS  read-only
    STATUS      current
    DESCRIPTION
        "Number of approvals in the previous day."

    ::= { dpStatusWebAppFwAcceptedEntry 6 }

--

dpStatusWebAppFwRejectedTable OBJECT-TYPE
    SYNTAX      SEQUENCE OF DPStatusWebAppFwRejectedEntry
    MAX-ACCESS  not-accessible
    STATUS      current
    DESCRIPTION
        "The number of rejections by the Web Application Firewall."

    ::= { dpStatus 96 }

dpStatusWebAppFwRejectedEntry OBJECT-TYPE
    SYNTAX      DPStatusWebAppFwRejectedEntry
    MAX-ACCESS  not-accessible
    STATUS      current
    DESCRIPTION "Table row."
    INDEX { IMPLIED dpStatusWebAppFwRejectedfirewall }

    ::= { dpStatusWebAppFwRejectedTable 1 }

DPStatusWebAppFwRejectedEntry ::= SEQUENCE {
    dpStatusWebAppFwRejectedfirewall    DisplayString,
    dpStatusWebAppFwRejectedtenSeconds    Counter32,
    dpStatusWebAppFwRejectedoneMinute    Counter32,
    dpStatusWebAppFwRejectedtenMinutes    Counter32,
    dpStatusWebAppFwRejectedoneHour    Counter32,
    dpStatusWebAppFwRejectedoneDay    Counter32
}

dpStatusWebAppFwRejectedfirewall OBJECT-TYPE
    SYNTAX      DisplayString
    MAX-ACCESS  read-only
    STATUS      current
    DESCRIPTION
        "Firewall"

    ::= { dpStatusWebAppFwRejectedEntry 1 }

dpStatusWebAppFwRejectedtenSeconds OBJECT-TYPE
    SYNTAX      Counter32
    MAX-ACCESS  read-only
    STATUS      current
    DESCRIPTION
        "Number of rejections in the previous 10 seconds."

    ::= { dpStatusWebAppFwRejectedEntry 2 }

dpStatusWebAppFwRejectedoneMinute OBJECT-TYPE
    SYNTAX      Counter32
    MAX-ACCESS  read-only
    STATUS      current
    DESCRIPTION
        "Number of rejections in the previous minute."

    ::= { dpStatusWebAppFwRejectedEntry 3 }

dpStatusWebAppFwRejectedtenMinutes OBJECT-TYPE
    SYNTAX      Counter32
    MAX-ACCESS  read-only
    STATUS      current
    DESCRIPTION
        "Number of rejections in the previous 10 minutes."

    ::= { dpStatusWebAppFwRejectedEntry 4 }

dpStatusWebAppFwRejectedoneHour OBJECT-TYPE
    SYNTAX      Counter32
    MAX-ACCESS  read-only
    STATUS      current
    DESCRIPTION
        "Number of rejections in the previous hour."

    ::= { dpStatusWebAppFwRejectedEntry 5 }

dpStatusWebAppFwRejectedoneDay OBJECT-TYPE
    SYNTAX      Counter32
    MAX-ACCESS  read-only
    STATUS      current
    DESCRIPTION
        "Number of rejections in the previous day."

    ::= { dpStatusWebAppFwRejectedEntry 6 }

--

dpStatusEnvironmentalFanSensorsTable OBJECT-TYPE
    SYNTAX      SEQUENCE OF DPStatusEnvironmentalFanSensorsEntry
    MAX-ACCESS  not-accessible
    STATUS      current
    DESCRIPTION
        "Sensors that read fan speeds, from the fans in the appliance."

    ::= { dpStatus 97 }

dpStatusEnvironmentalFanSensorsEntry OBJECT-TYPE
    SYNTAX      DPStatusEnvironmentalFanSensorsEntry
    MAX-ACCESS  not-accessible
    STATUS      current
    DESCRIPTION "Table row."
    INDEX { dpStatusEnvironmentalFanSensorsFanID }

    ::= { dpStatusEnvironmentalFanSensorsTable 1 }

DPStatusEnvironmentalFanSensorsEntry ::= SEQUENCE {
    dpStatusEnvironmentalFanSensorsFanID    INTEGER,
    dpStatusEnvironmentalFanSensorsFanSpeed    Unsigned32,
    dpStatusEnvironmentalFanSensorsLowerCriticalThreshold    Integer32,
    dpStatusEnvironmentalFanSensorsReadingStatus    INTEGER,
    dpStatusEnvironmentalFanSensorsUpperCriticalThreshold    Integer32
}

dpStatusEnvironmentalFanSensorsFanID OBJECT-TYPE
    SYNTAX      INTEGER { 
                        cpu-1(1),
                        cpu-2(2),
                        chassis-1(3),
                        chassis-2(4),
                        chassis-3(5),
                        chassis-4(6),
                        chassis-5(7),
                        chassis-6(8),
                        chassis-7(9),
                        chassis-8(10),
                        fan-tray-1-fan-1(11),
                        fan-tray-1-fan-2(12),
                        fan-tray-1-fan-3(13),
                        fan-tray-1-fan-4(14),
                        fan-tray-2-fan-1(15),
                        fan-tray-2-fan-2(16),
                        fan-tray-2-fan-3(17),
                        fan-tray-2-fan-4(18),
                        fan-tray-3-fan-1(19),
                        fan-tray-3-fan-2(20),
                        fan-tray-3-fan-3(21),
                        fan-tray-3-fan-4(22),
                        hard-disk-tray-fan-1(23),
                        hard-disk-tray-fan-2(24),
                        fan-1a(25),
                        fan-1b(26),
                        fan-2a(27),
                        fan-2b(28),
                        fan-3a(29),
                        fan-3b(30),
                        fan-4a(31),
                        fan-4b(32),
                        fan-1(33),
                        fan-2(34),
                        fan-3(35)
                }
    MAX-ACCESS  read-only
    STATUS      current
    DESCRIPTION
        "The identification for the fan."

    ::= { dpStatusEnvironmentalFanSensorsEntry 1 }

dpStatusEnvironmentalFanSensorsFanSpeed OBJECT-TYPE
    SYNTAX      Unsigned32 (0..65535)
    UNITS       "RPM"
    MAX-ACCESS  read-only
    STATUS      current
    DESCRIPTION
        "The speed of the fan in revolutions per minute (RPM)."

    ::= { dpStatusEnvironmentalFanSensorsEntry 2 }

dpStatusEnvironmentalFanSensorsLowerCriticalThreshold OBJECT-TYPE
    SYNTAX      Integer32
    MAX-ACCESS  read-only
    STATUS      current
    DESCRIPTION
        "The lowest allowable reading of the fan speed sensor."

    ::= { dpStatusEnvironmentalFanSensorsEntry 3 }

dpStatusEnvironmentalFanSensorsReadingStatus OBJECT-TYPE
    SYNTAX      INTEGER { 
                        lowerNonRecoverable(1),
                        lowerCritical(2),
                        lowerNonCritical(3),
                        ok(4),
                        upperNonCritical(5),
                        upperCritical(6),
                        upperNonRecoverable(7),
                        failure(8),
                        noReading(9),
                        invalid(10)
                }
    MAX-ACCESS  read-only
    STATUS      current
    DESCRIPTION
        "An indicator of whether the current fan speed is OK or the fan speed is
        below the lower critical threshold. If the status is not OK, replace the
        fan (if replacing the fan is applicable on the machine type of the
        appliance); otherwise, replace the appliance."

    ::= { dpStatusEnvironmentalFanSensorsEntry 4 }

dpStatusEnvironmentalFanSensorsUpperCriticalThreshold OBJECT-TYPE
    SYNTAX      Integer32
    MAX-ACCESS  read-only
    STATUS      obsolete
    DESCRIPTION
        "The highest allowable reading of the fan speed sensor. If the maximum
        speed for a fan does not exist, no value is displayed."

    ::= { dpStatusEnvironmentalFanSensorsEntry 5 }

--

dpStatusDNSCacheHostStatusTable OBJECT-TYPE
    SYNTAX      SEQUENCE OF DPStatusDNSCacheHostStatusEntry
    MAX-ACCESS  not-accessible
    STATUS      obsolete
    DESCRIPTION
        "deprecated due to indexing problems
        Note: this is obsoleted and is replaced by dpStatusDNSCacheHostStatus2 as of release 7.2.0.1"

    ::= { dpStatus 98 }

dpStatusDNSCacheHostStatusEntry OBJECT-TYPE
    SYNTAX      DPStatusDNSCacheHostStatusEntry
    MAX-ACCESS  not-accessible
    STATUS      obsolete
    DESCRIPTION "Table row."
    INDEX { IMPLIED dpStatusDNSCacheHostStatusHostname }

    ::= { dpStatusDNSCacheHostStatusTable 1 }

DPStatusDNSCacheHostStatusEntry ::= SEQUENCE {
    dpStatusDNSCacheHostStatusHostname    DisplayString,
    dpStatusDNSCacheHostStatusIPAddress    IpAddress
}

dpStatusDNSCacheHostStatusHostname OBJECT-TYPE
    SYNTAX      DisplayString
    MAX-ACCESS  read-only
    STATUS      obsolete
    DESCRIPTION "No description yet."

    ::= { dpStatusDNSCacheHostStatusEntry 1 }

dpStatusDNSCacheHostStatusIPAddress OBJECT-TYPE
    SYNTAX      IpAddress
    MAX-ACCESS  read-only
    STATUS      obsolete
    DESCRIPTION "No description yet."

    ::= { dpStatusDNSCacheHostStatusEntry 2 }

--

dpStatusTibcoEMSStatusTable OBJECT-TYPE
    SYNTAX      SEQUENCE OF DPStatusTibcoEMSStatusEntry
    MAX-ACCESS  not-accessible
    STATUS      current
    DESCRIPTION
        "Tibco Enterprise Message Service status."

    ::= { dpStatus 99 }

dpStatusTibcoEMSStatusEntry OBJECT-TYPE
    SYNTAX      DPStatusTibcoEMSStatusEntry
    MAX-ACCESS  not-accessible
    STATUS      current
    DESCRIPTION "Table row."
    INDEX { IMPLIED dpConfigTibcoEMSServerIndex }

    ::= { dpStatusTibcoEMSStatusTable 1 }

DPStatusTibcoEMSStatusEntry ::= SEQUENCE {
    dpStatusTibcoEMSStatusServer    DisplayString,
    dpStatusTibcoEMSStatusReceivedMessages    Unsigned32,
    dpStatusTibcoEMSStatusSentMessages    Unsigned32,
    dpStatusTibcoEMSStatusReceivedFaults    Unsigned32,
    dpStatusTibcoEMSStatusSentFaults    Unsigned32
}

dpStatusTibcoEMSStatusServer OBJECT-TYPE
    SYNTAX      DisplayString
    MAX-ACCESS  read-only
    STATUS      current
    DESCRIPTION
        "Name of the Tibco EMS server."

    ::= { dpStatusTibcoEMSStatusEntry 1 }

dpStatusTibcoEMSStatusReceivedMessages OBJECT-TYPE
    SYNTAX      Unsigned32
    MAX-ACCESS  read-only
    STATUS      current
    DESCRIPTION
        "Number of messages received by this server."

    ::= { dpStatusTibcoEMSStatusEntry 2 }

dpStatusTibcoEMSStatusSentMessages OBJECT-TYPE
    SYNTAX      Unsigned32
    MAX-ACCESS  read-only
    STATUS      current
    DESCRIPTION
        "Number of messages sent by this server."

    ::= { dpStatusTibcoEMSStatusEntry 3 }

dpStatusTibcoEMSStatusReceivedFaults OBJECT-TYPE
    SYNTAX      Unsigned32
    MAX-ACCESS  read-only
    STATUS      current
    DESCRIPTION
        "Number of errors detected by this server during receive operations."

    ::= { dpStatusTibcoEMSStatusEntry 4 }

dpStatusTibcoEMSStatusSentFaults OBJECT-TYPE
    SYNTAX      Unsigned32
    MAX-ACCESS  read-only
    STATUS      current
    DESCRIPTION
        "Number of errors detected by this server during send operations."

    ::= { dpStatusTibcoEMSStatusEntry 5 }

--

dpStatusFirmwareStatusTable OBJECT-TYPE
    SYNTAX      SEQUENCE OF DPStatusFirmwareStatusEntry
    MAX-ACCESS  not-accessible
    STATUS      deprecated
    DESCRIPTION
        "Information about the current firmware installations.
        Note: this is obsoleted and is replaced by dpStatusFirmwareStatus2"

    ::= { dpStatus 100 }

dpStatusFirmwareStatusEntry OBJECT-TYPE
    SYNTAX      DPStatusFirmwareStatusEntry
    MAX-ACCESS  not-accessible
    STATUS      deprecated
    DESCRIPTION "Table row."
    INDEX { dpStatusFirmwareStatusType }

    ::= { dpStatusFirmwareStatusTable 1 }

DPStatusFirmwareStatusEntry ::= SEQUENCE {
    dpStatusFirmwareStatusType    INTEGER,
    dpStatusFirmwareStatusVersion    DisplayString,
    dpStatusFirmwareStatusBuild    DisplayString,
    dpStatusFirmwareStatusBuildDate    DisplayString,
    dpStatusFirmwareStatusInstallDate    DisplayString,
    dpStatusFirmwareStatusBootCount    Unsigned32
}

dpStatusFirmwareStatusType OBJECT-TYPE
    SYNTAX      INTEGER { 
                        primary(1),
                        secondary(2)
                }
    MAX-ACCESS  read-only
    STATUS      deprecated
    DESCRIPTION
        "The type of the firmware installation type. Can be primary or secondary.
        The secondary firmware image is used when rolling back the firmware."

    ::= { dpStatusFirmwareStatusEntry 1 }

dpStatusFirmwareStatusVersion OBJECT-TYPE
    SYNTAX      DisplayString
    MAX-ACCESS  read-only
    STATUS      deprecated
    DESCRIPTION
        "The version of this firmware image."

    ::= { dpStatusFirmwareStatusEntry 2 }

dpStatusFirmwareStatusBuild OBJECT-TYPE
    SYNTAX      DisplayString
    MAX-ACCESS  read-only
    STATUS      deprecated
    DESCRIPTION
        "The specific build of this firmware image."

    ::= { dpStatusFirmwareStatusEntry 3 }

dpStatusFirmwareStatusBuildDate OBJECT-TYPE
    SYNTAX      DisplayString
    MAX-ACCESS  read-only
    STATUS      deprecated
    DESCRIPTION
        "Date of the firmware build."

    ::= { dpStatusFirmwareStatusEntry 4 }

dpStatusFirmwareStatusInstallDate OBJECT-TYPE
    SYNTAX      DisplayString
    MAX-ACCESS  read-only
    STATUS      deprecated
    DESCRIPTION
        "Date that this firmware was installed."

    ::= { dpStatusFirmwareStatusEntry 5 }

dpStatusFirmwareStatusBootCount OBJECT-TYPE
    SYNTAX      Unsigned32
    MAX-ACCESS  read-only
    STATUS      deprecated
    DESCRIPTION
        "The number of times the firmware image was restarted through an appliance
        reboot or a firmware reload. The count is from the initial firmware load
        on the appliance till the current time. The count is independent of
        firmware version."

    ::= { dpStatusFirmwareStatusEntry 6 }

--

dpStatusStylesheetStatusSimpleIndexTable OBJECT-TYPE
    SYNTAX      SEQUENCE OF DPStatusStylesheetStatusSimpleIndexEntry
    MAX-ACCESS  not-accessible
    STATUS      current
    DESCRIPTION
        "A report of the status of XSL stylesheets and WSDL files compiled during
        processing. The compiler log messages are helpful for debugging and
        development. Once compiled, these files are cached for speed. The compiled
        files may be flushed from the cache and/or refreshed periodically.
        Note: this obsoletes dpStatusStylesheetStatus"

    ::= { dpStatus 101 }

dpStatusStylesheetStatusSimpleIndexEntry OBJECT-TYPE
    SYNTAX      DPStatusStylesheetStatusSimpleIndexEntry
    MAX-ACCESS  not-accessible
    STATUS      current
    DESCRIPTION "Table row."
    INDEX { dpConfigXMLManagerIndex, dpStatusStylesheetStatusSimpleIndexID, dpStatusStylesheetStatusSimpleIndexOutputMode }

    ::= { dpStatusStylesheetStatusSimpleIndexTable 1 }

DPStatusStylesheetStatusSimpleIndexEntry ::= SEQUENCE {
    dpStatusStylesheetStatusSimpleIndexXMLManager    DisplayString,
    dpStatusStylesheetStatusSimpleIndexID    Unsigned32,
    dpStatusStylesheetStatusSimpleIndexOutputMode    INTEGER,
    dpStatusStylesheetStatusSimpleIndexURL    DisplayString,
    dpStatusStylesheetStatusSimpleIndexCompileOptions    DisplayString,
    dpStatusStylesheetStatusSimpleIndexStatus    INTEGER,
    dpStatusStylesheetStatusSimpleIndexCompileSpeed    DPTimeIntervalMillis,
    dpStatusStylesheetStatusSimpleIndexRefreshInterval    DPTimeIntervalSeconds,
    dpStatusStylesheetStatusSimpleIndexFlushable    INTEGER,
    dpStatusStylesheetStatusSimpleIndexLastRefresh    TimeStamp,
    dpStatusStylesheetStatusSimpleIndexMessage    DisplayString,
    dpStatusStylesheetStatusSimpleIndexLog    DisplayString,
    dpStatusStylesheetStatusSimpleIndexXG4Enabled    INTEGER,
    dpStatusStylesheetStatusSimpleIndexXG4Size    Unsigned32,
    dpStatusStylesheetStatusSimpleIndexMemSize    Unsigned32
}

dpStatusStylesheetStatusSimpleIndexXMLManager OBJECT-TYPE
    SYNTAX      DisplayString
    MAX-ACCESS  read-only
    STATUS      current
    DESCRIPTION
        "The name of the XML Manager performing the compiling and caching of the
        stylesheet or WSDL."

    ::= { dpStatusStylesheetStatusSimpleIndexEntry 1 }

dpStatusStylesheetStatusSimpleIndexID OBJECT-TYPE
    SYNTAX      Unsigned32
    MAX-ACCESS  read-only
    STATUS      current
    DESCRIPTION
        "A unique identifier assigned by the system to the compiled stylesheet or
        WSDL."

    ::= { dpStatusStylesheetStatusSimpleIndexEntry 2 }

dpStatusStylesheetStatusSimpleIndexOutputMode OBJECT-TYPE
    SYNTAX      INTEGER { 
                        general(1),
                        stream(2),
                        context(3),
                        events(4)
                }
    MAX-ACCESS  read-only
    STATUS      current
    DESCRIPTION
        "The output mode used by the compiler. The value 'general' indicates
        general-purpose compilation mode, no specialization. The value 'stream'
        indicated specialized compilation mode for direct output to a network
        stream. The value 'context' indicates specialized compilation mode for
        output to a temporary context variable. The value 'events' indicates
        specialized compilation mode for event-driven output."

    ::= { dpStatusStylesheetStatusSimpleIndexEntry 3 }

dpStatusStylesheetStatusSimpleIndexURL OBJECT-TYPE
    SYNTAX      DisplayString
    MAX-ACCESS  read-only
    STATUS      current
    DESCRIPTION
        "The URL of the stylesheet or WSDL compiled. This may reside on or off the
        device."

    ::= { dpStatusStylesheetStatusSimpleIndexEntry 4 }

dpStatusStylesheetStatusSimpleIndexCompileOptions OBJECT-TYPE
    SYNTAX      DisplayString
    MAX-ACCESS  read-only
    STATUS      current
    DESCRIPTION
        "The Compile options applied to the stylesheet or WSDL. Compile options are
        set by a Compile Options Policy associated with the XML manager used."

    ::= { dpStatusStylesheetStatusSimpleIndexEntry 5 }

dpStatusStylesheetStatusSimpleIndexStatus OBJECT-TYPE
    SYNTAX      INTEGER { 
                        ready(1),
                        pending(2),
                        bad(3),
                        expired(4)
                }
    MAX-ACCESS  read-only
    STATUS      current
    DESCRIPTION
        "The current status of the compiled stylesheet or WSDL. The value 'ready'
        indicates ready for execution, does not require further compilation. The
        value 'pending' indicates that it is waiting for compilation, the system
        has a queue for compilation. The value 'bad' indicates that is failed to
        compile, cannot execute. Check the Compiler log for reasons. The value
        'expired' indicates that it has expired from the cache; cannot execute.
        This indicates the file has not been required for processing for the cache
        lifetime amount of time. On next request, it will automatically recompile."

    ::= { dpStatusStylesheetStatusSimpleIndexEntry 6 }

dpStatusStylesheetStatusSimpleIndexCompileSpeed OBJECT-TYPE
    SYNTAX      DPTimeIntervalMillis
    UNITS       "ms"
    MAX-ACCESS  read-only
    STATUS      current
    DESCRIPTION
        "Time to compile in milliseconds."

    ::= { dpStatusStylesheetStatusSimpleIndexEntry 7 }

dpStatusStylesheetStatusSimpleIndexRefreshInterval OBJECT-TYPE
    SYNTAX      DPTimeIntervalSeconds
    UNITS       "sec"
    MAX-ACCESS  read-only
    STATUS      current
    DESCRIPTION
        "Time between automatic refreshes in seconds. When an automatic refresh is
        in force, files are fetched and recompiled to maintain a fresh cache."

    ::= { dpStatusStylesheetStatusSimpleIndexEntry 8 }

dpStatusStylesheetStatusSimpleIndexFlushable OBJECT-TYPE
    SYNTAX      INTEGER { 
                        on(1),
                        off(2)
                }
    MAX-ACCESS  read-only
    STATUS      current
    DESCRIPTION
        "Indicates ability to remove (flush) from cache. If the compiled version of
        the file can be flushed from the cache (in effect forcing a refresh the
        next time the file is called), click the Flush Stylesheet Cache button on
        the XML Manager object page to optionally remove the file from the
        compiled cache. Useful during development and debugging."

    ::= { dpStatusStylesheetStatusSimpleIndexEntry 9 }

dpStatusStylesheetStatusSimpleIndexLastRefresh OBJECT-TYPE
    SYNTAX      TimeStamp
    MAX-ACCESS  read-only
    STATUS      current
    DESCRIPTION
        "Timestamp of the last refresh. Indicates length of time in cache. Use the
        Refresh button to immediately refresh a compiled stylesheet or WSDL."

    ::= { dpStatusStylesheetStatusSimpleIndexEntry 10 }

dpStatusStylesheetStatusSimpleIndexMessage OBJECT-TYPE
    SYNTAX      DisplayString
    MAX-ACCESS  read-only
    STATUS      current
    DESCRIPTION
        "Helpful compiler messages."

    ::= { dpStatusStylesheetStatusSimpleIndexEntry 11 }

dpStatusStylesheetStatusSimpleIndexLog OBJECT-TYPE
    SYNTAX      DisplayString
    MAX-ACCESS  read-only
    STATUS      current
    DESCRIPTION
        "Helpful compiler log messages. Any compilation errors can be found here."

    ::= { dpStatusStylesheetStatusSimpleIndexEntry 12 }

dpStatusStylesheetStatusSimpleIndexXG4Enabled OBJECT-TYPE
    SYNTAX      INTEGER { 
                        on(1),
                        off(2)
                }
    MAX-ACCESS  read-only
    STATUS      current
    DESCRIPTION
        "Reports use (on) of XML hardware acceleration during compile of particular
        stylesheet or WSDL."

    ::= { dpStatusStylesheetStatusSimpleIndexEntry 13 }

dpStatusStylesheetStatusSimpleIndexXG4Size OBJECT-TYPE
    SYNTAX      Unsigned32
    UNITS       "%"
    MAX-ACCESS  read-only
    STATUS      current
    DESCRIPTION
        "Reports usage percentage of XML hardware acceleration during compile of
        particular stylesheet or WSDL."

    ::= { dpStatusStylesheetStatusSimpleIndexEntry 14 }

dpStatusStylesheetStatusSimpleIndexMemSize OBJECT-TYPE
    SYNTAX      Unsigned32
    UNITS       "KB"
    MAX-ACCESS  read-only
    STATUS      current
    DESCRIPTION
        "The memory used by the compiled stylesheet in KB."

    ::= { dpStatusStylesheetStatusSimpleIndexEntry 15 }

--

dpStatusDocumentStatusSimpleIndexTable OBJECT-TYPE
    SYNTAX      SEQUENCE OF DPStatusDocumentStatusSimpleIndexEntry
    MAX-ACCESS  not-accessible
    STATUS      current
    DESCRIPTION
        "Displays status information about documents in the document cache.
        Note: this obsoletes dpStatusDocumentStatus"

    ::= { dpStatus 102 }

dpStatusDocumentStatusSimpleIndexEntry OBJECT-TYPE
    SYNTAX      DPStatusDocumentStatusSimpleIndexEntry
    MAX-ACCESS  not-accessible
    STATUS      current
    DESCRIPTION "Table row."
    INDEX { dpConfigXMLManagerIndex, dpStatusDocumentStatusSimpleIndexID }

    ::= { dpStatusDocumentStatusSimpleIndexTable 1 }

DPStatusDocumentStatusSimpleIndexEntry ::= SEQUENCE {
    dpStatusDocumentStatusSimpleIndexXMLManager    DisplayString,
    dpStatusDocumentStatusSimpleIndexID    Unsigned32,
    dpStatusDocumentStatusSimpleIndexURL    DisplayString,
    dpStatusDocumentStatusSimpleIndexExpiry    DisplayString,
    dpStatusDocumentStatusSimpleIndexCacheKey    DisplayString
}

dpStatusDocumentStatusSimpleIndexXMLManager OBJECT-TYPE
    SYNTAX      DisplayString
    MAX-ACCESS  read-only
    STATUS      current
    DESCRIPTION
        "The name of the XML manager managing the document."

    ::= { dpStatusDocumentStatusSimpleIndexEntry 1 }

dpStatusDocumentStatusSimpleIndexID OBJECT-TYPE
    SYNTAX      Unsigned32
    MAX-ACCESS  read-only
    STATUS      current
    DESCRIPTION
        "A unique identifier assigned to the document."

    ::= { dpStatusDocumentStatusSimpleIndexEntry 2 }

dpStatusDocumentStatusSimpleIndexURL OBJECT-TYPE
    SYNTAX      DisplayString
    MAX-ACCESS  read-only
    STATUS      current
    DESCRIPTION
        "The URL used to obtain the document."

    ::= { dpStatusDocumentStatusSimpleIndexEntry 3 }

dpStatusDocumentStatusSimpleIndexExpiry OBJECT-TYPE
    SYNTAX      DisplayString
    MAX-ACCESS  read-only
    STATUS      current
    DESCRIPTION
        "The time at which the document will expire from the cache."

    ::= { dpStatusDocumentStatusSimpleIndexEntry 4 }

dpStatusDocumentStatusSimpleIndexCacheKey OBJECT-TYPE
    SYNTAX      DisplayString
    MAX-ACCESS  read-only
    STATUS      current
    DESCRIPTION
        "The unique key used to lookup the document."

    ::= { dpStatusDocumentStatusSimpleIndexEntry 5 }

--

dpStatusStylesheetExecutionsSimpleIndexTable OBJECT-TYPE
    SYNTAX      SEQUENCE OF DPStatusStylesheetExecutionsSimpleIndexEntry
    MAX-ACCESS  not-accessible
    STATUS      current
    DESCRIPTION
        "This display reports stylesheet execution counts.
        Note: this obsoletes dpStatusStylesheetExecutions"

    ::= { dpStatus 103 }

dpStatusStylesheetExecutionsSimpleIndexEntry OBJECT-TYPE
    SYNTAX      DPStatusStylesheetExecutionsSimpleIndexEntry
    MAX-ACCESS  not-accessible
    STATUS      current
    DESCRIPTION "Table row."
    INDEX { dpStatusStylesheetExecutionsSimpleIndexXMLManager, dpStatusStylesheetExecutionsSimpleIndexID, dpStatusStylesheetExecutionsSimpleIndexOutputMode }

    ::= { dpStatusStylesheetExecutionsSimpleIndexTable 1 }

DPStatusStylesheetExecutionsSimpleIndexEntry ::= SEQUENCE {
    dpStatusStylesheetExecutionsSimpleIndexXMLManager    DisplayString,
    dpStatusStylesheetExecutionsSimpleIndexID    Unsigned32,
    dpStatusStylesheetExecutionsSimpleIndexOutputMode    INTEGER,
    dpStatusStylesheetExecutionsSimpleIndexURL    DisplayString,
    dpStatusStylesheetExecutionsSimpleIndextenSeconds    Counter32,
    dpStatusStylesheetExecutionsSimpleIndexoneMinute    Counter32,
    dpStatusStylesheetExecutionsSimpleIndextenMinutes    Counter32,
    dpStatusStylesheetExecutionsSimpleIndexoneHour    Counter32,
    dpStatusStylesheetExecutionsSimpleIndexoneDay    Counter32
}

dpStatusStylesheetExecutionsSimpleIndexXMLManager OBJECT-TYPE
    SYNTAX      DisplayString
    MAX-ACCESS  read-only
    STATUS      current
    DESCRIPTION "No description yet."

    ::= { dpStatusStylesheetExecutionsSimpleIndexEntry 1 }

dpStatusStylesheetExecutionsSimpleIndexID OBJECT-TYPE
    SYNTAX      Unsigned32
    MAX-ACCESS  read-only
    STATUS      current
    DESCRIPTION "No description yet."

    ::= { dpStatusStylesheetExecutionsSimpleIndexEntry 2 }

dpStatusStylesheetExecutionsSimpleIndexOutputMode OBJECT-TYPE
    SYNTAX      INTEGER { 
                        general(1),
                        stream(2),
                        context(3),
                        events(4)
                }
    MAX-ACCESS  read-only
    STATUS      current
    DESCRIPTION
        "The output mode used by the compiler. The value 'general' indicates
        general-purpose compilation mode, no specialization. The value 'stream'
        indicated specialized compilation mode for direct output to a network
        stream. The value 'context' indicates specialized compilation mode for
        output to a temporary context variable. The value 'events' indicates
        specialized compilation mode for event-driven output."

    ::= { dpStatusStylesheetExecutionsSimpleIndexEntry 3 }

dpStatusStylesheetExecutionsSimpleIndexURL OBJECT-TYPE
    SYNTAX      DisplayString
    MAX-ACCESS  read-only
    STATUS      current
    DESCRIPTION
        "The stylesheet source may reside on the device or remotely. This URL
        indicates the source location of the stylesheet in the cache"

    ::= { dpStatusStylesheetExecutionsSimpleIndexEntry 4 }

dpStatusStylesheetExecutionsSimpleIndextenSeconds OBJECT-TYPE
    SYNTAX      Counter32
    MAX-ACCESS  read-only
    STATUS      current
    DESCRIPTION
        "Count of executions during the last 10 seconds"

    ::= { dpStatusStylesheetExecutionsSimpleIndexEntry 5 }

dpStatusStylesheetExecutionsSimpleIndexoneMinute OBJECT-TYPE
    SYNTAX      Counter32
    MAX-ACCESS  read-only
    STATUS      current
    DESCRIPTION
        "Count of executions during the last 1 minute"

    ::= { dpStatusStylesheetExecutionsSimpleIndexEntry 6 }

dpStatusStylesheetExecutionsSimpleIndextenMinutes OBJECT-TYPE
    SYNTAX      Counter32
    MAX-ACCESS  read-only
    STATUS      current
    DESCRIPTION
        "Count of executions during the last 10 minutes"

    ::= { dpStatusStylesheetExecutionsSimpleIndexEntry 7 }

dpStatusStylesheetExecutionsSimpleIndexoneHour OBJECT-TYPE
    SYNTAX      Counter32
    MAX-ACCESS  read-only
    STATUS      current
    DESCRIPTION
        "Count of executions during the last 1 hour"

    ::= { dpStatusStylesheetExecutionsSimpleIndexEntry 8 }

dpStatusStylesheetExecutionsSimpleIndexoneDay OBJECT-TYPE
    SYNTAX      Counter32
    MAX-ACCESS  read-only
    STATUS      current
    DESCRIPTION
        "Count of executions during the last 1 day"

    ::= { dpStatusStylesheetExecutionsSimpleIndexEntry 9 }

--

dpStatusStylesheetMeanExecutionTimeSimpleIndexTable OBJECT-TYPE
    SYNTAX      SEQUENCE OF DPStatusStylesheetMeanExecutionTimeSimpleIndexEntry
    MAX-ACCESS  not-accessible
    STATUS      current
    DESCRIPTION
        "Stylesheet mean execution times
        Note: this obsoletes dpStatusStylesheetMeanExecutionTime"

    ::= { dpStatus 104 }

dpStatusStylesheetMeanExecutionTimeSimpleIndexEntry OBJECT-TYPE
    SYNTAX      DPStatusStylesheetMeanExecutionTimeSimpleIndexEntry
    MAX-ACCESS  not-accessible
    STATUS      current
    DESCRIPTION "Table row."
    INDEX { dpStatusStylesheetMeanExecutionTimeSimpleIndexXMLManager, dpStatusStylesheetMeanExecutionTimeSimpleIndexID, dpStatusStylesheetMeanExecutionTimeSimpleIndexOutputMode }

    ::= { dpStatusStylesheetMeanExecutionTimeSimpleIndexTable 1 }

DPStatusStylesheetMeanExecutionTimeSimpleIndexEntry ::= SEQUENCE {
    dpStatusStylesheetMeanExecutionTimeSimpleIndexXMLManager    DisplayString,
    dpStatusStylesheetMeanExecutionTimeSimpleIndexID    Unsigned32,
    dpStatusStylesheetMeanExecutionTimeSimpleIndexOutputMode    INTEGER,
    dpStatusStylesheetMeanExecutionTimeSimpleIndexURL    DisplayString,
    dpStatusStylesheetMeanExecutionTimeSimpleIndextenSeconds    Counter32,
    dpStatusStylesheetMeanExecutionTimeSimpleIndexoneMinute    Counter32,
    dpStatusStylesheetMeanExecutionTimeSimpleIndextenMinutes    Counter32,
    dpStatusStylesheetMeanExecutionTimeSimpleIndexoneHour    Counter32,
    dpStatusStylesheetMeanExecutionTimeSimpleIndexoneDay    Counter32
}

dpStatusStylesheetMeanExecutionTimeSimpleIndexXMLManager OBJECT-TYPE
    SYNTAX      DisplayString
    MAX-ACCESS  read-only
    STATUS      current
    DESCRIPTION
        "The name of the XML manager executing the stylesheets."

    ::= { dpStatusStylesheetMeanExecutionTimeSimpleIndexEntry 1 }

dpStatusStylesheetMeanExecutionTimeSimpleIndexID OBJECT-TYPE
    SYNTAX      Unsigned32
    MAX-ACCESS  read-only
    STATUS      current
    DESCRIPTION
        "Cache index identifier"

    ::= { dpStatusStylesheetMeanExecutionTimeSimpleIndexEntry 2 }

dpStatusStylesheetMeanExecutionTimeSimpleIndexOutputMode OBJECT-TYPE
    SYNTAX      INTEGER { 
                        general(1),
                        stream(2),
                        context(3),
                        events(4)
                }
    MAX-ACCESS  read-only
    STATUS      current
    DESCRIPTION
        "The output mode used by the compiler. The value 'general' indicates
        general-purpose compilation mode, no specialization. The value 'stream'
        indicated specialized compilation mode for direct output to a network
        stream. The value 'context' indicates specialized compilation mode for
        output to a temporary context variable. The value 'events' indicates
        specialized compilation mode for event-driven output."

    ::= { dpStatusStylesheetMeanExecutionTimeSimpleIndexEntry 3 }

dpStatusStylesheetMeanExecutionTimeSimpleIndexURL OBJECT-TYPE
    SYNTAX      DisplayString
    MAX-ACCESS  read-only
    STATUS      current
    DESCRIPTION
        "The URL of the stylesheet or WSDL. This may refer to a location off the
        device or to a location on the device."

    ::= { dpStatusStylesheetMeanExecutionTimeSimpleIndexEntry 4 }

dpStatusStylesheetMeanExecutionTimeSimpleIndextenSeconds OBJECT-TYPE
    SYNTAX      Counter32
    UNITS       "ms"
    MAX-ACCESS  read-only
    STATUS      current
    DESCRIPTION
        "Average execution time over the last 10 seconds."

    ::= { dpStatusStylesheetMeanExecutionTimeSimpleIndexEntry 5 }

dpStatusStylesheetMeanExecutionTimeSimpleIndexoneMinute OBJECT-TYPE
    SYNTAX      Counter32
    UNITS       "ms"
    MAX-ACCESS  read-only
    STATUS      current
    DESCRIPTION
        "Average execution time over the last minute."

    ::= { dpStatusStylesheetMeanExecutionTimeSimpleIndexEntry 6 }

dpStatusStylesheetMeanExecutionTimeSimpleIndextenMinutes OBJECT-TYPE
    SYNTAX      Counter32
    UNITS       "ms"
    MAX-ACCESS  read-only
    STATUS      current
    DESCRIPTION
        "Average execution time over the last 10 minutes."

    ::= { dpStatusStylesheetMeanExecutionTimeSimpleIndexEntry 7 }

dpStatusStylesheetMeanExecutionTimeSimpleIndexoneHour OBJECT-TYPE
    SYNTAX      Counter32
    UNITS       "ms"
    MAX-ACCESS  read-only
    STATUS      current
    DESCRIPTION
        "Average execution time over the last 1 hour."

    ::= { dpStatusStylesheetMeanExecutionTimeSimpleIndexEntry 8 }

dpStatusStylesheetMeanExecutionTimeSimpleIndexoneDay OBJECT-TYPE
    SYNTAX      Counter32
    UNITS       "ms"
    MAX-ACCESS  read-only
    STATUS      current
    DESCRIPTION
        "Average execution time over the last day."

    ::= { dpStatusStylesheetMeanExecutionTimeSimpleIndexEntry 9 }

--

dpStatusStylesheetProfilesSimpleIndexTable OBJECT-TYPE
    SYNTAX      SEQUENCE OF DPStatusStylesheetProfilesSimpleIndexEntry
    MAX-ACCESS  not-accessible
    STATUS      current
    DESCRIPTION
        "Table that summarizes profiling information about style sheets. The table
        reports each template, global variable, and dp:profile element that the
        style sheet processes in their own entry. No data is available unless an
        XML Manager with a Compile Options Policy with Profiling enabled matches a
        request or response that the device processed.
        Note: this obsoletes dpStatusStylesheetProfiles"

    ::= { dpStatus 105 }

dpStatusStylesheetProfilesSimpleIndexEntry OBJECT-TYPE
    SYNTAX      DPStatusStylesheetProfilesSimpleIndexEntry
    MAX-ACCESS  not-accessible
    STATUS      current
    DESCRIPTION "Table row."
    INDEX { dpConfigXMLManagerIndex, dpStatusStylesheetProfilesSimpleIndexID, dpStatusStylesheetProfilesSimpleIndexOutputMode, dpStatusStylesheetProfilesSimpleIndexIndex }

    ::= { dpStatusStylesheetProfilesSimpleIndexTable 1 }

DPStatusStylesheetProfilesSimpleIndexEntry ::= SEQUENCE {
    dpStatusStylesheetProfilesSimpleIndexXMLManager    DisplayString,
    dpStatusStylesheetProfilesSimpleIndexID    Unsigned32,
    dpStatusStylesheetProfilesSimpleIndexOutputMode    INTEGER,
    dpStatusStylesheetProfilesSimpleIndexURL    DisplayString,
    dpStatusStylesheetProfilesSimpleIndexIndex    Unsigned32,
    dpStatusStylesheetProfilesSimpleIndexName    DisplayString,
    dpStatusStylesheetProfilesSimpleIndexLocation    DisplayString,
    dpStatusStylesheetProfilesSimpleIndexCount    Counter32,
    dpStatusStylesheetProfilesSimpleIndexType    DisplayString,
    dpStatusStylesheetProfilesSimpleIndexTotalTimeMS    Unsigned32
}

dpStatusStylesheetProfilesSimpleIndexXMLManager OBJECT-TYPE
    SYNTAX      DisplayString
    MAX-ACCESS  read-only
    STATUS      current
    DESCRIPTION
        "The name of the XML manager employed."

    ::= { dpStatusStylesheetProfilesSimpleIndexEntry 1 }

dpStatusStylesheetProfilesSimpleIndexID OBJECT-TYPE
    SYNTAX      Unsigned32
    MAX-ACCESS  read-only
    STATUS      current
    DESCRIPTION
        "A number that identifies the style sheet in the cache that processed this
        request."

    ::= { dpStatusStylesheetProfilesSimpleIndexEntry 2 }

dpStatusStylesheetProfilesSimpleIndexOutputMode OBJECT-TYPE
    SYNTAX      INTEGER { 
                        general(1),
                        stream(2),
                        context(3),
                        events(4)
                }
    MAX-ACCESS  read-only
    STATUS      current
    DESCRIPTION
        "The output mode of the compiler."

    ::= { dpStatusStylesheetProfilesSimpleIndexEntry 3 }

dpStatusStylesheetProfilesSimpleIndexURL OBJECT-TYPE
    SYNTAX      DisplayString
    MAX-ACCESS  read-only
    STATUS      current
    DESCRIPTION
        "The URL of the style sheet. This value might refer to a remote location or
        to a location on the device."

    ::= { dpStatusStylesheetProfilesSimpleIndexEntry 4 }

dpStatusStylesheetProfilesSimpleIndexIndex OBJECT-TYPE
    SYNTAX      Unsigned32
    MAX-ACCESS  read-only
    STATUS      current
    DESCRIPTION
        "An index of the calls made to this style sheet."

    ::= { dpStatusStylesheetProfilesSimpleIndexEntry 5 }

dpStatusStylesheetProfilesSimpleIndexName OBJECT-TYPE
    SYNTAX      DisplayString
    MAX-ACCESS  read-only
    STATUS      current
    DESCRIPTION
        "The name of the template, global variable, or dp:profile node in the style
        sheet that the entry represents. Each named template in the style sheet is
        listed if processed by the style sheet. If a style sheet calls the same
        template from multiple places in the style sheet, each of the multiple
        entries is listed."

    ::= { dpStatusStylesheetProfilesSimpleIndexEntry 6 }

dpStatusStylesheetProfilesSimpleIndexLocation OBJECT-TYPE
    SYNTAX      DisplayString
    MAX-ACCESS  read-only
    STATUS      current
    DESCRIPTION
        "The line number in the style sheet where the template was called or the
        location of the declaration of a global variable or dp:profile element.
        For example, a report of local:///mine.xsl:16 indicates a template was
        called on line 16 of the indicated style sheet. Entries with the
        'built-in' location refer to the implicit templates defined by the XSLT
        1.0 specification."

    ::= { dpStatusStylesheetProfilesSimpleIndexEntry 7 }

dpStatusStylesheetProfilesSimpleIndexCount OBJECT-TYPE
    SYNTAX      Counter32
    MAX-ACCESS  read-only
    STATUS      current
    DESCRIPTION
        "The number of times the listed entry ran during the processing of a
        request by the style sheet. A template or dp:profile node can be called
        more than once during the processing of a style sheet."

    ::= { dpStatusStylesheetProfilesSimpleIndexEntry 9 }

dpStatusStylesheetProfilesSimpleIndexType OBJECT-TYPE
    SYNTAX      DisplayString
    MAX-ACCESS  read-only
    STATUS      current
    DESCRIPTION
        "The type of this entry. The value can be either a template, global
        variable, dp:profile node, or the total for the entire stylesheet
        execution."

    ::= { dpStatusStylesheetProfilesSimpleIndexEntry 10 }

dpStatusStylesheetProfilesSimpleIndexTotalTimeMS OBJECT-TYPE
    SYNTAX      Unsigned32
    UNITS       "ms"
    MAX-ACCESS  read-only
    STATUS      current
    DESCRIPTION
        "The total time, measured in milliseconds, spent processing the
        instructions represented in this entry. The instructions represented by a
        given entry can run more than once, as indicated by the count. The total
        time is the sum measured across all runs of the style sheet. As some
        entries represent nested portions of the stylesheet processing, the sum of
        all entries do not equal the total time."

    ::= { dpStatusStylesheetProfilesSimpleIndexEntry 11 }

--

dpStatusWSWSDLStatusSimpleIndexTable OBJECT-TYPE
    SYNTAX      SEQUENCE OF DPStatusWSWSDLStatusSimpleIndexEntry
    MAX-ACCESS  not-accessible
    STATUS      current
    DESCRIPTION "Note: this obsoletes dpStatusWSWSDLStatus"

    ::= { dpStatus 106 }

dpStatusWSWSDLStatusSimpleIndexEntry OBJECT-TYPE
    SYNTAX      DPStatusWSWSDLStatusSimpleIndexEntry
    MAX-ACCESS  not-accessible
    STATUS      current
    DESCRIPTION "Table row."
    INDEX { dpConfigWSGatewayIndex, dpStatusWSWSDLStatusSimpleIndexID }

    ::= { dpStatusWSWSDLStatusSimpleIndexTable 1 }

DPStatusWSWSDLStatusSimpleIndexEntry ::= SEQUENCE {
    dpStatusWSWSDLStatusSimpleIndexWSGateway    DisplayString,
    dpStatusWSWSDLStatusSimpleIndexID    Unsigned32,
    dpStatusWSWSDLStatusSimpleIndexWSDLSourceLocation    DisplayString,
    dpStatusWSWSDLStatusSimpleIndexStatus    INTEGER,
    dpStatusWSWSDLStatusSimpleIndexRefreshInterval    DPTimeIntervalSeconds,
    dpStatusWSWSDLStatusSimpleIndexLastRefresh    TimeStamp,
    dpStatusWSWSDLStatusSimpleIndexLog    DisplayString,
    dpStatusWSWSDLStatusSimpleIndexPolicyExecution    Unsigned32
}

dpStatusWSWSDLStatusSimpleIndexWSGateway OBJECT-TYPE
    SYNTAX      DisplayString
    MAX-ACCESS  read-only
    STATUS      current
    DESCRIPTION "No description yet."

    ::= { dpStatusWSWSDLStatusSimpleIndexEntry 1 }

dpStatusWSWSDLStatusSimpleIndexID OBJECT-TYPE
    SYNTAX      Unsigned32
    MAX-ACCESS  read-only
    STATUS      current
    DESCRIPTION "No description yet."

    ::= { dpStatusWSWSDLStatusSimpleIndexEntry 2 }

dpStatusWSWSDLStatusSimpleIndexWSDLSourceLocation OBJECT-TYPE
    SYNTAX      DisplayString
    MAX-ACCESS  read-only
    STATUS      current
    DESCRIPTION "No description yet."

    ::= { dpStatusWSWSDLStatusSimpleIndexEntry 3 }

dpStatusWSWSDLStatusSimpleIndexStatus OBJECT-TYPE
    SYNTAX      INTEGER { 
                        processing(1),
                        okay(2),
                        warning(3),
                        error(4)
                }
    MAX-ACCESS  read-only
    STATUS      current
    DESCRIPTION "No description yet."

    ::= { dpStatusWSWSDLStatusSimpleIndexEntry 4 }

dpStatusWSWSDLStatusSimpleIndexRefreshInterval OBJECT-TYPE
    SYNTAX      DPTimeIntervalSeconds
    UNITS       "seconds"
    MAX-ACCESS  read-only
    STATUS      current
    DESCRIPTION "No description yet."

    ::= { dpStatusWSWSDLStatusSimpleIndexEntry 5 }

dpStatusWSWSDLStatusSimpleIndexLastRefresh OBJECT-TYPE
    SYNTAX      TimeStamp
    MAX-ACCESS  read-only
    STATUS      current
    DESCRIPTION "No description yet."

    ::= { dpStatusWSWSDLStatusSimpleIndexEntry 6 }

dpStatusWSWSDLStatusSimpleIndexLog OBJECT-TYPE
    SYNTAX      DisplayString
    MAX-ACCESS  read-only
    STATUS      current
    DESCRIPTION "No description yet."

    ::= { dpStatusWSWSDLStatusSimpleIndexEntry 7 }

dpStatusWSWSDLStatusSimpleIndexPolicyExecution OBJECT-TYPE
    SYNTAX      Unsigned32
    MAX-ACCESS  read-only
    STATUS      current
    DESCRIPTION "No description yet."

    ::= { dpStatusWSWSDLStatusSimpleIndexEntry 8 }

--

dpStatusWebSphereJMSStatusTable OBJECT-TYPE
    SYNTAX      SEQUENCE OF DPStatusWebSphereJMSStatusEntry
    MAX-ACCESS  not-accessible
    STATUS      current
    DESCRIPTION "Table."

    ::= { dpStatus 107 }

dpStatusWebSphereJMSStatusEntry OBJECT-TYPE
    SYNTAX      DPStatusWebSphereJMSStatusEntry
    MAX-ACCESS  not-accessible
    STATUS      current
    DESCRIPTION "Table row."
    INDEX { IMPLIED dpConfigWebSphereJMSServerIndex }

    ::= { dpStatusWebSphereJMSStatusTable 1 }

DPStatusWebSphereJMSStatusEntry ::= SEQUENCE {
    dpStatusWebSphereJMSStatusServer    DisplayString,
    dpStatusWebSphereJMSStatusReceivedMessages    Unsigned32,
    dpStatusWebSphereJMSStatusSentMessages    Unsigned32,
    dpStatusWebSphereJMSStatusReceivedFaults    Unsigned32,
    dpStatusWebSphereJMSStatusSentFaults    Unsigned32
}

dpStatusWebSphereJMSStatusServer OBJECT-TYPE
    SYNTAX      DisplayString
    MAX-ACCESS  read-only
    STATUS      current
    DESCRIPTION "No description yet."

    ::= { dpStatusWebSphereJMSStatusEntry 1 }

dpStatusWebSphereJMSStatusReceivedMessages OBJECT-TYPE
    SYNTAX      Unsigned32
    MAX-ACCESS  read-only
    STATUS      current
    DESCRIPTION "No description yet."

    ::= { dpStatusWebSphereJMSStatusEntry 2 }

dpStatusWebSphereJMSStatusSentMessages OBJECT-TYPE
    SYNTAX      Unsigned32
    MAX-ACCESS  read-only
    STATUS      current
    DESCRIPTION "No description yet."

    ::= { dpStatusWebSphereJMSStatusEntry 3 }

dpStatusWebSphereJMSStatusReceivedFaults OBJECT-TYPE
    SYNTAX      Unsigned32
    MAX-ACCESS  read-only
    STATUS      current
    DESCRIPTION "No description yet."

    ::= { dpStatusWebSphereJMSStatusEntry 4 }

dpStatusWebSphereJMSStatusSentFaults OBJECT-TYPE
    SYNTAX      Unsigned32
    MAX-ACCESS  read-only
    STATUS      current
    DESCRIPTION "No description yet."

    ::= { dpStatusWebSphereJMSStatusEntry 5 }

--

dpStatusServicesStatusTable OBJECT-TYPE
    SYNTAX      SEQUENCE OF DPStatusServicesStatusEntry
    MAX-ACCESS  not-accessible
    STATUS      current
    DESCRIPTION
        "Status of active services."

    ::= { dpStatus 108 }

dpStatusServicesStatusEntry OBJECT-TYPE
    SYNTAX      DPStatusServicesStatusEntry
    MAX-ACCESS  not-accessible
    STATUS      current
    DESCRIPTION "Table row."
    INDEX { dpStatusServicesStatusLocalIP, dpStatusServicesStatusLocalPort, dpStatusServicesStatusServiceClass, IMPLIED dpStatusServicesStatusServiceName }

    ::= { dpStatusServicesStatusTable 1 }

DPStatusServicesStatusEntry ::= SEQUENCE {
    dpStatusServicesStatusLocalIP    IpAddress,
    dpStatusServicesStatusLocalPort    Unsigned32,
    dpStatusServicesStatusServiceClass    INTEGER,
    dpStatusServicesStatusServiceName    DisplayString
}

dpStatusServicesStatusLocalIP OBJECT-TYPE
    SYNTAX      IpAddress
    MAX-ACCESS  read-only
    STATUS      current
    DESCRIPTION
        "IP address being used by this service."

    ::= { dpStatusServicesStatusEntry 1 }

dpStatusServicesStatusLocalPort OBJECT-TYPE
    SYNTAX      Unsigned32 (0..65535)
    MAX-ACCESS  read-only
    STATUS      current
    DESCRIPTION
        "Port being used by this service."

    ::= { dpStatusServicesStatusEntry 2 }

dpStatusServicesStatusServiceClass OBJECT-TYPE
    SYNTAX      INTEGER { 
                        configBase(0),
                        dNSNameService(1),
                        ethernetInterface(2),
                        cRLFetch(3),
                        hTTPService(4),
                        statistics(5),
                        traceTarget(6),
                        nTPService(7),
                        throttler(8),
                        stylePolicy(9),
                        hTTPUserAgent(10),
                        tCPProxyService(12),
                        uRLMap(13),
                        uRLRefreshPolicy(14),
                        user(15),
                        networkSettings(16),
                        xMLManager(17),
                        mQQM(18),
                        xSLProxyService(19),
                        mQGW(20),
                        sSLProxyService(21),
                        stylePolicyRule(22),
                        errorReportSettings(23),
                        iPInterface(25),
                        matching(26),
                        systemSettings(27),
                        sNMPSettings(28),
                        rADIUSSettings(29),
                        userGroup(30),
                        shellAlias(31),
                        xSLCoprocService(32),
                        telnetService(33),
                        cryptoSSKey(34),
                        messageMonitor(35),
                        uRLRewritePolicy(36),
                        sSLProxyProfile(37),
                        hTTPProxyService(38),
                        service(39),
                        cryptoFWCred(41),
                        xMLFirewallService(42),
                        cryptoKey(43),
                        cryptoCertificate(44),
                        cryptoIdentCred(45),
                        cryptoValCred(46),
                        cryptoProfile(47),
                        logTarget(48),
                        sSHService(49),
                        crypto(50),
                        webGUI(51),
                        eventlog(52),
                        accessControl(53),
                        messageFlowControl(54),
                        mQConfiguration(55),
                        deviceSettings(56),
                        deviceManagementService(57),
                        networkConfiguration(58),
                        logLabel(59),
                        mgmtInterface(60),
                        messageMatching(61),
                        messageType(62),
                        countMonitor(63),
                        durationMonitor(64),
                        filterAction(65),
                        hTTPInputConversionMap(66),
                        compileOptionsPolicy(68),
                        xPathRoutingMap(69),
                        schemaExceptionMap(70),
                        reserved71(71),
                        documentCryptoMap(72),
                        tAM(73),
                        domain(74),
                        timeSettings(75),
                        dynamicXMLContentMap(77),
                        dynamicStylesheet(78),
                        dynamicSchema(79),
                        accessControlList(80),
                        importPackage(81),
                        mQhost(82),
                        mQproxy(83),
                        loadBalancerGroup(84),
                        rBMSettings(85),
                        includeConfig(86),
                        certMonitor(87),
                        hostAlias(88),
                        aAAPolicy(91),
                        stylePolicyAction(92),
                        cryptoKerberosKDC(93),
                        webServiceMonitor(94),
                        wSGateway(95),
                        stylePolicyRuleBase(96),
                        wSStylePolicyRule(97),
                        wSStylePolicy(98),
                        webServicesAgent(99),
                        gatewayBase(100),
                        multiProtocolGateway(101),
                        sourceProtocolHandler(102),
                        hTTPSourceProtocolHandler(103),
                        hTTPSSourceProtocolHandler(104),
                        mQSourceProtocolHandler(105),
                        xTCProtocolHandler(106),
                        cryptoKerberosKeytab(109),
                        statelessTCPSourceProtocolHandler(110),
                        sLMCredClass(111),
                        sLMRsrcClass(112),
                        sLMSchedule(113),
                        sLMAction(114),
                        sLMPolicy(115),
                        peerGroup(116),
                        reserved117(117),
                        tFIMEndpoint(118),
                        xmltrace(120),
                        nFSClientSettings(121),
                        wSEndpointRewritePolicy(122),
                        sQLDataSource(124),
                        nFSStaticMount(125),
                        nFSDynamicMounts(126),
                        webAppErrorHandlingPolicy(127),
                        simpleCountMonitor(128),
                        nameValueProfile(129),
                        webAppResponse(130),
                        webAppRequest(131),
                        webAppFW(132),
                        appSecurityPolicy(133),
                        uDDIRegistry(134),
                        webAppSessionPolicy(135),
                        jMSServer(136),
                        tibcoEMSServer(137),
                        tibcoEMSSourceProtocolHandler(138),
                        xACMLPDP(139),
                        jMSSourceProtocolHandler(140),
                        webSphereJMSServer(141),
                        webSphereJMSSourceProtocolHandler(142),
                        processingMetadata(143),
                        mTOMPolicy(144),
                        fTPServerSourceProtocolHandler(145),
                        filePollerSourceProtocolHandler(146),
                        nFSFilePollerSourceProtocolHandler(147),
                        fTPFilePollerSourceProtocolHandler(148),
                        fTPQuoteCommands(149),
                        mQQMBase(150),
                        mQQMGroup(151),
                        wSRRServer(152),
                        wSRRSubscription(153),
                        webServiceSubscription(154),
                        uDDISubscription(155),
                        vLANInterface(156),
                        conformancePolicy(157),
                        sOAPHeaderDisposition(158),
                        policyAttachments(159),
                        policyParameters(160),
                        iMSConnect(161),
                        iMSConnectSourceProtocolHandler(162),
                        lDAPSearchParameters(163),
                        configDeploymentPolicy(164),
                        compactFlash(165),
                        raidVolume(166),
                        iScsiInitiatorConfig(167),
                        lLMSourceProtocolHandler(168),
                        tRVSourceProtocolHandler(169),
                        iScsiHBAConfig(170),
                        iScsiTargetConfig(171),
                        iScsiVolumeConfig(172),
                        iScsiChapConfig(173),
                        zosNSSClient(174),
                        sSHServerSourceProtocolHandler(175),
                        fTPDemonSourceProtocolHandler(176),
                        aS3SourceProtocolHandler(177),
                        aS2SourceProtocolHandler(178),
                        b2BXPathRoutingPolicy(179),
                        lLMInstance(180),
                        lLMMulticastReceive(181),
                        lLMMulticastTransmit(182),
                        lLMUnicast(183),
                        lLMMulticastTierGroup(184),
                        lLMRoute(186),
                        lLMPolicy(187),
                        fibreChannelHBA(188),
                        fibreChannelTarget(189),
                        fibreChannelVolume(190),
                        webB2BViewer(192),
                        b2BPersistence(193),
                        b2BProfileGroup(194),
                        b2BGateway(195),
                        b2BProfile(196),
                        wCCService(197),
                        formsLoginPolicy(198),
                        tRVPolicy(199),
                        tRVRoute(200),
                        tRVTransport(201),
                        lLMPolicyBase(202),
                        lLMRouteBase(203),
                        pOPPollerSourceProtocolHandlerBase(204),
                        aS1PollerSourceProtocolHandler(205),
                        pOPPollerSourceProtocolHandler(206),
                        sMTPServerConnection(207),
                        xM70Persistence(208),
                        wSRRSavedSearchSubscription(209),
                        eBMS2SourceProtocolHandler(210),
                        sAMLAttributes(211),
                        sSHClientProfile(212),
                        sFTPFilePollerSourceProtocolHandler(213),
                        zHybridTargetControlService(214),
                        multipathService(215),
                        clusterService(216),
                        secureCloudConnector(217),
                        iPMILanChannel(218),
                        iPMIUser(219),
                        b2BCPACollaboration(220),
                        mQFTESourceProtocolHandler(221),
                        b2BCPA(222),
                        b2BCPASenderSetting(223),
                        b2BCPAReceiverSetting(224),
                        oAuthSupportedClient(225),
                        oAuthSupportedClientGroup(226),
                        sSLSNIServerProfile(227),
                        xC10Grid(235),
                        runtimeSettings(246),
                        sQLRuntimeSettings(247),
                        webApplicationGateway(248),
                        interopService(249),
                        oDRConnectorGroup(250),
                        oDR(251),
                        sSLClientProfile(253),
                        sSLServerProfile(254),
                        sSLSNIMapping(256),
                        webTokenService(266),
                        messageContentFilters(267),
                        mCFBase(268),
                        mCFHttpHeader(269),
                        mCFXPath(270),
                        mCFHttpURL(271),
                        mCFHttpMethod(272),
                        iMSCalloutSourceProtocolHandler(273),
                        pattern(274),
                        mCFCustomRule(275),
                        aS2ProxySourceProtocolHandler(277),
                        luna(278),
                        lunaPartition(279),
                        configSequence(280),
                        lunaHAGroup(285),
                        lunaHASettings(286),
                        wAXHNProxy(300),
                        hNApplication(301),
                        cloudGatewayService(302),
                        cloudConnectorService(303),
                        jSONSettings(308),
                        iPMulticast(309),
                        deploymentPolicyParametersBinding(310),
                        lDAPConnectionPool(311),
                        mPGWErrorHandlingPolicy(312),
                        mPGWErrorAction(313),
                        language(314),
                        domainAvailability(315),
                        generatedPolicy(316),
                        passwordMap(320),
                        aAAJWTValidator(321),
                        aAAJWTGenerator(322),
                        linkAggregation(333),
                        cookieAttributePolicy(334),
                        iSAMReverseProxy(335),
                        iSAMReverseProxyJunction(336),
                        iSAMRuntime(337),
                        passwordAlias(338),
                        auditLog(340),
                        jWERecipient(345),
                        jOSESignatureIdentifier(346),
                        jWSSignature(347),
                        jWEHeader(348),
                        jOSERecipientIdentifier(349),
                        secureGatewayClient(350),
                        cacheGrid(351),
                        wXSGrid(352),
                        domainSettings(353),
                        mQAUI(354),
                        gWScriptSettings(358),
                        aPICollection(359),
                        aPIGateway(360),
                        aPIDefinition(361),
                        aPIPath(362),
                        aPIOperation(363),
                        aPIPlan(364),
                        aPISecurityDefinition(365),
                        aPISecurityAPIKey(366),
                        aPISecurityOAuth(368),
                        aPISecurityRequirement(369),
                        controlList(370),
                        aPILDAPRegistry(371),
                        aPIRule(372),
                        aPISecurityOAuthReq(373),
                        gWSRemoteDebug(374),
                        mQAUIMFT(375),
                        assemblyActionUserSecurity(376),
                        aPISecurityBasicAuth(377),
                        aPISchema(378),
                        aPIUserRegistry(379),
                        aPIAuthURLRegistry(380),
                        assemblyActionClientSecurity(381),
                        restMgmtInterface(400),
                        secureBackupMode(402),
                        aPIConnectGatewayService(403),
                        standaloneStandbyControlInterface(450),
                        standaloneStandbyControl(451),
                        tenant(452),
                        socialLoginPolicy(455),
                        eBMS3SourceProtocolHandler(456),
                        dFDLSettings(460),
                        parseSettings(461),
                        accessProfile(462),
                        iLMTScanner(500),
                        quotaEnforcementServer(504),
                        sSHServerProfile(505),
                        quotaEnforcementMatchClass(506),
                        quotaEnforcementGroupClass(507),
                        quotaEnforcementAlgorithm(508),
                        quotaEnforcementSchedule(509),
                        sSHDomainClientProfile(510),
                        quotaEnforcementPolicyGroup(511),
                        quotaEnforcementPolicyBase(512),
                        quotaEnforcementAction(513),
                        quotaEnforcementPolicy(514),
                        gatewayPeering(526),
                        stylePolicyActionBase(600),
                        assemblyActionBase(601),
                        assemblyAction(602),
                        assemblyLogic(603),
                        aPIExecute(605),
                        aPIResult(607),
                        assemblyLogicSwitch(609),
                        assembly(610),
                        assemblyActionInvoke(611),
                        assemblyActionSetVar(612),
                        assemblyActionThrow(613),
                        aPIRouting(614),
                        aPISecurity(615),
                        aPIRateLimit(616),
                        assemblyActionXml2Json(617),
                        aPIAction(618),
                        assemblyActionXSLT(619),
                        assemblyActionGatewayScript(620),
                        aPIClientIdentification(621),
                        assemblyActionMap(622),
                        assemblyActionJWTValidate(623),
                        assemblyActionParse(624),
                        aPICORS(625),
                        operationRateLimit(626),
                        analyticsEndpoint(627),
                        assemblyActionJWTGenerate(628),
                        assemblyActionJson2Xml(629),
                        assemblyActionOAuth(630),
                        oAuthProviderSettings(640),
                        aPISecurityTokenManager(641),
                        assemblyActionValidate(642),
                        aPIDebugProbe(643),
                        aPIApplicationType(644),
                        assemblyFunction(645),
                        assemblyActionFunctionCall(646),
                        gatewayPeeringManager(648),
                        assemblyActionLog(649),
                        assemblyActionRateLimit(650),
                        assemblyActionRedact(651),
                        productInsights(850)
                }
    MAX-ACCESS  read-only
    STATUS      current
    DESCRIPTION
        "Type of service."

    ::= { dpStatusServicesStatusEntry 3 }

dpStatusServicesStatusServiceName OBJECT-TYPE
    SYNTAX      DisplayString
    MAX-ACCESS  read-only
    STATUS      current
    DESCRIPTION
        "Name of the service."

    ::= { dpStatusServicesStatusEntry 4 }

--

dpStatusWSOperationMetricsTable OBJECT-TYPE
    SYNTAX      SEQUENCE OF DPStatusWSOperationMetricsEntry
    MAX-ACCESS  not-accessible
    STATUS      obsolete
    DESCRIPTION
        "Common metrics for web service endpoints
        Note: this is obsoleted and is replaced by dpStatusWSOperationMetricsSimpleIndex as of release
    3.6.1"

    ::= { dpStatus 109 }

dpStatusWSOperationMetricsEntry OBJECT-TYPE
    SYNTAX      DPStatusWSOperationMetricsEntry
    MAX-ACCESS  not-accessible
    STATUS      obsolete
    DESCRIPTION "Table row."
    INDEX { dpStatusWSOperationMetricsServiceEndpoint, dpStatusWSOperationMetricsPortType, IMPLIED dpStatusWSOperationMetricsOperation }

    ::= { dpStatusWSOperationMetricsTable 1 }

DPStatusWSOperationMetricsEntry ::= SEQUENCE {
    dpStatusWSOperationMetricsServiceEndpoint    DisplayString,
    dpStatusWSOperationMetricsPortType    DisplayString,
    dpStatusWSOperationMetricsOperation    DisplayString,
    dpStatusWSOperationMetricsNumberOfRequests    Counter32,
    dpStatusWSOperationMetricsNumberOfFailedRequests    Counter32,
    dpStatusWSOperationMetricsNumberOfSuccessfulRequests    Counter32,
    dpStatusWSOperationMetricsServiceTime    DPTimeIntervalMillis,
    dpStatusWSOperationMetricsMaxResponseTime    DPTimeIntervalMillis,
    dpStatusWSOperationMetricsLastResponseTime    DPTimeIntervalMillis,
    dpStatusWSOperationMetricsMaxRequestSize    Unsigned32,
    dpStatusWSOperationMetricsLastRequestSize    Unsigned32,
    dpStatusWSOperationMetricsMaxResponseSize    Unsigned32,
    dpStatusWSOperationMetricsLastResponseSize    Unsigned32
}

dpStatusWSOperationMetricsServiceEndpoint OBJECT-TYPE
    SYNTAX      DisplayString
    MAX-ACCESS  read-only
    STATUS      obsolete
    DESCRIPTION "No description yet."

    ::= { dpStatusWSOperationMetricsEntry 1 }

dpStatusWSOperationMetricsPortType OBJECT-TYPE
    SYNTAX      DisplayString
    MAX-ACCESS  read-only
    STATUS      obsolete
    DESCRIPTION "No description yet."

    ::= { dpStatusWSOperationMetricsEntry 2 }

dpStatusWSOperationMetricsOperation OBJECT-TYPE
    SYNTAX      DisplayString
    MAX-ACCESS  read-only
    STATUS      obsolete
    DESCRIPTION "No description yet."

    ::= { dpStatusWSOperationMetricsEntry 3 }

dpStatusWSOperationMetricsNumberOfRequests OBJECT-TYPE
    SYNTAX      Counter32
    MAX-ACCESS  read-only
    STATUS      obsolete
    DESCRIPTION "No description yet."

    ::= { dpStatusWSOperationMetricsEntry 4 }

dpStatusWSOperationMetricsNumberOfFailedRequests OBJECT-TYPE
    SYNTAX      Counter32
    MAX-ACCESS  read-only
    STATUS      obsolete
    DESCRIPTION "No description yet."

    ::= { dpStatusWSOperationMetricsEntry 5 }

dpStatusWSOperationMetricsNumberOfSuccessfulRequests OBJECT-TYPE
    SYNTAX      Counter32
    MAX-ACCESS  read-only
    STATUS      obsolete
    DESCRIPTION "No description yet."

    ::= { dpStatusWSOperationMetricsEntry 6 }

dpStatusWSOperationMetricsServiceTime OBJECT-TYPE
    SYNTAX      DPTimeIntervalMillis
    UNITS       "msec"
    MAX-ACCESS  read-only
    STATUS      obsolete
    DESCRIPTION "No description yet."

    ::= { dpStatusWSOperationMetricsEntry 7 }

dpStatusWSOperationMetricsMaxResponseTime OBJECT-TYPE
    SYNTAX      DPTimeIntervalMillis
    UNITS       "msec"
    MAX-ACCESS  read-only
    STATUS      obsolete
    DESCRIPTION "No description yet."

    ::= { dpStatusWSOperationMetricsEntry 8 }

dpStatusWSOperationMetricsLastResponseTime OBJECT-TYPE
    SYNTAX      DPTimeIntervalMillis
    UNITS       "msec"
    MAX-ACCESS  read-only
    STATUS      obsolete
    DESCRIPTION "No description yet."

    ::= { dpStatusWSOperationMetricsEntry 9 }

dpStatusWSOperationMetricsMaxRequestSize OBJECT-TYPE
    SYNTAX      Unsigned32
    UNITS       "bytes"
    MAX-ACCESS  read-only
    STATUS      obsolete
    DESCRIPTION "No description yet."

    ::= { dpStatusWSOperationMetricsEntry 10 }

dpStatusWSOperationMetricsLastRequestSize OBJECT-TYPE
    SYNTAX      Unsigned32
    UNITS       "bytes"
    MAX-ACCESS  read-only
    STATUS      obsolete
    DESCRIPTION "No description yet."

    ::= { dpStatusWSOperationMetricsEntry 11 }

dpStatusWSOperationMetricsMaxResponseSize OBJECT-TYPE
    SYNTAX      Unsigned32
    UNITS       "bytes"
    MAX-ACCESS  read-only
    STATUS      obsolete
    DESCRIPTION "No description yet."

    ::= { dpStatusWSOperationMetricsEntry 12 }

dpStatusWSOperationMetricsLastResponseSize OBJECT-TYPE
    SYNTAX      Unsigned32
    UNITS       "bytes"
    MAX-ACCESS  read-only
    STATUS      obsolete
    DESCRIPTION "No description yet."

    ::= { dpStatusWSOperationMetricsEntry 13 }

--

dpStatusFilePollerStatusTable OBJECT-TYPE
    SYNTAX      SEQUENCE OF DPStatusFilePollerStatusEntry
    MAX-ACCESS  not-accessible
    STATUS      current
    DESCRIPTION
        "Status of all file pollers."

    ::= { dpStatus 110 }

dpStatusFilePollerStatusEntry OBJECT-TYPE
    SYNTAX      DPStatusFilePollerStatusEntry
    MAX-ACCESS  not-accessible
    STATUS      current
    DESCRIPTION "Table row."
    INDEX { dpStatusFilePollerStatusType, IMPLIED dpStatusFilePollerStatusName }

    ::= { dpStatusFilePollerStatusTable 1 }

DPStatusFilePollerStatusEntry ::= SEQUENCE {
    dpStatusFilePollerStatusType    INTEGER,
    dpStatusFilePollerStatusName    DisplayString,
    dpStatusFilePollerStatusTarget    DisplayString,
    dpStatusFilePollerStatusPollCount    Counter32,
    dpStatusFilePollerStatusTransactionsPerPoll    Counter32,
    dpStatusFilePollerStatusSeizedFiles    Counter32,
    dpStatusFilePollerStatusPollsWithOutTransactions    Counter32
}

dpStatusFilePollerStatusType OBJECT-TYPE
    SYNTAX      INTEGER { 
                        nfsFilePoller(1),
                        ftpFilePoller(2),
                        sftpFilePoller(3)
                }
    MAX-ACCESS  read-only
    STATUS      current
    DESCRIPTION
        "The type of file poller."

    ::= { dpStatusFilePollerStatusEntry 1 }

dpStatusFilePollerStatusName OBJECT-TYPE
    SYNTAX      DisplayString
    MAX-ACCESS  read-only
    STATUS      current
    DESCRIPTION
        "The name of the file poller."

    ::= { dpStatusFilePollerStatusEntry 2 }

dpStatusFilePollerStatusTarget OBJECT-TYPE
    SYNTAX      DisplayString
    MAX-ACCESS  read-only
    STATUS      current
    DESCRIPTION
        "The directory on the remote server to poll."

    ::= { dpStatusFilePollerStatusEntry 3 }

dpStatusFilePollerStatusPollCount OBJECT-TYPE
    SYNTAX      Counter32
    MAX-ACCESS  read-only
    STATUS      current
    DESCRIPTION
        "The number of times that the file handler polled the target directory."

    ::= { dpStatusFilePollerStatusEntry 4 }

dpStatusFilePollerStatusTransactionsPerPoll OBJECT-TYPE
    SYNTAX      Counter32
    MAX-ACCESS  read-only
    STATUS      current
    DESCRIPTION
        "The average number of transactions that the poll sequence started."

    ::= { dpStatusFilePollerStatusEntry 5 }

dpStatusFilePollerStatusSeizedFiles OBJECT-TYPE
    SYNTAX      Counter32
    MAX-ACCESS  read-only
    STATUS      current
    DESCRIPTION
        "The number of transactions that another poller started but this poller
        finished."

    ::= { dpStatusFilePollerStatusEntry 6 }

dpStatusFilePollerStatusPollsWithOutTransactions OBJECT-TYPE
    SYNTAX      Counter32
    MAX-ACCESS  read-only
    STATUS      current
    DESCRIPTION
        "The number of poll sequences that yielded no transactions."

    ::= { dpStatusFilePollerStatusEntry 7 }

--

dpStatusDynamicQueueManagerTable OBJECT-TYPE
    SYNTAX      SEQUENCE OF DPStatusDynamicQueueManagerEntry
    MAX-ACCESS  not-accessible
    STATUS      current
    DESCRIPTION
        "Status of the Dynamic IBM MQ queue manager."

    ::= { dpStatus 111 }

dpStatusDynamicQueueManagerEntry OBJECT-TYPE
    SYNTAX      DPStatusDynamicQueueManagerEntry
    MAX-ACCESS  not-accessible
    STATUS      current
    DESCRIPTION "Table row."
    INDEX { IMPLIED dpConfigMQQMIndex }

    ::= { dpStatusDynamicQueueManagerTable 1 }

DPStatusDynamicQueueManagerEntry ::= SEQUENCE {
    dpStatusDynamicQueueManagerQueueManager    DisplayString,
    dpStatusDynamicQueueManagerConnections    Unsigned32,
    dpStatusDynamicQueueManagerReceivedMessages    Unsigned32,
    dpStatusDynamicQueueManagerSentMessages    Unsigned32,
    dpStatusDynamicQueueManagerReceiveFaults    Unsigned32,
    dpStatusDynamicQueueManagerSendFaults    Unsigned32
}

dpStatusDynamicQueueManagerQueueManager OBJECT-TYPE
    SYNTAX      DisplayString
    MAX-ACCESS  read-only
    STATUS      current
    DESCRIPTION
        "Name of the Dynamic IBM MQ queue manager."

    ::= { dpStatusDynamicQueueManagerEntry 1 }

dpStatusDynamicQueueManagerConnections OBJECT-TYPE
    SYNTAX      Unsigned32
    MAX-ACCESS  read-only
    STATUS      current
    DESCRIPTION
        "Number of connections established."

    ::= { dpStatusDynamicQueueManagerEntry 2 }

dpStatusDynamicQueueManagerReceivedMessages OBJECT-TYPE
    SYNTAX      Unsigned32
    MAX-ACCESS  read-only
    STATUS      current
    DESCRIPTION
        "Number of messages received by this queue manager."

    ::= { dpStatusDynamicQueueManagerEntry 3 }

dpStatusDynamicQueueManagerSentMessages OBJECT-TYPE
    SYNTAX      Unsigned32
    MAX-ACCESS  read-only
    STATUS      current
    DESCRIPTION
        "Number of messages sent by this queue manager."

    ::= { dpStatusDynamicQueueManagerEntry 4 }

dpStatusDynamicQueueManagerReceiveFaults OBJECT-TYPE
    SYNTAX      Unsigned32
    MAX-ACCESS  read-only
    STATUS      current
    DESCRIPTION
        "Number of errors detected by this queue manager during receive operations."

    ::= { dpStatusDynamicQueueManagerEntry 5 }

dpStatusDynamicQueueManagerSendFaults OBJECT-TYPE
    SYNTAX      Unsigned32
    MAX-ACCESS  read-only
    STATUS      current
    DESCRIPTION
        "Number of errors detected by this queue manager during send operations."

    ::= { dpStatusDynamicQueueManagerEntry 6 }

dpStatusFirmwareVersion OBJECT IDENTIFIER ::= { dpStatus 112 }

dpStatusFirmwareVersionSerial OBJECT-TYPE
    SYNTAX      DisplayString
    MAX-ACCESS  read-only
    STATUS      deprecated
    DESCRIPTION
        "The serial number of the appliance. This number is unique to each
        appliance."

    ::= { dpStatusFirmwareVersion 1 }

dpStatusFirmwareVersionVersion OBJECT-TYPE
    SYNTAX      DisplayString
    MAX-ACCESS  read-only
    STATUS      deprecated
    DESCRIPTION
        "The version of the firmware."

    ::= { dpStatusFirmwareVersion 2 }

dpStatusFirmwareVersionBuild OBJECT-TYPE
    SYNTAX      DisplayString
    MAX-ACCESS  read-only
    STATUS      deprecated
    DESCRIPTION
        "The build number of the firmware."

    ::= { dpStatusFirmwareVersion 3 }

dpStatusFirmwareVersionBuildDate OBJECT-TYPE
    SYNTAX      DisplayString
    MAX-ACCESS  read-only
    STATUS      deprecated
    DESCRIPTION
        "The date on which the firmware was built."

    ::= { dpStatusFirmwareVersion 4 }

dpStatusFirmwareVersionWatchdogBuild OBJECT-TYPE
    SYNTAX      DisplayString
    MAX-ACCESS  read-only
    STATUS      deprecated
    DESCRIPTION
        "The build number of the system health monitor."

    ::= { dpStatusFirmwareVersion 5 }

dpStatusFirmwareVersionInstalledDPOS OBJECT-TYPE
    SYNTAX      DisplayString
    MAX-ACCESS  read-only
    STATUS      deprecated
    DESCRIPTION
        "The version number of the DataPower appliance manager."

    ::= { dpStatusFirmwareVersion 6 }

dpStatusFirmwareVersionRunningDPOS OBJECT-TYPE
    SYNTAX      DisplayString
    MAX-ACCESS  read-only
    STATUS      deprecated
    DESCRIPTION
        "The version number of the DataPower appliance manager."

    ::= { dpStatusFirmwareVersion 7 }

dpStatusFirmwareVersionXMLAccelerator OBJECT-TYPE
    SYNTAX      DisplayString
    MAX-ACCESS  read-only
    STATUS      deprecated
    DESCRIPTION
        "The type of XML accelerator."

    ::= { dpStatusFirmwareVersion 8 }

dpStatusFirmwareVersionMachineType OBJECT-TYPE
    SYNTAX      DisplayString
    MAX-ACCESS  read-only
    STATUS      deprecated
    DESCRIPTION
        "The IBM machine type of the appliance."

    ::= { dpStatusFirmwareVersion 9 }

dpStatusFirmwareVersionModelType OBJECT-TYPE
    SYNTAX      DisplayString
    MAX-ACCESS  read-only
    STATUS      deprecated
    DESCRIPTION
        "The IBM model type of the appliance."

    ::= { dpStatusFirmwareVersion 10 }

dpStatusFirmwareVersionTenant OBJECT-TYPE
    SYNTAX      DisplayString
    MAX-ACCESS  read-only
    STATUS      deprecated
    DESCRIPTION
        "The name of DP tenant, '--' for drouter-0 (a.k.a. 'landlord')."

    ::= { dpStatusFirmwareVersion 11 }

--

dpStatusUDDISubscriptionStatusSimpleIndexTable OBJECT-TYPE
    SYNTAX      SEQUENCE OF DPStatusUDDISubscriptionStatusSimpleIndexEntry
    MAX-ACCESS  not-accessible
    STATUS      current
    DESCRIPTION "Table."

    ::= { dpStatus 113 }

dpStatusUDDISubscriptionStatusSimpleIndexEntry OBJECT-TYPE
    SYNTAX      DPStatusUDDISubscriptionStatusSimpleIndexEntry
    MAX-ACCESS  not-accessible
    STATUS      current
    DESCRIPTION "Table row."
    INDEX { IMPLIED dpConfigUDDISubscriptionIndex }

    ::= { dpStatusUDDISubscriptionStatusSimpleIndexTable 1 }

DPStatusUDDISubscriptionStatusSimpleIndexEntry ::= SEQUENCE {
    dpStatusUDDISubscriptionStatusSimpleIndexSubscription    DisplayString,
    dpStatusUDDISubscriptionStatusSimpleIndexServicesStatus    INTEGER,
    dpStatusUDDISubscriptionStatusSimpleIndexSubscriptionStatus    INTEGER,
    dpStatusUDDISubscriptionStatusSimpleIndexServices    Unsigned32,
    dpStatusUDDISubscriptionStatusSimpleIndexServicesAdded    Unsigned32,
    dpStatusUDDISubscriptionStatusSimpleIndexServicesDeleted    Unsigned32,
    dpStatusUDDISubscriptionStatusSimpleIndexServicesModified    Unsigned32
}

dpStatusUDDISubscriptionStatusSimpleIndexSubscription OBJECT-TYPE
    SYNTAX      DisplayString
    MAX-ACCESS  read-only
    STATUS      current
    DESCRIPTION "No description yet."

    ::= { dpStatusUDDISubscriptionStatusSimpleIndexEntry 1 }

dpStatusUDDISubscriptionStatusSimpleIndexServicesStatus OBJECT-TYPE
    SYNTAX      INTEGER { 
                        okay(1),
                        missingWSDL(2)
                }
    MAX-ACCESS  read-only
    STATUS      current
    DESCRIPTION "No description yet."

    ::= { dpStatusUDDISubscriptionStatusSimpleIndexEntry 2 }

dpStatusUDDISubscriptionStatusSimpleIndexSubscriptionStatus OBJECT-TYPE
    SYNTAX      INTEGER { 
                        initializing(1),
                        okay(2),
                        error(3)
                }
    MAX-ACCESS  read-only
    STATUS      current
    DESCRIPTION "No description yet."

    ::= { dpStatusUDDISubscriptionStatusSimpleIndexEntry 3 }

dpStatusUDDISubscriptionStatusSimpleIndexServices OBJECT-TYPE
    SYNTAX      Unsigned32
    MAX-ACCESS  read-only
    STATUS      current
    DESCRIPTION "No description yet."

    ::= { dpStatusUDDISubscriptionStatusSimpleIndexEntry 4 }

dpStatusUDDISubscriptionStatusSimpleIndexServicesAdded OBJECT-TYPE
    SYNTAX      Unsigned32
    MAX-ACCESS  read-only
    STATUS      current
    DESCRIPTION "No description yet."

    ::= { dpStatusUDDISubscriptionStatusSimpleIndexEntry 5 }

dpStatusUDDISubscriptionStatusSimpleIndexServicesDeleted OBJECT-TYPE
    SYNTAX      Unsigned32
    MAX-ACCESS  read-only
    STATUS      current
    DESCRIPTION "No description yet."

    ::= { dpStatusUDDISubscriptionStatusSimpleIndexEntry 6 }

dpStatusUDDISubscriptionStatusSimpleIndexServicesModified OBJECT-TYPE
    SYNTAX      Unsigned32
    MAX-ACCESS  read-only
    STATUS      current
    DESCRIPTION "No description yet."

    ::= { dpStatusUDDISubscriptionStatusSimpleIndexEntry 7 }

--

dpStatusUDDISubscriptionKeyStatusSimpleIndexTable OBJECT-TYPE
    SYNTAX      SEQUENCE OF DPStatusUDDISubscriptionKeyStatusSimpleIndexEntry
    MAX-ACCESS  not-accessible
    STATUS      current
    DESCRIPTION "Table."

    ::= { dpStatus 114 }

dpStatusUDDISubscriptionKeyStatusSimpleIndexEntry OBJECT-TYPE
    SYNTAX      DPStatusUDDISubscriptionKeyStatusSimpleIndexEntry
    MAX-ACCESS  not-accessible
    STATUS      current
    DESCRIPTION "Table row."
    INDEX { dpConfigUDDISubscriptionIndex, IMPLIED dpStatusUDDISubscriptionKeyStatusSimpleIndexSubscriptionKey }

    ::= { dpStatusUDDISubscriptionKeyStatusSimpleIndexTable 1 }

DPStatusUDDISubscriptionKeyStatusSimpleIndexEntry ::= SEQUENCE {
    dpStatusUDDISubscriptionKeyStatusSimpleIndexSubscription    DisplayString,
    dpStatusUDDISubscriptionKeyStatusSimpleIndexSubscriptionKey    DisplayString,
    dpStatusUDDISubscriptionKeyStatusSimpleIndexStatus    INTEGER,
    dpStatusUDDISubscriptionKeyStatusSimpleIndexLastCoverageStart    TimeStamp,
    dpStatusUDDISubscriptionKeyStatusSimpleIndexLastCoverageEnd    TimeStamp,
    dpStatusUDDISubscriptionKeyStatusSimpleIndexLastRequest    TimeStamp,
    dpStatusUDDISubscriptionKeyStatusSimpleIndexNotifyInterval    DPTimeIntervalSeconds
}

dpStatusUDDISubscriptionKeyStatusSimpleIndexSubscription OBJECT-TYPE
    SYNTAX      DisplayString
    MAX-ACCESS  read-only
    STATUS      current
    DESCRIPTION "No description yet."

    ::= { dpStatusUDDISubscriptionKeyStatusSimpleIndexEntry 1 }

dpStatusUDDISubscriptionKeyStatusSimpleIndexSubscriptionKey OBJECT-TYPE
    SYNTAX      DisplayString
    MAX-ACCESS  read-only
    STATUS      current
    DESCRIPTION "No description yet."

    ::= { dpStatusUDDISubscriptionKeyStatusSimpleIndexEntry 2 }

dpStatusUDDISubscriptionKeyStatusSimpleIndexStatus OBJECT-TYPE
    SYNTAX      INTEGER { 
                        initializing(1),
                        okay(2),
                        error(3)
                }
    MAX-ACCESS  read-only
    STATUS      current
    DESCRIPTION
        "Status of last update"

    ::= { dpStatusUDDISubscriptionKeyStatusSimpleIndexEntry 3 }

dpStatusUDDISubscriptionKeyStatusSimpleIndexLastCoverageStart OBJECT-TYPE
    SYNTAX      TimeStamp
    MAX-ACCESS  read-only
    STATUS      current
    DESCRIPTION "No description yet."

    ::= { dpStatusUDDISubscriptionKeyStatusSimpleIndexEntry 4 }

dpStatusUDDISubscriptionKeyStatusSimpleIndexLastCoverageEnd OBJECT-TYPE
    SYNTAX      TimeStamp
    MAX-ACCESS  read-only
    STATUS      current
    DESCRIPTION "No description yet."

    ::= { dpStatusUDDISubscriptionKeyStatusSimpleIndexEntry 5 }

dpStatusUDDISubscriptionKeyStatusSimpleIndexLastRequest OBJECT-TYPE
    SYNTAX      TimeStamp
    MAX-ACCESS  read-only
    STATUS      current
    DESCRIPTION "No description yet."

    ::= { dpStatusUDDISubscriptionKeyStatusSimpleIndexEntry 6 }

dpStatusUDDISubscriptionKeyStatusSimpleIndexNotifyInterval OBJECT-TYPE
    SYNTAX      DPTimeIntervalSeconds
    MAX-ACCESS  read-only
    STATUS      current
    DESCRIPTION "No description yet."

    ::= { dpStatusUDDISubscriptionKeyStatusSimpleIndexEntry 7 }

--

dpStatusUDDISubscriptionServiceStatusSimpleIndexTable OBJECT-TYPE
    SYNTAX      SEQUENCE OF DPStatusUDDISubscriptionServiceStatusSimpleIndexEntry
    MAX-ACCESS  not-accessible
    STATUS      current
    DESCRIPTION "Table."

    ::= { dpStatus 115 }

dpStatusUDDISubscriptionServiceStatusSimpleIndexEntry OBJECT-TYPE
    SYNTAX      DPStatusUDDISubscriptionServiceStatusSimpleIndexEntry
    MAX-ACCESS  not-accessible
    STATUS      current
    DESCRIPTION "Table row."
    INDEX { dpConfigUDDISubscriptionIndex, dpStatusUDDISubscriptionServiceStatusSimpleIndexServiceKey, dpStatusUDDISubscriptionServiceStatusSimpleIndexEndPoint, dpStatusUDDISubscriptionServiceStatusSimpleIndexServiceName, dpStatusUDDISubscriptionServiceStatusSimpleIndexPortName, dpStatusUDDISubscriptionServiceStatusSimpleIndexWSDLKey, IMPLIED dpStatusUDDISubscriptionServiceStatusSimpleIndexWSDLURL }

    ::= { dpStatusUDDISubscriptionServiceStatusSimpleIndexTable 1 }

DPStatusUDDISubscriptionServiceStatusSimpleIndexEntry ::= SEQUENCE {
    dpStatusUDDISubscriptionServiceStatusSimpleIndexSubscription    DisplayString,
    dpStatusUDDISubscriptionServiceStatusSimpleIndexServiceKey    DisplayString,
    dpStatusUDDISubscriptionServiceStatusSimpleIndexStatus    INTEGER,
    dpStatusUDDISubscriptionServiceStatusSimpleIndexEndPoint    DisplayString,
    dpStatusUDDISubscriptionServiceStatusSimpleIndexServiceName    DisplayString,
    dpStatusUDDISubscriptionServiceStatusSimpleIndexPortName    DisplayString,
    dpStatusUDDISubscriptionServiceStatusSimpleIndexNamespace    DisplayString,
    dpStatusUDDISubscriptionServiceStatusSimpleIndexWSDLKey    DisplayString,
    dpStatusUDDISubscriptionServiceStatusSimpleIndexWSDLURL    DisplayString,
    dpStatusUDDISubscriptionServiceStatusSimpleIndexBindingName    DisplayString,
    dpStatusUDDISubscriptionServiceStatusSimpleIndexBindingNamespace    DisplayString
}

dpStatusUDDISubscriptionServiceStatusSimpleIndexSubscription OBJECT-TYPE
    SYNTAX      DisplayString
    MAX-ACCESS  read-only
    STATUS      current
    DESCRIPTION "No description yet."

    ::= { dpStatusUDDISubscriptionServiceStatusSimpleIndexEntry 1 }

dpStatusUDDISubscriptionServiceStatusSimpleIndexServiceKey OBJECT-TYPE
    SYNTAX      DisplayString
    MAX-ACCESS  read-only
    STATUS      current
    DESCRIPTION "No description yet."

    ::= { dpStatusUDDISubscriptionServiceStatusSimpleIndexEntry 2 }

dpStatusUDDISubscriptionServiceStatusSimpleIndexStatus OBJECT-TYPE
    SYNTAX      INTEGER { 
                        okay(1),
                        missingWSDL(2)
                }
    MAX-ACCESS  read-only
    STATUS      current
    DESCRIPTION "No description yet."

    ::= { dpStatusUDDISubscriptionServiceStatusSimpleIndexEntry 3 }

dpStatusUDDISubscriptionServiceStatusSimpleIndexEndPoint OBJECT-TYPE
    SYNTAX      DisplayString
    MAX-ACCESS  read-only
    STATUS      current
    DESCRIPTION "No description yet."

    ::= { dpStatusUDDISubscriptionServiceStatusSimpleIndexEntry 4 }

dpStatusUDDISubscriptionServiceStatusSimpleIndexServiceName OBJECT-TYPE
    SYNTAX      DisplayString
    MAX-ACCESS  read-only
    STATUS      current
    DESCRIPTION "No description yet."

    ::= { dpStatusUDDISubscriptionServiceStatusSimpleIndexEntry 5 }

dpStatusUDDISubscriptionServiceStatusSimpleIndexPortName OBJECT-TYPE
    SYNTAX      DisplayString
    MAX-ACCESS  read-only
    STATUS      current
    DESCRIPTION "No description yet."

    ::= { dpStatusUDDISubscriptionServiceStatusSimpleIndexEntry 6 }

dpStatusUDDISubscriptionServiceStatusSimpleIndexNamespace OBJECT-TYPE
    SYNTAX      DisplayString
    MAX-ACCESS  read-only
    STATUS      current
    DESCRIPTION "No description yet."

    ::= { dpStatusUDDISubscriptionServiceStatusSimpleIndexEntry 7 }

dpStatusUDDISubscriptionServiceStatusSimpleIndexWSDLKey OBJECT-TYPE
    SYNTAX      DisplayString
    MAX-ACCESS  read-only
    STATUS      current
    DESCRIPTION "No description yet."

    ::= { dpStatusUDDISubscriptionServiceStatusSimpleIndexEntry 8 }

dpStatusUDDISubscriptionServiceStatusSimpleIndexWSDLURL OBJECT-TYPE
    SYNTAX      DisplayString
    MAX-ACCESS  read-only
    STATUS      current
    DESCRIPTION "No description yet."

    ::= { dpStatusUDDISubscriptionServiceStatusSimpleIndexEntry 9 }

dpStatusUDDISubscriptionServiceStatusSimpleIndexBindingName OBJECT-TYPE
    SYNTAX      DisplayString
    MAX-ACCESS  read-only
    STATUS      current
    DESCRIPTION "No description yet."

    ::= { dpStatusUDDISubscriptionServiceStatusSimpleIndexEntry 10 }

dpStatusUDDISubscriptionServiceStatusSimpleIndexBindingNamespace OBJECT-TYPE
    SYNTAX      DisplayString
    MAX-ACCESS  read-only
    STATUS      current
    DESCRIPTION "No description yet."

    ::= { dpStatusUDDISubscriptionServiceStatusSimpleIndexEntry 11 }

--

dpStatusLibraryVersionTable OBJECT-TYPE
    SYNTAX      SEQUENCE OF DPStatusLibraryVersionEntry
    MAX-ACCESS  not-accessible
    STATUS      current
    DESCRIPTION
        "Version information of installed libraries."

    ::= { dpStatus 116 }

dpStatusLibraryVersionEntry OBJECT-TYPE
    SYNTAX      DPStatusLibraryVersionEntry
    MAX-ACCESS  not-accessible
    STATUS      current
    DESCRIPTION "Table row."
    INDEX { IMPLIED dpStatusLibraryVersionLibrary }

    ::= { dpStatusLibraryVersionTable 1 }

DPStatusLibraryVersionEntry ::= SEQUENCE {
    dpStatusLibraryVersionLibrary    DisplayString,
    dpStatusLibraryVersionVersion    DisplayString
}

dpStatusLibraryVersionLibrary OBJECT-TYPE
    SYNTAX      DisplayString
    MAX-ACCESS  read-only
    STATUS      current
    DESCRIPTION
        "The name of the library."

    ::= { dpStatusLibraryVersionEntry 1 }

dpStatusLibraryVersionVersion OBJECT-TYPE
    SYNTAX      DisplayString
    MAX-ACCESS  read-only
    STATUS      current
    DESCRIPTION
        "The version of the library."

    ::= { dpStatusLibraryVersionEntry 2 }

--

dpStatusWSRRSubscriptionStatusTable OBJECT-TYPE
    SYNTAX      SEQUENCE OF DPStatusWSRRSubscriptionStatusEntry
    MAX-ACCESS  not-accessible
    STATUS      current
    DESCRIPTION "Table."

    ::= { dpStatus 117 }

dpStatusWSRRSubscriptionStatusEntry OBJECT-TYPE
    SYNTAX      DPStatusWSRRSubscriptionStatusEntry
    MAX-ACCESS  not-accessible
    STATUS      current
    DESCRIPTION "Table row."
    INDEX { IMPLIED dpConfigWSRRSubscriptionIndex }

    ::= { dpStatusWSRRSubscriptionStatusTable 1 }

DPStatusWSRRSubscriptionStatusEntry ::= SEQUENCE {
    dpStatusWSRRSubscriptionStatusSubscription    DisplayString,
    dpStatusWSRRSubscriptionStatusStatus    INTEGER,
    dpStatusWSRRSubscriptionStatusLastRefresh    TimeStamp,
    dpStatusWSRRSubscriptionStatusMethod    INTEGER,
    dpStatusWSRRSubscriptionStatusRefreshInterval    DPTimeIntervalSeconds,
    dpStatusWSRRSubscriptionStatusCount    Unsigned32,
    dpStatusWSRRSubscriptionStatusServiceVersionCount    Unsigned32
}

dpStatusWSRRSubscriptionStatusSubscription OBJECT-TYPE
    SYNTAX      DisplayString
    MAX-ACCESS  read-only
    STATUS      current
    DESCRIPTION
        "Name of the subscription object."

    ::= { dpStatusWSRRSubscriptionStatusEntry 1 }

dpStatusWSRRSubscriptionStatusStatus OBJECT-TYPE
    SYNTAX      INTEGER { 
                        okay(1),
                        error(2),
                        synchronizing(3)
                }
    MAX-ACCESS  read-only
    STATUS      current
    DESCRIPTION
        "Status of the subscription."

    ::= { dpStatusWSRRSubscriptionStatusEntry 2 }

dpStatusWSRRSubscriptionStatusLastRefresh OBJECT-TYPE
    SYNTAX      TimeStamp
    MAX-ACCESS  read-only
    STATUS      current
    DESCRIPTION
        "Timestamp of the last synchronization with the Service Registry. Use the
        Synchronize button to immediately refresh the subscription."

    ::= { dpStatusWSRRSubscriptionStatusEntry 3 }

dpStatusWSRRSubscriptionStatusMethod OBJECT-TYPE
    SYNTAX      INTEGER { 
                        manual(1),
                        poll(2),
                        automatic(3)
                }
    MAX-ACCESS  read-only
    STATUS      current
    DESCRIPTION
        "Method to keep WSRR subscription up-to-date."

    ::= { dpStatusWSRRSubscriptionStatusEntry 4 }

dpStatusWSRRSubscriptionStatusRefreshInterval OBJECT-TYPE
    SYNTAX      DPTimeIntervalSeconds
    MAX-ACCESS  read-only
    STATUS      current
    DESCRIPTION
        "Auto-refresh interval."

    ::= { dpStatusWSRRSubscriptionStatusEntry 5 }

dpStatusWSRRSubscriptionStatusCount OBJECT-TYPE
    SYNTAX      Unsigned32
    MAX-ACCESS  read-only
    STATUS      current
    DESCRIPTION
        "Number of WSDLs found in the Registry for this subscription. See WSRR
        Subscription Service Status screen for more information about individual
        WSDLs."

    ::= { dpStatusWSRRSubscriptionStatusEntry 6 }

dpStatusWSRRSubscriptionStatusServiceVersionCount OBJECT-TYPE
    SYNTAX      Unsigned32
    MAX-ACCESS  read-only
    STATUS      current
    DESCRIPTION
        "Number of Service Versions found in the Registry for this subscription."

    ::= { dpStatusWSRRSubscriptionStatusEntry 7 }

--

dpStatusWSRRSubscriptionServiceStatusTable OBJECT-TYPE
    SYNTAX      SEQUENCE OF DPStatusWSRRSubscriptionServiceStatusEntry
    MAX-ACCESS  not-accessible
    STATUS      current
    DESCRIPTION "Table."

    ::= { dpStatus 118 }

dpStatusWSRRSubscriptionServiceStatusEntry OBJECT-TYPE
    SYNTAX      DPStatusWSRRSubscriptionServiceStatusEntry
    MAX-ACCESS  not-accessible
    STATUS      current
    DESCRIPTION "Table row."
    INDEX { dpConfigWSRRSubscriptionIndex, IMPLIED dpStatusWSRRSubscriptionServiceStatusBsrURI }

    ::= { dpStatusWSRRSubscriptionServiceStatusTable 1 }

DPStatusWSRRSubscriptionServiceStatusEntry ::= SEQUENCE {
    dpStatusWSRRSubscriptionServiceStatusSubscription    DisplayString,
    dpStatusWSRRSubscriptionServiceStatusBsrURI    DisplayString,
    dpStatusWSRRSubscriptionServiceStatusWSDLName    DisplayString,
    dpStatusWSRRSubscriptionServiceStatusLocation    DisplayString,
    dpStatusWSRRSubscriptionServiceStatusDescription    DisplayString,
    dpStatusWSRRSubscriptionServiceStatusVersion    DisplayString
}

dpStatusWSRRSubscriptionServiceStatusSubscription OBJECT-TYPE
    SYNTAX      DisplayString
    MAX-ACCESS  read-only
    STATUS      current
    DESCRIPTION
        "Name of the subscription object."

    ::= { dpStatusWSRRSubscriptionServiceStatusEntry 1 }

dpStatusWSRRSubscriptionServiceStatusBsrURI OBJECT-TYPE
    SYNTAX      DisplayString
    MAX-ACCESS  read-only
    STATUS      current
    DESCRIPTION
        "Document identifier assigned by WSRR."

    ::= { dpStatusWSRRSubscriptionServiceStatusEntry 2 }

dpStatusWSRRSubscriptionServiceStatusWSDLName OBJECT-TYPE
    SYNTAX      DisplayString
    MAX-ACCESS  read-only
    STATUS      current
    DESCRIPTION "No description yet."

    ::= { dpStatusWSRRSubscriptionServiceStatusEntry 3 }

dpStatusWSRRSubscriptionServiceStatusLocation OBJECT-TYPE
    SYNTAX      DisplayString
    MAX-ACCESS  read-only
    STATUS      current
    DESCRIPTION
        "The location value assigned by WSRR. Typically, the value is the file
        name."

    ::= { dpStatusWSRRSubscriptionServiceStatusEntry 4 }

dpStatusWSRRSubscriptionServiceStatusDescription OBJECT-TYPE
    SYNTAX      DisplayString
    MAX-ACCESS  read-only
    STATUS      current
    DESCRIPTION
        "The file or resource description assigned by WSRR."

    ::= { dpStatusWSRRSubscriptionServiceStatusEntry 5 }

dpStatusWSRRSubscriptionServiceStatusVersion OBJECT-TYPE
    SYNTAX      DisplayString
    MAX-ACCESS  read-only
    STATUS      current
    DESCRIPTION
        "The version description assigned by WSRR."

    ::= { dpStatusWSRRSubscriptionServiceStatusEntry 6 }

--

dpStatusDomainCheckpointStatusTable OBJECT-TYPE
    SYNTAX      SEQUENCE OF DPStatusDomainCheckpointStatusEntry
    MAX-ACCESS  not-accessible
    STATUS      current
    DESCRIPTION
        "A configuration checkpoint contains configuration data from a specific
        point in time. You can use configuration checkpoints to return to the
        configuration that was in place at the time that the checkpoint was
        created. Each checkpoint is uniquely identified by its name, date and
        time. The checkpoints are stored in the chkpoints: directory."

    ::= { dpStatus 119 }

dpStatusDomainCheckpointStatusEntry OBJECT-TYPE
    SYNTAX      DPStatusDomainCheckpointStatusEntry
    MAX-ACCESS  not-accessible
    STATUS      current
    DESCRIPTION "Table row."
    INDEX { dpStatusDomainCheckpointStatusDate, dpStatusDomainCheckpointStatusTime }

    ::= { dpStatusDomainCheckpointStatusTable 1 }

DPStatusDomainCheckpointStatusEntry ::= SEQUENCE {
    dpStatusDomainCheckpointStatusDate    DisplayString,
    dpStatusDomainCheckpointStatusTime    Unsigned32,
    dpStatusDomainCheckpointStatusChkName    DisplayString
}

dpStatusDomainCheckpointStatusDate OBJECT-TYPE
    SYNTAX      DisplayString
    MAX-ACCESS  read-only
    STATUS      current
    DESCRIPTION
        "The date on which this configuration checkpoint was saved."

    ::= { dpStatusDomainCheckpointStatusEntry 1 }

dpStatusDomainCheckpointStatusTime OBJECT-TYPE
    SYNTAX      Unsigned32
    MAX-ACCESS  read-only
    STATUS      current
    DESCRIPTION
        "The time at which this configuration checkpoint was saved."

    ::= { dpStatusDomainCheckpointStatusEntry 2 }

dpStatusDomainCheckpointStatusChkName OBJECT-TYPE
    SYNTAX      DisplayString
    MAX-ACCESS  read-only
    STATUS      current
    DESCRIPTION
        "The name of this configuration checkpoint."

    ::= { dpStatusDomainCheckpointStatusEntry 3 }

--

dpStatusWSRRSubscriptionPolicyAttachmentsStatusTable OBJECT-TYPE
    SYNTAX      SEQUENCE OF DPStatusWSRRSubscriptionPolicyAttachmentsStatusEntry
    MAX-ACCESS  not-accessible
    STATUS      current
    DESCRIPTION "Table."

    ::= { dpStatus 120 }

dpStatusWSRRSubscriptionPolicyAttachmentsStatusEntry OBJECT-TYPE
    SYNTAX      DPStatusWSRRSubscriptionPolicyAttachmentsStatusEntry
    MAX-ACCESS  not-accessible
    STATUS      current
    DESCRIPTION "Table row."
    INDEX { dpConfigWSRRSubscriptionIndex, IMPLIED dpStatusWSRRSubscriptionPolicyAttachmentsStatusAttachmentPoint }

    ::= { dpStatusWSRRSubscriptionPolicyAttachmentsStatusTable 1 }

DPStatusWSRRSubscriptionPolicyAttachmentsStatusEntry ::= SEQUENCE {
    dpStatusWSRRSubscriptionPolicyAttachmentsStatusSubscription    DisplayString,
    dpStatusWSRRSubscriptionPolicyAttachmentsStatusAttachmentPoint    DisplayString,
    dpStatusWSRRSubscriptionPolicyAttachmentsStatusAttachmentURLs    DisplayString
}

dpStatusWSRRSubscriptionPolicyAttachmentsStatusSubscription OBJECT-TYPE
    SYNTAX      DisplayString
    MAX-ACCESS  read-only
    STATUS      current
    DESCRIPTION
        "The name of the WSRR saved search subscription."

    ::= { dpStatusWSRRSubscriptionPolicyAttachmentsStatusEntry 1 }

dpStatusWSRRSubscriptionPolicyAttachmentsStatusAttachmentPoint OBJECT-TYPE
    SYNTAX      DisplayString
    MAX-ACCESS  read-only
    STATUS      current
    DESCRIPTION
        "The location in the subscribed Web service where the policy reference is
        attached. The notation uses WSDL 1.1 URI element notation"

    ::= { dpStatusWSRRSubscriptionPolicyAttachmentsStatusEntry 2 }

dpStatusWSRRSubscriptionPolicyAttachmentsStatusAttachmentURLs OBJECT-TYPE
    SYNTAX      DisplayString
    MAX-ACCESS  read-only
    STATUS      current
    DESCRIPTION
        "The URL reference to the WS-Policy document in WSRR which is applied to
        the policy attachment point."

    ::= { dpStatusWSRRSubscriptionPolicyAttachmentsStatusEntry 3 }

--

dpStatusSLMSummaryStatusTable OBJECT-TYPE
    SYNTAX      SEQUENCE OF DPStatusSLMSummaryStatusEntry
    MAX-ACCESS  not-accessible
    STATUS      current
    DESCRIPTION
        "Service Level Monitor (SLM) summary"

    ::= { dpStatus 121 }

dpStatusSLMSummaryStatusEntry OBJECT-TYPE
    SYNTAX      DPStatusSLMSummaryStatusEntry
    MAX-ACCESS  not-accessible
    STATUS      current
    DESCRIPTION "Table row."
    INDEX { dpConfigSLMPolicyIndex, dpStatusSLMSummaryStatusSLMId }

    ::= { dpStatusSLMSummaryStatusTable 1 }

DPStatusSLMSummaryStatusEntry ::= SEQUENCE {
    dpStatusSLMSummaryStatusSLMPolicy    DisplayString,
    dpStatusSLMSummaryStatusSLMId    Unsigned32,
    dpStatusSLMSummaryStatusMessages    Counter32,
    dpStatusSLMSummaryStatusErrors    Counter32,
    dpStatusSLMSummaryStatusThrottled    Counter32,
    dpStatusSLMSummaryStatusAverage    DPTimeIntervalMillis,
    dpStatusSLMSummaryStatusMinimum    DPTimeIntervalMillis,
    dpStatusSLMSummaryStatusMaximum    DPTimeIntervalMillis,
    dpStatusSLMSummaryStatusTotalMessages    Counter32,
    dpStatusSLMSummaryStatusTotalErrors    Counter32,
    dpStatusSLMSummaryStatusTotalThrottled    Counter32,
    dpStatusSLMSummaryStatusTotalAverage    DPTimeIntervalMillis,
    dpStatusSLMSummaryStatusTotalMinimum    DPTimeIntervalMillis,
    dpStatusSLMSummaryStatusTotalMaximum    DPTimeIntervalMillis
}

dpStatusSLMSummaryStatusSLMPolicy OBJECT-TYPE
    SYNTAX      DisplayString
    MAX-ACCESS  read-only
    STATUS      current
    DESCRIPTION
        "The name of the SLM policy."

    ::= { dpStatusSLMSummaryStatusEntry 1 }

dpStatusSLMSummaryStatusSLMId OBJECT-TYPE
    SYNTAX      Unsigned32
    MAX-ACCESS  read-only
    STATUS      current
    DESCRIPTION
        "The ID of the SLM statements in the SLM policy."

    ::= { dpStatusSLMSummaryStatusEntry 2 }

dpStatusSLMSummaryStatusMessages OBJECT-TYPE
    SYNTAX      Counter32
    MAX-ACCESS  read-only
    STATUS      current
    DESCRIPTION
        "The number of messages that the statement processed in the previous
        minute."

    ::= { dpStatusSLMSummaryStatusEntry 3 }

dpStatusSLMSummaryStatusErrors OBJECT-TYPE
    SYNTAX      Counter32
    MAX-ACCESS  read-only
    STATUS      current
    DESCRIPTION
        "The number of messages processed that the statement processed with errors
        in the previous minute."

    ::= { dpStatusSLMSummaryStatusEntry 4 }

dpStatusSLMSummaryStatusThrottled OBJECT-TYPE
    SYNTAX      Counter32
    MAX-ACCESS  read-only
    STATUS      current
    DESCRIPTION
        "The number of messages that the statement throttled in the previous
        minute."

    ::= { dpStatusSLMSummaryStatusEntry 5 }

dpStatusSLMSummaryStatusAverage OBJECT-TYPE
    SYNTAX      DPTimeIntervalMillis
    MAX-ACCESS  read-only
    STATUS      current
    DESCRIPTION
        "The average response time in milliseconds for all messages that the
        statement processed in the previous minute."

    ::= { dpStatusSLMSummaryStatusEntry 6 }

dpStatusSLMSummaryStatusMinimum OBJECT-TYPE
    SYNTAX      DPTimeIntervalMillis
    MAX-ACCESS  read-only
    STATUS      current
    DESCRIPTION
        "The minimum response time in milliseconds for any message that the
        statement processed in the previous minute."

    ::= { dpStatusSLMSummaryStatusEntry 7 }

dpStatusSLMSummaryStatusMaximum OBJECT-TYPE
    SYNTAX      DPTimeIntervalMillis
    MAX-ACCESS  read-only
    STATUS      current
    DESCRIPTION
        "The maximum response time in milliseconds for any message that the
        statement processed in the previous minute."

    ::= { dpStatusSLMSummaryStatusEntry 8 }

dpStatusSLMSummaryStatusTotalMessages OBJECT-TYPE
    SYNTAX      Counter32
    MAX-ACCESS  read-only
    STATUS      current
    DESCRIPTION
        "The total number of messages that the statement processed."

    ::= { dpStatusSLMSummaryStatusEntry 9 }

dpStatusSLMSummaryStatusTotalErrors OBJECT-TYPE
    SYNTAX      Counter32
    MAX-ACCESS  read-only
    STATUS      current
    DESCRIPTION
        "The total number of messages that the statement processed with errors."

    ::= { dpStatusSLMSummaryStatusEntry 10 }

dpStatusSLMSummaryStatusTotalThrottled OBJECT-TYPE
    SYNTAX      Counter32
    MAX-ACCESS  read-only
    STATUS      current
    DESCRIPTION
        "The total number of messages that the statement throttled."

    ::= { dpStatusSLMSummaryStatusEntry 11 }

dpStatusSLMSummaryStatusTotalAverage OBJECT-TYPE
    SYNTAX      DPTimeIntervalMillis
    MAX-ACCESS  read-only
    STATUS      current
    DESCRIPTION
        "The average response time in milliseconds for all messages that the
        statement processed."

    ::= { dpStatusSLMSummaryStatusEntry 12 }

dpStatusSLMSummaryStatusTotalMinimum OBJECT-TYPE
    SYNTAX      DPTimeIntervalMillis
    MAX-ACCESS  read-only
    STATUS      current
    DESCRIPTION
        "The minimum response time in milliseconds for any message that the
        statement processed."

    ::= { dpStatusSLMSummaryStatusEntry 13 }

dpStatusSLMSummaryStatusTotalMaximum OBJECT-TYPE
    SYNTAX      DPTimeIntervalMillis
    MAX-ACCESS  read-only
    STATUS      current
    DESCRIPTION
        "The maximum response time in milliseconds for any message that the
        statement processed."

    ::= { dpStatusSLMSummaryStatusEntry 14 }

--

dpStatusRoutingStatus2Table OBJECT-TYPE
    SYNTAX      SEQUENCE OF DPStatusRoutingStatus2Entry
    MAX-ACCESS  not-accessible
    STATUS      obsolete
    DESCRIPTION
        "This table describes the IP routes on the system. This includes static and
        default routes created by configuration, and dynamic routes from discovery
        protocols.
        Note: this is obsoleted and is replaced by dpStatusRoutingStatus3 as of release 6.0.2"

    ::= { dpStatus 122 }

dpStatusRoutingStatus2Entry OBJECT-TYPE
    SYNTAX      DPStatusRoutingStatus2Entry
    MAX-ACCESS  not-accessible
    STATUS      obsolete
    DESCRIPTION "Table row."
    INDEX { dpStatusRoutingStatus2Destination, dpStatusRoutingStatus2InterfaceType, dpStatusRoutingStatus2MacInterface, IMPLIED dpStatusRoutingStatus2VlanName }

    ::= { dpStatusRoutingStatus2Table 1 }

DPStatusRoutingStatus2Entry ::= SEQUENCE {
    dpStatusRoutingStatus2Destination    IpNetworkAddress,
    dpStatusRoutingStatus2InterfaceType    INTEGER,
    dpStatusRoutingStatus2MacInterface    INTEGER,
    dpStatusRoutingStatus2VlanName    DisplayString,
    dpStatusRoutingStatus2Gateway    IpAddress,
    dpStatusRoutingStatus2Metric    Unsigned32,
    dpStatusRoutingStatus2RouteType    INTEGER,
    dpStatusRoutingStatus2RouteProto    INTEGER
}

dpStatusRoutingStatus2Destination OBJECT-TYPE
    SYNTAX      IpNetworkAddress
    MAX-ACCESS  read-only
    STATUS      obsolete
    DESCRIPTION
        "The IP subnet or aggregate that is the destination of this route."

    ::= { dpStatusRoutingStatus2Entry 1 }

dpStatusRoutingStatus2InterfaceType OBJECT-TYPE
    SYNTAX      INTEGER { 
                        other(1),
                        ethernet(6),
                        tunnel(131),
                        vLAN(135),
                        aggregate(161)
                }
    MAX-ACCESS  read-only
    STATUS      obsolete
    DESCRIPTION
        "The type of device interface used for this route. Ethernet indicates that
        it is on the base Ethernet MAC interface. VLAN indicates that it is on an
        IEEE 802.1Q VLAN on top of the base Ethernet MAC interface. Tunnel
        indicates that it is on a tun interface."

    ::= { dpStatusRoutingStatus2Entry 2 }

dpStatusRoutingStatus2MacInterface OBJECT-TYPE
    SYNTAX      INTEGER { 
                        eth0(1),
                        eth1(2),
                        eth2(3),
                        eth3(4),
                        mgt0(5),
                        eth4(6),
                        eth5(8),
                        eth6(9),
                        eth7(10),
                        eth8(11),
                        eth9(12),
                        eth10(13),
                        tun(14),
                        mgt1(15),
                        eth11(16),
                        eth12(17),
                        eth13(18),
                        eth14(19),
                        eth15(20),
                        eth16(21),
                        eth17(22),
                        eth20(23),
                        eth21(24),
                        eth22(25),
                        eth23(26),
                        eth24(27),
                        eth25(28),
                        eth26(29),
                        eth27(30),
                        eth30(31),
                        eth31(32),
                        eth32(33),
                        eth33(34)
                }
    MAX-ACCESS  read-only
    STATUS      obsolete
    DESCRIPTION
        "The Ethernet interface used for this route. If it is via a VLAN interface,
        this is the Ethernet interface that VLAN is running over. If it is via a
        tun interface this is empty."

    ::= { dpStatusRoutingStatus2Entry 3 }

dpStatusRoutingStatus2VlanName OBJECT-TYPE
    SYNTAX      DisplayString
    MAX-ACCESS  read-only
    STATUS      obsolete
    DESCRIPTION
        "The name of the VLAN or tunnel interface for this route. If not using a
        VLAN or tun interface, this is empty."

    ::= { dpStatusRoutingStatus2Entry 4 }

dpStatusRoutingStatus2Gateway OBJECT-TYPE
    SYNTAX      IpAddress
    MAX-ACCESS  read-only
    STATUS      obsolete
    DESCRIPTION
        "The next hop gateway for traffic using this route. For routes with a Route
        Type of local, this will be 0.0.0.0 for IP Version 4 or :: for IP Version
        6."

    ::= { dpStatusRoutingStatus2Entry 5 }

dpStatusRoutingStatus2Metric OBJECT-TYPE
    SYNTAX      Unsigned32
    MAX-ACCESS  read-only
    STATUS      obsolete
    DESCRIPTION
        "The metric for this route. Given multiple routes with the same
        destination, the one with the lowest metric is used."

    ::= { dpStatusRoutingStatus2Entry 6 }

dpStatusRoutingStatus2RouteType OBJECT-TYPE
    SYNTAX      INTEGER { 
                        other(1),
                        local(3),
                        remote(4)
                }
    MAX-ACCESS  read-only
    STATUS      obsolete
    DESCRIPTION
        "The type of route. The value local means that the Gateway is the final
        destination. The value remote means that the Gateway is not the final
        destination."

    ::= { dpStatusRoutingStatus2Entry 13 }

dpStatusRoutingStatus2RouteProto OBJECT-TYPE
    SYNTAX      INTEGER { 
                        other(1),
                        local(2),
                        netmgmt(3),
                        icmp(4),
                        ipv6nd(100),
                        ipv6ra(101)
                }
    MAX-ACCESS  read-only
    STATUS      obsolete
    DESCRIPTION
        "The protocol by which this route was learned. Only routes created by
        management can be deleted through the user interface."

    ::= { dpStatusRoutingStatus2Entry 14 }

--

dpStatusVlanInterfaceStatusTable OBJECT-TYPE
    SYNTAX      SEQUENCE OF DPStatusVlanInterfaceStatusEntry
    MAX-ACCESS  not-accessible
    STATUS      obsolete
    DESCRIPTION
        "This table provides status for all VLAN interfaces.
        Note: this is obsoleted and is replaced by dpStatusVlanInterfaceStatus2 as of release 6.0.2"

    ::= { dpStatus 123 }

dpStatusVlanInterfaceStatusEntry OBJECT-TYPE
    SYNTAX      DPStatusVlanInterfaceStatusEntry
    MAX-ACCESS  not-accessible
    STATUS      obsolete
    DESCRIPTION "Table row."
    INDEX { IMPLIED dpStatusVlanInterfaceStatusName }

    ::= { dpStatusVlanInterfaceStatusTable 1 }

DPStatusVlanInterfaceStatusEntry ::= SEQUENCE {
    dpStatusVlanInterfaceStatusName    DisplayString,
    dpStatusVlanInterfaceStatusInterfaceIndex    Unsigned32,
    dpStatusVlanInterfaceStatusOnEthernet    INTEGER,
    dpStatusVlanInterfaceStatusVlanIdentifier    Unsigned32
}

dpStatusVlanInterfaceStatusName OBJECT-TYPE
    SYNTAX      DisplayString
    MAX-ACCESS  read-only
    STATUS      obsolete
    DESCRIPTION
        "Indicates the name of the VLAN interface in the configuration."

    ::= { dpStatusVlanInterfaceStatusEntry 1 }

dpStatusVlanInterfaceStatusInterfaceIndex OBJECT-TYPE
    SYNTAX      Unsigned32
    MAX-ACCESS  read-only
    STATUS      obsolete
    DESCRIPTION
        "Indicates the SNMP ifIndex value of the row in the SNMP ifTable that
        corresponds to the VLAN interface."

    ::= { dpStatusVlanInterfaceStatusEntry 2 }

dpStatusVlanInterfaceStatusOnEthernet OBJECT-TYPE
    SYNTAX      INTEGER { 
                        eth0(1),
                        eth1(2),
                        eth2(3),
                        eth3(4),
                        mgt0(5),
                        eth4(6),
                        eth5(8),
                        eth6(9),
                        eth7(10),
                        eth8(11),
                        eth9(12),
                        eth10(13),
                        tun(14),
                        mgt1(15),
                        eth11(16),
                        eth12(17),
                        eth13(18),
                        eth14(19),
                        eth15(20),
                        eth16(21),
                        eth17(22),
                        eth20(23),
                        eth21(24),
                        eth22(25),
                        eth23(26),
                        eth24(27),
                        eth25(28),
                        eth26(29),
                        eth27(30),
                        eth30(31),
                        eth31(32),
                        eth32(33),
                        eth33(34)
                }
    MAX-ACCESS  read-only
    STATUS      obsolete
    DESCRIPTION
        "Indicates the Ethernet interface that this VLAN interface is operating on."

    ::= { dpStatusVlanInterfaceStatusEntry 3 }

dpStatusVlanInterfaceStatusVlanIdentifier OBJECT-TYPE
    SYNTAX      Unsigned32
    MAX-ACCESS  read-only
    STATUS      obsolete
    DESCRIPTION
        "Indicates the VLAN identifier that uniquely identifies this particular
        VLAN interface on its associated physical Ethernet network."

    ::= { dpStatusVlanInterfaceStatusEntry 4 }

--

dpStatusNetworkInterfaceStatusTable OBJECT-TYPE
    SYNTAX      SEQUENCE OF DPStatusNetworkInterfaceStatusEntry
    MAX-ACCESS  not-accessible
    STATUS      current
    DESCRIPTION
        "This table provides the generic status of all network interfaces on the
        appliance."

    ::= { dpStatus 124 }

dpStatusNetworkInterfaceStatusEntry OBJECT-TYPE
    SYNTAX      DPStatusNetworkInterfaceStatusEntry
    MAX-ACCESS  not-accessible
    STATUS      current
    DESCRIPTION "Table row."
    INDEX { dpStatusNetworkInterfaceStatusInterfaceIndex, dpStatusNetworkInterfaceStatusIP, dpStatusNetworkInterfaceStatusPrefixLength }

    ::= { dpStatusNetworkInterfaceStatusTable 1 }

DPStatusNetworkInterfaceStatusEntry ::= SEQUENCE {
    dpStatusNetworkInterfaceStatusInterfaceIndex    Unsigned32,
    dpStatusNetworkInterfaceStatusInterfaceType    INTEGER,
    dpStatusNetworkInterfaceStatusName    DisplayString,
    dpStatusNetworkInterfaceStatusAdminStatus    INTEGER,
    dpStatusNetworkInterfaceStatusOperStatus    INTEGER,
    dpStatusNetworkInterfaceStatusIPType    InetAddressType,
    dpStatusNetworkInterfaceStatusIP    InetAddress,
    dpStatusNetworkInterfaceStatusPrefixLength    InetAddressPrefixLength,
    dpStatusNetworkInterfaceStatusMACAddress    MacAddress,
    dpStatusNetworkInterfaceStatusMTU    Unsigned32,
    dpStatusNetworkInterfaceStatusRxKbytes    Counter32,
    dpStatusNetworkInterfaceStatusRxPackets    Counter32,
    dpStatusNetworkInterfaceStatusRxErrors    Counter32,
    dpStatusNetworkInterfaceStatusRxDrops    Counter32,
    dpStatusNetworkInterfaceStatusTxKbytes    Counter32,
    dpStatusNetworkInterfaceStatusTxPackets    Counter32,
    dpStatusNetworkInterfaceStatusTxErrors    Counter32,
    dpStatusNetworkInterfaceStatusTxDrops    Counter32,
    dpStatusNetworkInterfaceStatusRxHCBytes    Counter64,
    dpStatusNetworkInterfaceStatusRxHCPackets    Counter64,
    dpStatusNetworkInterfaceStatusRxErrors2    Counter32,
    dpStatusNetworkInterfaceStatusRxDrops2    Counter32,
    dpStatusNetworkInterfaceStatusTxHCBytes    Counter64,
    dpStatusNetworkInterfaceStatusTxHCPackets    Counter64,
    dpStatusNetworkInterfaceStatusTxErrors2    Counter32,
    dpStatusNetworkInterfaceStatusTxDrops2    Counter32
}

dpStatusNetworkInterfaceStatusInterfaceIndex OBJECT-TYPE
    SYNTAX      Unsigned32
    MAX-ACCESS  read-only
    STATUS      current
    DESCRIPTION
        "The value of the SNMP ifIndex column in the ifTable for the interface."

    ::= { dpStatusNetworkInterfaceStatusEntry 1 }

dpStatusNetworkInterfaceStatusInterfaceType OBJECT-TYPE
    SYNTAX      INTEGER { 
                        other(1),
                        ethernet(6),
                        tunnel(131),
                        vLAN(135),
                        aggregate(161)
                }
    MAX-ACCESS  read-only
    STATUS      current
    DESCRIPTION
        "The interface type of the network interface."

    ::= { dpStatusNetworkInterfaceStatusEntry 2 }

dpStatusNetworkInterfaceStatusName OBJECT-TYPE
    SYNTAX      DisplayString
    MAX-ACCESS  read-only
    STATUS      current
    DESCRIPTION
        "The configuration name of the interface."

    ::= { dpStatusNetworkInterfaceStatusEntry 3 }

dpStatusNetworkInterfaceStatusAdminStatus OBJECT-TYPE
    SYNTAX      INTEGER { 
                        up(1),
                        down(2)
                }
    MAX-ACCESS  read-only
    STATUS      current
    DESCRIPTION
        "The configured administrative state of the interface."

    ::= { dpStatusNetworkInterfaceStatusEntry 4 }

dpStatusNetworkInterfaceStatusOperStatus OBJECT-TYPE
    SYNTAX      INTEGER { 
                        up(1),
                        down(2),
                        testing(3),
                        unknown(4),
                        dormant(5),
                        notPresent(6),
                        lowerLayerDown(7)
                }
    MAX-ACCESS  read-only
    STATUS      current
    DESCRIPTION
        "The current operational state of the interface."

    ::= { dpStatusNetworkInterfaceStatusEntry 5 }

dpStatusNetworkInterfaceStatusIPType OBJECT-TYPE
    SYNTAX      InetAddressType
    MAX-ACCESS  read-only
    STATUS      current
    DESCRIPTION
        "The IP address version: ipv4 or ipv6."

    ::= { dpStatusNetworkInterfaceStatusEntry 6 }

dpStatusNetworkInterfaceStatusIP OBJECT-TYPE
    SYNTAX      InetAddress
    MAX-ACCESS  read-only
    STATUS      current
    DESCRIPTION
        "The primary IP address for the interface."

    ::= { dpStatusNetworkInterfaceStatusEntry 7 }

dpStatusNetworkInterfaceStatusPrefixLength OBJECT-TYPE
    SYNTAX      InetAddressPrefixLength
    MAX-ACCESS  read-only
    STATUS      current
    DESCRIPTION
        "The prefix length of the IP address that represents the configured
        netmask."

    ::= { dpStatusNetworkInterfaceStatusEntry 8 }

dpStatusNetworkInterfaceStatusMACAddress OBJECT-TYPE
    SYNTAX      MacAddress
    MAX-ACCESS  read-only
    STATUS      current
    DESCRIPTION
        "The current MAC address of the interface. The address can be the
        preprogrammed one, overridden by your configuration, or overridden by
        standby control if the interface is the active member of the standby
        group."

    ::= { dpStatusNetworkInterfaceStatusEntry 9 }

dpStatusNetworkInterfaceStatusMTU OBJECT-TYPE
    SYNTAX      Unsigned32
    UNITS       "bytes"
    MAX-ACCESS  read-only
    STATUS      current
    DESCRIPTION
        "Maximum transmission unit for the interface."

    ::= { dpStatusNetworkInterfaceStatusEntry 10 }

dpStatusNetworkInterfaceStatusRxKbytes OBJECT-TYPE
    SYNTAX      Counter32
    MAX-ACCESS  read-only
    STATUS      obsolete
    DESCRIPTION
        "NONTRANSLATABLE"

    ::= { dpStatusNetworkInterfaceStatusEntry 11 }

dpStatusNetworkInterfaceStatusRxPackets OBJECT-TYPE
    SYNTAX      Counter32
    MAX-ACCESS  read-only
    STATUS      obsolete
    DESCRIPTION
        "NONTRANSLATABLE"

    ::= { dpStatusNetworkInterfaceStatusEntry 12 }

dpStatusNetworkInterfaceStatusRxErrors OBJECT-TYPE
    SYNTAX      Counter32
    MAX-ACCESS  read-only
    STATUS      obsolete
    DESCRIPTION
        "NONTRANSLATABLE"

    ::= { dpStatusNetworkInterfaceStatusEntry 13 }

dpStatusNetworkInterfaceStatusRxDrops OBJECT-TYPE
    SYNTAX      Counter32
    MAX-ACCESS  read-only
    STATUS      obsolete
    DESCRIPTION
        "NONTRANSLATABLE"

    ::= { dpStatusNetworkInterfaceStatusEntry 14 }

dpStatusNetworkInterfaceStatusTxKbytes OBJECT-TYPE
    SYNTAX      Counter32
    MAX-ACCESS  read-only
    STATUS      obsolete
    DESCRIPTION
        "NONTRANSLATABLE"

    ::= { dpStatusNetworkInterfaceStatusEntry 15 }

dpStatusNetworkInterfaceStatusTxPackets OBJECT-TYPE
    SYNTAX      Counter32
    MAX-ACCESS  read-only
    STATUS      obsolete
    DESCRIPTION
        "NONTRANSLATABLE"

    ::= { dpStatusNetworkInterfaceStatusEntry 16 }

dpStatusNetworkInterfaceStatusTxErrors OBJECT-TYPE
    SYNTAX      Counter32
    MAX-ACCESS  read-only
    STATUS      obsolete
    DESCRIPTION
        "NONTRANSLATABLE"

    ::= { dpStatusNetworkInterfaceStatusEntry 17 }

dpStatusNetworkInterfaceStatusTxDrops OBJECT-TYPE
    SYNTAX      Counter32
    MAX-ACCESS  read-only
    STATUS      obsolete
    DESCRIPTION
        "NONTRANSLATABLE"

    ::= { dpStatusNetworkInterfaceStatusEntry 18 }

dpStatusNetworkInterfaceStatusRxHCBytes OBJECT-TYPE
    SYNTAX      Counter64
    MAX-ACCESS  read-only
    STATUS      current
    DESCRIPTION
        "The amount of data successfully received on the interface, which includes
        MAC framing overhead."

    ::= { dpStatusNetworkInterfaceStatusEntry 19 }

dpStatusNetworkInterfaceStatusRxHCPackets OBJECT-TYPE
    SYNTAX      Counter64
    MAX-ACCESS  read-only
    STATUS      current
    DESCRIPTION
        "The number of packets successfully received on the interface that were
        passed up to the network layer for processing."

    ::= { dpStatusNetworkInterfaceStatusEntry 20 }

dpStatusNetworkInterfaceStatusRxErrors2 OBJECT-TYPE
    SYNTAX      Counter32
    MAX-ACCESS  read-only
    STATUS      current
    DESCRIPTION
        "The number of packets that could not be received due to errors in the
        packet or in the hardware."

    ::= { dpStatusNetworkInterfaceStatusEntry 21 }

dpStatusNetworkInterfaceStatusRxDrops2 OBJECT-TYPE
    SYNTAX      Counter32
    MAX-ACCESS  read-only
    STATUS      current
    DESCRIPTION
        "The number of received packets that were not in error, but were not passed
        up to the network layer due to resource constraints."

    ::= { dpStatusNetworkInterfaceStatusEntry 22 }

dpStatusNetworkInterfaceStatusTxHCBytes OBJECT-TYPE
    SYNTAX      Counter64
    MAX-ACCESS  read-only
    STATUS      current
    DESCRIPTION
        "The amount of data successfully transmitted on the interface, which
        includes MAC framing overhead."

    ::= { dpStatusNetworkInterfaceStatusEntry 23 }

dpStatusNetworkInterfaceStatusTxHCPackets OBJECT-TYPE
    SYNTAX      Counter64
    MAX-ACCESS  read-only
    STATUS      current
    DESCRIPTION
        "The number of packets successfully transmitted on the interface."

    ::= { dpStatusNetworkInterfaceStatusEntry 24 }

dpStatusNetworkInterfaceStatusTxErrors2 OBJECT-TYPE
    SYNTAX      Counter32
    MAX-ACCESS  read-only
    STATUS      current
    DESCRIPTION
        "The number of packets that were not successfully transmitted due to errors
        on the network or in the hardware."

    ::= { dpStatusNetworkInterfaceStatusEntry 25 }

dpStatusNetworkInterfaceStatusTxDrops2 OBJECT-TYPE
    SYNTAX      Counter32
    MAX-ACCESS  read-only
    STATUS      current
    DESCRIPTION
        "The number of packets that were not transmitted because the network layer
        was generating packets faster than the physical network could accept them."

    ::= { dpStatusNetworkInterfaceStatusEntry 26 }

--

dpStatusNetworkReceiveDataThroughputTable OBJECT-TYPE
    SYNTAX      SEQUENCE OF DPStatusNetworkReceiveDataThroughputEntry
    MAX-ACCESS  not-accessible
    STATUS      current
    DESCRIPTION
        "This table gives the receive throughput, in kibibit per second, for all
        network interfaces on the system."

    ::= { dpStatus 125 }

dpStatusNetworkReceiveDataThroughputEntry OBJECT-TYPE
    SYNTAX      DPStatusNetworkReceiveDataThroughputEntry
    MAX-ACCESS  not-accessible
    STATUS      current
    DESCRIPTION "Table row."
    INDEX { dpStatusNetworkReceiveDataThroughputInterfaceType, IMPLIED dpStatusNetworkReceiveDataThroughputInterfaceName }

    ::= { dpStatusNetworkReceiveDataThroughputTable 1 }

DPStatusNetworkReceiveDataThroughputEntry ::= SEQUENCE {
    dpStatusNetworkReceiveDataThroughputInterfaceType    INTEGER,
    dpStatusNetworkReceiveDataThroughputInterfaceName    DisplayString,
    dpStatusNetworkReceiveDataThroughputTenSecondsBits    Gauge32,
    dpStatusNetworkReceiveDataThroughputOneMinuteBits    Gauge32,
    dpStatusNetworkReceiveDataThroughputTenMinutesBits    Gauge32,
    dpStatusNetworkReceiveDataThroughputOneHourBits    Gauge32,
    dpStatusNetworkReceiveDataThroughputOneDayBits    Gauge32
}

dpStatusNetworkReceiveDataThroughputInterfaceType OBJECT-TYPE
    SYNTAX      INTEGER { 
                        other(1),
                        ethernet(6),
                        tunnel(131),
                        vLAN(135),
                        aggregate(161)
                }
    MAX-ACCESS  read-only
    STATUS      current
    DESCRIPTION
        "The type of this interface."

    ::= { dpStatusNetworkReceiveDataThroughputEntry 1 }

dpStatusNetworkReceiveDataThroughputInterfaceName OBJECT-TYPE
    SYNTAX      DisplayString
    MAX-ACCESS  read-only
    STATUS      current
    DESCRIPTION
        "The management name of this interface."

    ::= { dpStatusNetworkReceiveDataThroughputEntry 2 }

dpStatusNetworkReceiveDataThroughputTenSecondsBits OBJECT-TYPE
    SYNTAX      Gauge32
    UNITS       "Kibit/s"
    MAX-ACCESS  read-only
    STATUS      current
    DESCRIPTION
        "The average receive throughput over the last 10 seconds."

    ::= { dpStatusNetworkReceiveDataThroughputEntry 3 }

dpStatusNetworkReceiveDataThroughputOneMinuteBits OBJECT-TYPE
    SYNTAX      Gauge32
    UNITS       "Kibit/s"
    MAX-ACCESS  read-only
    STATUS      current
    DESCRIPTION
        "The average receive throughput over the last minute."

    ::= { dpStatusNetworkReceiveDataThroughputEntry 4 }

dpStatusNetworkReceiveDataThroughputTenMinutesBits OBJECT-TYPE
    SYNTAX      Gauge32
    UNITS       "Kibit/s"
    MAX-ACCESS  read-only
    STATUS      current
    DESCRIPTION
        "The average receive throughput over the last 10 minutes."

    ::= { dpStatusNetworkReceiveDataThroughputEntry 5 }

dpStatusNetworkReceiveDataThroughputOneHourBits OBJECT-TYPE
    SYNTAX      Gauge32
    UNITS       "Kibit/s"
    MAX-ACCESS  read-only
    STATUS      current
    DESCRIPTION
        "The average receive throughput over the last hour."

    ::= { dpStatusNetworkReceiveDataThroughputEntry 6 }

dpStatusNetworkReceiveDataThroughputOneDayBits OBJECT-TYPE
    SYNTAX      Gauge32
    UNITS       "Kibit/s"
    MAX-ACCESS  read-only
    STATUS      current
    DESCRIPTION
        "The average receive throughput over the last day."

    ::= { dpStatusNetworkReceiveDataThroughputEntry 7 }

--

dpStatusNetworkReceivePacketThroughputTable OBJECT-TYPE
    SYNTAX      SEQUENCE OF DPStatusNetworkReceivePacketThroughputEntry
    MAX-ACCESS  not-accessible
    STATUS      current
    DESCRIPTION
        "This table gives the receive throughput, in packets per second, for all
        network interfaces on the system."

    ::= { dpStatus 126 }

dpStatusNetworkReceivePacketThroughputEntry OBJECT-TYPE
    SYNTAX      DPStatusNetworkReceivePacketThroughputEntry
    MAX-ACCESS  not-accessible
    STATUS      current
    DESCRIPTION "Table row."
    INDEX { dpStatusNetworkReceivePacketThroughputInterfaceType, IMPLIED dpStatusNetworkReceivePacketThroughputInterfaceName }

    ::= { dpStatusNetworkReceivePacketThroughputTable 1 }

DPStatusNetworkReceivePacketThroughputEntry ::= SEQUENCE {
    dpStatusNetworkReceivePacketThroughputInterfaceType    INTEGER,
    dpStatusNetworkReceivePacketThroughputInterfaceName    DisplayString,
    dpStatusNetworkReceivePacketThroughputtenSeconds    Gauge32,
    dpStatusNetworkReceivePacketThroughputoneMinute    Gauge32,
    dpStatusNetworkReceivePacketThroughputtenMinutes    Gauge32,
    dpStatusNetworkReceivePacketThroughputoneHour    Gauge32,
    dpStatusNetworkReceivePacketThroughputoneDay    Gauge32
}

dpStatusNetworkReceivePacketThroughputInterfaceType OBJECT-TYPE
    SYNTAX      INTEGER { 
                        other(1),
                        ethernet(6),
                        tunnel(131),
                        vLAN(135),
                        aggregate(161)
                }
    MAX-ACCESS  read-only
    STATUS      current
    DESCRIPTION
        "The type of this interface."

    ::= { dpStatusNetworkReceivePacketThroughputEntry 1 }

dpStatusNetworkReceivePacketThroughputInterfaceName OBJECT-TYPE
    SYNTAX      DisplayString
    MAX-ACCESS  read-only
    STATUS      current
    DESCRIPTION
        "The management name of this interface."

    ::= { dpStatusNetworkReceivePacketThroughputEntry 2 }

dpStatusNetworkReceivePacketThroughputtenSeconds OBJECT-TYPE
    SYNTAX      Gauge32
    UNITS       "packets/sec"
    MAX-ACCESS  read-only
    STATUS      current
    DESCRIPTION
        "The average receive throughput over the last 10 seconds."

    ::= { dpStatusNetworkReceivePacketThroughputEntry 3 }

dpStatusNetworkReceivePacketThroughputoneMinute OBJECT-TYPE
    SYNTAX      Gauge32
    UNITS       "packets/sec"
    MAX-ACCESS  read-only
    STATUS      current
    DESCRIPTION
        "The average receive throughput over the last minute."

    ::= { dpStatusNetworkReceivePacketThroughputEntry 4 }

dpStatusNetworkReceivePacketThroughputtenMinutes OBJECT-TYPE
    SYNTAX      Gauge32
    UNITS       "packets/sec"
    MAX-ACCESS  read-only
    STATUS      current
    DESCRIPTION
        "The average receive throughput over the last 10 minutes."

    ::= { dpStatusNetworkReceivePacketThroughputEntry 5 }

dpStatusNetworkReceivePacketThroughputoneHour OBJECT-TYPE
    SYNTAX      Gauge32
    UNITS       "packets/sec"
    MAX-ACCESS  read-only
    STATUS      current
    DESCRIPTION
        "The average receive throughput over the last hour."

    ::= { dpStatusNetworkReceivePacketThroughputEntry 6 }

dpStatusNetworkReceivePacketThroughputoneDay OBJECT-TYPE
    SYNTAX      Gauge32
    UNITS       "packets/sec"
    MAX-ACCESS  read-only
    STATUS      current
    DESCRIPTION
        "The average receive throughput over the last day."

    ::= { dpStatusNetworkReceivePacketThroughputEntry 7 }

--

dpStatusNetworkTransmitDataThroughputTable OBJECT-TYPE
    SYNTAX      SEQUENCE OF DPStatusNetworkTransmitDataThroughputEntry
    MAX-ACCESS  not-accessible
    STATUS      current
    DESCRIPTION
        "This table gives the transmit throughput, in kibibit per second, for all
        network interfaces on the system."

    ::= { dpStatus 127 }

dpStatusNetworkTransmitDataThroughputEntry OBJECT-TYPE
    SYNTAX      DPStatusNetworkTransmitDataThroughputEntry
    MAX-ACCESS  not-accessible
    STATUS      current
    DESCRIPTION "Table row."
    INDEX { dpStatusNetworkTransmitDataThroughputInterfaceType, IMPLIED dpStatusNetworkTransmitDataThroughputInterfaceName }

    ::= { dpStatusNetworkTransmitDataThroughputTable 1 }

DPStatusNetworkTransmitDataThroughputEntry ::= SEQUENCE {
    dpStatusNetworkTransmitDataThroughputInterfaceType    INTEGER,
    dpStatusNetworkTransmitDataThroughputInterfaceName    DisplayString,
    dpStatusNetworkTransmitDataThroughputTenSecondsBits    Gauge32,
    dpStatusNetworkTransmitDataThroughputOneMinuteBits    Gauge32,
    dpStatusNetworkTransmitDataThroughputTenMinutesBits    Gauge32,
    dpStatusNetworkTransmitDataThroughputOneHourBits    Gauge32,
    dpStatusNetworkTransmitDataThroughputOneDayBits    Gauge32
}

dpStatusNetworkTransmitDataThroughputInterfaceType OBJECT-TYPE
    SYNTAX      INTEGER { 
                        other(1),
                        ethernet(6),
                        tunnel(131),
                        vLAN(135),
                        aggregate(161)
                }
    MAX-ACCESS  read-only
    STATUS      current
    DESCRIPTION
        "The type of this interface."

    ::= { dpStatusNetworkTransmitDataThroughputEntry 1 }

dpStatusNetworkTransmitDataThroughputInterfaceName OBJECT-TYPE
    SYNTAX      DisplayString
    MAX-ACCESS  read-only
    STATUS      current
    DESCRIPTION
        "The management name of this interface."

    ::= { dpStatusNetworkTransmitDataThroughputEntry 2 }

dpStatusNetworkTransmitDataThroughputTenSecondsBits OBJECT-TYPE
    SYNTAX      Gauge32
    UNITS       "Kibit/s"
    MAX-ACCESS  read-only
    STATUS      current
    DESCRIPTION
        "The average transmit throughput over the last 10 seconds."

    ::= { dpStatusNetworkTransmitDataThroughputEntry 3 }

dpStatusNetworkTransmitDataThroughputOneMinuteBits OBJECT-TYPE
    SYNTAX      Gauge32
    UNITS       "Kibit/s"
    MAX-ACCESS  read-only
    STATUS      current
    DESCRIPTION
        "The average transmit throughput over the last minute."

    ::= { dpStatusNetworkTransmitDataThroughputEntry 4 }

dpStatusNetworkTransmitDataThroughputTenMinutesBits OBJECT-TYPE
    SYNTAX      Gauge32
    UNITS       "Kibit/s"
    MAX-ACCESS  read-only
    STATUS      current
    DESCRIPTION
        "The average transmit throughput over the last 10 minutes."

    ::= { dpStatusNetworkTransmitDataThroughputEntry 5 }

dpStatusNetworkTransmitDataThroughputOneHourBits OBJECT-TYPE
    SYNTAX      Gauge32
    UNITS       "Kibit/s"
    MAX-ACCESS  read-only
    STATUS      current
    DESCRIPTION
        "The average transmit throughput over the last hour."

    ::= { dpStatusNetworkTransmitDataThroughputEntry 6 }

dpStatusNetworkTransmitDataThroughputOneDayBits OBJECT-TYPE
    SYNTAX      Gauge32
    UNITS       "Kibit/s"
    MAX-ACCESS  read-only
    STATUS      current
    DESCRIPTION
        "The average transmit throughput over the last day."

    ::= { dpStatusNetworkTransmitDataThroughputEntry 7 }

--

dpStatusNetworkTransmitPacketThroughputTable OBJECT-TYPE
    SYNTAX      SEQUENCE OF DPStatusNetworkTransmitPacketThroughputEntry
    MAX-ACCESS  not-accessible
    STATUS      current
    DESCRIPTION
        "This table gives the transmit throughput, in packets per second, for all
        network interfaces on the system."

    ::= { dpStatus 128 }

dpStatusNetworkTransmitPacketThroughputEntry OBJECT-TYPE
    SYNTAX      DPStatusNetworkTransmitPacketThroughputEntry
    MAX-ACCESS  not-accessible
    STATUS      current
    DESCRIPTION "Table row."
    INDEX { dpStatusNetworkTransmitPacketThroughputInterfaceType, IMPLIED dpStatusNetworkTransmitPacketThroughputInterfaceName }

    ::= { dpStatusNetworkTransmitPacketThroughputTable 1 }

DPStatusNetworkTransmitPacketThroughputEntry ::= SEQUENCE {
    dpStatusNetworkTransmitPacketThroughputInterfaceType    INTEGER,
    dpStatusNetworkTransmitPacketThroughputInterfaceName    DisplayString,
    dpStatusNetworkTransmitPacketThroughputtenSeconds    Gauge32,
    dpStatusNetworkTransmitPacketThroughputoneMinute    Gauge32,
    dpStatusNetworkTransmitPacketThroughputtenMinutes    Gauge32,
    dpStatusNetworkTransmitPacketThroughputoneHour    Gauge32,
    dpStatusNetworkTransmitPacketThroughputoneDay    Gauge32
}

dpStatusNetworkTransmitPacketThroughputInterfaceType OBJECT-TYPE
    SYNTAX      INTEGER { 
                        other(1),
                        ethernet(6),
                        tunnel(131),
                        vLAN(135),
                        aggregate(161)
                }
    MAX-ACCESS  read-only
    STATUS      current
    DESCRIPTION
        "The type of this interface."

    ::= { dpStatusNetworkTransmitPacketThroughputEntry 1 }

dpStatusNetworkTransmitPacketThroughputInterfaceName OBJECT-TYPE
    SYNTAX      DisplayString
    MAX-ACCESS  read-only
    STATUS      current
    DESCRIPTION
        "The management name of this interface."

    ::= { dpStatusNetworkTransmitPacketThroughputEntry 2 }

dpStatusNetworkTransmitPacketThroughputtenSeconds OBJECT-TYPE
    SYNTAX      Gauge32
    UNITS       "packets/sec"
    MAX-ACCESS  read-only
    STATUS      current
    DESCRIPTION
        "The average transmit throughput over the last 10 seconds."

    ::= { dpStatusNetworkTransmitPacketThroughputEntry 3 }

dpStatusNetworkTransmitPacketThroughputoneMinute OBJECT-TYPE
    SYNTAX      Gauge32
    UNITS       "packets/sec"
    MAX-ACCESS  read-only
    STATUS      current
    DESCRIPTION
        "The average transmit throughput over the last minute."

    ::= { dpStatusNetworkTransmitPacketThroughputEntry 4 }

dpStatusNetworkTransmitPacketThroughputtenMinutes OBJECT-TYPE
    SYNTAX      Gauge32
    UNITS       "packets/sec"
    MAX-ACCESS  read-only
    STATUS      current
    DESCRIPTION
        "The average transmit throughput over the last 10 minutes."

    ::= { dpStatusNetworkTransmitPacketThroughputEntry 5 }

dpStatusNetworkTransmitPacketThroughputoneHour OBJECT-TYPE
    SYNTAX      Gauge32
    UNITS       "packets/sec"
    MAX-ACCESS  read-only
    STATUS      current
    DESCRIPTION
        "The average transmit throughput over the last hour."

    ::= { dpStatusNetworkTransmitPacketThroughputEntry 6 }

dpStatusNetworkTransmitPacketThroughputoneDay OBJECT-TYPE
    SYNTAX      Gauge32
    UNITS       "packets/sec"
    MAX-ACCESS  read-only
    STATUS      current
    DESCRIPTION
        "The average transmit throughput over the last day."

    ::= { dpStatusNetworkTransmitPacketThroughputEntry 7 }

--

dpStatusLoadBalancerStatus2Table OBJECT-TYPE
    SYNTAX      SEQUENCE OF DPStatusLoadBalancerStatus2Entry
    MAX-ACCESS  not-accessible
    STATUS      current
    DESCRIPTION
        "Displays the status of all load balancer groups."

    ::= { dpStatus 129 }

dpStatusLoadBalancerStatus2Entry OBJECT-TYPE
    SYNTAX      DPStatusLoadBalancerStatus2Entry
    MAX-ACCESS  not-accessible
    STATUS      current
    DESCRIPTION "Table row."
    INDEX { dpConfigLoadBalancerGroupIndex, dpStatusLoadBalancerStatus2Server, dpStatusLoadBalancerStatus2Port }

    ::= { dpStatusLoadBalancerStatus2Table 1 }

DPStatusLoadBalancerStatus2Entry ::= SEQUENCE {
    dpStatusLoadBalancerStatus2Group    DisplayString,
    dpStatusLoadBalancerStatus2Server    DisplayString,
    dpStatusLoadBalancerStatus2Port    InetPortNumber,
    dpStatusLoadBalancerStatus2Health    INTEGER,
    dpStatusLoadBalancerStatus2Weight    Unsigned32,
    dpStatusLoadBalancerStatus2AdminState    INTEGER
}

dpStatusLoadBalancerStatus2Group OBJECT-TYPE
    SYNTAX      DisplayString
    MAX-ACCESS  read-only
    STATUS      current
    DESCRIPTION
        "The name of the load balancer group."

    ::= { dpStatusLoadBalancerStatus2Entry 1 }

dpStatusLoadBalancerStatus2Server OBJECT-TYPE
    SYNTAX      DisplayString
    MAX-ACCESS  read-only
    STATUS      current
    DESCRIPTION
        "The IP address or host name of the load balancer member."

    ::= { dpStatusLoadBalancerStatus2Entry 2 }

dpStatusLoadBalancerStatus2Port OBJECT-TYPE
    SYNTAX      InetPortNumber
    MAX-ACCESS  read-only
    STATUS      current
    DESCRIPTION
        "The member-specific target port or 0 if using the DataPower
        service-defined port."

    ::= { dpStatusLoadBalancerStatus2Entry 3 }

dpStatusLoadBalancerStatus2Health OBJECT-TYPE
    SYNTAX      INTEGER { 
                        up(1),
                        softdown(2),
                        down(3)
                }
    MAX-ACCESS  read-only
    STATUS      current
    DESCRIPTION
        "The health status of a given load balancer member. Possible values are:
        up, softdown, or down."

    ::= { dpStatusLoadBalancerStatus2Entry 4 }

dpStatusLoadBalancerStatus2Weight OBJECT-TYPE
    SYNTAX      Unsigned32
    MAX-ACCESS  read-only
    STATUS      current
    DESCRIPTION
        "The weight given to this server. Weights are used in weighted load
        balancing decisions for algorithms such as Weighted Round Robin or
        Weighted Least Outstanding Connections."

    ::= { dpStatusLoadBalancerStatus2Entry 5 }

dpStatusLoadBalancerStatus2AdminState OBJECT-TYPE
    SYNTAX      INTEGER { 
                        enabled(1),
                        disabled(2)
                }
    MAX-ACCESS  read-only
    STATUS      current
    DESCRIPTION
        "The administrative state overrides the health of the server."

    ::= { dpStatusLoadBalancerStatus2Entry 6 }

--

dpStatusEthernetMAUStatusTable OBJECT-TYPE
    SYNTAX      SEQUENCE OF DPStatusEthernetMAUStatusEntry
    MAX-ACCESS  not-accessible
    STATUS      current
    DESCRIPTION
        "This table provides the device-specific status of Ethernet MAUs on the
        system. Note that some interfaces do not support this feature."

    ::= { dpStatus 130 }

dpStatusEthernetMAUStatusEntry OBJECT-TYPE
    SYNTAX      DPStatusEthernetMAUStatusEntry
    MAX-ACCESS  not-accessible
    STATUS      current
    DESCRIPTION "Table row."
    INDEX { dpStatusEthernetMAUStatusInterfaceIndex, dpStatusEthernetMAUStatusMauIndex }

    ::= { dpStatusEthernetMAUStatusTable 1 }

DPStatusEthernetMAUStatusEntry ::= SEQUENCE {
    dpStatusEthernetMAUStatusInterfaceIndex    Integer32,
    dpStatusEthernetMAUStatusName    DisplayString,
    dpStatusEthernetMAUStatusMauIndex    Integer32,
    dpStatusEthernetMAUStatusStatus    INTEGER,
    dpStatusEthernetMAUStatusJabberState    INTEGER,
    dpStatusEthernetMAUStatusAutoNegRemoteSignaling    INTEGER,
    dpStatusEthernetMAUStatusAutoNegConfig    INTEGER,
    dpStatusEthernetMAUStatusAutoNegCapabilities    BITS,
    dpStatusEthernetMAUStatusAutoNegCapabilitiesAdvertised    BITS,
    dpStatusEthernetMAUStatusAutoNegCapabilitiesLinkPartner    BITS,
    dpStatusEthernetMAUStatusAutoNegRemoteFaultAdvertised    INTEGER,
    dpStatusEthernetMAUStatusAutoNegRemoteFaultReceived    INTEGER
}

dpStatusEthernetMAUStatusInterfaceIndex OBJECT-TYPE
    SYNTAX      Integer32 (1..2147483647)
    MAX-ACCESS  read-only
    STATUS      current
    DESCRIPTION
        "The value of the SNMP ifIndex column in the ifTable for this interface."

    ::= { dpStatusEthernetMAUStatusEntry 1 }

dpStatusEthernetMAUStatusName OBJECT-TYPE
    SYNTAX      DisplayString
    MAX-ACCESS  read-only
    STATUS      current
    DESCRIPTION
        "The configuration name of this interface."

    ::= { dpStatusEthernetMAUStatusEntry 2 }

dpStatusEthernetMAUStatusMauIndex OBJECT-TYPE
    SYNTAX      Integer32 (1..32)
    MAX-ACCESS  read-only
    STATUS      current
    DESCRIPTION
        "The index of this particular MAU on this Ethernet interface."

    ::= { dpStatusEthernetMAUStatusEntry 3 }

dpStatusEthernetMAUStatusStatus OBJECT-TYPE
    SYNTAX      INTEGER { 
                        other(1),
                        unknown(2),
                        available(3),
                        notAvailable(4),
                        remoteFault(5),
                        offline(10)
                }
    MAX-ACCESS  read-only
    STATUS      current
    DESCRIPTION
        "The current MAU link status."

    ::= { dpStatusEthernetMAUStatusEntry 4 }

dpStatusEthernetMAUStatusJabberState OBJECT-TYPE
    SYNTAX      INTEGER { 
                        other(1),
                        unknown(2),
                        noJabber(3),
                        jabbering(4)
                }
    MAX-ACCESS  read-only
    STATUS      current
    DESCRIPTION
        "The current MAU jabber error state."

    ::= { dpStatusEthernetMAUStatusEntry 5 }

dpStatusEthernetMAUStatusAutoNegRemoteSignaling OBJECT-TYPE
    SYNTAX      INTEGER { 
                        detected(1),
                        notDetected(2)
                }
    MAX-ACCESS  read-only
    STATUS      current
    DESCRIPTION
        "Does the remote end support auto-negotiation. Will be notDetected if no
        FLP bursts received."

    ::= { dpStatusEthernetMAUStatusEntry 6 }

dpStatusEthernetMAUStatusAutoNegConfig OBJECT-TYPE
    SYNTAX      INTEGER { 
                        other(1),
                        configuring(2),
                        complete(3),
                        disabled(4),
                        parallelDetectFail(5)
                }
    MAX-ACCESS  read-only
    STATUS      current
    DESCRIPTION
        "The current status of the auto-negotiation process."

    ::= { dpStatusEthernetMAUStatusEntry 7 }

dpStatusEthernetMAUStatusAutoNegCapabilities OBJECT-TYPE
    SYNTAX      BITS { 
                        eth10baseTHD(0),
                        eth10baseTFD(1),
                        eth100baseXHD(2),
                        eth100baseXFD(3),
                        eth100baseT4HD(4),
                        eth100baseTXHD(5),
                        eth100baseTXFD(6),
                        eth100baseT2HD(7),
                        eth100baseT2FD(8),
                        eth1000baseTHD(9),
                        eth1000baseTFD(10),
                        eth1000baseXHD(11),
                        eth1000baseXFD(12),
                        ethAsymPauseFD(13),
                        ethSymPauseFD(14),
                        ethAsymSymPauseFD(15)
                }
    MAX-ACCESS  read-only
    STATUS      current
    DESCRIPTION
        "The capabilities of this Ethernet MAU."

    ::= { dpStatusEthernetMAUStatusEntry 8 }

dpStatusEthernetMAUStatusAutoNegCapabilitiesAdvertised OBJECT-TYPE
    SYNTAX      BITS { 
                        eth10baseTHD(0),
                        eth10baseTFD(1),
                        eth100baseXHD(2),
                        eth100baseXFD(3),
                        eth100baseT4HD(4),
                        eth100baseTXHD(5),
                        eth100baseTXFD(6),
                        eth100baseT2HD(7),
                        eth100baseT2FD(8),
                        eth1000baseTHD(9),
                        eth1000baseTFD(10),
                        eth1000baseXHD(11),
                        eth1000baseXFD(12),
                        ethAsymPauseFD(13),
                        ethSymPauseFD(14),
                        ethAsymSymPauseFD(15)
                }
    MAX-ACCESS  read-only
    STATUS      current
    DESCRIPTION
        "The capabilities of this Ethernet MAU being advertised in
        auto-negotiation."

    ::= { dpStatusEthernetMAUStatusEntry 9 }

dpStatusEthernetMAUStatusAutoNegCapabilitiesLinkPartner OBJECT-TYPE
    SYNTAX      BITS { 
                        eth10baseTHD(0),
                        eth10baseTFD(1),
                        eth100baseXHD(2),
                        eth100baseXFD(3),
                        eth100baseT4HD(4),
                        eth100baseTXHD(5),
                        eth100baseTXFD(6),
                        eth100baseT2HD(7),
                        eth100baseT2FD(8),
                        eth1000baseTHD(9),
                        eth1000baseTFD(10),
                        eth1000baseXHD(11),
                        eth1000baseXFD(12),
                        ethAsymPauseFD(13),
                        ethSymPauseFD(14),
                        ethAsymSymPauseFD(15)
                }
    MAX-ACCESS  read-only
    STATUS      current
    DESCRIPTION
        "The capabilities of the peer Ethernet MAU received by auto-negotiation."

    ::= { dpStatusEthernetMAUStatusEntry 10 }

dpStatusEthernetMAUStatusAutoNegRemoteFaultAdvertised OBJECT-TYPE
    SYNTAX      INTEGER { 
                        noError(1),
                        offline(2),
                        linkFailure(3),
                        autoNegError(4)
                }
    MAX-ACCESS  read-only
    STATUS      current
    DESCRIPTION
        "Whether a local fault is causing advertising of remote fault to peer."

    ::= { dpStatusEthernetMAUStatusEntry 11 }

dpStatusEthernetMAUStatusAutoNegRemoteFaultReceived OBJECT-TYPE
    SYNTAX      INTEGER { 
                        noError(1),
                        offline(2),
                        linkFailure(3),
                        autoNegError(4)
                }
    MAX-ACCESS  read-only
    STATUS      current
    DESCRIPTION
        "Whether a remote fault is causing reception of remote fault from peer."

    ::= { dpStatusEthernetMAUStatusEntry 12 }

--

dpStatusEthernetMIIRegisterStatusTable OBJECT-TYPE
    SYNTAX      SEQUENCE OF DPStatusEthernetMIIRegisterStatusEntry
    MAX-ACCESS  not-accessible
    STATUS      current
    DESCRIPTION
        "This table provides the MII registers of all Ethernet MAUs on the system
        having access to the MII registers. Note that some interfaces provide data
        only for a subset of the registers and some interfaces don't provide any
        register data at all."

    ::= { dpStatus 131 }

dpStatusEthernetMIIRegisterStatusEntry OBJECT-TYPE
    SYNTAX      DPStatusEthernetMIIRegisterStatusEntry
    MAX-ACCESS  not-accessible
    STATUS      current
    DESCRIPTION "Table row."
    INDEX { dpStatusEthernetMIIRegisterStatusInterfaceIndex, dpStatusEthernetMIIRegisterStatusMauIndex }

    ::= { dpStatusEthernetMIIRegisterStatusTable 1 }

DPStatusEthernetMIIRegisterStatusEntry ::= SEQUENCE {
    dpStatusEthernetMIIRegisterStatusInterfaceIndex    Integer32,
    dpStatusEthernetMIIRegisterStatusName    DisplayString,
    dpStatusEthernetMIIRegisterStatusMauIndex    Integer32,
    dpStatusEthernetMIIRegisterStatusControl    Unsigned32,
    dpStatusEthernetMIIRegisterStatusStatus    Unsigned32,
    dpStatusEthernetMIIRegisterStatusPhyIdentifierHigh    Unsigned32,
    dpStatusEthernetMIIRegisterStatusPhyIdentifierLow    Unsigned32,
    dpStatusEthernetMIIRegisterStatusAutoNegAdvertisement    Unsigned32,
    dpStatusEthernetMIIRegisterStatusAutoNegLinkPartnerAbility    Unsigned32,
    dpStatusEthernetMIIRegisterStatusAutoNegExpansion    Unsigned32,
    dpStatusEthernetMIIRegisterStatusAutoNegNextPageTransmit    Unsigned32,
    dpStatusEthernetMIIRegisterStatusAutoNegLinkPartnerRecNextPage    Unsigned32,
    dpStatusEthernetMIIRegisterStatusMasterSlaveControlRegister    Unsigned32,
    dpStatusEthernetMIIRegisterStatusMasterSlaveStatusRegister    Unsigned32,
    dpStatusEthernetMIIRegisterStatusPSEControl    Unsigned32,
    dpStatusEthernetMIIRegisterStatusPSEStatus    Unsigned32,
    dpStatusEthernetMIIRegisterStatusMMDAccessControl    Unsigned32,
    dpStatusEthernetMIIRegisterStatusMMDAccessAddressData    Unsigned32,
    dpStatusEthernetMIIRegisterStatusExtendedStatus    Unsigned32,
    dpStatusEthernetMIIRegisterStatusVendor16    Unsigned32,
    dpStatusEthernetMIIRegisterStatusVendor17    Unsigned32,
    dpStatusEthernetMIIRegisterStatusVendor18    Unsigned32,
    dpStatusEthernetMIIRegisterStatusVendor19    Unsigned32,
    dpStatusEthernetMIIRegisterStatusVendor20    Unsigned32,
    dpStatusEthernetMIIRegisterStatusVendor21    Unsigned32,
    dpStatusEthernetMIIRegisterStatusVendor22    Unsigned32,
    dpStatusEthernetMIIRegisterStatusVendor23    Unsigned32,
    dpStatusEthernetMIIRegisterStatusVendor24    Unsigned32,
    dpStatusEthernetMIIRegisterStatusVendor25    Unsigned32,
    dpStatusEthernetMIIRegisterStatusVendor26    Unsigned32,
    dpStatusEthernetMIIRegisterStatusVendor27    Unsigned32,
    dpStatusEthernetMIIRegisterStatusVendor28    Unsigned32,
    dpStatusEthernetMIIRegisterStatusVendor29    Unsigned32,
    dpStatusEthernetMIIRegisterStatusVendor30    Unsigned32,
    dpStatusEthernetMIIRegisterStatusVendor31    Unsigned32
}

dpStatusEthernetMIIRegisterStatusInterfaceIndex OBJECT-TYPE
    SYNTAX      Integer32 (1..2147483647)
    MAX-ACCESS  read-only
    STATUS      current
    DESCRIPTION
        "The value of the SNMP ifIndex column in the ifTable for this interface."

    ::= { dpStatusEthernetMIIRegisterStatusEntry 1 }

dpStatusEthernetMIIRegisterStatusName OBJECT-TYPE
    SYNTAX      DisplayString
    MAX-ACCESS  read-only
    STATUS      current
    DESCRIPTION
        "The configuration name of this interface."

    ::= { dpStatusEthernetMIIRegisterStatusEntry 2 }

dpStatusEthernetMIIRegisterStatusMauIndex OBJECT-TYPE
    SYNTAX      Integer32 (1..32)
    MAX-ACCESS  read-only
    STATUS      current
    DESCRIPTION
        "The index of this particular MAU on this Ethernet interface."

    ::= { dpStatusEthernetMIIRegisterStatusEntry 3 }

dpStatusEthernetMIIRegisterStatusControl OBJECT-TYPE
    SYNTAX      Unsigned32 (0..65535)
    MAX-ACCESS  read-only
    STATUS      current
    DESCRIPTION
        "The current read value of the MII control register on this MAU."

    ::= { dpStatusEthernetMIIRegisterStatusEntry 4 }

dpStatusEthernetMIIRegisterStatusStatus OBJECT-TYPE
    SYNTAX      Unsigned32 (0..65535)
    MAX-ACCESS  read-only
    STATUS      current
    DESCRIPTION
        "The current read value of the MII status register on this MAU."

    ::= { dpStatusEthernetMIIRegisterStatusEntry 5 }

dpStatusEthernetMIIRegisterStatusPhyIdentifierHigh OBJECT-TYPE
    SYNTAX      Unsigned32 (0..65535)
    MAX-ACCESS  read-only
    STATUS      current
    DESCRIPTION
        "The current read value of the MII PHY identifier high register on this
        MAU."

    ::= { dpStatusEthernetMIIRegisterStatusEntry 6 }

dpStatusEthernetMIIRegisterStatusPhyIdentifierLow OBJECT-TYPE
    SYNTAX      Unsigned32 (0..65535)
    MAX-ACCESS  read-only
    STATUS      current
    DESCRIPTION
        "The current read value of the MII PHY identifier low register on this MAU."

    ::= { dpStatusEthernetMIIRegisterStatusEntry 7 }

dpStatusEthernetMIIRegisterStatusAutoNegAdvertisement OBJECT-TYPE
    SYNTAX      Unsigned32 (0..65535)
    MAX-ACCESS  read-only
    STATUS      current
    DESCRIPTION
        "The current read value of the MII auto-negotiation advertisement register
        on this MAU."

    ::= { dpStatusEthernetMIIRegisterStatusEntry 8 }

dpStatusEthernetMIIRegisterStatusAutoNegLinkPartnerAbility OBJECT-TYPE
    SYNTAX      Unsigned32 (0..65535)
    MAX-ACCESS  read-only
    STATUS      current
    DESCRIPTION
        "The current read value of the MII auto-negotiation link partner base page
        ability register on this MAU."

    ::= { dpStatusEthernetMIIRegisterStatusEntry 9 }

dpStatusEthernetMIIRegisterStatusAutoNegExpansion OBJECT-TYPE
    SYNTAX      Unsigned32 (0..65535)
    MAX-ACCESS  read-only
    STATUS      current
    DESCRIPTION
        "The current read value of the MII auto-negotiation expansion register on
        this MAU."

    ::= { dpStatusEthernetMIIRegisterStatusEntry 10 }

dpStatusEthernetMIIRegisterStatusAutoNegNextPageTransmit OBJECT-TYPE
    SYNTAX      Unsigned32 (0..65535)
    MAX-ACCESS  read-only
    STATUS      current
    DESCRIPTION
        "The current read value of the MII auto-negotiation next page transmit
        register on this MAU."

    ::= { dpStatusEthernetMIIRegisterStatusEntry 11 }

dpStatusEthernetMIIRegisterStatusAutoNegLinkPartnerRecNextPage OBJECT-TYPE
    SYNTAX      Unsigned32 (0..65535)
    MAX-ACCESS  read-only
    STATUS      current
    DESCRIPTION
        "The current read value of the MII auto-negotiation link partner received
        next page register on this MAU."

    ::= { dpStatusEthernetMIIRegisterStatusEntry 12 }

dpStatusEthernetMIIRegisterStatusMasterSlaveControlRegister OBJECT-TYPE
    SYNTAX      Unsigned32 (0..65535)
    MAX-ACCESS  read-only
    STATUS      current
    DESCRIPTION
        "The current read value of the MII master slave control register register
        on this MAU."

    ::= { dpStatusEthernetMIIRegisterStatusEntry 13 }

dpStatusEthernetMIIRegisterStatusMasterSlaveStatusRegister OBJECT-TYPE
    SYNTAX      Unsigned32 (0..65535)
    MAX-ACCESS  read-only
    STATUS      current
    DESCRIPTION
        "The current read value of the MII master slave status register register on
        this MAU."

    ::= { dpStatusEthernetMIIRegisterStatusEntry 14 }

dpStatusEthernetMIIRegisterStatusPSEControl OBJECT-TYPE
    SYNTAX      Unsigned32 (0..65535)
    MAX-ACCESS  read-only
    STATUS      current
    DESCRIPTION
        "The current read value of the MII PSE control register on this MAU."

    ::= { dpStatusEthernetMIIRegisterStatusEntry 15 }

dpStatusEthernetMIIRegisterStatusPSEStatus OBJECT-TYPE
    SYNTAX      Unsigned32 (0..65535)
    MAX-ACCESS  read-only
    STATUS      current
    DESCRIPTION
        "The current read value of the MII PSE status register on this MAU."

    ::= { dpStatusEthernetMIIRegisterStatusEntry 16 }

dpStatusEthernetMIIRegisterStatusMMDAccessControl OBJECT-TYPE
    SYNTAX      Unsigned32 (0..65535)
    MAX-ACCESS  read-only
    STATUS      current
    DESCRIPTION
        "The current read value of the MII MMD access control register on this MAU."

    ::= { dpStatusEthernetMIIRegisterStatusEntry 17 }

dpStatusEthernetMIIRegisterStatusMMDAccessAddressData OBJECT-TYPE
    SYNTAX      Unsigned32 (0..65535)
    MAX-ACCESS  read-only
    STATUS      current
    DESCRIPTION
        "The current read value of the MII MMD access address data register on this
        MAU."

    ::= { dpStatusEthernetMIIRegisterStatusEntry 18 }

dpStatusEthernetMIIRegisterStatusExtendedStatus OBJECT-TYPE
    SYNTAX      Unsigned32 (0..65535)
    MAX-ACCESS  read-only
    STATUS      current
    DESCRIPTION
        "The current read value of the MII extended status register on this MAU."

    ::= { dpStatusEthernetMIIRegisterStatusEntry 19 }

dpStatusEthernetMIIRegisterStatusVendor16 OBJECT-TYPE
    SYNTAX      Unsigned32 (0..65535)
    MAX-ACCESS  read-only
    STATUS      current
    DESCRIPTION
        "The current read value of the MII vendor register 16 on this MAU."

    ::= { dpStatusEthernetMIIRegisterStatusEntry 20 }

dpStatusEthernetMIIRegisterStatusVendor17 OBJECT-TYPE
    SYNTAX      Unsigned32 (0..65535)
    MAX-ACCESS  read-only
    STATUS      current
    DESCRIPTION
        "The current read value of the MII vendor register 17 on this MAU."

    ::= { dpStatusEthernetMIIRegisterStatusEntry 21 }

dpStatusEthernetMIIRegisterStatusVendor18 OBJECT-TYPE
    SYNTAX      Unsigned32 (0..65535)
    MAX-ACCESS  read-only
    STATUS      current
    DESCRIPTION
        "The current read value of the MII vendor register 18 on this MAU."

    ::= { dpStatusEthernetMIIRegisterStatusEntry 22 }

dpStatusEthernetMIIRegisterStatusVendor19 OBJECT-TYPE
    SYNTAX      Unsigned32 (0..65535)
    MAX-ACCESS  read-only
    STATUS      current
    DESCRIPTION
        "The current read value of the MII vendor register 19 on this MAU."

    ::= { dpStatusEthernetMIIRegisterStatusEntry 23 }

dpStatusEthernetMIIRegisterStatusVendor20 OBJECT-TYPE
    SYNTAX      Unsigned32 (0..65535)
    MAX-ACCESS  read-only
    STATUS      current
    DESCRIPTION
        "The current read value of the MII vendor register 20 on this MAU."

    ::= { dpStatusEthernetMIIRegisterStatusEntry 24 }

dpStatusEthernetMIIRegisterStatusVendor21 OBJECT-TYPE
    SYNTAX      Unsigned32 (0..65535)
    MAX-ACCESS  read-only
    STATUS      current
    DESCRIPTION
        "The current read value of the MII vendor register 21 on this MAU."

    ::= { dpStatusEthernetMIIRegisterStatusEntry 25 }

dpStatusEthernetMIIRegisterStatusVendor22 OBJECT-TYPE
    SYNTAX      Unsigned32 (0..65535)
    MAX-ACCESS  read-only
    STATUS      current
    DESCRIPTION
        "The current read value of the MII vendor register 22 on this MAU."

    ::= { dpStatusEthernetMIIRegisterStatusEntry 26 }

dpStatusEthernetMIIRegisterStatusVendor23 OBJECT-TYPE
    SYNTAX      Unsigned32 (0..65535)
    MAX-ACCESS  read-only
    STATUS      current
    DESCRIPTION
        "The current read value of the MII vendor register 23 on this MAU."

    ::= { dpStatusEthernetMIIRegisterStatusEntry 27 }

dpStatusEthernetMIIRegisterStatusVendor24 OBJECT-TYPE
    SYNTAX      Unsigned32 (0..65535)
    MAX-ACCESS  read-only
    STATUS      current
    DESCRIPTION
        "The current read value of the MII vendor register 24 on this MAU."

    ::= { dpStatusEthernetMIIRegisterStatusEntry 28 }

dpStatusEthernetMIIRegisterStatusVendor25 OBJECT-TYPE
    SYNTAX      Unsigned32 (0..65535)
    MAX-ACCESS  read-only
    STATUS      current
    DESCRIPTION
        "The current read value of the MII vendor register 25 on this MAU."

    ::= { dpStatusEthernetMIIRegisterStatusEntry 29 }

dpStatusEthernetMIIRegisterStatusVendor26 OBJECT-TYPE
    SYNTAX      Unsigned32 (0..65535)
    MAX-ACCESS  read-only
    STATUS      current
    DESCRIPTION
        "The current read value of the MII vendor register 26 on this MAU."

    ::= { dpStatusEthernetMIIRegisterStatusEntry 30 }

dpStatusEthernetMIIRegisterStatusVendor27 OBJECT-TYPE
    SYNTAX      Unsigned32 (0..65535)
    MAX-ACCESS  read-only
    STATUS      current
    DESCRIPTION
        "The current read value of the MII vendor register 27 on this MAU."

    ::= { dpStatusEthernetMIIRegisterStatusEntry 31 }

dpStatusEthernetMIIRegisterStatusVendor28 OBJECT-TYPE
    SYNTAX      Unsigned32 (0..65535)
    MAX-ACCESS  read-only
    STATUS      current
    DESCRIPTION
        "The current read value of the MII vendor register 28 on this MAU."

    ::= { dpStatusEthernetMIIRegisterStatusEntry 32 }

dpStatusEthernetMIIRegisterStatusVendor29 OBJECT-TYPE
    SYNTAX      Unsigned32 (0..65535)
    MAX-ACCESS  read-only
    STATUS      current
    DESCRIPTION
        "The current read value of the MII vendor register 29 on this MAU."

    ::= { dpStatusEthernetMIIRegisterStatusEntry 33 }

dpStatusEthernetMIIRegisterStatusVendor30 OBJECT-TYPE
    SYNTAX      Unsigned32 (0..65535)
    MAX-ACCESS  read-only
    STATUS      current
    DESCRIPTION
        "The current read value of the MII vendor register 30 on this MAU."

    ::= { dpStatusEthernetMIIRegisterStatusEntry 34 }

dpStatusEthernetMIIRegisterStatusVendor31 OBJECT-TYPE
    SYNTAX      Unsigned32 (0..65535)
    MAX-ACCESS  read-only
    STATUS      current
    DESCRIPTION
        "The current read value of the MII vendor register 31 on this MAU."

    ::= { dpStatusEthernetMIIRegisterStatusEntry 35 }

--

dpStatusEthernetCountersStatusTable OBJECT-TYPE
    SYNTAX      SEQUENCE OF DPStatusEthernetCountersStatusEntry
    MAX-ACCESS  not-accessible
    STATUS      current
    DESCRIPTION
        "This table provides the detailed statistics available for each Ethernet
        device on the system. Note that different interfaces on different models
        keep different statistics, so some entries in this table may have no
        value."

    ::= { dpStatus 132 }

dpStatusEthernetCountersStatusEntry OBJECT-TYPE
    SYNTAX      DPStatusEthernetCountersStatusEntry
    MAX-ACCESS  not-accessible
    STATUS      current
    DESCRIPTION "Table row."
    INDEX { dpStatusEthernetCountersStatusInterfaceIndex }

    ::= { dpStatusEthernetCountersStatusTable 1 }

DPStatusEthernetCountersStatusEntry ::= SEQUENCE {
    dpStatusEthernetCountersStatusInterfaceIndex    Integer32,
    dpStatusEthernetCountersStatusName    DisplayString,
    dpStatusEthernetCountersStatusInUnicastPackets    Counter64,
    dpStatusEthernetCountersStatusInMulticastPackets    Counter64,
    dpStatusEthernetCountersStatusInBroadcastPackets    Counter64,
    dpStatusEthernetCountersStatusOutUnicastPackets    Counter64,
    dpStatusEthernetCountersStatusOutMulticastPackets    Counter64,
    dpStatusEthernetCountersStatusOutBroadcastPackets    Counter64,
    dpStatusEthernetCountersStatusInOctets    Counter64,
    dpStatusEthernetCountersStatusOutOctets    Counter64,
    dpStatusEthernetCountersStatusInErrors    Counter64,
    dpStatusEthernetCountersStatusOutErrors    Counter64,
    dpStatusEthernetCountersStatusOutDiscards    Counter64,
    dpStatusEthernetCountersStatusAlignmentErrors    Counter64,
    dpStatusEthernetCountersStatusFCSErrors    Counter64,
    dpStatusEthernetCountersStatusSingleCollisionFrames    Counter64,
    dpStatusEthernetCountersStatusMultipleCollisionFrames    Counter64,
    dpStatusEthernetCountersStatusSQETestErrors    Counter64,
    dpStatusEthernetCountersStatusDeferredTransmissions    Counter64,
    dpStatusEthernetCountersStatusLateCollisions    Counter64,
    dpStatusEthernetCountersStatusExcessiveCollisions    Counter64,
    dpStatusEthernetCountersStatusInternalMacTransmitErrors    Counter64,
    dpStatusEthernetCountersStatusCarrierSenseErrors    Counter64,
    dpStatusEthernetCountersStatusFrameTooShorts    Counter64,
    dpStatusEthernetCountersStatusFrameTooLongs    Counter64,
    dpStatusEthernetCountersStatusInternalMacReceiveErrors    Counter64,
    dpStatusEthernetCountersStatusInPauseFrames    Counter64,
    dpStatusEthernetCountersStatusOutPauseFrames    Counter64
}

dpStatusEthernetCountersStatusInterfaceIndex OBJECT-TYPE
    SYNTAX      Integer32 (1..2147483647)
    MAX-ACCESS  read-only
    STATUS      current
    DESCRIPTION
        "The value of the SNMP ifIndex column in the ifTable for this interface."

    ::= { dpStatusEthernetCountersStatusEntry 1 }

dpStatusEthernetCountersStatusName OBJECT-TYPE
    SYNTAX      DisplayString
    MAX-ACCESS  read-only
    STATUS      current
    DESCRIPTION
        "The configuration name of this interface."

    ::= { dpStatusEthernetCountersStatusEntry 2 }

dpStatusEthernetCountersStatusInUnicastPackets OBJECT-TYPE
    SYNTAX      Counter64
    UNITS       "packets"
    MAX-ACCESS  read-only
    STATUS      current
    DESCRIPTION
        "The number of unicast packets received on this interface."

    ::= { dpStatusEthernetCountersStatusEntry 3 }

dpStatusEthernetCountersStatusInMulticastPackets OBJECT-TYPE
    SYNTAX      Counter64
    UNITS       "packets"
    MAX-ACCESS  read-only
    STATUS      current
    DESCRIPTION
        "The number of multicast packets received on this interface."

    ::= { dpStatusEthernetCountersStatusEntry 4 }

dpStatusEthernetCountersStatusInBroadcastPackets OBJECT-TYPE
    SYNTAX      Counter64
    UNITS       "packets"
    MAX-ACCESS  read-only
    STATUS      current
    DESCRIPTION
        "The number of broadcast packets received on this interface."

    ::= { dpStatusEthernetCountersStatusEntry 5 }

dpStatusEthernetCountersStatusOutUnicastPackets OBJECT-TYPE
    SYNTAX      Counter64
    UNITS       "packets"
    MAX-ACCESS  read-only
    STATUS      current
    DESCRIPTION
        "The number of unicast packets transmitted on this interface."

    ::= { dpStatusEthernetCountersStatusEntry 6 }

dpStatusEthernetCountersStatusOutMulticastPackets OBJECT-TYPE
    SYNTAX      Counter64
    UNITS       "packets"
    MAX-ACCESS  read-only
    STATUS      current
    DESCRIPTION
        "The number of multicast packets transmitted on this interface."

    ::= { dpStatusEthernetCountersStatusEntry 7 }

dpStatusEthernetCountersStatusOutBroadcastPackets OBJECT-TYPE
    SYNTAX      Counter64
    UNITS       "packets"
    MAX-ACCESS  read-only
    STATUS      current
    DESCRIPTION
        "The number of broadcast packets transmitted on this interface."

    ::= { dpStatusEthernetCountersStatusEntry 8 }

dpStatusEthernetCountersStatusInOctets OBJECT-TYPE
    SYNTAX      Counter64
    UNITS       "bytes"
    MAX-ACCESS  read-only
    STATUS      current
    DESCRIPTION
        "The number of bytes received on this interface at the MAC level."

    ::= { dpStatusEthernetCountersStatusEntry 9 }

dpStatusEthernetCountersStatusOutOctets OBJECT-TYPE
    SYNTAX      Counter64
    UNITS       "bytes"
    MAX-ACCESS  read-only
    STATUS      current
    DESCRIPTION
        "The number of bytes transmitted on this interface at the MAC level."

    ::= { dpStatusEthernetCountersStatusEntry 10 }

dpStatusEthernetCountersStatusInErrors OBJECT-TYPE
    SYNTAX      Counter64
    MAX-ACCESS  read-only
    STATUS      current
    DESCRIPTION
        "The total number of receive errors on this interface."

    ::= { dpStatusEthernetCountersStatusEntry 11 }

dpStatusEthernetCountersStatusOutErrors OBJECT-TYPE
    SYNTAX      Counter64
    MAX-ACCESS  read-only
    STATUS      current
    DESCRIPTION
        "The total number of transmit errors on this interface."

    ::= { dpStatusEthernetCountersStatusEntry 12 }

dpStatusEthernetCountersStatusOutDiscards OBJECT-TYPE
    SYNTAX      Counter64
    MAX-ACCESS  read-only
    STATUS      current
    DESCRIPTION
        "The number of packets not transmitted for flow control reasons."

    ::= { dpStatusEthernetCountersStatusEntry 13 }

dpStatusEthernetCountersStatusAlignmentErrors OBJECT-TYPE
    SYNTAX      Counter64
    MAX-ACCESS  read-only
    STATUS      current
    DESCRIPTION
        "The number of packets received on this interface that were not an integral
        number of bytes in length."

    ::= { dpStatusEthernetCountersStatusEntry 14 }

dpStatusEthernetCountersStatusFCSErrors OBJECT-TYPE
    SYNTAX      Counter64
    MAX-ACCESS  read-only
    STATUS      current
    DESCRIPTION
        "The number of packets received on this interface with an invalid Frame
        Check Sequence (checksum). This does not include FCS errors on packets
        that were too long or too short."

    ::= { dpStatusEthernetCountersStatusEntry 15 }

dpStatusEthernetCountersStatusSingleCollisionFrames OBJECT-TYPE
    SYNTAX      Counter64
    MAX-ACCESS  read-only
    STATUS      current
    DESCRIPTION
        "The number of packets sucessfully transmitted on this interface after a
        single collision. This can only happen when the interface is running in
        Half-Duplex mode."

    ::= { dpStatusEthernetCountersStatusEntry 16 }

dpStatusEthernetCountersStatusMultipleCollisionFrames OBJECT-TYPE
    SYNTAX      Counter64
    MAX-ACCESS  read-only
    STATUS      current
    DESCRIPTION
        "The number of packets sucessfully transmitted on this interface after
        multiple collisions, but less than 16 collisions. This can only happen
        when the interface is running in Half-Duplex mode."

    ::= { dpStatusEthernetCountersStatusEntry 17 }

dpStatusEthernetCountersStatusSQETestErrors OBJECT-TYPE
    SYNTAX      Counter64
    MAX-ACCESS  read-only
    STATUS      current
    DESCRIPTION
        "The number of times that an SQE test error was encountered. This only can
        happen when the link is operating in 10BASE-T Half-Duplex."

    ::= { dpStatusEthernetCountersStatusEntry 18 }

dpStatusEthernetCountersStatusDeferredTransmissions OBJECT-TYPE
    SYNTAX      Counter64
    MAX-ACCESS  read-only
    STATUS      current
    DESCRIPTION
        "The number of frames for which the first transmission attempt was deferred
        because the medium was busy. This can only happen when the interface is
        running in Half-Duplex mode."

    ::= { dpStatusEthernetCountersStatusEntry 19 }

dpStatusEthernetCountersStatusLateCollisions OBJECT-TYPE
    SYNTAX      Counter64
    MAX-ACCESS  read-only
    STATUS      current
    DESCRIPTION
        "The number of times that a collision was detected later than one slot time
        after the transmission of a packet. This can only happen when the
        interface is running in Half-Duplex mode."

    ::= { dpStatusEthernetCountersStatusEntry 20 }

dpStatusEthernetCountersStatusExcessiveCollisions OBJECT-TYPE
    SYNTAX      Counter64
    MAX-ACCESS  read-only
    STATUS      current
    DESCRIPTION
        "The number of times that transmission of a packet failed because it
        encountered sixteen collisions in a row. This can only happen when the
        interface is running in Half-Duplex mode."

    ::= { dpStatusEthernetCountersStatusEntry 21 }

dpStatusEthernetCountersStatusInternalMacTransmitErrors OBJECT-TYPE
    SYNTAX      Counter64
    MAX-ACCESS  read-only
    STATUS      current
    DESCRIPTION
        "The number of times that transmission of packets failed due to errors
        inside the MAC layer of the Ethernet interface. These may be due to
        temporary resource limitations."

    ::= { dpStatusEthernetCountersStatusEntry 22 }

dpStatusEthernetCountersStatusCarrierSenseErrors OBJECT-TYPE
    SYNTAX      Counter64
    MAX-ACCESS  read-only
    STATUS      current
    DESCRIPTION
        "The number transmitted packets during which there were failures of carrier
        sense. This can only happen when the interface is running in Half-Duplex
        mode."

    ::= { dpStatusEthernetCountersStatusEntry 23 }

dpStatusEthernetCountersStatusFrameTooShorts OBJECT-TYPE
    SYNTAX      Counter64
    MAX-ACCESS  read-only
    STATUS      current
    DESCRIPTION
        "The number of received packets that were shorter than 64 bytes. This can
        be the result of a collision. Such packages are also known as runts."

    ::= { dpStatusEthernetCountersStatusEntry 24 }

dpStatusEthernetCountersStatusFrameTooLongs OBJECT-TYPE
    SYNTAX      Counter64
    MAX-ACCESS  read-only
    STATUS      current
    DESCRIPTION
        "The number of received packets that were longer than the configured MTU.
        This can be the result of a collision, as well as due to incompatible
        configuration."

    ::= { dpStatusEthernetCountersStatusEntry 25 }

dpStatusEthernetCountersStatusInternalMacReceiveErrors OBJECT-TYPE
    SYNTAX      Counter64
    MAX-ACCESS  read-only
    STATUS      current
    DESCRIPTION
        "The number of times that reception of packets failed due to errors inside
        the MAC layer of the Ethernet interface. These may be due to temporary
        resource limitations."

    ::= { dpStatusEthernetCountersStatusEntry 26 }

dpStatusEthernetCountersStatusInPauseFrames OBJECT-TYPE
    SYNTAX      Counter64
    MAX-ACCESS  read-only
    STATUS      current
    DESCRIPTION
        "The number of pause frames received."

    ::= { dpStatusEthernetCountersStatusEntry 27 }

dpStatusEthernetCountersStatusOutPauseFrames OBJECT-TYPE
    SYNTAX      Counter64
    MAX-ACCESS  read-only
    STATUS      current
    DESCRIPTION
        "The number of pause frames transmitted."

    ::= { dpStatusEthernetCountersStatusEntry 28 }

--

dpStatusVoltageSensorsTable OBJECT-TYPE
    SYNTAX      SEQUENCE OF DPStatusVoltageSensorsEntry
    MAX-ACCESS  not-accessible
    STATUS      current
    DESCRIPTION
        "Sensors that read voltages, from the power supplies and other components
        of the appliance."

    ::= { dpStatus 140 }

dpStatusVoltageSensorsEntry OBJECT-TYPE
    SYNTAX      DPStatusVoltageSensorsEntry
    MAX-ACCESS  not-accessible
    STATUS      current
    DESCRIPTION "Table row."
    INDEX { IMPLIED dpStatusVoltageSensorsName }

    ::= { dpStatusVoltageSensorsTable 1 }

DPStatusVoltageSensorsEntry ::= SEQUENCE {
    dpStatusVoltageSensorsName    DisplayString,
    dpStatusVoltageSensorsValue    Integer32,
    dpStatusVoltageSensorsLowerCriticalThreshold    Integer32,
    dpStatusVoltageSensorsUpperCriticalThreshold    Integer32,
    dpStatusVoltageSensorsReadingStatus    INTEGER
}

dpStatusVoltageSensorsName OBJECT-TYPE
    SYNTAX      DisplayString
    MAX-ACCESS  read-only
    STATUS      current
    DESCRIPTION
        "The name of the voltage sensor that is being monitored."

    ::= { dpStatusVoltageSensorsEntry 1 }

dpStatusVoltageSensorsValue OBJECT-TYPE
    SYNTAX      Integer32
    UNITS       "mV"
    MAX-ACCESS  read-only
    STATUS      current
    DESCRIPTION
        "The most recent reading of the voltage sensor in millivolts. There are
        only three significant digits."

    ::= { dpStatusVoltageSensorsEntry 2 }

dpStatusVoltageSensorsLowerCriticalThreshold OBJECT-TYPE
    SYNTAX      Integer32
    UNITS       "mV"
    MAX-ACCESS  read-only
    STATUS      current
    DESCRIPTION
        "The lowest allowable reading of the voltage sensor in millivolts."

    ::= { dpStatusVoltageSensorsEntry 3 }

dpStatusVoltageSensorsUpperCriticalThreshold OBJECT-TYPE
    SYNTAX      Integer32
    UNITS       "mV"
    MAX-ACCESS  read-only
    STATUS      current
    DESCRIPTION
        "The highest allowable reading of the voltage sensor in millivolts."

    ::= { dpStatusVoltageSensorsEntry 4 }

dpStatusVoltageSensorsReadingStatus OBJECT-TYPE
    SYNTAX      INTEGER { 
                        lowerNonRecoverable(1),
                        lowerCritical(2),
                        lowerNonCritical(3),
                        ok(4),
                        upperNonCritical(5),
                        upperCritical(6),
                        upperNonRecoverable(7),
                        failure(8),
                        noReading(9),
                        invalid(10)
                }
    MAX-ACCESS  read-only
    STATUS      current
    DESCRIPTION
        "An indicator of whether the current voltage is OK or the voltage exceeds
        the upper or lower critical threshold. If the status is not OK, check
        whether the temperature is too high or the fan does not work. If the
        temperature is normal and the fan works, the appliance must have failed.
        Replace the appliance."

    ::= { dpStatusVoltageSensorsEntry 5 }

--

dpStatusTemperatureSensorsTable OBJECT-TYPE
    SYNTAX      SEQUENCE OF DPStatusTemperatureSensorsEntry
    MAX-ACCESS  not-accessible
    STATUS      current
    DESCRIPTION
        "Sensors that read temperatures, both of the air flowing through the
        appliance and of key components in the appliance."

    ::= { dpStatus 141 }

dpStatusTemperatureSensorsEntry OBJECT-TYPE
    SYNTAX      DPStatusTemperatureSensorsEntry
    MAX-ACCESS  not-accessible
    STATUS      current
    DESCRIPTION "Table row."
    INDEX { IMPLIED dpStatusTemperatureSensorsName }

    ::= { dpStatusTemperatureSensorsTable 1 }

DPStatusTemperatureSensorsEntry ::= SEQUENCE {
    dpStatusTemperatureSensorsName    DisplayString,
    dpStatusTemperatureSensorsValue    Integer32,
    dpStatusTemperatureSensorsUpperNonCriticalThreshold    Integer32,
    dpStatusTemperatureSensorsUpperNonRecoverableThreshold    Integer32,
    dpStatusTemperatureSensorsReadingStatus    INTEGER,
    dpStatusTemperatureSensorsUpperCriticalThreshold    Integer32
}

dpStatusTemperatureSensorsName OBJECT-TYPE
    SYNTAX      DisplayString
    MAX-ACCESS  read-only
    STATUS      current
    DESCRIPTION
        "The name of the temperature sensor that is being monitored."

    ::= { dpStatusTemperatureSensorsEntry 1 }

dpStatusTemperatureSensorsValue OBJECT-TYPE
    SYNTAX      Integer32
    UNITS       "Degrees C"
    MAX-ACCESS  read-only
    STATUS      current
    DESCRIPTION
        "The most recent reading of the temperature sensor in degree Celsius. There
        are only three significant digits."

    ::= { dpStatusTemperatureSensorsEntry 2 }

dpStatusTemperatureSensorsUpperNonCriticalThreshold OBJECT-TYPE
    SYNTAX      Integer32
    MAX-ACCESS  read-only
    STATUS      current
    DESCRIPTION
        "The temperature at which a warning of high temperature occurs. If the
        current temperature is above this value, investigate the cause and correct
        the problem."

    ::= { dpStatusTemperatureSensorsEntry 3 }

dpStatusTemperatureSensorsUpperNonRecoverableThreshold OBJECT-TYPE
    SYNTAX      Integer32
    MAX-ACCESS  read-only
    STATUS      current
    DESCRIPTION
        "The temperature at which a risk of permanent damage to the appliance
        exists. If the current temperature is above this threshold, correct the
        problem immediately; otherwise, turn off the power supply of the
        appliance."

    ::= { dpStatusTemperatureSensorsEntry 4 }

dpStatusTemperatureSensorsReadingStatus OBJECT-TYPE
    SYNTAX      INTEGER { 
                        lowerNonRecoverable(1),
                        lowerCritical(2),
                        lowerNonCritical(3),
                        ok(4),
                        upperNonCritical(5),
                        upperCritical(6),
                        upperNonRecoverable(7),
                        failure(8),
                        noReading(9),
                        invalid(10)
                }
    MAX-ACCESS  read-only
    STATUS      current
    DESCRIPTION
        "An indicator of whether the current temperature is OK or exceeds the
        warning, danger, or critical threshold."

    ::= { dpStatusTemperatureSensorsEntry 5 }

dpStatusTemperatureSensorsUpperCriticalThreshold OBJECT-TYPE
    SYNTAX      Integer32
    MAX-ACCESS  read-only
    STATUS      current
    DESCRIPTION
        "The temperature at which a critical error of high temperature occurs. If
        the current temperature is above this value, correct the problem
        immediately."

    ::= { dpStatusTemperatureSensorsEntry 6 }

--

dpStatusOtherSensorsTable OBJECT-TYPE
    SYNTAX      SEQUENCE OF DPStatusOtherSensorsEntry
    MAX-ACCESS  not-accessible
    STATUS      current
    DESCRIPTION
        "Sensors that have true or false values."

    ::= { dpStatus 142 }

dpStatusOtherSensorsEntry OBJECT-TYPE
    SYNTAX      DPStatusOtherSensorsEntry
    MAX-ACCESS  not-accessible
    STATUS      current
    DESCRIPTION "Table row."
    INDEX { IMPLIED dpStatusOtherSensorsName }

    ::= { dpStatusOtherSensorsTable 1 }

DPStatusOtherSensorsEntry ::= SEQUENCE {
    dpStatusOtherSensorsName    DisplayString,
    dpStatusOtherSensorsValue    INTEGER,
    dpStatusOtherSensorsReadingStatus    INTEGER
}

dpStatusOtherSensorsName OBJECT-TYPE
    SYNTAX      DisplayString
    MAX-ACCESS  read-only
    STATUS      current
    DESCRIPTION
        "The name of the sensor that is being monitored. The name is in the form of
        a descriptive predicate. If the value of the sensor is true, the
        descriptive predicate is true; if the value of the sensor is false, the
        descriptive predicate is false. For example, the sensor name Intrusion
        detected with a value of false means that intrusion is not detected."

    ::= { dpStatusOtherSensorsEntry 1 }

dpStatusOtherSensorsValue OBJECT-TYPE
    SYNTAX      INTEGER { 
                        true(1),
                        false(2)
                }
    MAX-ACCESS  read-only
    STATUS      current
    DESCRIPTION
        "The value of the sensor. The value is either true or false."

    ::= { dpStatusOtherSensorsEntry 2 }

dpStatusOtherSensorsReadingStatus OBJECT-TYPE
    SYNTAX      INTEGER { 
                        lowerNonRecoverable(1),
                        lowerCritical(2),
                        lowerNonCritical(3),
                        ok(4),
                        upperNonCritical(5),
                        upperCritical(6),
                        upperNonRecoverable(7),
                        failure(8),
                        noReading(9),
                        invalid(10)
                }
    MAX-ACCESS  read-only
    STATUS      current
    DESCRIPTION
        "The current status of the sensor. The status can be one of the following
        values: #b#OK#/b#: The reading of the sensor is normal. #b#Failure#/b#:
        The reading of the sensor indicates a problem or a failure in the
        appliance. #b#No reading#/b#: No reading of the sensor is available at
        this time. An internal hardware or software error might occur. Contact IBM
        Support. #b#Invalid#/b#: The DataPower software requested a sensor reading
        by using an invalid sensor identifier. An internal DataPower software
        error might occur. Contact IBM Support."

    ::= { dpStatusOtherSensorsEntry 3 }

dpStatusBattery OBJECT IDENTIFIER ::= { dpStatus 143 }

dpStatusBatteryInstallationDate OBJECT-TYPE
    SYNTAX      DisplayString
    MAX-ACCESS  read-only
    STATUS      current
    DESCRIPTION
        "The date that the system battery was last marked as replaced. This will
        read 'Unavailable' on DataPower 9001 and 9002 systems, as they do not
        track battery status."

    ::= { dpStatusBattery 1 }

--

dpStatusPowerSensorsTable OBJECT-TYPE
    SYNTAX      SEQUENCE OF DPStatusPowerSensorsEntry
    MAX-ACCESS  not-accessible
    STATUS      current
    DESCRIPTION
        "Sensors that read electrical power, from the power supplies and other
        components of the appliance."

    ::= { dpStatus 144 }

dpStatusPowerSensorsEntry OBJECT-TYPE
    SYNTAX      DPStatusPowerSensorsEntry
    MAX-ACCESS  not-accessible
    STATUS      current
    DESCRIPTION "Table row."
    INDEX { IMPLIED dpStatusPowerSensorsName }

    ::= { dpStatusPowerSensorsTable 1 }

DPStatusPowerSensorsEntry ::= SEQUENCE {
    dpStatusPowerSensorsName    DisplayString,
    dpStatusPowerSensorsValue    Integer32
}

dpStatusPowerSensorsName OBJECT-TYPE
    SYNTAX      DisplayString
    MAX-ACCESS  read-only
    STATUS      current
    DESCRIPTION
        "The name of the power sensor that is being monitored."

    ::= { dpStatusPowerSensorsEntry 1 }

dpStatusPowerSensorsValue OBJECT-TYPE
    SYNTAX      Integer32
    UNITS       "mW"
    MAX-ACCESS  read-only
    STATUS      current
    DESCRIPTION
        "The most recent reading of the power sensor in milliwatts. There are only
        three significant digits."

    ::= { dpStatusPowerSensorsEntry 2 }

--

dpStatusPCIBusTable OBJECT-TYPE
    SYNTAX      SEQUENCE OF DPStatusPCIBusEntry
    MAX-ACCESS  not-accessible
    STATUS      current
    DESCRIPTION
        "List of the PCI functions on the system. They are identified by domain,
        bus, device, and function."

    ::= { dpStatus 150 }

dpStatusPCIBusEntry OBJECT-TYPE
    SYNTAX      DPStatusPCIBusEntry
    MAX-ACCESS  not-accessible
    STATUS      current
    DESCRIPTION "Table row."
    INDEX { IMPLIED dpStatusPCIBusAddress }

    ::= { dpStatusPCIBusTable 1 }

DPStatusPCIBusEntry ::= SEQUENCE {
    dpStatusPCIBusAddress    DisplayString,
    dpStatusPCIBusVendorID    Unsigned32,
    dpStatusPCIBusDeviceID    Unsigned32,
    dpStatusPCIBusClass    Unsigned32,
    dpStatusPCIBusRevision    Unsigned32,
    dpStatusPCIBusInterruptLine    Unsigned32
}

dpStatusPCIBusAddress OBJECT-TYPE
    SYNTAX      DisplayString
    MAX-ACCESS  read-only
    STATUS      current
    DESCRIPTION
        "The PCI address of this function. This is a series of hexadecimal numbers,
        in the format xxxx:xx:xx.x, with each group being domain, bus, target, and
        function in turn. So 0000:01:02.3 is domain 0, bus 1, target 2, and
        function 3."

    ::= { dpStatusPCIBusEntry 1 }

dpStatusPCIBusVendorID OBJECT-TYPE
    SYNTAX      Unsigned32 (0..65535)
    MAX-ACCESS  read-only
    STATUS      current
    DESCRIPTION
        "The vendor identification of this PCI function."

    ::= { dpStatusPCIBusEntry 2 }

dpStatusPCIBusDeviceID OBJECT-TYPE
    SYNTAX      Unsigned32 (0..65535)
    MAX-ACCESS  read-only
    STATUS      current
    DESCRIPTION
        "The device identification of this PCI function. Each vendor assigns their
        own device identifications."

    ::= { dpStatusPCIBusEntry 3 }

dpStatusPCIBusClass OBJECT-TYPE
    SYNTAX      Unsigned32 (0..65535)
    MAX-ACCESS  read-only
    STATUS      current
    DESCRIPTION
        "The class of this PCI function. Class values are assigned by the PCI SIG."

    ::= { dpStatusPCIBusEntry 4 }

dpStatusPCIBusRevision OBJECT-TYPE
    SYNTAX      Unsigned32 (0..256)
    MAX-ACCESS  read-only
    STATUS      current
    DESCRIPTION
        "The Revision of this PCI function."

    ::= { dpStatusPCIBusEntry 5 }

dpStatusPCIBusInterruptLine OBJECT-TYPE
    SYNTAX      Unsigned32 (0..256)
    MAX-ACCESS  read-only
    STATUS      current
    DESCRIPTION
        "The interrupt line assigned to this PCI function, if any. If none is
        assigned, no value is displayed."

    ::= { dpStatusPCIBusEntry 6 }

--

dpStatusSQLStatusTable OBJECT-TYPE
    SYNTAX      SEQUENCE OF DPStatusSQLStatusEntry
    MAX-ACCESS  not-accessible
    STATUS      current
    DESCRIPTION
        "SQL data source statistics."

    ::= { dpStatus 152 }

dpStatusSQLStatusEntry OBJECT-TYPE
    SYNTAX      DPStatusSQLStatusEntry
    MAX-ACCESS  not-accessible
    STATUS      current
    DESCRIPTION "Table row."
    INDEX { IMPLIED dpConfigSQLDataSourceIndex }

    ::= { dpStatusSQLStatusTable 1 }

DPStatusSQLStatusEntry ::= SEQUENCE {
    dpStatusSQLStatusDataSource    DisplayString,
    dpStatusSQLStatusReadRequests    Unsigned32,
    dpStatusSQLStatusWriteRequests    Unsigned32,
    dpStatusSQLStatusFailedReadRequests    Unsigned32,
    dpStatusSQLStatusFailedWriteRequests    Unsigned32
}

dpStatusSQLStatusDataSource OBJECT-TYPE
    SYNTAX      DisplayString
    MAX-ACCESS  read-only
    STATUS      current
    DESCRIPTION
        "Name of the SQL data source."

    ::= { dpStatusSQLStatusEntry 1 }

dpStatusSQLStatusReadRequests OBJECT-TYPE
    SYNTAX      Unsigned32
    MAX-ACCESS  read-only
    STATUS      current
    DESCRIPTION
        "Number of read requests to this SQL data source."

    ::= { dpStatusSQLStatusEntry 2 }

dpStatusSQLStatusWriteRequests OBJECT-TYPE
    SYNTAX      Unsigned32
    MAX-ACCESS  read-only
    STATUS      current
    DESCRIPTION
        "Number of modify requests to this SQL data source."

    ::= { dpStatusSQLStatusEntry 3 }

dpStatusSQLStatusFailedReadRequests OBJECT-TYPE
    SYNTAX      Unsigned32
    MAX-ACCESS  read-only
    STATUS      current
    DESCRIPTION
        "Number of failed read requests to this SQL data source."

    ::= { dpStatusSQLStatusEntry 4 }

dpStatusSQLStatusFailedWriteRequests OBJECT-TYPE
    SYNTAX      Unsigned32
    MAX-ACCESS  read-only
    STATUS      current
    DESCRIPTION
        "Number of failed modify requests to this SQL data source."

    ::= { dpStatusSQLStatusEntry 5 }

--

dpStatusHTTPTransactions2Table OBJECT-TYPE
    SYNTAX      SEQUENCE OF DPStatusHTTPTransactions2Entry
    MAX-ACCESS  not-accessible
    STATUS      current
    DESCRIPTION
        "Transaction rates for services. The rates are integers that represent the
        number of transactions per second (tps) over the specified time periods.
        Because of rounding and the 10 second refresh interval, the status
        provider displays 0 tps for services although these services processed
        transactions during that time period. Note that the status provider does
        not include current transactions."

    ::= { dpStatus 153 }

dpStatusHTTPTransactions2Entry OBJECT-TYPE
    SYNTAX      DPStatusHTTPTransactions2Entry
    MAX-ACCESS  not-accessible
    STATUS      current
    DESCRIPTION "Table row."
    INDEX { dpStatusHTTPTransactions2serviceClass, IMPLIED dpStatusHTTPTransactions2proxy }

    ::= { dpStatusHTTPTransactions2Table 1 }

DPStatusHTTPTransactions2Entry ::= SEQUENCE {
    dpStatusHTTPTransactions2serviceClass    INTEGER,
    dpStatusHTTPTransactions2proxy    DisplayString,
    dpStatusHTTPTransactions2tenSeconds    Unsigned32,
    dpStatusHTTPTransactions2oneMinute    Unsigned32,
    dpStatusHTTPTransactions2tenMinutes    Unsigned32,
    dpStatusHTTPTransactions2oneHour    Unsigned32,
    dpStatusHTTPTransactions2oneDay    Unsigned32
}

dpStatusHTTPTransactions2serviceClass OBJECT-TYPE
    SYNTAX      INTEGER { 
                        xSLProxyService(19),
                        xMLFirewallService(42),
                        wSGateway(95),
                        multiProtocolGateway(101),
                        webAppFW(132),
                        b2BGateway(195),
                        webTokenService(266),
                        apiGateway(360)
                }
    MAX-ACCESS  read-only
    STATUS      current
    DESCRIPTION
        "The type of service."

    ::= { dpStatusHTTPTransactions2Entry 1 }

dpStatusHTTPTransactions2proxy OBJECT-TYPE
    SYNTAX      DisplayString
    MAX-ACCESS  read-only
    STATUS      current
    DESCRIPTION
        "The name of the service."

    ::= { dpStatusHTTPTransactions2Entry 2 }

dpStatusHTTPTransactions2tenSeconds OBJECT-TYPE
    SYNTAX      Unsigned32
    UNITS       "tps"
    MAX-ACCESS  read-only
    STATUS      current
    DESCRIPTION
        "The transactions per second over the previous 10 seconds."

    ::= { dpStatusHTTPTransactions2Entry 3 }

dpStatusHTTPTransactions2oneMinute OBJECT-TYPE
    SYNTAX      Unsigned32
    UNITS       "tps"
    MAX-ACCESS  read-only
    STATUS      current
    DESCRIPTION
        "The transactions per second over the previous minute."

    ::= { dpStatusHTTPTransactions2Entry 4 }

dpStatusHTTPTransactions2tenMinutes OBJECT-TYPE
    SYNTAX      Unsigned32
    UNITS       "tps"
    MAX-ACCESS  read-only
    STATUS      current
    DESCRIPTION
        "The transactions per second over the previous 10 minutes."

    ::= { dpStatusHTTPTransactions2Entry 5 }

dpStatusHTTPTransactions2oneHour OBJECT-TYPE
    SYNTAX      Unsigned32
    UNITS       "tps"
    MAX-ACCESS  read-only
    STATUS      current
    DESCRIPTION
        "The transactions per second over the previous hour."

    ::= { dpStatusHTTPTransactions2Entry 6 }

dpStatusHTTPTransactions2oneDay OBJECT-TYPE
    SYNTAX      Unsigned32
    UNITS       "tps"
    MAX-ACCESS  read-only
    STATUS      current
    DESCRIPTION
        "The transactions per second over the previous day."

    ::= { dpStatusHTTPTransactions2Entry 7 }

--

dpStatusHTTPMeanTransactionTime2Table OBJECT-TYPE
    SYNTAX      SEQUENCE OF DPStatusHTTPMeanTransactionTime2Entry
    MAX-ACCESS  not-accessible
    STATUS      current
    DESCRIPTION
        "Mean transaction times"

    ::= { dpStatus 154 }

dpStatusHTTPMeanTransactionTime2Entry OBJECT-TYPE
    SYNTAX      DPStatusHTTPMeanTransactionTime2Entry
    MAX-ACCESS  not-accessible
    STATUS      current
    DESCRIPTION "Table row."
    INDEX { dpStatusHTTPMeanTransactionTime2serviceClass, IMPLIED dpStatusHTTPMeanTransactionTime2proxy }

    ::= { dpStatusHTTPMeanTransactionTime2Table 1 }

DPStatusHTTPMeanTransactionTime2Entry ::= SEQUENCE {
    dpStatusHTTPMeanTransactionTime2serviceClass    INTEGER,
    dpStatusHTTPMeanTransactionTime2proxy    DisplayString,
    dpStatusHTTPMeanTransactionTime2tenSeconds    Counter32,
    dpStatusHTTPMeanTransactionTime2oneMinute    Counter32,
    dpStatusHTTPMeanTransactionTime2tenMinutes    Counter32,
    dpStatusHTTPMeanTransactionTime2oneHour    Counter32,
    dpStatusHTTPMeanTransactionTime2oneDay    Counter32
}

dpStatusHTTPMeanTransactionTime2serviceClass OBJECT-TYPE
    SYNTAX      INTEGER { 
                        xSLProxyService(19),
                        xMLFirewallService(42),
                        wSGateway(95),
                        multiProtocolGateway(101),
                        webAppFW(132),
                        b2BGateway(195),
                        webTokenService(266),
                        apiGateway(360)
                }
    MAX-ACCESS  read-only
    STATUS      current
    DESCRIPTION
        "Service name"

    ::= { dpStatusHTTPMeanTransactionTime2Entry 1 }

dpStatusHTTPMeanTransactionTime2proxy OBJECT-TYPE
    SYNTAX      DisplayString
    MAX-ACCESS  read-only
    STATUS      current
    DESCRIPTION
        "Proxy service name"

    ::= { dpStatusHTTPMeanTransactionTime2Entry 2 }

dpStatusHTTPMeanTransactionTime2tenSeconds OBJECT-TYPE
    SYNTAX      Counter32
    UNITS       "ms"
    MAX-ACCESS  read-only
    STATUS      current
    DESCRIPTION
        "The mean transaction time over the last 10 seconds."

    ::= { dpStatusHTTPMeanTransactionTime2Entry 3 }

dpStatusHTTPMeanTransactionTime2oneMinute OBJECT-TYPE
    SYNTAX      Counter32
    UNITS       "ms"
    MAX-ACCESS  read-only
    STATUS      current
    DESCRIPTION
        "The mean transaction time over the last minute."

    ::= { dpStatusHTTPMeanTransactionTime2Entry 4 }

dpStatusHTTPMeanTransactionTime2tenMinutes OBJECT-TYPE
    SYNTAX      Counter32
    UNITS       "ms"
    MAX-ACCESS  read-only
    STATUS      current
    DESCRIPTION
        "The mean transaction time over the last 10 minutes."

    ::= { dpStatusHTTPMeanTransactionTime2Entry 5 }

dpStatusHTTPMeanTransactionTime2oneHour OBJECT-TYPE
    SYNTAX      Counter32
    UNITS       "ms"
    MAX-ACCESS  read-only
    STATUS      current
    DESCRIPTION
        "The mean transaction time over the last hour."

    ::= { dpStatusHTTPMeanTransactionTime2Entry 6 }

dpStatusHTTPMeanTransactionTime2oneDay OBJECT-TYPE
    SYNTAX      Counter32
    UNITS       "ms"
    MAX-ACCESS  read-only
    STATUS      current
    DESCRIPTION
        "The mean transaction time over the last day."

    ::= { dpStatusHTTPMeanTransactionTime2Entry 7 }

--

dpStatusXC10GridStatusTable OBJECT-TYPE
    SYNTAX      SEQUENCE OF DPStatusXC10GridStatusEntry
    MAX-ACCESS  not-accessible
    STATUS      current
    DESCRIPTION
        "XC10 Grid statistics."

    ::= { dpStatus 155 }

dpStatusXC10GridStatusEntry OBJECT-TYPE
    SYNTAX      DPStatusXC10GridStatusEntry
    MAX-ACCESS  not-accessible
    STATUS      current
    DESCRIPTION "Table row."
    INDEX { IMPLIED dpConfigXC10GridIndex }

    ::= { dpStatusXC10GridStatusTable 1 }

DPStatusXC10GridStatusEntry ::= SEQUENCE {
    dpStatusXC10GridStatusXC10Grid    DisplayString,
    dpStatusXC10GridStatusReadRequests    Counter64,
    dpStatusXC10GridStatusWriteRequests    Counter64,
    dpStatusXC10GridStatusDeleteRequests    Counter64,
    dpStatusXC10GridStatusCacheHits    Counter64,
    dpStatusXC10GridStatusCacheMisses    Counter64,
    dpStatusXC10GridStatusFailedReadRequests    Counter64,
    dpStatusXC10GridStatusFailedWriteRequests    Counter64,
    dpStatusXC10GridStatusFailedDeleteRequests    Counter64
}

dpStatusXC10GridStatusXC10Grid OBJECT-TYPE
    SYNTAX      DisplayString
    MAX-ACCESS  read-only
    STATUS      current
    DESCRIPTION
        "Name of the XC10 Grid."

    ::= { dpStatusXC10GridStatusEntry 1 }

dpStatusXC10GridStatusReadRequests OBJECT-TYPE
    SYNTAX      Counter64
    MAX-ACCESS  read-only
    STATUS      current
    DESCRIPTION
        "Number of read requests to this grid."

    ::= { dpStatusXC10GridStatusEntry 2 }

dpStatusXC10GridStatusWriteRequests OBJECT-TYPE
    SYNTAX      Counter64
    MAX-ACCESS  read-only
    STATUS      current
    DESCRIPTION
        "Number of write requests to this grid."

    ::= { dpStatusXC10GridStatusEntry 3 }

dpStatusXC10GridStatusDeleteRequests OBJECT-TYPE
    SYNTAX      Counter64
    MAX-ACCESS  read-only
    STATUS      current
    DESCRIPTION
        "Number of delete requests to this grid."

    ::= { dpStatusXC10GridStatusEntry 4 }

dpStatusXC10GridStatusCacheHits OBJECT-TYPE
    SYNTAX      Counter64
    MAX-ACCESS  read-only
    STATUS      current
    DESCRIPTION
        "Number of requests served by this grid."

    ::= { dpStatusXC10GridStatusEntry 5 }

dpStatusXC10GridStatusCacheMisses OBJECT-TYPE
    SYNTAX      Counter64
    MAX-ACCESS  read-only
    STATUS      current
    DESCRIPTION
        "Number of requests unable to be served by this grid."

    ::= { dpStatusXC10GridStatusEntry 6 }

dpStatusXC10GridStatusFailedReadRequests OBJECT-TYPE
    SYNTAX      Counter64
    MAX-ACCESS  read-only
    STATUS      current
    DESCRIPTION
        "Number of failed read requests to this grid."

    ::= { dpStatusXC10GridStatusEntry 7 }

dpStatusXC10GridStatusFailedWriteRequests OBJECT-TYPE
    SYNTAX      Counter64
    MAX-ACCESS  read-only
    STATUS      current
    DESCRIPTION
        "Number of failed write requests to this grid."

    ::= { dpStatusXC10GridStatusEntry 8 }

dpStatusXC10GridStatusFailedDeleteRequests OBJECT-TYPE
    SYNTAX      Counter64
    MAX-ACCESS  read-only
    STATUS      current
    DESCRIPTION
        "Number of failed delete requests to this grid."

    ::= { dpStatusXC10GridStatusEntry 9 }

--

dpStatusIMSConnectstatusTable OBJECT-TYPE
    SYNTAX      SEQUENCE OF DPStatusIMSConnectstatusEntry
    MAX-ACCESS  not-accessible
    STATUS      current
    DESCRIPTION
        "IMS Connect status."

    ::= { dpStatus 163 }

dpStatusIMSConnectstatusEntry OBJECT-TYPE
    SYNTAX      DPStatusIMSConnectstatusEntry
    MAX-ACCESS  not-accessible
    STATUS      current
    DESCRIPTION "Table row."
    INDEX { IMPLIED dpConfigIMSConnectIndex }

    ::= { dpStatusIMSConnectstatusTable 1 }

DPStatusIMSConnectstatusEntry ::= SEQUENCE {
    dpStatusIMSConnectstatusIMSConnect    DisplayString,
    dpStatusIMSConnectstatusRequests    Unsigned32,
    dpStatusIMSConnectstatusResponses    Unsigned32,
    dpStatusIMSConnectstatusRequestErrors    Unsigned32,
    dpStatusIMSConnectstatusResponseErrors    Unsigned32
}

dpStatusIMSConnectstatusIMSConnect OBJECT-TYPE
    SYNTAX      DisplayString
    MAX-ACCESS  read-only
    STATUS      current
    DESCRIPTION
        "IMS Connect object."

    ::= { dpStatusIMSConnectstatusEntry 1 }

dpStatusIMSConnectstatusRequests OBJECT-TYPE
    SYNTAX      Unsigned32
    MAX-ACCESS  read-only
    STATUS      current
    DESCRIPTION
        "The number of requests successfully received and sent to IMS Connect."

    ::= { dpStatusIMSConnectstatusEntry 2 }

dpStatusIMSConnectstatusResponses OBJECT-TYPE
    SYNTAX      Unsigned32
    MAX-ACCESS  read-only
    STATUS      current
    DESCRIPTION
        "The number of responses received from IMS Connect."

    ::= { dpStatusIMSConnectstatusEntry 3 }

dpStatusIMSConnectstatusRequestErrors OBJECT-TYPE
    SYNTAX      Unsigned32
    MAX-ACCESS  read-only
    STATUS      current
    DESCRIPTION
        "The number of errors during processing of requests."

    ::= { dpStatusIMSConnectstatusEntry 4 }

dpStatusIMSConnectstatusResponseErrors OBJECT-TYPE
    SYNTAX      Unsigned32
    MAX-ACCESS  read-only
    STATUS      current
    DESCRIPTION
        "The number of errors during processing of responses."

    ::= { dpStatusIMSConnectstatusEntry 5 }

--

dpStatusWSOperationsStatusSimpleIndexTable OBJECT-TYPE
    SYNTAX      SEQUENCE OF DPStatusWSOperationsStatusSimpleIndexEntry
    MAX-ACCESS  not-accessible
    STATUS      current
    DESCRIPTION "Note: this obsoletes dpStatusWSOperationsStatus"

    ::= { dpStatus 164 }

dpStatusWSOperationsStatusSimpleIndexEntry OBJECT-TYPE
    SYNTAX      DPStatusWSOperationsStatusSimpleIndexEntry
    MAX-ACCESS  not-accessible
    STATUS      current
    DESCRIPTION "Table row."
    INDEX { dpConfigWSGatewayIndex, dpStatusWSOperationsStatusSimpleIndexGatewayRegistrationIndex }

    ::= { dpStatusWSOperationsStatusSimpleIndexTable 1 }

DPStatusWSOperationsStatusSimpleIndexEntry ::= SEQUENCE {
    dpStatusWSOperationsStatusSimpleIndexWSGateway    DisplayString,
    dpStatusWSOperationsStatusSimpleIndexGatewayRegistrationIndex    Unsigned32,
    dpStatusWSOperationsStatusSimpleIndexInterface    IpAddress,
    dpStatusWSOperationsStatusSimpleIndexPort    Unsigned32,
    dpStatusWSOperationsStatusSimpleIndexURL    DisplayString,
    dpStatusWSOperationsStatusSimpleIndexSOAPAction    DisplayString,
    dpStatusWSOperationsStatusSimpleIndexSOAPBody    DisplayString,
    dpStatusWSOperationsStatusSimpleIndexStatus    INTEGER,
    dpStatusWSOperationsStatusSimpleIndexRemoteURL    DisplayString,
    dpStatusWSOperationsStatusSimpleIndexFrontsideProtocol    INTEGER,
    dpStatusWSOperationsStatusSimpleIndexBacksideProtocol    INTEGER
}

dpStatusWSOperationsStatusSimpleIndexWSGateway OBJECT-TYPE
    SYNTAX      DisplayString
    MAX-ACCESS  read-only
    STATUS      current
    DESCRIPTION "No description yet."

    ::= { dpStatusWSOperationsStatusSimpleIndexEntry 1 }

dpStatusWSOperationsStatusSimpleIndexGatewayRegistrationIndex OBJECT-TYPE
    SYNTAX      Unsigned32
    MAX-ACCESS  read-only
    STATUS      current
    DESCRIPTION "No description yet."

    ::= { dpStatusWSOperationsStatusSimpleIndexEntry 2 }

dpStatusWSOperationsStatusSimpleIndexInterface OBJECT-TYPE
    SYNTAX      IpAddress
    MAX-ACCESS  read-only
    STATUS      current
    DESCRIPTION "No description yet."

    ::= { dpStatusWSOperationsStatusSimpleIndexEntry 3 }

dpStatusWSOperationsStatusSimpleIndexPort OBJECT-TYPE
    SYNTAX      Unsigned32 (0..65535)
    MAX-ACCESS  read-only
    STATUS      current
    DESCRIPTION "No description yet."

    ::= { dpStatusWSOperationsStatusSimpleIndexEntry 4 }

dpStatusWSOperationsStatusSimpleIndexURL OBJECT-TYPE
    SYNTAX      DisplayString
    MAX-ACCESS  read-only
    STATUS      current
    DESCRIPTION "No description yet."

    ::= { dpStatusWSOperationsStatusSimpleIndexEntry 5 }

dpStatusWSOperationsStatusSimpleIndexSOAPAction OBJECT-TYPE
    SYNTAX      DisplayString
    MAX-ACCESS  read-only
    STATUS      current
    DESCRIPTION "No description yet."

    ::= { dpStatusWSOperationsStatusSimpleIndexEntry 6 }

dpStatusWSOperationsStatusSimpleIndexSOAPBody OBJECT-TYPE
    SYNTAX      DisplayString
    MAX-ACCESS  read-only
    STATUS      current
    DESCRIPTION "No description yet."

    ::= { dpStatusWSOperationsStatusSimpleIndexEntry 7 }

dpStatusWSOperationsStatusSimpleIndexStatus OBJECT-TYPE
    SYNTAX      INTEGER { 
                        registered(1),
                        unregistered(2),
                        registrationError(3)
                }
    MAX-ACCESS  read-only
    STATUS      current
    DESCRIPTION "No description yet."

    ::= { dpStatusWSOperationsStatusSimpleIndexEntry 8 }

dpStatusWSOperationsStatusSimpleIndexRemoteURL OBJECT-TYPE
    SYNTAX      DisplayString
    MAX-ACCESS  read-only
    STATUS      current
    DESCRIPTION "No description yet."

    ::= { dpStatusWSOperationsStatusSimpleIndexEntry 9 }

dpStatusWSOperationsStatusSimpleIndexFrontsideProtocol OBJECT-TYPE
    SYNTAX      INTEGER { 
                        default(1),
                        soap-11(2),
                        soap-12(3),
                        http-get(4)
                }
    MAX-ACCESS  read-only
    STATUS      current
    DESCRIPTION "No description yet."

    ::= { dpStatusWSOperationsStatusSimpleIndexEntry 10 }

dpStatusWSOperationsStatusSimpleIndexBacksideProtocol OBJECT-TYPE
    SYNTAX      INTEGER { 
                        default(1),
                        soap-11(2),
                        soap-12(3),
                        http-get(4)
                }
    MAX-ACCESS  read-only
    STATUS      current
    DESCRIPTION "No description yet."

    ::= { dpStatusWSOperationsStatusSimpleIndexEntry 11 }

--

dpStatusDynamicTibcoEMSStatusTable OBJECT-TYPE
    SYNTAX      SEQUENCE OF DPStatusDynamicTibcoEMSStatusEntry
    MAX-ACCESS  not-accessible
    STATUS      current
    DESCRIPTION
        "Status of the Dynamic TIBCO Enterprise Message Service."

    ::= { dpStatus 165 }

dpStatusDynamicTibcoEMSStatusEntry OBJECT-TYPE
    SYNTAX      DPStatusDynamicTibcoEMSStatusEntry
    MAX-ACCESS  not-accessible
    STATUS      current
    DESCRIPTION "Table row."
    INDEX { IMPLIED dpConfigTibcoEMSServerIndex }

    ::= { dpStatusDynamicTibcoEMSStatusTable 1 }

DPStatusDynamicTibcoEMSStatusEntry ::= SEQUENCE {
    dpStatusDynamicTibcoEMSStatusServer    DisplayString,
    dpStatusDynamicTibcoEMSStatusReceivedMessages    Unsigned32,
    dpStatusDynamicTibcoEMSStatusSentMessages    Unsigned32,
    dpStatusDynamicTibcoEMSStatusReceivedFaults    Unsigned32,
    dpStatusDynamicTibcoEMSStatusSentFaults    Unsigned32
}

dpStatusDynamicTibcoEMSStatusServer OBJECT-TYPE
    SYNTAX      DisplayString
    MAX-ACCESS  read-only
    STATUS      current
    DESCRIPTION
        "Name of the TIBCO EMS server object."

    ::= { dpStatusDynamicTibcoEMSStatusEntry 1 }

dpStatusDynamicTibcoEMSStatusReceivedMessages OBJECT-TYPE
    SYNTAX      Unsigned32
    MAX-ACCESS  read-only
    STATUS      current
    DESCRIPTION
        "Number of messages received by this server."

    ::= { dpStatusDynamicTibcoEMSStatusEntry 2 }

dpStatusDynamicTibcoEMSStatusSentMessages OBJECT-TYPE
    SYNTAX      Unsigned32
    MAX-ACCESS  read-only
    STATUS      current
    DESCRIPTION
        "Number of messages sent by this server."

    ::= { dpStatusDynamicTibcoEMSStatusEntry 3 }

dpStatusDynamicTibcoEMSStatusReceivedFaults OBJECT-TYPE
    SYNTAX      Unsigned32
    MAX-ACCESS  read-only
    STATUS      current
    DESCRIPTION
        "Number of errors detected by this server during receive operations."

    ::= { dpStatusDynamicTibcoEMSStatusEntry 4 }

dpStatusDynamicTibcoEMSStatusSentFaults OBJECT-TYPE
    SYNTAX      Unsigned32
    MAX-ACCESS  read-only
    STATUS      current
    DESCRIPTION
        "Number of errors detected by this server during send operations."

    ::= { dpStatusDynamicTibcoEMSStatusEntry 5 }

--

dpStatusRaidVolumeStatusTable OBJECT-TYPE
    SYNTAX      SEQUENCE OF DPStatusRaidVolumeStatusEntry
    MAX-ACCESS  not-accessible
    STATUS      obsolete
    DESCRIPTION
        "Deprecated due to indexing problems.
        Note: this is obsoleted and is replaced by dpStatusRaidVolumeStatus2 as of release 3.8.1"

    ::= { dpStatus 166 }

dpStatusRaidVolumeStatusEntry OBJECT-TYPE
    SYNTAX      DPStatusRaidVolumeStatusEntry
    MAX-ACCESS  not-accessible
    STATUS      obsolete
    DESCRIPTION "Table row."
    INDEX { dpStatusRaidVolumeStatusVolumeNumber }

    ::= { dpStatusRaidVolumeStatusTable 1 }

DPStatusRaidVolumeStatusEntry ::= SEQUENCE {
    dpStatusRaidVolumeStatusVolumeNumber    Unsigned32,
    dpStatusRaidVolumeStatusType    INTEGER,
    dpStatusRaidVolumeStatusVolumeID    Unsigned32,
    dpStatusRaidVolumeStatusNumPhysDisks    Unsigned32,
    dpStatusRaidVolumeStatusState    INTEGER,
    dpStatusRaidVolumeStatusEnabled    INTEGER,
    dpStatusRaidVolumeStatusQuiesced    INTEGER,
    dpStatusRaidVolumeStatusResyncInProgress    INTEGER,
    dpStatusRaidVolumeStatusResyncPercentage    Unsigned32,
    dpStatusRaidVolumeStatusInactiveStatus    INTEGER,
    dpStatusRaidVolumeStatusBadBlockTableFull    INTEGER,
    dpStatusRaidVolumeStatusWriteCachingEnable    INTEGER
}

dpStatusRaidVolumeStatusVolumeNumber OBJECT-TYPE
    SYNTAX      Unsigned32
    MAX-ACCESS  read-only
    STATUS      obsolete
    DESCRIPTION "No description yet."

    ::= { dpStatusRaidVolumeStatusEntry 1 }

dpStatusRaidVolumeStatusType OBJECT-TYPE
    SYNTAX      INTEGER { 
                        unknown(1),
                        raid-0(2),
                        raid-1(3)
                }
    MAX-ACCESS  read-only
    STATUS      obsolete
    DESCRIPTION "No description yet."

    ::= { dpStatusRaidVolumeStatusEntry 2 }

dpStatusRaidVolumeStatusVolumeID OBJECT-TYPE
    SYNTAX      Unsigned32
    MAX-ACCESS  read-only
    STATUS      obsolete
    DESCRIPTION "No description yet."

    ::= { dpStatusRaidVolumeStatusEntry 3 }

dpStatusRaidVolumeStatusNumPhysDisks OBJECT-TYPE
    SYNTAX      Unsigned32
    MAX-ACCESS  read-only
    STATUS      obsolete
    DESCRIPTION "No description yet."

    ::= { dpStatusRaidVolumeStatusEntry 4 }

dpStatusRaidVolumeStatusState OBJECT-TYPE
    SYNTAX      INTEGER { 
                        optimal(1),
                        degraded(2),
                        failed(3),
                        missing(4)
                }
    MAX-ACCESS  read-only
    STATUS      obsolete
    DESCRIPTION "No description yet."

    ::= { dpStatusRaidVolumeStatusEntry 5 }

dpStatusRaidVolumeStatusEnabled OBJECT-TYPE
    SYNTAX      INTEGER { 
                        true(1),
                        false(2)
                }
    MAX-ACCESS  read-only
    STATUS      obsolete
    DESCRIPTION "No description yet."

    ::= { dpStatusRaidVolumeStatusEntry 6 }

dpStatusRaidVolumeStatusQuiesced OBJECT-TYPE
    SYNTAX      INTEGER { 
                        true(1),
                        false(2)
                }
    MAX-ACCESS  read-only
    STATUS      obsolete
    DESCRIPTION "No description yet."

    ::= { dpStatusRaidVolumeStatusEntry 7 }

dpStatusRaidVolumeStatusResyncInProgress OBJECT-TYPE
    SYNTAX      INTEGER { 
                        true(1),
                        false(2)
                }
    MAX-ACCESS  read-only
    STATUS      obsolete
    DESCRIPTION "No description yet."

    ::= { dpStatusRaidVolumeStatusEntry 8 }

dpStatusRaidVolumeStatusResyncPercentage OBJECT-TYPE
    SYNTAX      Unsigned32
    MAX-ACCESS  read-only
    STATUS      obsolete
    DESCRIPTION "No description yet."

    ::= { dpStatusRaidVolumeStatusEntry 9 }

dpStatusRaidVolumeStatusInactiveStatus OBJECT-TYPE
    SYNTAX      INTEGER { 
                        active(1),
                        unknown(2),
                        stale-metadata(3),
                        foreign-volume(4),
                        insufficient-resources(5),
                        clone-volume(6),
                        insufficient-metadata(7),
                        previously-deleted(8)
                }
    MAX-ACCESS  read-only
    STATUS      obsolete
    DESCRIPTION "No description yet."

    ::= { dpStatusRaidVolumeStatusEntry 10 }

dpStatusRaidVolumeStatusBadBlockTableFull OBJECT-TYPE
    SYNTAX      INTEGER { 
                        true(1),
                        false(2)
                }
    MAX-ACCESS  read-only
    STATUS      obsolete
    DESCRIPTION "No description yet."

    ::= { dpStatusRaidVolumeStatusEntry 11 }

dpStatusRaidVolumeStatusWriteCachingEnable OBJECT-TYPE
    SYNTAX      INTEGER { 
                        true(1),
                        false(2)
                }
    MAX-ACCESS  read-only
    STATUS      obsolete
    DESCRIPTION "No description yet."

    ::= { dpStatusRaidVolumeStatusEntry 12 }

--

dpStatusRaidPhysDiskStatusTable OBJECT-TYPE
    SYNTAX      SEQUENCE OF DPStatusRaidPhysDiskStatusEntry
    MAX-ACCESS  not-accessible
    STATUS      obsolete
    DESCRIPTION
        "Deprecated due to indexing problems.
        Note: this is obsoleted and is replaced by dpStatusRaidPhysDiskStatus2 as of release 3.8.1"

    ::= { dpStatus 167 }

dpStatusRaidPhysDiskStatusEntry OBJECT-TYPE
    SYNTAX      DPStatusRaidPhysDiskStatusEntry
    MAX-ACCESS  not-accessible
    STATUS      obsolete
    DESCRIPTION "Table row."
    INDEX { dpStatusRaidPhysDiskStatusVolumeNumber, dpStatusRaidPhysDiskStatusDiskNumber }

    ::= { dpStatusRaidPhysDiskStatusTable 1 }

DPStatusRaidPhysDiskStatusEntry ::= SEQUENCE {
    dpStatusRaidPhysDiskStatusVolumeNumber    Unsigned32,
    dpStatusRaidPhysDiskStatusDiskNumber    Unsigned32,
    dpStatusRaidPhysDiskStatusPhysDiskNum    Unsigned32,
    dpStatusRaidPhysDiskStatusTarget    Unsigned32,
    dpStatusRaidPhysDiskStatusLocation    DisplayString,
    dpStatusRaidPhysDiskStatusState    INTEGER,
    dpStatusRaidPhysDiskStatusRole    INTEGER,
    dpStatusRaidPhysDiskStatusVendorID    DisplayString,
    dpStatusRaidPhysDiskStatusProductID    DisplayString,
    dpStatusRaidPhysDiskStatusRevision    DisplayString,
    dpStatusRaidPhysDiskStatusIdentifier    DisplayString,
    dpStatusRaidPhysDiskStatusOutOfSync    INTEGER,
    dpStatusRaidPhysDiskStatusQuiesced    INTEGER,
    dpStatusRaidPhysDiskStatusInactiveVolume    INTEGER,
    dpStatusRaidPhysDiskStatusOptimalPrevious    INTEGER
}

dpStatusRaidPhysDiskStatusVolumeNumber OBJECT-TYPE
    SYNTAX      Unsigned32
    MAX-ACCESS  read-only
    STATUS      obsolete
    DESCRIPTION "No description yet."

    ::= { dpStatusRaidPhysDiskStatusEntry 1 }

dpStatusRaidPhysDiskStatusDiskNumber OBJECT-TYPE
    SYNTAX      Unsigned32
    MAX-ACCESS  read-only
    STATUS      obsolete
    DESCRIPTION "No description yet."

    ::= { dpStatusRaidPhysDiskStatusEntry 2 }

dpStatusRaidPhysDiskStatusPhysDiskNum OBJECT-TYPE
    SYNTAX      Unsigned32
    MAX-ACCESS  read-only
    STATUS      obsolete
    DESCRIPTION "No description yet."

    ::= { dpStatusRaidPhysDiskStatusEntry 3 }

dpStatusRaidPhysDiskStatusTarget OBJECT-TYPE
    SYNTAX      Unsigned32
    MAX-ACCESS  read-only
    STATUS      obsolete
    DESCRIPTION "No description yet."

    ::= { dpStatusRaidPhysDiskStatusEntry 4 }

dpStatusRaidPhysDiskStatusLocation OBJECT-TYPE
    SYNTAX      DisplayString
    MAX-ACCESS  read-only
    STATUS      obsolete
    DESCRIPTION "No description yet."

    ::= { dpStatusRaidPhysDiskStatusEntry 5 }

dpStatusRaidPhysDiskStatusState OBJECT-TYPE
    SYNTAX      INTEGER { 
                        online(1),
                        missing(2),
                        not-compatible(3),
                        failed(4),
                        initializing(5),
                        requested-offline(6),
                        requested-failed(7),
                        other-offline(8)
                }
    MAX-ACCESS  read-only
    STATUS      obsolete
    DESCRIPTION "No description yet."

    ::= { dpStatusRaidPhysDiskStatusEntry 6 }

dpStatusRaidPhysDiskStatusRole OBJECT-TYPE
    SYNTAX      INTEGER { 
                        other(1),
                        primary(2),
                        secondary(3)
                }
    MAX-ACCESS  read-only
    STATUS      obsolete
    DESCRIPTION "No description yet."

    ::= { dpStatusRaidPhysDiskStatusEntry 7 }

dpStatusRaidPhysDiskStatusVendorID OBJECT-TYPE
    SYNTAX      DisplayString
    MAX-ACCESS  read-only
    STATUS      obsolete
    DESCRIPTION "No description yet."

    ::= { dpStatusRaidPhysDiskStatusEntry 8 }

dpStatusRaidPhysDiskStatusProductID OBJECT-TYPE
    SYNTAX      DisplayString
    MAX-ACCESS  read-only
    STATUS      obsolete
    DESCRIPTION "No description yet."

    ::= { dpStatusRaidPhysDiskStatusEntry 9 }

dpStatusRaidPhysDiskStatusRevision OBJECT-TYPE
    SYNTAX      DisplayString
    MAX-ACCESS  read-only
    STATUS      obsolete
    DESCRIPTION "No description yet."

    ::= { dpStatusRaidPhysDiskStatusEntry 10 }

dpStatusRaidPhysDiskStatusIdentifier OBJECT-TYPE
    SYNTAX      DisplayString
    MAX-ACCESS  read-only
    STATUS      obsolete
    DESCRIPTION "No description yet."

    ::= { dpStatusRaidPhysDiskStatusEntry 11 }

dpStatusRaidPhysDiskStatusOutOfSync OBJECT-TYPE
    SYNTAX      INTEGER { 
                        true(1),
                        false(2)
                }
    MAX-ACCESS  read-only
    STATUS      obsolete
    DESCRIPTION "No description yet."

    ::= { dpStatusRaidPhysDiskStatusEntry 12 }

dpStatusRaidPhysDiskStatusQuiesced OBJECT-TYPE
    SYNTAX      INTEGER { 
                        true(1),
                        false(2)
                }
    MAX-ACCESS  read-only
    STATUS      obsolete
    DESCRIPTION "No description yet."

    ::= { dpStatusRaidPhysDiskStatusEntry 13 }

dpStatusRaidPhysDiskStatusInactiveVolume OBJECT-TYPE
    SYNTAX      INTEGER { 
                        true(1),
                        false(2)
                }
    MAX-ACCESS  read-only
    STATUS      obsolete
    DESCRIPTION "No description yet."

    ::= { dpStatusRaidPhysDiskStatusEntry 14 }

dpStatusRaidPhysDiskStatusOptimalPrevious OBJECT-TYPE
    SYNTAX      INTEGER { 
                        true(1),
                        false(2)
                }
    MAX-ACCESS  read-only
    STATUS      obsolete
    DESCRIPTION "No description yet."

    ::= { dpStatusRaidPhysDiskStatusEntry 15 }

--

dpStatusNDCacheStatusTable OBJECT-TYPE
    SYNTAX      SEQUENCE OF DPStatusNDCacheStatusEntry
    MAX-ACCESS  not-accessible
    STATUS      obsolete
    DESCRIPTION
        "Status of IPv6 Neighbor Discovery translations on all interfaces. Only
        complete cache entries are shown.
        Note: this is obsoleted and is replaced by dpStatusNDCacheStatus2 as of release 6.0.2"

    ::= { dpStatus 174 }

dpStatusNDCacheStatusEntry OBJECT-TYPE
    SYNTAX      DPStatusNDCacheStatusEntry
    MAX-ACCESS  not-accessible
    STATUS      obsolete
    DESCRIPTION "Table row."
    INDEX { dpStatusNDCacheStatusIPAddress, dpStatusNDCacheStatusInterfaceIndex }

    ::= { dpStatusNDCacheStatusTable 1 }

DPStatusNDCacheStatusEntry ::= SEQUENCE {
    dpStatusNDCacheStatusIPAddress    IpAddress,
    dpStatusNDCacheStatusHardwareAddress    MacAddress,
    dpStatusNDCacheStatusInterface    INTEGER,
    dpStatusNDCacheStatusInterfaceIndex    Unsigned32,
    dpStatusNDCacheStatusInterfaceType    INTEGER,
    dpStatusNDCacheStatusVlanName    DisplayString,
    dpStatusNDCacheStatusState    INTEGER
}

dpStatusNDCacheStatusIPAddress OBJECT-TYPE
    SYNTAX      IpAddress
    MAX-ACCESS  read-only
    STATUS      obsolete
    DESCRIPTION
        "The IPv6 address of the network interface node corresponding to the MAC
        address listed in this ND cache entry."

    ::= { dpStatusNDCacheStatusEntry 1 }

dpStatusNDCacheStatusHardwareAddress OBJECT-TYPE
    SYNTAX      MacAddress
    MAX-ACCESS  read-only
    STATUS      obsolete
    DESCRIPTION
        "The MAC address of this network interface node."

    ::= { dpStatusNDCacheStatusEntry 2 }

dpStatusNDCacheStatusInterface OBJECT-TYPE
    SYNTAX      INTEGER { 
                        eth0(1),
                        eth1(2),
                        eth2(3),
                        eth3(4),
                        mgt0(5),
                        eth4(6),
                        eth5(8),
                        eth6(9),
                        eth7(10),
                        eth8(11),
                        eth9(12),
                        eth10(13),
                        tun(14),
                        mgt1(15),
                        eth11(16),
                        eth12(17),
                        eth13(18),
                        eth14(19),
                        eth15(20),
                        eth16(21),
                        eth17(22),
                        eth20(23),
                        eth21(24),
                        eth22(25),
                        eth23(26),
                        eth24(27),
                        eth25(28),
                        eth26(29),
                        eth27(30),
                        eth30(31),
                        eth31(32),
                        eth32(33),
                        eth33(34)
                }
    MAX-ACCESS  read-only
    STATUS      obsolete
    DESCRIPTION
        "The device network interface (such as eth0, eth1) to which this cache
        entry corresponds. If the entry is on a VLAN, this is the Ethernet
        interface that VLAN is on."

    ::= { dpStatusNDCacheStatusEntry 3 }

dpStatusNDCacheStatusInterfaceIndex OBJECT-TYPE
    SYNTAX      Unsigned32 (1..2147483647)
    MAX-ACCESS  read-only
    STATUS      obsolete
    DESCRIPTION
        "The index of the interface holding the cache entry."

    ::= { dpStatusNDCacheStatusEntry 4 }

dpStatusNDCacheStatusInterfaceType OBJECT-TYPE
    SYNTAX      INTEGER { 
                        other(1),
                        ethernet(6),
                        tunnel(131),
                        vLAN(135),
                        aggregate(161)
                }
    MAX-ACCESS  read-only
    STATUS      obsolete
    DESCRIPTION
        "The type of the interface this cache entry is on. Ethernet indicates that
        it is on the base Ethernet MAC interface. VLAN indicates that it is on an
        IEEE 802.1Q VLAN on top of the base Ethernet MAC interface."

    ::= { dpStatusNDCacheStatusEntry 5 }

dpStatusNDCacheStatusVlanName OBJECT-TYPE
    SYNTAX      DisplayString
    MAX-ACCESS  read-only
    STATUS      obsolete
    DESCRIPTION
        "If this ND cache entry is on a VLAN, this is the name of that VLAN."

    ::= { dpStatusNDCacheStatusEntry 6 }

dpStatusNDCacheStatusState OBJECT-TYPE
    SYNTAX      INTEGER { 
                        incomplete(1),
                        reachable(2),
                        stale(3),
                        delay(4),
                        probe(5),
                        failed(6),
                        noarp(7),
                        permanent(8)
                }
    MAX-ACCESS  read-only
    STATUS      obsolete
    DESCRIPTION
        "The life cycle state of the destination address as it pertains to the
        cache."

    ::= { dpStatusNDCacheStatusEntry 7 }

dpStatusIScsiInitiatorStatus OBJECT IDENTIFIER ::= { dpStatus 179 }

dpStatusIScsiInitiatorStatusIScsiName OBJECT-TYPE
    SYNTAX      DisplayString
    MAX-ACCESS  read-only
    STATUS      obsolete
    DESCRIPTION
        "iSCSI qualified name for this initiator."

    ::= { dpStatusIScsiInitiatorStatus 1 }

--

dpStatusIScsiHBAStatusTable OBJECT-TYPE
    SYNTAX      SEQUENCE OF DPStatusIScsiHBAStatusEntry
    MAX-ACCESS  not-accessible
    STATUS      obsolete
    DESCRIPTION
        "Show status of iSCSI host bus adapter.
        Note: this is obsoleted and is replaced by dpStatusIScsiInitiatorStatus as of release 3.8.0.0"

    ::= { dpStatus 180 }

dpStatusIScsiHBAStatusEntry OBJECT-TYPE
    SYNTAX      DPStatusIScsiHBAStatusEntry
    MAX-ACCESS  not-accessible
    STATUS      obsolete
    DESCRIPTION "Table row."
    INDEX { IMPLIED dpStatusIScsiHBAStatusHBAInstance }

    ::= { dpStatusIScsiHBAStatusTable 1 }

DPStatusIScsiHBAStatusEntry ::= SEQUENCE {
    dpStatusIScsiHBAStatusHBAInstance    DisplayString,
    dpStatusIScsiHBAStatusOpState    INTEGER,
    dpStatusIScsiHBAStatusIScsiName    DisplayString,
    dpStatusIScsiHBAStatusIpAddress    IpNetworkAddress,
    dpStatusIScsiHBAStatusDefaultGateway    IpAddress,
    dpStatusIScsiHBAStatusMacAddress    MacAddress,
    dpStatusIScsiHBAStatusLinkStatus    INTEGER,
    dpStatusIScsiHBAStatusUseDHCP    DisplayString
}

dpStatusIScsiHBAStatusHBAInstance OBJECT-TYPE
    SYNTAX      DisplayString
    MAX-ACCESS  read-only
    STATUS      obsolete
    DESCRIPTION
        "Host bus adapter instance."

    ::= { dpStatusIScsiHBAStatusEntry 1 }

dpStatusIScsiHBAStatusOpState OBJECT-TYPE
    SYNTAX      INTEGER { 
                        up(1),
                        down(2)
                }
    MAX-ACCESS  read-only
    STATUS      obsolete
    DESCRIPTION
        "The intended state of the interface."

    ::= { dpStatusIScsiHBAStatusEntry 2 }

dpStatusIScsiHBAStatusIScsiName OBJECT-TYPE
    SYNTAX      DisplayString
    MAX-ACCESS  read-only
    STATUS      obsolete
    DESCRIPTION
        "A valid iSCSI name for this HBA instance."

    ::= { dpStatusIScsiHBAStatusEntry 3 }

dpStatusIScsiHBAStatusIpAddress OBJECT-TYPE
    SYNTAX      IpNetworkAddress
    MAX-ACCESS  read-only
    STATUS      obsolete
    DESCRIPTION
        "IP address for this HBA instance."

    ::= { dpStatusIScsiHBAStatusEntry 4 }

dpStatusIScsiHBAStatusDefaultGateway OBJECT-TYPE
    SYNTAX      IpAddress
    MAX-ACCESS  read-only
    STATUS      obsolete
    DESCRIPTION
        "Default IP gateway for this HBA instance."

    ::= { dpStatusIScsiHBAStatusEntry 5 }

dpStatusIScsiHBAStatusMacAddress OBJECT-TYPE
    SYNTAX      MacAddress
    MAX-ACCESS  read-only
    STATUS      obsolete
    DESCRIPTION
        "MAC address for this HBA."

    ::= { dpStatusIScsiHBAStatusEntry 6 }

dpStatusIScsiHBAStatusLinkStatus OBJECT-TYPE
    SYNTAX      INTEGER { 
                        ok(1),
                        no-link(2)
                }
    MAX-ACCESS  read-only
    STATUS      obsolete
    DESCRIPTION
        "Link state of the HBA."

    ::= { dpStatusIScsiHBAStatusEntry 7 }

dpStatusIScsiHBAStatusUseDHCP OBJECT-TYPE
    SYNTAX      DisplayString
    MAX-ACCESS  read-only
    STATUS      obsolete
    DESCRIPTION
        "Indicates if DHCP is enabled."

    ::= { dpStatusIScsiHBAStatusEntry 8 }

--

dpStatusIScsiTargetStatusTable OBJECT-TYPE
    SYNTAX      SEQUENCE OF DPStatusIScsiTargetStatusEntry
    MAX-ACCESS  not-accessible
    STATUS      obsolete
    DESCRIPTION "Note: this is obsoleted and is replaced by dpStatusFirmwareVersion as of release 7.0.0.0"

    ::= { dpStatus 181 }

dpStatusIScsiTargetStatusEntry OBJECT-TYPE
    SYNTAX      DPStatusIScsiTargetStatusEntry
    MAX-ACCESS  not-accessible
    STATUS      obsolete
    DESCRIPTION "Table row."
    INDEX { IMPLIED dpStatusIScsiTargetStatusTargetInstance }

    ::= { dpStatusIScsiTargetStatusTable 1 }

DPStatusIScsiTargetStatusEntry ::= SEQUENCE {
    dpStatusIScsiTargetStatusTargetInstance    DisplayString,
    dpStatusIScsiTargetStatusOpState    INTEGER,
    dpStatusIScsiTargetStatusConnectionState    DisplayString,
    dpStatusIScsiTargetStatusTargetName    DisplayString,
    dpStatusIScsiTargetStatusHostAddress    DisplayString,
    dpStatusIScsiTargetStatusPortNumber    Unsigned32
}

dpStatusIScsiTargetStatusTargetInstance OBJECT-TYPE
    SYNTAX      DisplayString
    MAX-ACCESS  read-only
    STATUS      obsolete
    DESCRIPTION
        "iSCSI target instance."

    ::= { dpStatusIScsiTargetStatusEntry 1 }

dpStatusIScsiTargetStatusOpState OBJECT-TYPE
    SYNTAX      INTEGER { 
                        up(1),
                        down(2)
                }
    MAX-ACCESS  read-only
    STATUS      obsolete
    DESCRIPTION "No description yet."

    ::= { dpStatusIScsiTargetStatusEntry 2 }

dpStatusIScsiTargetStatusConnectionState OBJECT-TYPE
    SYNTAX      DisplayString
    MAX-ACCESS  read-only
    STATUS      obsolete
    DESCRIPTION
        "Connection state for this instance."

    ::= { dpStatusIScsiTargetStatusEntry 3 }

dpStatusIScsiTargetStatusTargetName OBJECT-TYPE
    SYNTAX      DisplayString
    MAX-ACCESS  read-only
    STATUS      obsolete
    DESCRIPTION
        "iSCSI target name for this instance."

    ::= { dpStatusIScsiTargetStatusEntry 4 }

dpStatusIScsiTargetStatusHostAddress OBJECT-TYPE
    SYNTAX      DisplayString
    MAX-ACCESS  read-only
    STATUS      obsolete
    DESCRIPTION
        "Host address of this target instance."

    ::= { dpStatusIScsiTargetStatusEntry 5 }

dpStatusIScsiTargetStatusPortNumber OBJECT-TYPE
    SYNTAX      Unsigned32 (0..65535)
    MAX-ACCESS  read-only
    STATUS      obsolete
    DESCRIPTION
        "Port number of this target instance."

    ::= { dpStatusIScsiTargetStatusEntry 6 }

--

dpStatusIScsiVolumeStatusTable OBJECT-TYPE
    SYNTAX      SEQUENCE OF DPStatusIScsiVolumeStatusEntry
    MAX-ACCESS  not-accessible
    STATUS      obsolete
    DESCRIPTION "Note: this is obsoleted and is replaced by dpStatusFirmwareVersion as of release 7.0.0.0"

    ::= { dpStatus 182 }

dpStatusIScsiVolumeStatusEntry OBJECT-TYPE
    SYNTAX      DPStatusIScsiVolumeStatusEntry
    MAX-ACCESS  not-accessible
    STATUS      obsolete
    DESCRIPTION "Table row."
    INDEX { IMPLIED dpStatusIScsiVolumeStatusVolumeInstance }

    ::= { dpStatusIScsiVolumeStatusTable 1 }

DPStatusIScsiVolumeStatusEntry ::= SEQUENCE {
    dpStatusIScsiVolumeStatusVolumeInstance    DisplayString,
    dpStatusIScsiVolumeStatusOpState    INTEGER,
    dpStatusIScsiVolumeStatusReadOnly    DisplayString,
    dpStatusIScsiVolumeStatusDirectory    DisplayString,
    dpStatusIScsiVolumeStatusLunValue    Unsigned32
}

dpStatusIScsiVolumeStatusVolumeInstance OBJECT-TYPE
    SYNTAX      DisplayString
    MAX-ACCESS  read-only
    STATUS      obsolete
    DESCRIPTION
        "iSCSI volume instance."

    ::= { dpStatusIScsiVolumeStatusEntry 1 }

dpStatusIScsiVolumeStatusOpState OBJECT-TYPE
    SYNTAX      INTEGER { 
                        up(1),
                        down(2)
                }
    MAX-ACCESS  read-only
    STATUS      obsolete
    DESCRIPTION "No description yet."

    ::= { dpStatusIScsiVolumeStatusEntry 2 }

dpStatusIScsiVolumeStatusReadOnly OBJECT-TYPE
    SYNTAX      DisplayString
    MAX-ACCESS  read-only
    STATUS      obsolete
    DESCRIPTION "No description yet."

    ::= { dpStatusIScsiVolumeStatusEntry 3 }

dpStatusIScsiVolumeStatusDirectory OBJECT-TYPE
    SYNTAX      DisplayString
    MAX-ACCESS  read-only
    STATUS      obsolete
    DESCRIPTION
        "Mount point for this volume instance."

    ::= { dpStatusIScsiVolumeStatusEntry 4 }

dpStatusIScsiVolumeStatusLunValue OBJECT-TYPE
    SYNTAX      Unsigned32 (0..65535)
    MAX-ACCESS  read-only
    STATUS      obsolete
    DESCRIPTION
        "LUN for this volume instance."

    ::= { dpStatusIScsiVolumeStatusEntry 5 }

--

dpStatusWSOperationMetricsSimpleIndexTable OBJECT-TYPE
    SYNTAX      SEQUENCE OF DPStatusWSOperationMetricsSimpleIndexEntry
    MAX-ACCESS  not-accessible
    STATUS      current
    DESCRIPTION
        "Common metrics for web service endpoints
        Note: this obsoletes dpStatusWSOperationMetrics"

    ::= { dpStatus 183 }

dpStatusWSOperationMetricsSimpleIndexEntry OBJECT-TYPE
    SYNTAX      DPStatusWSOperationMetricsSimpleIndexEntry
    MAX-ACCESS  not-accessible
    STATUS      current
    DESCRIPTION "Table row."
    INDEX { dpStatusWSOperationMetricsSimpleIndexID }

    ::= { dpStatusWSOperationMetricsSimpleIndexTable 1 }

DPStatusWSOperationMetricsSimpleIndexEntry ::= SEQUENCE {
    dpStatusWSOperationMetricsSimpleIndexID    Unsigned32,
    dpStatusWSOperationMetricsSimpleIndexServiceEndpoint    DisplayString,
    dpStatusWSOperationMetricsSimpleIndexPortType    DisplayString,
    dpStatusWSOperationMetricsSimpleIndexOperation    DisplayString,
    dpStatusWSOperationMetricsSimpleIndexNumberOfRequests    Counter32,
    dpStatusWSOperationMetricsSimpleIndexNumberOfFailedRequests    Counter32,
    dpStatusWSOperationMetricsSimpleIndexNumberOfSuccessfulRequests    Counter32,
    dpStatusWSOperationMetricsSimpleIndexServiceTime    DPTimeIntervalMillis,
    dpStatusWSOperationMetricsSimpleIndexMaxResponseTime    DPTimeIntervalMillis,
    dpStatusWSOperationMetricsSimpleIndexLastResponseTime    DPTimeIntervalMillis,
    dpStatusWSOperationMetricsSimpleIndexMaxRequestSize    Unsigned32,
    dpStatusWSOperationMetricsSimpleIndexLastRequestSize    Unsigned32,
    dpStatusWSOperationMetricsSimpleIndexMaxResponseSize    Unsigned32,
    dpStatusWSOperationMetricsSimpleIndexLastResponseSize    Unsigned32
}

dpStatusWSOperationMetricsSimpleIndexID OBJECT-TYPE
    SYNTAX      Unsigned32
    MAX-ACCESS  read-only
    STATUS      current
    DESCRIPTION
        "A unique identifier assigned to the WS Operation."

    ::= { dpStatusWSOperationMetricsSimpleIndexEntry 1 }

dpStatusWSOperationMetricsSimpleIndexServiceEndpoint OBJECT-TYPE
    SYNTAX      DisplayString
    MAX-ACCESS  read-only
    STATUS      current
    DESCRIPTION "No description yet."

    ::= { dpStatusWSOperationMetricsSimpleIndexEntry 2 }

dpStatusWSOperationMetricsSimpleIndexPortType OBJECT-TYPE
    SYNTAX      DisplayString
    MAX-ACCESS  read-only
    STATUS      current
    DESCRIPTION "No description yet."

    ::= { dpStatusWSOperationMetricsSimpleIndexEntry 3 }

dpStatusWSOperationMetricsSimpleIndexOperation OBJECT-TYPE
    SYNTAX      DisplayString
    MAX-ACCESS  read-only
    STATUS      current
    DESCRIPTION "No description yet."

    ::= { dpStatusWSOperationMetricsSimpleIndexEntry 4 }

dpStatusWSOperationMetricsSimpleIndexNumberOfRequests OBJECT-TYPE
    SYNTAX      Counter32
    MAX-ACCESS  read-only
    STATUS      current
    DESCRIPTION "No description yet."

    ::= { dpStatusWSOperationMetricsSimpleIndexEntry 5 }

dpStatusWSOperationMetricsSimpleIndexNumberOfFailedRequests OBJECT-TYPE
    SYNTAX      Counter32
    MAX-ACCESS  read-only
    STATUS      current
    DESCRIPTION "No description yet."

    ::= { dpStatusWSOperationMetricsSimpleIndexEntry 6 }

dpStatusWSOperationMetricsSimpleIndexNumberOfSuccessfulRequests OBJECT-TYPE
    SYNTAX      Counter32
    MAX-ACCESS  read-only
    STATUS      current
    DESCRIPTION "No description yet."

    ::= { dpStatusWSOperationMetricsSimpleIndexEntry 7 }

dpStatusWSOperationMetricsSimpleIndexServiceTime OBJECT-TYPE
    SYNTAX      DPTimeIntervalMillis
    UNITS       "ms"
    MAX-ACCESS  read-only
    STATUS      current
    DESCRIPTION "No description yet."

    ::= { dpStatusWSOperationMetricsSimpleIndexEntry 8 }

dpStatusWSOperationMetricsSimpleIndexMaxResponseTime OBJECT-TYPE
    SYNTAX      DPTimeIntervalMillis
    UNITS       "ms"
    MAX-ACCESS  read-only
    STATUS      current
    DESCRIPTION "No description yet."

    ::= { dpStatusWSOperationMetricsSimpleIndexEntry 9 }

dpStatusWSOperationMetricsSimpleIndexLastResponseTime OBJECT-TYPE
    SYNTAX      DPTimeIntervalMillis
    UNITS       "ms"
    MAX-ACCESS  read-only
    STATUS      current
    DESCRIPTION "No description yet."

    ::= { dpStatusWSOperationMetricsSimpleIndexEntry 10 }

dpStatusWSOperationMetricsSimpleIndexMaxRequestSize OBJECT-TYPE
    SYNTAX      Unsigned32
    UNITS       "bytes"
    MAX-ACCESS  read-only
    STATUS      current
    DESCRIPTION "No description yet."

    ::= { dpStatusWSOperationMetricsSimpleIndexEntry 11 }

dpStatusWSOperationMetricsSimpleIndexLastRequestSize OBJECT-TYPE
    SYNTAX      Unsigned32
    UNITS       "bytes"
    MAX-ACCESS  read-only
    STATUS      current
    DESCRIPTION "No description yet."

    ::= { dpStatusWSOperationMetricsSimpleIndexEntry 12 }

dpStatusWSOperationMetricsSimpleIndexMaxResponseSize OBJECT-TYPE
    SYNTAX      Unsigned32
    UNITS       "bytes"
    MAX-ACCESS  read-only
    STATUS      current
    DESCRIPTION "No description yet."

    ::= { dpStatusWSOperationMetricsSimpleIndexEntry 13 }

dpStatusWSOperationMetricsSimpleIndexLastResponseSize OBJECT-TYPE
    SYNTAX      Unsigned32
    UNITS       "bytes"
    MAX-ACCESS  read-only
    STATUS      current
    DESCRIPTION "No description yet."

    ::= { dpStatusWSOperationMetricsSimpleIndexEntry 14 }

--

dpStatusFibreChannelHBAStatusTable OBJECT-TYPE
    SYNTAX      SEQUENCE OF DPStatusFibreChannelHBAStatusEntry
    MAX-ACCESS  not-accessible
    STATUS      current
    DESCRIPTION "Table."

    ::= { dpStatus 185 }

dpStatusFibreChannelHBAStatusEntry OBJECT-TYPE
    SYNTAX      DPStatusFibreChannelHBAStatusEntry
    MAX-ACCESS  not-accessible
    STATUS      current
    DESCRIPTION "Table row."
    INDEX { IMPLIED dpStatusFibreChannelHBAStatusHBAInstance }

    ::= { dpStatusFibreChannelHBAStatusTable 1 }

DPStatusFibreChannelHBAStatusEntry ::= SEQUENCE {
    dpStatusFibreChannelHBAStatusHBAInstance    DisplayString,
    dpStatusFibreChannelHBAStatusOpState    INTEGER,
    dpStatusFibreChannelHBAStatusWorldWidePortNumber    DisplayString,
    dpStatusFibreChannelHBAStatusPortState    DisplayString,
    dpStatusFibreChannelHBAStatusPortSpeed    DisplayString,
    dpStatusFibreChannelHBAStatusPortType    DisplayString,
    dpStatusFibreChannelHBAStatusSupportedSpeeds    DisplayString
}

dpStatusFibreChannelHBAStatusHBAInstance OBJECT-TYPE
    SYNTAX      DisplayString
    MAX-ACCESS  read-only
    STATUS      current
    DESCRIPTION
        "Host Bus Adapter instance."

    ::= { dpStatusFibreChannelHBAStatusEntry 1 }

dpStatusFibreChannelHBAStatusOpState OBJECT-TYPE
    SYNTAX      INTEGER { 
                        up(1),
                        down(2)
                }
    MAX-ACCESS  read-only
    STATUS      current
    DESCRIPTION "No description yet."

    ::= { dpStatusFibreChannelHBAStatusEntry 2 }

dpStatusFibreChannelHBAStatusWorldWidePortNumber OBJECT-TYPE
    SYNTAX      DisplayString
    MAX-ACCESS  read-only
    STATUS      current
    DESCRIPTION
        "The World Wide Port Number for this HBA instance."

    ::= { dpStatusFibreChannelHBAStatusEntry 3 }

dpStatusFibreChannelHBAStatusPortState OBJECT-TYPE
    SYNTAX      DisplayString
    MAX-ACCESS  read-only
    STATUS      current
    DESCRIPTION
        "The state of the port for this HBA instance."

    ::= { dpStatusFibreChannelHBAStatusEntry 4 }

dpStatusFibreChannelHBAStatusPortSpeed OBJECT-TYPE
    SYNTAX      DisplayString
    MAX-ACCESS  read-only
    STATUS      current
    DESCRIPTION
        "The speed of the port for this HBA instance."

    ::= { dpStatusFibreChannelHBAStatusEntry 5 }

dpStatusFibreChannelHBAStatusPortType OBJECT-TYPE
    SYNTAX      DisplayString
    MAX-ACCESS  read-only
    STATUS      current
    DESCRIPTION
        "The type of the port for this HBA instance."

    ::= { dpStatusFibreChannelHBAStatusEntry 6 }

dpStatusFibreChannelHBAStatusSupportedSpeeds OBJECT-TYPE
    SYNTAX      DisplayString
    MAX-ACCESS  read-only
    STATUS      current
    DESCRIPTION
        "The speeds supported by the port for this HBA instance."

    ::= { dpStatusFibreChannelHBAStatusEntry 7 }

--

dpStatusFibreChannelTargetStatusTable OBJECT-TYPE
    SYNTAX      SEQUENCE OF DPStatusFibreChannelTargetStatusEntry
    MAX-ACCESS  not-accessible
    STATUS      current
    DESCRIPTION "Table."

    ::= { dpStatus 186 }

dpStatusFibreChannelTargetStatusEntry OBJECT-TYPE
    SYNTAX      DPStatusFibreChannelTargetStatusEntry
    MAX-ACCESS  not-accessible
    STATUS      current
    DESCRIPTION "Table row."
    INDEX { IMPLIED dpStatusFibreChannelTargetStatusTargetInstance }

    ::= { dpStatusFibreChannelTargetStatusTable 1 }

DPStatusFibreChannelTargetStatusEntry ::= SEQUENCE {
    dpStatusFibreChannelTargetStatusTargetInstance    DisplayString,
    dpStatusFibreChannelTargetStatusOpState    INTEGER,
    dpStatusFibreChannelTargetStatusWorldWidePortNumber    DisplayString,
    dpStatusFibreChannelTargetStatusPortState    DisplayString
}

dpStatusFibreChannelTargetStatusTargetInstance OBJECT-TYPE
    SYNTAX      DisplayString
    MAX-ACCESS  read-only
    STATUS      current
    DESCRIPTION
        "The Fibre Channel target instance."

    ::= { dpStatusFibreChannelTargetStatusEntry 1 }

dpStatusFibreChannelTargetStatusOpState OBJECT-TYPE
    SYNTAX      INTEGER { 
                        up(1),
                        down(2)
                }
    MAX-ACCESS  read-only
    STATUS      current
    DESCRIPTION "No description yet."

    ::= { dpStatusFibreChannelTargetStatusEntry 2 }

dpStatusFibreChannelTargetStatusWorldWidePortNumber OBJECT-TYPE
    SYNTAX      DisplayString
    MAX-ACCESS  read-only
    STATUS      current
    DESCRIPTION
        "The World Wide Port Number of this target instance."

    ::= { dpStatusFibreChannelTargetStatusEntry 3 }

dpStatusFibreChannelTargetStatusPortState OBJECT-TYPE
    SYNTAX      DisplayString
    MAX-ACCESS  read-only
    STATUS      current
    DESCRIPTION
        "The state of the port of this target instance."

    ::= { dpStatusFibreChannelTargetStatusEntry 4 }

--

dpStatusLLMInstanceStatusTable OBJECT-TYPE
    SYNTAX      SEQUENCE OF DPStatusLLMInstanceStatusEntry
    MAX-ACCESS  not-accessible
    STATUS      current
    DESCRIPTION "Table."

    ::= { dpStatus 190 }

dpStatusLLMInstanceStatusEntry OBJECT-TYPE
    SYNTAX      DPStatusLLMInstanceStatusEntry
    MAX-ACCESS  not-accessible
    STATUS      current
    DESCRIPTION "Table row."
    INDEX { IMPLIED dpStatusLLMInstanceStatusLLMInstance }

    ::= { dpStatusLLMInstanceStatusTable 1 }

DPStatusLLMInstanceStatusEntry ::= SEQUENCE {
    dpStatusLLMInstanceStatusLLMInstance    DisplayString,
    dpStatusLLMInstanceStatusOpState    INTEGER,
    dpStatusLLMInstanceStatusMessagesSent    Counter64,
    dpStatusLLMInstanceStatusPacketsSent    Counter64,
    dpStatusLLMInstanceStatusBytesSent    Counter64,
    dpStatusLLMInstanceStatusRateSent    Counter64,
    dpStatusLLMInstanceStatusReceivedNacks    Counter64,
    dpStatusLLMInstanceStatusRepairSent    Counter64,
    dpStatusLLMInstanceStatusMessagesReceived    Counter64,
    dpStatusLLMInstanceStatusPacketsReceived    Counter64,
    dpStatusLLMInstanceStatusBytesReceived    Counter64,
    dpStatusLLMInstanceStatusRateReceived    Counter64,
    dpStatusLLMInstanceStatusSentNacks    Counter64,
    dpStatusLLMInstanceStatusRepairSentReceived    Counter64,
    dpStatusLLMInstanceStatusPacketLost    Counter64,
    dpStatusLLMInstanceStatusPacketDrop    Counter64,
    dpStatusLLMInstanceStatusPacketDup    Counter64
}

dpStatusLLMInstanceStatusLLMInstance OBJECT-TYPE
    SYNTAX      DisplayString
    MAX-ACCESS  read-only
    STATUS      current
    DESCRIPTION "No description yet."

    ::= { dpStatusLLMInstanceStatusEntry 1 }

dpStatusLLMInstanceStatusOpState OBJECT-TYPE
    SYNTAX      INTEGER { 
                        up(1),
                        down(2)
                }
    MAX-ACCESS  read-only
    STATUS      current
    DESCRIPTION "No description yet."

    ::= { dpStatusLLMInstanceStatusEntry 2 }

dpStatusLLMInstanceStatusMessagesSent OBJECT-TYPE
    SYNTAX      Counter64
    MAX-ACCESS  read-only
    STATUS      current
    DESCRIPTION "No description yet."

    ::= { dpStatusLLMInstanceStatusEntry 3 }

dpStatusLLMInstanceStatusPacketsSent OBJECT-TYPE
    SYNTAX      Counter64
    MAX-ACCESS  read-only
    STATUS      current
    DESCRIPTION "No description yet."

    ::= { dpStatusLLMInstanceStatusEntry 4 }

dpStatusLLMInstanceStatusBytesSent OBJECT-TYPE
    SYNTAX      Counter64
    MAX-ACCESS  read-only
    STATUS      current
    DESCRIPTION "No description yet."

    ::= { dpStatusLLMInstanceStatusEntry 5 }

dpStatusLLMInstanceStatusRateSent OBJECT-TYPE
    SYNTAX      Counter64
    MAX-ACCESS  read-only
    STATUS      current
    DESCRIPTION "No description yet."

    ::= { dpStatusLLMInstanceStatusEntry 6 }

dpStatusLLMInstanceStatusReceivedNacks OBJECT-TYPE
    SYNTAX      Counter64
    MAX-ACCESS  read-only
    STATUS      current
    DESCRIPTION "No description yet."

    ::= { dpStatusLLMInstanceStatusEntry 7 }

dpStatusLLMInstanceStatusRepairSent OBJECT-TYPE
    SYNTAX      Counter64
    MAX-ACCESS  read-only
    STATUS      current
    DESCRIPTION "No description yet."

    ::= { dpStatusLLMInstanceStatusEntry 8 }

dpStatusLLMInstanceStatusMessagesReceived OBJECT-TYPE
    SYNTAX      Counter64
    MAX-ACCESS  read-only
    STATUS      current
    DESCRIPTION "No description yet."

    ::= { dpStatusLLMInstanceStatusEntry 9 }

dpStatusLLMInstanceStatusPacketsReceived OBJECT-TYPE
    SYNTAX      Counter64
    MAX-ACCESS  read-only
    STATUS      current
    DESCRIPTION "No description yet."

    ::= { dpStatusLLMInstanceStatusEntry 10 }

dpStatusLLMInstanceStatusBytesReceived OBJECT-TYPE
    SYNTAX      Counter64
    MAX-ACCESS  read-only
    STATUS      current
    DESCRIPTION "No description yet."

    ::= { dpStatusLLMInstanceStatusEntry 11 }

dpStatusLLMInstanceStatusRateReceived OBJECT-TYPE
    SYNTAX      Counter64
    MAX-ACCESS  read-only
    STATUS      current
    DESCRIPTION "No description yet."

    ::= { dpStatusLLMInstanceStatusEntry 12 }

dpStatusLLMInstanceStatusSentNacks OBJECT-TYPE
    SYNTAX      Counter64
    MAX-ACCESS  read-only
    STATUS      current
    DESCRIPTION "No description yet."

    ::= { dpStatusLLMInstanceStatusEntry 13 }

dpStatusLLMInstanceStatusRepairSentReceived OBJECT-TYPE
    SYNTAX      Counter64
    MAX-ACCESS  read-only
    STATUS      current
    DESCRIPTION "No description yet."

    ::= { dpStatusLLMInstanceStatusEntry 14 }

dpStatusLLMInstanceStatusPacketLost OBJECT-TYPE
    SYNTAX      Counter64
    MAX-ACCESS  read-only
    STATUS      current
    DESCRIPTION "No description yet."

    ::= { dpStatusLLMInstanceStatusEntry 15 }

dpStatusLLMInstanceStatusPacketDrop OBJECT-TYPE
    SYNTAX      Counter64
    MAX-ACCESS  read-only
    STATUS      current
    DESCRIPTION "No description yet."

    ::= { dpStatusLLMInstanceStatusEntry 16 }

dpStatusLLMInstanceStatusPacketDup OBJECT-TYPE
    SYNTAX      Counter64
    MAX-ACCESS  read-only
    STATUS      current
    DESCRIPTION "No description yet."

    ::= { dpStatusLLMInstanceStatusEntry 17 }

--

dpStatusLLMSelectionStatusTable OBJECT-TYPE
    SYNTAX      SEQUENCE OF DPStatusLLMSelectionStatusEntry
    MAX-ACCESS  not-accessible
    STATUS      current
    DESCRIPTION "Table."

    ::= { dpStatus 191 }

dpStatusLLMSelectionStatusEntry OBJECT-TYPE
    SYNTAX      DPStatusLLMSelectionStatusEntry
    MAX-ACCESS  not-accessible
    STATUS      current
    DESCRIPTION "Table row."
    INDEX { dpStatusLLMSelectionStatusName, dpStatusLLMSelectionStatusType }

    ::= { dpStatusLLMSelectionStatusTable 1 }

DPStatusLLMSelectionStatusEntry ::= SEQUENCE {
    dpStatusLLMSelectionStatusName    DisplayString,
    dpStatusLLMSelectionStatusType    INTEGER,
    dpStatusLLMSelectionStatusOpState    INTEGER,
    dpStatusLLMSelectionStatusTrue    Counter64,
    dpStatusLLMSelectionStatusFalse    Counter64,
    dpStatusLLMSelectionStatusUnknown    Counter64,
    dpStatusLLMSelectionStatusInactive    Counter64,
    dpStatusLLMSelectionStatusErrors    Counter64,
    dpStatusLLMSelectionStatusBytes    Counter64
}

dpStatusLLMSelectionStatusName OBJECT-TYPE
    SYNTAX      DisplayString
    MAX-ACCESS  read-only
    STATUS      current
    DESCRIPTION "No description yet."

    ::= { dpStatusLLMSelectionStatusEntry 1 }

dpStatusLLMSelectionStatusType OBJECT-TYPE
    SYNTAX      INTEGER { 
                        route(1),
                        policy(2)
                }
    MAX-ACCESS  read-only
    STATUS      current
    DESCRIPTION "No description yet."

    ::= { dpStatusLLMSelectionStatusEntry 2 }

dpStatusLLMSelectionStatusOpState OBJECT-TYPE
    SYNTAX      INTEGER { 
                        up(1),
                        down(2)
                }
    MAX-ACCESS  read-only
    STATUS      current
    DESCRIPTION "No description yet."

    ::= { dpStatusLLMSelectionStatusEntry 3 }

dpStatusLLMSelectionStatusTrue OBJECT-TYPE
    SYNTAX      Counter64
    MAX-ACCESS  read-only
    STATUS      current
    DESCRIPTION "No description yet."

    ::= { dpStatusLLMSelectionStatusEntry 4 }

dpStatusLLMSelectionStatusFalse OBJECT-TYPE
    SYNTAX      Counter64
    MAX-ACCESS  read-only
    STATUS      current
    DESCRIPTION "No description yet."

    ::= { dpStatusLLMSelectionStatusEntry 5 }

dpStatusLLMSelectionStatusUnknown OBJECT-TYPE
    SYNTAX      Counter64
    MAX-ACCESS  read-only
    STATUS      current
    DESCRIPTION "No description yet."

    ::= { dpStatusLLMSelectionStatusEntry 6 }

dpStatusLLMSelectionStatusInactive OBJECT-TYPE
    SYNTAX      Counter64
    MAX-ACCESS  read-only
    STATUS      current
    DESCRIPTION "No description yet."

    ::= { dpStatusLLMSelectionStatusEntry 7 }

dpStatusLLMSelectionStatusErrors OBJECT-TYPE
    SYNTAX      Counter64
    MAX-ACCESS  read-only
    STATUS      current
    DESCRIPTION "No description yet."

    ::= { dpStatusLLMSelectionStatusEntry 8 }

dpStatusLLMSelectionStatusBytes OBJECT-TYPE
    SYNTAX      Counter64
    MAX-ACCESS  read-only
    STATUS      current
    DESCRIPTION "No description yet."

    ::= { dpStatusLLMSelectionStatusEntry 9 }

--

dpStatusUDPTableTable OBJECT-TYPE
    SYNTAX      SEQUENCE OF DPStatusUDPTableEntry
    MAX-ACCESS  not-accessible
    STATUS      current
    DESCRIPTION
        "This table describes all active UDP connections on the system."

    ::= { dpStatus 192 }

dpStatusUDPTableEntry OBJECT-TYPE
    SYNTAX      DPStatusUDPTableEntry
    MAX-ACCESS  not-accessible
    STATUS      current
    DESCRIPTION "Table row."
    INDEX { dpStatusUDPTablelocalIP, dpStatusUDPTablelocalPort, dpStatusUDPTableremoteIP, dpStatusUDPTableremotePort }

    ::= { dpStatusUDPTableTable 1 }

DPStatusUDPTableEntry ::= SEQUENCE {
    dpStatusUDPTablelocalIP    IpAddress,
    dpStatusUDPTablelocalPort    Unsigned32,
    dpStatusUDPTableremoteIP    IpAddress,
    dpStatusUDPTableremotePort    Unsigned32
}

dpStatusUDPTablelocalIP OBJECT-TYPE
    SYNTAX      IpAddress
    MAX-ACCESS  read-only
    STATUS      current
    DESCRIPTION
        "The local IP address of this UDP connection."

    ::= { dpStatusUDPTableEntry 1 }

dpStatusUDPTablelocalPort OBJECT-TYPE
    SYNTAX      Unsigned32 (0..65535)
    MAX-ACCESS  read-only
    STATUS      current
    DESCRIPTION
        "The local UDP port number."

    ::= { dpStatusUDPTableEntry 2 }

dpStatusUDPTableremoteIP OBJECT-TYPE
    SYNTAX      IpAddress
    MAX-ACCESS  read-only
    STATUS      current
    DESCRIPTION
        "The remote UDP address."

    ::= { dpStatusUDPTableEntry 3 }

dpStatusUDPTableremotePort OBJECT-TYPE
    SYNTAX      Unsigned32 (0..65535)
    MAX-ACCESS  read-only
    STATUS      current
    DESCRIPTION
        "The remote UDP port number."

    ::= { dpStatusUDPTableEntry 4 }

--

dpStatusIGMPStatusTable OBJECT-TYPE
    SYNTAX      SEQUENCE OF DPStatusIGMPStatusEntry
    MAX-ACCESS  not-accessible
    STATUS      current
    DESCRIPTION
        "This table describes all Internet Group Management Protocol (IGMP) status
        on the system."

    ::= { dpStatus 193 }

dpStatusIGMPStatusEntry OBJECT-TYPE
    SYNTAX      DPStatusIGMPStatusEntry
    MAX-ACCESS  not-accessible
    STATUS      current
    DESCRIPTION "Table row."
    INDEX { dpStatusIGMPStatusInterfaceIdx, dpStatusIGMPStatusInterface, dpStatusIGMPStatusInterfaceType, dpStatusIGMPStatusGroup }

    ::= { dpStatusIGMPStatusTable 1 }

DPStatusIGMPStatusEntry ::= SEQUENCE {
    dpStatusIGMPStatusInterfaceIdx    Unsigned32,
    dpStatusIGMPStatusInterface    DisplayString,
    dpStatusIGMPStatusInterfaceType    INTEGER,
    dpStatusIGMPStatusRefCount    Gauge32,
    dpStatusIGMPStatusGroup    IpAddress
}

dpStatusIGMPStatusInterfaceIdx OBJECT-TYPE
    SYNTAX      Unsigned32
    MAX-ACCESS  read-only
    STATUS      current
    DESCRIPTION
        "The index of the local interface associated with the group."

    ::= { dpStatusIGMPStatusEntry 1 }

dpStatusIGMPStatusInterface OBJECT-TYPE
    SYNTAX      DisplayString
    MAX-ACCESS  read-only
    STATUS      current
    DESCRIPTION
        "The local interface associated with the group."

    ::= { dpStatusIGMPStatusEntry 2 }

dpStatusIGMPStatusInterfaceType OBJECT-TYPE
    SYNTAX      INTEGER { 
                        other(1),
                        ethernet(6),
                        tunnel(131),
                        vLAN(135),
                        aggregate(161)
                }
    MAX-ACCESS  read-only
    STATUS      current
    DESCRIPTION
        "The type of device interface used for this route. Ethernet indicates that
        it is on the base Ethernet MAC interface. VLAN indicates that it is on an
        IEEE 802.1Q VLAN on top of the base Ethernet MAC interface."

    ::= { dpStatusIGMPStatusEntry 3 }

dpStatusIGMPStatusRefCount OBJECT-TYPE
    SYNTAX      Gauge32
    MAX-ACCESS  read-only
    STATUS      current
    DESCRIPTION
        "Reference count"

    ::= { dpStatusIGMPStatusEntry 4 }

dpStatusIGMPStatusGroup OBJECT-TYPE
    SYNTAX      IpAddress
    MAX-ACCESS  read-only
    STATUS      current
    DESCRIPTION
        "IGMP group"

    ::= { dpStatusIGMPStatusEntry 5 }

--

dpStatusZosNSSstatusTable OBJECT-TYPE
    SYNTAX      SEQUENCE OF DPStatusZosNSSstatusEntry
    MAX-ACCESS  not-accessible
    STATUS      current
    DESCRIPTION "Table."

    ::= { dpStatus 194 }

dpStatusZosNSSstatusEntry OBJECT-TYPE
    SYNTAX      DPStatusZosNSSstatusEntry
    MAX-ACCESS  not-accessible
    STATUS      current
    DESCRIPTION "Table row."
    INDEX { IMPLIED dpConfigZosNSSClientIndex }

    ::= { dpStatusZosNSSstatusTable 1 }

DPStatusZosNSSstatusEntry ::= SEQUENCE {
    dpStatusZosNSSstatusZosNSSClient    DisplayString,
    dpStatusZosNSSstatusNumAuthenRequests    Unsigned32,
    dpStatusZosNSSstatusNumAuthorRequests    Unsigned32
}

dpStatusZosNSSstatusZosNSSClient OBJECT-TYPE
    SYNTAX      DisplayString
    MAX-ACCESS  read-only
    STATUS      current
    DESCRIPTION "No description yet."

    ::= { dpStatusZosNSSstatusEntry 1 }

dpStatusZosNSSstatusNumAuthenRequests OBJECT-TYPE
    SYNTAX      Unsigned32
    MAX-ACCESS  read-only
    STATUS      current
    DESCRIPTION "No description yet."

    ::= { dpStatusZosNSSstatusEntry 2 }

dpStatusZosNSSstatusNumAuthorRequests OBJECT-TYPE
    SYNTAX      Unsigned32
    MAX-ACCESS  read-only
    STATUS      current
    DESCRIPTION "No description yet."

    ::= { dpStatusZosNSSstatusEntry 3 }

--

dpStatusRaidPartitionStatusTable OBJECT-TYPE
    SYNTAX      SEQUENCE OF DPStatusRaidPartitionStatusEntry
    MAX-ACCESS  not-accessible
    STATUS      current
    DESCRIPTION
        "Details about the RAID partition."

    ::= { dpStatus 195 }

dpStatusRaidPartitionStatusEntry OBJECT-TYPE
    SYNTAX      DPStatusRaidPartitionStatusEntry
    MAX-ACCESS  not-accessible
    STATUS      current
    DESCRIPTION "Table row."
    INDEX { dpStatusRaidPartitionStatusVolumeName, dpStatusRaidPartitionStatusPartitionIndex }

    ::= { dpStatusRaidPartitionStatusTable 1 }

DPStatusRaidPartitionStatusEntry ::= SEQUENCE {
    dpStatusRaidPartitionStatusVolumeName    DisplayString,
    dpStatusRaidPartitionStatusPartitionIndex    Unsigned32,
    dpStatusRaidPartitionStatusPurpose    INTEGER,
    dpStatusRaidPartitionStatusEncryption    INTEGER,
    dpStatusRaidPartitionStatusKeySource    INTEGER,
    dpStatusRaidPartitionStatusTotalSize    Unsigned32,
    dpStatusRaidPartitionStatusFreeSpace    Unsigned32
}

dpStatusRaidPartitionStatusVolumeName OBJECT-TYPE
    SYNTAX      DisplayString
    MAX-ACCESS  read-only
    STATUS      current
    DESCRIPTION
        "The name of the RAID volume."

    ::= { dpStatusRaidPartitionStatusEntry 1 }

dpStatusRaidPartitionStatusPartitionIndex OBJECT-TYPE
    SYNTAX      Unsigned32 (1..8)
    MAX-ACCESS  read-only
    STATUS      current
    DESCRIPTION
        "The index of the partition on the RAID volume."

    ::= { dpStatusRaidPartitionStatusEntry 2 }

dpStatusRaidPartitionStatusPurpose OBJECT-TYPE
    SYNTAX      INTEGER { 
                        localStorage(1),
                        b2bPersistence(2)
                }
    MAX-ACCESS  read-only
    STATUS      current
    DESCRIPTION
        "The contents of the partition."

    ::= { dpStatusRaidPartitionStatusEntry 3 }

dpStatusRaidPartitionStatusEncryption OBJECT-TYPE
    SYNTAX      INTEGER { 
                        none-Unsupported(1),
                        none(2),
                        aes(3),
                        aesSha(4)
                }
    MAX-ACCESS  read-only
    STATUS      current
    DESCRIPTION
        "The algorithm used to encrypt the partition, if application."

    ::= { dpStatusRaidPartitionStatusEntry 4 }

dpStatusRaidPartitionStatusKeySource OBJECT-TYPE
    SYNTAX      INTEGER { 
                        na(1),
                        none(2),
                        internalKey(3),
                        userPassphrase(4)
                }
    MAX-ACCESS  read-only
    STATUS      current
    DESCRIPTION
        "The method used to encrypt the partition, if any."

    ::= { dpStatusRaidPartitionStatusEntry 5 }

dpStatusRaidPartitionStatusTotalSize OBJECT-TYPE
    SYNTAX      Unsigned32
    UNITS       "KB"
    MAX-ACCESS  read-only
    STATUS      current
    DESCRIPTION
        "The total size of the partition in kilobytes, including file system
        overhead."

    ::= { dpStatusRaidPartitionStatusEntry 6 }

dpStatusRaidPartitionStatusFreeSpace OBJECT-TYPE
    SYNTAX      Unsigned32
    UNITS       "KB"
    MAX-ACCESS  read-only
    STATUS      current
    DESCRIPTION
        "The free space that is available on the partition for storing data."

    ::= { dpStatusRaidPartitionStatusEntry 7 }

--

dpStatusSelfBalancedTableTable OBJECT-TYPE
    SYNTAX      SEQUENCE OF DPStatusSelfBalancedTableEntry
    MAX-ACCESS  not-accessible
    STATUS      current
    DESCRIPTION
        "This table describes all local services that are listening for incoming
        connections on a self-balanced standby control virtual IP address. For
        each entry in the table, the configuration object that created the
        listener is shown."

    ::= { dpStatus 196 }

dpStatusSelfBalancedTableEntry OBJECT-TYPE
    SYNTAX      DPStatusSelfBalancedTableEntry
    MAX-ACCESS  not-accessible
    STATUS      current
    DESCRIPTION "Table row."
    INDEX { dpStatusSelfBalancedTablelocalVIPA, dpStatusSelfBalancedTablelocalPort }

    ::= { dpStatusSelfBalancedTableTable 1 }

DPStatusSelfBalancedTableEntry ::= SEQUENCE {
    dpStatusSelfBalancedTablelocalVIPA    IpAddress,
    dpStatusSelfBalancedTablelocalPort    Unsigned32,
    dpStatusSelfBalancedTablelocalSSL    DisplayString,
    dpStatusSelfBalancedTableserviceDomain    DisplayString,
    dpStatusSelfBalancedTableserviceType    INTEGER,
    dpStatusSelfBalancedTableserviceName    DisplayString
}

dpStatusSelfBalancedTablelocalVIPA OBJECT-TYPE
    SYNTAX      IpAddress
    MAX-ACCESS  read-only
    STATUS      current
    DESCRIPTION
        "The virtual IP address upon which connections are being accepted. An
        address of 0.0.0.0 means that connections will be accepted at any IP
        address of the system, a specific address indicates that connections will
        only be accepted at that virtual IP address."

    ::= { dpStatusSelfBalancedTableEntry 1 }

dpStatusSelfBalancedTablelocalPort OBJECT-TYPE
    SYNTAX      Unsigned32 (0..65535)
    MAX-ACCESS  read-only
    STATUS      current
    DESCRIPTION
        "The port number of the listener."

    ::= { dpStatusSelfBalancedTableEntry 2 }

dpStatusSelfBalancedTablelocalSSL OBJECT-TYPE
    SYNTAX      DisplayString
    MAX-ACCESS  read-only
    STATUS      current
    DESCRIPTION
        "Denotes whether the local listener supports the SSL protocol."

    ::= { dpStatusSelfBalancedTableEntry 3 }

dpStatusSelfBalancedTableserviceDomain OBJECT-TYPE
    SYNTAX      DisplayString
    MAX-ACCESS  read-only
    STATUS      current
    DESCRIPTION
        "The domain that the configuration object that created the listener is in."

    ::= { dpStatusSelfBalancedTableEntry 4 }

dpStatusSelfBalancedTableserviceType OBJECT-TYPE
    SYNTAX      INTEGER { 
                        configBase(0),
                        dNSNameService(1),
                        ethernetInterface(2),
                        cRLFetch(3),
                        hTTPService(4),
                        statistics(5),
                        traceTarget(6),
                        nTPService(7),
                        throttler(8),
                        stylePolicy(9),
                        hTTPUserAgent(10),
                        tCPProxyService(12),
                        uRLMap(13),
                        uRLRefreshPolicy(14),
                        user(15),
                        networkSettings(16),
                        xMLManager(17),
                        mQQM(18),
                        xSLProxyService(19),
                        mQGW(20),
                        sSLProxyService(21),
                        stylePolicyRule(22),
                        errorReportSettings(23),
                        iPInterface(25),
                        matching(26),
                        systemSettings(27),
                        sNMPSettings(28),
                        rADIUSSettings(29),
                        userGroup(30),
                        shellAlias(31),
                        xSLCoprocService(32),
                        telnetService(33),
                        cryptoSSKey(34),
                        messageMonitor(35),
                        uRLRewritePolicy(36),
                        sSLProxyProfile(37),
                        hTTPProxyService(38),
                        service(39),
                        cryptoFWCred(41),
                        xMLFirewallService(42),
                        cryptoKey(43),
                        cryptoCertificate(44),
                        cryptoIdentCred(45),
                        cryptoValCred(46),
                        cryptoProfile(47),
                        logTarget(48),
                        sSHService(49),
                        crypto(50),
                        webGUI(51),
                        eventlog(52),
                        accessControl(53),
                        messageFlowControl(54),
                        mQConfiguration(55),
                        deviceSettings(56),
                        deviceManagementService(57),
                        networkConfiguration(58),
                        logLabel(59),
                        mgmtInterface(60),
                        messageMatching(61),
                        messageType(62),
                        countMonitor(63),
                        durationMonitor(64),
                        filterAction(65),
                        hTTPInputConversionMap(66),
                        compileOptionsPolicy(68),
                        xPathRoutingMap(69),
                        schemaExceptionMap(70),
                        reserved71(71),
                        documentCryptoMap(72),
                        tAM(73),
                        domain(74),
                        timeSettings(75),
                        dynamicXMLContentMap(77),
                        dynamicStylesheet(78),
                        dynamicSchema(79),
                        accessControlList(80),
                        importPackage(81),
                        mQhost(82),
                        mQproxy(83),
                        loadBalancerGroup(84),
                        rBMSettings(85),
                        includeConfig(86),
                        certMonitor(87),
                        hostAlias(88),
                        aAAPolicy(91),
                        stylePolicyAction(92),
                        cryptoKerberosKDC(93),
                        webServiceMonitor(94),
                        wSGateway(95),
                        stylePolicyRuleBase(96),
                        wSStylePolicyRule(97),
                        wSStylePolicy(98),
                        webServicesAgent(99),
                        gatewayBase(100),
                        multiProtocolGateway(101),
                        sourceProtocolHandler(102),
                        hTTPSourceProtocolHandler(103),
                        hTTPSSourceProtocolHandler(104),
                        mQSourceProtocolHandler(105),
                        xTCProtocolHandler(106),
                        cryptoKerberosKeytab(109),
                        statelessTCPSourceProtocolHandler(110),
                        sLMCredClass(111),
                        sLMRsrcClass(112),
                        sLMSchedule(113),
                        sLMAction(114),
                        sLMPolicy(115),
                        peerGroup(116),
                        reserved117(117),
                        tFIMEndpoint(118),
                        xmltrace(120),
                        nFSClientSettings(121),
                        wSEndpointRewritePolicy(122),
                        sQLDataSource(124),
                        nFSStaticMount(125),
                        nFSDynamicMounts(126),
                        webAppErrorHandlingPolicy(127),
                        simpleCountMonitor(128),
                        nameValueProfile(129),
                        webAppResponse(130),
                        webAppRequest(131),
                        webAppFW(132),
                        appSecurityPolicy(133),
                        uDDIRegistry(134),
                        webAppSessionPolicy(135),
                        jMSServer(136),
                        tibcoEMSServer(137),
                        tibcoEMSSourceProtocolHandler(138),
                        xACMLPDP(139),
                        jMSSourceProtocolHandler(140),
                        webSphereJMSServer(141),
                        webSphereJMSSourceProtocolHandler(142),
                        processingMetadata(143),
                        mTOMPolicy(144),
                        fTPServerSourceProtocolHandler(145),
                        filePollerSourceProtocolHandler(146),
                        nFSFilePollerSourceProtocolHandler(147),
                        fTPFilePollerSourceProtocolHandler(148),
                        fTPQuoteCommands(149),
                        mQQMBase(150),
                        mQQMGroup(151),
                        wSRRServer(152),
                        wSRRSubscription(153),
                        webServiceSubscription(154),
                        uDDISubscription(155),
                        vLANInterface(156),
                        conformancePolicy(157),
                        sOAPHeaderDisposition(158),
                        policyAttachments(159),
                        policyParameters(160),
                        iMSConnect(161),
                        iMSConnectSourceProtocolHandler(162),
                        lDAPSearchParameters(163),
                        configDeploymentPolicy(164),
                        compactFlash(165),
                        raidVolume(166),
                        iScsiInitiatorConfig(167),
                        lLMSourceProtocolHandler(168),
                        tRVSourceProtocolHandler(169),
                        iScsiHBAConfig(170),
                        iScsiTargetConfig(171),
                        iScsiVolumeConfig(172),
                        iScsiChapConfig(173),
                        zosNSSClient(174),
                        sSHServerSourceProtocolHandler(175),
                        fTPDemonSourceProtocolHandler(176),
                        aS3SourceProtocolHandler(177),
                        aS2SourceProtocolHandler(178),
                        b2BXPathRoutingPolicy(179),
                        lLMInstance(180),
                        lLMMulticastReceive(181),
                        lLMMulticastTransmit(182),
                        lLMUnicast(183),
                        lLMMulticastTierGroup(184),
                        lLMRoute(186),
                        lLMPolicy(187),
                        fibreChannelHBA(188),
                        fibreChannelTarget(189),
                        fibreChannelVolume(190),
                        webB2BViewer(192),
                        b2BPersistence(193),
                        b2BProfileGroup(194),
                        b2BGateway(195),
                        b2BProfile(196),
                        wCCService(197),
                        formsLoginPolicy(198),
                        tRVPolicy(199),
                        tRVRoute(200),
                        tRVTransport(201),
                        lLMPolicyBase(202),
                        lLMRouteBase(203),
                        pOPPollerSourceProtocolHandlerBase(204),
                        aS1PollerSourceProtocolHandler(205),
                        pOPPollerSourceProtocolHandler(206),
                        sMTPServerConnection(207),
                        xM70Persistence(208),
                        wSRRSavedSearchSubscription(209),
                        eBMS2SourceProtocolHandler(210),
                        sAMLAttributes(211),
                        sSHClientProfile(212),
                        sFTPFilePollerSourceProtocolHandler(213),
                        zHybridTargetControlService(214),
                        multipathService(215),
                        clusterService(216),
                        secureCloudConnector(217),
                        iPMILanChannel(218),
                        iPMIUser(219),
                        b2BCPACollaboration(220),
                        mQFTESourceProtocolHandler(221),
                        b2BCPA(222),
                        b2BCPASenderSetting(223),
                        b2BCPAReceiverSetting(224),
                        oAuthSupportedClient(225),
                        oAuthSupportedClientGroup(226),
                        sSLSNIServerProfile(227),
                        xC10Grid(235),
                        runtimeSettings(246),
                        sQLRuntimeSettings(247),
                        webApplicationGateway(248),
                        interopService(249),
                        oDRConnectorGroup(250),
                        oDR(251),
                        sSLClientProfile(253),
                        sSLServerProfile(254),
                        sSLSNIMapping(256),
                        webTokenService(266),
                        messageContentFilters(267),
                        mCFBase(268),
                        mCFHttpHeader(269),
                        mCFXPath(270),
                        mCFHttpURL(271),
                        mCFHttpMethod(272),
                        iMSCalloutSourceProtocolHandler(273),
                        pattern(274),
                        mCFCustomRule(275),
                        aS2ProxySourceProtocolHandler(277),
                        luna(278),
                        lunaPartition(279),
                        configSequence(280),
                        lunaHAGroup(285),
                        lunaHASettings(286),
                        wAXHNProxy(300),
                        hNApplication(301),
                        cloudGatewayService(302),
                        cloudConnectorService(303),
                        jSONSettings(308),
                        iPMulticast(309),
                        deploymentPolicyParametersBinding(310),
                        lDAPConnectionPool(311),
                        mPGWErrorHandlingPolicy(312),
                        mPGWErrorAction(313),
                        language(314),
                        domainAvailability(315),
                        generatedPolicy(316),
                        passwordMap(320),
                        aAAJWTValidator(321),
                        aAAJWTGenerator(322),
                        linkAggregation(333),
                        cookieAttributePolicy(334),
                        iSAMReverseProxy(335),
                        iSAMReverseProxyJunction(336),
                        iSAMRuntime(337),
                        passwordAlias(338),
                        auditLog(340),
                        jWERecipient(345),
                        jOSESignatureIdentifier(346),
                        jWSSignature(347),
                        jWEHeader(348),
                        jOSERecipientIdentifier(349),
                        secureGatewayClient(350),
                        cacheGrid(351),
                        wXSGrid(352),
                        domainSettings(353),
                        mQAUI(354),
                        gWScriptSettings(358),
                        aPICollection(359),
                        aPIGateway(360),
                        aPIDefinition(361),
                        aPIPath(362),
                        aPIOperation(363),
                        aPIPlan(364),
                        aPISecurityDefinition(365),
                        aPISecurityAPIKey(366),
                        aPISecurityOAuth(368),
                        aPISecurityRequirement(369),
                        controlList(370),
                        aPILDAPRegistry(371),
                        aPIRule(372),
                        aPISecurityOAuthReq(373),
                        gWSRemoteDebug(374),
                        mQAUIMFT(375),
                        assemblyActionUserSecurity(376),
                        aPISecurityBasicAuth(377),
                        aPISchema(378),
                        aPIUserRegistry(379),
                        aPIAuthURLRegistry(380),
                        assemblyActionClientSecurity(381),
                        restMgmtInterface(400),
                        secureBackupMode(402),
                        aPIConnectGatewayService(403),
                        standaloneStandbyControlInterface(450),
                        standaloneStandbyControl(451),
                        tenant(452),
                        socialLoginPolicy(455),
                        eBMS3SourceProtocolHandler(456),
                        dFDLSettings(460),
                        parseSettings(461),
                        accessProfile(462),
                        iLMTScanner(500),
                        quotaEnforcementServer(504),
                        sSHServerProfile(505),
                        quotaEnforcementMatchClass(506),
                        quotaEnforcementGroupClass(507),
                        quotaEnforcementAlgorithm(508),
                        quotaEnforcementSchedule(509),
                        sSHDomainClientProfile(510),
                        quotaEnforcementPolicyGroup(511),
                        quotaEnforcementPolicyBase(512),
                        quotaEnforcementAction(513),
                        quotaEnforcementPolicy(514),
                        gatewayPeering(526),
                        stylePolicyActionBase(600),
                        assemblyActionBase(601),
                        assemblyAction(602),
                        assemblyLogic(603),
                        aPIExecute(605),
                        aPIResult(607),
                        assemblyLogicSwitch(609),
                        assembly(610),
                        assemblyActionInvoke(611),
                        assemblyActionSetVar(612),
                        assemblyActionThrow(613),
                        aPIRouting(614),
                        aPISecurity(615),
                        aPIRateLimit(616),
                        assemblyActionXml2Json(617),
                        aPIAction(618),
                        assemblyActionXSLT(619),
                        assemblyActionGatewayScript(620),
                        aPIClientIdentification(621),
                        assemblyActionMap(622),
                        assemblyActionJWTValidate(623),
                        assemblyActionParse(624),
                        aPICORS(625),
                        operationRateLimit(626),
                        analyticsEndpoint(627),
                        assemblyActionJWTGenerate(628),
                        assemblyActionJson2Xml(629),
                        assemblyActionOAuth(630),
                        oAuthProviderSettings(640),
                        aPISecurityTokenManager(641),
                        assemblyActionValidate(642),
                        aPIDebugProbe(643),
                        aPIApplicationType(644),
                        assemblyFunction(645),
                        assemblyActionFunctionCall(646),
                        gatewayPeeringManager(648),
                        assemblyActionLog(649),
                        assemblyActionRateLimit(650),
                        assemblyActionRedact(651),
                        productInsights(850)
                }
    MAX-ACCESS  read-only
    STATUS      current
    DESCRIPTION
        "The type of configuration object that created the listener."

    ::= { dpStatusSelfBalancedTableEntry 5 }

dpStatusSelfBalancedTableserviceName OBJECT-TYPE
    SYNTAX      DisplayString
    MAX-ACCESS  read-only
    STATUS      current
    DESCRIPTION
        "The name of the configuration object that created the listener."

    ::= { dpStatusSelfBalancedTableEntry 6 }

--

dpStatusSelfBalancedStatusTable OBJECT-TYPE
    SYNTAX      SEQUENCE OF DPStatusSelfBalancedStatusEntry
    MAX-ACCESS  not-accessible
    STATUS      obsolete
    DESCRIPTION
        "Status of self-balanced services in standby control groups.
        Note: this is obsoleted and is replaced by dpStatusSelfBalancedStatus2 as of release 5.0.0"

    ::= { dpStatus 197 }

dpStatusSelfBalancedStatusEntry OBJECT-TYPE
    SYNTAX      DPStatusSelfBalancedStatusEntry
    MAX-ACCESS  not-accessible
    STATUS      obsolete
    DESCRIPTION "Table row."
    INDEX { dpStatusSelfBalancedStatuslocalVIPA }

    ::= { dpStatusSelfBalancedStatusTable 1 }

DPStatusSelfBalancedStatusEntry ::= SEQUENCE {
    dpStatusSelfBalancedStatuslocalVIPA    IpAddress,
    dpStatusSelfBalancedStatusport    Unsigned32,
    dpStatusSelfBalancedStatusrealServer    IpAddress,
    dpStatusSelfBalancedStatustargetState    INTEGER,
    dpStatusSelfBalancedStatusserviceDomain    DisplayString,
    dpStatusSelfBalancedStatusserviceType    INTEGER,
    dpStatusSelfBalancedStatusserviceName    DisplayString,
    dpStatusSelfBalancedStatusweight    Unsigned32,
    dpStatusSelfBalancedStatusactiveconns    Unsigned32,
    dpStatusSelfBalancedStatusinactiveconns    Unsigned32
}

dpStatusSelfBalancedStatuslocalVIPA OBJECT-TYPE
    SYNTAX      IpAddress
    MAX-ACCESS  read-only
    STATUS      obsolete
    DESCRIPTION
        "The Virtual IP address that the service is accepting requests on."

    ::= { dpStatusSelfBalancedStatusEntry 1 }

dpStatusSelfBalancedStatusport OBJECT-TYPE
    SYNTAX      Unsigned32 (0..65535)
    MAX-ACCESS  read-only
    STATUS      obsolete
    DESCRIPTION
        "The port that the service is accepting requests on."

    ::= { dpStatusSelfBalancedStatusEntry 2 }

dpStatusSelfBalancedStatusrealServer OBJECT-TYPE
    SYNTAX      IpAddress
    MAX-ACCESS  read-only
    STATUS      obsolete
    DESCRIPTION
        "The IP address of the target appliance."

    ::= { dpStatusSelfBalancedStatusEntry 3 }

dpStatusSelfBalancedStatustargetState OBJECT-TYPE
    SYNTAX      INTEGER { 
                        active(1),
                        standby(2)
                }
    MAX-ACCESS  read-only
    STATUS      obsolete
    DESCRIPTION
        "The state of the target in the standby control group."

    ::= { dpStatusSelfBalancedStatusEntry 4 }

dpStatusSelfBalancedStatusserviceDomain OBJECT-TYPE
    SYNTAX      DisplayString
    MAX-ACCESS  read-only
    STATUS      obsolete
    DESCRIPTION
        "The domain where the service object exists."

    ::= { dpStatusSelfBalancedStatusEntry 5 }

dpStatusSelfBalancedStatusserviceType OBJECT-TYPE
    SYNTAX      INTEGER { 
                        configBase(0),
                        dNSNameService(1),
                        ethernetInterface(2),
                        cRLFetch(3),
                        hTTPService(4),
                        statistics(5),
                        traceTarget(6),
                        nTPService(7),
                        throttler(8),
                        stylePolicy(9),
                        hTTPUserAgent(10),
                        tCPProxyService(12),
                        uRLMap(13),
                        uRLRefreshPolicy(14),
                        user(15),
                        networkSettings(16),
                        xMLManager(17),
                        mQQM(18),
                        xSLProxyService(19),
                        mQGW(20),
                        sSLProxyService(21),
                        stylePolicyRule(22),
                        errorReportSettings(23),
                        iPInterface(25),
                        matching(26),
                        systemSettings(27),
                        sNMPSettings(28),
                        rADIUSSettings(29),
                        userGroup(30),
                        shellAlias(31),
                        xSLCoprocService(32),
                        telnetService(33),
                        cryptoSSKey(34),
                        messageMonitor(35),
                        uRLRewritePolicy(36),
                        sSLProxyProfile(37),
                        hTTPProxyService(38),
                        service(39),
                        cryptoFWCred(41),
                        xMLFirewallService(42),
                        cryptoKey(43),
                        cryptoCertificate(44),
                        cryptoIdentCred(45),
                        cryptoValCred(46),
                        cryptoProfile(47),
                        logTarget(48),
                        sSHService(49),
                        crypto(50),
                        webGUI(51),
                        eventlog(52),
                        accessControl(53),
                        messageFlowControl(54),
                        mQConfiguration(55),
                        deviceSettings(56),
                        deviceManagementService(57),
                        networkConfiguration(58),
                        logLabel(59),
                        mgmtInterface(60),
                        messageMatching(61),
                        messageType(62),
                        countMonitor(63),
                        durationMonitor(64),
                        filterAction(65),
                        hTTPInputConversionMap(66),
                        compileOptionsPolicy(68),
                        xPathRoutingMap(69),
                        schemaExceptionMap(70),
                        reserved71(71),
                        documentCryptoMap(72),
                        tAM(73),
                        domain(74),
                        timeSettings(75),
                        dynamicXMLContentMap(77),
                        dynamicStylesheet(78),
                        dynamicSchema(79),
                        accessControlList(80),
                        importPackage(81),
                        mQhost(82),
                        mQproxy(83),
                        loadBalancerGroup(84),
                        rBMSettings(85),
                        includeConfig(86),
                        certMonitor(87),
                        hostAlias(88),
                        aAAPolicy(91),
                        stylePolicyAction(92),
                        cryptoKerberosKDC(93),
                        webServiceMonitor(94),
                        wSGateway(95),
                        stylePolicyRuleBase(96),
                        wSStylePolicyRule(97),
                        wSStylePolicy(98),
                        webServicesAgent(99),
                        gatewayBase(100),
                        multiProtocolGateway(101),
                        sourceProtocolHandler(102),
                        hTTPSourceProtocolHandler(103),
                        hTTPSSourceProtocolHandler(104),
                        mQSourceProtocolHandler(105),
                        xTCProtocolHandler(106),
                        cryptoKerberosKeytab(109),
                        statelessTCPSourceProtocolHandler(110),
                        sLMCredClass(111),
                        sLMRsrcClass(112),
                        sLMSchedule(113),
                        sLMAction(114),
                        sLMPolicy(115),
                        peerGroup(116),
                        reserved117(117),
                        tFIMEndpoint(118),
                        xmltrace(120),
                        nFSClientSettings(121),
                        wSEndpointRewritePolicy(122),
                        sQLDataSource(124),
                        nFSStaticMount(125),
                        nFSDynamicMounts(126),
                        webAppErrorHandlingPolicy(127),
                        simpleCountMonitor(128),
                        nameValueProfile(129),
                        webAppResponse(130),
                        webAppRequest(131),
                        webAppFW(132),
                        appSecurityPolicy(133),
                        uDDIRegistry(134),
                        webAppSessionPolicy(135),
                        jMSServer(136),
                        tibcoEMSServer(137),
                        tibcoEMSSourceProtocolHandler(138),
                        xACMLPDP(139),
                        jMSSourceProtocolHandler(140),
                        webSphereJMSServer(141),
                        webSphereJMSSourceProtocolHandler(142),
                        processingMetadata(143),
                        mTOMPolicy(144),
                        fTPServerSourceProtocolHandler(145),
                        filePollerSourceProtocolHandler(146),
                        nFSFilePollerSourceProtocolHandler(147),
                        fTPFilePollerSourceProtocolHandler(148),
                        fTPQuoteCommands(149),
                        mQQMBase(150),
                        mQQMGroup(151),
                        wSRRServer(152),
                        wSRRSubscription(153),
                        webServiceSubscription(154),
                        uDDISubscription(155),
                        vLANInterface(156),
                        conformancePolicy(157),
                        sOAPHeaderDisposition(158),
                        policyAttachments(159),
                        policyParameters(160),
                        iMSConnect(161),
                        iMSConnectSourceProtocolHandler(162),
                        lDAPSearchParameters(163),
                        configDeploymentPolicy(164),
                        compactFlash(165),
                        raidVolume(166),
                        iScsiInitiatorConfig(167),
                        lLMSourceProtocolHandler(168),
                        tRVSourceProtocolHandler(169),
                        iScsiHBAConfig(170),
                        iScsiTargetConfig(171),
                        iScsiVolumeConfig(172),
                        iScsiChapConfig(173),
                        zosNSSClient(174),
                        sSHServerSourceProtocolHandler(175),
                        fTPDemonSourceProtocolHandler(176),
                        aS3SourceProtocolHandler(177),
                        aS2SourceProtocolHandler(178),
                        b2BXPathRoutingPolicy(179),
                        lLMInstance(180),
                        lLMMulticastReceive(181),
                        lLMMulticastTransmit(182),
                        lLMUnicast(183),
                        lLMMulticastTierGroup(184),
                        lLMRoute(186),
                        lLMPolicy(187),
                        fibreChannelHBA(188),
                        fibreChannelTarget(189),
                        fibreChannelVolume(190),
                        webB2BViewer(192),
                        b2BPersistence(193),
                        b2BProfileGroup(194),
                        b2BGateway(195),
                        b2BProfile(196),
                        wCCService(197),
                        formsLoginPolicy(198),
                        tRVPolicy(199),
                        tRVRoute(200),
                        tRVTransport(201),
                        lLMPolicyBase(202),
                        lLMRouteBase(203),
                        pOPPollerSourceProtocolHandlerBase(204),
                        aS1PollerSourceProtocolHandler(205),
                        pOPPollerSourceProtocolHandler(206),
                        sMTPServerConnection(207),
                        xM70Persistence(208),
                        wSRRSavedSearchSubscription(209),
                        eBMS2SourceProtocolHandler(210),
                        sAMLAttributes(211),
                        sSHClientProfile(212),
                        sFTPFilePollerSourceProtocolHandler(213),
                        zHybridTargetControlService(214),
                        multipathService(215),
                        clusterService(216),
                        secureCloudConnector(217),
                        iPMILanChannel(218),
                        iPMIUser(219),
                        b2BCPACollaboration(220),
                        mQFTESourceProtocolHandler(221),
                        b2BCPA(222),
                        b2BCPASenderSetting(223),
                        b2BCPAReceiverSetting(224),
                        oAuthSupportedClient(225),
                        oAuthSupportedClientGroup(226),
                        sSLSNIServerProfile(227),
                        xC10Grid(235),
                        runtimeSettings(246),
                        sQLRuntimeSettings(247),
                        webApplicationGateway(248),
                        interopService(249),
                        oDRConnectorGroup(250),
                        oDR(251),
                        sSLClientProfile(253),
                        sSLServerProfile(254),
                        sSLSNIMapping(256),
                        webTokenService(266),
                        messageContentFilters(267),
                        mCFBase(268),
                        mCFHttpHeader(269),
                        mCFXPath(270),
                        mCFHttpURL(271),
                        mCFHttpMethod(272),
                        iMSCalloutSourceProtocolHandler(273),
                        pattern(274),
                        mCFCustomRule(275),
                        aS2ProxySourceProtocolHandler(277),
                        luna(278),
                        lunaPartition(279),
                        configSequence(280),
                        lunaHAGroup(285),
                        lunaHASettings(286),
                        wAXHNProxy(300),
                        hNApplication(301),
                        cloudGatewayService(302),
                        cloudConnectorService(303),
                        jSONSettings(308),
                        iPMulticast(309),
                        deploymentPolicyParametersBinding(310),
                        lDAPConnectionPool(311),
                        mPGWErrorHandlingPolicy(312),
                        mPGWErrorAction(313),
                        language(314),
                        domainAvailability(315),
                        generatedPolicy(316),
                        passwordMap(320),
                        aAAJWTValidator(321),
                        aAAJWTGenerator(322),
                        linkAggregation(333),
                        cookieAttributePolicy(334),
                        iSAMReverseProxy(335),
                        iSAMReverseProxyJunction(336),
                        iSAMRuntime(337),
                        passwordAlias(338),
                        auditLog(340),
                        jWERecipient(345),
                        jOSESignatureIdentifier(346),
                        jWSSignature(347),
                        jWEHeader(348),
                        jOSERecipientIdentifier(349),
                        secureGatewayClient(350),
                        cacheGrid(351),
                        wXSGrid(352),
                        domainSettings(353),
                        mQAUI(354),
                        gWScriptSettings(358),
                        aPICollection(359),
                        aPIGateway(360),
                        aPIDefinition(361),
                        aPIPath(362),
                        aPIOperation(363),
                        aPIPlan(364),
                        aPISecurityDefinition(365),
                        aPISecurityAPIKey(366),
                        aPISecurityOAuth(368),
                        aPISecurityRequirement(369),
                        controlList(370),
                        aPILDAPRegistry(371),
                        aPIRule(372),
                        aPISecurityOAuthReq(373),
                        gWSRemoteDebug(374),
                        mQAUIMFT(375),
                        assemblyActionUserSecurity(376),
                        aPISecurityBasicAuth(377),
                        aPISchema(378),
                        aPIUserRegistry(379),
                        aPIAuthURLRegistry(380),
                        assemblyActionClientSecurity(381),
                        restMgmtInterface(400),
                        secureBackupMode(402),
                        aPIConnectGatewayService(403),
                        standaloneStandbyControlInterface(450),
                        standaloneStandbyControl(451),
                        tenant(452),
                        socialLoginPolicy(455),
                        eBMS3SourceProtocolHandler(456),
                        dFDLSettings(460),
                        parseSettings(461),
                        accessProfile(462),
                        iLMTScanner(500),
                        quotaEnforcementServer(504),
                        sSHServerProfile(505),
                        quotaEnforcementMatchClass(506),
                        quotaEnforcementGroupClass(507),
                        quotaEnforcementAlgorithm(508),
                        quotaEnforcementSchedule(509),
                        sSHDomainClientProfile(510),
                        quotaEnforcementPolicyGroup(511),
                        quotaEnforcementPolicyBase(512),
                        quotaEnforcementAction(513),
                        quotaEnforcementPolicy(514),
                        gatewayPeering(526),
                        stylePolicyActionBase(600),
                        assemblyActionBase(601),
                        assemblyAction(602),
                        assemblyLogic(603),
                        aPIExecute(605),
                        aPIResult(607),
                        assemblyLogicSwitch(609),
                        assembly(610),
                        assemblyActionInvoke(611),
                        assemblyActionSetVar(612),
                        assemblyActionThrow(613),
                        aPIRouting(614),
                        aPISecurity(615),
                        aPIRateLimit(616),
                        assemblyActionXml2Json(617),
                        aPIAction(618),
                        assemblyActionXSLT(619),
                        assemblyActionGatewayScript(620),
                        aPIClientIdentification(621),
                        assemblyActionMap(622),
                        assemblyActionJWTValidate(623),
                        assemblyActionParse(624),
                        aPICORS(625),
                        operationRateLimit(626),
                        analyticsEndpoint(627),
                        assemblyActionJWTGenerate(628),
                        assemblyActionJson2Xml(629),
                        assemblyActionOAuth(630),
                        oAuthProviderSettings(640),
                        aPISecurityTokenManager(641),
                        assemblyActionValidate(642),
                        aPIDebugProbe(643),
                        aPIApplicationType(644),
                        assemblyFunction(645),
                        assemblyActionFunctionCall(646),
                        gatewayPeeringManager(648),
                        assemblyActionLog(649),
                        assemblyActionRateLimit(650),
                        assemblyActionRedact(651),
                        productInsights(850)
                }
    MAX-ACCESS  read-only
    STATUS      obsolete
    DESCRIPTION
        "The type of the service object."

    ::= { dpStatusSelfBalancedStatusEntry 6 }

dpStatusSelfBalancedStatusserviceName OBJECT-TYPE
    SYNTAX      DisplayString
    MAX-ACCESS  read-only
    STATUS      obsolete
    DESCRIPTION
        "The name of the service object."

    ::= { dpStatusSelfBalancedStatusEntry 7 }

dpStatusSelfBalancedStatusweight OBJECT-TYPE
    SYNTAX      Unsigned32 (0..65535)
    MAX-ACCESS  read-only
    STATUS      obsolete
    DESCRIPTION
        "The weight of this target. The weight is determined by the processing
        capabilities of each appliance, and is used in the connection distribution
        decisions by the active member of the standby control group."

    ::= { dpStatusSelfBalancedStatusEntry 8 }

dpStatusSelfBalancedStatusactiveconns OBJECT-TYPE
    SYNTAX      Unsigned32
    MAX-ACCESS  read-only
    STATUS      obsolete
    DESCRIPTION
        "The number of connections in a TCP ESTABLISHED state to this target. This
        information will only be displayed on the row for the active member of the
        standby control group, and might differ from the actual number of
        connections because self balancing is not the endpoint for TCP
        connections."

    ::= { dpStatusSelfBalancedStatusEntry 9 }

dpStatusSelfBalancedStatusinactiveconns OBJECT-TYPE
    SYNTAX      Unsigned32
    MAX-ACCESS  read-only
    STATUS      obsolete
    DESCRIPTION
        "The number of connections that are not established to this target. This
        includes previously active connections that have closed but not yet timed
        out. There might be a large number of inactive connections depending on
        the number of connections per second received and the connection time out.
        This information will only be displayed on the row for the active member
        of the standby control group and might differ from the connections in
        TIME_WAIT because self balancing is not the endpoint for TCP connections."

    ::= { dpStatusSelfBalancedStatusEntry 10 }

--

dpStatusTibcoRVCMLedgerStatusTable OBJECT-TYPE
    SYNTAX      SEQUENCE OF DPStatusTibcoRVCMLedgerStatusEntry
    MAX-ACCESS  not-accessible
    STATUS      current
    DESCRIPTION
        "Details of the Certified Messaging ledgers for the TIBCO RV Routes which
        are in the up state. The information extracted from the ledger files is
        useful in identifying slow and unresponsive certified messaging listeners.
        Slow and unresponsive listeners cause ledger files to grow thereby
        consuming memory and disk space. To reclaim space in a ledger file due to
        a slow or unresponsive listener use the Remove Listener action. This
        action terminates the previously established Certified Delivery Agreement
        between the TIBCO RV Route and the specific listener. Once the listener is
        removed, any messages remaining in the ledger file waiting for this
        specific listener to acknowledge are removed from the ledger. After a
        listener has been removed, the listener can attempt to re-establish a new
        Certified Delivery Agreement with the TIBCO RV Route. To prevent the
        listener from establishing a Certified Delivery Agreement, use Disallow
        Listener located within the TIBCO RV Route object."

    ::= { dpStatus 198 }

dpStatusTibcoRVCMLedgerStatusEntry OBJECT-TYPE
    SYNTAX      DPStatusTibcoRVCMLedgerStatusEntry
    MAX-ACCESS  not-accessible
    STATUS      current
    DESCRIPTION "Table row."
    INDEX { IMPLIED dpStatusTibcoRVCMLedgerStatusName }

    ::= { dpStatusTibcoRVCMLedgerStatusTable 1 }

DPStatusTibcoRVCMLedgerStatusEntry ::= SEQUENCE {
    dpStatusTibcoRVCMLedgerStatusName    DisplayString,
    dpStatusTibcoRVCMLedgerStatusSubject    DisplayString,
    dpStatusTibcoRVCMLedgerStatusSeqnoLastSent    Counter64,
    dpStatusTibcoRVCMLedgerStatusTotalMsgs    Counter64,
    dpStatusTibcoRVCMLedgerStatusTotalSize    Counter64,
    dpStatusTibcoRVCMLedgerStatusListenerName    DisplayString,
    dpStatusTibcoRVCMLedgerStatusListenerLastConfirmed    Counter64
}

dpStatusTibcoRVCMLedgerStatusName OBJECT-TYPE
    SYNTAX      DisplayString
    MAX-ACCESS  read-only
    STATUS      current
    DESCRIPTION
        "The name of the TIBCO RV Route."

    ::= { dpStatusTibcoRVCMLedgerStatusEntry 1 }

dpStatusTibcoRVCMLedgerStatusSubject OBJECT-TYPE
    SYNTAX      DisplayString
    MAX-ACCESS  read-only
    STATUS      current
    DESCRIPTION
        "The name of the TIBCO RV subject."

    ::= { dpStatusTibcoRVCMLedgerStatusEntry 2 }

dpStatusTibcoRVCMLedgerStatusSeqnoLastSent OBJECT-TYPE
    SYNTAX      Counter64
    MAX-ACCESS  read-only
    STATUS      current
    DESCRIPTION
        "The sequence number of the last message sent to all listeners."

    ::= { dpStatusTibcoRVCMLedgerStatusEntry 3 }

dpStatusTibcoRVCMLedgerStatusTotalMsgs OBJECT-TYPE
    SYNTAX      Counter64
    MAX-ACCESS  read-only
    STATUS      current
    DESCRIPTION
        "The total number of outbound messages stored in the ledger. The value is
        not specific to a certified messaging listener, rather it is specific to
        the TIBCO RV Route."

    ::= { dpStatusTibcoRVCMLedgerStatusEntry 4 }

dpStatusTibcoRVCMLedgerStatusTotalSize OBJECT-TYPE
    SYNTAX      Counter64
    UNITS       "bytes"
    MAX-ACCESS  read-only
    STATUS      current
    DESCRIPTION
        "The total size of all outbound messages stored in the ledger. The value is
        not specific to a certified messaging listener, rather it is specific to
        the TIBCO RV Route."

    ::= { dpStatusTibcoRVCMLedgerStatusEntry 5 }

dpStatusTibcoRVCMLedgerStatusListenerName OBJECT-TYPE
    SYNTAX      DisplayString
    MAX-ACCESS  read-only
    STATUS      current
    DESCRIPTION
        "The name of the Certified Messaging Listener."

    ::= { dpStatusTibcoRVCMLedgerStatusEntry 6 }

dpStatusTibcoRVCMLedgerStatusListenerLastConfirmed OBJECT-TYPE
    SYNTAX      Counter64
    MAX-ACCESS  read-only
    STATUS      current
    DESCRIPTION
        "The sequence number of the last message the Certified Messaging Listener
        confirmed."

    ::= { dpStatusTibcoRVCMLedgerStatusEntry 7 }

--

dpStatusSSHKnownHostStatusTable OBJECT-TYPE
    SYNTAX      SEQUENCE OF DPStatusSSHKnownHostStatusEntry
    MAX-ACCESS  not-accessible
    STATUS      current
    DESCRIPTION
        "SSH known host tables for the SSH client profile. If the host key of an
        SSH server changes, delete the SSH client known host entry, then add an
        SSH client known host to the SSH client profile."

    ::= { dpStatus 199 }

dpStatusSSHKnownHostStatusEntry OBJECT-TYPE
    SYNTAX      DPStatusSSHKnownHostStatusEntry
    MAX-ACCESS  not-accessible
    STATUS      current
    DESCRIPTION "Table row."
    INDEX { dpStatusSSHKnownHostStatusHost, IMPLIED dpStatusSSHKnownHostStatusClientName }

    ::= { dpStatusSSHKnownHostStatusTable 1 }

DPStatusSSHKnownHostStatusEntry ::= SEQUENCE {
    dpStatusSSHKnownHostStatusHost    DisplayString,
    dpStatusSSHKnownHostStatusType    DisplayString,
    dpStatusSSHKnownHostStatusClientName    DisplayString
}

dpStatusSSHKnownHostStatusHost OBJECT-TYPE
    SYNTAX      DisplayString
    MAX-ACCESS  read-only
    STATUS      current
    DESCRIPTION
        "The IP address of the SSH peer."

    ::= { dpStatusSSHKnownHostStatusEntry 1 }

dpStatusSSHKnownHostStatusType OBJECT-TYPE
    SYNTAX      DisplayString
    MAX-ACCESS  read-only
    STATUS      current
    DESCRIPTION
        "The key type recorded for the SSH peer."

    ::= { dpStatusSSHKnownHostStatusEntry 2 }

dpStatusSSHKnownHostStatusClientName OBJECT-TYPE
    SYNTAX      DisplayString
    MAX-ACCESS  read-only
    STATUS      current
    DESCRIPTION
        "The SSH client profile associated with the SSH peer."

    ::= { dpStatusSSHKnownHostStatusEntry 3 }

--

dpStatusDNSCacheHostStatus2Table OBJECT-TYPE
    SYNTAX      SEQUENCE OF DPStatusDNSCacheHostStatus2Entry
    MAX-ACCESS  not-accessible
    STATUS      obsolete
    DESCRIPTION
        "The host name/IP address pairs that are currently stored in the DNS cache.
        A new entry is stored each time DataPower successfully looks up a host
        name on a DNS server. The name can be either fully qualified (for example,
        servername.uk.ibm.com ), or a partial host name (for example, servername
        ).
        Note: this is obsoleted and is replaced by dpStatusDNSCacheHostStatus3 as of release 7.2.0.1"

    ::= { dpStatus 200 }

dpStatusDNSCacheHostStatus2Entry OBJECT-TYPE
    SYNTAX      DPStatusDNSCacheHostStatus2Entry
    MAX-ACCESS  not-accessible
    STATUS      obsolete
    DESCRIPTION "Table row."
    INDEX { dpStatusDNSCacheHostStatus2Hostname, dpStatusDNSCacheHostStatus2IPAddress }

    ::= { dpStatusDNSCacheHostStatus2Table 1 }

DPStatusDNSCacheHostStatus2Entry ::= SEQUENCE {
    dpStatusDNSCacheHostStatus2Hostname    DisplayString,
    dpStatusDNSCacheHostStatus2IPAddress    IpAddress
}

dpStatusDNSCacheHostStatus2Hostname OBJECT-TYPE
    SYNTAX      DisplayString
    MAX-ACCESS  read-only
    STATUS      obsolete
    DESCRIPTION
        "The host name that the appliance located on a configured DNS server using
        a configured DNS search domain."

    ::= { dpStatusDNSCacheHostStatus2Entry 1 }

dpStatusDNSCacheHostStatus2IPAddress OBJECT-TYPE
    SYNTAX      IpAddress
    MAX-ACCESS  read-only
    STATUS      obsolete
    DESCRIPTION
        "The numeric IP address corresponding to the given host name."

    ::= { dpStatusDNSCacheHostStatus2Entry 2 }

--

dpStatusSystemUsageTableTable OBJECT-TYPE
    SYNTAX      SEQUENCE OF DPStatusSystemUsageTableEntry
    MAX-ACCESS  not-accessible
    STATUS      obsolete
    DESCRIPTION
        "Component level system usage.
        Note: this is obsoleted and is replaced by dpStatusSystemUsage2Table as of release 4.0.1"

    ::= { dpStatus 201 }

dpStatusSystemUsageTableEntry OBJECT-TYPE
    SYNTAX      DPStatusSystemUsageTableEntry
    MAX-ACCESS  not-accessible
    STATUS      obsolete
    DESCRIPTION "Table row."
    INDEX { dpStatusSystemUsageTableTaskName }

    ::= { dpStatusSystemUsageTableTable 1 }

DPStatusSystemUsageTableEntry ::= SEQUENCE {
    dpStatusSystemUsageTableTaskName    INTEGER,
    dpStatusSystemUsageTableLoad    Unsigned32,
    dpStatusSystemUsageTableWorkList    Unsigned32,
    dpStatusSystemUsageTableCPU    Unsigned32,
    dpStatusSystemUsageTableMemory    Unsigned32,
    dpStatusSystemUsageTableFileCount    Unsigned32
}

dpStatusSystemUsageTableTaskName OBJECT-TYPE
    SYNTAX      INTEGER { 
                        main(1),
                        llm(2),
                        b2bp(3),
                        wtx(4),
                        ssh(5),
                        odbc(6),
                        db2cli(7),
                        secureCloudConnector(8),
                        dco(9),
                        waxhn(10),
                        imscallout(11),
                        jsdebugger(12),
                        nfs(13),
                        isam(14),
                        sgclient(15),
                        sshd(16),
                        quotaEnforcement(17),
                        luna(18),
                        lunaClient(19),
                        launcher(20),
                        apic-gw-service(21),
                        gateway-peering(22)
                }
    MAX-ACCESS  read-only
    STATUS      obsolete
    DESCRIPTION
        "The name of the task or component."

    ::= { dpStatusSystemUsageTableEntry 1 }

dpStatusSystemUsageTableLoad OBJECT-TYPE
    SYNTAX      Unsigned32
    UNITS       "%"
    MAX-ACCESS  read-only
    STATUS      obsolete
    DESCRIPTION
        "The percentage of total load on the device during the measurement
        interval. A load above 90 indicates that the device is at or near load
        capacity. High load values are not necessarily indicative of a problem,
        provided that transaction latencies are not affected. Low load values
        means that the appliance is looking for work; high load means that the
        appliance is doing work."

    ::= { dpStatusSystemUsageTableEntry 2 }

dpStatusSystemUsageTableWorkList OBJECT-TYPE
    SYNTAX      Unsigned32
    MAX-ACCESS  read-only
    STATUS      obsolete
    DESCRIPTION
        "The number of pending work items including internal communication in the
        queue for processing by the device. This number is for internal
        diagnostics is not intended for purposes of capacity planning."

    ::= { dpStatusSystemUsageTableEntry 3 }

dpStatusSystemUsageTableCPU OBJECT-TYPE
    SYNTAX      Unsigned32
    UNITS       "%"
    MAX-ACCESS  read-only
    STATUS      obsolete
    DESCRIPTION
        "The percentage of CPU used by this component."

    ::= { dpStatusSystemUsageTableEntry 4 }

dpStatusSystemUsageTableMemory OBJECT-TYPE
    SYNTAX      Unsigned32
    UNITS       "%"
    MAX-ACCESS  read-only
    STATUS      obsolete
    DESCRIPTION
        "The percentage of memory used by this component. The cumulative task
        memory is not comparable to the memory usage as reported by the memory
        usage status provider. This value helps to identify which components are
        contributing to memory usage."

    ::= { dpStatusSystemUsageTableEntry 5 }

dpStatusSystemUsageTableFileCount OBJECT-TYPE
    SYNTAX      Unsigned32
    MAX-ACCESS  read-only
    STATUS      obsolete
    DESCRIPTION
        "Number of open file descriptors. The file count increases when the device
        accepts new connections, or opens a file for reading and decreases when
        this descriptor is closed. This value helps to identify which components
        are contributing to high open file counts."

    ::= { dpStatusSystemUsageTableEntry 6 }

--

dpStatusXMLNamesStatusTable OBJECT-TYPE
    SYNTAX      SEQUENCE OF DPStatusXMLNamesStatusEntry
    MAX-ACCESS  not-accessible
    STATUS      current
    DESCRIPTION "Table."

    ::= { dpStatus 207 }

dpStatusXMLNamesStatusEntry OBJECT-TYPE
    SYNTAX      DPStatusXMLNamesStatusEntry
    MAX-ACCESS  not-accessible
    STATUS      current
    DESCRIPTION "Table row."
    INDEX { IMPLIED dpStatusXMLNamesStatusType }

    ::= { dpStatusXMLNamesStatusTable 1 }

DPStatusXMLNamesStatusEntry ::= SEQUENCE {
    dpStatusXMLNamesStatusType    DisplayString,
    dpStatusXMLNamesStatusUsed    Unsigned32,
    dpStatusXMLNamesStatusPercentFree    Unsigned32,
    dpStatusXMLNamesStatusMaximum    Unsigned32
}

dpStatusXMLNamesStatusType OBJECT-TYPE
    SYNTAX      DisplayString
    MAX-ACCESS  read-only
    STATUS      current
    DESCRIPTION "No description yet."

    ::= { dpStatusXMLNamesStatusEntry 1 }

dpStatusXMLNamesStatusUsed OBJECT-TYPE
    SYNTAX      Unsigned32
    MAX-ACCESS  read-only
    STATUS      current
    DESCRIPTION "No description yet."

    ::= { dpStatusXMLNamesStatusEntry 2 }

dpStatusXMLNamesStatusPercentFree OBJECT-TYPE
    SYNTAX      Unsigned32
    MAX-ACCESS  read-only
    STATUS      current
    DESCRIPTION "No description yet."

    ::= { dpStatusXMLNamesStatusEntry 3 }

dpStatusXMLNamesStatusMaximum OBJECT-TYPE
    SYNTAX      Unsigned32
    MAX-ACCESS  read-only
    STATUS      current
    DESCRIPTION "No description yet."

    ::= { dpStatusXMLNamesStatusEntry 4 }

--

dpStatusZHybridTCSstatusTable OBJECT-TYPE
    SYNTAX      SEQUENCE OF DPStatusZHybridTCSstatusEntry
    MAX-ACCESS  not-accessible
    STATUS      current
    DESCRIPTION "Table."

    ::= { dpStatus 208 }

dpStatusZHybridTCSstatusEntry OBJECT-TYPE
    SYNTAX      DPStatusZHybridTCSstatusEntry
    MAX-ACCESS  not-accessible
    STATUS      current
    DESCRIPTION "Table row."
    INDEX { dpStatusZHybridTCSstatusSDIP, dpStatusZHybridTCSstatusDVIPA, dpStatusZHybridTCSstatusDPort }

    ::= { dpStatusZHybridTCSstatusTable 1 }

DPStatusZHybridTCSstatusEntry ::= SEQUENCE {
    dpStatusZHybridTCSstatusSDIP    IpAddress,
    dpStatusZHybridTCSstatusSDPort    Unsigned32,
    dpStatusZHybridTCSstatusDVIPA    IpAddress,
    dpStatusZHybridTCSstatusDPort    Unsigned32,
    dpStatusZHybridTCSstatusReady    DisplayString,
    dpStatusZHybridTCSstatusCurrConns    Integer32,
    dpStatusZHybridTCSstatusTotConns    Unsigned32
}

dpStatusZHybridTCSstatusSDIP OBJECT-TYPE
    SYNTAX      IpAddress
    MAX-ACCESS  read-only
    STATUS      current
    DESCRIPTION
        "The IP address of the Sysplex Distributor that initiated the connection."

    ::= { dpStatusZHybridTCSstatusEntry 1 }

dpStatusZHybridTCSstatusSDPort OBJECT-TYPE
    SYNTAX      Unsigned32 (0..65535)
    MAX-ACCESS  read-only
    STATUS      current
    DESCRIPTION
        "The Sysplex Distributor port on the control connection to the Target
        Control Service."

    ::= { dpStatusZHybridTCSstatusEntry 2 }

dpStatusZHybridTCSstatusDVIPA OBJECT-TYPE
    SYNTAX      IpAddress
    MAX-ACCESS  read-only
    STATUS      current
    DESCRIPTION
        "The Distributed Virtual IP Address of the Sysplex Distributor."

    ::= { dpStatusZHybridTCSstatusEntry 3 }

dpStatusZHybridTCSstatusDPort OBJECT-TYPE
    SYNTAX      Unsigned32 (0..65535)
    MAX-ACCESS  read-only
    STATUS      current
    DESCRIPTION
        "The port on which the service is listening."

    ::= { dpStatusZHybridTCSstatusEntry 4 }

dpStatusZHybridTCSstatusReady OBJECT-TYPE
    SYNTAX      DisplayString
    MAX-ACCESS  read-only
    STATUS      current
    DESCRIPTION
        "Indicates whether the service is listening on the Service Port."

    ::= { dpStatusZHybridTCSstatusEntry 5 }

dpStatusZHybridTCSstatusCurrConns OBJECT-TYPE
    SYNTAX      Integer32
    MAX-ACCESS  read-only
    STATUS      current
    DESCRIPTION
        "The number of connections currently opened on the Target Control Service."

    ::= { dpStatusZHybridTCSstatusEntry 6 }

dpStatusZHybridTCSstatusTotConns OBJECT-TYPE
    SYNTAX      Unsigned32
    MAX-ACCESS  read-only
    STATUS      current
    DESCRIPTION
        "The total number of connections to the service from the time Sysplex
        Distributor registered with the Target Control Service."

    ::= { dpStatusZHybridTCSstatusEntry 7 }

--

dpStatusWSRRSavedSearchSubscriptionStatusTable OBJECT-TYPE
    SYNTAX      SEQUENCE OF DPStatusWSRRSavedSearchSubscriptionStatusEntry
    MAX-ACCESS  not-accessible
    STATUS      current
    DESCRIPTION "Table."

    ::= { dpStatus 210 }

dpStatusWSRRSavedSearchSubscriptionStatusEntry OBJECT-TYPE
    SYNTAX      DPStatusWSRRSavedSearchSubscriptionStatusEntry
    MAX-ACCESS  not-accessible
    STATUS      current
    DESCRIPTION "Table row."
    INDEX { IMPLIED dpConfigWSRRSavedSearchSubscriptionIndex }

    ::= { dpStatusWSRRSavedSearchSubscriptionStatusTable 1 }

DPStatusWSRRSavedSearchSubscriptionStatusEntry ::= SEQUENCE {
    dpStatusWSRRSavedSearchSubscriptionStatusSubscription    DisplayString,
    dpStatusWSRRSavedSearchSubscriptionStatusStatus    INTEGER,
    dpStatusWSRRSavedSearchSubscriptionStatusLastRefresh    TimeStamp,
    dpStatusWSRRSavedSearchSubscriptionStatusMethod    INTEGER,
    dpStatusWSRRSavedSearchSubscriptionStatusRefreshInterval    DPTimeIntervalSeconds,
    dpStatusWSRRSavedSearchSubscriptionStatusCount    Unsigned32,
    dpStatusWSRRSavedSearchSubscriptionStatusServiceVersionCount    Unsigned32
}

dpStatusWSRRSavedSearchSubscriptionStatusSubscription OBJECT-TYPE
    SYNTAX      DisplayString
    MAX-ACCESS  read-only
    STATUS      current
    DESCRIPTION
        "The name of the WSRR saved search subscription that is assigned during the
        configuration fo the subscription."

    ::= { dpStatusWSRRSavedSearchSubscriptionStatusEntry 1 }

dpStatusWSRRSavedSearchSubscriptionStatusStatus OBJECT-TYPE
    SYNTAX      INTEGER { 
                        okay(1),
                        error(2),
                        synchronizing(3)
                }
    MAX-ACCESS  read-only
    STATUS      current
    DESCRIPTION
        "The status of the last synchronization. The status is one of the following
        values:"

    ::= { dpStatusWSRRSavedSearchSubscriptionStatusEntry 2 }

dpStatusWSRRSavedSearchSubscriptionStatusLastRefresh OBJECT-TYPE
    SYNTAX      TimeStamp
    MAX-ACCESS  read-only
    STATUS      current
    DESCRIPTION
        "The timestamp of the last synchronization with the Service Registry. Use
        the Synchronize action to immediately refresh the subscription."

    ::= { dpStatusWSRRSavedSearchSubscriptionStatusEntry 3 }

dpStatusWSRRSavedSearchSubscriptionStatusMethod OBJECT-TYPE
    SYNTAX      INTEGER { 
                        manual(1),
                        poll(2),
                        automatic(3)
                }
    MAX-ACCESS  read-only
    STATUS      current
    DESCRIPTION
        "The method to keep WSRR saved search subscription up-to-date."

    ::= { dpStatusWSRRSavedSearchSubscriptionStatusEntry 4 }

dpStatusWSRRSavedSearchSubscriptionStatusRefreshInterval OBJECT-TYPE
    SYNTAX      DPTimeIntervalSeconds
    MAX-ACCESS  read-only
    STATUS      current
    DESCRIPTION
        "The refresh interval. This value is meaningful only when the
        synchronization method is poll."

    ::= { dpStatusWSRRSavedSearchSubscriptionStatusEntry 5 }

dpStatusWSRRSavedSearchSubscriptionStatusCount OBJECT-TYPE
    SYNTAX      Unsigned32
    MAX-ACCESS  read-only
    STATUS      current
    DESCRIPTION
        "Number of WSDLs found in the Registry for this subscription. See WSRR
        Subscription Service Status screen for more information about individual
        WSDLs."

    ::= { dpStatusWSRRSavedSearchSubscriptionStatusEntry 6 }

dpStatusWSRRSavedSearchSubscriptionStatusServiceVersionCount OBJECT-TYPE
    SYNTAX      Unsigned32
    MAX-ACCESS  read-only
    STATUS      current
    DESCRIPTION
        "Number of Service Versions found in the Registry for this saved search
        subscription."

    ::= { dpStatusWSRRSavedSearchSubscriptionStatusEntry 7 }

--

dpStatusWSRRSavedSearchSubscriptionServiceStatusTable OBJECT-TYPE
    SYNTAX      SEQUENCE OF DPStatusWSRRSavedSearchSubscriptionServiceStatusEntry
    MAX-ACCESS  not-accessible
    STATUS      current
    DESCRIPTION "Table."

    ::= { dpStatus 211 }

dpStatusWSRRSavedSearchSubscriptionServiceStatusEntry OBJECT-TYPE
    SYNTAX      DPStatusWSRRSavedSearchSubscriptionServiceStatusEntry
    MAX-ACCESS  not-accessible
    STATUS      current
    DESCRIPTION "Table row."
    INDEX { dpConfigWSRRSavedSearchSubscriptionIndex, IMPLIED dpStatusWSRRSavedSearchSubscriptionServiceStatusBsrURI }

    ::= { dpStatusWSRRSavedSearchSubscriptionServiceStatusTable 1 }

DPStatusWSRRSavedSearchSubscriptionServiceStatusEntry ::= SEQUENCE {
    dpStatusWSRRSavedSearchSubscriptionServiceStatusSubscription    DisplayString,
    dpStatusWSRRSavedSearchSubscriptionServiceStatusBsrURI    DisplayString,
    dpStatusWSRRSavedSearchSubscriptionServiceStatusWSDLName    DisplayString,
    dpStatusWSRRSavedSearchSubscriptionServiceStatusLocation    DisplayString,
    dpStatusWSRRSavedSearchSubscriptionServiceStatusDescription    DisplayString,
    dpStatusWSRRSavedSearchSubscriptionServiceStatusVersion    DisplayString
}

dpStatusWSRRSavedSearchSubscriptionServiceStatusSubscription OBJECT-TYPE
    SYNTAX      DisplayString
    MAX-ACCESS  read-only
    STATUS      current
    DESCRIPTION
        "The name of the WSRR saved search subscription that is assigned during the
        configuration of the subscription."

    ::= { dpStatusWSRRSavedSearchSubscriptionServiceStatusEntry 1 }

dpStatusWSRRSavedSearchSubscriptionServiceStatusBsrURI OBJECT-TYPE
    SYNTAX      DisplayString
    MAX-ACCESS  read-only
    STATUS      current
    DESCRIPTION
        "The document identifier assigned by WSRR."

    ::= { dpStatusWSRRSavedSearchSubscriptionServiceStatusEntry 2 }

dpStatusWSRRSavedSearchSubscriptionServiceStatusWSDLName OBJECT-TYPE
    SYNTAX      DisplayString
    MAX-ACCESS  read-only
    STATUS      current
    DESCRIPTION
        "The logical name of the WSDL file assigned by WSRR."

    ::= { dpStatusWSRRSavedSearchSubscriptionServiceStatusEntry 3 }

dpStatusWSRRSavedSearchSubscriptionServiceStatusLocation OBJECT-TYPE
    SYNTAX      DisplayString
    MAX-ACCESS  read-only
    STATUS      current
    DESCRIPTION
        "The location value assigned by WSRR. Typically, the value is the file
        name."

    ::= { dpStatusWSRRSavedSearchSubscriptionServiceStatusEntry 4 }

dpStatusWSRRSavedSearchSubscriptionServiceStatusDescription OBJECT-TYPE
    SYNTAX      DisplayString
    MAX-ACCESS  read-only
    STATUS      current
    DESCRIPTION
        "The file or resource description assigned by WSRR."

    ::= { dpStatusWSRRSavedSearchSubscriptionServiceStatusEntry 5 }

dpStatusWSRRSavedSearchSubscriptionServiceStatusVersion OBJECT-TYPE
    SYNTAX      DisplayString
    MAX-ACCESS  read-only
    STATUS      current
    DESCRIPTION
        "The version description assigned by WSRR."

    ::= { dpStatusWSRRSavedSearchSubscriptionServiceStatusEntry 6 }

--

dpStatusWSRRSavdSrchSubsPolicyAttachmentsStatusTable OBJECT-TYPE
    SYNTAX      SEQUENCE OF DPStatusWSRRSavdSrchSubsPolicyAttachmentsStatusEntry
    MAX-ACCESS  not-accessible
    STATUS      current
    DESCRIPTION "Table."

    ::= { dpStatus 212 }

dpStatusWSRRSavdSrchSubsPolicyAttachmentsStatusEntry OBJECT-TYPE
    SYNTAX      DPStatusWSRRSavdSrchSubsPolicyAttachmentsStatusEntry
    MAX-ACCESS  not-accessible
    STATUS      current
    DESCRIPTION "Table row."
    INDEX { dpConfigWSRRSavedSearchSubscriptionIndex, IMPLIED dpStatusWSRRSavdSrchSubsPolicyAttachmentsStatusAttachmentPoint }

    ::= { dpStatusWSRRSavdSrchSubsPolicyAttachmentsStatusTable 1 }

DPStatusWSRRSavdSrchSubsPolicyAttachmentsStatusEntry ::= SEQUENCE {
    dpStatusWSRRSavdSrchSubsPolicyAttachmentsStatusSubscription    DisplayString,
    dpStatusWSRRSavdSrchSubsPolicyAttachmentsStatusAttachmentPoint    DisplayString,
    dpStatusWSRRSavdSrchSubsPolicyAttachmentsStatusAttachmentURLs    DisplayString
}

dpStatusWSRRSavdSrchSubsPolicyAttachmentsStatusSubscription OBJECT-TYPE
    SYNTAX      DisplayString
    MAX-ACCESS  read-only
    STATUS      current
    DESCRIPTION
        "Name of the saved search subscription object."

    ::= { dpStatusWSRRSavdSrchSubsPolicyAttachmentsStatusEntry 1 }

dpStatusWSRRSavdSrchSubsPolicyAttachmentsStatusAttachmentPoint OBJECT-TYPE
    SYNTAX      DisplayString
    MAX-ACCESS  read-only
    STATUS      current
    DESCRIPTION "No description yet."

    ::= { dpStatusWSRRSavdSrchSubsPolicyAttachmentsStatusEntry 2 }

dpStatusWSRRSavdSrchSubsPolicyAttachmentsStatusAttachmentURLs OBJECT-TYPE
    SYNTAX      DisplayString
    MAX-ACCESS  read-only
    STATUS      current
    DESCRIPTION "No description yet."

    ::= { dpStatusWSRRSavdSrchSubsPolicyAttachmentsStatusEntry 3 }

dpStatusB2BHighAvailabilityStatus OBJECT IDENTIFIER ::= { dpStatus 245 }

dpStatusB2BHighAvailabilityStatusPersistenceState OBJECT-TYPE
    SYNTAX      DisplayString
    MAX-ACCESS  read-only
    STATUS      current
    DESCRIPTION
        "Lists the current state of the persistence store state machine."

    ::= { dpStatusB2BHighAvailabilityStatus 1 }

dpStatusB2BHighAvailabilityStatusConnectionStatus OBJECT-TYPE
    SYNTAX      DisplayString
    MAX-ACCESS  read-only
    STATUS      current
    DESCRIPTION
        "Lists the current status of the connection to the backup appliance managed
        by the persistence store."

    ::= { dpStatusB2BHighAvailabilityStatus 2 }

--

dpStatusDNSNameServerStatus2Table OBJECT-TYPE
    SYNTAX      SEQUENCE OF DPStatusDNSNameServerStatus2Entry
    MAX-ACCESS  not-accessible
    STATUS      current
    DESCRIPTION
        "List of configured and acquired name servers."

    ::= { dpStatus 247 }

dpStatusDNSNameServerStatus2Entry OBJECT-TYPE
    SYNTAX      DPStatusDNSNameServerStatus2Entry
    MAX-ACCESS  not-accessible
    STATUS      current
    DESCRIPTION "Table row."
    INDEX { dpStatusDNSNameServerStatus2SearchOrderIndex }

    ::= { dpStatusDNSNameServerStatus2Table 1 }

DPStatusDNSNameServerStatus2Entry ::= SEQUENCE {
    dpStatusDNSNameServerStatus2SearchOrderIndex    Unsigned32,
    dpStatusDNSNameServerStatus2IPAddress    IpAddress,
    dpStatusDNSNameServerStatus2UDPPort    Unsigned32,
    dpStatusDNSNameServerStatus2TCPPort    Unsigned32,
    dpStatusDNSNameServerStatus2MaxRetries    Unsigned32
}

dpStatusDNSNameServerStatus2SearchOrderIndex OBJECT-TYPE
    SYNTAX      Unsigned32
    MAX-ACCESS  read-only
    STATUS      current
    DESCRIPTION
        "The name servers will be searched for in the specified order."

    ::= { dpStatusDNSNameServerStatus2Entry 1 }

dpStatusDNSNameServerStatus2IPAddress OBJECT-TYPE
    SYNTAX      IpAddress
    MAX-ACCESS  read-only
    STATUS      current
    DESCRIPTION
        "The numeric IP address for any DNS server that is configured for use on
        this appliance."

    ::= { dpStatusDNSNameServerStatus2Entry 2 }

dpStatusDNSNameServerStatus2UDPPort OBJECT-TYPE
    SYNTAX      Unsigned32 (0..65535)
    MAX-ACCESS  read-only
    STATUS      current
    DESCRIPTION
        "The UDP port number of the DNS server. (The default DNS UDP port is 53.)
        When the load balancing algorithm is first alive, this value is ignored."

    ::= { dpStatusDNSNameServerStatus2Entry 3 }

dpStatusDNSNameServerStatus2TCPPort OBJECT-TYPE
    SYNTAX      Unsigned32 (0..65535)
    MAX-ACCESS  read-only
    STATUS      current
    DESCRIPTION
        "The TCP port number of the DNS server. (The default DNS TCP port is also
        53.) When the load balancing algorithm is first alive, this value is
        ignored."

    ::= { dpStatusDNSNameServerStatus2Entry 4 }

dpStatusDNSNameServerStatus2MaxRetries OBJECT-TYPE
    SYNTAX      Unsigned32
    MAX-ACCESS  read-only
    STATUS      current
    DESCRIPTION
        "The maximum number of lookup requests that are sent to a given DNS name
        server before a connection failure is reported. However, if the load
        balancing algorithm is first alive, the individual host uses the top-level
        retry setting from DNS settings."

    ::= { dpStatusDNSNameServerStatus2Entry 5 }

--

dpStatusFailureNotificationStatusTable OBJECT-TYPE
    SYNTAX      SEQUENCE OF DPStatusFailureNotificationStatusEntry
    MAX-ACCESS  not-accessible
    STATUS      obsolete
    DESCRIPTION
        "Deprecated due to indexing problems
        Note: this is obsoleted and is replaced by dpStatusFailureNotificationStatus2 as of release
    4.0.0"

    ::= { dpStatus 248 }

dpStatusFailureNotificationStatusEntry OBJECT-TYPE
    SYNTAX      DPStatusFailureNotificationStatusEntry
    MAX-ACCESS  not-accessible
    STATUS      obsolete
    DESCRIPTION "Table row."
    INDEX { IMPLIED dpStatusFailureNotificationStatusDate }

    ::= { dpStatusFailureNotificationStatusTable 1 }

DPStatusFailureNotificationStatusEntry ::= SEQUENCE {
    dpStatusFailureNotificationStatusDate    DisplayString,
    dpStatusFailureNotificationStatusReason    INTEGER,
    dpStatusFailureNotificationStatusUploadStatus    INTEGER,
    dpStatusFailureNotificationStatusLocation    DisplayString
}

dpStatusFailureNotificationStatusDate OBJECT-TYPE
    SYNTAX      DisplayString
    MAX-ACCESS  read-only
    STATUS      obsolete
    DESCRIPTION
        "Date and time the error report was created."

    ::= { dpStatusFailureNotificationStatusEntry 1 }

dpStatusFailureNotificationStatusReason OBJECT-TYPE
    SYNTAX      INTEGER { 
                        crash(1),
                        watchdog(2),
                        low-memory(3),
                        low-descriptor(4),
                        user-requested(5),
                        on-startup(6),
                        on-shutdown(7),
                        throttle(8),
                        descriptor-error(9),
                        unknown(10)
                }
    MAX-ACCESS  read-only
    STATUS      obsolete
    DESCRIPTION
        "Date and time the error report was created."

    ::= { dpStatusFailureNotificationStatusEntry 2 }

dpStatusFailureNotificationStatusUploadStatus OBJECT-TYPE
    SYNTAX      INTEGER { 
                        success(1),
                        failure(2),
                        in-progress(3)
                }
    MAX-ACCESS  read-only
    STATUS      obsolete
    DESCRIPTION
        "Date and time the error report was created."

    ::= { dpStatusFailureNotificationStatusEntry 3 }

dpStatusFailureNotificationStatusLocation OBJECT-TYPE
    SYNTAX      DisplayString
    MAX-ACCESS  read-only
    STATUS      obsolete
    DESCRIPTION
        "Date and time the error report was created."

    ::= { dpStatusFailureNotificationStatusEntry 4 }

--

dpStatusRaidVolumeStatus2Table OBJECT-TYPE
    SYNTAX      SEQUENCE OF DPStatusRaidVolumeStatus2Entry
    MAX-ACCESS  not-accessible
    STATUS      current
    DESCRIPTION
        "Details about the RAID volumes"

    ::= { dpStatus 249 }

dpStatusRaidVolumeStatus2Entry OBJECT-TYPE
    SYNTAX      DPStatusRaidVolumeStatus2Entry
    MAX-ACCESS  not-accessible
    STATUS      current
    DESCRIPTION "Table row."
    INDEX { dpStatusRaidVolumeStatus2VolumeNumber, dpStatusRaidVolumeStatus2Type }

    ::= { dpStatusRaidVolumeStatus2Table 1 }

DPStatusRaidVolumeStatus2Entry ::= SEQUENCE {
    dpStatusRaidVolumeStatus2VolumeNumber    Unsigned32,
    dpStatusRaidVolumeStatus2Type    INTEGER,
    dpStatusRaidVolumeStatus2VolumeID    Unsigned32,
    dpStatusRaidVolumeStatus2NumPhysDisks    Unsigned32,
    dpStatusRaidVolumeStatus2State    INTEGER,
    dpStatusRaidVolumeStatus2Enabled    INTEGER,
    dpStatusRaidVolumeStatus2Quiesced    INTEGER,
    dpStatusRaidVolumeStatus2ResyncInProgress    INTEGER,
    dpStatusRaidVolumeStatus2ResyncPercentage    Unsigned32,
    dpStatusRaidVolumeStatus2InactiveStatus    INTEGER,
    dpStatusRaidVolumeStatus2BadBlockTableFull    INTEGER,
    dpStatusRaidVolumeStatus2WriteCachingEnable    INTEGER
}

dpStatusRaidVolumeStatus2VolumeNumber OBJECT-TYPE
    SYNTAX      Unsigned32
    MAX-ACCESS  read-only
    STATUS      current
    DESCRIPTION
        "The number of the RAID volume in the system. Numbering starting with 0."

    ::= { dpStatusRaidVolumeStatus2Entry 1 }

dpStatusRaidVolumeStatus2Type OBJECT-TYPE
    SYNTAX      INTEGER { 
                        unknown(1),
                        raid-0(2),
                        raid-1(3)
                }
    MAX-ACCESS  read-only
    STATUS      current
    DESCRIPTION
        "The type of RAID volume. The incorporation of a particular type does not
        mean that the software supports creating or using this type of volume."

    ::= { dpStatusRaidVolumeStatus2Entry 2 }

dpStatusRaidVolumeStatus2VolumeID OBJECT-TYPE
    SYNTAX      Unsigned32
    MAX-ACCESS  read-only
    STATUS      current
    DESCRIPTION
        "The volume identifier that the RAID controller assigned to the volume."

    ::= { dpStatusRaidVolumeStatus2Entry 3 }

dpStatusRaidVolumeStatus2NumPhysDisks OBJECT-TYPE
    SYNTAX      Unsigned32
    MAX-ACCESS  read-only
    STATUS      current
    DESCRIPTION
        "The number of physical disks that are configured to be part of the RAID
        volume."

    ::= { dpStatusRaidVolumeStatus2Entry 4 }

dpStatusRaidVolumeStatus2State OBJECT-TYPE
    SYNTAX      INTEGER { 
                        optimal(1),
                        degraded(2),
                        failed(3),
                        missing(4)
                }
    MAX-ACCESS  read-only
    STATUS      current
    DESCRIPTION
        "The overall state of the RAID volume."

    ::= { dpStatusRaidVolumeStatus2Entry 5 }

dpStatusRaidVolumeStatus2Enabled OBJECT-TYPE
    SYNTAX      INTEGER { 
                        true(1),
                        false(2)
                }
    MAX-ACCESS  read-only
    STATUS      current
    DESCRIPTION
        "Whether the RAID volume is enabled. If not enabled, there is no file
        system access to the volume."

    ::= { dpStatusRaidVolumeStatus2Entry 6 }

dpStatusRaidVolumeStatus2Quiesced OBJECT-TYPE
    SYNTAX      INTEGER { 
                        true(1),
                        false(2)
                }
    MAX-ACCESS  read-only
    STATUS      current
    DESCRIPTION
        "Whether the RAID volume is quiesced. When quiesced, the volume is enabled
        but no commands (read, write) can be sent to it."

    ::= { dpStatusRaidVolumeStatus2Entry 7 }

dpStatusRaidVolumeStatus2ResyncInProgress OBJECT-TYPE
    SYNTAX      INTEGER { 
                        true(1),
                        false(2)
                }
    MAX-ACCESS  read-only
    STATUS      current
    DESCRIPTION
        "Whether resynchronization of the RAID volume is in progress.
        Resynchronization occurs when the data on the secondary drive is not the
        same that on the primary drive. Resynchronization copies blocks from the
        primary drive to the secondary drive until they match."

    ::= { dpStatusRaidVolumeStatus2Entry 8 }

dpStatusRaidVolumeStatus2ResyncPercentage OBJECT-TYPE
    SYNTAX      Unsigned32
    UNITS       "%"
    MAX-ACCESS  read-only
    STATUS      current
    DESCRIPTION
        "The percentage of the total blocks that are not the same on the primary
        and secondary drives. The value is rounded to the nearest percent, except
        that the result will never be 100% unless resynchronization is absolutely
        complete."

    ::= { dpStatusRaidVolumeStatus2Entry 9 }

dpStatusRaidVolumeStatus2InactiveStatus OBJECT-TYPE
    SYNTAX      INTEGER { 
                        active(1),
                        unknown(2),
                        stale-metadata(3),
                        foreign-volume(4),
                        insufficient-resources(5),
                        clone-volume(6),
                        insufficient-metadata(7),
                        previously-deleted(8)
                }
    MAX-ACCESS  read-only
    STATUS      current
    DESCRIPTION
        "If the RAID volume is active, the status will be 'active'. If the volume
        is inactive, it gives the reason why it is inactive."

    ::= { dpStatusRaidVolumeStatus2Entry 10 }

dpStatusRaidVolumeStatus2BadBlockTableFull OBJECT-TYPE
    SYNTAX      INTEGER { 
                        true(1),
                        false(2)
                }
    MAX-ACCESS  read-only
    STATUS      current
    DESCRIPTION
        "Whether the bad block table on the RAID volume is full."

    ::= { dpStatusRaidVolumeStatus2Entry 11 }

dpStatusRaidVolumeStatus2WriteCachingEnable OBJECT-TYPE
    SYNTAX      INTEGER { 
                        true(1),
                        false(2)
                }
    MAX-ACCESS  read-only
    STATUS      current
    DESCRIPTION
        "Whether write caching on the RAID volume is enabled."

    ::= { dpStatusRaidVolumeStatus2Entry 12 }

--

dpStatusRaidPhysDiskStatus2Table OBJECT-TYPE
    SYNTAX      SEQUENCE OF DPStatusRaidPhysDiskStatus2Entry
    MAX-ACCESS  not-accessible
    STATUS      current
    DESCRIPTION
        "Details about the phyusical disks that are part of the RAID volume."

    ::= { dpStatus 250 }

dpStatusRaidPhysDiskStatus2Entry OBJECT-TYPE
    SYNTAX      DPStatusRaidPhysDiskStatus2Entry
    MAX-ACCESS  not-accessible
    STATUS      current
    DESCRIPTION "Table row."
    INDEX { dpStatusRaidPhysDiskStatus2VolumeNumber, dpStatusRaidPhysDiskStatus2DiskNumber }

    ::= { dpStatusRaidPhysDiskStatus2Table 1 }

DPStatusRaidPhysDiskStatus2Entry ::= SEQUENCE {
    dpStatusRaidPhysDiskStatus2VolumeNumber    Unsigned32,
    dpStatusRaidPhysDiskStatus2DiskNumber    Unsigned32,
    dpStatusRaidPhysDiskStatus2PhysDiskNum    Unsigned32,
    dpStatusRaidPhysDiskStatus2Target    Unsigned32,
    dpStatusRaidPhysDiskStatus2Location    DisplayString,
    dpStatusRaidPhysDiskStatus2State    INTEGER,
    dpStatusRaidPhysDiskStatus2Role    INTEGER,
    dpStatusRaidPhysDiskStatus2VendorID    DisplayString,
    dpStatusRaidPhysDiskStatus2ProductID    DisplayString,
    dpStatusRaidPhysDiskStatus2Revision    DisplayString,
    dpStatusRaidPhysDiskStatus2Identifier    DisplayString,
    dpStatusRaidPhysDiskStatus2OutOfSync    INTEGER,
    dpStatusRaidPhysDiskStatus2Quiesced    INTEGER,
    dpStatusRaidPhysDiskStatus2InactiveVolume    INTEGER,
    dpStatusRaidPhysDiskStatus2OptimalPrevious    INTEGER
}

dpStatusRaidPhysDiskStatus2VolumeNumber OBJECT-TYPE
    SYNTAX      Unsigned32
    MAX-ACCESS  read-only
    STATUS      current
    DESCRIPTION
        "The RAID volume of which this physical disk is a part. Each physical disk
        is in only one RAID volume."

    ::= { dpStatusRaidPhysDiskStatus2Entry 1 }

dpStatusRaidPhysDiskStatus2DiskNumber OBJECT-TYPE
    SYNTAX      Unsigned32
    MAX-ACCESS  read-only
    STATUS      current
    DESCRIPTION
        "The number of the disk in the RAID volume. Numbering starts with 1."

    ::= { dpStatusRaidPhysDiskStatus2Entry 2 }

dpStatusRaidPhysDiskStatus2PhysDiskNum OBJECT-TYPE
    SYNTAX      Unsigned32
    MAX-ACCESS  read-only
    STATUS      current
    DESCRIPTION
        "The physical disk number of this disk. The RAID controller assigns this
        number."

    ::= { dpStatusRaidPhysDiskStatus2Entry 3 }

dpStatusRaidPhysDiskStatus2Target OBJECT-TYPE
    SYNTAX      Unsigned32
    MAX-ACCESS  read-only
    STATUS      current
    DESCRIPTION
        "The SCSI target of the disk."

    ::= { dpStatusRaidPhysDiskStatus2Entry 4 }

dpStatusRaidPhysDiskStatus2Location OBJECT-TYPE
    SYNTAX      DisplayString
    MAX-ACCESS  read-only
    STATUS      current
    DESCRIPTION
        "The physical location of this disk. 'HDD0' is the top disk in the module,
        and 'HDD1' is the bottom disk in the module."

    ::= { dpStatusRaidPhysDiskStatus2Entry 5 }

dpStatusRaidPhysDiskStatus2State OBJECT-TYPE
    SYNTAX      INTEGER { 
                        online(1),
                        missing(2),
                        not-compatible(3),
                        failed(4),
                        initializing(5),
                        requested-offline(6),
                        requested-failed(7),
                        other-offline(8)
                }
    MAX-ACCESS  read-only
    STATUS      current
    DESCRIPTION
        "The current state of the physical disk."

    ::= { dpStatusRaidPhysDiskStatus2Entry 6 }

dpStatusRaidPhysDiskStatus2Role OBJECT-TYPE
    SYNTAX      INTEGER { 
                        other(1),
                        primary(2),
                        secondary(3)
                }
    MAX-ACCESS  read-only
    STATUS      current
    DESCRIPTION
        "The role of the disk in the RAID volume. When the contents on the disks
        disagree, the primary disk wins and the secondary disk is synchronized to
        match the primary disk."

    ::= { dpStatusRaidPhysDiskStatus2Entry 7 }

dpStatusRaidPhysDiskStatus2VendorID OBJECT-TYPE
    SYNTAX      DisplayString
    MAX-ACCESS  read-only
    STATUS      current
    DESCRIPTION
        "The vendor identification string for the hard disk drive."

    ::= { dpStatusRaidPhysDiskStatus2Entry 8 }

dpStatusRaidPhysDiskStatus2ProductID OBJECT-TYPE
    SYNTAX      DisplayString
    MAX-ACCESS  read-only
    STATUS      current
    DESCRIPTION
        "The product identification string for the hard disk drive."

    ::= { dpStatusRaidPhysDiskStatus2Entry 9 }

dpStatusRaidPhysDiskStatus2Revision OBJECT-TYPE
    SYNTAX      DisplayString
    MAX-ACCESS  read-only
    STATUS      current
    DESCRIPTION
        "The revision string of the hard disk drive from the vendor."

    ::= { dpStatusRaidPhysDiskStatus2Entry 10 }

dpStatusRaidPhysDiskStatus2Identifier OBJECT-TYPE
    SYNTAX      DisplayString
    MAX-ACCESS  read-only
    STATUS      current
    DESCRIPTION
        "The vendors identifier string that is read from the hard disk drive.
        Generally, the identifier is unique for each physical drive."

    ::= { dpStatusRaidPhysDiskStatus2Entry 11 }

dpStatusRaidPhysDiskStatus2OutOfSync OBJECT-TYPE
    SYNTAX      INTEGER { 
                        true(1),
                        false(2)
                }
    MAX-ACCESS  read-only
    STATUS      current
    DESCRIPTION
        "For the secondary drive, means that it is not fully sycnhronized with the
        primary drive."

    ::= { dpStatusRaidPhysDiskStatus2Entry 12 }

dpStatusRaidPhysDiskStatus2Quiesced OBJECT-TYPE
    SYNTAX      INTEGER { 
                        true(1),
                        false(2)
                }
    MAX-ACCESS  read-only
    STATUS      current
    DESCRIPTION
        "Indicates whether the disk drive is quiesced, which prevents it from
        receiving read/write commands."

    ::= { dpStatusRaidPhysDiskStatus2Entry 13 }

dpStatusRaidPhysDiskStatus2InactiveVolume OBJECT-TYPE
    SYNTAX      INTEGER { 
                        true(1),
                        false(2)
                }
    MAX-ACCESS  read-only
    STATUS      current
    DESCRIPTION
        "If true, the physical disk is not a member of the RAID volume."

    ::= { dpStatusRaidPhysDiskStatus2Entry 14 }

dpStatusRaidPhysDiskStatus2OptimalPrevious OBJECT-TYPE
    SYNTAX      INTEGER { 
                        true(1),
                        false(2)
                }
    MAX-ACCESS  read-only
    STATUS      current
    DESCRIPTION
        "True if the previous state was optimal, else false."

    ::= { dpStatusRaidPhysDiskStatus2Entry 15 }

--

dpStatusMultipathStatusTable OBJECT-TYPE
    SYNTAX      SEQUENCE OF DPStatusMultipathStatusEntry
    MAX-ACCESS  not-accessible
    STATUS      current
    DESCRIPTION
        "Multipath status"

    ::= { dpStatus 251 }

dpStatusMultipathStatusEntry OBJECT-TYPE
    SYNTAX      DPStatusMultipathStatusEntry
    MAX-ACCESS  not-accessible
    STATUS      current
    DESCRIPTION "Table row."
    INDEX { IMPLIED dpStatusMultipathStatusVolume }

    ::= { dpStatusMultipathStatusTable 1 }

DPStatusMultipathStatusEntry ::= SEQUENCE {
    dpStatusMultipathStatusVolume    DisplayString,
    dpStatusMultipathStatusGroupNumber    Unsigned32,
    dpStatusMultipathStatusGroupPriority    Unsigned32,
    dpStatusMultipathStatusHBA    DisplayString,
    dpStatusMultipathStatusBus    Unsigned32,
    dpStatusMultipathStatusTarget    DisplayString,
    dpStatusMultipathStatusLUN    Unsigned32,
    dpStatusMultipathStatusGroupState    DisplayString,
    dpStatusMultipathStatusPathState    DisplayString,
    dpStatusMultipathStatusDeviceState    DisplayString
}

dpStatusMultipathStatusVolume OBJECT-TYPE
    SYNTAX      DisplayString
    MAX-ACCESS  read-only
    STATUS      current
    DESCRIPTION
        "Name of the logical volume object."

    ::= { dpStatusMultipathStatusEntry 1 }

dpStatusMultipathStatusGroupNumber OBJECT-TYPE
    SYNTAX      Unsigned32
    MAX-ACCESS  read-only
    STATUS      current
    DESCRIPTION
        "Multipath group to which this path belongs."

    ::= { dpStatusMultipathStatusEntry 2 }

dpStatusMultipathStatusGroupPriority OBJECT-TYPE
    SYNTAX      Unsigned32
    MAX-ACCESS  read-only
    STATUS      current
    DESCRIPTION
        "Numeric priority value for this group."

    ::= { dpStatusMultipathStatusEntry 3 }

dpStatusMultipathStatusHBA OBJECT-TYPE
    SYNTAX      DisplayString
    MAX-ACCESS  read-only
    STATUS      current
    DESCRIPTION
        "The Host Bus Adapter associated with this path."

    ::= { dpStatusMultipathStatusEntry 4 }

dpStatusMultipathStatusBus OBJECT-TYPE
    SYNTAX      Unsigned32
    MAX-ACCESS  read-only
    STATUS      current
    DESCRIPTION
        "The number of the SCSI BUS associated with this path."

    ::= { dpStatusMultipathStatusEntry 5 }

dpStatusMultipathStatusTarget OBJECT-TYPE
    SYNTAX      DisplayString
    MAX-ACCESS  read-only
    STATUS      current
    DESCRIPTION
        "The target object associated with this path."

    ::= { dpStatusMultipathStatusEntry 6 }

dpStatusMultipathStatusLUN OBJECT-TYPE
    SYNTAX      Unsigned32
    MAX-ACCESS  read-only
    STATUS      current
    DESCRIPTION
        "The SCSI Logical Unit number associated with this volume."

    ::= { dpStatusMultipathStatusEntry 7 }

dpStatusMultipathStatusGroupState OBJECT-TYPE
    SYNTAX      DisplayString
    MAX-ACCESS  read-only
    STATUS      current
    DESCRIPTION
        "Current state of the multipath path group. Possible states of a path group
        are: active If a path in the active path group is in the ready state, it
        will be sent any I/O requests for the multipath device. At most one path
        group can be in the active state. enabled If no paths in the active path
        group are in the ready state, I/O requests will instead be sent to the
        enabled path groups. Multiple path groups can be in the enabled state.
        disabled If no paths in the active or enabled path groups are in the ready
        state, I/O will be sent to the disabled path groups. Multiple path groups
        can be in the disabled state."

    ::= { dpStatusMultipathStatusEntry 8 }

dpStatusMultipathStatusPathState OBJECT-TYPE
    SYNTAX      DisplayString
    MAX-ACCESS  read-only
    STATUS      current
    DESCRIPTION
        "Current state of the multipath path. Possible states of a path are: active
        The most recent I/O request for this path was successful. failed The most
        recent I/O request for this path failed."

    ::= { dpStatusMultipathStatusEntry 9 }

dpStatusMultipathStatusDeviceState OBJECT-TYPE
    SYNTAX      DisplayString
    MAX-ACCESS  read-only
    STATUS      current
    DESCRIPTION
        "Current state of the device associated with the path. Possible states of a
        device are: ready The path is up and is available for I/O requests. faulty
        The path is down and is not available for I/O requests. ghost The path is
        passive. shaky The path is up, but is temporarily not available for I/O
        requests."

    ::= { dpStatusMultipathStatusEntry 10 }

--

dpStatusIPMISelEventsTable OBJECT-TYPE
    SYNTAX      SEQUENCE OF DPStatusIPMISelEventsEntry
    MAX-ACCESS  not-accessible
    STATUS      current
    DESCRIPTION
        "This table provides the Intelligent Platform Management Interface (IPMI)
        System Event Log (SEL) events that the Baseboard Management Controller
        (BMC) collected. The IPMI events pertain to memory errors, out-of-bound
        sensors, power cycling, restart failures, and other like events. The
        contents of this status provider are cryptic. This information is
        primarily for IBM Support and included in error reports. IBM Support can
        use this information to determine whether there was a hardware failure."

    ::= { dpStatus 252 }

dpStatusIPMISelEventsEntry OBJECT-TYPE
    SYNTAX      DPStatusIPMISelEventsEntry
    MAX-ACCESS  not-accessible
    STATUS      current
    DESCRIPTION "Table row."
    INDEX { dpStatusIPMISelEventsIndex }

    ::= { dpStatusIPMISelEventsTable 1 }

DPStatusIPMISelEventsEntry ::= SEQUENCE {
    dpStatusIPMISelEventsIndex    Unsigned32,
    dpStatusIPMISelEventsTimestamp    DisplayString,
    dpStatusIPMISelEventsRecordType    Unsigned32,
    dpStatusIPMISelEventsSensorType    INTEGER,
    dpStatusIPMISelEventsSensorNumber    Unsigned32,
    dpStatusIPMISelEventsSensorName    DisplayString,
    dpStatusIPMISelEventsEventReadingTypeCode    INTEGER,
    dpStatusIPMISelEventsEventData2    INTEGER,
    dpStatusIPMISelEventsEventDirection    INTEGER,
    dpStatusIPMISelEventsExtra    DisplayString
}

dpStatusIPMISelEventsIndex OBJECT-TYPE
    SYNTAX      Unsigned32
    MAX-ACCESS  read-only
    STATUS      current
    DESCRIPTION
        "The simple sequential index into this table."

    ::= { dpStatusIPMISelEventsEntry 1 }

dpStatusIPMISelEventsTimestamp OBJECT-TYPE
    SYNTAX      DisplayString
    MAX-ACCESS  read-only
    STATUS      current
    DESCRIPTION
        "Timestamp when this event was written to the SEL in the IPMI BMC."

    ::= { dpStatusIPMISelEventsEntry 2 }

dpStatusIPMISelEventsRecordType OBJECT-TYPE
    SYNTAX      Unsigned32 (0..255)
    MAX-ACCESS  read-only
    STATUS      current
    DESCRIPTION
        "The record type in hex of this record."

    ::= { dpStatusIPMISelEventsEntry 3 }

dpStatusIPMISelEventsSensorType OBJECT-TYPE
    SYNTAX      INTEGER { 
                        reserved(0),
                        temperature(1),
                        voltage(2),
                        current(3),
                        fan(4),
                        physicalSecurity(5),
                        platformSecurityViolationAttempt(6),
                        processor(7),
                        powerSupply(8),
                        powerUnit(9),
                        coolingDevice(10),
                        otherUnitsBasedSensor(11),
                        memory(12),
                        driveSlot(13),
                        postMemoryResize(14),
                        systemFirmwareProgress(15),
                        eventLoggingDisabled(16),
                        watchdog1(17),
                        systemEvent(18),
                        criticalInterrupt(19),
                        button(20),
                        moduleOrBoard(21),
                        microcontrollerOrCoprocessor(22),
                        addInCard(23),
                        chassis(24),
                        chipSet(25),
                        otherFru(26),
                        cableOrInterconnect(27),
                        terminator(28),
                        systemBootRestartInitiated(29),
                        bootError(30),
                        osBoot(31),
                        osCriticalStop(32),
                        slotOrConnector(33),
                        systemAcpiPowerStatus(34),
                        watchdog2(35),
                        platformAlert(36),
                        entityPresence(37),
                        monitorAsicIc(38),
                        lan(39),
                        managmentSubsystemHealth(40),
                        battery(41),
                        sessionAudit(42),
                        versionChange(43),
                        fruState(44),
                        kernel(256)
                }
    MAX-ACCESS  read-only
    STATUS      current
    DESCRIPTION
        "The type of sensor that generated this event."

    ::= { dpStatusIPMISelEventsEntry 4 }

dpStatusIPMISelEventsSensorNumber OBJECT-TYPE
    SYNTAX      Unsigned32 (0..255)
    MAX-ACCESS  read-only
    STATUS      current
    DESCRIPTION
        "The internal IPMI BMC sensor number of the sensor that generated this
        event."

    ::= { dpStatusIPMISelEventsEntry 5 }

dpStatusIPMISelEventsSensorName OBJECT-TYPE
    SYNTAX      DisplayString
    MAX-ACCESS  read-only
    STATUS      current
    DESCRIPTION
        "The name of the sensor that generated this event."

    ::= { dpStatusIPMISelEventsEntry 6 }

dpStatusIPMISelEventsEventReadingTypeCode OBJECT-TYPE
    SYNTAX      INTEGER { 
                        none(1),
                        undefined(2),
                        lowerNonCriticalGoingLow(3),
                        lowerNonCriticalGoingHigh(4),
                        lowerCriticalGoingLow(5),
                        lowerCriticalGoingHigh(6),
                        lowerNonRecoverableGoingLow(7),
                        lowerNonRecoverableGoingHigh(8),
                        upperNonCriticalGoingLow(9),
                        upperNonCriticalGoingHigh(10),
                        upperCriticalGoingLow(11),
                        upperCriticalGoingHigh(12),
                        upperNonRecoverableGoingLow(13),
                        upperNonRecoverableGoingHigh(14),
                        transitionToIdle(15),
                        transitionToActive(16),
                        transitionToBusy(17),
                        stateDeasserted(18),
                        stateAsserted(19),
                        predictiveFailureDeasserted(20),
                        predictiveFailureAsserted(21),
                        limitNotExceeded(22),
                        limitExceeded(23),
                        performanceMet(24),
                        performanceLags(25),
                        transitionToOK(26),
                        transitionToNonCriticalFromOK(27),
                        transitionToCriticalFromLessSevere(28),
                        transitionToNonRecoverableFromLessSevere(29),
                        transitionToNonCriticalFromMoreSevere(30),
                        transitionToCriticalFromNonRecoverable(31),
                        transitionToNonRecoverable(32),
                        monitor(33),
                        informational(34),
                        deviceRemovedOrAbsent(35),
                        deviceInsertedOrPresent(36),
                        deviceDisabled(37),
                        deviceEnabled(38),
                        transitionToRunning(39),
                        transitionToInTest(40),
                        transitionToPowerOff(41),
                        transitionToOnLine(42),
                        transitionToOffLine(43),
                        transitionToOffDuty(44),
                        transitionToDegraded(45),
                        transitionToPowerSave(46),
                        installError(47),
                        fullyRedundant(48),
                        redundancyLost(49),
                        redundancyDegraded(50),
                        nonRedundantSufficientResourcesFromRedundant(51),
                        nonRedundantSufficientResourcesFromInsufficient(52),
                        nonRedundantInsufficientResources(53),
                        redundancyDegradedFromFullyRedundant(54),
                        redundancyDegradedFRomNonRedundant(55),
                        acpiD0PowerState(56),
                        acpiD1PowerState(57),
                        acpiD2PowerState(58),
                        acpiD3PowerState(59),
                        temperature(60),
                        voltage(61),
                        current(62),
                        fan(63),
                        generalChassisIntrusion(64),
                        driveBayIntrusion(65),
                        ioCardAreaIntrusion(66),
                        processorAreaIntrusion(67),
                        lanLeashLost(68),
                        unauthorizedDockUndock(69),
                        fanAreaIntrusion(70),
                        secureModeViolationAttempt(71),
                        preBootPasswordViolationUser(72),
                        preBootPasswordViolationSetup(73),
                        preBootPasswordViolationNetworkBoot(74),
                        otherPreBootPasswordViolation(75),
                        outOfBandAccessPasswordViolation(76),
                        ierr(77),
                        thermalTrip(78),
                        frb1BistFailure(79),
                        frb2HangInPostFailure(80),
                        frb3ProcessorStartupInitializationFailure(81),
                        configurationError(82),
                        smbiosUncorrectableCpuComplexError(83),
                        processorPresenceDetected(84),
                        processorDisabled(85),
                        terminatorPresenceDetected(86),
                        processorAutomaticallyThrottled(87),
                        powerSupplyPresenceDetected(88),
                        powerSupplyFailureDetected(89),
                        powerSupplyPredictiveFailure(90),
                        powerSupplyAcLost(91),
                        powerSupplyAcLostOrOutOfRange(92),
                        powerSupplyAcOutOfRangeButPresent(93),
                        powerSupplyConfigurationError(94),
                        powerUnitPowerOff(95),
                        powerUnitPowerCycle(96),
                        powerUnit240VaPowerDown(97),
                        powerUnitInterlockPowerDown(98),
                        powerUnitAcLost(99),
                        powerUnitSoftPowerControlFailure(100),
                        powerUnitFailureDetected(101),
                        powerUnitPredictiveFailure(102),
                        correctableEcc(103),
                        uncorrectableEcc(104),
                        parity(105),
                        memoryScrubFailed(106),
                        memoryDeviceDisabled(107),
                        correctableEccLoggingLimitReached(108),
                        memoryPresenceDetected(109),
                        memoryConfigurationError(110),
                        memorySpare(111),
                        memoryAutomaticallyThrottled(112),
                        memoryCriticalOvertemperature(113),
                        drivePresence(114),
                        driveFault(115),
                        drivePredictiveFailure(116),
                        driveHotSpare(117),
                        driveConsistencyCheckInProgress(118),
                        driveInCriticalArray(119),
                        driveInFailedArray(120),
                        driveRebuildInProgress(121),
                        driveRebuildAborted(122),
                        systemFirmwareError(123),
                        systemFirmwareHang(124),
                        systemFirmwareProgress(125),
                        correctableMemoryErrorLoggingDisabled(126),
                        eventLoggingDisabled(127),
                        logAreaReset(128),
                        allEventLoggingDisabled(129),
                        selFull(130),
                        selAlmostFull(131),
                        biosWatchdogReset(132),
                        osWatchdogReset(133),
                        osWatchdogShutDown(134),
                        osWatchdogPowerDown(135),
                        osWatchdogPowerCycle(136),
                        osWatchdogNmiDiagnosticInterrupt(137),
                        osWatchdogExpiredStatusOnly(138),
                        osWatchdogPreTimeoutInterrupt(139),
                        systemReconfigured(140),
                        oemSystemBootEvent(141),
                        undeterminedSystemHardwareFailure(142),
                        entryAddedToAuxiliaryLog(143),
                        pefAction(144),
                        timestampClockSync(145),
                        frontPanelNmiInterrupt(146),
                        busTimeout(147),
                        ioChannelCheckNmi(148),
                        softwareNmi(149),
                        pciPerr(150),
                        pciSerr(151),
                        eisaFailSafeTimeout(152),
                        busCorrectableError(153),
                        busUncorrectableError(154),
                        fatalNmi(155),
                        busFatalError(156),
                        busDegraded(157),
                        powerButtonPressed(158),
                        sleepButtonPressed(159),
                        resetButtonPressed(160),
                        fruLatchOpen(161),
                        fruServiceRequestButton(162),
                        softPowerControlFailure(163),
                        initiatedByPowerUp(164),
                        initiatedByHardReset(165),
                        initiatedByWarmReset(166),
                        userRequestedPxeBoot(167),
                        automaticBootToDiagnostic(168),
                        noBootableMedia(169),
                        nonBootableDiskette(170),
                        pxeServerNotFound(171),
                        invalidBootSector(172),
                        timeoutWaitingForUserSelectionOfBootSource(173),
                        aBootCompleted(174),
                        cBootCompleted(175),
                        pxeBootCompleted(176),
                        diagnosticBootCompleted(177),
                        cdromBootCompleted(178),
                        romBootCompleted(179),
                        bootCompleted(180),
                        stopDuringOsLoadInitialization(181),
                        runTimeStop(182),
                        slotFaultStatusAsserted(183),
                        slotIdentifyStatusAsserted(184),
                        slotDeviceInstalled(185),
                        slotReadyForDeviceInstallation(186),
                        slotReadyForDeviceRemoval(187),
                        slotPowerIsOff(188),
                        slotDeviceRemovalRequest(189),
                        slotInterlockAsserted(190),
                        slotIsDisabled(191),
                        slotHoldsSpare(192),
                        acpiS0G0PowerState(193),
                        acpiS1PowerState(194),
                        acpiS2PowerState(195),
                        acpiS3PowerState(196),
                        acpiS4PowerState(197),
                        acpiS5G2PowerState(198),
                        acpiS4S5SoftOff(199),
                        acpiG3PowerState(200),
                        acpiSleepingS1S2S3(201),
                        acpiG1PowerState(202),
                        acpiS5OverrideState(203),
                        acpiLegacyOnState(204),
                        acpiLegacyOffState(205),
                        acpiUnknown(206),
                        watchdog2TimeExpired(207),
                        watchdog2HardReset(208),
                        watchdog2PowerDown(209),
                        watchdog2PowerCycle(210),
                        watchdog2TimerInterrupt(211),
                        platformGeneratedPage(212),
                        platformGeneratedLanAlert(213),
                        platformGeneratedEventTrap(214),
                        platformGeneratedSnmpTrap(215),
                        entityPresent(216),
                        entityAbsent(217),
                        entityDisabled(218),
                        lanHeartbeatLost(219),
                        lanHeartbeat(220),
                        sensorAccessDegradedOrUnavailable(221),
                        controllerAccessDegradedOrUnavailable(222),
                        managementControllerOffLine(223),
                        managementControllerUnavailable(224),
                        batteryLow(225),
                        batteryFailed(226),
                        batteryPresenceDetected(227),
                        sessionActivated(228),
                        sessionDeactivated(229),
                        hardwareVersionChange(230),
                        firmwareVersionChange(231),
                        hardwareIncompatibility(232),
                        firmwareIncompatibility(233),
                        entityIsUnsupportedHardwareVersion(234),
                        entityContainsUnsupportedFirmwareVersion(235),
                        hardwareChangeSuccessful(236),
                        firmwareChangeSuccessful(237),
                        fruNotInstalled(238),
                        fruInactive(239),
                        fruActivationRequested(240),
                        fruActivationInProgress(241),
                        fruActive(242),
                        fruDeactivationRequested(243),
                        fruDeactivationInProgress(244),
                        fruCommunicationLost(245),
                        kernelPanic(246)
                }
    MAX-ACCESS  read-only
    STATUS      current
    DESCRIPTION
        "The type of event transition that the sensor made that caused this event
        record to be added to the BMC SEL. The presence of a enumeration value
        does not imply that the enumeration value is used by the product."

    ::= { dpStatusIPMISelEventsEntry 7 }

dpStatusIPMISelEventsEventData2 OBJECT-TYPE
    SYNTAX      INTEGER { 
                        none(1),
                        unspecified(2),
                        noSystemMemoryInstalled(3),
                        noUsableSystemMemory(4),
                        unrecoverableHardDiskDeviceFailure(5),
                        unrecoverableSystemBoardFailure(6),
                        unrecoverableDisketteSubsystemFailure(7),
                        unrecoverableHardDiskControllerFailure(8),
                        unrecoverableKeyboardFailure(9),
                        removableBootMediaNotFound(10),
                        unrecoverableVideoControllerFailure(11),
                        noVideoDeviceDetected(12),
                        firmwareRomCorruptionDetected(13),
                        cpuVoltageMismatch(14),
                        cpuSpeedMatchingFailure(15),
                        memoryInitialization(16),
                        hardDiskInitialization(17),
                        secondaryProcessorInitialization(18),
                        userAuthentication(19),
                        userInitiatedSystemStartup(20),
                        usbResourceConfiguration(21),
                        pciResourceConfiguration(22),
                        optionRomInitialization(23),
                        videoInitialization(24),
                        cacheInitialization(25),
                        smbusInitialization(26),
                        keyboardControllerInitialization(27),
                        embeddedManagementControllerInitialization(28),
                        dockingStationAttachment(29),
                        enablingDockingStation(30),
                        dockingStationEjection(31),
                        disablingDockingStation(32),
                        callingOperatingSystemWakeupVector(33),
                        startingOperatingSystemBoot(34),
                        baseboardInitialization(35),
                        reserved(36),
                        floppyInitialization(37),
                        keyboardTest(38),
                        pointingDeviceTest(39),
                        primaryProcessorInitialization(40),
                        interruptTypeSMI(41),
                        interruptTypeNMI(42),
                        interruptTypeMessagingInterrupt(43)
                }
    MAX-ACCESS  read-only
    STATUS      current
    DESCRIPTION
        "Additional data for some event types from the Event Data 2 field of the
        SEL entry."

    ::= { dpStatusIPMISelEventsEntry 8 }

dpStatusIPMISelEventsEventDirection OBJECT-TYPE
    SYNTAX      INTEGER { 
                        none(1),
                        asserted(2),
                        deasserted(3)
                }
    MAX-ACCESS  read-only
    STATUS      current
    DESCRIPTION
        "The direction of the sensor event that caused this event record to be
        added to the BMC SEL."

    ::= { dpStatusIPMISelEventsEntry 9 }

dpStatusIPMISelEventsExtra OBJECT-TYPE
    SYNTAX      DisplayString
    MAX-ACCESS  read-only
    STATUS      current
    DESCRIPTION
        "Extra information used for some event types."

    ::= { dpStatusIPMISelEventsEntry 10 }

--

dpStatusServicesMemoryStatusTable OBJECT-TYPE
    SYNTAX      SEQUENCE OF DPStatusServicesMemoryStatusEntry
    MAX-ACCESS  not-accessible
    STATUS      deprecated
    DESCRIPTION
        "Details of memory usage by services.
        Note: this is obsoleted and is replaced by dpStatusServicesMemoryStatus2"

    ::= { dpStatus 253 }

dpStatusServicesMemoryStatusEntry OBJECT-TYPE
    SYNTAX      DPStatusServicesMemoryStatusEntry
    MAX-ACCESS  not-accessible
    STATUS      deprecated
    DESCRIPTION "Table row."
    INDEX { dpStatusServicesMemoryStatusserviceClass, IMPLIED dpStatusServicesMemoryStatusserviceName }

    ::= { dpStatusServicesMemoryStatusTable 1 }

DPStatusServicesMemoryStatusEntry ::= SEQUENCE {
    dpStatusServicesMemoryStatusserviceClass    INTEGER,
    dpStatusServicesMemoryStatusserviceName    DisplayString,
    dpStatusServicesMemoryStatuscurrent    Unsigned32,
    dpStatusServicesMemoryStatusoneMinute    Unsigned32,
    dpStatusServicesMemoryStatusfiveMinutes    Unsigned32,
    dpStatusServicesMemoryStatustenMinutes    Unsigned32,
    dpStatusServicesMemoryStatusoneHour    Unsigned32,
    dpStatusServicesMemoryStatustwelveHours    Unsigned32,
    dpStatusServicesMemoryStatusoneDay    Unsigned32,
    dpStatusServicesMemoryStatuslifetime    Unsigned32
}

dpStatusServicesMemoryStatusserviceClass OBJECT-TYPE
    SYNTAX      INTEGER { 
                        xSLProxyService(19),
                        xMLFirewallService(42),
                        wSGateway(95),
                        multiProtocolGateway(101),
                        webAppFW(132),
                        b2BGateway(195),
                        webTokenService(266),
                        apiGateway(360)
                }
    MAX-ACCESS  read-only
    STATUS      deprecated
    DESCRIPTION
        "The type of service being considered."

    ::= { dpStatusServicesMemoryStatusEntry 1 }

dpStatusServicesMemoryStatusserviceName OBJECT-TYPE
    SYNTAX      DisplayString
    MAX-ACCESS  read-only
    STATUS      deprecated
    DESCRIPTION
        "Name of the service."

    ::= { dpStatusServicesMemoryStatusEntry 2 }

dpStatusServicesMemoryStatuscurrent OBJECT-TYPE
    SYNTAX      Unsigned32
    UNITS       "kilobytes"
    MAX-ACCESS  read-only
    STATUS      deprecated
    DESCRIPTION
        "Current memory being used by this service."

    ::= { dpStatusServicesMemoryStatusEntry 3 }

dpStatusServicesMemoryStatusoneMinute OBJECT-TYPE
    SYNTAX      Unsigned32
    UNITS       "kilobytes"
    MAX-ACCESS  read-only
    STATUS      deprecated
    DESCRIPTION
        "The peak memory usage by the service over the previous minute."

    ::= { dpStatusServicesMemoryStatusEntry 4 }

dpStatusServicesMemoryStatusfiveMinutes OBJECT-TYPE
    SYNTAX      Unsigned32
    UNITS       "kilobytes"
    MAX-ACCESS  read-only
    STATUS      deprecated
    DESCRIPTION
        "The peak memory usage by the service in the interval between 1 and 5
        minutes ago."

    ::= { dpStatusServicesMemoryStatusEntry 5 }

dpStatusServicesMemoryStatustenMinutes OBJECT-TYPE
    SYNTAX      Unsigned32
    UNITS       "kilobytes"
    MAX-ACCESS  read-only
    STATUS      deprecated
    DESCRIPTION
        "The peak memory usage by the service in the interval between 5 and 10
        minutes ago."

    ::= { dpStatusServicesMemoryStatusEntry 6 }

dpStatusServicesMemoryStatusoneHour OBJECT-TYPE
    SYNTAX      Unsigned32
    UNITS       "kilobytes"
    MAX-ACCESS  read-only
    STATUS      deprecated
    DESCRIPTION
        "The peak memory usage by the service in the interval between 10 minutes
        and 1 hour ago."

    ::= { dpStatusServicesMemoryStatusEntry 7 }

dpStatusServicesMemoryStatustwelveHours OBJECT-TYPE
    SYNTAX      Unsigned32
    UNITS       "kilobytes"
    MAX-ACCESS  read-only
    STATUS      deprecated
    DESCRIPTION
        "The peak memory usage by the service in the interval between 1 and 12
        hours ago."

    ::= { dpStatusServicesMemoryStatusEntry 8 }

dpStatusServicesMemoryStatusoneDay OBJECT-TYPE
    SYNTAX      Unsigned32
    UNITS       "kilobytes"
    MAX-ACCESS  read-only
    STATUS      deprecated
    DESCRIPTION
        "The peak memory usage by the service in the interval between 12 hours and
        1 day ago."

    ::= { dpStatusServicesMemoryStatusEntry 9 }

dpStatusServicesMemoryStatuslifetime OBJECT-TYPE
    SYNTAX      Unsigned32
    UNITS       "kilobytes"
    MAX-ACCESS  read-only
    STATUS      deprecated
    DESCRIPTION
        "The peak memory usage by the service over its lifetime."

    ::= { dpStatusServicesMemoryStatusEntry 10 }

--

dpStatusSecureCloudConnectorConnectionsStatusTable OBJECT-TYPE
    SYNTAX      SEQUENCE OF DPStatusSecureCloudConnectorConnectionsStatusEntry
    MAX-ACCESS  not-accessible
    STATUS      deprecated
    DESCRIPTION
        "Displays the status of all configured Secure Cloud Connectors."

    ::= { dpStatus 254 }

dpStatusSecureCloudConnectorConnectionsStatusEntry OBJECT-TYPE
    SYNTAX      DPStatusSecureCloudConnectorConnectionsStatusEntry
    MAX-ACCESS  not-accessible
    STATUS      deprecated
    DESCRIPTION "Table row."
    INDEX { dpStatusSecureCloudConnectorConnectionsStatusRemotePort, dpStatusSecureCloudConnectorConnectionsStatusLocalTunnelIP, IMPLIED dpStatusSecureCloudConnectorConnectionsStatusRemoteTunnelIP }

    ::= { dpStatusSecureCloudConnectorConnectionsStatusTable 1 }

DPStatusSecureCloudConnectorConnectionsStatusEntry ::= SEQUENCE {
    dpStatusSecureCloudConnectorConnectionsStatusConfig    DisplayString,
    dpStatusSecureCloudConnectorConnectionsStatusAdminState    INTEGER,
    dpStatusSecureCloudConnectorConnectionsStatusOpState    INTEGER,
    dpStatusSecureCloudConnectorConnectionsStatusInterface    DisplayString,
    dpStatusSecureCloudConnectorConnectionsStatusRemoteIP    DisplayString,
    dpStatusSecureCloudConnectorConnectionsStatusRemotePort    Unsigned32,
    dpStatusSecureCloudConnectorConnectionsStatusLocalTunnelIP    DisplayString,
    dpStatusSecureCloudConnectorConnectionsStatusRemoteTunnelIP    DisplayString,
    dpStatusSecureCloudConnectorConnectionsStatusStartTime    TimeStamp,
    dpStatusSecureCloudConnectorConnectionsStatusRxKbytes    Counter64,
    dpStatusSecureCloudConnectorConnectionsStatusRxPackets    Counter64,
    dpStatusSecureCloudConnectorConnectionsStatusRxErrors    Counter64,
    dpStatusSecureCloudConnectorConnectionsStatusRxDrops    Counter64,
    dpStatusSecureCloudConnectorConnectionsStatusTxKbytes    Counter64,
    dpStatusSecureCloudConnectorConnectionsStatusTxPackets    Counter64,
    dpStatusSecureCloudConnectorConnectionsStatusTxErrors    Counter64,
    dpStatusSecureCloudConnectorConnectionsStatusTxDrops    Counter64
}

dpStatusSecureCloudConnectorConnectionsStatusConfig OBJECT-TYPE
    SYNTAX      DisplayString
    MAX-ACCESS  read-only
    STATUS      deprecated
    DESCRIPTION
        "The name of Secure Cloud Connector."

    ::= { dpStatusSecureCloudConnectorConnectionsStatusEntry 1 }

dpStatusSecureCloudConnectorConnectionsStatusAdminState OBJECT-TYPE
    SYNTAX      INTEGER { 
                        enabled(1),
                        disabled(2)
                }
    MAX-ACCESS  read-only
    STATUS      deprecated
    DESCRIPTION
        "The administrative state of the Secure Cloud Connector."

    ::= { dpStatusSecureCloudConnectorConnectionsStatusEntry 2 }

dpStatusSecureCloudConnectorConnectionsStatusOpState OBJECT-TYPE
    SYNTAX      INTEGER { 
                        up(1),
                        down(2)
                }
    MAX-ACCESS  read-only
    STATUS      deprecated
    DESCRIPTION
        "The operational state of the Secure Cloud Connector."

    ::= { dpStatusSecureCloudConnectorConnectionsStatusEntry 3 }

dpStatusSecureCloudConnectorConnectionsStatusInterface OBJECT-TYPE
    SYNTAX      DisplayString
    MAX-ACCESS  read-only
    STATUS      deprecated
    DESCRIPTION
        "The name of the interface."

    ::= { dpStatusSecureCloudConnectorConnectionsStatusEntry 4 }

dpStatusSecureCloudConnectorConnectionsStatusRemoteIP OBJECT-TYPE
    SYNTAX      DisplayString
    MAX-ACCESS  read-only
    STATUS      deprecated
    DESCRIPTION
        "The remote host name of the cloud server instance for Secure Cloud
        Connector communications."

    ::= { dpStatusSecureCloudConnectorConnectionsStatusEntry 5 }

dpStatusSecureCloudConnectorConnectionsStatusRemotePort OBJECT-TYPE
    SYNTAX      Unsigned32 (0..65535)
    MAX-ACCESS  read-only
    STATUS      deprecated
    DESCRIPTION
        "The remote IP port number of the SSH server of the cloud server."

    ::= { dpStatusSecureCloudConnectorConnectionsStatusEntry 6 }

dpStatusSecureCloudConnectorConnectionsStatusLocalTunnelIP OBJECT-TYPE
    SYNTAX      DisplayString
    MAX-ACCESS  read-only
    STATUS      deprecated
    DESCRIPTION
        "The Local tunnel IPv4 address of the local tunnel endpoint."

    ::= { dpStatusSecureCloudConnectorConnectionsStatusEntry 7 }

dpStatusSecureCloudConnectorConnectionsStatusRemoteTunnelIP OBJECT-TYPE
    SYNTAX      DisplayString
    MAX-ACCESS  read-only
    STATUS      deprecated
    DESCRIPTION
        "The Remote tunnel IPv4 address of the remote tunnel endpoint."

    ::= { dpStatusSecureCloudConnectorConnectionsStatusEntry 8 }

dpStatusSecureCloudConnectorConnectionsStatusStartTime OBJECT-TYPE
    SYNTAX      TimeStamp
    MAX-ACCESS  read-only
    STATUS      deprecated
    DESCRIPTION
        "Lists the timestamp when the connection started."

    ::= { dpStatusSecureCloudConnectorConnectionsStatusEntry 9 }

dpStatusSecureCloudConnectorConnectionsStatusRxKbytes OBJECT-TYPE
    SYNTAX      Counter64
    MAX-ACCESS  read-only
    STATUS      deprecated
    DESCRIPTION
        "The kilobytes of traffic received."

    ::= { dpStatusSecureCloudConnectorConnectionsStatusEntry 10 }

dpStatusSecureCloudConnectorConnectionsStatusRxPackets OBJECT-TYPE
    SYNTAX      Counter64
    MAX-ACCESS  read-only
    STATUS      deprecated
    DESCRIPTION
        "The number of packets received."

    ::= { dpStatusSecureCloudConnectorConnectionsStatusEntry 11 }

dpStatusSecureCloudConnectorConnectionsStatusRxErrors OBJECT-TYPE
    SYNTAX      Counter64
    MAX-ACCESS  read-only
    STATUS      deprecated
    DESCRIPTION
        "The number of errors encountered during reception."

    ::= { dpStatusSecureCloudConnectorConnectionsStatusEntry 12 }

dpStatusSecureCloudConnectorConnectionsStatusRxDrops OBJECT-TYPE
    SYNTAX      Counter64
    MAX-ACCESS  read-only
    STATUS      deprecated
    DESCRIPTION
        "The number of received packets that were dropped."

    ::= { dpStatusSecureCloudConnectorConnectionsStatusEntry 13 }

dpStatusSecureCloudConnectorConnectionsStatusTxKbytes OBJECT-TYPE
    SYNTAX      Counter64
    MAX-ACCESS  read-only
    STATUS      deprecated
    DESCRIPTION
        "The kilobytes of traffic transmitted."

    ::= { dpStatusSecureCloudConnectorConnectionsStatusEntry 14 }

dpStatusSecureCloudConnectorConnectionsStatusTxPackets OBJECT-TYPE
    SYNTAX      Counter64
    MAX-ACCESS  read-only
    STATUS      deprecated
    DESCRIPTION
        "The number of packets transmitted."

    ::= { dpStatusSecureCloudConnectorConnectionsStatusEntry 15 }

dpStatusSecureCloudConnectorConnectionsStatusTxErrors OBJECT-TYPE
    SYNTAX      Counter64
    MAX-ACCESS  read-only
    STATUS      deprecated
    DESCRIPTION
        "The number of transmission errors."

    ::= { dpStatusSecureCloudConnectorConnectionsStatusEntry 16 }

dpStatusSecureCloudConnectorConnectionsStatusTxDrops OBJECT-TYPE
    SYNTAX      Counter64
    MAX-ACCESS  read-only
    STATUS      deprecated
    DESCRIPTION
        "The number of packets dropped during transmission."

    ::= { dpStatusSecureCloudConnectorConnectionsStatusEntry 17 }

--

dpStatusSSHKnownHostFileStatusTable OBJECT-TYPE
    SYNTAX      SEQUENCE OF DPStatusSSHKnownHostFileStatusEntry
    MAX-ACCESS  not-accessible
    STATUS      obsolete
    DESCRIPTION
        "SSH known host tables for the SSH client profile. If the table is no
        longer needed, it can be deleted using the 'Delete Table' button.
        Note: this is obsoleted and is replaced by dpStatusSSHKnownHostFileStatus2 as of release 5.0.0"

    ::= { dpStatus 255 }

dpStatusSSHKnownHostFileStatusEntry OBJECT-TYPE
    SYNTAX      DPStatusSSHKnownHostFileStatusEntry
    MAX-ACCESS  not-accessible
    STATUS      obsolete
    DESCRIPTION "Table row."
    INDEX { IMPLIED dpStatusSSHKnownHostFileStatusDomainName }

    ::= { dpStatusSSHKnownHostFileStatusTable 1 }

DPStatusSSHKnownHostFileStatusEntry ::= SEQUENCE {
    dpStatusSSHKnownHostFileStatusDomainName    DisplayString,
    dpStatusSSHKnownHostFileStatusClientName    DisplayString
}

dpStatusSSHKnownHostFileStatusDomainName OBJECT-TYPE
    SYNTAX      DisplayString
    MAX-ACCESS  read-only
    STATUS      obsolete
    DESCRIPTION
        "The domain name associated with the table."

    ::= { dpStatusSSHKnownHostFileStatusEntry 1 }

dpStatusSSHKnownHostFileStatusClientName OBJECT-TYPE
    SYNTAX      DisplayString
    MAX-ACCESS  read-only
    STATUS      obsolete
    DESCRIPTION
        "The SSH client profile name associated with the table."

    ::= { dpStatusSSHKnownHostFileStatusEntry 2 }

--

dpStatusSQLRuntimeStatusTable OBJECT-TYPE
    SYNTAX      SEQUENCE OF DPStatusSQLRuntimeStatusEntry
    MAX-ACCESS  not-accessible
    STATUS      current
    DESCRIPTION
        "The memory status of each sql runtime environment is reported. There may
        be more than one runtime running under the same profile."

    ::= { dpStatus 256 }

dpStatusSQLRuntimeStatusEntry OBJECT-TYPE
    SYNTAX      DPStatusSQLRuntimeStatusEntry
    MAX-ACCESS  not-accessible
    STATUS      current
    DESCRIPTION "Table row."
    INDEX { dpStatusSQLRuntimeStatusInstance }

    ::= { dpStatusSQLRuntimeStatusTable 1 }

DPStatusSQLRuntimeStatusEntry ::= SEQUENCE {
    dpStatusSQLRuntimeStatusInstance    Unsigned32,
    dpStatusSQLRuntimeStatusProfileName    DisplayString,
    dpStatusSQLRuntimeStatusMaxMemory    Unsigned32,
    dpStatusSQLRuntimeStatusFreeMemory    Unsigned32,
    dpStatusSQLRuntimeStatusTotalMemory    Unsigned32,
    dpStatusSQLRuntimeStatusMaxMemory2    Gauge32,
    dpStatusSQLRuntimeStatusFreeMemory2    Gauge32,
    dpStatusSQLRuntimeStatusTotalMemory2    Gauge32
}

dpStatusSQLRuntimeStatusInstance OBJECT-TYPE
    SYNTAX      Unsigned32
    MAX-ACCESS  read-only
    STATUS      current
    DESCRIPTION
        "An automatic identifier for this runtime. There may be multiple runtimes
        for each profile."

    ::= { dpStatusSQLRuntimeStatusEntry 1 }

dpStatusSQLRuntimeStatusProfileName OBJECT-TYPE
    SYNTAX      DisplayString
    MAX-ACCESS  read-only
    STATUS      current
    DESCRIPTION
        "Name given to the profile in the runtime settings."

    ::= { dpStatusSQLRuntimeStatusEntry 2 }

dpStatusSQLRuntimeStatusMaxMemory OBJECT-TYPE
    SYNTAX      Unsigned32
    UNITS       "kibibytes"
    MAX-ACCESS  read-only
    STATUS      obsolete
    DESCRIPTION
        "The maximum memory allowed for any runtime in this profile. This value is
        configurable in the runtime settings. Obsoleted in release 5.0.0.0 due to
        incompatible SNMP changes in release 4.0.1.0. When read via SNMP, the
        value type improperly returns Counter64 from release 4.0.1.0 to release
        4.0.1.7 and from release 4.0.2.0 to release 4.0.2.3."

    ::= { dpStatusSQLRuntimeStatusEntry 3 }

dpStatusSQLRuntimeStatusFreeMemory OBJECT-TYPE
    SYNTAX      Unsigned32
    UNITS       "kibibytes"
    MAX-ACCESS  read-only
    STATUS      obsolete
    DESCRIPTION
        "The amount of free memory currently available to the runtime environment.
        Obsoleted in release 5.0.0.0 due to incompatible SNMP changes in release
        4.0.1.0. When read via SNMP, the value type improperly returns Counter64
        from release 4.0.1.0 to release 4.0.1.7 and from release 4.0.2.0 to
        release 4.0.2.3."

    ::= { dpStatusSQLRuntimeStatusEntry 4 }

dpStatusSQLRuntimeStatusTotalMemory OBJECT-TYPE
    SYNTAX      Unsigned32
    UNITS       "kibibytes"
    MAX-ACCESS  read-only
    STATUS      obsolete
    DESCRIPTION
        "The total memory consumed by this runtime, including all the services
        running in this runtime. Obsoleted in release 5.0.0.0 due to incompatible
        SNMP changes in release 4.0.1.0. When read via SNMP, the value type
        improperly returns Counter64 from release 4.0.1.0 to release 4.0.1.7 and
        from release 4.0.2.0 to release 4.0.2.3."

    ::= { dpStatusSQLRuntimeStatusEntry 5 }

dpStatusSQLRuntimeStatusMaxMemory2 OBJECT-TYPE
    SYNTAX      Gauge32
    UNITS       "kibibytes"
    MAX-ACCESS  read-only
    STATUS      current
    DESCRIPTION
        "The maximum memory allowed for any runtime in this profile. This value is
        configurable in the runtime settings."

    ::= { dpStatusSQLRuntimeStatusEntry 6 }

dpStatusSQLRuntimeStatusFreeMemory2 OBJECT-TYPE
    SYNTAX      Gauge32
    UNITS       "kibibytes"
    MAX-ACCESS  read-only
    STATUS      current
    DESCRIPTION
        "The amount of free memory currently available to the runtime environment."

    ::= { dpStatusSQLRuntimeStatusEntry 7 }

dpStatusSQLRuntimeStatusTotalMemory2 OBJECT-TYPE
    SYNTAX      Gauge32
    UNITS       "kibibytes"
    MAX-ACCESS  read-only
    STATUS      current
    DESCRIPTION
        "The total memory consumed by this runtime, including all the services
        running in this runtime."

    ::= { dpStatusSQLRuntimeStatusEntry 8 }

--

dpStatusRaidArrayStatusTable OBJECT-TYPE
    SYNTAX      SEQUENCE OF DPStatusRaidArrayStatusEntry
    MAX-ACCESS  not-accessible
    STATUS      current
    DESCRIPTION
        "Details about the status of the RAID array."

    ::= { dpStatus 257 }

dpStatusRaidArrayStatusEntry OBJECT-TYPE
    SYNTAX      DPStatusRaidArrayStatusEntry
    MAX-ACCESS  not-accessible
    STATUS      current
    DESCRIPTION "Table row."
    INDEX { dpStatusRaidArrayStatusControllerID, dpStatusRaidArrayStatusArrayID }

    ::= { dpStatusRaidArrayStatusTable 1 }

DPStatusRaidArrayStatusEntry ::= SEQUENCE {
    dpStatusRaidArrayStatusControllerID    Unsigned32,
    dpStatusRaidArrayStatusArrayID    Unsigned32,
    dpStatusRaidArrayStatusLogicalDriveID    Unsigned32,
    dpStatusRaidArrayStatusRaidLevel    INTEGER,
    dpStatusRaidArrayStatusNumPhysicalDrives    Unsigned32,
    dpStatusRaidArrayStatusTotalSize    Unsigned32
}

dpStatusRaidArrayStatusControllerID OBJECT-TYPE
    SYNTAX      Unsigned32
    MAX-ACCESS  read-only
    STATUS      current
    DESCRIPTION
        "The reference number of the RAID card. The value is always 1."

    ::= { dpStatusRaidArrayStatusEntry 1 }

dpStatusRaidArrayStatusArrayID OBJECT-TYPE
    SYNTAX      Unsigned32
    MAX-ACCESS  read-only
    STATUS      current
    DESCRIPTION
        "The referece number of the this array. Numbering starts with 1."

    ::= { dpStatusRaidArrayStatusEntry 2 }

dpStatusRaidArrayStatusLogicalDriveID OBJECT-TYPE
    SYNTAX      Unsigned32
    MAX-ACCESS  read-only
    STATUS      current
    DESCRIPTION
        "The identifier of the logical driver of which this array is part."

    ::= { dpStatusRaidArrayStatusEntry 3 }

dpStatusRaidArrayStatusRaidLevel OBJECT-TYPE
    SYNTAX      INTEGER { 
                        raidLevel0(1),
                        raidLevel1(2),
                        raidLevel1E(3),
                        raidLevel5(4),
                        raidLevel6(5),
                        raidLevel10(6),
                        raidLevel50(7),
                        raidLevel60(8),
                        undefined(9)
                }
    MAX-ACCESS  read-only
    STATUS      current
    DESCRIPTION
        "The RAID level of this array configuration."

    ::= { dpStatusRaidArrayStatusEntry 4 }

dpStatusRaidArrayStatusNumPhysicalDrives OBJECT-TYPE
    SYNTAX      Unsigned32
    MAX-ACCESS  read-only
    STATUS      current
    DESCRIPTION
        "The number of the physical drives for this array."

    ::= { dpStatusRaidArrayStatusEntry 5 }

dpStatusRaidArrayStatusTotalSize OBJECT-TYPE
    SYNTAX      Unsigned32
    UNITS       "MB"
    MAX-ACCESS  read-only
    STATUS      current
    DESCRIPTION
        "The normalized size of this array in megabytes. The value is rounded down
        to an even multiple, which allows you to swap drives of the same nominal
        size but might not be the same raw size."

    ::= { dpStatusRaidArrayStatusEntry 6 }

--

dpStatusRaidBatteryBackUpStatusTable OBJECT-TYPE
    SYNTAX      SEQUENCE OF DPStatusRaidBatteryBackUpStatusEntry
    MAX-ACCESS  not-accessible
    STATUS      current
    DESCRIPTION
        "The details about the battery backup unit (BBU) of the RAID controller.
        The BBU protects against the loss of cached data in the event of a power
        failure."

    ::= { dpStatus 258 }

dpStatusRaidBatteryBackUpStatusEntry OBJECT-TYPE
    SYNTAX      DPStatusRaidBatteryBackUpStatusEntry
    MAX-ACCESS  not-accessible
    STATUS      current
    DESCRIPTION "Table row."
    INDEX { dpStatusRaidBatteryBackUpStatusControllerID }

    ::= { dpStatusRaidBatteryBackUpStatusTable 1 }

DPStatusRaidBatteryBackUpStatusEntry ::= SEQUENCE {
    dpStatusRaidBatteryBackUpStatusControllerID    Unsigned32,
    dpStatusRaidBatteryBackUpStatusBatteryType    INTEGER,
    dpStatusRaidBatteryBackUpStatusSerial    Unsigned32,
    dpStatusRaidBatteryBackUpStatusName    DisplayString,
    dpStatusRaidBatteryBackUpStatusStatus    INTEGER,
    dpStatusRaidBatteryBackUpStatusVoltage    Unsigned32,
    dpStatusRaidBatteryBackUpStatusCurrent    Integer32,
    dpStatusRaidBatteryBackUpStatusTemperature    Unsigned32,
    dpStatusRaidBatteryBackUpStatusDesignCapacity    Unsigned32,
    dpStatusRaidBatteryBackUpStatusDesignVoltage    Unsigned32,
    dpStatusRaidBatteryBackUpStatusRemainingCapacity    Unsigned32,
    dpStatusRaidBatteryBackUpStatusFullChargeCapacity    Unsigned32,
    dpStatusRaidBatteryBackUpStatusRunTimeToEmpty    Unsigned32,
    dpStatusRaidBatteryBackUpStatusAvgTimeToEmpty    Unsigned32,
    dpStatusRaidBatteryBackUpStatusAvgTimeToFull    Unsigned32,
    dpStatusRaidBatteryBackUpStatusCycleCount    Unsigned32,
    dpStatusRaidBatteryBackUpStatusRemainingCapacityAlarm    Unsigned32,
    dpStatusRaidBatteryBackUpStatusRemainingTimeAlarm    Unsigned32
}

dpStatusRaidBatteryBackUpStatusControllerID OBJECT-TYPE
    SYNTAX      Unsigned32
    MAX-ACCESS  read-only
    STATUS      current
    DESCRIPTION
        "The reference number of the RAID controller. The value is always 1."

    ::= { dpStatusRaidBatteryBackUpStatusEntry 1 }

dpStatusRaidBatteryBackUpStatusBatteryType OBJECT-TYPE
    SYNTAX      INTEGER { 
                        noBatteryPresent(1),
                        ibbu(2),
                        bbu(3),
                        zcrLegacyBBU(4),
                        itbbu3(5),
                        ibbu08(6),
                        unknown(7)
                }
    MAX-ACCESS  read-only
    STATUS      current
    DESCRIPTION
        "The type of the BBU."

    ::= { dpStatusRaidBatteryBackUpStatusEntry 2 }

dpStatusRaidBatteryBackUpStatusSerial OBJECT-TYPE
    SYNTAX      Unsigned32
    MAX-ACCESS  read-only
    STATUS      current
    DESCRIPTION
        "The serial number of the BBU."

    ::= { dpStatusRaidBatteryBackUpStatusEntry 3 }

dpStatusRaidBatteryBackUpStatusName OBJECT-TYPE
    SYNTAX      DisplayString
    MAX-ACCESS  read-only
    STATUS      current
    DESCRIPTION
        "The product name of the BBU."

    ::= { dpStatusRaidBatteryBackUpStatusEntry 4 }

dpStatusRaidBatteryBackUpStatusStatus OBJECT-TYPE
    SYNTAX      INTEGER { 
                        chargeActive(1),
                        dischargeActive(2),
                        i2cErrorsDetected(3),
                        learnCycleActive(4),
                        learnCycleFailed(5),
                        learnCycleRequested(6),
                        learnCycleTimeout(7),
                        packMissing(8),
                        temperatureHigh(9),
                        voltageLow(10),
                        periodicLearnRequired(11),
                        remainingCapacityLow(12),
                        replacePack(13),
                        normal(14),
                        undefined(15),
                        transparentLearn(16)
                }
    MAX-ACCESS  read-only
    STATUS      current
    DESCRIPTION
        "The status of the BBU."

    ::= { dpStatusRaidBatteryBackUpStatusEntry 5 }

dpStatusRaidBatteryBackUpStatusVoltage OBJECT-TYPE
    SYNTAX      Unsigned32
    UNITS       "mV"
    MAX-ACCESS  read-only
    STATUS      current
    DESCRIPTION
        "The actual voltage of the battery in millivolts."

    ::= { dpStatusRaidBatteryBackUpStatusEntry 6 }

dpStatusRaidBatteryBackUpStatusCurrent OBJECT-TYPE
    SYNTAX      Integer32
    UNITS       "mA"
    MAX-ACCESS  read-only
    STATUS      current
    DESCRIPTION
        "The current that flows through the battery terminals in milliamperes."

    ::= { dpStatusRaidBatteryBackUpStatusEntry 7 }

dpStatusRaidBatteryBackUpStatusTemperature OBJECT-TYPE
    SYNTAX      Unsigned32
    UNITS       "C"
    MAX-ACCESS  read-only
    STATUS      current
    DESCRIPTION
        "The temperature of the battery in degrees Celcius."

    ::= { dpStatusRaidBatteryBackUpStatusEntry 8 }

dpStatusRaidBatteryBackUpStatusDesignCapacity OBJECT-TYPE
    SYNTAX      Unsigned32
    UNITS       "mAh"
    MAX-ACCESS  read-only
    STATUS      current
    DESCRIPTION
        "The designed capacity of the battery in milliampere-hour."

    ::= { dpStatusRaidBatteryBackUpStatusEntry 9 }

dpStatusRaidBatteryBackUpStatusDesignVoltage OBJECT-TYPE
    SYNTAX      Unsigned32
    UNITS       "mV"
    MAX-ACCESS  read-only
    STATUS      current
    DESCRIPTION
        "The designed voltage of the battery in millivolts."

    ::= { dpStatusRaidBatteryBackUpStatusEntry 10 }

dpStatusRaidBatteryBackUpStatusRemainingCapacity OBJECT-TYPE
    SYNTAX      Unsigned32
    UNITS       "mAh"
    MAX-ACCESS  read-only
    STATUS      current
    DESCRIPTION
        "The predicted capacity remaining in the battery in milliampere-hour."

    ::= { dpStatusRaidBatteryBackUpStatusEntry 11 }

dpStatusRaidBatteryBackUpStatusFullChargeCapacity OBJECT-TYPE
    SYNTAX      Unsigned32
    UNITS       "mAh"
    MAX-ACCESS  read-only
    STATUS      current
    DESCRIPTION
        "The predicted capacity of the battery when fully charged in
        milliampere-hour."

    ::= { dpStatusRaidBatteryBackUpStatusEntry 12 }

dpStatusRaidBatteryBackUpStatusRunTimeToEmpty OBJECT-TYPE
    SYNTAX      Unsigned32
    UNITS       "minutes"
    MAX-ACCESS  read-only
    STATUS      current
    DESCRIPTION
        "The relative gain or loss of the battery in response to a change in the
        power policy in minutes."

    ::= { dpStatusRaidBatteryBackUpStatusEntry 13 }

dpStatusRaidBatteryBackUpStatusAvgTimeToEmpty OBJECT-TYPE
    SYNTAX      Unsigned32
    UNITS       "minutes"
    MAX-ACCESS  read-only
    STATUS      current
    DESCRIPTION
        "The time in minutes to deplete the battery. The time is calculated based
        on the 1-minute rolling average of the power that is being charged to the
        battery."

    ::= { dpStatusRaidBatteryBackUpStatusEntry 14 }

dpStatusRaidBatteryBackUpStatusAvgTimeToFull OBJECT-TYPE
    SYNTAX      Unsigned32
    UNITS       "minutes"
    MAX-ACCESS  read-only
    STATUS      current
    DESCRIPTION
        "Time in minutes to fully charge the battery. The time is calculated based
        on the 1-minute rolling average of the power that is being charged to the
        battery."

    ::= { dpStatusRaidBatteryBackUpStatusEntry 15 }

dpStatusRaidBatteryBackUpStatusCycleCount OBJECT-TYPE
    SYNTAX      Unsigned32
    MAX-ACCESS  read-only
    STATUS      current
    DESCRIPTION
        "The number of charge cycles that the battery has experienced."

    ::= { dpStatusRaidBatteryBackUpStatusEntry 16 }

dpStatusRaidBatteryBackUpStatusRemainingCapacityAlarm OBJECT-TYPE
    SYNTAX      Unsigned32
    UNITS       "mAh"
    MAX-ACCESS  read-only
    STATUS      current
    DESCRIPTION
        "The threshold of the remaining capacity in milliampere-hour. When the
        threshold is reached, the system will throw an alarm. If the 'Battery
        Type' is iBBU08, this is deprecated and does not display any value."

    ::= { dpStatusRaidBatteryBackUpStatusEntry 17 }

dpStatusRaidBatteryBackUpStatusRemainingTimeAlarm OBJECT-TYPE
    SYNTAX      Unsigned32
    UNITS       "minutes"
    MAX-ACCESS  read-only
    STATUS      current
    DESCRIPTION
        "The threshold of the remaining time in minutes. When the threshold is
        reached, the system will throw an alarm. If the 'Battery Type' is iBBU08,
        this is deprecated and does not display any value."

    ::= { dpStatusRaidBatteryBackUpStatusEntry 18 }

--

dpStatusRaidLogicalDriveStatusTable OBJECT-TYPE
    SYNTAX      SEQUENCE OF DPStatusRaidLogicalDriveStatusEntry
    MAX-ACCESS  not-accessible
    STATUS      current
    DESCRIPTION
        "Details about the RAID logical drive."

    ::= { dpStatus 259 }

dpStatusRaidLogicalDriveStatusEntry OBJECT-TYPE
    SYNTAX      DPStatusRaidLogicalDriveStatusEntry
    MAX-ACCESS  not-accessible
    STATUS      current
    DESCRIPTION "Table row."
    INDEX { dpStatusRaidLogicalDriveStatusControllerID, dpStatusRaidLogicalDriveStatusLogicalDriveID }

    ::= { dpStatusRaidLogicalDriveStatusTable 1 }

DPStatusRaidLogicalDriveStatusEntry ::= SEQUENCE {
    dpStatusRaidLogicalDriveStatusControllerID    Unsigned32,
    dpStatusRaidLogicalDriveStatusLogicalDriveID    Unsigned32,
    dpStatusRaidLogicalDriveStatusLogicalDriveName    DisplayString,
    dpStatusRaidLogicalDriveStatusRaidLevel    INTEGER,
    dpStatusRaidLogicalDriveStatusNumPhysicalDrives    Unsigned32,
    dpStatusRaidLogicalDriveStatusState    INTEGER,
    dpStatusRaidLogicalDriveStatusInitProgress    INTEGER,
    dpStatusRaidLogicalDriveStatusCurrReadPolicy    INTEGER,
    dpStatusRaidLogicalDriveStatusCurrWritePolicy    INTEGER,
    dpStatusRaidLogicalDriveStatusCurrCachePolicy    INTEGER,
    dpStatusRaidLogicalDriveStatusAccessPolicy    INTEGER,
    dpStatusRaidLogicalDriveStatusBadBlockExists    INTEGER,
    dpStatusRaidLogicalDriveStatusTotalSize    Unsigned32
}

dpStatusRaidLogicalDriveStatusControllerID OBJECT-TYPE
    SYNTAX      Unsigned32
    MAX-ACCESS  read-only
    STATUS      current
    DESCRIPTION
        "The reference number of the RAID card. The value is always 1."

    ::= { dpStatusRaidLogicalDriveStatusEntry 1 }

dpStatusRaidLogicalDriveStatusLogicalDriveID OBJECT-TYPE
    SYNTAX      Unsigned32
    MAX-ACCESS  read-only
    STATUS      current
    DESCRIPTION
        "The reference number of this logical drive."

    ::= { dpStatusRaidLogicalDriveStatusEntry 2 }

dpStatusRaidLogicalDriveStatusLogicalDriveName OBJECT-TYPE
    SYNTAX      DisplayString
    MAX-ACCESS  read-only
    STATUS      current
    DESCRIPTION
        "The name of the logical drive. The value is always 'raid0'."

    ::= { dpStatusRaidLogicalDriveStatusEntry 3 }

dpStatusRaidLogicalDriveStatusRaidLevel OBJECT-TYPE
    SYNTAX      INTEGER { 
                        raidLevel0(1),
                        raidLevel1(2),
                        raidLevel1E(3),
                        raidLevel5(4),
                        raidLevel6(5),
                        raidLevel10(6),
                        raidLevel50(7),
                        raidLevel60(8),
                        undefined(9)
                }
    MAX-ACCESS  read-only
    STATUS      current
    DESCRIPTION
        "The configuration of the RAID level for the logical disk in the RAID
        volume."

    ::= { dpStatusRaidLogicalDriveStatusEntry 4 }

dpStatusRaidLogicalDriveStatusNumPhysicalDrives OBJECT-TYPE
    SYNTAX      Unsigned32
    MAX-ACCESS  read-only
    STATUS      current
    DESCRIPTION
        "The number of physical drives in the logical drive."

    ::= { dpStatusRaidLogicalDriveStatusEntry 5 }

dpStatusRaidLogicalDriveStatusState OBJECT-TYPE
    SYNTAX      INTEGER { 
                        offline(1),
                        partiallyDegraded(2),
                        degraded(3),
                        optimal(4),
                        unknown(5)
                }
    MAX-ACCESS  read-only
    STATUS      current
    DESCRIPTION
        "The state of a logical disk in a RAID volume."

    ::= { dpStatusRaidLogicalDriveStatusEntry 6 }

dpStatusRaidLogicalDriveStatusInitProgress OBJECT-TYPE
    SYNTAX      INTEGER { 
                        noInitInProgress(1),
                        quickInitInProgress(2),
                        fullInitInProgress(3),
                        unknown(4)
                }
    MAX-ACCESS  read-only
    STATUS      current
    DESCRIPTION
        "The progress of the initialization of the logical drive."

    ::= { dpStatusRaidLogicalDriveStatusEntry 7 }

dpStatusRaidLogicalDriveStatusCurrReadPolicy OBJECT-TYPE
    SYNTAX      INTEGER { 
                        noReadAhead(1),
                        adaptiveReadAhead(2),
                        readAhead(3),
                        writeThrough(4),
                        writeBack(5),
                        writeCachingOkIfBadBBU(6),
                        cachedIO(7),
                        directIO(8)
                }
    MAX-ACCESS  read-only
    STATUS      current
    DESCRIPTION
        "The read policy in effect."

    ::= { dpStatusRaidLogicalDriveStatusEntry 8 }

dpStatusRaidLogicalDriveStatusCurrWritePolicy OBJECT-TYPE
    SYNTAX      INTEGER { 
                        noReadAhead(1),
                        adaptiveReadAhead(2),
                        readAhead(3),
                        writeThrough(4),
                        writeBack(5),
                        writeCachingOkIfBadBBU(6),
                        cachedIO(7),
                        directIO(8)
                }
    MAX-ACCESS  read-only
    STATUS      current
    DESCRIPTION
        "The write policy in effect."

    ::= { dpStatusRaidLogicalDriveStatusEntry 9 }

dpStatusRaidLogicalDriveStatusCurrCachePolicy OBJECT-TYPE
    SYNTAX      INTEGER { 
                        noReadAhead(1),
                        adaptiveReadAhead(2),
                        readAhead(3),
                        writeThrough(4),
                        writeBack(5),
                        writeCachingOkIfBadBBU(6),
                        cachedIO(7),
                        directIO(8)
                }
    MAX-ACCESS  read-only
    STATUS      current
    DESCRIPTION
        "The cache policy in effect."

    ::= { dpStatusRaidLogicalDriveStatusEntry 10 }

dpStatusRaidLogicalDriveStatusAccessPolicy OBJECT-TYPE
    SYNTAX      INTEGER { 
                        readWrite(1),
                        readOnly(2),
                        blocked(3),
                        unknown(4)
                }
    MAX-ACCESS  read-only
    STATUS      current
    DESCRIPTION
        "The access policy in effect for the logical drive."

    ::= { dpStatusRaidLogicalDriveStatusEntry 11 }

dpStatusRaidLogicalDriveStatusBadBlockExists OBJECT-TYPE
    SYNTAX      INTEGER { 
                        noBadBlock(1),
                        badBlockExist(2)
                }
    MAX-ACCESS  read-only
    STATUS      current
    DESCRIPTION
        "An indicator of whether there are bad blocks in the logical drive."

    ::= { dpStatusRaidLogicalDriveStatusEntry 12 }

dpStatusRaidLogicalDriveStatusTotalSize OBJECT-TYPE
    SYNTAX      Unsigned32
    UNITS       "MB"
    MAX-ACCESS  read-only
    STATUS      current
    DESCRIPTION
        "The total size of the logical drive in megabytes."

    ::= { dpStatusRaidLogicalDriveStatusEntry 13 }

--

dpStatusRaidPhysicalDriveStatusTable OBJECT-TYPE
    SYNTAX      SEQUENCE OF DPStatusRaidPhysicalDriveStatusEntry
    MAX-ACCESS  not-accessible
    STATUS      current
    DESCRIPTION
        "Details about the RAID physical drives"

    ::= { dpStatus 260 }

dpStatusRaidPhysicalDriveStatusEntry OBJECT-TYPE
    SYNTAX      DPStatusRaidPhysicalDriveStatusEntry
    MAX-ACCESS  not-accessible
    STATUS      current
    DESCRIPTION "Table row."
    INDEX { dpStatusRaidPhysicalDriveStatusControllerID, dpStatusRaidPhysicalDriveStatusDeviceID }

    ::= { dpStatusRaidPhysicalDriveStatusTable 1 }

DPStatusRaidPhysicalDriveStatusEntry ::= SEQUENCE {
    dpStatusRaidPhysicalDriveStatusControllerID    Unsigned32,
    dpStatusRaidPhysicalDriveStatusDeviceID    Unsigned32,
    dpStatusRaidPhysicalDriveStatusArrayID    Unsigned32,
    dpStatusRaidPhysicalDriveStatusLogicalDriveID    Unsigned32,
    dpStatusRaidPhysicalDriveStatusLogicalDriveName    DisplayString,
    dpStatusRaidPhysicalDriveStatusPosition    INTEGER,
    dpStatusRaidPhysicalDriveStatusState    INTEGER,
    dpStatusRaidPhysicalDriveStatusProgressPercent    Unsigned32,
    dpStatusRaidPhysicalDriveStatusRawSize    Unsigned32,
    dpStatusRaidPhysicalDriveStatusCoercedSize    Unsigned32,
    dpStatusRaidPhysicalDriveStatusInterfaceType    INTEGER,
    dpStatusRaidPhysicalDriveStatusInterfaceSpeed    INTEGER,
    dpStatusRaidPhysicalDriveStatusSASaddress    DisplayString,
    dpStatusRaidPhysicalDriveStatusVendorID    DisplayString,
    dpStatusRaidPhysicalDriveStatusProductID    DisplayString,
    dpStatusRaidPhysicalDriveStatusRevision    DisplayString,
    dpStatusRaidPhysicalDriveStatusSpecificInfo    DisplayString,
    dpStatusRaidPhysicalDriveStatusFailure    INTEGER,
    dpStatusRaidPhysicalDriveStatusTemperature    DisplayString
}

dpStatusRaidPhysicalDriveStatusControllerID OBJECT-TYPE
    SYNTAX      Unsigned32
    MAX-ACCESS  read-only
    STATUS      current
    DESCRIPTION
        "The RAID controller ID. Numbering starts with 1."

    ::= { dpStatusRaidPhysicalDriveStatusEntry 1 }

dpStatusRaidPhysicalDriveStatusDeviceID OBJECT-TYPE
    SYNTAX      Unsigned32
    MAX-ACCESS  read-only
    STATUS      current
    DESCRIPTION
        "The device identifier of the physical drive. Numbering starts with 1."

    ::= { dpStatusRaidPhysicalDriveStatusEntry 2 }

dpStatusRaidPhysicalDriveStatusArrayID OBJECT-TYPE
    SYNTAX      Unsigned32
    MAX-ACCESS  read-only
    STATUS      current
    DESCRIPTION
        "The RAID array identifier to which this physical drive joins."

    ::= { dpStatusRaidPhysicalDriveStatusEntry 3 }

dpStatusRaidPhysicalDriveStatusLogicalDriveID OBJECT-TYPE
    SYNTAX      Unsigned32
    MAX-ACCESS  read-only
    STATUS      current
    DESCRIPTION
        "The logical drive identifier of which this physical drive is a part."

    ::= { dpStatusRaidPhysicalDriveStatusEntry 4 }

dpStatusRaidPhysicalDriveStatusLogicalDriveName OBJECT-TYPE
    SYNTAX      DisplayString
    MAX-ACCESS  read-only
    STATUS      current
    DESCRIPTION
        "The name of the logical drive. The value is always 'raid0'."

    ::= { dpStatusRaidPhysicalDriveStatusEntry 5 }

dpStatusRaidPhysicalDriveStatusPosition OBJECT-TYPE
    SYNTAX      INTEGER { 
                        hDD0(1),
                        hDD1(2),
                        hDD2(3),
                        hDD3(4),
                        b5S1(5),
                        b5S2(6),
                        b7S1(7),
                        b7S2(8),
                        undefined(9)
                }
    MAX-ACCESS  read-only
    STATUS      current
    DESCRIPTION
        "The location of the physical drive from the front panel point-of-view of
        the appliance."

    ::= { dpStatusRaidPhysicalDriveStatusEntry 6 }

dpStatusRaidPhysicalDriveStatusState OBJECT-TYPE
    SYNTAX      INTEGER { 
                        unconfiguredGood(1),
                        unconfiguredGoodForeign(2),
                        unconfiguredBad(3),
                        unconfiguredBadForeign(4),
                        hotSpare(5),
                        offline(6),
                        failed(7),
                        rebuild(8),
                        online(9),
                        copyback(10),
                        system(11),
                        undefined(12)
                }
    MAX-ACCESS  read-only
    STATUS      current
    DESCRIPTION
        "The current state of the physical drive."

    ::= { dpStatusRaidPhysicalDriveStatusEntry 7 }

dpStatusRaidPhysicalDriveStatusProgressPercent OBJECT-TYPE
    SYNTAX      Unsigned32
    UNITS       "%"
    MAX-ACCESS  read-only
    STATUS      current
    DESCRIPTION
        "The current progress percentage of the operation on the physical drive.
        Operations can be rebuild, copyback, patrol, or clear."

    ::= { dpStatusRaidPhysicalDriveStatusEntry 8 }

dpStatusRaidPhysicalDriveStatusRawSize OBJECT-TYPE
    SYNTAX      Unsigned32
    UNITS       "MB"
    MAX-ACCESS  read-only
    STATUS      current
    DESCRIPTION
        "The exact size of the drive in megabytes."

    ::= { dpStatusRaidPhysicalDriveStatusEntry 9 }

dpStatusRaidPhysicalDriveStatusCoercedSize OBJECT-TYPE
    SYNTAX      Unsigned32
    UNITS       "MB"
    MAX-ACCESS  read-only
    STATUS      current
    DESCRIPTION
        "The normalized size in megabytes. The value is rounded down to an even
        multiple, which allows you to swap drives of the same nominal size but
        might not be the same raw size."

    ::= { dpStatusRaidPhysicalDriveStatusEntry 10 }

dpStatusRaidPhysicalDriveStatusInterfaceType OBJECT-TYPE
    SYNTAX      INTEGER { 
                        unknown(1),
                        parallelSCSI(2),
                        sas(3),
                        sata(4),
                        fiberChannel(5),
                        undefined(6)
                }
    MAX-ACCESS  read-only
    STATUS      current
    DESCRIPTION
        "The interface type of the drive."

    ::= { dpStatusRaidPhysicalDriveStatusEntry 11 }

dpStatusRaidPhysicalDriveStatusInterfaceSpeed OBJECT-TYPE
    SYNTAX      INTEGER { 
                        serial1point5GigabitsPerSecond(1),
                        serial3point0GigabitsPerSecond(2),
                        serial6point0GigabitsPerSecond(3),
                        notApplicable(4)
                }
    MAX-ACCESS  read-only
    STATUS      current
    DESCRIPTION
        "The SAS interface speed negotiated between the RAID controller and the
        physical drive."

    ::= { dpStatusRaidPhysicalDriveStatusEntry 12 }

dpStatusRaidPhysicalDriveStatusSASaddress OBJECT-TYPE
    SYNTAX      DisplayString
    MAX-ACCESS  read-only
    STATUS      current
    DESCRIPTION
        "The SAS address of a physical drive."

    ::= { dpStatusRaidPhysicalDriveStatusEntry 13 }

dpStatusRaidPhysicalDriveStatusVendorID OBJECT-TYPE
    SYNTAX      DisplayString
    MAX-ACCESS  read-only
    STATUS      current
    DESCRIPTION
        "The vendor identification string for the hard disk drive."

    ::= { dpStatusRaidPhysicalDriveStatusEntry 14 }

dpStatusRaidPhysicalDriveStatusProductID OBJECT-TYPE
    SYNTAX      DisplayString
    MAX-ACCESS  read-only
    STATUS      current
    DESCRIPTION
        "The product identification string for the hard disk drive."

    ::= { dpStatusRaidPhysicalDriveStatusEntry 15 }

dpStatusRaidPhysicalDriveStatusRevision OBJECT-TYPE
    SYNTAX      DisplayString
    MAX-ACCESS  read-only
    STATUS      current
    DESCRIPTION
        "The revision string of the hard disk drive from the vendor."

    ::= { dpStatusRaidPhysicalDriveStatusEntry 16 }

dpStatusRaidPhysicalDriveStatusSpecificInfo OBJECT-TYPE
    SYNTAX      DisplayString
    MAX-ACCESS  read-only
    STATUS      current
    DESCRIPTION
        "The vendor specific information string that is read from the hard drive.
        Generally, the identifier is unique for each physical drive."

    ::= { dpStatusRaidPhysicalDriveStatusEntry 17 }

dpStatusRaidPhysicalDriveStatusFailure OBJECT-TYPE
    SYNTAX      INTEGER { 
                        yes(1),
                        no(2)
                }
    MAX-ACCESS  read-only
    STATUS      current
    DESCRIPTION
        "If the hard disk failure state shows Yes, replace this drive as soon as
        possible to avoid possible data loss."

    ::= { dpStatusRaidPhysicalDriveStatusEntry 18 }

dpStatusRaidPhysicalDriveStatusTemperature OBJECT-TYPE
    SYNTAX      DisplayString
    UNITS       "Degree C/Degree F"
    MAX-ACCESS  read-only
    STATUS      current
    DESCRIPTION
        "The temperature of the hard disk drive."

    ::= { dpStatusRaidPhysicalDriveStatusEntry 19 }

--

dpStatusCurrentSensorsTable OBJECT-TYPE
    SYNTAX      SEQUENCE OF DPStatusCurrentSensorsEntry
    MAX-ACCESS  not-accessible
    STATUS      current
    DESCRIPTION
        "Sensors that read electrical currents, from the power supplies and other
        components of the appliance."

    ::= { dpStatus 261 }

dpStatusCurrentSensorsEntry OBJECT-TYPE
    SYNTAX      DPStatusCurrentSensorsEntry
    MAX-ACCESS  not-accessible
    STATUS      current
    DESCRIPTION "Table row."
    INDEX { IMPLIED dpStatusCurrentSensorsName }

    ::= { dpStatusCurrentSensorsTable 1 }

DPStatusCurrentSensorsEntry ::= SEQUENCE {
    dpStatusCurrentSensorsName    DisplayString,
    dpStatusCurrentSensorsValue    Integer32,
    dpStatusCurrentSensorsUpperCriticalThreshold    Integer32,
    dpStatusCurrentSensorsReadingStatus    INTEGER
}

dpStatusCurrentSensorsName OBJECT-TYPE
    SYNTAX      DisplayString
    MAX-ACCESS  read-only
    STATUS      current
    DESCRIPTION
        "The name of the current sensor that is being monitored."

    ::= { dpStatusCurrentSensorsEntry 1 }

dpStatusCurrentSensorsValue OBJECT-TYPE
    SYNTAX      Integer32
    UNITS       "mA"
    MAX-ACCESS  read-only
    STATUS      current
    DESCRIPTION
        "The most recent reading of the current sensor in milliamperes. There are
        only three significant digits."

    ::= { dpStatusCurrentSensorsEntry 2 }

dpStatusCurrentSensorsUpperCriticalThreshold OBJECT-TYPE
    SYNTAX      Integer32
    UNITS       "mA"
    MAX-ACCESS  read-only
    STATUS      current
    DESCRIPTION
        "The maximum allowable reading of the current sensor in milliamperes."

    ::= { dpStatusCurrentSensorsEntry 3 }

dpStatusCurrentSensorsReadingStatus OBJECT-TYPE
    SYNTAX      INTEGER { 
                        lowerNonRecoverable(1),
                        lowerCritical(2),
                        lowerNonCritical(3),
                        ok(4),
                        upperNonCritical(5),
                        upperCritical(6),
                        upperNonRecoverable(7),
                        failure(8),
                        noReading(9),
                        invalid(10)
                }
    MAX-ACCESS  read-only
    STATUS      current
    DESCRIPTION
        "An indicator of whether the current reading is OK or the reading exceeds
        the upper critical threshold. If the status is not OK, check whether the
        temperature is too high or the fan does not work. If the temperature is
        normal and the fan works, the appliance must have failed. Replace the
        appliance."

    ::= { dpStatusCurrentSensorsEntry 4 }

--

dpStatusDomainsMemoryStatusTable OBJECT-TYPE
    SYNTAX      SEQUENCE OF DPStatusDomainsMemoryStatusEntry
    MAX-ACCESS  not-accessible
    STATUS      deprecated
    DESCRIPTION
        "Details of memory usage by services and caches for a specific domain.
        Note: this is obsoleted and is replaced by dpStatusDomainsMemoryStatus2"

    ::= { dpStatus 263 }

dpStatusDomainsMemoryStatusEntry OBJECT-TYPE
    SYNTAX      DPStatusDomainsMemoryStatusEntry
    MAX-ACCESS  not-accessible
    STATUS      deprecated
    DESCRIPTION "Table row."
    INDEX { IMPLIED dpStatusDomainsMemoryStatusDomain }

    ::= { dpStatusDomainsMemoryStatusTable 1 }

DPStatusDomainsMemoryStatusEntry ::= SEQUENCE {
    dpStatusDomainsMemoryStatusDomain    DisplayString,
    dpStatusDomainsMemoryStatusServicesCurrent    Unsigned32,
    dpStatusDomainsMemoryStatusServicesOneMinute    Unsigned32,
    dpStatusDomainsMemoryStatusServicesFiveMinutes    Unsigned32,
    dpStatusDomainsMemoryStatusServicesTenMinutes    Unsigned32,
    dpStatusDomainsMemoryStatusServicesOneHour    Unsigned32,
    dpStatusDomainsMemoryStatusServicesTwelveHours    Unsigned32,
    dpStatusDomainsMemoryStatusServicesOneDay    Unsigned32,
    dpStatusDomainsMemoryStatusServicesLifetime    Unsigned32,
    dpStatusDomainsMemoryStatusDocumentCaches    Unsigned32,
    dpStatusDomainsMemoryStatusStylesheetCaches    Unsigned32
}

dpStatusDomainsMemoryStatusDomain OBJECT-TYPE
    SYNTAX      DisplayString
    MAX-ACCESS  read-only
    STATUS      deprecated
    DESCRIPTION
        "The name of the domain."

    ::= { dpStatusDomainsMemoryStatusEntry 1 }

dpStatusDomainsMemoryStatusServicesCurrent OBJECT-TYPE
    SYNTAX      Unsigned32
    UNITS       "kilobytes"
    MAX-ACCESS  read-only
    STATUS      deprecated
    DESCRIPTION
        "Current total memory being used by all services of this domain."

    ::= { dpStatusDomainsMemoryStatusEntry 2 }

dpStatusDomainsMemoryStatusServicesOneMinute OBJECT-TYPE
    SYNTAX      Unsigned32
    UNITS       "kilobytes"
    MAX-ACCESS  read-only
    STATUS      deprecated
    DESCRIPTION
        "The peak memory usage by services of this domain over the previous minute."

    ::= { dpStatusDomainsMemoryStatusEntry 3 }

dpStatusDomainsMemoryStatusServicesFiveMinutes OBJECT-TYPE
    SYNTAX      Unsigned32
    UNITS       "kilobytes"
    MAX-ACCESS  read-only
    STATUS      deprecated
    DESCRIPTION
        "The peak memory usage by services of this domain in the interval between 1
        and 5 minutes ago."

    ::= { dpStatusDomainsMemoryStatusEntry 4 }

dpStatusDomainsMemoryStatusServicesTenMinutes OBJECT-TYPE
    SYNTAX      Unsigned32
    UNITS       "kilobytes"
    MAX-ACCESS  read-only
    STATUS      deprecated
    DESCRIPTION
        "The peak memory usage by services of this domain in the interval between 5
        and 10 minutes ago."

    ::= { dpStatusDomainsMemoryStatusEntry 5 }

dpStatusDomainsMemoryStatusServicesOneHour OBJECT-TYPE
    SYNTAX      Unsigned32
    UNITS       "kilobytes"
    MAX-ACCESS  read-only
    STATUS      deprecated
    DESCRIPTION
        "The peak memory usage by services of this domain in the interval between
        10 minutes and 1 hour ago."

    ::= { dpStatusDomainsMemoryStatusEntry 6 }

dpStatusDomainsMemoryStatusServicesTwelveHours OBJECT-TYPE
    SYNTAX      Unsigned32
    UNITS       "kilobytes"
    MAX-ACCESS  read-only
    STATUS      deprecated
    DESCRIPTION
        "The peak memory usage by services of this domain in the interval between 1
        and 12 hours ago."

    ::= { dpStatusDomainsMemoryStatusEntry 7 }

dpStatusDomainsMemoryStatusServicesOneDay OBJECT-TYPE
    SYNTAX      Unsigned32
    UNITS       "kilobytes"
    MAX-ACCESS  read-only
    STATUS      deprecated
    DESCRIPTION
        "The peak memory usage by services of this domain in the interval between
        12 hours and 1 day ago."

    ::= { dpStatusDomainsMemoryStatusEntry 8 }

dpStatusDomainsMemoryStatusServicesLifetime OBJECT-TYPE
    SYNTAX      Unsigned32
    UNITS       "kilobytes"
    MAX-ACCESS  read-only
    STATUS      deprecated
    DESCRIPTION
        "The peak memory usage by services of this domain over its lifetime."

    ::= { dpStatusDomainsMemoryStatusEntry 9 }

dpStatusDomainsMemoryStatusDocumentCaches OBJECT-TYPE
    SYNTAX      Unsigned32
    UNITS       "kilobytes"
    MAX-ACCESS  read-only
    STATUS      deprecated
    DESCRIPTION
        "Total memory usage by all document caches in this domain."

    ::= { dpStatusDomainsMemoryStatusEntry 10 }

dpStatusDomainsMemoryStatusStylesheetCaches OBJECT-TYPE
    SYNTAX      Unsigned32
    UNITS       "kilobytes"
    MAX-ACCESS  read-only
    STATUS      deprecated
    DESCRIPTION
        "Total memory usage by all stylesheet caches in this domain."

    ::= { dpStatusDomainsMemoryStatusEntry 11 }

--

dpStatusFailureNotificationStatus2Table OBJECT-TYPE
    SYNTAX      SEQUENCE OF DPStatusFailureNotificationStatus2Entry
    MAX-ACCESS  not-accessible
    STATUS      current
    DESCRIPTION
        "Failure notification maintains a history of recently generated error
        reports. The number of entries maintained depends on the configuration of
        report history kept under failure notification. Status is only available
        when upload report option is enabled."

    ::= { dpStatus 264 }

dpStatusFailureNotificationStatus2Entry OBJECT-TYPE
    SYNTAX      DPStatusFailureNotificationStatus2Entry
    MAX-ACCESS  not-accessible
    STATUS      current
    DESCRIPTION "Table row."
    INDEX { dpStatusFailureNotificationStatus2Date, dpStatusFailureNotificationStatus2Reason, dpStatusFailureNotificationStatus2UploadStatus }

    ::= { dpStatusFailureNotificationStatus2Table 1 }

DPStatusFailureNotificationStatus2Entry ::= SEQUENCE {
    dpStatusFailureNotificationStatus2Date    DisplayString,
    dpStatusFailureNotificationStatus2Reason    INTEGER,
    dpStatusFailureNotificationStatus2UploadStatus    INTEGER,
    dpStatusFailureNotificationStatus2Location    DisplayString
}

dpStatusFailureNotificationStatus2Date OBJECT-TYPE
    SYNTAX      DisplayString
    MAX-ACCESS  read-only
    STATUS      current
    DESCRIPTION
        "Date and time the error report was created, in the format of
        YYYYMMDDHHMMSSMILTMZ where MIL is millisecond and TMZ is timezone."

    ::= { dpStatusFailureNotificationStatus2Entry 1 }

dpStatusFailureNotificationStatus2Reason OBJECT-TYPE
    SYNTAX      INTEGER { 
                        crash(1),
                        watchdog(2),
                        low-memory(3),
                        low-descriptor(4),
                        user-requested(5),
                        on-startup(6),
                        on-shutdown(7),
                        throttle(8),
                        descriptor-error(9),
                        unknown(10)
                }
    MAX-ACCESS  read-only
    STATUS      current
    DESCRIPTION
        "Event that triggered the creation of this error report."

    ::= { dpStatusFailureNotificationStatus2Entry 2 }

dpStatusFailureNotificationStatus2UploadStatus OBJECT-TYPE
    SYNTAX      INTEGER { 
                        success(1),
                        failure(2),
                        in-progress(3)
                }
    MAX-ACCESS  read-only
    STATUS      current
    DESCRIPTION
        "Upload attempted success or failure status."

    ::= { dpStatusFailureNotificationStatus2Entry 3 }

dpStatusFailureNotificationStatus2Location OBJECT-TYPE
    SYNTAX      DisplayString
    MAX-ACCESS  read-only
    STATUS      current
    DESCRIPTION
        "Location the error report was written to."

    ::= { dpStatusFailureNotificationStatus2Entry 4 }

--

dpStatusSystemUsage2TableTable OBJECT-TYPE
    SYNTAX      SEQUENCE OF DPStatusSystemUsage2TableEntry
    MAX-ACCESS  not-accessible
    STATUS      current
    DESCRIPTION
        "Component level system usage."

    ::= { dpStatus 265 }

dpStatusSystemUsage2TableEntry OBJECT-TYPE
    SYNTAX      DPStatusSystemUsage2TableEntry
    MAX-ACCESS  not-accessible
    STATUS      current
    DESCRIPTION "Table row."
    INDEX { dpStatusSystemUsage2TableTaskID, dpStatusSystemUsage2TableTaskName }

    ::= { dpStatusSystemUsage2TableTable 1 }

DPStatusSystemUsage2TableEntry ::= SEQUENCE {
    dpStatusSystemUsage2TableTaskID    Unsigned32,
    dpStatusSystemUsage2TableTaskName    INTEGER,
    dpStatusSystemUsage2TableLoad    Unsigned32,
    dpStatusSystemUsage2TableWorkList    Unsigned32,
    dpStatusSystemUsage2TableCPU    Unsigned32,
    dpStatusSystemUsage2TableMemory    Unsigned32,
    dpStatusSystemUsage2TableFileCount    Unsigned32
}

dpStatusSystemUsage2TableTaskID OBJECT-TYPE
    SYNTAX      Unsigned32
    MAX-ACCESS  read-only
    STATUS      current
    DESCRIPTION
        "Instance of the task."

    ::= { dpStatusSystemUsage2TableEntry 1 }

dpStatusSystemUsage2TableTaskName OBJECT-TYPE
    SYNTAX      INTEGER { 
                        main(1),
                        llm(2),
                        b2bp(3),
                        wtx(4),
                        ssh(5),
                        odbc(6),
                        db2cli(7),
                        secureCloudConnector(8),
                        dco(9),
                        waxhn(10),
                        imscallout(11),
                        jsdebugger(12),
                        nfs(13),
                        isam(14),
                        sgclient(15),
                        sshd(16),
                        quotaEnforcement(17),
                        luna(18),
                        lunaClient(19),
                        launcher(20),
                        apic-gw-service(21),
                        gateway-peering(22)
                }
    MAX-ACCESS  read-only
    STATUS      current
    DESCRIPTION
        "The name of the task or component."

    ::= { dpStatusSystemUsage2TableEntry 2 }

dpStatusSystemUsage2TableLoad OBJECT-TYPE
    SYNTAX      Unsigned32
    UNITS       "%"
    MAX-ACCESS  read-only
    STATUS      current
    DESCRIPTION
        "The percentage of total load for the task during the measurement interval.
        A load above 90 indicates that the task is at or near load capacity. High
        load values are not necessarily indicative of a problem, provided that
        transaction latencies are not affected. Low load values mean that the task
        is looking for work; high load values mean that the task is doing work."

    ::= { dpStatusSystemUsage2TableEntry 3 }

dpStatusSystemUsage2TableWorkList OBJECT-TYPE
    SYNTAX      Unsigned32
    MAX-ACCESS  read-only
    STATUS      current
    DESCRIPTION
        "The number of pending work items including internal communication in the
        queue for processing by the appliance. This number is for internal
        diagnostics and is not intended for purposes of capacity planning."

    ::= { dpStatusSystemUsage2TableEntry 4 }

dpStatusSystemUsage2TableCPU OBJECT-TYPE
    SYNTAX      Unsigned32
    UNITS       "%"
    MAX-ACCESS  read-only
    STATUS      current
    DESCRIPTION
        "The percentage of CPU used by this task."

    ::= { dpStatusSystemUsage2TableEntry 5 }

dpStatusSystemUsage2TableMemory OBJECT-TYPE
    SYNTAX      Unsigned32
    UNITS       "%"
    MAX-ACCESS  read-only
    STATUS      current
    DESCRIPTION
        "The percentage of memory used by this task. This ratio is relative to the
        amount of memory accessible to each task, rather than the memory
        accessible to the appliance as a whole. The cumulative task memory is not
        comparable to the memory usage as reported by the memory usage status
        provider."

    ::= { dpStatusSystemUsage2TableEntry 6 }

dpStatusSystemUsage2TableFileCount OBJECT-TYPE
    SYNTAX      Unsigned32
    MAX-ACCESS  read-only
    STATUS      current
    DESCRIPTION
        "Number of open file handles. The file count increases when the appliance
        accepts new connections, or opens a file for reading. The count decreases
        when this file handle is closed. The file count helps to identify which
        tasks are contributing to high open file counts."

    ::= { dpStatusSystemUsage2TableEntry 7 }

--

dpStatusIPMulticastStatusTable OBJECT-TYPE
    SYNTAX      SEQUENCE OF DPStatusIPMulticastStatusEntry
    MAX-ACCESS  not-accessible
    STATUS      current
    DESCRIPTION
        "Counts of traffic exchange through IP multicast"

    ::= { dpStatus 266 }

dpStatusIPMulticastStatusEntry OBJECT-TYPE
    SYNTAX      DPStatusIPMulticastStatusEntry
    MAX-ACCESS  not-accessible
    STATUS      current
    DESCRIPTION "Table row."
    INDEX { dpConfigIPMulticastIndex, dpStatusIPMulticastStatusSender }

    ::= { dpStatusIPMulticastStatusTable 1 }

DPStatusIPMulticastStatusEntry ::= SEQUENCE {
    dpStatusIPMulticastStatusIPMulticast    DisplayString,
    dpStatusIPMulticastStatusSender    IpAddress,
    dpStatusIPMulticastStatusValid    Counter32,
    dpStatusIPMulticastStatusInvalid    Counter32,
    dpStatusIPMulticastStatusLost    Counter32,
    dpStatusIPMulticastStatusNaksSent    Counter32,
    dpStatusIPMulticastStatusNaksRecv    Counter32
}

dpStatusIPMulticastStatusIPMulticast OBJECT-TYPE
    SYNTAX      DisplayString
    MAX-ACCESS  read-only
    STATUS      current
    DESCRIPTION "No description yet."

    ::= { dpStatusIPMulticastStatusEntry 1 }

dpStatusIPMulticastStatusSender OBJECT-TYPE
    SYNTAX      IpAddress
    MAX-ACCESS  read-only
    STATUS      current
    DESCRIPTION "No description yet."

    ::= { dpStatusIPMulticastStatusEntry 2 }

dpStatusIPMulticastStatusValid OBJECT-TYPE
    SYNTAX      Counter32
    MAX-ACCESS  read-only
    STATUS      current
    DESCRIPTION "No description yet."

    ::= { dpStatusIPMulticastStatusEntry 3 }

dpStatusIPMulticastStatusInvalid OBJECT-TYPE
    SYNTAX      Counter32
    MAX-ACCESS  read-only
    STATUS      current
    DESCRIPTION "No description yet."

    ::= { dpStatusIPMulticastStatusEntry 4 }

dpStatusIPMulticastStatusLost OBJECT-TYPE
    SYNTAX      Counter32
    MAX-ACCESS  read-only
    STATUS      current
    DESCRIPTION "No description yet."

    ::= { dpStatusIPMulticastStatusEntry 5 }

dpStatusIPMulticastStatusNaksSent OBJECT-TYPE
    SYNTAX      Counter32
    MAX-ACCESS  read-only
    STATUS      current
    DESCRIPTION "No description yet."

    ::= { dpStatusIPMulticastStatusEntry 6 }

dpStatusIPMulticastStatusNaksRecv OBJECT-TYPE
    SYNTAX      Counter32
    MAX-ACCESS  read-only
    STATUS      current
    DESCRIPTION "No description yet."

    ::= { dpStatusIPMulticastStatusEntry 7 }

--

dpStatusKerberosTicketsTable OBJECT-TYPE
    SYNTAX      SEQUENCE OF DPStatusKerberosTicketsEntry
    MAX-ACCESS  not-accessible
    STATUS      obsolete
    DESCRIPTION
        "List of cached Kerberos service tickets.
        Note: this is obsoleted and is replaced by dpStatusKerberosTickets2 as of release 6.0.0"

    ::= { dpStatus 267 }

dpStatusKerberosTicketsEntry OBJECT-TYPE
    SYNTAX      DPStatusKerberosTicketsEntry
    MAX-ACCESS  not-accessible
    STATUS      obsolete
    DESCRIPTION "Table row."
    INDEX { dpStatusKerberosTicketsRealm, dpStatusKerberosTicketsClient, IMPLIED dpStatusKerberosTicketsServer }

    ::= { dpStatusKerberosTicketsTable 1 }

DPStatusKerberosTicketsEntry ::= SEQUENCE {
    dpStatusKerberosTicketsRealm    DisplayString,
    dpStatusKerberosTicketsClient    DisplayString,
    dpStatusKerberosTicketsServer    DisplayString,
    dpStatusKerberosTicketsExpirationTime    TimeStamp
}

dpStatusKerberosTicketsRealm OBJECT-TYPE
    SYNTAX      DisplayString
    MAX-ACCESS  read-only
    STATUS      obsolete
    DESCRIPTION
        "Kerberos realm"

    ::= { dpStatusKerberosTicketsEntry 1 }

dpStatusKerberosTicketsClient OBJECT-TYPE
    SYNTAX      DisplayString
    MAX-ACCESS  read-only
    STATUS      obsolete
    DESCRIPTION
        "Kerberos client principal"

    ::= { dpStatusKerberosTicketsEntry 2 }

dpStatusKerberosTicketsServer OBJECT-TYPE
    SYNTAX      DisplayString
    MAX-ACCESS  read-only
    STATUS      obsolete
    DESCRIPTION
        "Kerberos server principal"

    ::= { dpStatusKerberosTicketsEntry 3 }

dpStatusKerberosTicketsExpirationTime OBJECT-TYPE
    SYNTAX      TimeStamp
    MAX-ACCESS  read-only
    STATUS      obsolete
    DESCRIPTION
        "Expiration time"

    ::= { dpStatusKerberosTicketsEntry 4 }

--

dpStatusIPAddressStatusTable OBJECT-TYPE
    SYNTAX      SEQUENCE OF DPStatusIPAddressStatusEntry
    MAX-ACCESS  not-accessible
    STATUS      current
    DESCRIPTION
        "This table provides status about all interfaces on the appliance."

    ::= { dpStatus 268 }

dpStatusIPAddressStatusEntry OBJECT-TYPE
    SYNTAX      DPStatusIPAddressStatusEntry
    MAX-ACCESS  not-accessible
    STATUS      current
    DESCRIPTION "Table row."
    INDEX { dpStatusIPAddressStatusIndex, dpStatusIPAddressStatusPrefixLength, dpStatusIPAddressStatusIP }

    ::= { dpStatusIPAddressStatusTable 1 }

DPStatusIPAddressStatusEntry ::= SEQUENCE {
    dpStatusIPAddressStatusName    DisplayString,
    dpStatusIPAddressStatusIndex    Unsigned32,
    dpStatusIPAddressStatusIPVersion    InetAddressType,
    dpStatusIPAddressStatusPrefixLength    InetAddressPrefixLength,
    dpStatusIPAddressStatusIP    InetAddress
}

dpStatusIPAddressStatusName OBJECT-TYPE
    SYNTAX      DisplayString
    MAX-ACCESS  read-only
    STATUS      current
    DESCRIPTION
        "Indicates the name of the interface in the configuration."

    ::= { dpStatusIPAddressStatusEntry 1 }

dpStatusIPAddressStatusIndex OBJECT-TYPE
    SYNTAX      Unsigned32
    MAX-ACCESS  read-only
    STATUS      current
    DESCRIPTION
        "The value of the SNMP ifIndex column in the ifTable for the interface."

    ::= { dpStatusIPAddressStatusEntry 2 }

dpStatusIPAddressStatusIPVersion OBJECT-TYPE
    SYNTAX      InetAddressType
    MAX-ACCESS  read-only
    STATUS      current
    DESCRIPTION
        "Indicates the version of IP Address for the interface."

    ::= { dpStatusIPAddressStatusEntry 3 }

dpStatusIPAddressStatusPrefixLength OBJECT-TYPE
    SYNTAX      InetAddressPrefixLength
    MAX-ACCESS  read-only
    STATUS      current
    DESCRIPTION
        "Indicates the prefix length for the interface. The prefix length
        represents the configured netmask for the interface."

    ::= { dpStatusIPAddressStatusEntry 4 }

dpStatusIPAddressStatusIP OBJECT-TYPE
    SYNTAX      InetAddress
    MAX-ACCESS  read-only
    STATUS      current
    DESCRIPTION
        "Indicates the IP address for the interface."

    ::= { dpStatusIPAddressStatusEntry 5 }

--

dpStatusSelfBalancedStatus2Table OBJECT-TYPE
    SYNTAX      SEQUENCE OF DPStatusSelfBalancedStatus2Entry
    MAX-ACCESS  not-accessible
    STATUS      current
    DESCRIPTION
        "Status of self-balanced services in standby control groups."

    ::= { dpStatus 269 }

dpStatusSelfBalancedStatus2Entry OBJECT-TYPE
    SYNTAX      DPStatusSelfBalancedStatus2Entry
    MAX-ACCESS  not-accessible
    STATUS      current
    DESCRIPTION "Table row."
    INDEX { dpStatusSelfBalancedStatus2localVIPA, dpStatusSelfBalancedStatus2port, dpStatusSelfBalancedStatus2realServer }

    ::= { dpStatusSelfBalancedStatus2Table 1 }

DPStatusSelfBalancedStatus2Entry ::= SEQUENCE {
    dpStatusSelfBalancedStatus2localVIPA    IpAddress,
    dpStatusSelfBalancedStatus2port    Unsigned32,
    dpStatusSelfBalancedStatus2realServer    IpAddress,
    dpStatusSelfBalancedStatus2targetState    INTEGER,
    dpStatusSelfBalancedStatus2serviceDomain    DisplayString,
    dpStatusSelfBalancedStatus2serviceType    INTEGER,
    dpStatusSelfBalancedStatus2serviceName    DisplayString,
    dpStatusSelfBalancedStatus2weight    Unsigned32,
    dpStatusSelfBalancedStatus2activeconns    Unsigned32,
    dpStatusSelfBalancedStatus2inactiveconns    Unsigned32
}

dpStatusSelfBalancedStatus2localVIPA OBJECT-TYPE
    SYNTAX      IpAddress
    MAX-ACCESS  read-only
    STATUS      current
    DESCRIPTION
        "The Virtual IP address that the service is accepting requests on."

    ::= { dpStatusSelfBalancedStatus2Entry 1 }

dpStatusSelfBalancedStatus2port OBJECT-TYPE
    SYNTAX      Unsigned32 (0..65535)
    MAX-ACCESS  read-only
    STATUS      current
    DESCRIPTION
        "The port that the service is accepting requests on."

    ::= { dpStatusSelfBalancedStatus2Entry 2 }

dpStatusSelfBalancedStatus2realServer OBJECT-TYPE
    SYNTAX      IpAddress
    MAX-ACCESS  read-only
    STATUS      current
    DESCRIPTION
        "The IP Address of the target appliance."

    ::= { dpStatusSelfBalancedStatus2Entry 3 }

dpStatusSelfBalancedStatus2targetState OBJECT-TYPE
    SYNTAX      INTEGER { 
                        active(1),
                        standby(2)
                }
    MAX-ACCESS  read-only
    STATUS      current
    DESCRIPTION
        "The state of the target in the standby control group."

    ::= { dpStatusSelfBalancedStatus2Entry 4 }

dpStatusSelfBalancedStatus2serviceDomain OBJECT-TYPE
    SYNTAX      DisplayString
    MAX-ACCESS  read-only
    STATUS      current
    DESCRIPTION
        "The domain where the service object exists."

    ::= { dpStatusSelfBalancedStatus2Entry 5 }

dpStatusSelfBalancedStatus2serviceType OBJECT-TYPE
    SYNTAX      INTEGER { 
                        configBase(0),
                        dNSNameService(1),
                        ethernetInterface(2),
                        cRLFetch(3),
                        hTTPService(4),
                        statistics(5),
                        traceTarget(6),
                        nTPService(7),
                        throttler(8),
                        stylePolicy(9),
                        hTTPUserAgent(10),
                        tCPProxyService(12),
                        uRLMap(13),
                        uRLRefreshPolicy(14),
                        user(15),
                        networkSettings(16),
                        xMLManager(17),
                        mQQM(18),
                        xSLProxyService(19),
                        mQGW(20),
                        sSLProxyService(21),
                        stylePolicyRule(22),
                        errorReportSettings(23),
                        iPInterface(25),
                        matching(26),
                        systemSettings(27),
                        sNMPSettings(28),
                        rADIUSSettings(29),
                        userGroup(30),
                        shellAlias(31),
                        xSLCoprocService(32),
                        telnetService(33),
                        cryptoSSKey(34),
                        messageMonitor(35),
                        uRLRewritePolicy(36),
                        sSLProxyProfile(37),
                        hTTPProxyService(38),
                        service(39),
                        cryptoFWCred(41),
                        xMLFirewallService(42),
                        cryptoKey(43),
                        cryptoCertificate(44),
                        cryptoIdentCred(45),
                        cryptoValCred(46),
                        cryptoProfile(47),
                        logTarget(48),
                        sSHService(49),
                        crypto(50),
                        webGUI(51),
                        eventlog(52),
                        accessControl(53),
                        messageFlowControl(54),
                        mQConfiguration(55),
                        deviceSettings(56),
                        deviceManagementService(57),
                        networkConfiguration(58),
                        logLabel(59),
                        mgmtInterface(60),
                        messageMatching(61),
                        messageType(62),
                        countMonitor(63),
                        durationMonitor(64),
                        filterAction(65),
                        hTTPInputConversionMap(66),
                        compileOptionsPolicy(68),
                        xPathRoutingMap(69),
                        schemaExceptionMap(70),
                        reserved71(71),
                        documentCryptoMap(72),
                        tAM(73),
                        domain(74),
                        timeSettings(75),
                        dynamicXMLContentMap(77),
                        dynamicStylesheet(78),
                        dynamicSchema(79),
                        accessControlList(80),
                        importPackage(81),
                        mQhost(82),
                        mQproxy(83),
                        loadBalancerGroup(84),
                        rBMSettings(85),
                        includeConfig(86),
                        certMonitor(87),
                        hostAlias(88),
                        aAAPolicy(91),
                        stylePolicyAction(92),
                        cryptoKerberosKDC(93),
                        webServiceMonitor(94),
                        wSGateway(95),
                        stylePolicyRuleBase(96),
                        wSStylePolicyRule(97),
                        wSStylePolicy(98),
                        webServicesAgent(99),
                        gatewayBase(100),
                        multiProtocolGateway(101),
                        sourceProtocolHandler(102),
                        hTTPSourceProtocolHandler(103),
                        hTTPSSourceProtocolHandler(104),
                        mQSourceProtocolHandler(105),
                        xTCProtocolHandler(106),
                        cryptoKerberosKeytab(109),
                        statelessTCPSourceProtocolHandler(110),
                        sLMCredClass(111),
                        sLMRsrcClass(112),
                        sLMSchedule(113),
                        sLMAction(114),
                        sLMPolicy(115),
                        peerGroup(116),
                        reserved117(117),
                        tFIMEndpoint(118),
                        xmltrace(120),
                        nFSClientSettings(121),
                        wSEndpointRewritePolicy(122),
                        sQLDataSource(124),
                        nFSStaticMount(125),
                        nFSDynamicMounts(126),
                        webAppErrorHandlingPolicy(127),
                        simpleCountMonitor(128),
                        nameValueProfile(129),
                        webAppResponse(130),
                        webAppRequest(131),
                        webAppFW(132),
                        appSecurityPolicy(133),
                        uDDIRegistry(134),
                        webAppSessionPolicy(135),
                        jMSServer(136),
                        tibcoEMSServer(137),
                        tibcoEMSSourceProtocolHandler(138),
                        xACMLPDP(139),
                        jMSSourceProtocolHandler(140),
                        webSphereJMSServer(141),
                        webSphereJMSSourceProtocolHandler(142),
                        processingMetadata(143),
                        mTOMPolicy(144),
                        fTPServerSourceProtocolHandler(145),
                        filePollerSourceProtocolHandler(146),
                        nFSFilePollerSourceProtocolHandler(147),
                        fTPFilePollerSourceProtocolHandler(148),
                        fTPQuoteCommands(149),
                        mQQMBase(150),
                        mQQMGroup(151),
                        wSRRServer(152),
                        wSRRSubscription(153),
                        webServiceSubscription(154),
                        uDDISubscription(155),
                        vLANInterface(156),
                        conformancePolicy(157),
                        sOAPHeaderDisposition(158),
                        policyAttachments(159),
                        policyParameters(160),
                        iMSConnect(161),
                        iMSConnectSourceProtocolHandler(162),
                        lDAPSearchParameters(163),
                        configDeploymentPolicy(164),
                        compactFlash(165),
                        raidVolume(166),
                        iScsiInitiatorConfig(167),
                        lLMSourceProtocolHandler(168),
                        tRVSourceProtocolHandler(169),
                        iScsiHBAConfig(170),
                        iScsiTargetConfig(171),
                        iScsiVolumeConfig(172),
                        iScsiChapConfig(173),
                        zosNSSClient(174),
                        sSHServerSourceProtocolHandler(175),
                        fTPDemonSourceProtocolHandler(176),
                        aS3SourceProtocolHandler(177),
                        aS2SourceProtocolHandler(178),
                        b2BXPathRoutingPolicy(179),
                        lLMInstance(180),
                        lLMMulticastReceive(181),
                        lLMMulticastTransmit(182),
                        lLMUnicast(183),
                        lLMMulticastTierGroup(184),
                        lLMRoute(186),
                        lLMPolicy(187),
                        fibreChannelHBA(188),
                        fibreChannelTarget(189),
                        fibreChannelVolume(190),
                        webB2BViewer(192),
                        b2BPersistence(193),
                        b2BProfileGroup(194),
                        b2BGateway(195),
                        b2BProfile(196),
                        wCCService(197),
                        formsLoginPolicy(198),
                        tRVPolicy(199),
                        tRVRoute(200),
                        tRVTransport(201),
                        lLMPolicyBase(202),
                        lLMRouteBase(203),
                        pOPPollerSourceProtocolHandlerBase(204),
                        aS1PollerSourceProtocolHandler(205),
                        pOPPollerSourceProtocolHandler(206),
                        sMTPServerConnection(207),
                        xM70Persistence(208),
                        wSRRSavedSearchSubscription(209),
                        eBMS2SourceProtocolHandler(210),
                        sAMLAttributes(211),
                        sSHClientProfile(212),
                        sFTPFilePollerSourceProtocolHandler(213),
                        zHybridTargetControlService(214),
                        multipathService(215),
                        clusterService(216),
                        secureCloudConnector(217),
                        iPMILanChannel(218),
                        iPMIUser(219),
                        b2BCPACollaboration(220),
                        mQFTESourceProtocolHandler(221),
                        b2BCPA(222),
                        b2BCPASenderSetting(223),
                        b2BCPAReceiverSetting(224),
                        oAuthSupportedClient(225),
                        oAuthSupportedClientGroup(226),
                        sSLSNIServerProfile(227),
                        xC10Grid(235),
                        runtimeSettings(246),
                        sQLRuntimeSettings(247),
                        webApplicationGateway(248),
                        interopService(249),
                        oDRConnectorGroup(250),
                        oDR(251),
                        sSLClientProfile(253),
                        sSLServerProfile(254),
                        sSLSNIMapping(256),
                        webTokenService(266),
                        messageContentFilters(267),
                        mCFBase(268),
                        mCFHttpHeader(269),
                        mCFXPath(270),
                        mCFHttpURL(271),
                        mCFHttpMethod(272),
                        iMSCalloutSourceProtocolHandler(273),
                        pattern(274),
                        mCFCustomRule(275),
                        aS2ProxySourceProtocolHandler(277),
                        luna(278),
                        lunaPartition(279),
                        configSequence(280),
                        lunaHAGroup(285),
                        lunaHASettings(286),
                        wAXHNProxy(300),
                        hNApplication(301),
                        cloudGatewayService(302),
                        cloudConnectorService(303),
                        jSONSettings(308),
                        iPMulticast(309),
                        deploymentPolicyParametersBinding(310),
                        lDAPConnectionPool(311),
                        mPGWErrorHandlingPolicy(312),
                        mPGWErrorAction(313),
                        language(314),
                        domainAvailability(315),
                        generatedPolicy(316),
                        passwordMap(320),
                        aAAJWTValidator(321),
                        aAAJWTGenerator(322),
                        linkAggregation(333),
                        cookieAttributePolicy(334),
                        iSAMReverseProxy(335),
                        iSAMReverseProxyJunction(336),
                        iSAMRuntime(337),
                        passwordAlias(338),
                        auditLog(340),
                        jWERecipient(345),
                        jOSESignatureIdentifier(346),
                        jWSSignature(347),
                        jWEHeader(348),
                        jOSERecipientIdentifier(349),
                        secureGatewayClient(350),
                        cacheGrid(351),
                        wXSGrid(352),
                        domainSettings(353),
                        mQAUI(354),
                        gWScriptSettings(358),
                        aPICollection(359),
                        aPIGateway(360),
                        aPIDefinition(361),
                        aPIPath(362),
                        aPIOperation(363),
                        aPIPlan(364),
                        aPISecurityDefinition(365),
                        aPISecurityAPIKey(366),
                        aPISecurityOAuth(368),
                        aPISecurityRequirement(369),
                        controlList(370),
                        aPILDAPRegistry(371),
                        aPIRule(372),
                        aPISecurityOAuthReq(373),
                        gWSRemoteDebug(374),
                        mQAUIMFT(375),
                        assemblyActionUserSecurity(376),
                        aPISecurityBasicAuth(377),
                        aPISchema(378),
                        aPIUserRegistry(379),
                        aPIAuthURLRegistry(380),
                        assemblyActionClientSecurity(381),
                        restMgmtInterface(400),
                        secureBackupMode(402),
                        aPIConnectGatewayService(403),
                        standaloneStandbyControlInterface(450),
                        standaloneStandbyControl(451),
                        tenant(452),
                        socialLoginPolicy(455),
                        eBMS3SourceProtocolHandler(456),
                        dFDLSettings(460),
                        parseSettings(461),
                        accessProfile(462),
                        iLMTScanner(500),
                        quotaEnforcementServer(504),
                        sSHServerProfile(505),
                        quotaEnforcementMatchClass(506),
                        quotaEnforcementGroupClass(507),
                        quotaEnforcementAlgorithm(508),
                        quotaEnforcementSchedule(509),
                        sSHDomainClientProfile(510),
                        quotaEnforcementPolicyGroup(511),
                        quotaEnforcementPolicyBase(512),
                        quotaEnforcementAction(513),
                        quotaEnforcementPolicy(514),
                        gatewayPeering(526),
                        stylePolicyActionBase(600),
                        assemblyActionBase(601),
                        assemblyAction(602),
                        assemblyLogic(603),
                        aPIExecute(605),
                        aPIResult(607),
                        assemblyLogicSwitch(609),
                        assembly(610),
                        assemblyActionInvoke(611),
                        assemblyActionSetVar(612),
                        assemblyActionThrow(613),
                        aPIRouting(614),
                        aPISecurity(615),
                        aPIRateLimit(616),
                        assemblyActionXml2Json(617),
                        aPIAction(618),
                        assemblyActionXSLT(619),
                        assemblyActionGatewayScript(620),
                        aPIClientIdentification(621),
                        assemblyActionMap(622),
                        assemblyActionJWTValidate(623),
                        assemblyActionParse(624),
                        aPICORS(625),
                        operationRateLimit(626),
                        analyticsEndpoint(627),
                        assemblyActionJWTGenerate(628),
                        assemblyActionJson2Xml(629),
                        assemblyActionOAuth(630),
                        oAuthProviderSettings(640),
                        aPISecurityTokenManager(641),
                        assemblyActionValidate(642),
                        aPIDebugProbe(643),
                        aPIApplicationType(644),
                        assemblyFunction(645),
                        assemblyActionFunctionCall(646),
                        gatewayPeeringManager(648),
                        assemblyActionLog(649),
                        assemblyActionRateLimit(650),
                        assemblyActionRedact(651),
                        productInsights(850)
                }
    MAX-ACCESS  read-only
    STATUS      current
    DESCRIPTION
        "The type of the service object."

    ::= { dpStatusSelfBalancedStatus2Entry 6 }

dpStatusSelfBalancedStatus2serviceName OBJECT-TYPE
    SYNTAX      DisplayString
    MAX-ACCESS  read-only
    STATUS      current
    DESCRIPTION
        "The name of the service object."

    ::= { dpStatusSelfBalancedStatus2Entry 7 }

dpStatusSelfBalancedStatus2weight OBJECT-TYPE
    SYNTAX      Unsigned32 (0..65535)
    MAX-ACCESS  read-only
    STATUS      current
    DESCRIPTION
        "The weight (processing capabilities) of this target. The processing
        capabilities of each appliance are used in the connection distribution
        decisions by the active member of the standby group. For standby members
        in the standby group, this value is always 0."

    ::= { dpStatusSelfBalancedStatus2Entry 8 }

dpStatusSelfBalancedStatus2activeconns OBJECT-TYPE
    SYNTAX      Unsigned32
    MAX-ACCESS  read-only
    STATUS      current
    DESCRIPTION
        "The number of connections in a TCP ESTABLISHED state to this target. This
        information is available for only the active member of the standby group.
        The actual number can differ because self balancing is not the endpoint
        for TCP connections."

    ::= { dpStatusSelfBalancedStatus2Entry 9 }

dpStatusSelfBalancedStatus2inactiveconns OBJECT-TYPE
    SYNTAX      Unsigned32
    MAX-ACCESS  read-only
    STATUS      current
    DESCRIPTION
        "Indicates the number of connections of established, idle connection to
        this target. This number includes previously active connections that are
        closed but not yet timed out. Depending on the number of connections per
        second that were received and the connection timeout, there might be many
        inactive connections. This information is available for only the active
        member of the standby group. The actual number can differ from the
        connections in the TCP TIME_WAIT state because self balancing is not the
        endpoint for TCP connections."

    ::= { dpStatusSelfBalancedStatus2Entry 10 }

dpStatusHypervisor OBJECT IDENTIFIER ::= { dpStatus 270 }

dpStatusHypervisorEdition OBJECT-TYPE
    SYNTAX      INTEGER { 
                        production(1),
                        nonproduction(2),
                        developers(3),
                        developers-limited(4)
                }
    MAX-ACCESS  read-only
    STATUS      deprecated
    DESCRIPTION
        "Shows whether this virtual appliance is Production Edition, Non-Production
        Edition, or Developers Edition."

    ::= { dpStatusHypervisor 1 }

dpStatusHypervisorHypervisor OBJECT-TYPE
    SYNTAX      DisplayString
    MAX-ACCESS  read-only
    STATUS      deprecated
    DESCRIPTION
        "The hypervisor that this virtual appliance is running on. This information
        is provided by the hypervisor in the DMI information."

    ::= { dpStatusHypervisor 2 }

dpStatusHypervisorVirtualCPUs OBJECT-TYPE
    SYNTAX      Unsigned32
    MAX-ACCESS  read-only
    STATUS      deprecated
    DESCRIPTION
        "The number of virtual CPUs that are emulated by the hypervisor."

    ::= { dpStatusHypervisor 3 }

dpStatusHypervisorMemory OBJECT-TYPE
    SYNTAX      Unsigned32
    UNITS       "Gigabytes"
    MAX-ACCESS  read-only
    STATUS      deprecated
    DESCRIPTION
        "The amount of virtual memory that is emulated by the hypervisor."

    ::= { dpStatusHypervisor 4 }

dpStatusHypervisorUUID OBJECT-TYPE
    SYNTAX      DisplayString
    MAX-ACCESS  read-only
    STATUS      deprecated
    DESCRIPTION
        "The UUID of this virtual appliance that is assigned by the hypervisor.
        This information is provided by the hypervisor in the DMI information."

    ::= { dpStatusHypervisor 5 }

--

dpStatusKerberosTickets2Table OBJECT-TYPE
    SYNTAX      SEQUENCE OF DPStatusKerberosTickets2Entry
    MAX-ACCESS  not-accessible
    STATUS      current
    DESCRIPTION
        "List of cached Kerberos tickets.
        Note: this obsoletes dpStatusKerberosTickets"

    ::= { dpStatus 271 }

dpStatusKerberosTickets2Entry OBJECT-TYPE
    SYNTAX      DPStatusKerberosTickets2Entry
    MAX-ACCESS  not-accessible
    STATUS      current
    DESCRIPTION "Table row."
    INDEX { dpStatusKerberosTickets2Realm, dpStatusKerberosTickets2Owner, dpStatusKerberosTickets2Client, IMPLIED dpStatusKerberosTickets2Server }

    ::= { dpStatusKerberosTickets2Table 1 }

DPStatusKerberosTickets2Entry ::= SEQUENCE {
    dpStatusKerberosTickets2Realm    DisplayString,
    dpStatusKerberosTickets2Owner    DisplayString,
    dpStatusKerberosTickets2Client    DisplayString,
    dpStatusKerberosTickets2Server    DisplayString,
    dpStatusKerberosTickets2ExpirationTime    TimeStamp,
    dpStatusKerberosTickets2Flags    BITS
}

dpStatusKerberosTickets2Realm OBJECT-TYPE
    SYNTAX      DisplayString
    MAX-ACCESS  read-only
    STATUS      current
    DESCRIPTION
        "Identifies the Kerberos realm in the ticket."

    ::= { dpStatusKerberosTickets2Entry 1 }

dpStatusKerberosTickets2Owner OBJECT-TYPE
    SYNTAX      DisplayString
    MAX-ACCESS  read-only
    STATUS      current
    DESCRIPTION
        "Identifies the Kerberos principal that owns the ticket."

    ::= { dpStatusKerberosTickets2Entry 2 }

dpStatusKerberosTickets2Client OBJECT-TYPE
    SYNTAX      DisplayString
    MAX-ACCESS  read-only
    STATUS      current
    DESCRIPTION
        "Identifies the Kerberos client principal in the ticket."

    ::= { dpStatusKerberosTickets2Entry 3 }

dpStatusKerberosTickets2Server OBJECT-TYPE
    SYNTAX      DisplayString
    MAX-ACCESS  read-only
    STATUS      current
    DESCRIPTION
        "Identifies the Kerberos server principal in the ticket."

    ::= { dpStatusKerberosTickets2Entry 4 }

dpStatusKerberosTickets2ExpirationTime OBJECT-TYPE
    SYNTAX      TimeStamp
    MAX-ACCESS  read-only
    STATUS      current
    DESCRIPTION
        "Identifies when the ticket expires."

    ::= { dpStatusKerberosTickets2Entry 5 }

dpStatusKerberosTickets2Flags OBJECT-TYPE
    SYNTAX      BITS { 
                        ok-as-delegate(18),
                        transited-policy-checked(19),
                        hw-authent(20),
                        pre-authent(21),
                        initial(22),
                        renewable(23),
                        invalid(24),
                        postdated(25),
                        may-postdate(26),
                        proxy(27),
                        proxiable(28),
                        forwarded(29),
                        forwardable(30),
                        reserved(31)
                }
    MAX-ACCESS  read-only
    STATUS      current
    DESCRIPTION
        "Identifies the Kerberos flags in the ticket."

    ::= { dpStatusKerberosTickets2Entry 6 }

--

dpStatusOAuthCachesStatusTable OBJECT-TYPE
    SYNTAX      SEQUENCE OF DPStatusOAuthCachesStatusEntry
    MAX-ACCESS  not-accessible
    STATUS      current
    DESCRIPTION
        "List of OAuth cache tickets."

    ::= { dpStatus 272 }

dpStatusOAuthCachesStatusEntry OBJECT-TYPE
    SYNTAX      DPStatusOAuthCachesStatusEntry
    MAX-ACCESS  not-accessible
    STATUS      current
    DESCRIPTION "Table row."
    INDEX { dpStatusOAuthCachesStatusClientId, dpStatusOAuthCachesStatusCacheType }

    ::= { dpStatusOAuthCachesStatusTable 1 }

DPStatusOAuthCachesStatusEntry ::= SEQUENCE {
    dpStatusOAuthCachesStatusClientId    DisplayString,
    dpStatusOAuthCachesStatusCacheType    INTEGER,
    dpStatusOAuthCachesStatusLastPruned    TimeStamp,
    dpStatusOAuthCachesStatusCount    Gauge32
}

dpStatusOAuthCachesStatusClientId OBJECT-TYPE
    SYNTAX      DisplayString
    MAX-ACCESS  read-only
    STATUS      current
    DESCRIPTION
        "The client ID of the OAuth client."

    ::= { dpStatusOAuthCachesStatusEntry 1 }

dpStatusOAuthCachesStatusCacheType OBJECT-TYPE
    SYNTAX      INTEGER { 
                        dpstate(1),
                        azcode(2),
                        access(3),
                        refresh(4)
                }
    MAX-ACCESS  read-only
    STATUS      current
    DESCRIPTION
        "The type of cache that the appliance deletes."

    ::= { dpStatusOAuthCachesStatusEntry 2 }

dpStatusOAuthCachesStatusLastPruned OBJECT-TYPE
    SYNTAX      TimeStamp
    MAX-ACCESS  read-only
    STATUS      current
    DESCRIPTION
        "The time when the appliance last deletes the expired entries."

    ::= { dpStatusOAuthCachesStatusEntry 3 }

dpStatusOAuthCachesStatusCount OBJECT-TYPE
    SYNTAX      Gauge32
    MAX-ACCESS  read-only
    STATUS      current
    DESCRIPTION
        "The number of entries in the cache."

    ::= { dpStatusOAuthCachesStatusEntry 4 }

dpStatusCryptoModeStatus OBJECT IDENTIFIER ::= { dpStatus 273 }

dpStatusCryptoModeStatusTargetMode OBJECT-TYPE
    SYNTAX      INTEGER { 
                        permissive(1),
                        fips-140-2-l1(2)
                }
    MAX-ACCESS  read-only
    STATUS      current
    DESCRIPTION
        "Indicates the cryptographic mode that the firmware is expected to be
        running in currently. This is the mode that is requested in the previous
        run of the firmware and this mode is expected to take effect at the
        previous firmware reload."

    ::= { dpStatusCryptoModeStatus 1 }

dpStatusCryptoModeStatusActualMode OBJECT-TYPE
    SYNTAX      INTEGER { 
                        permissive(1),
                        fips-140-2-l1(2)
                }
    MAX-ACCESS  read-only
    STATUS      current
    DESCRIPTION
        "Indicates the cryptographic mode that the firmware is actually running in.
        The current mode should be equivalent to the target mode unless a problem
        occurred during the previous firmware reload."

    ::= { dpStatusCryptoModeStatus 2 }

dpStatusCryptoModeStatusPendingTargetMode OBJECT-TYPE
    SYNTAX      INTEGER { 
                        permissive(1),
                        fips-140-2-l1(2)
                }
    MAX-ACCESS  read-only
    STATUS      current
    DESCRIPTION
        "Indicates the cryptographic mode that the firmware is expected to run in
        after the next firmware reload."

    ::= { dpStatusCryptoModeStatus 3 }

dpStatusCryptoHwDisableStatus OBJECT IDENTIFIER ::= { dpStatus 274 }

dpStatusCryptoHwDisableStatusTargetDisableAmount OBJECT-TYPE
    SYNTAX      INTEGER { 
                        none(1),
                        all(2),
                        rsa(3)
                }
    MAX-ACCESS  read-only
    STATUS      current
    DESCRIPTION
        "Indicates the aspects of the cryptographic hardware that are expected to
        be currently disabled after the previous firmware reload."

    ::= { dpStatusCryptoHwDisableStatus 1 }

dpStatusCryptoHwDisableStatusActualDisableAmount OBJECT-TYPE
    SYNTAX      INTEGER { 
                        none(1),
                        all(2),
                        rsa(3)
                }
    MAX-ACCESS  read-only
    STATUS      current
    DESCRIPTION
        "Indicates the aspects of the cryptographic hardware that are actually
        disabled now. Current disablement mode should be equivalent to the target
        disablement mode unless a problem occurred during the previous firmware
        reload."

    ::= { dpStatusCryptoHwDisableStatus 2 }

dpStatusCryptoHwDisableStatusPendingTargetDisableAmount OBJECT-TYPE
    SYNTAX      INTEGER { 
                        none(1),
                        all(2),
                        rsa(3)
                }
    MAX-ACCESS  read-only
    STATUS      current
    DESCRIPTION
        "Indicates the aspects of the cryptographic hardware that are expected to
        be disabled after the next firmware reload."

    ::= { dpStatusCryptoHwDisableStatus 3 }

--

dpStatusRoutingStatus3Table OBJECT-TYPE
    SYNTAX      SEQUENCE OF DPStatusRoutingStatus3Entry
    MAX-ACCESS  not-accessible
    STATUS      current
    DESCRIPTION
        "This table describes the IP routes on the appliance. The table includes
        static and default routes from interface configuration and dynamic routes
        from discovery protocols."

    ::= { dpStatus 275 }

dpStatusRoutingStatus3Entry OBJECT-TYPE
    SYNTAX      DPStatusRoutingStatus3Entry
    MAX-ACCESS  not-accessible
    STATUS      current
    DESCRIPTION "Table row."
    INDEX { dpStatusRoutingStatus3IPType, dpStatusRoutingStatus3Destination, dpStatusRoutingStatus3PrefixLength, dpStatusRoutingStatus3InterfaceType, dpStatusRoutingStatus3MacInterface, dpStatusRoutingStatus3GatewayIPType, dpStatusRoutingStatus3Gateway, dpStatusRoutingStatus3Metric }

    ::= { dpStatusRoutingStatus3Table 1 }

DPStatusRoutingStatus3Entry ::= SEQUENCE {
    dpStatusRoutingStatus3IPType    InetAddressType,
    dpStatusRoutingStatus3Destination    InetAddress,
    dpStatusRoutingStatus3PrefixLength    InetAddressPrefixLength,
    dpStatusRoutingStatus3InterfaceType    INTEGER,
    dpStatusRoutingStatus3MacInterface    DisplayString,
    dpStatusRoutingStatus3GatewayIPType    InetAddressType,
    dpStatusRoutingStatus3Gateway    InetAddress,
    dpStatusRoutingStatus3Metric    Unsigned32
}

dpStatusRoutingStatus3IPType OBJECT-TYPE
    SYNTAX      InetAddressType
    MAX-ACCESS  read-only
    STATUS      current
    DESCRIPTION
        "The version of the IP address: ipv4 or ipv6."

    ::= { dpStatusRoutingStatus3Entry 1 }

dpStatusRoutingStatus3Destination OBJECT-TYPE
    SYNTAX      InetAddress
    MAX-ACCESS  read-only
    STATUS      current
    DESCRIPTION
        "The IP subnet or aggregate that is the destination of the route."

    ::= { dpStatusRoutingStatus3Entry 2 }

dpStatusRoutingStatus3PrefixLength OBJECT-TYPE
    SYNTAX      InetAddressPrefixLength
    MAX-ACCESS  read-only
    STATUS      current
    DESCRIPTION
        "The prefix length of the IP address that represents the configured
        netmask."

    ::= { dpStatusRoutingStatus3Entry 3 }

dpStatusRoutingStatus3InterfaceType OBJECT-TYPE
    SYNTAX      INTEGER { 
                        other(1),
                        ethernet(6),
                        tunnel(131),
                        vLAN(135),
                        aggregate(161)
                }
    MAX-ACCESS  read-only
    STATUS      current
    DESCRIPTION
        "The type of device interface used for this route. For example, Ethernet
        indicates that the interface is on the base Ethernet MAC interface and
        VLAN indicates that the interface is on an IEEE 802.1Q VLAN on top of the
        base Ethernet MAC interface."

    ::= { dpStatusRoutingStatus3Entry 4 }

dpStatusRoutingStatus3MacInterface OBJECT-TYPE
    SYNTAX      DisplayString
    MAX-ACCESS  read-only
    STATUS      current
    DESCRIPTION
        "The configured name of the interface for the route."

    ::= { dpStatusRoutingStatus3Entry 5 }

dpStatusRoutingStatus3GatewayIPType OBJECT-TYPE
    SYNTAX      InetAddressType
    MAX-ACCESS  read-only
    STATUS      current
    DESCRIPTION
        "The IP address version that corresponds to the next hop gateway: ipv4 or
        ipv6."

    ::= { dpStatusRoutingStatus3Entry 6 }

dpStatusRoutingStatus3Gateway OBJECT-TYPE
    SYNTAX      InetAddress
    MAX-ACCESS  read-only
    STATUS      current
    DESCRIPTION
        "The next hop gateway for traffic that uses the route. For routes with a
        local route type, the value i 0.0.0.0 for IPv4 and :: for IPv6."

    ::= { dpStatusRoutingStatus3Entry 7 }

dpStatusRoutingStatus3Metric OBJECT-TYPE
    SYNTAX      Unsigned32
    MAX-ACCESS  read-only
    STATUS      current
    DESCRIPTION
        "The metric for the route. When the same destination has multiple routes,
        the route with the lowest metric is used."

    ::= { dpStatusRoutingStatus3Entry 8 }

--

dpStatusLinkAggregationMemberStatusTable OBJECT-TYPE
    SYNTAX      SEQUENCE OF DPStatusLinkAggregationMemberStatusEntry
    MAX-ACCESS  not-accessible
    STATUS      current
    DESCRIPTION
        "This table provides a mapping of links to aggregates on the system."

    ::= { dpStatus 277 }

dpStatusLinkAggregationMemberStatusEntry OBJECT-TYPE
    SYNTAX      DPStatusLinkAggregationMemberStatusEntry
    MAX-ACCESS  not-accessible
    STATUS      current
    DESCRIPTION "Table row."
    INDEX { dpStatusLinkAggregationMemberStatusAggregateIndex, dpStatusLinkAggregationMemberStatusMemberIndex }

    ::= { dpStatusLinkAggregationMemberStatusTable 1 }

DPStatusLinkAggregationMemberStatusEntry ::= SEQUENCE {
    dpStatusLinkAggregationMemberStatusAggregateIndex    Unsigned32,
    dpStatusLinkAggregationMemberStatusAggregateName    DisplayString,
    dpStatusLinkAggregationMemberStatusMgmtName    DisplayString,
    dpStatusLinkAggregationMemberStatusMemberIndex    Unsigned32,
    dpStatusLinkAggregationMemberStatusMemberName    DisplayString,
    dpStatusLinkAggregationMemberStatusAggregatorID    Unsigned32
}

dpStatusLinkAggregationMemberStatusAggregateIndex OBJECT-TYPE
    SYNTAX      Unsigned32
    MAX-ACCESS  read-only
    STATUS      current
    DESCRIPTION
        "The index that identifies the link aggregation."

    ::= { dpStatusLinkAggregationMemberStatusEntry 1 }

dpStatusLinkAggregationMemberStatusAggregateName OBJECT-TYPE
    SYNTAX      DisplayString
    MAX-ACCESS  read-only
    STATUS      current
    DESCRIPTION
        "Indicates the name of the inteface in the system kernel."

    ::= { dpStatusLinkAggregationMemberStatusEntry 2 }

dpStatusLinkAggregationMemberStatusMgmtName OBJECT-TYPE
    SYNTAX      DisplayString
    MAX-ACCESS  read-only
    STATUS      current
    DESCRIPTION
        "Indicates the name of the interface in the configuration."

    ::= { dpStatusLinkAggregationMemberStatusEntry 3 }

dpStatusLinkAggregationMemberStatusMemberIndex OBJECT-TYPE
    SYNTAX      Unsigned32
    MAX-ACCESS  read-only
    STATUS      current
    DESCRIPTION
        "The index that identifies the member interface."

    ::= { dpStatusLinkAggregationMemberStatusEntry 4 }

dpStatusLinkAggregationMemberStatusMemberName OBJECT-TYPE
    SYNTAX      DisplayString
    MAX-ACCESS  read-only
    STATUS      current
    DESCRIPTION
        "The system name of the member interface."

    ::= { dpStatusLinkAggregationMemberStatusEntry 5 }

dpStatusLinkAggregationMemberStatusAggregatorID OBJECT-TYPE
    SYNTAX      Unsigned32
    MAX-ACCESS  read-only
    STATUS      current
    DESCRIPTION
        "Aggregator ID assigned to the interface."

    ::= { dpStatusLinkAggregationMemberStatusEntry 6 }

--

dpStatusLinkStatusTable OBJECT-TYPE
    SYNTAX      SEQUENCE OF DPStatusLinkStatusEntry
    MAX-ACCESS  not-accessible
    STATUS      current
    DESCRIPTION
        "This table provides status for all interfaces on the appliance."

    ::= { dpStatus 278 }

dpStatusLinkStatusEntry OBJECT-TYPE
    SYNTAX      DPStatusLinkStatusEntry
    MAX-ACCESS  not-accessible
    STATUS      current
    DESCRIPTION "Table row."
    INDEX { dpStatusLinkStatusName, dpStatusLinkStatusIndex }

    ::= { dpStatusLinkStatusTable 1 }

DPStatusLinkStatusEntry ::= SEQUENCE {
    dpStatusLinkStatusName    DisplayString,
    dpStatusLinkStatusIndex    Unsigned32,
    dpStatusLinkStatusStatus    INTEGER,
    dpStatusLinkStatusMode    INTEGER,
    dpStatusLinkStatusType    INTEGER,
    dpStatusLinkStatusMTU    Unsigned32,
    dpStatusLinkStatusAggregate    DisplayString,
    dpStatusLinkStatusLinkAddress    MacAddress
}

dpStatusLinkStatusName OBJECT-TYPE
    SYNTAX      DisplayString
    MAX-ACCESS  read-only
    STATUS      current
    DESCRIPTION
        "Indicates the name of the interface in the configuration."

    ::= { dpStatusLinkStatusEntry 1 }

dpStatusLinkStatusIndex OBJECT-TYPE
    SYNTAX      Unsigned32
    MAX-ACCESS  read-only
    STATUS      current
    DESCRIPTION
        "Identifies the ifIndex for the interface."

    ::= { dpStatusLinkStatusEntry 2 }

dpStatusLinkStatusStatus OBJECT-TYPE
    SYNTAX      INTEGER { 
                        ok(1),
                        no-link(2)
                }
    MAX-ACCESS  read-only
    STATUS      current
    DESCRIPTION
        "Identifies the current link state for the interface."

    ::= { dpStatusLinkStatusEntry 3 }

dpStatusLinkStatusMode OBJECT-TYPE
    SYNTAX      INTEGER { 
                        dr10BASE-T-HD(0),
                        dr10BASE-T-FD(256),
                        dr100BASE-TX-HD(8192),
                        dr100BASE-TX-FD(8448),
                        dr1000BASE-T-FD(65535),
                        dr1000BASE-KX(65536),
                        dr10GBASE-KX4(131072),
                        dr40GBASE-CR4(262144),
                        none(524288)
                }
    MAX-ACCESS  read-only
    STATUS      current
    DESCRIPTION
        "Identifies the actual fixed, configured, or negotiated Ethernet PHY mode,
        including speed and duplex."

    ::= { dpStatusLinkStatusEntry 4 }

dpStatusLinkStatusType OBJECT-TYPE
    SYNTAX      INTEGER { 
                        other(1),
                        ethernet(6),
                        tunnel(131),
                        vLAN(135),
                        aggregate(161)
                }
    MAX-ACCESS  read-only
    STATUS      current
    DESCRIPTION
        "Indicates the type of interface: Ethernet, VLAN, Tunnel, or Other."

    ::= { dpStatusLinkStatusEntry 5 }

dpStatusLinkStatusMTU OBJECT-TYPE
    SYNTAX      Unsigned32
    MAX-ACCESS  read-only
    STATUS      current
    DESCRIPTION
        "Identifies the maximum transmission unit (MTU) for the interface."

    ::= { dpStatusLinkStatusEntry 6 }

dpStatusLinkStatusAggregate OBJECT-TYPE
    SYNTAX      DisplayString
    MAX-ACCESS  read-only
    STATUS      current
    DESCRIPTION
        "Indicates the associated aggregate interface, if any."

    ::= { dpStatusLinkStatusEntry 7 }

dpStatusLinkStatusLinkAddress OBJECT-TYPE
    SYNTAX      MacAddress
    MAX-ACCESS  read-only
    STATUS      current
    DESCRIPTION
        "Identifies the physical IP address for the interface. The default value
        for Ethernet interfaces is programmed in the Ethernet hardware."

    ::= { dpStatusLinkStatusEntry 8 }

--

dpStatusLinkAggregationStatusTable OBJECT-TYPE
    SYNTAX      SEQUENCE OF DPStatusLinkAggregationStatusEntry
    MAX-ACCESS  not-accessible
    STATUS      current
    DESCRIPTION
        "This table provides statistics for aggregate interfaces."

    ::= { dpStatus 279 }

dpStatusLinkAggregationStatusEntry OBJECT-TYPE
    SYNTAX      DPStatusLinkAggregationStatusEntry
    MAX-ACCESS  not-accessible
    STATUS      current
    DESCRIPTION "Table row."
    INDEX { dpStatusLinkAggregationStatusIndex }

    ::= { dpStatusLinkAggregationStatusTable 1 }

DPStatusLinkAggregationStatusEntry ::= SEQUENCE {
    dpStatusLinkAggregationStatusIndex    Unsigned32,
    dpStatusLinkAggregationStatusName    DisplayString,
    dpStatusLinkAggregationStatusMgmtName    DisplayString,
    dpStatusLinkAggregationStatusMTU    Unsigned32,
    dpStatusLinkAggregationStatusMode    INTEGER,
    dpStatusLinkAggregationStatusStatus    INTEGER,
    dpStatusLinkAggregationStatusPrimary    DisplayString,
    dpStatusLinkAggregationStatusActive    DisplayString,
    dpStatusLinkAggregationStatusLACPHashPolicy    DisplayString,
    dpStatusLinkAggregationStatusLACPDURate    DisplayString,
    dpStatusLinkAggregationStatusLACPSelectionPolicy    DisplayString,
    dpStatusLinkAggregationStatusLACPAggregatorID    Unsigned32,
    dpStatusLinkAggregationStatusLACPNumPorts    Unsigned32,
    dpStatusLinkAggregationStatusLACPActorKey    Unsigned32,
    dpStatusLinkAggregationStatusLACPPartnerKey    Unsigned32,
    dpStatusLinkAggregationStatusLACPPartnerMAC    DisplayString,
    dpStatusLinkAggregationStatusMIIStatus    INTEGER
}

dpStatusLinkAggregationStatusIndex OBJECT-TYPE
    SYNTAX      Unsigned32
    MAX-ACCESS  read-only
    STATUS      current
    DESCRIPTION
        "Identifies the index that identifies the aggregate interface."

    ::= { dpStatusLinkAggregationStatusEntry 1 }

dpStatusLinkAggregationStatusName OBJECT-TYPE
    SYNTAX      DisplayString
    MAX-ACCESS  read-only
    STATUS      current
    DESCRIPTION
        "Indicates the name of the inteface in the system kernel."

    ::= { dpStatusLinkAggregationStatusEntry 2 }

dpStatusLinkAggregationStatusMgmtName OBJECT-TYPE
    SYNTAX      DisplayString
    MAX-ACCESS  read-only
    STATUS      current
    DESCRIPTION
        "Indicates the name of the interface in the configuration."

    ::= { dpStatusLinkAggregationStatusEntry 3 }

dpStatusLinkAggregationStatusMTU OBJECT-TYPE
    SYNTAX      Unsigned32
    MAX-ACCESS  read-only
    STATUS      current
    DESCRIPTION
        "Identifies the maximum transmission unit (MTU) for the aggregation."

    ::= { dpStatusLinkAggregationStatusEntry 4 }

dpStatusLinkAggregationStatusMode OBJECT-TYPE
    SYNTAX      INTEGER { 
                        none(-1),
                        ab(1),
                        lacp(4),
                        tlb(5)
                }
    MAX-ACCESS  read-only
    STATUS      current
    DESCRIPTION
        "Indicates the mode for link aggregation."

    ::= { dpStatusLinkAggregationStatusEntry 5 }

dpStatusLinkAggregationStatusStatus OBJECT-TYPE
    SYNTAX      INTEGER { 
                        ok(1),
                        no-link(2)
                }
    MAX-ACCESS  read-only
    STATUS      current
    DESCRIPTION
        "Indicates the link state of the aggregate interface."

    ::= { dpStatusLinkAggregationStatusEntry 6 }

dpStatusLinkAggregationStatusPrimary OBJECT-TYPE
    SYNTAX      DisplayString
    MAX-ACCESS  read-only
    STATUS      current
    DESCRIPTION
        "Indicates which link, if any, is primary when the link aggregation mode is
        active-backup."

    ::= { dpStatusLinkAggregationStatusEntry 7 }

dpStatusLinkAggregationStatusActive OBJECT-TYPE
    SYNTAX      DisplayString
    MAX-ACCESS  read-only
    STATUS      current
    DESCRIPTION
        "Indicates the active link when the link aggregation mode is transmit-based
        load balancing or active-backup."

    ::= { dpStatusLinkAggregationStatusEntry 8 }

dpStatusLinkAggregationStatusLACPHashPolicy OBJECT-TYPE
    SYNTAX      DisplayString
    MAX-ACCESS  read-only
    STATUS      current
    DESCRIPTION
        "With the LACP aggregation mode, indicates the distribution algorithm for
        outbound packets among the active physical interfaces. The policy should
        match the configuration."

    ::= { dpStatusLinkAggregationStatusEntry 9 }

dpStatusLinkAggregationStatusLACPDURate OBJECT-TYPE
    SYNTAX      DisplayString
    MAX-ACCESS  read-only
    STATUS      current
    DESCRIPTION
        "With the LACP aggregation mode, indicates the transmission rate that
        members send LACP frames. The rate can be either fast or slow. In LACP,
        the frame uses the term LACPDU."

    ::= { dpStatusLinkAggregationStatusEntry 10 }

dpStatusLinkAggregationStatusLACPSelectionPolicy OBJECT-TYPE
    SYNTAX      DisplayString
    MAX-ACCESS  read-only
    STATUS      current
    DESCRIPTION
        "With the LACP aggregation mode, indicates the selection policy. The policy
        should match the configuration."

    ::= { dpStatusLinkAggregationStatusEntry 11 }

dpStatusLinkAggregationStatusLACPAggregatorID OBJECT-TYPE
    SYNTAX      Unsigned32
    MAX-ACCESS  read-only
    STATUS      current
    DESCRIPTION
        "With the LACP aggregation mode, indicates the ID of the active aggregator."

    ::= { dpStatusLinkAggregationStatusEntry 12 }

dpStatusLinkAggregationStatusLACPNumPorts OBJECT-TYPE
    SYNTAX      Unsigned32
    MAX-ACCESS  read-only
    STATUS      current
    DESCRIPTION
        "With the LACP aggregation mode, indicates the number of available ports
        for the active aggregator."

    ::= { dpStatusLinkAggregationStatusEntry 13 }

dpStatusLinkAggregationStatusLACPActorKey OBJECT-TYPE
    SYNTAX      Unsigned32
    MAX-ACCESS  read-only
    STATUS      current
    DESCRIPTION
        "With the LACP aggregation mode, identifies the value of the operational
        key that the Actor assigned to the port."

    ::= { dpStatusLinkAggregationStatusEntry 14 }

dpStatusLinkAggregationStatusLACPPartnerKey OBJECT-TYPE
    SYNTAX      Unsigned32
    MAX-ACCESS  read-only
    STATUS      current
    DESCRIPTION
        "With the LACP aggregation mode, identifies the physical MAC address of the
        Partner."

    ::= { dpStatusLinkAggregationStatusEntry 15 }

dpStatusLinkAggregationStatusLACPPartnerMAC OBJECT-TYPE
    SYNTAX      DisplayString
    MAX-ACCESS  read-only
    STATUS      current
    DESCRIPTION
        "The physical MAC address of the Partner"

    ::= { dpStatusLinkAggregationStatusEntry 16 }

dpStatusLinkAggregationStatusMIIStatus OBJECT-TYPE
    SYNTAX      INTEGER { 
                        ok(1),
                        no-link(2)
                }
    MAX-ACCESS  read-only
    STATUS      current
    DESCRIPTION
        "Indicates the MII link state of the aggregation."

    ::= { dpStatusLinkAggregationStatusEntry 17 }

--

dpStatusVlanInterfaceStatus2Table OBJECT-TYPE
    SYNTAX      SEQUENCE OF DPStatusVlanInterfaceStatus2Entry
    MAX-ACCESS  not-accessible
    STATUS      current
    DESCRIPTION
        "This table provides status for all VLAN interfaces."

    ::= { dpStatus 280 }

dpStatusVlanInterfaceStatus2Entry OBJECT-TYPE
    SYNTAX      DPStatusVlanInterfaceStatus2Entry
    MAX-ACCESS  not-accessible
    STATUS      current
    DESCRIPTION "Table row."
    INDEX { IMPLIED dpStatusVlanInterfaceStatus2Name }

    ::= { dpStatusVlanInterfaceStatus2Table 1 }

DPStatusVlanInterfaceStatus2Entry ::= SEQUENCE {
    dpStatusVlanInterfaceStatus2Name    DisplayString,
    dpStatusVlanInterfaceStatus2MgmtName    DisplayString,
    dpStatusVlanInterfaceStatus2InterfaceIndex    Unsigned32,
    dpStatusVlanInterfaceStatus2OnIfIndex    Unsigned32,
    dpStatusVlanInterfaceStatus2OnIfName    DisplayString,
    dpStatusVlanInterfaceStatus2VlanIdentifier    Unsigned32
}

dpStatusVlanInterfaceStatus2Name OBJECT-TYPE
    SYNTAX      DisplayString
    MAX-ACCESS  read-only
    STATUS      current
    DESCRIPTION
        "Indicates the name of the inteface in the system kernel."

    ::= { dpStatusVlanInterfaceStatus2Entry 1 }

dpStatusVlanInterfaceStatus2MgmtName OBJECT-TYPE
    SYNTAX      DisplayString
    MAX-ACCESS  read-only
    STATUS      current
    DESCRIPTION
        "Indicates the name of the interface in the configuration."

    ::= { dpStatusVlanInterfaceStatus2Entry 2 }

dpStatusVlanInterfaceStatus2InterfaceIndex OBJECT-TYPE
    SYNTAX      Unsigned32
    MAX-ACCESS  read-only
    STATUS      current
    DESCRIPTION
        "The SNMP ifIndex value of the row in the SNMP ifTable for the VLAN
        interface."

    ::= { dpStatusVlanInterfaceStatus2Entry 3 }

dpStatusVlanInterfaceStatus2OnIfIndex OBJECT-TYPE
    SYNTAX      Unsigned32
    MAX-ACCESS  read-only
    STATUS      current
    DESCRIPTION
        "The SNMP ifIndex of the parent interface of the VLAN interface."

    ::= { dpStatusVlanInterfaceStatus2Entry 4 }

dpStatusVlanInterfaceStatus2OnIfName OBJECT-TYPE
    SYNTAX      DisplayString
    MAX-ACCESS  read-only
    STATUS      current
    DESCRIPTION
        "The name of the parent interface of the VLAN interface."

    ::= { dpStatusVlanInterfaceStatus2Entry 5 }

dpStatusVlanInterfaceStatus2VlanIdentifier OBJECT-TYPE
    SYNTAX      Unsigned32
    MAX-ACCESS  read-only
    STATUS      current
    DESCRIPTION
        "The VLAN identifier that uniquely identifies the VLAN interface on its
        associated physical Ethernet network."

    ::= { dpStatusVlanInterfaceStatus2Entry 6 }

--

dpStatusFirmwareStatus2Table OBJECT-TYPE
    SYNTAX      SEQUENCE OF DPStatusFirmwareStatus2Entry
    MAX-ACCESS  not-accessible
    STATUS      current
    DESCRIPTION
        "Information about the current firmware installations."

    ::= { dpStatus 287 }

dpStatusFirmwareStatus2Entry OBJECT-TYPE
    SYNTAX      DPStatusFirmwareStatus2Entry
    MAX-ACCESS  not-accessible
    STATUS      current
    DESCRIPTION "Table row."
    INDEX { dpStatusFirmwareStatus2Type }

    ::= { dpStatusFirmwareStatus2Table 1 }

DPStatusFirmwareStatus2Entry ::= SEQUENCE {
    dpStatusFirmwareStatus2Type    INTEGER,
    dpStatusFirmwareStatus2Version    DisplayString,
    dpStatusFirmwareStatus2Build    DisplayString,
    dpStatusFirmwareStatus2BuildDate    DisplayString,
    dpStatusFirmwareStatus2DeliveryType    INTEGER,
    dpStatusFirmwareStatus2InstallDate    DisplayString,
    dpStatusFirmwareStatus2BootCount    Unsigned32
}

dpStatusFirmwareStatus2Type OBJECT-TYPE
    SYNTAX      INTEGER { 
                        primary(1),
                        secondary(2)
                }
    MAX-ACCESS  read-only
    STATUS      current
    DESCRIPTION
        "The type of the firmware installation type. Can be primary or secondary.
        The secondary firmware image is used when rolling back the firmware."

    ::= { dpStatusFirmwareStatus2Entry 1 }

dpStatusFirmwareStatus2Version OBJECT-TYPE
    SYNTAX      DisplayString
    MAX-ACCESS  read-only
    STATUS      current
    DESCRIPTION
        "The version of this firmware image."

    ::= { dpStatusFirmwareStatus2Entry 2 }

dpStatusFirmwareStatus2Build OBJECT-TYPE
    SYNTAX      DisplayString
    MAX-ACCESS  read-only
    STATUS      current
    DESCRIPTION
        "The specific build of this firmware image."

    ::= { dpStatusFirmwareStatus2Entry 3 }

dpStatusFirmwareStatus2BuildDate OBJECT-TYPE
    SYNTAX      DisplayString
    MAX-ACCESS  read-only
    STATUS      current
    DESCRIPTION
        "Date of the firmware build."

    ::= { dpStatusFirmwareStatus2Entry 4 }

dpStatusFirmwareStatus2DeliveryType OBJECT-TYPE
    SYNTAX      INTEGER { 
                        lTS(1),
                        cD(2)
                }
    MAX-ACCESS  read-only
    STATUS      current
    DESCRIPTION
        "Indicates the delivery type."

    ::= { dpStatusFirmwareStatus2Entry 5 }

dpStatusFirmwareStatus2InstallDate OBJECT-TYPE
    SYNTAX      DisplayString
    MAX-ACCESS  read-only
    STATUS      current
    DESCRIPTION
        "Date that this firmware was installed."

    ::= { dpStatusFirmwareStatus2Entry 6 }

dpStatusFirmwareStatus2BootCount OBJECT-TYPE
    SYNTAX      Unsigned32
    MAX-ACCESS  read-only
    STATUS      current
    DESCRIPTION
        "The number of times the firmware image was restarted through an appliance
        reboot or a firmware reload. The count is from the initial firmware load
        on the appliance till the current time. The count is independent of
        firmware version."

    ::= { dpStatusFirmwareStatus2Entry 7 }

--

dpStatusHNViewCacheResultTable OBJECT-TYPE
    SYNTAX      SEQUENCE OF DPStatusHNViewCacheResultEntry
    MAX-ACCESS  not-accessible
    STATUS      current
    DESCRIPTION
        "Displays the results of the cache search."

    ::= { dpStatus 301 }

dpStatusHNViewCacheResultEntry OBJECT-TYPE
    SYNTAX      DPStatusHNViewCacheResultEntry
    MAX-ACCESS  not-accessible
    STATUS      current
    DESCRIPTION "Table row."
    INDEX { IMPLIED dpStatusHNViewCacheResulturl }

    ::= { dpStatusHNViewCacheResultTable 1 }

DPStatusHNViewCacheResultEntry ::= SEQUENCE {
    dpStatusHNViewCacheResulturl    DisplayString,
    dpStatusHNViewCacheResultrequestDate    TimeStamp,
    dpStatusHNViewCacheResultresponseDate    TimeStamp,
    dpStatusHNViewCacheResultsize    Unsigned32,
    dpStatusHNViewCacheResultrequestHeaders    DisplayString,
    dpStatusHNViewCacheResultresponseHeaders    DisplayString,
    dpStatusHNViewCacheResultstatus    INTEGER
}

dpStatusHNViewCacheResulturl OBJECT-TYPE
    SYNTAX      DisplayString
    MAX-ACCESS  read-only
    STATUS      current
    DESCRIPTION
        "Specifies the associated URL of the cache item."

    ::= { dpStatusHNViewCacheResultEntry 1 }

dpStatusHNViewCacheResultrequestDate OBJECT-TYPE
    SYNTAX      TimeStamp
    MAX-ACCESS  read-only
    STATUS      current
    DESCRIPTION
        "Specifies the date stamp of the cache item from the proxy request."

    ::= { dpStatusHNViewCacheResultEntry 2 }

dpStatusHNViewCacheResultresponseDate OBJECT-TYPE
    SYNTAX      TimeStamp
    MAX-ACCESS  read-only
    STATUS      current
    DESCRIPTION
        "Specifies the date stamp of the cache item from the response of the origin
        to the proxy."

    ::= { dpStatusHNViewCacheResultEntry 3 }

dpStatusHNViewCacheResultsize OBJECT-TYPE
    SYNTAX      Unsigned32
    UNITS       "Bytes"
    MAX-ACCESS  read-only
    STATUS      current
    DESCRIPTION
        "Specifies the size of the item in the cache."

    ::= { dpStatusHNViewCacheResultEntry 4 }

dpStatusHNViewCacheResultrequestHeaders OBJECT-TYPE
    SYNTAX      DisplayString
    MAX-ACCESS  read-only
    STATUS      current
    DESCRIPTION
        "Specifies the request headers of the cache item."

    ::= { dpStatusHNViewCacheResultEntry 5 }

dpStatusHNViewCacheResultresponseHeaders OBJECT-TYPE
    SYNTAX      DisplayString
    MAX-ACCESS  read-only
    STATUS      current
    DESCRIPTION
        "Specifies the response headers of the cache item."

    ::= { dpStatusHNViewCacheResultEntry 6 }

dpStatusHNViewCacheResultstatus OBJECT-TYPE
    SYNTAX      INTEGER { 
                        error(1),
                        partial(2),
                        done(3)
                }
    MAX-ACCESS  read-only
    STATUS      current
    DESCRIPTION
        "Status of the cache search."

    ::= { dpStatusHNViewCacheResultEntry 7 }

--

dpStatusHNPurgeStatusTable OBJECT-TYPE
    SYNTAX      SEQUENCE OF DPStatusHNPurgeStatusEntry
    MAX-ACCESS  not-accessible
    STATUS      current
    DESCRIPTION
        "Displays the status of the cache purge action."

    ::= { dpStatus 302 }

dpStatusHNPurgeStatusEntry OBJECT-TYPE
    SYNTAX      DPStatusHNPurgeStatusEntry
    MAX-ACCESS  not-accessible
    STATUS      current
    DESCRIPTION "Table row."
    INDEX { dpStatusHNPurgeStatusid }

    ::= { dpStatusHNPurgeStatusTable 1 }

DPStatusHNPurgeStatusEntry ::= SEQUENCE {
    dpStatusHNPurgeStatusid    Unsigned32,
    dpStatusHNPurgeStatuspurgeExp    DisplayString,
    dpStatusHNPurgeStatusstatus    INTEGER
}

dpStatusHNPurgeStatusid OBJECT-TYPE
    SYNTAX      Unsigned32
    MAX-ACCESS  read-only
    STATUS      current
    DESCRIPTION
        "Specifies the ID for this cache purge."

    ::= { dpStatusHNPurgeStatusEntry 1 }

dpStatusHNPurgeStatuspurgeExp OBJECT-TYPE
    SYNTAX      DisplayString
    MAX-ACCESS  read-only
    STATUS      current
    DESCRIPTION
        "The regular expression that is being used to filter the cache for purging."

    ::= { dpStatusHNPurgeStatusEntry 2 }

dpStatusHNPurgeStatusstatus OBJECT-TYPE
    SYNTAX      INTEGER { 
                        started(1),
                        pending(2),
                        success(3),
                        error(4)
                }
    MAX-ACCESS  read-only
    STATUS      current
    DESCRIPTION
        "Indicates whether the purge is started, pending, completed, or reports an
        error."

    ::= { dpStatusHNPurgeStatusEntry 3 }

--

dpStatusHNAppStatsTable OBJECT-TYPE
    SYNTAX      SEQUENCE OF DPStatusHNAppStatsEntry
    MAX-ACCESS  not-accessible
    STATUS      current
    DESCRIPTION
        "Displays WAXHN accelerated host name status."

    ::= { dpStatus 303 }

dpStatusHNAppStatsEntry OBJECT-TYPE
    SYNTAX      DPStatusHNAppStatsEntry
    MAX-ACCESS  not-accessible
    STATUS      current
    DESCRIPTION "Table row."
    INDEX { IMPLIED dpStatusHNAppStatshostname }

    ::= { dpStatusHNAppStatsTable 1 }

DPStatusHNAppStatsEntry ::= SEQUENCE {
    dpStatusHNAppStatshostname    DisplayString,
    dpStatusHNAppStatsbytesFromOrigin    Unsigned32,
    dpStatusHNAppStatsbytesToClient    Unsigned32,
    dpStatusHNAppStatsbytesFromCache    Unsigned32,
    dpStatusHNAppStatstotalTransactions    Unsigned32,
    dpStatusHNAppStatstotalTransactionsFromCache    Unsigned32
}

dpStatusHNAppStatshostname OBJECT-TYPE
    SYNTAX      DisplayString
    MAX-ACCESS  read-only
    STATUS      current
    DESCRIPTION
        "Specifies the host name of the accelerated application."

    ::= { dpStatusHNAppStatsEntry 1 }

dpStatusHNAppStatsbytesFromOrigin OBJECT-TYPE
    SYNTAX      Unsigned32
    UNITS       "Bytes"
    MAX-ACCESS  read-only
    STATUS      current
    DESCRIPTION
        "Specifies the amount of data sent by the origin to the proxy for the
        accelerated host name."

    ::= { dpStatusHNAppStatsEntry 2 }

dpStatusHNAppStatsbytesToClient OBJECT-TYPE
    SYNTAX      Unsigned32
    UNITS       "Bytes"
    MAX-ACCESS  read-only
    STATUS      current
    DESCRIPTION
        "Specifies the amount of data sent from the proxy to the client for the
        accelerated host name."

    ::= { dpStatusHNAppStatsEntry 3 }

dpStatusHNAppStatsbytesFromCache OBJECT-TYPE
    SYNTAX      Unsigned32
    UNITS       "Bytes"
    MAX-ACCESS  read-only
    STATUS      current
    DESCRIPTION
        "Specifies the amount of data served from the cache for the accelerated
        host name."

    ::= { dpStatusHNAppStatsEntry 4 }

dpStatusHNAppStatstotalTransactions OBJECT-TYPE
    SYNTAX      Unsigned32
    MAX-ACCESS  read-only
    STATUS      current
    DESCRIPTION
        "Specifies the total number of transactions for the accelerated host name."

    ::= { dpStatusHNAppStatsEntry 5 }

dpStatusHNAppStatstotalTransactionsFromCache OBJECT-TYPE
    SYNTAX      Unsigned32
    MAX-ACCESS  read-only
    STATUS      current
    DESCRIPTION
        "Specifies the total number of transactions from the cache for the
        accelerated host name."

    ::= { dpStatusHNAppStatsEntry 6 }

--

dpStatusPolicyDomainStatusTable OBJECT-TYPE
    SYNTAX      SEQUENCE OF DPStatusPolicyDomainStatusEntry
    MAX-ACCESS  not-accessible
    STATUS      current
    DESCRIPTION "Table."

    ::= { dpStatus 306 }

dpStatusPolicyDomainStatusEntry OBJECT-TYPE
    SYNTAX      DPStatusPolicyDomainStatusEntry
    MAX-ACCESS  not-accessible
    STATUS      current
    DESCRIPTION "Table row."
    INDEX { dpStatusPolicyDomainStatusID }

    ::= { dpStatusPolicyDomainStatusTable 1 }

DPStatusPolicyDomainStatusEntry ::= SEQUENCE {
    dpStatusPolicyDomainStatusID    Unsigned32,
    dpStatusPolicyDomainStatusDescription    DisplayString,
    dpStatusPolicyDomainStatusNamespace    DisplayString,
    dpStatusPolicyDomainStatusURL    DisplayString
}

dpStatusPolicyDomainStatusID OBJECT-TYPE
    SYNTAX      Unsigned32
    MAX-ACCESS  read-only
    STATUS      current
    DESCRIPTION
        "Unique identifier."

    ::= { dpStatusPolicyDomainStatusEntry 1 }

dpStatusPolicyDomainStatusDescription OBJECT-TYPE
    SYNTAX      DisplayString
    MAX-ACCESS  read-only
    STATUS      current
    DESCRIPTION
        "The name of the policy domain."

    ::= { dpStatusPolicyDomainStatusEntry 2 }

dpStatusPolicyDomainStatusNamespace OBJECT-TYPE
    SYNTAX      DisplayString
    MAX-ACCESS  read-only
    STATUS      current
    DESCRIPTION
        "The namespace for the policy domain."

    ::= { dpStatusPolicyDomainStatusEntry 3 }

dpStatusPolicyDomainStatusURL OBJECT-TYPE
    SYNTAX      DisplayString
    MAX-ACCESS  read-only
    STATUS      current
    DESCRIPTION
        "The URL for custom policy domains, built-in policy domains display
        'System'."

    ::= { dpStatusPolicyDomainStatusEntry 4 }

--

dpStatusMQConnStatusTable OBJECT-TYPE
    SYNTAX      SEQUENCE OF DPStatusMQConnStatusEntry
    MAX-ACCESS  not-accessible
    STATUS      current
    DESCRIPTION
        "IBM MQ TCP connection status."

    ::= { dpStatus 308 }

dpStatusMQConnStatusEntry OBJECT-TYPE
    SYNTAX      DPStatusMQConnStatusEntry
    MAX-ACCESS  not-accessible
    STATUS      current
    DESCRIPTION "Table row."
    INDEX { IMPLIED dpConfigMQQMIndex }

    ::= { dpStatusMQConnStatusTable 1 }

DPStatusMQConnStatusEntry ::= SEQUENCE {
    dpStatusMQConnStatusQueueManager    DisplayString,
    dpStatusMQConnStatusTotalConnLimit    Unsigned32,
    dpStatusMQConnStatusTotalConn    Unsigned32,
    dpStatusMQConnStatusTotalIdleConn    Unsigned32,
    dpStatusMQConnStatusTotalActiveConn    Unsigned32,
    dpStatusMQConnStatusActiveFrontConn    Unsigned32,
    dpStatusMQConnStatusActiveBackConn    Unsigned32
}

dpStatusMQConnStatusQueueManager OBJECT-TYPE
    SYNTAX      DisplayString
    MAX-ACCESS  read-only
    STATUS      current
    DESCRIPTION
        "IBM MQ queue manager name."

    ::= { dpStatusMQConnStatusEntry 1 }

dpStatusMQConnStatusTotalConnLimit OBJECT-TYPE
    SYNTAX      Unsigned32
    MAX-ACCESS  read-only
    STATUS      current
    DESCRIPTION
        "Total number of open TCP connections to allow by this IBM MQ queue
        manager."

    ::= { dpStatusMQConnStatusEntry 2 }

dpStatusMQConnStatusTotalConn OBJECT-TYPE
    SYNTAX      Unsigned32
    MAX-ACCESS  read-only
    STATUS      current
    DESCRIPTION
        "Total number of TCP connections established by this IBM MQ queue manager."

    ::= { dpStatusMQConnStatusEntry 3 }

dpStatusMQConnStatusTotalIdleConn OBJECT-TYPE
    SYNTAX      Unsigned32
    MAX-ACCESS  read-only
    STATUS      current
    DESCRIPTION
        "Total number of idle TCP connections established by this IBM MQ queue
        manager."

    ::= { dpStatusMQConnStatusEntry 4 }

dpStatusMQConnStatusTotalActiveConn OBJECT-TYPE
    SYNTAX      Unsigned32
    MAX-ACCESS  read-only
    STATUS      current
    DESCRIPTION
        "Total number of active TCP connections established by this IBM MQ queue
        manager."

    ::= { dpStatusMQConnStatusEntry 5 }

dpStatusMQConnStatusActiveFrontConn OBJECT-TYPE
    SYNTAX      Unsigned32
    MAX-ACCESS  read-only
    STATUS      current
    DESCRIPTION
        "Number of active front-end TCP connections established by this IBM MQ
        queue manager."

    ::= { dpStatusMQConnStatusEntry 6 }

dpStatusMQConnStatusActiveBackConn OBJECT-TYPE
    SYNTAX      Unsigned32
    MAX-ACCESS  read-only
    STATUS      current
    DESCRIPTION
        "Number of active back-end TCP connections established by this IBM MQ queue
        manager."

    ::= { dpStatusMQConnStatusEntry 7 }

--

dpStatusSSHKnownHostFileStatus2Table OBJECT-TYPE
    SYNTAX      SEQUENCE OF DPStatusSSHKnownHostFileStatus2Entry
    MAX-ACCESS  not-accessible
    STATUS      current
    DESCRIPTION
        "SSH known host tables for the SSH client profile. If the table is no
        longer needed, it can be deleted using the 'Delete Table' button."

    ::= { dpStatus 309 }

dpStatusSSHKnownHostFileStatus2Entry OBJECT-TYPE
    SYNTAX      DPStatusSSHKnownHostFileStatus2Entry
    MAX-ACCESS  not-accessible
    STATUS      current
    DESCRIPTION "Table row."
    INDEX { dpStatusSSHKnownHostFileStatus2DomainName, IMPLIED dpStatusSSHKnownHostFileStatus2ClientName }

    ::= { dpStatusSSHKnownHostFileStatus2Table 1 }

DPStatusSSHKnownHostFileStatus2Entry ::= SEQUENCE {
    dpStatusSSHKnownHostFileStatus2DomainName    DisplayString,
    dpStatusSSHKnownHostFileStatus2ClientName    DisplayString
}

dpStatusSSHKnownHostFileStatus2DomainName OBJECT-TYPE
    SYNTAX      DisplayString
    MAX-ACCESS  read-only
    STATUS      current
    DESCRIPTION
        "The domain name associated with the table."

    ::= { dpStatusSSHKnownHostFileStatus2Entry 1 }

dpStatusSSHKnownHostFileStatus2ClientName OBJECT-TYPE
    SYNTAX      DisplayString
    MAX-ACCESS  read-only
    STATUS      current
    DESCRIPTION
        "The SSH client profile name associated with the table."

    ::= { dpStatusSSHKnownHostFileStatus2Entry 2 }

--

dpStatusServiceVersionStatusTable OBJECT-TYPE
    SYNTAX      SEQUENCE OF DPStatusServiceVersionStatusEntry
    MAX-ACCESS  not-accessible
    STATUS      current
    DESCRIPTION "Table."

    ::= { dpStatus 312 }

dpStatusServiceVersionStatusEntry OBJECT-TYPE
    SYNTAX      DPStatusServiceVersionStatusEntry
    MAX-ACCESS  not-accessible
    STATUS      current
    DESCRIPTION "Table row."
    INDEX { dpConfigGatewayBaseIndex, dpStatusServiceVersionStatusID }

    ::= { dpStatusServiceVersionStatusTable 1 }

DPStatusServiceVersionStatusEntry ::= SEQUENCE {
    dpStatusServiceVersionStatusMPGateway    DisplayString,
    dpStatusServiceVersionStatusID    Unsigned32,
    dpStatusServiceVersionStatusServiceVersionSourceLocation    DisplayString,
    dpStatusServiceVersionStatusStatus    INTEGER,
    dpStatusServiceVersionStatusLastRefresh    TimeStamp,
    dpStatusServiceVersionStatusLog    DisplayString,
    dpStatusServiceVersionStatusPolicyExecution    Unsigned32
}

dpStatusServiceVersionStatusMPGateway OBJECT-TYPE
    SYNTAX      DisplayString
    MAX-ACCESS  read-only
    STATUS      current
    DESCRIPTION "No description yet."

    ::= { dpStatusServiceVersionStatusEntry 1 }

dpStatusServiceVersionStatusID OBJECT-TYPE
    SYNTAX      Unsigned32
    MAX-ACCESS  read-only
    STATUS      current
    DESCRIPTION "No description yet."

    ::= { dpStatusServiceVersionStatusEntry 2 }

dpStatusServiceVersionStatusServiceVersionSourceLocation OBJECT-TYPE
    SYNTAX      DisplayString
    MAX-ACCESS  read-only
    STATUS      current
    DESCRIPTION "No description yet."

    ::= { dpStatusServiceVersionStatusEntry 3 }

dpStatusServiceVersionStatusStatus OBJECT-TYPE
    SYNTAX      INTEGER { 
                        processing(1),
                        okay(2),
                        warning(3),
                        error(4)
                }
    MAX-ACCESS  read-only
    STATUS      current
    DESCRIPTION "No description yet."

    ::= { dpStatusServiceVersionStatusEntry 4 }

dpStatusServiceVersionStatusLastRefresh OBJECT-TYPE
    SYNTAX      TimeStamp
    MAX-ACCESS  read-only
    STATUS      current
    DESCRIPTION "No description yet."

    ::= { dpStatusServiceVersionStatusEntry 5 }

dpStatusServiceVersionStatusLog OBJECT-TYPE
    SYNTAX      DisplayString
    MAX-ACCESS  read-only
    STATUS      current
    DESCRIPTION "No description yet."

    ::= { dpStatusServiceVersionStatusEntry 6 }

dpStatusServiceVersionStatusPolicyExecution OBJECT-TYPE
    SYNTAX      Unsigned32
    MAX-ACCESS  read-only
    STATUS      current
    DESCRIPTION "No description yet."

    ::= { dpStatusServiceVersionStatusEntry 7 }

--

dpStatusSQLConnectionPoolStatusTable OBJECT-TYPE
    SYNTAX      SEQUENCE OF DPStatusSQLConnectionPoolStatusEntry
    MAX-ACCESS  not-accessible
    STATUS      current
    DESCRIPTION
        "SQL data source connection pool statistics."

    ::= { dpStatus 313 }

dpStatusSQLConnectionPoolStatusEntry OBJECT-TYPE
    SYNTAX      DPStatusSQLConnectionPoolStatusEntry
    MAX-ACCESS  not-accessible
    STATUS      current
    DESCRIPTION "Table row."
    INDEX { IMPLIED dpConfigSQLDataSourceIndex }

    ::= { dpStatusSQLConnectionPoolStatusTable 1 }

DPStatusSQLConnectionPoolStatusEntry ::= SEQUENCE {
    dpStatusSQLConnectionPoolStatusDataSource    DisplayString,
    dpStatusSQLConnectionPoolStatusTotalConnections    Unsigned32,
    dpStatusSQLConnectionPoolStatusIdleConnections    Unsigned32,
    dpStatusSQLConnectionPoolStatusActiveConnections    Unsigned32
}

dpStatusSQLConnectionPoolStatusDataSource OBJECT-TYPE
    SYNTAX      DisplayString
    MAX-ACCESS  read-only
    STATUS      current
    DESCRIPTION
        "Name of the SQL data source."

    ::= { dpStatusSQLConnectionPoolStatusEntry 1 }

dpStatusSQLConnectionPoolStatusTotalConnections OBJECT-TYPE
    SYNTAX      Unsigned32
    MAX-ACCESS  read-only
    STATUS      current
    DESCRIPTION
        "Total number of connections to this SQL data source."

    ::= { dpStatusSQLConnectionPoolStatusEntry 2 }

dpStatusSQLConnectionPoolStatusIdleConnections OBJECT-TYPE
    SYNTAX      Unsigned32
    MAX-ACCESS  read-only
    STATUS      current
    DESCRIPTION
        "Number of idle connections to this SQL data source."

    ::= { dpStatusSQLConnectionPoolStatusEntry 3 }

dpStatusSQLConnectionPoolStatusActiveConnections OBJECT-TYPE
    SYNTAX      Unsigned32
    MAX-ACCESS  read-only
    STATUS      current
    DESCRIPTION
        "Number of active connections to this SQL data source."

    ::= { dpStatusSQLConnectionPoolStatusEntry 4 }

--

dpStatusLDAPPoolSummaryTable OBJECT-TYPE
    SYNTAX      SEQUENCE OF DPStatusLDAPPoolSummaryEntry
    MAX-ACCESS  not-accessible
    STATUS      current
    DESCRIPTION
        "The status of all LDAP connection pools in the domain. The use of LDAP
        connection pool use decrease the search time with LDAP servers by reusing
        connections from the pool. The values are for all LDAP server:port:BindDN
        combinations"

    ::= { dpStatus 314 }

dpStatusLDAPPoolSummaryEntry OBJECT-TYPE
    SYNTAX      DPStatusLDAPPoolSummaryEntry
    MAX-ACCESS  not-accessible
    STATUS      current
    DESCRIPTION "Table row."
    INDEX { IMPLIED dpStatusLDAPPoolSummaryPoolName }

    ::= { dpStatusLDAPPoolSummaryTable 1 }

DPStatusLDAPPoolSummaryEntry ::= SEQUENCE {
    dpStatusLDAPPoolSummaryPoolName    DisplayString,
    dpStatusLDAPPoolSummaryElementsInPool    Gauge32,
    dpStatusLDAPPoolSummaryPoolSizeLimitExceededs    Counter32,
    dpStatusLDAPPoolSummaryRejectedConnections    Counter32,
    dpStatusLDAPPoolSummaryCurrentConnections    Gauge32,
    dpStatusLDAPPoolSummaryPeakConnections    Gauge32
}

dpStatusLDAPPoolSummaryPoolName OBJECT-TYPE
    SYNTAX      DisplayString
    MAX-ACCESS  read-only
    STATUS      current
    DESCRIPTION
        "Indicates name of the LDAP connection pool configuration."

    ::= { dpStatusLDAPPoolSummaryEntry 1 }

dpStatusLDAPPoolSummaryElementsInPool OBJECT-TYPE
    SYNTAX      Gauge32
    MAX-ACCESS  read-only
    STATUS      current
    DESCRIPTION
        "Indicates the total number of LDAP client connections in the connection
        pool. This value includes in-use and idle connections."

    ::= { dpStatusLDAPPoolSummaryEntry 2 }

dpStatusLDAPPoolSummaryPoolSizeLimitExceededs OBJECT-TYPE
    SYNTAX      Counter32
    MAX-ACCESS  read-only
    STATUS      current
    DESCRIPTION
        "Indicates the number of times that the appliance reached the maximum pool
        size for this pool."

    ::= { dpStatusLDAPPoolSummaryEntry 3 }

dpStatusLDAPPoolSummaryRejectedConnections OBJECT-TYPE
    SYNTAX      Counter32
    MAX-ACCESS  read-only
    STATUS      current
    DESCRIPTION
        "Indicates the number of times that the appliance rejected an LDAP request."

    ::= { dpStatusLDAPPoolSummaryEntry 4 }

dpStatusLDAPPoolSummaryCurrentConnections OBJECT-TYPE
    SYNTAX      Gauge32
    MAX-ACCESS  read-only
    STATUS      current
    DESCRIPTION
        "Indicates the number of in-use LDAP connections in the connection pool."

    ::= { dpStatusLDAPPoolSummaryEntry 5 }

dpStatusLDAPPoolSummaryPeakConnections OBJECT-TYPE
    SYNTAX      Gauge32
    MAX-ACCESS  read-only
    STATUS      current
    DESCRIPTION
        "Indicates the total number of LDAP connections that the appliance created
        from the LDAP connection Pool."

    ::= { dpStatusLDAPPoolSummaryEntry 6 }

--

dpStatusODRConnectorGroupStatusTable OBJECT-TYPE
    SYNTAX      SEQUENCE OF DPStatusODRConnectorGroupStatusEntry
    MAX-ACCESS  not-accessible
    STATUS      deprecated
    DESCRIPTION
        "Displays the status of all ODR connector groups.
        Note: this is obsoleted and is replaced by dpStatusODRConnectorGroupStatus2"

    ::= { dpStatus 315 }

dpStatusODRConnectorGroupStatusEntry OBJECT-TYPE
    SYNTAX      DPStatusODRConnectorGroupStatusEntry
    MAX-ACCESS  not-accessible
    STATUS      deprecated
    DESCRIPTION "Table row."
    INDEX { dpConfigODRConnectorGroupIndex, dpStatusODRConnectorGroupStatusConnectorHost, dpStatusODRConnectorGroupStatusConnectorPort }

    ::= { dpStatusODRConnectorGroupStatusTable 1 }

DPStatusODRConnectorGroupStatusEntry ::= SEQUENCE {
    dpStatusODRConnectorGroupStatusConnectorGroup    DisplayString,
    dpStatusODRConnectorGroupStatusConnectorGroupState    DisplayString,
    dpStatusODRConnectorGroupStatusConnectorHost    DisplayString,
    dpStatusODRConnectorGroupStatusConnectorPort    Unsigned32,
    dpStatusODRConnectorGroupStatusConnectorCurrentlyActive    DisplayString
}

dpStatusODRConnectorGroupStatusConnectorGroup OBJECT-TYPE
    SYNTAX      DisplayString
    MAX-ACCESS  read-only
    STATUS      deprecated
    DESCRIPTION
        "The name of the ODR connector group."

    ::= { dpStatusODRConnectorGroupStatusEntry 1 }

dpStatusODRConnectorGroupStatusConnectorGroupState OBJECT-TYPE
    SYNTAX      DisplayString
    MAX-ACCESS  read-only
    STATUS      deprecated
    DESCRIPTION
        "The state of the ODR connector group."

    ::= { dpStatusODRConnectorGroupStatusEntry 2 }

dpStatusODRConnectorGroupStatusConnectorHost OBJECT-TYPE
    SYNTAX      DisplayString
    MAX-ACCESS  read-only
    STATUS      deprecated
    DESCRIPTION
        "The IP address or host name of the ODR connector."

    ::= { dpStatusODRConnectorGroupStatusEntry 3 }

dpStatusODRConnectorGroupStatusConnectorPort OBJECT-TYPE
    SYNTAX      Unsigned32
    MAX-ACCESS  read-only
    STATUS      deprecated
    DESCRIPTION
        "The port number of the ODR connector."

    ::= { dpStatusODRConnectorGroupStatusEntry 4 }

dpStatusODRConnectorGroupStatusConnectorCurrentlyActive OBJECT-TYPE
    SYNTAX      DisplayString
    MAX-ACCESS  read-only
    STATUS      deprecated
    DESCRIPTION
        "Indicates whether the given ODR connector is active. Possible values are:
        yes or no."

    ::= { dpStatusODRConnectorGroupStatusEntry 5 }

--

dpStatusODRLoadBalancerStatusTable OBJECT-TYPE
    SYNTAX      SEQUENCE OF DPStatusODRLoadBalancerStatusEntry
    MAX-ACCESS  not-accessible
    STATUS      current
    DESCRIPTION
        "Displays the status of the ODR load balancer group members."

    ::= { dpStatus 316 }

dpStatusODRLoadBalancerStatusEntry OBJECT-TYPE
    SYNTAX      DPStatusODRLoadBalancerStatusEntry
    MAX-ACCESS  not-accessible
    STATUS      current
    DESCRIPTION "Table row."
    INDEX { dpStatusODRLoadBalancerStatusGroup, dpStatusODRLoadBalancerStatusServer, dpStatusODRLoadBalancerStatusPort }

    ::= { dpStatusODRLoadBalancerStatusTable 1 }

DPStatusODRLoadBalancerStatusEntry ::= SEQUENCE {
    dpStatusODRLoadBalancerStatusGroup    DisplayString,
    dpStatusODRLoadBalancerStatusConnectorGroup    DisplayString,
    dpStatusODRLoadBalancerStatusServer    DisplayString,
    dpStatusODRLoadBalancerStatusPort    Unsigned32,
    dpStatusODRLoadBalancerStatusHealth    INTEGER,
    dpStatusODRLoadBalancerStatusAdminState    INTEGER
}

dpStatusODRLoadBalancerStatusGroup OBJECT-TYPE
    SYNTAX      DisplayString
    MAX-ACCESS  read-only
    STATUS      current
    DESCRIPTION
        "The name of the ODR load balancer group. Only a single ODR load balancer
        group is supported, so this value is always 'ODR-LBG'."

    ::= { dpStatusODRLoadBalancerStatusEntry 1 }

dpStatusODRLoadBalancerStatusConnectorGroup OBJECT-TYPE
    SYNTAX      DisplayString
    MAX-ACCESS  read-only
    STATUS      current
    DESCRIPTION
        "The name of the ODR connector group that each Load Balancer group member
        belongs to."

    ::= { dpStatusODRLoadBalancerStatusEntry 2 }

dpStatusODRLoadBalancerStatusServer OBJECT-TYPE
    SYNTAX      DisplayString
    MAX-ACCESS  read-only
    STATUS      current
    DESCRIPTION
        "The IP address or host name of the ODR load balancer group member."

    ::= { dpStatusODRLoadBalancerStatusEntry 3 }

dpStatusODRLoadBalancerStatusPort OBJECT-TYPE
    SYNTAX      Unsigned32
    MAX-ACCESS  read-only
    STATUS      current
    DESCRIPTION
        "The member-specific target port."

    ::= { dpStatusODRLoadBalancerStatusEntry 4 }

dpStatusODRLoadBalancerStatusHealth OBJECT-TYPE
    SYNTAX      INTEGER { 
                        up(1),
                        softdown(2),
                        down(3)
                }
    MAX-ACCESS  read-only
    STATUS      current
    DESCRIPTION
        "The health status of a given ODR load balancer group member. Possible
        values are: up, softdown, or down."

    ::= { dpStatusODRLoadBalancerStatusEntry 5 }

dpStatusODRLoadBalancerStatusAdminState OBJECT-TYPE
    SYNTAX      INTEGER { 
                        enabled(1),
                        disabled(2)
                }
    MAX-ACCESS  read-only
    STATUS      current
    DESCRIPTION
        "The administrative state overrides the health of the server."

    ::= { dpStatusODRLoadBalancerStatusEntry 6 }

--

dpStatusLDAPPoolEntriesTable OBJECT-TYPE
    SYNTAX      SEQUENCE OF DPStatusLDAPPoolEntriesEntry
    MAX-ACCESS  not-accessible
    STATUS      current
    DESCRIPTION
        "The LDAP connection pool entries status provider shows the key
        server:port:BindDN combinations for all connections in all LDAP connection
        pools in the domain."

    ::= { dpStatus 318 }

dpStatusLDAPPoolEntriesEntry OBJECT-TYPE
    SYNTAX      DPStatusLDAPPoolEntriesEntry
    MAX-ACCESS  not-accessible
    STATUS      current
    DESCRIPTION "Table row."
    INDEX { dpStatusLDAPPoolEntriesPoolName, dpStatusLDAPPoolEntriesLocalPort }

    ::= { dpStatusLDAPPoolEntriesTable 1 }

DPStatusLDAPPoolEntriesEntry ::= SEQUENCE {
    dpStatusLDAPPoolEntriesPoolName    DisplayString,
    dpStatusLDAPPoolEntriesState    DisplayString,
    dpStatusLDAPPoolEntriesLocalPort    Unsigned32,
    dpStatusLDAPPoolEntriesRequestsMade    Counter32,
    dpStatusLDAPPoolEntriesPoolKey    DisplayString
}

dpStatusLDAPPoolEntriesPoolName OBJECT-TYPE
    SYNTAX      DisplayString
    MAX-ACCESS  read-only
    STATUS      current
    DESCRIPTION
        "Indicates the name of the LDAP Connection Pool configuration."

    ::= { dpStatusLDAPPoolEntriesEntry 1 }

dpStatusLDAPPoolEntriesState OBJECT-TYPE
    SYNTAX      DisplayString
    MAX-ACCESS  read-only
    STATUS      current
    DESCRIPTION
        "Indicates whether the LDAP client currently handles a transaction or not."

    ::= { dpStatusLDAPPoolEntriesEntry 2 }

dpStatusLDAPPoolEntriesLocalPort OBJECT-TYPE
    SYNTAX      Unsigned32 (0..65535)
    MAX-ACCESS  read-only
    STATUS      current
    DESCRIPTION
        "Indicates the local port that the LDAP client uses to connect to the LDAP
        server."

    ::= { dpStatusLDAPPoolEntriesEntry 3 }

dpStatusLDAPPoolEntriesRequestsMade OBJECT-TYPE
    SYNTAX      Counter32
    MAX-ACCESS  read-only
    STATUS      current
    DESCRIPTION
        "Indicates the number of times that the appliance reused the LDAP client."

    ::= { dpStatusLDAPPoolEntriesEntry 4 }

dpStatusLDAPPoolEntriesPoolKey OBJECT-TYPE
    SYNTAX      DisplayString
    MAX-ACCESS  read-only
    STATUS      current
    DESCRIPTION
        "Indicates the key server:port:BindDN combination in the LDAP connection
        Pool. When the LDAP connection pool works with a load balancing group, the
        server name in the key is empty."

    ::= { dpStatusLDAPPoolEntriesEntry 5 }

--

dpStatusDebugActionStatusTable OBJECT-TYPE
    SYNTAX      SEQUENCE OF DPStatusDebugActionStatusEntry
    MAX-ACCESS  not-accessible
    STATUS      current
    DESCRIPTION
        "This status provider lists the active debug sessions in the current domain
        or in all domains."

    ::= { dpStatus 319 }

dpStatusDebugActionStatusEntry OBJECT-TYPE
    SYNTAX      DPStatusDebugActionStatusEntry
    MAX-ACCESS  not-accessible
    STATUS      current
    DESCRIPTION "Table row."
    INDEX { IMPLIED dpStatusDebugActionStatusScript }

    ::= { dpStatusDebugActionStatusTable 1 }

DPStatusDebugActionStatusEntry ::= SEQUENCE {
    dpStatusDebugActionStatusID    DisplayString,
    dpStatusDebugActionStatusTransaction    Counter64,
    dpStatusDebugActionStatusService    DisplayString,
    dpStatusDebugActionStatusScript    DisplayString,
    dpStatusDebugActionStatusRemoteAddress    DisplayString,
    dpStatusDebugActionStatusInUse    INTEGER,
    dpStatusDebugActionStatusUser    DisplayString,
    dpStatusDebugActionStatusFrom    DisplayString,
    dpStatusDebugActionStatusElapsedTime    DisplayString
}

dpStatusDebugActionStatusID OBJECT-TYPE
    SYNTAX      DisplayString
    MAX-ACCESS  read-only
    STATUS      current
    DESCRIPTION
        "The session identifier uniquely identifes a debug session."

    ::= { dpStatusDebugActionStatusEntry 1 }

dpStatusDebugActionStatusTransaction OBJECT-TYPE
    SYNTAX      Counter64
    MAX-ACCESS  read-only
    STATUS      current
    DESCRIPTION
        "The transaction identifier matches the 'tid' that can be found in the
        system log."

    ::= { dpStatusDebugActionStatusEntry 2 }

dpStatusDebugActionStatusService OBJECT-TYPE
    SYNTAX      DisplayString
    MAX-ACCESS  read-only
    STATUS      current
    DESCRIPTION
        "The service name which the debug session is running in."

    ::= { dpStatusDebugActionStatusEntry 3 }

dpStatusDebugActionStatusScript OBJECT-TYPE
    SYNTAX      DisplayString
    MAX-ACCESS  read-only
    STATUS      current
    DESCRIPTION
        "The file location specifies the stylesheet or script to be debuged."

    ::= { dpStatusDebugActionStatusEntry 4 }

dpStatusDebugActionStatusRemoteAddress OBJECT-TYPE
    SYNTAX      DisplayString
    MAX-ACCESS  read-only
    STATUS      current
    DESCRIPTION
        "The remote address shows the source IP address of the transaction that
        activates the debugger."

    ::= { dpStatusDebugActionStatusEntry 5 }

dpStatusDebugActionStatusInUse OBJECT-TYPE
    SYNTAX      INTEGER { 
                        no(0),
                        yes(1),
                        quiescing(2)
                }
    MAX-ACCESS  read-only
    STATUS      current
    DESCRIPTION
        "Each debug session can have one connection. The In Use property indicates
        whether there is an active connection attached to the session."

    ::= { dpStatusDebugActionStatusEntry 6 }

dpStatusDebugActionStatusUser OBJECT-TYPE
    SYNTAX      DisplayString
    MAX-ACCESS  read-only
    STATUS      current
    DESCRIPTION
        "If the session is in use, the Remote User shows the name of the user who
        is connecting to this session."

    ::= { dpStatusDebugActionStatusEntry 7 }

dpStatusDebugActionStatusFrom OBJECT-TYPE
    SYNTAX      DisplayString
    MAX-ACCESS  read-only
    STATUS      current
    DESCRIPTION
        "If the session is in use, the User Location shows the IP address of the
        remote user."

    ::= { dpStatusDebugActionStatusEntry 8 }

dpStatusDebugActionStatusElapsedTime OBJECT-TYPE
    SYNTAX      DisplayString
    MAX-ACCESS  read-only
    STATUS      current
    DESCRIPTION
        "The elapsed time specifies the time in seconds that has elapsed since the
        debug session started."

    ::= { dpStatusDebugActionStatusEntry 9 }

dpStatusFirmwareVersion2 OBJECT IDENTIFIER ::= { dpStatus 321 }

dpStatusFirmwareVersion2Serial OBJECT-TYPE
    SYNTAX      DisplayString
    MAX-ACCESS  read-only
    STATUS      deprecated
    DESCRIPTION
        "The serial number of the appliance. This number is unique to each
        appliance."

    ::= { dpStatusFirmwareVersion2 1 }

dpStatusFirmwareVersion2Version OBJECT-TYPE
    SYNTAX      DisplayString
    MAX-ACCESS  read-only
    STATUS      deprecated
    DESCRIPTION
        "The version of the firmware."

    ::= { dpStatusFirmwareVersion2 2 }

dpStatusFirmwareVersion2Build OBJECT-TYPE
    SYNTAX      DisplayString
    MAX-ACCESS  read-only
    STATUS      deprecated
    DESCRIPTION
        "The build number of the firmware."

    ::= { dpStatusFirmwareVersion2 3 }

dpStatusFirmwareVersion2BuildDate OBJECT-TYPE
    SYNTAX      DisplayString
    MAX-ACCESS  read-only
    STATUS      deprecated
    DESCRIPTION
        "The date on which the firmware was built."

    ::= { dpStatusFirmwareVersion2 4 }

dpStatusFirmwareVersion2WatchdogBuild OBJECT-TYPE
    SYNTAX      DisplayString
    MAX-ACCESS  read-only
    STATUS      deprecated
    DESCRIPTION
        "The build number of the system health monitor."

    ::= { dpStatusFirmwareVersion2 5 }

dpStatusFirmwareVersion2InstalledDPOS OBJECT-TYPE
    SYNTAX      DisplayString
    MAX-ACCESS  read-only
    STATUS      deprecated
    DESCRIPTION
        "The version number of the DataPower appliance manager."

    ::= { dpStatusFirmwareVersion2 6 }

dpStatusFirmwareVersion2RunningDPOS OBJECT-TYPE
    SYNTAX      DisplayString
    MAX-ACCESS  read-only
    STATUS      deprecated
    DESCRIPTION
        "The version number of the DataPower appliance manager."

    ::= { dpStatusFirmwareVersion2 7 }

dpStatusFirmwareVersion2XMLAccelerator OBJECT-TYPE
    SYNTAX      INTEGER { 
                        embedded(1)
                }
    MAX-ACCESS  read-only
    STATUS      deprecated
    DESCRIPTION
        "The type of XML accelerator."

    ::= { dpStatusFirmwareVersion2 8 }

dpStatusFirmwareVersion2MachineType OBJECT-TYPE
    SYNTAX      DisplayString
    MAX-ACCESS  read-only
    STATUS      deprecated
    DESCRIPTION
        "The IBM machine type of the appliance."

    ::= { dpStatusFirmwareVersion2 9 }

dpStatusFirmwareVersion2ModelType OBJECT-TYPE
    SYNTAX      DisplayString
    MAX-ACCESS  read-only
    STATUS      deprecated
    DESCRIPTION
        "The IBM model type of the appliance."

    ::= { dpStatusFirmwareVersion2 10 }

dpStatusFirmwareVersion2Tenant OBJECT-TYPE
    SYNTAX      DisplayString
    MAX-ACCESS  read-only
    STATUS      deprecated
    DESCRIPTION
        "The name of DP tenant, '--' for drouter-0 (a.k.a. 'landlord')."

    ::= { dpStatusFirmwareVersion2 11 }

--

dpStatusODRConnectorGroupStatus2Table OBJECT-TYPE
    SYNTAX      SEQUENCE OF DPStatusODRConnectorGroupStatus2Entry
    MAX-ACCESS  not-accessible
    STATUS      current
    DESCRIPTION
        "Displays the status of all ODR connector groups."

    ::= { dpStatus 322 }

dpStatusODRConnectorGroupStatus2Entry OBJECT-TYPE
    SYNTAX      DPStatusODRConnectorGroupStatus2Entry
    MAX-ACCESS  not-accessible
    STATUS      current
    DESCRIPTION "Table row."
    INDEX { dpConfigODRConnectorGroupIndex, dpStatusODRConnectorGroupStatus2ConnectorHost, dpStatusODRConnectorGroupStatus2ConnectorPort }

    ::= { dpStatusODRConnectorGroupStatus2Table 1 }

DPStatusODRConnectorGroupStatus2Entry ::= SEQUENCE {
    dpStatusODRConnectorGroupStatus2ConnectorGroup    DisplayString,
    dpStatusODRConnectorGroupStatus2ConnectorGroupState    INTEGER,
    dpStatusODRConnectorGroupStatus2ConnectorHost    DisplayString,
    dpStatusODRConnectorGroupStatus2ConnectorPort    InetPortNumber,
    dpStatusODRConnectorGroupStatus2ConnectorCurrentlyActive    INTEGER
}

dpStatusODRConnectorGroupStatus2ConnectorGroup OBJECT-TYPE
    SYNTAX      DisplayString
    MAX-ACCESS  read-only
    STATUS      current
    DESCRIPTION
        "The name of the ODR connector group."

    ::= { dpStatusODRConnectorGroupStatus2Entry 1 }

dpStatusODRConnectorGroupStatus2ConnectorGroupState OBJECT-TYPE
    SYNTAX      INTEGER { 
                        starting(1),
                        started(2),
                        partialStart(3),
                        failed(4),
                        stopping(5),
                        stopped(6)
                }
    MAX-ACCESS  read-only
    STATUS      current
    DESCRIPTION
        "The state of the ODR connector group."

    ::= { dpStatusODRConnectorGroupStatus2Entry 2 }

dpStatusODRConnectorGroupStatus2ConnectorHost OBJECT-TYPE
    SYNTAX      DisplayString
    MAX-ACCESS  read-only
    STATUS      current
    DESCRIPTION
        "The IP address or host name of the ODR connector."

    ::= { dpStatusODRConnectorGroupStatus2Entry 3 }

dpStatusODRConnectorGroupStatus2ConnectorPort OBJECT-TYPE
    SYNTAX      InetPortNumber
    MAX-ACCESS  read-only
    STATUS      current
    DESCRIPTION
        "The port number of the ODR connector."

    ::= { dpStatusODRConnectorGroupStatus2Entry 4 }

dpStatusODRConnectorGroupStatus2ConnectorCurrentlyActive OBJECT-TYPE
    SYNTAX      INTEGER { 
                        yes(1),
                        no(2)
                }
    MAX-ACCESS  read-only
    STATUS      current
    DESCRIPTION
        "Indicates whether the given ODR connector is active."

    ::= { dpStatusODRConnectorGroupStatus2Entry 5 }

dpStatusCryptoEngineStatus2 OBJECT IDENTIFIER ::= { dpStatus 323 }

dpStatusCryptoEngineStatus2EngineType OBJECT-TYPE
    SYNTAX      INTEGER { 
                        standard(1),
                        hardware1(2),
                        hardware2(3),
                        hsm1(4),
                        hsm2(5),
                        hsm3(6),
                        hardware3(7)
                }
    MAX-ACCESS  read-only
    STATUS      current
    DESCRIPTION
        "The hardware type that is installed. Type 2 is a pure accelerator. HSM,
        which is a module for secure storage of private keys, also performs
        on-board cryptographic operations."

    ::= { dpStatusCryptoEngineStatus2 1 }

dpStatusCryptoEngineStatus2EngineStatus OBJECT-TYPE
    SYNTAX      INTEGER { 
                        fullyOperational(1),
                        fullyDisabled(2),
                        partiallyDisabled(3),
                        uncertifiedHSMFirmwareDetected(4),
                        hsmIsUninitialized(5),
                        hsmNeedsPowerCycle(6),
                        hsmDriverReloadFailed(7),
                        hsmPasswordLoginFailed(8),
                        hsmCredentialsNotFound(9),
                        microcodeLoadFailed(10),
                        microcodeFileNotFound(11),
                        runtimeErrorDetected(12)
                }
    MAX-ACCESS  read-only
    STATUS      current
    DESCRIPTION
        "A status message from the accelerator. If the message is 'HSM is
        uninitialized', you must initialize the HSM into one of the two FIPS 140-2
        levels before you can use it."

    ::= { dpStatusCryptoEngineStatus2 2 }

dpStatusCryptoEngineStatus2FIPSLevel OBJECT-TYPE
    SYNTAX      INTEGER { 
                        notApplicable(1),
                        uninitialized(2),
                        dr2(3),
                        dr3(4)
                }
    MAX-ACCESS  read-only
    STATUS      current
    DESCRIPTION
        "This information is applicable only to an appliance that has an HSM
        attached. Not initialized applies if the status message is 'HSM is
        uninitialized'. Levels 2 and 3 refer to the FIPS 140-2 level to which the
        HSM is initialized."

    ::= { dpStatusCryptoEngineStatus2 3 }

dpStatusCryptoEngineStatus2FIPSRole OBJECT-TYPE
    SYNTAX      INTEGER { 
                        notApplicable(1),
                        user(2),
                        officer(3)
                }
    MAX-ACCESS  read-only
    STATUS      current
    DESCRIPTION
        "This information is applicable only to an appliance that has an HSM
        attached. The HSM role that the appliance has assumed. Appliances with an
        HSM of type hsm1 never assume the role of Crypto Officer. Appliances with
        an HSM of type hsm2 need to assume the role of Crypto Officer in order to
        execute KWK cloning. All other operations require the role of Crypto User."

    ::= { dpStatusCryptoEngineStatus2 4 }

dpStatusCryptoEngineStatus2DisableAmount OBJECT-TYPE
    SYNTAX      INTEGER { 
                        none(1),
                        all(2),
                        rsa(3)
                }
    MAX-ACCESS  read-only
    STATUS      current
    DESCRIPTION
        "Parts of the cryptographic hardware functionality may be be disabled
        either at user request or by entering certain crypto modes. This field
        shows what cryptographic hardware functionality is currently disabled."

    ::= { dpStatusCryptoEngineStatus2 5 }

--

dpStatusRaidBatteryModuleStatusTable OBJECT-TYPE
    SYNTAX      SEQUENCE OF DPStatusRaidBatteryModuleStatusEntry
    MAX-ACCESS  not-accessible
    STATUS      current
    DESCRIPTION
        "The details about the battery backup unit (BBU) of the RAID controller.
        The BBU protects against the loss of cached data in the event of a power
        failure."

    ::= { dpStatus 324 }

dpStatusRaidBatteryModuleStatusEntry OBJECT-TYPE
    SYNTAX      DPStatusRaidBatteryModuleStatusEntry
    MAX-ACCESS  not-accessible
    STATUS      current
    DESCRIPTION "Table row."
    INDEX { dpStatusRaidBatteryModuleStatusControllerID }

    ::= { dpStatusRaidBatteryModuleStatusTable 1 }

DPStatusRaidBatteryModuleStatusEntry ::= SEQUENCE {
    dpStatusRaidBatteryModuleStatusControllerID    Unsigned32,
    dpStatusRaidBatteryModuleStatusBatteryType    DisplayString,
    dpStatusRaidBatteryModuleStatusSerial    Unsigned32,
    dpStatusRaidBatteryModuleStatusName    DisplayString,
    dpStatusRaidBatteryModuleStatusStatus    INTEGER,
    dpStatusRaidBatteryModuleStatusVoltage    Unsigned32,
    dpStatusRaidBatteryModuleStatusCurrent    Integer32,
    dpStatusRaidBatteryModuleStatusTemperature    Unsigned32,
    dpStatusRaidBatteryModuleStatusDesignCapacity    Unsigned32,
    dpStatusRaidBatteryModuleStatusDesignVoltage    Unsigned32
}

dpStatusRaidBatteryModuleStatusControllerID OBJECT-TYPE
    SYNTAX      Unsigned32
    MAX-ACCESS  read-only
    STATUS      current
    DESCRIPTION
        "The reference number of the RAID controller. The value is always 1."

    ::= { dpStatusRaidBatteryModuleStatusEntry 1 }

dpStatusRaidBatteryModuleStatusBatteryType OBJECT-TYPE
    SYNTAX      DisplayString
    MAX-ACCESS  read-only
    STATUS      current
    DESCRIPTION
        "The type of the BBU."

    ::= { dpStatusRaidBatteryModuleStatusEntry 2 }

dpStatusRaidBatteryModuleStatusSerial OBJECT-TYPE
    SYNTAX      Unsigned32
    MAX-ACCESS  read-only
    STATUS      current
    DESCRIPTION
        "The serial number of the BBU."

    ::= { dpStatusRaidBatteryModuleStatusEntry 3 }

dpStatusRaidBatteryModuleStatusName OBJECT-TYPE
    SYNTAX      DisplayString
    MAX-ACCESS  read-only
    STATUS      current
    DESCRIPTION
        "The product name of the BBU."

    ::= { dpStatusRaidBatteryModuleStatusEntry 4 }

dpStatusRaidBatteryModuleStatusStatus OBJECT-TYPE
    SYNTAX      INTEGER { 
                        chargeActive(1),
                        dischargeActive(2),
                        i2cErrorsDetected(3),
                        learnCycleActive(4),
                        learnCycleFailed(5),
                        learnCycleRequested(6),
                        learnCycleTimeout(7),
                        packMissing(8),
                        temperatureHigh(9),
                        voltageLow(10),
                        periodicLearnRequired(11),
                        remainingCapacityLow(12),
                        replacePack(13),
                        normal(14),
                        undefined(15),
                        transparentLearn(16)
                }
    MAX-ACCESS  read-only
    STATUS      current
    DESCRIPTION
        "The status of the BBU."

    ::= { dpStatusRaidBatteryModuleStatusEntry 5 }

dpStatusRaidBatteryModuleStatusVoltage OBJECT-TYPE
    SYNTAX      Unsigned32
    UNITS       "mV"
    MAX-ACCESS  read-only
    STATUS      current
    DESCRIPTION
        "The actual voltage of the battery in millivolts."

    ::= { dpStatusRaidBatteryModuleStatusEntry 6 }

dpStatusRaidBatteryModuleStatusCurrent OBJECT-TYPE
    SYNTAX      Integer32
    UNITS       "mA"
    MAX-ACCESS  read-only
    STATUS      current
    DESCRIPTION
        "The current that flows through the battery terminals in milliamperes."

    ::= { dpStatusRaidBatteryModuleStatusEntry 7 }

dpStatusRaidBatteryModuleStatusTemperature OBJECT-TYPE
    SYNTAX      Unsigned32
    UNITS       "C"
    MAX-ACCESS  read-only
    STATUS      current
    DESCRIPTION
        "The temperature of the battery in degrees Celcius."

    ::= { dpStatusRaidBatteryModuleStatusEntry 8 }

dpStatusRaidBatteryModuleStatusDesignCapacity OBJECT-TYPE
    SYNTAX      Unsigned32
    UNITS       "mAh"
    MAX-ACCESS  read-only
    STATUS      current
    DESCRIPTION
        "The designed capacity of the battery in milliampere-hour."

    ::= { dpStatusRaidBatteryModuleStatusEntry 9 }

dpStatusRaidBatteryModuleStatusDesignVoltage OBJECT-TYPE
    SYNTAX      Unsigned32
    UNITS       "mV"
    MAX-ACCESS  read-only
    STATUS      current
    DESCRIPTION
        "The designed voltage of the battery in millivolts."

    ::= { dpStatusRaidBatteryModuleStatusEntry 10 }

--

dpStatusLunaLatencyTable OBJECT-TYPE
    SYNTAX      SEQUENCE OF DPStatusLunaLatencyEntry
    MAX-ACCESS  not-accessible
    STATUS      current
    DESCRIPTION
        "Information about the cryptographic transactions that are processed by the
        SafeNet Luna Network HSM partitions."

    ::= { dpStatus 325 }

dpStatusLunaLatencyEntry OBJECT-TYPE
    SYNTAX      DPStatusLunaLatencyEntry
    MAX-ACCESS  not-accessible
    STATUS      current
    DESCRIPTION "Table row."
    INDEX { IMPLIED dpStatusLunaLatencyPartition }

    ::= { dpStatusLunaLatencyTable 1 }

DPStatusLunaLatencyEntry ::= SEQUENCE {
    dpStatusLunaLatencyPartition    DisplayString,
    dpStatusLunaLatencyLatest    Unsigned32,
    dpStatusLunaLatencyAverage    Unsigned32
}

dpStatusLunaLatencyPartition OBJECT-TYPE
    SYNTAX      DisplayString
    MAX-ACCESS  read-only
    STATUS      current
    DESCRIPTION
        "The name of the Luna HSM partition that the DataPower Gateway accesses for
        cryptographic transactions."

    ::= { dpStatusLunaLatencyEntry 1 }

dpStatusLunaLatencyLatest OBJECT-TYPE
    SYNTAX      Unsigned32
    UNITS       "ms"
    MAX-ACCESS  read-only
    STATUS      current
    DESCRIPTION
        "The latency in milliseconds of the last transaction."

    ::= { dpStatusLunaLatencyEntry 2 }

dpStatusLunaLatencyAverage OBJECT-TYPE
    SYNTAX      Unsigned32
    UNITS       "ms"
    MAX-ACCESS  read-only
    STATUS      current
    DESCRIPTION
        "A decayed average of the last 10 transactions in milliseconds where more
        weight is applied to the newest transaction."

    ::= { dpStatusLunaLatencyEntry 3 }

--

dpStatusStandbyStatus2Table OBJECT-TYPE
    SYNTAX      SEQUENCE OF DPStatusStandbyStatus2Entry
    MAX-ACCESS  not-accessible
    STATUS      current
    DESCRIPTION
        "Status of standby control protocol on Ethernet interfaces or VLANs on top
        of Ethernet interfaces."

    ::= { dpStatus 330 }

dpStatusStandbyStatus2Entry OBJECT-TYPE
    SYNTAX      DPStatusStandbyStatus2Entry
    MAX-ACCESS  not-accessible
    STATUS      current
    DESCRIPTION "Table row."
    INDEX { dpStatusStandbyStatus2InterfaceIndex }

    ::= { dpStatusStandbyStatus2Table 1 }

DPStatusStandbyStatus2Entry ::= SEQUENCE {
    dpStatusStandbyStatus2InterfaceIndex    Unsigned32,
    dpStatusStandbyStatus2InterfaceType    INTEGER,
    dpStatusStandbyStatus2Name    DisplayString,
    dpStatusStandbyStatus2Group    Unsigned32,
    dpStatusStandbyStatus2IP    IpAddress,
    dpStatusStandbyStatus2Priority    Unsigned32,
    dpStatusStandbyStatus2State    INTEGER,
    dpStatusStandbyStatus2Preempt    INTEGER,
    dpStatusStandbyStatus2GroupLeader    IpAddress,
    dpStatusStandbyStatus2SelfBalance    INTEGER,
    dpStatusStandbyStatus2DistAlg    INTEGER
}

dpStatusStandbyStatus2InterfaceIndex OBJECT-TYPE
    SYNTAX      Unsigned32
    MAX-ACCESS  read-only
    STATUS      current
    DESCRIPTION
        "Indicates the value of the SNMP ifIndex column in the ifTable for the
        interface that is running standby. The ifIndex is a unique value that is
        greater than zero for each interface."

    ::= { dpStatusStandbyStatus2Entry 1 }

dpStatusStandbyStatus2InterfaceType OBJECT-TYPE
    SYNTAX      INTEGER { 
                        other(1),
                        ethernet(6),
                        tunnel(131),
                        vLAN(135),
                        aggregate(161)
                }
    MAX-ACCESS  read-only
    STATUS      current
    DESCRIPTION
        "Indicates the interface type of the network interface that is running
        standby. Same numeric value as ifType in ifTable."

    ::= { dpStatusStandbyStatus2Entry 2 }

dpStatusStandbyStatus2Name OBJECT-TYPE
    SYNTAX      DisplayString
    MAX-ACCESS  read-only
    STATUS      current
    DESCRIPTION
        "Indicates the configuration name of the interface that is running standby."

    ::= { dpStatusStandbyStatus2Entry 3 }

dpStatusStandbyStatus2Group OBJECT-TYPE
    SYNTAX      Unsigned32 (1..255)
    MAX-ACCESS  read-only
    STATUS      current
    DESCRIPTION
        "Indicates the identifier for the standby group."

    ::= { dpStatusStandbyStatus2Entry 4 }

dpStatusStandbyStatus2IP OBJECT-TYPE
    SYNTAX      IpAddress
    MAX-ACCESS  read-only
    STATUS      current
    DESCRIPTION
        "Indicates the virtual IP address for the group, which is active on only
        one member of the standby group. This IP address is the address that
        external clients use to contact the group."

    ::= { dpStatusStandbyStatus2Entry 5 }

dpStatusStandbyStatus2Priority OBJECT-TYPE
    SYNTAX      Unsigned32 (0..255)
    MAX-ACCESS  read-only
    STATUS      current
    DESCRIPTION
        "Indicates the priority value. The appliance within the standby group with
        the highest assigned priority assumes the active role when there is an
        election."

    ::= { dpStatusStandbyStatus2Entry 6 }

dpStatusStandbyStatus2State OBJECT-TYPE
    SYNTAX      INTEGER { 
                        initial(1),
                        learn(2),
                        listen(3),
                        speak(4),
                        standby(5),
                        active(6)
                }
    MAX-ACCESS  read-only
    STATUS      current
    DESCRIPTION
        "Indicates the current state of this member in the standby group. If it is
        active, this member is the one that receives traffic for the IP address of
        the group. In other states, some other member of the group is active."

    ::= { dpStatusStandbyStatus2Entry 7 }

dpStatusStandbyStatus2Preempt OBJECT-TYPE
    SYNTAX      INTEGER { 
                        on(1),
                        off(2)
                }
    MAX-ACCESS  read-only
    STATUS      current
    DESCRIPTION
        "Indicates whether preemption is enabled. Do not enable preemption."

    ::= { dpStatusStandbyStatus2Entry 8 }

dpStatusStandbyStatus2GroupLeader OBJECT-TYPE
    SYNTAX      IpAddress
    MAX-ACCESS  read-only
    STATUS      current
    DESCRIPTION
        "Indicates the underlying IP address of the appliance in the group that is
        active and is receiving traffic to the virtual IP address."

    ::= { dpStatusStandbyStatus2Entry 9 }

dpStatusStandbyStatus2SelfBalance OBJECT-TYPE
    SYNTAX      INTEGER { 
                        on(1),
                        off(2)
                }
    MAX-ACCESS  read-only
    STATUS      current
    DESCRIPTION
        "With self-balancing enabled, indicates the active appliance that
        distributes incoming requests across all members of the standby group that
        have the self-balancing feature enabled."

    ::= { dpStatusStandbyStatus2Entry 10 }

dpStatusStandbyStatus2DistAlg OBJECT-TYPE
    SYNTAX      INTEGER { 
                        wlc(1),
                        rr(2)
                }
    MAX-ACCESS  read-only
    STATUS      current
    DESCRIPTION
        "Indicates the algorithm to distribute connections to members of the
        standby group that have the self-balancing feature enabled. All members in
        the standby group must use the same algorithm."

    ::= { dpStatusStandbyStatus2Entry 11 }

--

dpStatusServicesMemoryStatus2Table OBJECT-TYPE
    SYNTAX      SEQUENCE OF DPStatusServicesMemoryStatus2Entry
    MAX-ACCESS  not-accessible
    STATUS      current
    DESCRIPTION
        "Details of memory usage by services."

    ::= { dpStatus 331 }

dpStatusServicesMemoryStatus2Entry OBJECT-TYPE
    SYNTAX      DPStatusServicesMemoryStatus2Entry
    MAX-ACCESS  not-accessible
    STATUS      current
    DESCRIPTION "Table row."
    INDEX { dpStatusServicesMemoryStatus2serviceClass, IMPLIED dpStatusServicesMemoryStatus2serviceName }

    ::= { dpStatusServicesMemoryStatus2Table 1 }

DPStatusServicesMemoryStatus2Entry ::= SEQUENCE {
    dpStatusServicesMemoryStatus2serviceClass    INTEGER,
    dpStatusServicesMemoryStatus2serviceName    DisplayString,
    dpStatusServicesMemoryStatus2current    Gauge32,
    dpStatusServicesMemoryStatus2oneMinute    Gauge32,
    dpStatusServicesMemoryStatus2fiveMinutes    Gauge32,
    dpStatusServicesMemoryStatus2tenMinutes    Gauge32,
    dpStatusServicesMemoryStatus2oneHour    Gauge32,
    dpStatusServicesMemoryStatus2twelveHours    Gauge32,
    dpStatusServicesMemoryStatus2oneDay    Gauge32,
    dpStatusServicesMemoryStatus2lifetime    Gauge32
}

dpStatusServicesMemoryStatus2serviceClass OBJECT-TYPE
    SYNTAX      INTEGER { 
                        xSLProxyService(19),
                        xMLFirewallService(42),
                        wSGateway(95),
                        multiProtocolGateway(101),
                        webAppFW(132),
                        b2BGateway(195),
                        webTokenService(266),
                        apiGateway(360)
                }
    MAX-ACCESS  read-only
    STATUS      current
    DESCRIPTION
        "The type of service being considered."

    ::= { dpStatusServicesMemoryStatus2Entry 1 }

dpStatusServicesMemoryStatus2serviceName OBJECT-TYPE
    SYNTAX      DisplayString
    MAX-ACCESS  read-only
    STATUS      current
    DESCRIPTION
        "Name of the service."

    ::= { dpStatusServicesMemoryStatus2Entry 2 }

dpStatusServicesMemoryStatus2current OBJECT-TYPE
    SYNTAX      Gauge32
    UNITS       "megabytes"
    MAX-ACCESS  read-only
    STATUS      current
    DESCRIPTION
        "Current memory being used by this service."

    ::= { dpStatusServicesMemoryStatus2Entry 3 }

dpStatusServicesMemoryStatus2oneMinute OBJECT-TYPE
    SYNTAX      Gauge32
    UNITS       "megabytes"
    MAX-ACCESS  read-only
    STATUS      current
    DESCRIPTION
        "The peak memory usage by the service over the previous minute."

    ::= { dpStatusServicesMemoryStatus2Entry 4 }

dpStatusServicesMemoryStatus2fiveMinutes OBJECT-TYPE
    SYNTAX      Gauge32
    UNITS       "megabytes"
    MAX-ACCESS  read-only
    STATUS      current
    DESCRIPTION
        "The peak memory usage by the service in the interval between 1 and 5
        minutes ago."

    ::= { dpStatusServicesMemoryStatus2Entry 5 }

dpStatusServicesMemoryStatus2tenMinutes OBJECT-TYPE
    SYNTAX      Gauge32
    UNITS       "megabytes"
    MAX-ACCESS  read-only
    STATUS      current
    DESCRIPTION
        "The peak memory usage by the service in the interval between 5 and 10
        minutes ago."

    ::= { dpStatusServicesMemoryStatus2Entry 6 }

dpStatusServicesMemoryStatus2oneHour OBJECT-TYPE
    SYNTAX      Gauge32
    UNITS       "megabytes"
    MAX-ACCESS  read-only
    STATUS      current
    DESCRIPTION
        "The peak memory usage by the service in the interval between 10 minutes
        and 1 hour ago."

    ::= { dpStatusServicesMemoryStatus2Entry 7 }

dpStatusServicesMemoryStatus2twelveHours OBJECT-TYPE
    SYNTAX      Gauge32
    UNITS       "megabytes"
    MAX-ACCESS  read-only
    STATUS      current
    DESCRIPTION
        "The peak memory usage by the service in the interval between 1 and 12
        hours ago."

    ::= { dpStatusServicesMemoryStatus2Entry 8 }

dpStatusServicesMemoryStatus2oneDay OBJECT-TYPE
    SYNTAX      Gauge32
    UNITS       "megabytes"
    MAX-ACCESS  read-only
    STATUS      current
    DESCRIPTION
        "The peak memory usage by the service in the interval between 12 hours and
        1 day ago."

    ::= { dpStatusServicesMemoryStatus2Entry 9 }

dpStatusServicesMemoryStatus2lifetime OBJECT-TYPE
    SYNTAX      Gauge32
    UNITS       "megabytes"
    MAX-ACCESS  read-only
    STATUS      current
    DESCRIPTION
        "The peak memory usage by the service over its lifetime."

    ::= { dpStatusServicesMemoryStatus2Entry 10 }

--

dpStatusDomainsMemoryStatus2Table OBJECT-TYPE
    SYNTAX      SEQUENCE OF DPStatusDomainsMemoryStatus2Entry
    MAX-ACCESS  not-accessible
    STATUS      current
    DESCRIPTION
        "Details of memory usage by services and caches for a specific domain."

    ::= { dpStatus 332 }

dpStatusDomainsMemoryStatus2Entry OBJECT-TYPE
    SYNTAX      DPStatusDomainsMemoryStatus2Entry
    MAX-ACCESS  not-accessible
    STATUS      current
    DESCRIPTION "Table row."
    INDEX { IMPLIED dpStatusDomainsMemoryStatus2Domain }

    ::= { dpStatusDomainsMemoryStatus2Table 1 }

DPStatusDomainsMemoryStatus2Entry ::= SEQUENCE {
    dpStatusDomainsMemoryStatus2Domain    DisplayString,
    dpStatusDomainsMemoryStatus2ServicesCurrent    Gauge32,
    dpStatusDomainsMemoryStatus2ServicesOneMinute    Gauge32,
    dpStatusDomainsMemoryStatus2ServicesFiveMinutes    Gauge32,
    dpStatusDomainsMemoryStatus2ServicesTenMinutes    Gauge32,
    dpStatusDomainsMemoryStatus2ServicesOneHour    Gauge32,
    dpStatusDomainsMemoryStatus2ServicesTwelveHours    Gauge32,
    dpStatusDomainsMemoryStatus2ServicesOneDay    Gauge32,
    dpStatusDomainsMemoryStatus2ServicesLifetime    Gauge32,
    dpStatusDomainsMemoryStatus2DocumentCaches    Gauge32,
    dpStatusDomainsMemoryStatus2StylesheetCaches    Gauge32
}

dpStatusDomainsMemoryStatus2Domain OBJECT-TYPE
    SYNTAX      DisplayString
    MAX-ACCESS  read-only
    STATUS      current
    DESCRIPTION
        "The name of the domain."

    ::= { dpStatusDomainsMemoryStatus2Entry 1 }

dpStatusDomainsMemoryStatus2ServicesCurrent OBJECT-TYPE
    SYNTAX      Gauge32
    UNITS       "megabytes"
    MAX-ACCESS  read-only
    STATUS      current
    DESCRIPTION
        "Current total memory being used by all services of this domain."

    ::= { dpStatusDomainsMemoryStatus2Entry 2 }

dpStatusDomainsMemoryStatus2ServicesOneMinute OBJECT-TYPE
    SYNTAX      Gauge32
    UNITS       "megabytes"
    MAX-ACCESS  read-only
    STATUS      current
    DESCRIPTION
        "The peak memory usage by services of this domain over the previous minute."

    ::= { dpStatusDomainsMemoryStatus2Entry 3 }

dpStatusDomainsMemoryStatus2ServicesFiveMinutes OBJECT-TYPE
    SYNTAX      Gauge32
    UNITS       "megabytes"
    MAX-ACCESS  read-only
    STATUS      current
    DESCRIPTION
        "The peak memory usage by services of this domain in the interval between 1
        and 5 minutes ago."

    ::= { dpStatusDomainsMemoryStatus2Entry 4 }

dpStatusDomainsMemoryStatus2ServicesTenMinutes OBJECT-TYPE
    SYNTAX      Gauge32
    UNITS       "megabytes"
    MAX-ACCESS  read-only
    STATUS      current
    DESCRIPTION
        "The peak memory usage by services of this domain in the interval between 5
        and 10 minutes ago."

    ::= { dpStatusDomainsMemoryStatus2Entry 5 }

dpStatusDomainsMemoryStatus2ServicesOneHour OBJECT-TYPE
    SYNTAX      Gauge32
    UNITS       "megabytes"
    MAX-ACCESS  read-only
    STATUS      current
    DESCRIPTION
        "The peak memory usage by services of this domain in the interval between
        10 minutes and 1 hour ago."

    ::= { dpStatusDomainsMemoryStatus2Entry 6 }

dpStatusDomainsMemoryStatus2ServicesTwelveHours OBJECT-TYPE
    SYNTAX      Gauge32
    UNITS       "megabytes"
    MAX-ACCESS  read-only
    STATUS      current
    DESCRIPTION
        "The peak memory usage by services of this domain in the interval between 1
        and 12 hours ago."

    ::= { dpStatusDomainsMemoryStatus2Entry 7 }

dpStatusDomainsMemoryStatus2ServicesOneDay OBJECT-TYPE
    SYNTAX      Gauge32
    UNITS       "megabytes"
    MAX-ACCESS  read-only
    STATUS      current
    DESCRIPTION
        "The peak memory usage by services of this domain in the interval between
        12 hours and 1 day ago."

    ::= { dpStatusDomainsMemoryStatus2Entry 8 }

dpStatusDomainsMemoryStatus2ServicesLifetime OBJECT-TYPE
    SYNTAX      Gauge32
    UNITS       "megabytes"
    MAX-ACCESS  read-only
    STATUS      current
    DESCRIPTION
        "The peak memory usage by services of this domain over its lifetime."

    ::= { dpStatusDomainsMemoryStatus2Entry 9 }

dpStatusDomainsMemoryStatus2DocumentCaches OBJECT-TYPE
    SYNTAX      Gauge32
    UNITS       "kilobytes"
    MAX-ACCESS  read-only
    STATUS      current
    DESCRIPTION
        "Total memory usage by all document caches in this domain."

    ::= { dpStatusDomainsMemoryStatus2Entry 10 }

dpStatusDomainsMemoryStatus2StylesheetCaches OBJECT-TYPE
    SYNTAX      Gauge32
    UNITS       "kilobytes"
    MAX-ACCESS  read-only
    STATUS      current
    DESCRIPTION
        "Total memory usage by all stylesheet caches in this domain."

    ::= { dpStatusDomainsMemoryStatus2Entry 11 }

--

dpStatusSGClientStatusTable OBJECT-TYPE
    SYNTAX      SEQUENCE OF DPStatusSGClientStatusEntry
    MAX-ACCESS  not-accessible
    STATUS      current
    DESCRIPTION
        "Status of Secure Gateway clients."

    ::= { dpStatus 333 }

dpStatusSGClientStatusEntry OBJECT-TYPE
    SYNTAX      DPStatusSGClientStatusEntry
    MAX-ACCESS  not-accessible
    STATUS      current
    DESCRIPTION "Table row."
    INDEX { IMPLIED dpConfigSecureGatewayClientIndex }

    ::= { dpStatusSGClientStatusTable 1 }

DPStatusSGClientStatusEntry ::= SEQUENCE {
    dpStatusSGClientStatusName    DisplayString,
    dpStatusSGClientStatusTotalConn    Unsigned32,
    dpStatusSGClientStatusActiveConn    Unsigned32
}

dpStatusSGClientStatusName OBJECT-TYPE
    SYNTAX      DisplayString
    MAX-ACCESS  read-only
    STATUS      current
    DESCRIPTION
        "Name of the Secure Gateway client."

    ::= { dpStatusSGClientStatusEntry 1 }

dpStatusSGClientStatusTotalConn OBJECT-TYPE
    SYNTAX      Unsigned32
    MAX-ACCESS  read-only
    STATUS      current
    DESCRIPTION
        "Total number of connections that have ever been active since this Secure
        Gateway client was enabled."

    ::= { dpStatusSGClientStatusEntry 2 }

dpStatusSGClientStatusActiveConn OBJECT-TYPE
    SYNTAX      Unsigned32
    MAX-ACCESS  read-only
    STATUS      current
    DESCRIPTION
        "Number of currently active connections."

    ::= { dpStatusSGClientStatusEntry 3 }

--

dpStatusSGClientConnectionStatusTable OBJECT-TYPE
    SYNTAX      SEQUENCE OF DPStatusSGClientConnectionStatusEntry
    MAX-ACCESS  not-accessible
    STATUS      current
    DESCRIPTION
        "Secure Gateway client connection status."

    ::= { dpStatus 334 }

dpStatusSGClientConnectionStatusEntry OBJECT-TYPE
    SYNTAX      DPStatusSGClientConnectionStatusEntry
    MAX-ACCESS  not-accessible
    STATUS      current
    DESCRIPTION "Table row."
    INDEX { dpConfigSecureGatewayClientIndex, dpStatusSGClientConnectionStatusDestinationHost, dpStatusSGClientConnectionStatusDestinationPort }

    ::= { dpStatusSGClientConnectionStatusTable 1 }

DPStatusSGClientConnectionStatusEntry ::= SEQUENCE {
    dpStatusSGClientConnectionStatusGateway    DisplayString,
    dpStatusSGClientConnectionStatusDestinationHost    DisplayString,
    dpStatusSGClientConnectionStatusDestinationPort    Unsigned32
}

dpStatusSGClientConnectionStatusGateway OBJECT-TYPE
    SYNTAX      DisplayString
    MAX-ACCESS  read-only
    STATUS      current
    DESCRIPTION
        "Name of the Secure Gateway client."

    ::= { dpStatusSGClientConnectionStatusEntry 1 }

dpStatusSGClientConnectionStatusDestinationHost OBJECT-TYPE
    SYNTAX      DisplayString
    MAX-ACCESS  read-only
    STATUS      current
    DESCRIPTION
        "Host name or IP address of the destination of this connection."

    ::= { dpStatusSGClientConnectionStatusEntry 2 }

dpStatusSGClientConnectionStatusDestinationPort OBJECT-TYPE
    SYNTAX      Unsigned32
    MAX-ACCESS  read-only
    STATUS      current
    DESCRIPTION
        "Port number of the destination of this connection."

    ::= { dpStatusSGClientConnectionStatusEntry 3 }

dpStatusVirtualPlatform OBJECT IDENTIFIER ::= { dpStatus 335 }

dpStatusVirtualPlatformEdition OBJECT-TYPE
    SYNTAX      INTEGER { 
                        production(1),
                        nonproduction(2),
                        developers(3),
                        developers-limited(4)
                }
    MAX-ACCESS  read-only
    STATUS      obsolete
    DESCRIPTION
        "Shows whether the virtual appliance is Production Edition, Non-Production
        Edition, or Developers Edition."

    ::= { dpStatusVirtualPlatform 1 }

dpStatusVirtualPlatformHypervisor OBJECT-TYPE
    SYNTAX      DisplayString
    MAX-ACCESS  read-only
    STATUS      obsolete
    DESCRIPTION
        "Shows the hypervisor that this virtual appliance is running on. The
        hypervisor provides the information in the DMI data. The value is none
        when the appliance is hosted on a cloud platform."

    ::= { dpStatusVirtualPlatform 2 }

dpStatusVirtualPlatformVirtualCPUs OBJECT-TYPE
    SYNTAX      Unsigned32
    MAX-ACCESS  read-only
    STATUS      obsolete
    DESCRIPTION
        "Shows the number of virtual CPUs that are available to the virtual
        appliance."

    ::= { dpStatusVirtualPlatform 3 }

dpStatusVirtualPlatformMemory OBJECT-TYPE
    SYNTAX      Unsigned32
    UNITS       "Gigabytes"
    MAX-ACCESS  read-only
    STATUS      obsolete
    DESCRIPTION
        "Shows the amount of virtual memory that is available to the virtual
        appliance."

    ::= { dpStatusVirtualPlatform 4 }

dpStatusVirtualPlatformUUID OBJECT-TYPE
    SYNTAX      DisplayString
    MAX-ACCESS  read-only
    STATUS      obsolete
    DESCRIPTION
        "Shows the UUID of this virtual appliance that is assigned by the
        hypervisor. The hypervisor provides the information in the DMI data."

    ::= { dpStatusVirtualPlatform 5 }

dpStatusVirtualPlatformPlatform OBJECT-TYPE
    SYNTAX      DisplayString
    MAX-ACCESS  read-only
    STATUS      obsolete
    DESCRIPTION
        "Shows the name of the cloud platform provider. The host system provides
        the information. The value is none when the appliance is running in a
        hypervisor."

    ::= { dpStatusVirtualPlatform 6 }

dpStatusVirtualPlatformOSDistro OBJECT-TYPE
    SYNTAX      DisplayString
    MAX-ACCESS  read-only
    STATUS      obsolete
    DESCRIPTION
        "When the virtual appliance is hosted on a cloud platform, shows the name
        of the cloud OS Linux distribution. The host system provides the
        information."

    ::= { dpStatusVirtualPlatform 7 }

dpStatusHypervisor2 OBJECT IDENTIFIER ::= { dpStatus 336 }

dpStatusHypervisor2Edition OBJECT-TYPE
    SYNTAX      INTEGER { 
                        production(1),
                        nonproduction(2),
                        developers(3),
                        developers-limited(4)
                }
    MAX-ACCESS  read-only
    STATUS      deprecated
    DESCRIPTION
        "Shows whether this virtual appliance is Production Edition, Non-Production
        Edition, or Developers Edition."

    ::= { dpStatusHypervisor2 1 }

dpStatusHypervisor2Hypervisor OBJECT-TYPE
    SYNTAX      DisplayString
    MAX-ACCESS  read-only
    STATUS      deprecated
    DESCRIPTION
        "The hypervisor that this virtual appliance is running on. This information
        is provided by the hypervisor in the DMI information."

    ::= { dpStatusHypervisor2 2 }

dpStatusHypervisor2VirtualCPUs OBJECT-TYPE
    SYNTAX      Unsigned32
    MAX-ACCESS  read-only
    STATUS      deprecated
    DESCRIPTION
        "The number of virtual CPUs that are emulated by the hypervisor."

    ::= { dpStatusHypervisor2 3 }

dpStatusHypervisor2Memory OBJECT-TYPE
    SYNTAX      DisplayString
    UNITS       "Gigabytes"
    MAX-ACCESS  read-only
    STATUS      deprecated
    DESCRIPTION
        "The amount of virtual memory that is emulated by the hypervisor."

    ::= { dpStatusHypervisor2 4 }

dpStatusHypervisor2UUID OBJECT-TYPE
    SYNTAX      DisplayString
    MAX-ACCESS  read-only
    STATUS      deprecated
    DESCRIPTION
        "The UUID of this virtual appliance that is assigned by the hypervisor.
        This information is provided by the hypervisor in the DMI information."

    ::= { dpStatusHypervisor2 5 }

dpStatusVirtualPlatform2 OBJECT IDENTIFIER ::= { dpStatus 337 }

dpStatusVirtualPlatform2Edition OBJECT-TYPE
    SYNTAX      INTEGER { 
                        production(1),
                        nonproduction(2),
                        developers(3),
                        developers-limited(4)
                }
    MAX-ACCESS  read-only
    STATUS      obsolete
    DESCRIPTION
        "Shows the product name."

    ::= { dpStatusVirtualPlatform2 1 }

dpStatusVirtualPlatform2Hypervisor OBJECT-TYPE
    SYNTAX      DisplayString
    MAX-ACCESS  read-only
    STATUS      obsolete
    DESCRIPTION
        "Shows the hypervisor that the DataPower Gateway is running on. The value
        is always none when platform is docker or linux ."

    ::= { dpStatusVirtualPlatform2 2 }

dpStatusVirtualPlatform2VirtualCPUs OBJECT-TYPE
    SYNTAX      Unsigned32
    MAX-ACCESS  read-only
    STATUS      obsolete
    DESCRIPTION
        "Shows the number of virtual CPUs that are available."

    ::= { dpStatusVirtualPlatform2 3 }

dpStatusVirtualPlatform2Memory OBJECT-TYPE
    SYNTAX      DisplayString
    UNITS       "Gigabytes"
    MAX-ACCESS  read-only
    STATUS      obsolete
    DESCRIPTION
        "Shows the amount of virtual memory that is available."

    ::= { dpStatusVirtualPlatform2 4 }

dpStatusVirtualPlatform2UUID OBJECT-TYPE
    SYNTAX      DisplayString
    MAX-ACCESS  read-only
    STATUS      obsolete
    DESCRIPTION
        "Shows the assigned UUID."

    ::= { dpStatusVirtualPlatform2 5 }

dpStatusVirtualPlatform2Platform OBJECT-TYPE
    SYNTAX      DisplayString
    MAX-ACCESS  read-only
    STATUS      obsolete
    DESCRIPTION
        "Shows the platform type that is defined for the DataPower Gateway. The
        value is always blank for hypervisors."

    ::= { dpStatusVirtualPlatform2 6 }

dpStatusVirtualPlatform2OSDistro OBJECT-TYPE
    SYNTAX      DisplayString
    MAX-ACCESS  read-only
    STATUS      obsolete
    DESCRIPTION
        "The Linux operation system distribution that the DataPower Gateway is
        running. The value is always blank for hypervisors."

    ::= { dpStatusVirtualPlatform2 7 }

dpStatusVirtualPlatform3 OBJECT IDENTIFIER ::= { dpStatus 338 }

dpStatusVirtualPlatform3Edition OBJECT-TYPE
    SYNTAX      INTEGER { 
                        production(1),
                        nonproduction(2),
                        developers(3),
                        developers-limited(4)
                }
    MAX-ACCESS  read-only
    STATUS      current
    DESCRIPTION
        "Shows the product name."

    ::= { dpStatusVirtualPlatform3 1 }

dpStatusVirtualPlatform3Hypervisor OBJECT-TYPE
    SYNTAX      DisplayString
    MAX-ACCESS  read-only
    STATUS      current
    DESCRIPTION
        "Shows the hypervisor that the DataPower Gateway is running on. The value
        is always none when platform is docker or linux ."

    ::= { dpStatusVirtualPlatform3 2 }

dpStatusVirtualPlatform3VirtualCPUs OBJECT-TYPE
    SYNTAX      Unsigned32
    MAX-ACCESS  read-only
    STATUS      current
    DESCRIPTION
        "Shows the number of virtual CPUs that are available."

    ::= { dpStatusVirtualPlatform3 3 }

dpStatusVirtualPlatform3Memory OBJECT-TYPE
    SYNTAX      DisplayString
    UNITS       "Gigabytes"
    MAX-ACCESS  read-only
    STATUS      current
    DESCRIPTION
        "Shows the amount of virtual memory that is available."

    ::= { dpStatusVirtualPlatform3 4 }

dpStatusVirtualPlatform3UUID OBJECT-TYPE
    SYNTAX      DisplayString
    MAX-ACCESS  read-only
    STATUS      current
    DESCRIPTION
        "Shows the assigned UUID."

    ::= { dpStatusVirtualPlatform3 5 }

dpStatusVirtualPlatform3Platform OBJECT-TYPE
    SYNTAX      DisplayString
    MAX-ACCESS  read-only
    STATUS      current
    DESCRIPTION
        "Shows the platform type that is defined for the DataPower Gateway. The
        value is always blank for hypervisors."

    ::= { dpStatusVirtualPlatform3 6 }

dpStatusVirtualPlatform3OSDistro OBJECT-TYPE
    SYNTAX      DisplayString
    MAX-ACCESS  read-only
    STATUS      current
    DESCRIPTION
        "The Linux operation system distribution that the DataPower Gateway is
        running. The value is always blank for hypervisors."

    ::= { dpStatusVirtualPlatform3 7 }

dpStatusVirtualPlatform3Cores OBJECT-TYPE
    SYNTAX      Unsigned32
    MAX-ACCESS  read-only
    STATUS      current
    DESCRIPTION
        "The number of CPU cores."

    ::= { dpStatusVirtualPlatform3 8 }

dpStatusHypervisor3 OBJECT IDENTIFIER ::= { dpStatus 339 }

dpStatusHypervisor3Edition OBJECT-TYPE
    SYNTAX      INTEGER { 
                        production(1),
                        nonproduction(2),
                        developers(3),
                        developers-limited(4)
                }
    MAX-ACCESS  read-only
    STATUS      current
    DESCRIPTION
        "Shows whether this virtual appliance is Production Edition, Non-Production
        Edition, or Developers Edition."

    ::= { dpStatusHypervisor3 1 }

dpStatusHypervisor3Hypervisor OBJECT-TYPE
    SYNTAX      DisplayString
    MAX-ACCESS  read-only
    STATUS      current
    DESCRIPTION
        "The hypervisor that this virtual appliance is running on. This information
        is provided by the hypervisor in the DMI information."

    ::= { dpStatusHypervisor3 2 }

dpStatusHypervisor3VirtualCPUs OBJECT-TYPE
    SYNTAX      Unsigned32
    MAX-ACCESS  read-only
    STATUS      current
    DESCRIPTION
        "The number of virtual CPUs that are emulated by the hypervisor."

    ::= { dpStatusHypervisor3 3 }

dpStatusHypervisor3Memory OBJECT-TYPE
    SYNTAX      DisplayString
    UNITS       "Gigabytes"
    MAX-ACCESS  read-only
    STATUS      current
    DESCRIPTION
        "The amount of virtual memory that is emulated by the hypervisor."

    ::= { dpStatusHypervisor3 4 }

dpStatusHypervisor3UUID OBJECT-TYPE
    SYNTAX      DisplayString
    MAX-ACCESS  read-only
    STATUS      current
    DESCRIPTION
        "The UUID of this virtual appliance that is assigned by the hypervisor.
        This information is provided by the hypervisor in the DMI information."

    ::= { dpStatusHypervisor3 5 }

dpStatusHypervisor3Cores OBJECT-TYPE
    SYNTAX      Unsigned32
    MAX-ACCESS  read-only
    STATUS      current
    DESCRIPTION
        "The number of CPU cores."

    ::= { dpStatusHypervisor3 6 }

dpStatusFirmwareVersion3 OBJECT IDENTIFIER ::= { dpStatus 340 }

dpStatusFirmwareVersion3Serial OBJECT-TYPE
    SYNTAX      DisplayString
    MAX-ACCESS  read-only
    STATUS      current
    DESCRIPTION
        "The serial number of the appliance. This number is unique to each
        appliance."

    ::= { dpStatusFirmwareVersion3 1 }

dpStatusFirmwareVersion3Version OBJECT-TYPE
    SYNTAX      DisplayString
    MAX-ACCESS  read-only
    STATUS      current
    DESCRIPTION
        "The version of the firmware."

    ::= { dpStatusFirmwareVersion3 2 }

dpStatusFirmwareVersion3Build OBJECT-TYPE
    SYNTAX      DisplayString
    MAX-ACCESS  read-only
    STATUS      current
    DESCRIPTION
        "The build number of the firmware."

    ::= { dpStatusFirmwareVersion3 3 }

dpStatusFirmwareVersion3BuildDate OBJECT-TYPE
    SYNTAX      DisplayString
    MAX-ACCESS  read-only
    STATUS      current
    DESCRIPTION
        "The date on which the firmware was built."

    ::= { dpStatusFirmwareVersion3 4 }

dpStatusFirmwareVersion3DeliveryType OBJECT-TYPE
    SYNTAX      INTEGER { 
                        lTS(1),
                        cD(2)
                }
    MAX-ACCESS  read-only
    STATUS      current
    DESCRIPTION
        "Indicates the delivery type."

    ::= { dpStatusFirmwareVersion3 5 }

dpStatusFirmwareVersion3WatchdogBuild OBJECT-TYPE
    SYNTAX      DisplayString
    MAX-ACCESS  read-only
    STATUS      current
    DESCRIPTION
        "The build number of the system health monitor."

    ::= { dpStatusFirmwareVersion3 6 }

dpStatusFirmwareVersion3InstalledDPOS OBJECT-TYPE
    SYNTAX      DisplayString
    MAX-ACCESS  read-only
    STATUS      current
    DESCRIPTION
        "The version number of the DataPower appliance manager."

    ::= { dpStatusFirmwareVersion3 7 }

dpStatusFirmwareVersion3RunningDPOS OBJECT-TYPE
    SYNTAX      DisplayString
    MAX-ACCESS  read-only
    STATUS      current
    DESCRIPTION
        "The version number of the DataPower appliance manager."

    ::= { dpStatusFirmwareVersion3 8 }

dpStatusFirmwareVersion3XMLAccelerator OBJECT-TYPE
    SYNTAX      INTEGER { 
                        embedded(1)
                }
    MAX-ACCESS  read-only
    STATUS      current
    DESCRIPTION
        "The type of XML accelerator."

    ::= { dpStatusFirmwareVersion3 9 }

dpStatusFirmwareVersion3MachineType OBJECT-TYPE
    SYNTAX      DisplayString
    MAX-ACCESS  read-only
    STATUS      current
    DESCRIPTION
        "The IBM machine type of the appliance."

    ::= { dpStatusFirmwareVersion3 10 }

dpStatusFirmwareVersion3ModelType OBJECT-TYPE
    SYNTAX      DisplayString
    MAX-ACCESS  read-only
    STATUS      current
    DESCRIPTION
        "The IBM model type of the appliance."

    ::= { dpStatusFirmwareVersion3 11 }

dpStatusFirmwareVersion3Tenant OBJECT-TYPE
    SYNTAX      DisplayString
    MAX-ACCESS  read-only
    STATUS      current
    DESCRIPTION
        "The name of DP tenant, '--' for drouter-0 (a.k.a. 'landlord')."

    ::= { dpStatusFirmwareVersion3 12 }

--

dpStatusWXSGridStatusTable OBJECT-TYPE
    SYNTAX      SEQUENCE OF DPStatusWXSGridStatusEntry
    MAX-ACCESS  not-accessible
    STATUS      current
    DESCRIPTION
        "eXtreme Scale Grid statistics."

    ::= { dpStatus 352 }

dpStatusWXSGridStatusEntry OBJECT-TYPE
    SYNTAX      DPStatusWXSGridStatusEntry
    MAX-ACCESS  not-accessible
    STATUS      current
    DESCRIPTION "Table row."
    INDEX { IMPLIED dpConfigWXSGridIndex }

    ::= { dpStatusWXSGridStatusTable 1 }

DPStatusWXSGridStatusEntry ::= SEQUENCE {
    dpStatusWXSGridStatusWXSGrid    DisplayString,
    dpStatusWXSGridStatusReadRequests    Counter64,
    dpStatusWXSGridStatusWriteRequests    Counter64,
    dpStatusWXSGridStatusDeleteRequests    Counter64,
    dpStatusWXSGridStatusCacheHits    Counter64,
    dpStatusWXSGridStatusCacheMisses    Counter64,
    dpStatusWXSGridStatusFailedReadRequests    Counter64,
    dpStatusWXSGridStatusFailedWriteRequests    Counter64,
    dpStatusWXSGridStatusFailedDeleteRequests    Counter64
}

dpStatusWXSGridStatusWXSGrid OBJECT-TYPE
    SYNTAX      DisplayString
    MAX-ACCESS  read-only
    STATUS      current
    DESCRIPTION
        "Name of the eXtreme Scale Grid."

    ::= { dpStatusWXSGridStatusEntry 1 }

dpStatusWXSGridStatusReadRequests OBJECT-TYPE
    SYNTAX      Counter64
    MAX-ACCESS  read-only
    STATUS      current
    DESCRIPTION
        "Number of read requests to this grid."

    ::= { dpStatusWXSGridStatusEntry 2 }

dpStatusWXSGridStatusWriteRequests OBJECT-TYPE
    SYNTAX      Counter64
    MAX-ACCESS  read-only
    STATUS      current
    DESCRIPTION
        "Number of write requests to this grid."

    ::= { dpStatusWXSGridStatusEntry 3 }

dpStatusWXSGridStatusDeleteRequests OBJECT-TYPE
    SYNTAX      Counter64
    MAX-ACCESS  read-only
    STATUS      current
    DESCRIPTION
        "Number of delete requests to this grid."

    ::= { dpStatusWXSGridStatusEntry 4 }

dpStatusWXSGridStatusCacheHits OBJECT-TYPE
    SYNTAX      Counter64
    MAX-ACCESS  read-only
    STATUS      current
    DESCRIPTION
        "Number of requests served by this grid."

    ::= { dpStatusWXSGridStatusEntry 5 }

dpStatusWXSGridStatusCacheMisses OBJECT-TYPE
    SYNTAX      Counter64
    MAX-ACCESS  read-only
    STATUS      current
    DESCRIPTION
        "Number of requests unable to be served by this grid."

    ::= { dpStatusWXSGridStatusEntry 6 }

dpStatusWXSGridStatusFailedReadRequests OBJECT-TYPE
    SYNTAX      Counter64
    MAX-ACCESS  read-only
    STATUS      current
    DESCRIPTION
        "Number of failed read requests to this grid."

    ::= { dpStatusWXSGridStatusEntry 7 }

dpStatusWXSGridStatusFailedWriteRequests OBJECT-TYPE
    SYNTAX      Counter64
    MAX-ACCESS  read-only
    STATUS      current
    DESCRIPTION
        "Number of failed write requests to this grid."

    ::= { dpStatusWXSGridStatusEntry 8 }

dpStatusWXSGridStatusFailedDeleteRequests OBJECT-TYPE
    SYNTAX      Counter64
    MAX-ACCESS  read-only
    STATUS      current
    DESCRIPTION
        "Number of failed delete requests to this grid."

    ::= { dpStatusWXSGridStatusEntry 9 }

dpStatusDateTimeStatus2 OBJECT IDENTIFIER ::= { dpStatus 353 }

dpStatusDateTimeStatus2time OBJECT-TYPE
    SYNTAX      TimeStamp
    MAX-ACCESS  read-only
    STATUS      deprecated
    DESCRIPTION
        "The current local time. This time is obtained from the timezone settings
        established on the Time Settings object and with the date and time
        settings set on the System Control page."

    ::= { dpStatusDateTimeStatus2 1 }

dpStatusDateTimeStatus2timezone OBJECT-TYPE
    SYNTAX      DisplayString
    MAX-ACCESS  read-only
    STATUS      deprecated
    DESCRIPTION
        "The name of the time zone currently in effect, as set on the Time Settings
        page."

    ::= { dpStatusDateTimeStatus2 2 }

dpStatusDateTimeStatus2tzspec OBJECT-TYPE
    SYNTAX      DisplayString
    MAX-ACCESS  read-only
    STATUS      deprecated
    DESCRIPTION
        "The POSIX.1 timezone specification. See time settings for more
        information."

    ::= { dpStatusDateTimeStatus2 3 }

dpStatusDateTimeStatus2uptime3 OBJECT-TYPE
    SYNTAX      TimeTicks
    MAX-ACCESS  read-only
    STATUS      deprecated
    DESCRIPTION
        "The total amount of time the appliance has been up since the last reload
        or reboot. Note that a shutdown and reload resets this counter."

    ::= { dpStatusDateTimeStatus2 4 }

dpStatusDateTimeStatus2bootuptime3 OBJECT-TYPE
    SYNTAX      TimeTicks
    MAX-ACCESS  read-only
    STATUS      deprecated
    DESCRIPTION
        "The total amount of time in seconds since the last reboot. Note that this
        counter is reset by a shutdown and reboot , but not by a shutdown and
        reload ."

    ::= { dpStatusDateTimeStatus2 5 }

--

dpStatusDNSCacheHostStatus3Table OBJECT-TYPE
    SYNTAX      SEQUENCE OF DPStatusDNSCacheHostStatus3Entry
    MAX-ACCESS  not-accessible
    STATUS      obsolete
    DESCRIPTION
        "The host name/IP address pairs that are currently stored in the DNS cache.
        A new entry is stored each time DataPower successfully looks up a host
        name on a DNS server. The name can be either fully qualified (for example,
        servername.uk.ibm.com ), or a partial host name (for example, servername
        ).
        Note: this is obsoleted and is replaced by dpStatusDNSCacheHostStatus4 as of release 7.5.0.0"

    ::= { dpStatus 401 }

dpStatusDNSCacheHostStatus3Entry OBJECT-TYPE
    SYNTAX      DPStatusDNSCacheHostStatus3Entry
    MAX-ACCESS  not-accessible
    STATUS      obsolete
    DESCRIPTION "Table row."
    INDEX { dpStatusDNSCacheHostStatus3Hostname, dpStatusDNSCacheHostStatus3IPVersion, dpStatusDNSCacheHostStatus3IPAddress }

    ::= { dpStatusDNSCacheHostStatus3Table 1 }

DPStatusDNSCacheHostStatus3Entry ::= SEQUENCE {
    dpStatusDNSCacheHostStatus3Hostname    DisplayString,
    dpStatusDNSCacheHostStatus3IPVersion    InetAddressType,
    dpStatusDNSCacheHostStatus3IPAddress    InetAddress,
    dpStatusDNSCacheHostStatus3TTL    DPTimeIntervalSeconds,
    dpStatusDNSCacheHostStatus3IPPref    DisplayString
}

dpStatusDNSCacheHostStatus3Hostname OBJECT-TYPE
    SYNTAX      DisplayString
    MAX-ACCESS  read-only
    STATUS      obsolete
    DESCRIPTION
        "The host name that the appliance located on a configured DNS server using
        a configured DNS search domain."

    ::= { dpStatusDNSCacheHostStatus3Entry 1 }

dpStatusDNSCacheHostStatus3IPVersion OBJECT-TYPE
    SYNTAX      InetAddressType
    MAX-ACCESS  read-only
    STATUS      obsolete
    DESCRIPTION
        "The version of the IP address: ipv4 or ipv6."

    ::= { dpStatusDNSCacheHostStatus3Entry 2 }

dpStatusDNSCacheHostStatus3IPAddress OBJECT-TYPE
    SYNTAX      InetAddress
    MAX-ACCESS  read-only
    STATUS      obsolete
    DESCRIPTION
        "The numeric IP address corresponding to the given host name."

    ::= { dpStatusDNSCacheHostStatus3Entry 3 }

dpStatusDNSCacheHostStatus3TTL OBJECT-TYPE
    SYNTAX      DPTimeIntervalSeconds
    MAX-ACCESS  read-only
    STATUS      obsolete
    DESCRIPTION
        "The time to live that the DNS server provided for the host name."

    ::= { dpStatusDNSCacheHostStatus3Entry 4 }

dpStatusDNSCacheHostStatus3IPPref OBJECT-TYPE
    SYNTAX      DisplayString
    MAX-ACCESS  read-only
    STATUS      obsolete
    DESCRIPTION
        "The preferred IP address version."

    ::= { dpStatusDNSCacheHostStatus3Entry 5 }

--

dpStatusAuthCookieCacheStatusTable OBJECT-TYPE
    SYNTAX      SEQUENCE OF DPStatusAuthCookieCacheStatusEntry
    MAX-ACCESS  not-accessible
    STATUS      current
    DESCRIPTION
        "List of AuthCookie cache entries"

    ::= { dpStatus 402 }

dpStatusAuthCookieCacheStatusEntry OBJECT-TYPE
    SYNTAX      DPStatusAuthCookieCacheStatusEntry
    MAX-ACCESS  not-accessible
    STATUS      current
    DESCRIPTION "Table row."
    INDEX { dpStatusAuthCookieCacheStatusKey, dpStatusAuthCookieCacheStatusOwner, IMPLIED dpStatusAuthCookieCacheStatusDomain }

    ::= { dpStatusAuthCookieCacheStatusTable 1 }

DPStatusAuthCookieCacheStatusEntry ::= SEQUENCE {
    dpStatusAuthCookieCacheStatusKey    DisplayString,
    dpStatusAuthCookieCacheStatusValue    DisplayString,
    dpStatusAuthCookieCacheStatusExpiration    TimeStamp,
    dpStatusAuthCookieCacheStatusOwner    DisplayString,
    dpStatusAuthCookieCacheStatusDomain    DisplayString
}

dpStatusAuthCookieCacheStatusKey OBJECT-TYPE
    SYNTAX      DisplayString
    MAX-ACCESS  read-only
    STATUS      current
    DESCRIPTION
        "Hashed key for the cache entry"

    ::= { dpStatusAuthCookieCacheStatusEntry 1 }

dpStatusAuthCookieCacheStatusValue OBJECT-TYPE
    SYNTAX      DisplayString
    MAX-ACCESS  read-only
    STATUS      current
    DESCRIPTION
        "Data value stored in this entry"

    ::= { dpStatusAuthCookieCacheStatusEntry 2 }

dpStatusAuthCookieCacheStatusExpiration OBJECT-TYPE
    SYNTAX      TimeStamp
    MAX-ACCESS  read-only
    STATUS      current
    DESCRIPTION
        "When this cache entry expires"

    ::= { dpStatusAuthCookieCacheStatusEntry 3 }

dpStatusAuthCookieCacheStatusOwner OBJECT-TYPE
    SYNTAX      DisplayString
    MAX-ACCESS  read-only
    STATUS      current
    DESCRIPTION
        "Type of object that owns this cache entry"

    ::= { dpStatusAuthCookieCacheStatusEntry 4 }

dpStatusAuthCookieCacheStatusDomain OBJECT-TYPE
    SYNTAX      DisplayString
    MAX-ACCESS  read-only
    STATUS      current
    DESCRIPTION
        "Domain where this cache entry was created"

    ::= { dpStatusAuthCookieCacheStatusEntry 5 }

--

dpStatusDNSCacheHostStatus4Table OBJECT-TYPE
    SYNTAX      SEQUENCE OF DPStatusDNSCacheHostStatus4Entry
    MAX-ACCESS  not-accessible
    STATUS      current
    DESCRIPTION
        "The host name/IP address pairs that are currently stored in the DNS cache.
        A new entry is stored each time DataPower successfully looks up a host
        name on a DNS server. The name can be either fully qualified (for example,
        servername.uk.ibm.com ), or a partial host name (for example, servername
        )."

    ::= { dpStatus 403 }

dpStatusDNSCacheHostStatus4Entry OBJECT-TYPE
    SYNTAX      DPStatusDNSCacheHostStatus4Entry
    MAX-ACCESS  not-accessible
    STATUS      current
    DESCRIPTION "Table row."
    INDEX { dpStatusDNSCacheHostStatus4Hostname, dpStatusDNSCacheHostStatus4IPVersion, dpStatusDNSCacheHostStatus4IPAddress, IMPLIED dpStatusDNSCacheHostStatus4IPPref }

    ::= { dpStatusDNSCacheHostStatus4Table 1 }

DPStatusDNSCacheHostStatus4Entry ::= SEQUENCE {
    dpStatusDNSCacheHostStatus4Hostname    DisplayString,
    dpStatusDNSCacheHostStatus4IPVersion    InetAddressType,
    dpStatusDNSCacheHostStatus4IPAddress    InetAddress,
    dpStatusDNSCacheHostStatus4IPPref    DisplayString,
    dpStatusDNSCacheHostStatus4TTL    DPTimeIntervalSeconds
}

dpStatusDNSCacheHostStatus4Hostname OBJECT-TYPE
    SYNTAX      DisplayString
    MAX-ACCESS  read-only
    STATUS      current
    DESCRIPTION
        "The host name that the appliance located on a configured DNS server using
        a configured DNS search domain."

    ::= { dpStatusDNSCacheHostStatus4Entry 1 }

dpStatusDNSCacheHostStatus4IPVersion OBJECT-TYPE
    SYNTAX      InetAddressType
    MAX-ACCESS  read-only
    STATUS      current
    DESCRIPTION
        "The version of the IP address: ipv4 or ipv6."

    ::= { dpStatusDNSCacheHostStatus4Entry 2 }

dpStatusDNSCacheHostStatus4IPAddress OBJECT-TYPE
    SYNTAX      InetAddress
    MAX-ACCESS  read-only
    STATUS      current
    DESCRIPTION
        "The numeric IP address corresponding to the given host name."

    ::= { dpStatusDNSCacheHostStatus4Entry 3 }

dpStatusDNSCacheHostStatus4IPPref OBJECT-TYPE
    SYNTAX      DisplayString
    MAX-ACCESS  read-only
    STATUS      current
    DESCRIPTION
        "The preferred IP address version."

    ::= { dpStatusDNSCacheHostStatus4Entry 4 }

dpStatusDNSCacheHostStatus4TTL OBJECT-TYPE
    SYNTAX      DPTimeIntervalSeconds
    MAX-ACCESS  read-only
    STATUS      current
    DESCRIPTION
        "The time to live that the DNS server provided for the host name."

    ::= { dpStatusDNSCacheHostStatus4Entry 5 }

dpStatusQuotaEnforcementStatus OBJECT IDENTIFIER ::= { dpStatus 506 }

dpStatusQuotaEnforcementStatusState OBJECT-TYPE
    SYNTAX      DisplayString
    MAX-ACCESS  read-only
    STATUS      current
    DESCRIPTION
        "Lists the operational state of the quota enforcement server. The
        operational state is up or down."

    ::= { dpStatusQuotaEnforcementStatus 1 }

dpStatusQuotaEnforcementStatusMode OBJECT-TYPE
    SYNTAX      DisplayString
    MAX-ACCESS  read-only
    STATUS      current
    DESCRIPTION
        "Lists the mode that the quota enforcement server works in. The mode is
        standalone or peer group."

    ::= { dpStatusQuotaEnforcementStatus 2 }

dpStatusQuotaEnforcementStatusRole OBJECT-TYPE
    SYNTAX      DisplayString
    MAX-ACCESS  read-only
    STATUS      current
    DESCRIPTION
        "Lists the role that the appliance plays. The role is master or slave."

    ::= { dpStatusQuotaEnforcementStatus 3 }

dpStatusQuotaEnforcementStatusMaster OBJECT-TYPE
    SYNTAX      DisplayString
    MAX-ACCESS  read-only
    STATUS      current
    DESCRIPTION
        "Lists the IP address of the master in the peer group that the appliance
        belongs to. When the quota enforcement server is in standalone mode, the
        master information is not available."

    ::= { dpStatusQuotaEnforcementStatus 4 }

dpStatusQuotaEnforcementStatusConnectedSlaves OBJECT-TYPE
    SYNTAX      DisplayString
    MAX-ACCESS  read-only
    STATUS      current
    DESCRIPTION
        "Lists the number of slaves that the master is connected with. When the
        appliance is slave, the value is zero."

    ::= { dpStatusQuotaEnforcementStatus 5 }

dpStatusQuotaEnforcementStatusSize OBJECT-TYPE
    SYNTAX      DisplayString
    MAX-ACCESS  read-only
    STATUS      current
    DESCRIPTION
        "Lists the size of database in persistent storage. The unit is byte."

    ::= { dpStatusQuotaEnforcementStatus 6 }

dpStatusQuotaEnforcementStatusKeys OBJECT-TYPE
    SYNTAX      DisplayString
    MAX-ACCESS  read-only
    STATUS      current
    DESCRIPTION
        "Lists the total number of keys in database in persistent storage. Each key
        represents a threshold defined for the specific traffic type."

    ::= { dpStatusQuotaEnforcementStatus 7 }

--

dpStatusRateLimitRateStatusTable OBJECT-TYPE
    SYNTAX      SEQUENCE OF DPStatusRateLimitRateStatusEntry
    MAX-ACCESS  not-accessible
    STATUS      current
    DESCRIPTION
        "Displays the quota enforcement rate-based threshold status for the
        DataPower Gateway."

    ::= { dpStatus 507 }

dpStatusRateLimitRateStatusEntry OBJECT-TYPE
    SYNTAX      DPStatusRateLimitRateStatusEntry
    MAX-ACCESS  not-accessible
    STATUS      current
    DESCRIPTION "Table row."
    INDEX { IMPLIED dpStatusRateLimitRateStatusKeyName }

    ::= { dpStatusRateLimitRateStatusTable 1 }

DPStatusRateLimitRateStatusEntry ::= SEQUENCE {
    dpStatusRateLimitRateStatusKeyName    DisplayString,
    dpStatusRateLimitRateStatusIntervalType    DisplayString,
    dpStatusRateLimitRateStatusIntervalStart    DisplayString,
    dpStatusRateLimitRateStatusIntervalLength    DisplayString,
    dpStatusRateLimitRateStatusThresholdValue    DisplayString,
    dpStatusRateLimitRateStatusThresholdLevel    DisplayString,
    dpStatusRateLimitRateStatusExpiration    DisplayString
}

dpStatusRateLimitRateStatusKeyName OBJECT-TYPE
    SYNTAX      DisplayString
    MAX-ACCESS  read-only
    STATUS      current
    DESCRIPTION
        "Lists the key name that identifies the rate-based threshold."

    ::= { dpStatusRateLimitRateStatusEntry 1 }

dpStatusRateLimitRateStatusIntervalType OBJECT-TYPE
    SYNTAX      DisplayString
    MAX-ACCESS  read-only
    STATUS      current
    DESCRIPTION
        "Lists the interval type. The type is fixed or rolling."

    ::= { dpStatusRateLimitRateStatusEntry 2 }

dpStatusRateLimitRateStatusIntervalStart OBJECT-TYPE
    SYNTAX      DisplayString
    MAX-ACCESS  read-only
    STATUS      current
    DESCRIPTION
        "Lists the starting time of the interval."

    ::= { dpStatusRateLimitRateStatusEntry 3 }

dpStatusRateLimitRateStatusIntervalLength OBJECT-TYPE
    SYNTAX      DisplayString
    UNITS       "Seconds"
    MAX-ACCESS  read-only
    STATUS      current
    DESCRIPTION
        "Lists the interval between quota enforcements."

    ::= { dpStatusRateLimitRateStatusEntry 4 }

dpStatusRateLimitRateStatusThresholdValue OBJECT-TYPE
    SYNTAX      DisplayString
    MAX-ACCESS  read-only
    STATUS      current
    DESCRIPTION
        "Lists the number of remaining tokens in the current interval."

    ::= { dpStatusRateLimitRateStatusEntry 5 }

dpStatusRateLimitRateStatusThresholdLevel OBJECT-TYPE
    SYNTAX      DisplayString
    MAX-ACCESS  read-only
    STATUS      current
    DESCRIPTION
        "Lists the maximum number of tokens that can be requested per interval."

    ::= { dpStatusRateLimitRateStatusEntry 6 }

dpStatusRateLimitRateStatusExpiration OBJECT-TYPE
    SYNTAX      DisplayString
    MAX-ACCESS  read-only
    STATUS      current
    DESCRIPTION
        "Lists the expiration time of the key."

    ::= { dpStatusRateLimitRateStatusEntry 7 }

--

dpStatusRateLimitTokenBucketStatusTable OBJECT-TYPE
    SYNTAX      SEQUENCE OF DPStatusRateLimitTokenBucketStatusEntry
    MAX-ACCESS  not-accessible
    STATUS      current
    DESCRIPTION
        "Displays the quota enforcement token bucket threshold status for the
        DataPower Gateway."

    ::= { dpStatus 508 }

dpStatusRateLimitTokenBucketStatusEntry OBJECT-TYPE
    SYNTAX      DPStatusRateLimitTokenBucketStatusEntry
    MAX-ACCESS  not-accessible
    STATUS      current
    DESCRIPTION "Table row."
    INDEX { IMPLIED dpStatusRateLimitTokenBucketStatusKeyName }

    ::= { dpStatusRateLimitTokenBucketStatusTable 1 }

DPStatusRateLimitTokenBucketStatusEntry ::= SEQUENCE {
    dpStatusRateLimitTokenBucketStatusKeyName    DisplayString,
    dpStatusRateLimitTokenBucketStatusIntervalType    DisplayString,
    dpStatusRateLimitTokenBucketStatusIntervalStart    DisplayString,
    dpStatusRateLimitTokenBucketStatusIntervalLength    DisplayString,
    dpStatusRateLimitTokenBucketStatusIntervalLevel    DisplayString,
    dpStatusRateLimitTokenBucketStatusThresholdValue    DisplayString,
    dpStatusRateLimitTokenBucketStatusThresholdLevel    DisplayString,
    dpStatusRateLimitTokenBucketStatusExpiration    DisplayString
}

dpStatusRateLimitTokenBucketStatusKeyName OBJECT-TYPE
    SYNTAX      DisplayString
    MAX-ACCESS  read-only
    STATUS      current
    DESCRIPTION
        "Lists the key namethat identifies the token bucket threshold."

    ::= { dpStatusRateLimitTokenBucketStatusEntry 1 }

dpStatusRateLimitTokenBucketStatusIntervalType OBJECT-TYPE
    SYNTAX      DisplayString
    MAX-ACCESS  read-only
    STATUS      current
    DESCRIPTION
        "Lists the interval type. The type is fixed or rolling."

    ::= { dpStatusRateLimitTokenBucketStatusEntry 2 }

dpStatusRateLimitTokenBucketStatusIntervalStart OBJECT-TYPE
    SYNTAX      DisplayString
    MAX-ACCESS  read-only
    STATUS      current
    DESCRIPTION
        "Lists the starting time of the interval."

    ::= { dpStatusRateLimitTokenBucketStatusEntry 3 }

dpStatusRateLimitTokenBucketStatusIntervalLength OBJECT-TYPE
    SYNTAX      DisplayString
    UNITS       "Seconds"
    MAX-ACCESS  read-only
    STATUS      current
    DESCRIPTION
        "Lists the interval between quota enforcements."

    ::= { dpStatusRateLimitTokenBucketStatusEntry 4 }

dpStatusRateLimitTokenBucketStatusIntervalLevel OBJECT-TYPE
    SYNTAX      DisplayString
    MAX-ACCESS  read-only
    STATUS      current
    DESCRIPTION
        "Lists the number of tokens that refill the bucket per interval."

    ::= { dpStatusRateLimitTokenBucketStatusEntry 5 }

dpStatusRateLimitTokenBucketStatusThresholdValue OBJECT-TYPE
    SYNTAX      DisplayString
    MAX-ACCESS  read-only
    STATUS      current
    DESCRIPTION
        "Lists the number of remaining tokens in the current interval."

    ::= { dpStatusRateLimitTokenBucketStatusEntry 6 }

dpStatusRateLimitTokenBucketStatusThresholdLevel OBJECT-TYPE
    SYNTAX      DisplayString
    MAX-ACCESS  read-only
    STATUS      current
    DESCRIPTION
        "Lists the maximum number of tokens that a bucket can contain."

    ::= { dpStatusRateLimitTokenBucketStatusEntry 7 }

dpStatusRateLimitTokenBucketStatusExpiration OBJECT-TYPE
    SYNTAX      DisplayString
    MAX-ACCESS  read-only
    STATUS      current
    DESCRIPTION
        "Lists the expiration time of the key."

    ::= { dpStatusRateLimitTokenBucketStatusEntry 8 }

--

dpStatusRateLimitCountStatusTable OBJECT-TYPE
    SYNTAX      SEQUENCE OF DPStatusRateLimitCountStatusEntry
    MAX-ACCESS  not-accessible
    STATUS      current
    DESCRIPTION
        "Displays the quota enforcement counter status for the DataPower Gateway."

    ::= { dpStatus 509 }

dpStatusRateLimitCountStatusEntry OBJECT-TYPE
    SYNTAX      DPStatusRateLimitCountStatusEntry
    MAX-ACCESS  not-accessible
    STATUS      current
    DESCRIPTION "Table row."
    INDEX { IMPLIED dpStatusRateLimitCountStatusKeyName }

    ::= { dpStatusRateLimitCountStatusTable 1 }

DPStatusRateLimitCountStatusEntry ::= SEQUENCE {
    dpStatusRateLimitCountStatusKeyName    DisplayString,
    dpStatusRateLimitCountStatusThresholdValue    DisplayString
}

dpStatusRateLimitCountStatusKeyName OBJECT-TYPE
    SYNTAX      DisplayString
    MAX-ACCESS  read-only
    STATUS      current
    DESCRIPTION
        "Lists the key name that identifies the counter."

    ::= { dpStatusRateLimitCountStatusEntry 1 }

dpStatusRateLimitCountStatusThresholdValue OBJECT-TYPE
    SYNTAX      DisplayString
    MAX-ACCESS  read-only
    STATUS      current
    DESCRIPTION
        "Lists the current counter value."

    ::= { dpStatusRateLimitCountStatusEntry 2 }

--

dpStatusRateLimitConcurrentStatusTable OBJECT-TYPE
    SYNTAX      SEQUENCE OF DPStatusRateLimitConcurrentStatusEntry
    MAX-ACCESS  not-accessible
    STATUS      current
    DESCRIPTION
        "Displays the quota enforcement concurrent transactions status for the
        DataPower Gateway."

    ::= { dpStatus 510 }

dpStatusRateLimitConcurrentStatusEntry OBJECT-TYPE
    SYNTAX      DPStatusRateLimitConcurrentStatusEntry
    MAX-ACCESS  not-accessible
    STATUS      current
    DESCRIPTION "Table row."
    INDEX { IMPLIED dpStatusRateLimitConcurrentStatusKeyName }

    ::= { dpStatusRateLimitConcurrentStatusTable 1 }

DPStatusRateLimitConcurrentStatusEntry ::= SEQUENCE {
    dpStatusRateLimitConcurrentStatusKeyName    DisplayString,
    dpStatusRateLimitConcurrentStatusThresholdValue    DisplayString,
    dpStatusRateLimitConcurrentStatusPeakThresholdValue    DisplayString
}

dpStatusRateLimitConcurrentStatusKeyName OBJECT-TYPE
    SYNTAX      DisplayString
    MAX-ACCESS  read-only
    STATUS      current
    DESCRIPTION
        "Lists the key name that identifies concurrent transactions."

    ::= { dpStatusRateLimitConcurrentStatusEntry 1 }

dpStatusRateLimitConcurrentStatusThresholdValue OBJECT-TYPE
    SYNTAX      DisplayString
    MAX-ACCESS  read-only
    STATUS      current
    DESCRIPTION
        "Lists the current counter value for concurrent transactions."

    ::= { dpStatusRateLimitConcurrentStatusEntry 2 }

dpStatusRateLimitConcurrentStatusPeakThresholdValue OBJECT-TYPE
    SYNTAX      DisplayString
    MAX-ACCESS  read-only
    STATUS      current
    DESCRIPTION
        "Lists the highest counter value for concurrent transactions since the
        GatewayScript ratelimit module was called."

    ::= { dpStatusRateLimitConcurrentStatusEntry 3 }

--

dpStatusGatewayPeeringStatusTable OBJECT-TYPE
    SYNTAX      SEQUENCE OF DPStatusGatewayPeeringStatusEntry
    MAX-ACCESS  not-accessible
    STATUS      current
    DESCRIPTION
        "Displays the list of peer members and their individual status."

    ::= { dpStatus 513 }

dpStatusGatewayPeeringStatusEntry OBJECT-TYPE
    SYNTAX      DPStatusGatewayPeeringStatusEntry
    MAX-ACCESS  not-accessible
    STATUS      current
    DESCRIPTION "Table row."
    INDEX { dpStatusGatewayPeeringStatusAddress, IMPLIED dpStatusGatewayPeeringStatusName }

    ::= { dpStatusGatewayPeeringStatusTable 1 }

DPStatusGatewayPeeringStatusEntry ::= SEQUENCE {
    dpStatusGatewayPeeringStatusAddress    IpAddress,
    dpStatusGatewayPeeringStatusName    DisplayString,
    dpStatusGatewayPeeringStatusPendingUpdates    Unsigned32,
    dpStatusGatewayPeeringStatusReplicationOffset    Counter64,
    dpStatusGatewayPeeringStatusLinkStatus    INTEGER,
    dpStatusGatewayPeeringStatusPrimary    INTEGER
}

dpStatusGatewayPeeringStatusAddress OBJECT-TYPE
    SYNTAX      IpAddress
    MAX-ACCESS  read-only
    STATUS      current
    DESCRIPTION
        "The IP address that identifies the member in a peer group."

    ::= { dpStatusGatewayPeeringStatusEntry 1 }

dpStatusGatewayPeeringStatusName OBJECT-TYPE
    SYNTAX      DisplayString
    MAX-ACCESS  read-only
    STATUS      current
    DESCRIPTION
        "The name of the gateway Peering configuration that defines the member."

    ::= { dpStatusGatewayPeeringStatusEntry 2 }

dpStatusGatewayPeeringStatusPendingUpdates OBJECT-TYPE
    SYNTAX      Unsigned32
    MAX-ACCESS  read-only
    STATUS      current
    DESCRIPTION
        "Number of outstanding commands on this member."

    ::= { dpStatusGatewayPeeringStatusEntry 3 }

dpStatusGatewayPeeringStatusReplicationOffset OBJECT-TYPE
    SYNTAX      Counter64
    MAX-ACCESS  read-only
    STATUS      current
    DESCRIPTION
        "The replication offset of a member will match the offset of the primary
        when they share the same data replication. #b#Note:#/b# Data is replicated
        asynchronously as a constant stream of updates, so small deltas are
        expected between each of the members in the peer group."

    ::= { dpStatusGatewayPeeringStatusEntry 4 }

dpStatusGatewayPeeringStatusLinkStatus OBJECT-TYPE
    SYNTAX      INTEGER { 
                        ok(1),
                        down(2)
                }
    MAX-ACCESS  read-only
    STATUS      current
    DESCRIPTION
        "Healthiness of the network connection from this member to the primary."

    ::= { dpStatusGatewayPeeringStatusEntry 5 }

dpStatusGatewayPeeringStatusPrimary OBJECT-TYPE
    SYNTAX      INTEGER { 
                        yes(1),
                        no(2),
                        unknown(3)
                }
    MAX-ACCESS  read-only
    STATUS      current
    DESCRIPTION
        "Whether this member is primary in the peer group."

    ::= { dpStatusGatewayPeeringStatusEntry 6 }

--

dpStatusB2BMPCStatusTable OBJECT-TYPE
    SYNTAX      SEQUENCE OF DPStatusB2BMPCStatusEntry
    MAX-ACCESS  not-accessible
    STATUS      obsolete
    DESCRIPTION
        "Deprecated due to incomplete support for authentication with certificates.
        Displays the status of the ebMS message partition channels (MPCs) for the
        DataPower Gateway.
        Note: this is obsoleted and is replaced by dpStatusB2BMPCStatus2 as of release 7.5.2"

    ::= { dpStatus 520 }

dpStatusB2BMPCStatusEntry OBJECT-TYPE
    SYNTAX      DPStatusB2BMPCStatusEntry
    MAX-ACCESS  not-accessible
    STATUS      obsolete
    DESCRIPTION "Table row."
    INDEX { dpStatusB2BMPCStatusSubmitTransID, dpStatusB2BMPCStatusMPCName, dpStatusB2BMPCStatusUserName, dpStatusB2BMPCStatusSenderName, dpStatusB2BMPCStatusReceiverName, dpStatusB2BMPCStatusSubmitTime, dpStatusB2BMPCStatusSentTime, IMPLIED dpStatusB2BMPCStatusMessageStatus }

    ::= { dpStatusB2BMPCStatusTable 1 }

DPStatusB2BMPCStatusEntry ::= SEQUENCE {
    dpStatusB2BMPCStatusSubmitTransID    Integer32,
    dpStatusB2BMPCStatusMPCName    DisplayString,
    dpStatusB2BMPCStatusUserName    DisplayString,
    dpStatusB2BMPCStatusSenderName    DisplayString,
    dpStatusB2BMPCStatusReceiverName    DisplayString,
    dpStatusB2BMPCStatusSubmitTime    DisplayString,
    dpStatusB2BMPCStatusSentTime    DisplayString,
    dpStatusB2BMPCStatusMessageStatus    DisplayString
}

dpStatusB2BMPCStatusSubmitTransID OBJECT-TYPE
    SYNTAX      Integer32 (1..2147483647)
    MAX-ACCESS  read-only
    STATUS      obsolete
    DESCRIPTION
        "Lists the transaction ID of the submit operation for the message."

    ::= { dpStatusB2BMPCStatusEntry 1 }

dpStatusB2BMPCStatusMPCName OBJECT-TYPE
    SYNTAX      DisplayString
    MAX-ACCESS  read-only
    STATUS      obsolete
    DESCRIPTION
        "Lists the name of the MPC where the message payload is submitted."

    ::= { dpStatusB2BMPCStatusEntry 2 }

dpStatusB2BMPCStatusUserName OBJECT-TYPE
    SYNTAX      DisplayString
    MAX-ACCESS  read-only
    STATUS      obsolete
    DESCRIPTION
        "Lists the user name that is associated with the message."

    ::= { dpStatusB2BMPCStatusEntry 3 }

dpStatusB2BMPCStatusSenderName OBJECT-TYPE
    SYNTAX      DisplayString
    MAX-ACCESS  read-only
    STATUS      obsolete
    DESCRIPTION
        "Lists the name and ID of the B2B message sender."

    ::= { dpStatusB2BMPCStatusEntry 4 }

dpStatusB2BMPCStatusReceiverName OBJECT-TYPE
    SYNTAX      DisplayString
    MAX-ACCESS  read-only
    STATUS      obsolete
    DESCRIPTION
        "Lists the name and ID of the B2B message receiver."

    ::= { dpStatusB2BMPCStatusEntry 5 }

dpStatusB2BMPCStatusSubmitTime OBJECT-TYPE
    SYNTAX      DisplayString
    MAX-ACCESS  read-only
    STATUS      obsolete
    DESCRIPTION
        "Lists the time when the message is submitted to the MPC."

    ::= { dpStatusB2BMPCStatusEntry 6 }

dpStatusB2BMPCStatusSentTime OBJECT-TYPE
    SYNTAX      DisplayString
    MAX-ACCESS  read-only
    STATUS      obsolete
    DESCRIPTION
        "Lists the time when the message is sent to the B2B message receiver."

    ::= { dpStatusB2BMPCStatusEntry 7 }

dpStatusB2BMPCStatusMessageStatus OBJECT-TYPE
    SYNTAX      DisplayString
    MAX-ACCESS  read-only
    STATUS      obsolete
    DESCRIPTION
        "Lists the status of the messsage. The status can be one of the following:
        Submitted -- The message payload is submitted to the MPC. Pending -- The
        message payload is pulled from MPC and encapsulated into an ebMS message
        that is pending to be sent. Sent -- The ebMS message is sent."

    ::= { dpStatusB2BMPCStatusEntry 8 }

dpStatusTenantLicenses OBJECT IDENTIFIER ::= { dpStatus 523 }

dpStatusTenantLicensesTotalLicenses OBJECT-TYPE
    SYNTAX      Unsigned32
    MAX-ACCESS  read-only
    STATUS      current
    DESCRIPTION
        "Number of tenant that can be installed."

    ::= { dpStatusTenantLicenses 1 }

dpStatusTenantLicensesUsedLicenses OBJECT-TYPE
    SYNTAX      Unsigned32
    MAX-ACCESS  read-only
    STATUS      current
    DESCRIPTION
        "Number of tenants that are installed."

    ::= { dpStatusTenantLicenses 2 }

--

dpStatusB2BMPCStatus2Table OBJECT-TYPE
    SYNTAX      SEQUENCE OF DPStatusB2BMPCStatus2Entry
    MAX-ACCESS  not-accessible
    STATUS      current
    DESCRIPTION
        "Displays the status of the ebMS message partition channels (MPCs) for the
        DataPower Gateway."

    ::= { dpStatus 524 }

dpStatusB2BMPCStatus2Entry OBJECT-TYPE
    SYNTAX      DPStatusB2BMPCStatus2Entry
    MAX-ACCESS  not-accessible
    STATUS      current
    DESCRIPTION "Table row."
    INDEX { dpStatusB2BMPCStatus2SubmitTransID, dpStatusB2BMPCStatus2MPCName, dpStatusB2BMPCStatus2UserName, dpStatusB2BMPCStatus2ValCredName, dpStatusB2BMPCStatus2SenderName, dpStatusB2BMPCStatus2ReceiverName, dpStatusB2BMPCStatus2SubmitTime, dpStatusB2BMPCStatus2SentTime, IMPLIED dpStatusB2BMPCStatus2MessageStatus }

    ::= { dpStatusB2BMPCStatus2Table 1 }

DPStatusB2BMPCStatus2Entry ::= SEQUENCE {
    dpStatusB2BMPCStatus2SubmitTransID    Integer32,
    dpStatusB2BMPCStatus2MPCName    DisplayString,
    dpStatusB2BMPCStatus2UserName    DisplayString,
    dpStatusB2BMPCStatus2ValCredName    DisplayString,
    dpStatusB2BMPCStatus2SenderName    DisplayString,
    dpStatusB2BMPCStatus2ReceiverName    DisplayString,
    dpStatusB2BMPCStatus2SubmitTime    DisplayString,
    dpStatusB2BMPCStatus2SentTime    DisplayString,
    dpStatusB2BMPCStatus2MessageStatus    DisplayString
}

dpStatusB2BMPCStatus2SubmitTransID OBJECT-TYPE
    SYNTAX      Integer32 (1..2147483647)
    MAX-ACCESS  read-only
    STATUS      current
    DESCRIPTION
        "Lists the transaction ID of the submit operation for the message."

    ::= { dpStatusB2BMPCStatus2Entry 1 }

dpStatusB2BMPCStatus2MPCName OBJECT-TYPE
    SYNTAX      DisplayString
    MAX-ACCESS  read-only
    STATUS      current
    DESCRIPTION
        "Lists the name of the MPC where the message payload is submitted."

    ::= { dpStatusB2BMPCStatus2Entry 2 }

dpStatusB2BMPCStatus2UserName OBJECT-TYPE
    SYNTAX      DisplayString
    MAX-ACCESS  read-only
    STATUS      current
    DESCRIPTION
        "Lists the user name that is associated with the message."

    ::= { dpStatusB2BMPCStatus2Entry 3 }

dpStatusB2BMPCStatus2ValCredName OBJECT-TYPE
    SYNTAX      DisplayString
    MAX-ACCESS  read-only
    STATUS      current
    DESCRIPTION
        "Lists the name of the validation credential that is associated with the
        message."

    ::= { dpStatusB2BMPCStatus2Entry 4 }

dpStatusB2BMPCStatus2SenderName OBJECT-TYPE
    SYNTAX      DisplayString
    MAX-ACCESS  read-only
    STATUS      current
    DESCRIPTION
        "Lists the name and ID of the B2B message sender."

    ::= { dpStatusB2BMPCStatus2Entry 5 }

dpStatusB2BMPCStatus2ReceiverName OBJECT-TYPE
    SYNTAX      DisplayString
    MAX-ACCESS  read-only
    STATUS      current
    DESCRIPTION
        "Lists the name and ID of the B2B message receiver."

    ::= { dpStatusB2BMPCStatus2Entry 6 }

dpStatusB2BMPCStatus2SubmitTime OBJECT-TYPE
    SYNTAX      DisplayString
    MAX-ACCESS  read-only
    STATUS      current
    DESCRIPTION
        "Lists the time when the message is submitted to the MPC."

    ::= { dpStatusB2BMPCStatus2Entry 7 }

dpStatusB2BMPCStatus2SentTime OBJECT-TYPE
    SYNTAX      DisplayString
    MAX-ACCESS  read-only
    STATUS      current
    DESCRIPTION
        "Lists the time when the message is sent to the B2B message receiver."

    ::= { dpStatusB2BMPCStatus2Entry 8 }

dpStatusB2BMPCStatus2MessageStatus OBJECT-TYPE
    SYNTAX      DisplayString
    MAX-ACCESS  read-only
    STATUS      current
    DESCRIPTION
        "Lists the status of the messsage. The status can be one of the following:
        Submitted -- The message payload is submitted to the MPC. Pending -- The
        message payload is pulled from MPC and encapsulated into an ebMS message
        that is pending to be sent. Sent -- The ebMS message is sent."

    ::= { dpStatusB2BMPCStatus2Entry 9 }

--

dpStatusFibreChannelVolumeStatusTable OBJECT-TYPE
    SYNTAX      SEQUENCE OF DPStatusFibreChannelVolumeStatusEntry
    MAX-ACCESS  not-accessible
    STATUS      current
    DESCRIPTION
        "Show the status of Fibre Channel volumes."

    ::= { dpStatus 526 }

dpStatusFibreChannelVolumeStatusEntry OBJECT-TYPE
    SYNTAX      DPStatusFibreChannelVolumeStatusEntry
    MAX-ACCESS  not-accessible
    STATUS      current
    DESCRIPTION "Table row."
    INDEX { IMPLIED dpStatusFibreChannelVolumeStatusvolume }

    ::= { dpStatusFibreChannelVolumeStatusTable 1 }

DPStatusFibreChannelVolumeStatusEntry ::= SEQUENCE {
    dpStatusFibreChannelVolumeStatusvolume    DisplayString,
    dpStatusFibreChannelVolumeStatusluid    DisplayString,
    dpStatusFibreChannelVolumeStatusopState    DisplayString,
    dpStatusFibreChannelVolumeStatuslinkStatus    DisplayString
}

dpStatusFibreChannelVolumeStatusvolume OBJECT-TYPE
    SYNTAX      DisplayString
    MAX-ACCESS  read-only
    STATUS      current
    DESCRIPTION
        "Name of the Fibre Channel volume."

    ::= { dpStatusFibreChannelVolumeStatusEntry 1 }

dpStatusFibreChannelVolumeStatusluid OBJECT-TYPE
    SYNTAX      DisplayString
    MAX-ACCESS  read-only
    STATUS      current
    DESCRIPTION
        "Unique LUN ID used by the volume."

    ::= { dpStatusFibreChannelVolumeStatusEntry 2 }

dpStatusFibreChannelVolumeStatusopState OBJECT-TYPE
    SYNTAX      DisplayString
    MAX-ACCESS  read-only
    STATUS      current
    DESCRIPTION
        "Operational state of the volume object."

    ::= { dpStatusFibreChannelVolumeStatusEntry 3 }

dpStatusFibreChannelVolumeStatuslinkStatus OBJECT-TYPE
    SYNTAX      DisplayString
    MAX-ACCESS  read-only
    STATUS      current
    DESCRIPTION
        "Status of the link to the Fibre Channel volume."

    ::= { dpStatusFibreChannelVolumeStatusEntry 4 }

--

dpStatusFibreChannelLunsTable OBJECT-TYPE
    SYNTAX      SEQUENCE OF DPStatusFibreChannelLunsEntry
    MAX-ACCESS  not-accessible
    STATUS      current
    DESCRIPTION
        "List of discovered fibre channel LUNs."

    ::= { dpStatus 527 }

dpStatusFibreChannelLunsEntry OBJECT-TYPE
    SYNTAX      DPStatusFibreChannelLunsEntry
    MAX-ACCESS  not-accessible
    STATUS      current
    DESCRIPTION "Table row."
    INDEX { dpStatusFibreChannelLunslun, IMPLIED dpStatusFibreChannelLunswwpn }

    ::= { dpStatusFibreChannelLunsTable 1 }

DPStatusFibreChannelLunsEntry ::= SEQUENCE {
    dpStatusFibreChannelLunsluid    DisplayString,
    dpStatusFibreChannelLunshba    DisplayString,
    dpStatusFibreChannelLunslun    Unsigned32,
    dpStatusFibreChannelLunswwpn    DisplayString
}

dpStatusFibreChannelLunsluid OBJECT-TYPE
    SYNTAX      DisplayString
    MAX-ACCESS  read-only
    STATUS      current
    DESCRIPTION
        "Unique ID of a SAN LUN."

    ::= { dpStatusFibreChannelLunsEntry 1 }

dpStatusFibreChannelLunshba OBJECT-TYPE
    SYNTAX      DisplayString
    MAX-ACCESS  read-only
    STATUS      current
    DESCRIPTION
        "Host Bus Adapter instance."

    ::= { dpStatusFibreChannelLunsEntry 2 }

dpStatusFibreChannelLunslun OBJECT-TYPE
    SYNTAX      Unsigned32
    MAX-ACCESS  read-only
    STATUS      current
    DESCRIPTION
        "Logical unit number assigned by the operating system to the logical unit."

    ::= { dpStatusFibreChannelLunsEntry 3 }

dpStatusFibreChannelLunswwpn OBJECT-TYPE
    SYNTAX      DisplayString
    MAX-ACCESS  read-only
    STATUS      current
    DESCRIPTION
        "World-wide name of the target port to be queried for information about the
        logical unit."

    ::= { dpStatusFibreChannelLunsEntry 4 }

--

dpStatusTenantMemoryTable OBJECT-TYPE
    SYNTAX      SEQUENCE OF DPStatusTenantMemoryEntry
    MAX-ACCESS  not-accessible
    STATUS      current
    DESCRIPTION
        "Information about the memory usage of tenants."

    ::= { dpStatus 528 }

dpStatusTenantMemoryEntry OBJECT-TYPE
    SYNTAX      DPStatusTenantMemoryEntry
    MAX-ACCESS  not-accessible
    STATUS      current
    DESCRIPTION "Table row."
    INDEX { IMPLIED dpStatusTenantMemoryName }

    ::= { dpStatusTenantMemoryTable 1 }

DPStatusTenantMemoryEntry ::= SEQUENCE {
    dpStatusTenantMemoryName    DisplayString,
    dpStatusTenantMemoryLimit    DisplayString,
    dpStatusTenantMemoryUsage    DisplayString,
    dpStatusTenantMemoryPercentUsage    DisplayString,
    dpStatusTenantMemoryMaxUsage    DisplayString,
    dpStatusTenantMemoryMaxPercentUsage    DisplayString,
    dpStatusTenantMemoryAdminState    DisplayString
}

dpStatusTenantMemoryName OBJECT-TYPE
    SYNTAX      DisplayString
    MAX-ACCESS  read-only
    STATUS      current
    DESCRIPTION
        "The name of the tenant."

    ::= { dpStatusTenantMemoryEntry 1 }

dpStatusTenantMemoryLimit OBJECT-TYPE
    SYNTAX      DisplayString
    UNITS       "bytes"
    MAX-ACCESS  read-only
    STATUS      current
    DESCRIPTION
        "The total memory allocated to the landlord and tenants in bytes."

    ::= { dpStatusTenantMemoryEntry 2 }

dpStatusTenantMemoryUsage OBJECT-TYPE
    SYNTAX      DisplayString
    UNITS       "bytes"
    MAX-ACCESS  read-only
    STATUS      current
    DESCRIPTION
        "The tenant's current memory usage in bytes."

    ::= { dpStatusTenantMemoryEntry 3 }

dpStatusTenantMemoryPercentUsage OBJECT-TYPE
    SYNTAX      DisplayString
    MAX-ACCESS  read-only
    STATUS      current
    DESCRIPTION
        "The tenant's current memory usage as a percentage of its limit."

    ::= { dpStatusTenantMemoryEntry 4 }

dpStatusTenantMemoryMaxUsage OBJECT-TYPE
    SYNTAX      DisplayString
    UNITS       "bytes"
    MAX-ACCESS  read-only
    STATUS      current
    DESCRIPTION
        "The tenant's maximum allowable memory usage in bytes."

    ::= { dpStatusTenantMemoryEntry 5 }

dpStatusTenantMemoryMaxPercentUsage OBJECT-TYPE
    SYNTAX      DisplayString
    MAX-ACCESS  read-only
    STATUS      current
    DESCRIPTION
        "The tenant's maximum allowable memory usage as a percentage of the limit."

    ::= { dpStatusTenantMemoryEntry 6 }

dpStatusTenantMemoryAdminState OBJECT-TYPE
    SYNTAX      DisplayString
    MAX-ACCESS  read-only
    STATUS      current
    DESCRIPTION
        "Admin state (enabled or disabled) of the tenant."

    ::= { dpStatusTenantMemoryEntry 7 }

END

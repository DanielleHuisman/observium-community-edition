-- ***************************************************************
-- INFINERA-ENTITY-BPP-MIB
--   
-- Jan 2015, Kavitha Manjunatha
--   
--   
-- Copyright (c) 2010-2012 by Infinera Inc.
-- All rights reserved.
-- ****************************************************************

INFINERA-ENTITY-BPP-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    entLPPhysicalIndex                  FROM ENTITY-MIB
    equipment                           FROM INFINERA-REG-MIB
    InfnEqptType                        FROM INFINERA-TC-MIB;

bppMIB MODULE-IDENTITY
    LAST-UPDATED  "201501080000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for BPP equipment table."
        
::= { equipment 48 }

bppConformance       OBJECT IDENTIFIER ::= { bppMIB 3 }
bppCompliances       OBJECT IDENTIFIER ::= { bppConformance 1 }
bppGroups            OBJECT IDENTIFIER ::= { bppConformance 2 }

bppTable  OBJECT-TYPE
    SYNTAX SEQUENCE OF BppEntry
    MAX-ACCESS not-accessible
    STATUS     current
    DESCRIPTION 
        "This table contains all SCM modules that are currently present in a network element.
        "
    ::= { bppMIB 1 }

bppEntry  OBJECT-TYPE
    SYNTAX     BppEntry
    MAX-ACCESS not-accessible
    STATUS     current
    DESCRIPTION 
        "A row in the SCM table. Each row in the table is identified with a unique entPhysicalIndexID. 
        "
    INDEX { entLPPhysicalIndex }
    ::= { bppTable 1 }


BppEntry ::= SEQUENCE {
    bppMoId             DisplayString,
    bppProvEqptType     InfnEqptType,
    bppProvSerialNumber DisplayString
}

bppMoId  OBJECT-TYPE
    SYNTAX     DisplayString
    MAX-ACCESS read-create
    STATUS     current
    DESCRIPTION 
        "This is the primary Key of the objects e.g 1-A-1"
    ::= { bppEntry 1 }

bppProvEqptType  OBJECT-TYPE
    SYNTAX     InfnEqptType
    MAX-ACCESS read-create
    STATUS     current
    DESCRIPTION 
        "User provisioned SCM type."
    ::= { bppEntry 2 }
 
bppProvSerialNumber OBJECT-TYPE
    SYNTAX      DisplayString
    MAX-ACCESS  read-write
    STATUS      current
    DESCRIPTION ""
    ::= { bppEntry 3 }


bppCompliance  MODULE-COMPLIANCE
    STATUS     current
    DESCRIPTION 
        "Describes the requirements for conformance to the BPP-MIB"
    MODULE
        MANDATORY-GROUPS { bppGroup } 
    ::= { bppCompliances 1 }

bppGroup  OBJECT-GROUP
    OBJECTS { 
        bppMoId, 
        bppProvEqptType,
        bppProvSerialNumber
    }
    STATUS     current
    DESCRIPTION 
        " A collection of objects for managing a BPP module"
    ::= { bppGroups 1 }
END

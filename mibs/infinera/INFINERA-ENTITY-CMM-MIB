-- ***************************************************************
-- INFINERA-ENTITY-CMM-MIB
-- Copyright (c) 2008-2012 by Infinera Inc.
-- All rights reserved.
-- ****************************************************************

INFINERA-ENTITY-CMM-MIB DEFINITIONS ::= BEGIN

IMPORTS
    OBJECT-TYPE, MODULE-IDENTITY      FROM SNMPv2-SMI
    OBJECT-GROUP, MODULE-COMPLIANCE   FROM SNMPv2-CONF
    RowStatus, DisplayString          FROM SNMPv2-TC
    entLPPhysicalIndex                FROM ENTITY-MIB
    equipment                         FROM INFINERA-REG-MIB
    InfnEqptType                      FROM INFINERA-TC-MIB;

cmmMIB MODULE-IDENTITY
    LAST-UPDATED  "200810200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for CMM equipment table."
        
::= { equipment 19 }

cmmConformance       OBJECT IDENTIFIER ::= { cmmMIB 14 }
cmmCompliances       OBJECT IDENTIFIER ::= { cmmConformance 1 }
cmmGroups            OBJECT IDENTIFIER ::= { cmmConformance 2 }

cmmTable  OBJECT-TYPE
    SYNTAX SEQUENCE OF CmmEntry
    MAX-ACCESS not-accessible
    STATUS     current
    DESCRIPTION 
        "This table contains all CMM modules that are currently present in a network element.
        "
    ::= { cmmMIB 1 }

cmmEntry  OBJECT-TYPE
    SYNTAX     CmmEntry
    MAX-ACCESS not-accessible
    STATUS     current
    DESCRIPTION 
        "A row in the CMM table. Each row in the table is identified with a unique entPhysicalIndexID. 
        "
    INDEX { entLPPhysicalIndex }
    ::= { cmmTable 1 }

CmmEntry ::= SEQUENCE {
    cmmMoId                        DisplayString,
    cmmProvEqptType                InfnEqptType,
    cmmRowStatus                   RowStatus
}

cmmMoId  OBJECT-TYPE
    SYNTAX     DisplayString
    MAX-ACCESS read-create
    STATUS     current
    DESCRIPTION 
        "This is the primary Key of the objects e.g 1-A-3"
    ::= { cmmEntry 1 }

cmmProvEqptType  OBJECT-TYPE
    SYNTAX     InfnEqptType
    MAX-ACCESS read-create
    STATUS     current
    DESCRIPTION 
        "The configured CMM type."
    ::= { cmmEntry 2 }

    
cmmRowStatus  OBJECT-TYPE
    SYNTAX     RowStatus
    MAX-ACCESS read-create
    STATUS     current
    DESCRIPTION 
        "The row status of this CMM entry.
                Because rows in this table are indexed by entPhysicalIndex, to create a new row one must
                choose a value of entPhysicalIndex that is not already in use.
        
                A side-effect of the creation of a row in this table is the creation of a corresponding
                row in the eqptTable and the entPhysicalTable.
        
                The status may not be set to active if the cmmMoId, cmmProvEqptType,  objects are not set 
                to valid values.
        
                This row may only be deleted if it was a pre-provisioned row and the hardware is not present.
        
                If this row is deleted, the associated row in the Eqpt Table and entPhysicalTable will be
                deleted by the agent."
    ::= { cmmEntry 3 }

cmmCompliance  MODULE-COMPLIANCE
    STATUS     current
    DESCRIPTION 
        ""
    MODULE
        MANDATORY-GROUPS { cmmGroup } 
    ::= { cmmCompliances 1 }

cmmGroup  OBJECT-GROUP
    OBJECTS { 
        cmmMoId, 
        cmmProvEqptType, 
        cmmRowStatus }
    STATUS     current
    DESCRIPTION 
        ""
    ::= { cmmGroups 1 }
END

-- ***************************************************************
-- INFINERA-ENTITY-CWM-MIB
-- Copyright (c) 2008-2017 by Infinera Inc.
-- All rights reserved.
-- ****************************************************************

INFINERA-ENTITY-CWM-MIB DEFINITIONS ::= BEGIN

IMPORTS
    OBJECT-TYPE, MODULE-IDENTITY, Integer32        FROM SNMPv2-SMI
    OBJECT-GROUP, MODULE-COMPLIANCE                FROM SNMPv2-CONF
    TruthValue, DisplayString                      FROM SNMPv2-TC
    entPhysicalIndex                               FROM ENTITY-MIB
    equipment                                      FROM INFINERA-REG-MIB
    InfnEqptType                                   FROM INFINERA-TC-MIB;

cwmMIB MODULE-IDENTITY
    LAST-UPDATED  "201505100000Z"
    ORGANIZATION
        "Infinera"
    CONTACT-INFO
        "Infinera
                1322 Bordeaux Drive
                Sunnyvale, CA - 94089
                Contact : Technical Support
                Email   : support@infinera.com
                Phone   : 1-877-INF-5288"
    DESCRIPTION
        " "
::= { equipment 57 }


-- Conformance Statements

cwmConformance       OBJECT IDENTIFIER ::= { cwmMIB 3 }
cwmCompliances       OBJECT IDENTIFIER ::= { cwmConformance 1 }
cwmGroups            OBJECT IDENTIFIER ::= { cwmConformance 2 }

cwmTable  OBJECT-TYPE
    SYNTAX SEQUENCE OF CwmEntry
    MAX-ACCESS not-accessible
    STATUS     current
    DESCRIPTION
        "A list of CWM entries. Each entry is uniquely identified by the value
                of entPhysicalIndex."
    ::= { cwmMIB 1 }

cwmEntry  OBJECT-TYPE
    SYNTAX     CwmEntry
    MAX-ACCESS not-accessible
    STATUS     current
    DESCRIPTION
        "A CWM entry containing information pertaining to
            Infinera CWM modules. Entries will exist in this table for
            entPhysicalEntries of type CWM."
    INDEX { entPhysicalIndex }
    ::= { cwmTable 1 }

CwmEntry ::= SEQUENCE {
    cwmMoId                      DisplayString,
    cwmProvEqptType              InfnEqptType,
    cwmAssociatedDegree          DisplayString
}

cwmMoId     OBJECT-TYPE
    SYNTAX      DisplayString
    MAX-ACCESS  read-write
    STATUS      current
    DESCRIPTION ""
    ::= { cwmEntry 1 }

cwmProvEqptType OBJECT-TYPE
    SYNTAX      InfnEqptType
    MAX-ACCESS  read-write
    STATUS      current
    DESCRIPTION ""
    ::= { cwmEntry 2 }

cwmAssociatedDegree   OBJECT-TYPE
    SYNTAX      DisplayString
    MAX-ACCESS  read-write
    STATUS      current
    DESCRIPTION ""
    ::= { cwmEntry  3 }


cwmCompliance  MODULE-COMPLIANCE
    STATUS     current
    DESCRIPTION
        "Describes the requirements for conformance to the CWM-MIB"
    MODULE
        MANDATORY-GROUPS { cwmGroup }
    ::= { cwmCompliances 1 }

cwmGroup  OBJECT-GROUP
    OBJECTS {
        cwmMoId,
        cwmProvEqptType,
        cwmAssociatedDegree
    }
    STATUS     current
    DESCRIPTION
        " A collection of objects for managing a CWM module"
    ::= { cwmGroups 1 }
END

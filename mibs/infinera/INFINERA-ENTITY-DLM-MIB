-- ***************************************************************
-- INFINERA-ENTITY-DLM-MIB
--   
-- October 2008, Sharfuddin Syed / Narendra Gupta
--   
--   
-- Copyright (c) 2008-2012 by Infinera Inc.
-- All rights reserved.
-- ****************************************************************

INFINERA-ENTITY-DLM-MIB DEFINITIONS ::= BEGIN

IMPORTS
    OBJECT-TYPE, MODULE-IDENTITY      FROM SNMPv2-SMI
    OBJECT-GROUP, MODULE-COMPLIANCE   FROM SNMPv2-CONF
    RowStatus, DisplayString          FROM SNMPv2-TC
    entLPPhysicalIndex                FROM ENTITY-MIB
    equipment                         FROM INFINERA-REG-MIB
    InfnOperatingMode,
    InfnEqptType                      FROM INFINERA-TC-MIB;

dlmMIB MODULE-IDENTITY
    LAST-UPDATED  "200810200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for DLM equipment table."
        
::= { equipment 4 }

dlmConformance       OBJECT IDENTIFIER ::= { dlmMIB 3 }
dlmCompliances       OBJECT IDENTIFIER ::= { dlmConformance 1 }
dlmGroups            OBJECT IDENTIFIER ::= { dlmConformance 2 }

dlmTable  OBJECT-TYPE
    SYNTAX SEQUENCE OF DlmEntry
    MAX-ACCESS not-accessible
    STATUS     current
    DESCRIPTION 
        "This table contains all DLM modules that are currently present in a network element.
        "
    ::= { dlmMIB 1 }

dlmEntry  OBJECT-TYPE
    SYNTAX     DlmEntry
    MAX-ACCESS not-accessible
    STATUS     current
    DESCRIPTION 
        "A row in the DLM table. Each row in the table is identified with a unique entPhysicalIndexID. 
        "
    INDEX { entLPPhysicalIndex }
    ::= { dlmTable 1 }

DlmEntry ::= SEQUENCE {
    dlmMoId                        DisplayString,
    dlmProvEqptType                InfnEqptType,
    dlmPicDspVer                   DisplayString,
    dlmOperatingMode               InfnOperatingMode,
    dlmAvailableTunableOcgNumbers  Integer32,
    dlmProvisionedOcgNumber        Integer32,    
    dlmInstalledOcgNumber          Integer32,    
    dlmRowStatus                   RowStatus,
    dlmOpticsFirmwareVer           DisplayString
}

dlmMoId  OBJECT-TYPE
    SYNTAX     DisplayString
    MAX-ACCESS read-create
    STATUS     current
    DESCRIPTION 
        "This is the primary Key of the objects e.g 1-A-3"
    ::= { dlmEntry 1 }

dlmProvEqptType  OBJECT-TYPE
    SYNTAX     InfnEqptType
    MAX-ACCESS read-create
    STATUS     current
    DESCRIPTION 
        "The configured DLM type."
    ::= { dlmEntry 2 }

dlmPicDspVer  OBJECT-TYPE
    SYNTAX     DisplayString
    MAX-ACCESS read-only
    STATUS     current
    DESCRIPTION 
        "The hardware version of the PIC on the DLM."
    ::= { dlmEntry 3 }

dlmOperatingMode  OBJECT-TYPE
    SYNTAX     InfnOperatingMode
    MAX-ACCESS read-create
    STATUS     current
    DESCRIPTION 
        "This objects controls the operating mode for  XLM and DLM in Gen1 and Gen2 modes."
    DEFVAL  { gen2 }
    ::= { dlmEntry 4 }

dlmAvailableTunableOcgNumbers  OBJECT-TYPE
    SYNTAX     Integer32
    MAX-ACCESS read-only
    STATUS     current
    DESCRIPTION 
        "This objects represents the available ocgs in bits being set.
         For example if cards available OCG on AXLM-T4-1-C4 are 1, 9, 2and 10 then
         value will be 0x303, i.e. bit 1,9,2 and 10 are set. "
    ::= { dlmEntry 5 }

dlmProvisionedOcgNumber  OBJECT-TYPE
    SYNTAX     Integer32
    MAX-ACCESS read-create
    STATUS     current
    DESCRIPTION 
        "This represents the OCG number for which tunable line module will be tuned."
    ::= { dlmEntry 6 }

dlmInstalledOcgNumber  OBJECT-TYPE
    SYNTAX     Integer32
    MAX-ACCESS read-create
    STATUS     current
    DESCRIPTION 
        "This represents the OCG number for which the line module is tuned."
    ::= { dlmEntry 7 }
    
dlmRowStatus  OBJECT-TYPE
    SYNTAX     RowStatus
    MAX-ACCESS read-create
    STATUS     current
    DESCRIPTION 
        "The row status of this DLM entry.
                Because rows in this table are indexed by entPhysicalIndex, to create a new row one must
                choose a value of entPhysicalIndex that is not already in use.
        
                A side-effect of the creation of a row in this table is the creation of a corresponding
                row in the eqptTable and the entPhysicalTable.
        
                The status may not be set to active if the dlmMoId, dlmProvEqptType,  objects are not set 
                to valid values.
        
                This row may only be deleted if it was a pre-provisioned row and the hardware is not present.
        
                If this row is deleted, the associated row in the Eqpt Table and entPhysicalTable will be
                deleted by the agent."
    ::= { dlmEntry 8 }

dlmOpticsFirmwareVer  OBJECT-TYPE
    SYNTAX     DisplayString
    MAX-ACCESS read-only
    STATUS     current
    DESCRIPTION 
        "Optics Firmware Version of LM80."
    ::= { dlmEntry 9 }


dlmCompliance  MODULE-COMPLIANCE
    STATUS     current
    DESCRIPTION 
        ""
    MODULE
        MANDATORY-GROUPS { dlmGroup } 
    ::= { dlmCompliances 1 }

dlmGroup  OBJECT-GROUP
    OBJECTS { 
        dlmAvailableTunableOcgNumbers, 
        dlmMoId, 
        dlmOperatingMode, 
        dlmPicDspVer, 
        dlmProvEqptType, 
        dlmProvisionedOcgNumber,
        dlmInstalledOcgNumber,
        dlmRowStatus,
	dlmOpticsFirmwareVer }
    STATUS     current
    DESCRIPTION 
        ""
    ::= { dlmGroups 1 }
END

-- ***************************************************************
-- INFINERA-ENTITY-EQPT-MIB
--   
-- October 2008, Sharfuddin Syed / Narendra Gupta
--   
--   
-- Copyright (c) 2008-2012 by Infinera Inc.
-- All rights reserved.
-- ****************************************************************

INFINERA-ENTITY-EQPT-MIB DEFINITIONS ::= BEGIN

IMPORTS
    OBJECT-TYPE, MODULE-IDENTITY          FROM SNMPv2-SMI
    OBJECT-GROUP, MODULE-COMPLIANCE       FROM SNMPv2-CONF
    DisplayString                         FROM SNMPv2-TC
    entPhysicalIndex                      FROM ENTITY-MIB
    commonEquipment                       FROM INFINERA-REG-MIB
    FloatHundredths, FloatTenths, 
    FloatArbitraryPrecision,
    InfnCircuitPackType, InfnEqptType, 
    InfnOpsQualifierList, InfnArc, 
    InfnAvailabilityState, InfnCorrelatedRedunStatus,
    InfnLastRebootReason,
    InfnOperationalState, InfnAdminState  FROM INFINERA-TC-MIB;

eqptMIB MODULE-IDENTITY
    LAST-UPDATED  "200810200000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        "This is definition of nfinera equipment  mibs.
         "
::= { commonEquipment 1 }


-- Conformance Statements 

eqptConformance      OBJECT IDENTIFIER ::= { eqptMIB 3 }
eqptCompliances      OBJECT IDENTIFIER ::= { eqptConformance 1 }
eqptGroups           OBJECT IDENTIFIER ::= { eqptConformance 2 }

-- January 29, 2008
-- January 29, 2008

eqptTable  OBJECT-TYPE
    SYNTAX SEQUENCE OF EqptEntry
    MAX-ACCESS not-accessible
    STATUS     current
    DESCRIPTION 
        "A list of Eqpt entries.  Each entry is uniquely identified by the value
                of entPhysicalIndex."
    ::= { eqptMIB 1 }

eqptEntry  OBJECT-TYPE
    SYNTAX     EqptEntry
    MAX-ACCESS not-accessible
    STATUS     current
    DESCRIPTION 
        "An Eqpt entry containing information pertaining to
                Infinera equipment. Entries will exist in this table for
                all entPhysicalEntries that correspond to Infinera equipment."
    INDEX { entPhysicalIndex }
    ::= { eqptTable 1 }

EqptEntry ::= SEQUENCE {
    eqptMoId                   DisplayString,
    eqptLabel                  DisplayString,
    eqptAdministrativeState    InfnAdminState,
    eqptOperationalState       InfnOperationalState,
    eqptAvailabilityState      InfnAvailabilityState,
    eqptAlarmReportControl     InfnArc,
    eqptOpStateQualifierList   InfnOpsQualifierList,
    eqptAlarmInhibitState      InfnArc,
    eqptProvEqptType           InfnEqptType,
    eqptInstalledEqptType      InfnEqptType,
    eqptBaseCircuitPackType    InfnCircuitPackType,
    eqptCLEI                   DisplayString,
    eqptSAFpgaUpgradePending   INTEGER,
    eqptSAFpgaUpgradeFlag      INTEGER,
    eqptEqptMaxPowerDraw       FloatHundredths,
    eqptLastRebootTime         DisplayString,
    eqptLastRebootReason       InfnLastRebootReason,
    eqptInletTemp              FloatArbitraryPrecision,
    eqptOutletTemp             FloatArbitraryPrecision,
    eqptPartNumber              DisplayString,
    eqptSerialNumber            DisplayString,
    eqptManufacturedDate        DisplayString,
    eqptVendorId                DisplayString,
    eqptHardwareVersion         DisplayString,
    eqptFirmwareVersion         DisplayString,
    eqptPON                     DisplayString,
    eqptUniversalSlotUsage      Integer32,
    eqptFruInsertionDate        DisplayString,
    eqptRedundancyStatus		InfnCorrelatedRedunStatus
}

eqptMoId  OBJECT-TYPE
    SYNTAX     DisplayString
    MAX-ACCESS read-only
    STATUS     current
    DESCRIPTION 
        "MO identifier for this object"
    ::= { eqptEntry 1 }

eqptLabel  OBJECT-TYPE
    SYNTAX     DisplayString
    MAX-ACCESS read-write
    STATUS     current
    DESCRIPTION 
        "An identifier to identify the managed object."
    ::= { eqptEntry 2 }

eqptAdministrativeState  OBJECT-TYPE
    SYNTAX     InfnAdminState
    MAX-ACCESS read-write
    STATUS     current
    DESCRIPTION 
        "Parameter that enables to allow or prohibit the managed object from providing its designated service."
    DEFVAL  { unlocked }
    ::= { eqptEntry 3 }

eqptOperationalState  OBJECT-TYPE
    SYNTAX     InfnOperationalState
    MAX-ACCESS read-only
    STATUS     current
    DESCRIPTION 
        "It describes the actual state of the managed object in terms of its 
         ability to provide service."
    ::= { eqptEntry 4 }

eqptAvailabilityState  OBJECT-TYPE
    SYNTAX     InfnAvailabilityState
    MAX-ACCESS read-only
    STATUS     current
    DESCRIPTION 
        "It describes the actual state of the managed object in terms of its
         ability to provide service."
    ::= { eqptEntry 5 }

eqptAlarmReportControl  OBJECT-TYPE
    SYNTAX     InfnArc
    MAX-ACCESS read-write
    STATUS     current
    DESCRIPTION 
        "Enable or disable the alarm reporting by the managed object."
    DEFVAL  { allowed }
    ::= { eqptEntry 6 }

eqptOpStateQualifierList  OBJECT-TYPE
    SYNTAX     InfnOpsQualifierList
    MAX-ACCESS read-only
    STATUS     current
    DESCRIPTION 
        "It describes the secondry state of the managed object."
    ::= { eqptEntry 7 }

eqptAlarmInhibitState  OBJECT-TYPE
    SYNTAX     InfnArc
    MAX-ACCESS read-only
    STATUS     current
    DESCRIPTION 
        "Indicates the alarm reporting status of the managed object."
    ::= { eqptEntry 8 }

eqptProvEqptType  OBJECT-TYPE
    SYNTAX     InfnEqptType
    MAX-ACCESS read-only
    STATUS     current
    DESCRIPTION 
        "The configured equipment type."
    ::= { eqptEntry 9 }

eqptInstalledEqptType  OBJECT-TYPE
    SYNTAX     InfnEqptType
    MAX-ACCESS read-only
    STATUS     current
    DESCRIPTION 
        "The equipment type installed in the slot."
    ::= { eqptEntry 10 }

eqptBaseCircuitPackType  OBJECT-TYPE
    SYNTAX     InfnCircuitPackType
    MAX-ACCESS read-only
    STATUS     current
    DESCRIPTION 
        "Base Circuit Pack Type."
    ::= { eqptEntry 11 }

eqptCLEI  OBJECT-TYPE
    SYNTAX     DisplayString
    MAX-ACCESS read-only
    STATUS     current
    DESCRIPTION 
        "The Common Language Equipment Identifier of the equipment."
    ::= { eqptEntry 12 }

eqptSAFpgaUpgradePending  OBJECT-TYPE
    SYNTAX     INTEGER {
        none (1),
        sa (2)
    }
    MAX-ACCESS read-only
    STATUS     current
    DESCRIPTION 
        "Service affecting Fpga upgrade pending indication."
    ::= { eqptEntry 13 }

eqptSAFpgaUpgradeFlag  OBJECT-TYPE
    SYNTAX     INTEGER {
        upgradeOnNextColdBoot (1),
		doNotUpgrade (2),
		upgradeOnNextWarmBoot (3)
    }
    MAX-ACCESS read-only
    STATUS     current
    DESCRIPTION 
        "Service affecting Fpga upgrade control."
    ::= { eqptEntry 14 }

eqptEqptMaxPowerDraw  OBJECT-TYPE
    SYNTAX     FloatHundredths
    MAX-ACCESS read-only
    STATUS     current
    DESCRIPTION 
        "Parameter denoting the estimated power drawn by the FRU. This varies 
         depending on the type of the FRU."
    ::= { eqptEntry 15 }

eqptLastRebootTime  OBJECT-TYPE
    SYNTAX     DisplayString
    MAX-ACCESS read-only
    STATUS     current
    DESCRIPTION 
        "The last time this equipment booted, expressed in the format 
         YYYY-MM-DD<Space>hh:mm:ss. This value will be a zero-length string if
         the boot time is unknown or not applicable."
    ::= { eqptEntry 16 }

eqptLastRebootReason  OBJECT-TYPE
    SYNTAX     InfnLastRebootReason
    MAX-ACCESS read-only
    STATUS     current
    DESCRIPTION 
        "The reason which caused the last circuit pack reboot."
    ::= { eqptEntry 17 }

eqptInletTemp  OBJECT-TYPE
    SYNTAX     FloatArbitraryPrecision
    UNITS     "degrees Celcius"
    MAX-ACCESS read-only
    STATUS     current
    DESCRIPTION 
        "The inlet temperature in degree Celsius."
    ::= { eqptEntry 18 }

eqptOutletTemp  OBJECT-TYPE
    SYNTAX     FloatArbitraryPrecision
    UNITS     "degrees Celcius"
    MAX-ACCESS read-only
    STATUS     current
    DESCRIPTION 
        "The outlet temperature in degree Celsius."
    ::= { eqptEntry 19 }

eqptPartNumber  OBJECT-TYPE
    SYNTAX      DisplayString
    MAX-ACCESS  read-only
    STATUS      current
    DESCRIPTION ""
    ::= { eqptEntry 20 }

eqptSerialNumber    OBJECT-TYPE
    SYNTAX      DisplayString
    MAX-ACCESS  read-only
    STATUS      current
    DESCRIPTION ""
    ::= { eqptEntry 21 }

eqptManufacturedDate    OBJECT-TYPE
    SYNTAX      DisplayString
    MAX-ACCESS  read-only
    STATUS      current
    DESCRIPTION ""
    ::= { eqptEntry 22 }

eqptVendorId    OBJECT-TYPE
    SYNTAX      DisplayString
    MAX-ACCESS  read-only
    STATUS      current
    DESCRIPTION ""
    ::= { eqptEntry 23 }

eqptHardwareVersion     OBJECT-TYPE
    SYNTAX      DisplayString
    MAX-ACCESS  read-only
    STATUS      current
    DESCRIPTION ""
    ::= { eqptEntry 24 }

eqptFirmwareVersion     OBJECT-TYPE
    SYNTAX      DisplayString
    MAX-ACCESS  read-only
    STATUS      current
    DESCRIPTION ""
    ::= { eqptEntry 25 }

eqptPON     OBJECT-TYPE
    SYNTAX      DisplayString
    MAX-ACCESS  read-only
    STATUS      current
    DESCRIPTION ""
    ::= { eqptEntry 26 }

eqptUniversalSlotUsage OBJECT-TYPE
    SYNTAX      Integer32
    MAX-ACCESS  read-only
    STATUS      current
    DESCRIPTION ""
    ::= { eqptEntry 27 }

eqptFruInsertionDate        OBJECT-TYPE
    SYNTAX      DisplayString
    MAX-ACCESS  read-only
    STATUS      current
    DESCRIPTION ""
    ::= { eqptEntry 28 }

eqptRedundancyStatus OBJECT-TYPE
    SYNTAX      InfnCorrelatedRedunStatus
    MAX-ACCESS  read-only
    STATUS      current
    DESCRIPTION "Describes the redundancy state on controller card"
    ::= { eqptEntry 29 }

eqptCompliance  MODULE-COMPLIANCE
    STATUS     current
    DESCRIPTION 
        "Describes the requirements for conformance to the EQPT-MIB."
    MODULE
        MANDATORY-GROUPS { eqptGroup } 
    ::= { eqptCompliances 1 }

eqptGroup  OBJECT-GROUP
    OBJECTS { eqptMoId, 
        eqptLabel, 
        eqptAdministrativeState, 
        eqptOperationalState, 
        eqptAvailabilityState, 
        eqptAlarmReportControl, 
        eqptOpStateQualifierList, 
        eqptAlarmInhibitState, 
        eqptProvEqptType, 
        eqptInstalledEqptType, 
        eqptBaseCircuitPackType, 
        eqptCLEI, 
        eqptSAFpgaUpgradePending, 
        eqptSAFpgaUpgradeFlag, 
        eqptEqptMaxPowerDraw, 
        eqptLastRebootTime, 
        eqptLastRebootReason, 
        eqptInletTemp, 
        eqptOutletTemp,
        eqptPartNumber,
        eqptSerialNumber,
        eqptManufacturedDate,
        eqptVendorId,
        eqptHardwareVersion,
        eqptFirmwareVersion,
        eqptPON,
        eqptUniversalSlotUsage,
        eqptFruInsertionDate,
		eqptRedundancyStatus
    }
    STATUS     current
    DESCRIPTION 
        " A collection of objects for managing the eqpt"
    ::= { eqptGroups 1 }
END

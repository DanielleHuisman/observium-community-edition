-- ***************************************************************
-- INFINERA-ENTITY-EXTNSHELF-MIB
-- Copyright (c) 2008-2017 by Infinera Inc.
-- All rights reserved.
-- ****************************************************************

INFINERA-ENTITY-EXTNSHELF-MIB DEFINITIONS ::= BEGIN

IMPORTS
    OBJECT-TYPE, MODULE-IDENTITY, Integer32        FROM SNMPv2-SMI
    OBJECT-GROUP, MODULE-COMPLIANCE                FROM SNMPv2-CONF
    TruthValue, DisplayString                      FROM SNMPv2-TC
    entPhysicalIndex                               FROM ENTITY-MIB
    equipment                                      FROM INFINERA-REG-MIB
    InfnEqptType                                   FROM INFINERA-TC-MIB;

extnShelfMIB MODULE-IDENTITY
    LAST-UPDATED  "201505100000Z"
    ORGANIZATION
        "Infinera"
    CONTACT-INFO
        "Infinera
                1322 Bordeaux Drive
                Sunnyvale, CA - 94089
                Contact : Technical Support
                Email   : support@infinera.com
                Phone   : 1-877-INF-5288"
    DESCRIPTION
        " "
::= { equipment 53 }


-- Conformance Statements

extnShelfConformance       OBJECT IDENTIFIER ::= { extnShelfMIB 3 }
extnShelfCompliances       OBJECT IDENTIFIER ::= { extnShelfConformance 1 }
extnShelfGroups            OBJECT IDENTIFIER ::= { extnShelfConformance 2 }

extnShelfTable  OBJECT-TYPE
    SYNTAX SEQUENCE OF ExtnShelfEntry
    MAX-ACCESS not-accessible
    STATUS     current
    DESCRIPTION
        "A list of EXTNSHELF entries. Each entry is uniquely identified by the value
                of entPhysicalIndex."
    ::= { extnShelfMIB 1 }

extnShelfEntry  OBJECT-TYPE
    SYNTAX     ExtnShelfEntry
    MAX-ACCESS not-accessible
    STATUS     current
    DESCRIPTION
        "A EXTNSHELF entry containing information pertaining to
            Infinera EXTNSHELF modules. Entries will exist in this table for
            entPhysicalEntries of type EXTNSHELF."
    INDEX { entPhysicalIndex }
    ::= { extnShelfTable 1 }

ExtnShelfEntry ::= SEQUENCE {
    extnShelfMoId                      DisplayString,
    extnShelfProvEqptType              InfnEqptType,
    extnShelfProvSerialNumber          DisplayString
}

extnShelfMoId     OBJECT-TYPE
    SYNTAX      DisplayString
    MAX-ACCESS  read-write
    STATUS      current
    DESCRIPTION ""
    ::= { extnShelfEntry 1 }

extnShelfProvEqptType OBJECT-TYPE
    SYNTAX      InfnEqptType
    MAX-ACCESS  read-write
    STATUS      current
    DESCRIPTION ""
    ::= { extnShelfEntry 2 }

extnShelfProvSerialNumber   OBJECT-TYPE
    SYNTAX      DisplayString
    MAX-ACCESS  read-write
    STATUS      current
    DESCRIPTION ""
    ::= { extnShelfEntry  3 }


extnShelfCompliance  MODULE-COMPLIANCE
    STATUS     current
    DESCRIPTION
        "Describes the requirements for conformance to the EXTNSHELF-MIB"
    MODULE
        MANDATORY-GROUPS { extnShelfGroup }
    ::= { extnShelfCompliances 1 }

extnShelfGroup  OBJECT-GROUP
    OBJECTS {
        extnShelfMoId,
        extnShelfProvEqptType,
        extnShelfProvSerialNumber
    }
    STATUS     current
    DESCRIPTION
        " A collection of objects for managing a EXTNSHELF module"
    ::= { extnShelfGroups 1 }
END

-- ***************************************************************
-- INFINERA-ENTITY-FAN-MIB
--   
-- October 2008, Sharfuddin Syed / Narendra Gupta
--   
--   
-- Copyright (c) 2008-2012 by Infinera Inc.
-- All rights reserved.
-- ****************************************************************

INFINERA-ENTITY-FAN-MIB DEFINITIONS ::= BEGIN

IMPORTS
    OBJECT-TYPE, MODULE-IDENTITY     FROM SNMPv2-SMI
    OBJECT-GROUP, MODULE-COMPLIANCE  FROM SNMPv2-CONF
    DisplayString                    FROM SNMPv2-TC
    entLPPhysicalIndex               FROM ENTITY-MIB
    equipment                        FROM INFINERA-REG-MIB
    InfnEqptType                     FROM INFINERA-TC-MIB;

fanMIB MODULE-IDENTITY
    LAST-UPDATED  "200810200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for FAN equipment table."
::= { equipment 14 }

fanConformance       OBJECT IDENTIFIER ::= { fanMIB 3 }
fanCompliances       OBJECT IDENTIFIER ::= { fanConformance 1 }
fanGroups            OBJECT IDENTIFIER ::= { fanConformance 2 }

fanTable  OBJECT-TYPE
    SYNTAX SEQUENCE OF FanEntry
    MAX-ACCESS not-accessible
    STATUS     current
    DESCRIPTION 
        "This table contains all FAN modules that are currently present in a network element.
        "
    ::= { fanMIB 1 }

fanEntry  OBJECT-TYPE
    SYNTAX     FanEntry
    MAX-ACCESS not-accessible
    STATUS     current
    DESCRIPTION 
        ""
    INDEX { entLPPhysicalIndex }
    ::= { fanTable 1 }

FanEntry ::= SEQUENCE {
    fanMoId           DisplayString,
    fanProvEqptType   InfnEqptType
}

fanMoId  OBJECT-TYPE
    SYNTAX     DisplayString
    MAX-ACCESS read-only
    STATUS     current
    DESCRIPTION 
        "This is the primary Key of the objects e.g 1-A-3"
    ::= { fanEntry 1 }

fanProvEqptType  OBJECT-TYPE
    SYNTAX     InfnEqptType
    MAX-ACCESS read-only
    STATUS     current
    DESCRIPTION 
        "The configured FAN type."
    ::= { fanEntry 2 }

fanCompliance  MODULE-COMPLIANCE
    STATUS     current
    DESCRIPTION 
        ""
    MODULE
        MANDATORY-GROUPS { fanGroup } 
    ::= { fanCompliances 1 }

fanGroup  OBJECT-GROUP
    OBJECTS { fanMoId, 
        fanProvEqptType }
    STATUS     current
    DESCRIPTION 
        ""
    ::= { fanGroups 1 }
END

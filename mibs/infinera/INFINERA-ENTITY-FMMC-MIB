-- ***************************************************************
-- INFINERA-ENTITY-FMMC-MIB
--   
-- Copyright (c) 2008-2015 by Infinera Inc.
-- All rights reserved.
-- ****************************************************************

INFINERA-ENTITY-FMMC-MIB DEFINITIONS ::= BEGIN

IMPORTS
    OBJECT-TYPE, MODULE-IDENTITY, Integer32        FROM SNMPv2-SMI
    OBJECT-GROUP, MODULE-COMPLIANCE                FROM SNMPv2-CONF
    TruthValue, DisplayString                      FROM SNMPv2-TC
    entPhysicalIndex                               FROM ENTITY-MIB
    equipment                                      FROM INFINERA-REG-MIB
	InfnEqptType, InfnOperatingMode,
	InfnWaveInterfaceType,InfnAlienTxEDFAGain,
	InfnModelingMode,FloatThousandths,
	InfnCBandOlosSoakTime                          FROM INFINERA-TC-MIB;

fmmcMIB MODULE-IDENTITY
    LAST-UPDATED  "201508170000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "
::= { equipment 47 } 

-- Conformance Statements

fmmcConformance       OBJECT IDENTIFIER ::= { fmmcMIB 3 }
fmmcCompliances       OBJECT IDENTIFIER ::= { fmmcConformance 1 }
fmmcGroups            OBJECT IDENTIFIER ::= { fmmcConformance 2 }

fmmc5Table  OBJECT-TYPE
    SYNTAX SEQUENCE OF Fmmc5Entry
    MAX-ACCESS not-accessible
    STATUS     current
    DESCRIPTION 
        "A list of FMMC entries. Each entry is uniquely identified by the value
                of entPhysicalIndex."
    ::= { fmmcMIB 1 }

fmmc5Entry  OBJECT-TYPE
    SYNTAX     Fmmc5Entry
    MAX-ACCESS not-accessible
    STATUS     current
    DESCRIPTION 
        "A FMMC entry containing information pertaining to
            Infinera FMMC modules. Entries will exist in this table for
            entPhysicalEntries of type FMMC."
    INDEX { entPhysicalIndex }
    ::= { fmmc5Table 1 }

Fmmc5Entry ::= SEQUENCE {
    fmmc5MoId                      DisplayString,
    fmmc5ProvEqptType              InfnEqptType,
    fmmc5OperatingMode			  InfnOperatingMode
}

fmmc5MoId     OBJECT-TYPE
    SYNTAX      DisplayString
    MAX-ACCESS  read-write
    STATUS      current
    DESCRIPTION ""
    ::= { fmmc5Entry 1 }

fmmc5ProvEqptType OBJECT-TYPE
    SYNTAX      InfnEqptType
    MAX-ACCESS  read-write
    STATUS      current
    DESCRIPTION ""
    ::= { fmmc5Entry 2 }
   
fmmc5OperatingMode	 OBJECT-TYPE
    SYNTAX     	InfnOperatingMode 
    MAX-ACCESS  read-only
    STATUS      current
    DESCRIPTION ""
    ::= { fmmc5Entry  3 }

-- **********************************************************************************
-- FMMC12 
-- **********************************************************************************

fmmc12Table  OBJECT-TYPE
    SYNTAX SEQUENCE OF Fmmc12Entry
    MAX-ACCESS not-accessible
    STATUS     current
    DESCRIPTION
        "A list of FMMC12 entries. Each entry is uniquely identified by the value
                of entPhysicalIndex."
    ::= { fmmcMIB 2 }

fmmc12Entry  OBJECT-TYPE
    SYNTAX     Fmmc12Entry
    MAX-ACCESS not-accessible
    STATUS     current
    DESCRIPTION
        "A FMMC12 entry containing information pertaining to
            Infinera FMMC12 modules. Entries will exist in this table for
            entPhysicalEntries of type FMMC12."
    INDEX { entPhysicalIndex }
    ::= { fmmc12Table 1 }

Fmmc12Entry ::= SEQUENCE {
    fmmc12MoId              DisplayString,
    fmmc12ProvEqptType      InfnEqptType,
    fmmc12OperatingMode     InfnOperatingMode,
    fmmc12InputSource       InfnWaveInterfaceType,
    fmmc12AlienTxEDFAGain   InfnAlienTxEDFAGain,
    fmmc12ModelingMode      InfnModelingMode,
    fmmc12OlosSoakTime      InfnCBandOlosSoakTime
}

 fmmc12MoId     OBJECT-TYPE
     SYNTAX      DisplayString
     MAX-ACCESS  read-write
     STATUS      current
     DESCRIPTION ""
     ::= { fmmc12Entry 1 }
 
 fmmc12ProvEqptType OBJECT-TYPE
     SYNTAX      InfnEqptType
     MAX-ACCESS  read-write
     STATUS      current
     DESCRIPTION ""
     ::= { fmmc12Entry 2 }
   
 fmmc12OperatingMode  OBJECT-TYPE
     SYNTAX      InfnOperatingMode
     MAX-ACCESS  read-write
     STATUS      current
     DESCRIPTION ""
     ::= { fmmc12Entry  3 }
 
 fmmc12InputSource   OBJECT-TYPE
     SYNTAX      InfnWaveInterfaceType
     MAX-ACCESS  read-write
     STATUS      current
     DESCRIPTION ""
     ::= { fmmc12Entry  4 }
 
 fmmc12AlienTxEDFAGain   OBJECT-TYPE
     SYNTAX      InfnAlienTxEDFAGain
     MAX-ACCESS  read-write
     STATUS      current
     DESCRIPTION ""
     ::= { fmmc12Entry  5 }
fmmc12ModelingMode  OBJECT-TYPE
    SYNTAX      InfnModelingMode
    MAX-ACCESS  read-write
    STATUS      current
    DESCRIPTION ""
    ::= { fmmc12Entry  6 }

fmmc12OlosSoakTime  OBJECT-TYPE
    SYNTAX      InfnCBandOlosSoakTime
    MAX-ACCESS  read-write
    STATUS      current
    DESCRIPTION ""
    ::= { fmmc12Entry  7 }



fmmcCompliance  MODULE-COMPLIANCE
    STATUS     current
    DESCRIPTION 
        "Describes the requirements for conformance to the FMMC-MIB"
    MODULE
        MANDATORY-GROUPS { fmmc5Group } 
    ::= { fmmcCompliances 1 }

fmmc12Compliance  MODULE-COMPLIANCE
    STATUS     current
    DESCRIPTION
        "Describes the requirements for conformance to the FMMC12-MIB"
    MODULE
        MANDATORY-GROUPS { fmmc12Group }
    ::= { fmmcCompliances 2 }


fmmc5Group  OBJECT-GROUP
    OBJECTS {
        fmmc5MoId,
        fmmc5ProvEqptType,
        fmmc5OperatingMode
    }
    STATUS     current
    DESCRIPTION 
        " A collection of objects for managing a FMMC module"
    ::= { fmmcGroups 1 }

fmmc12Group  OBJECT-GROUP
    OBJECTS {
        fmmc12MoId,
        fmmc12ProvEqptType,
        fmmc12OperatingMode,
        fmmc12InputSource,
        fmmc12AlienTxEDFAGain,
        fmmc12ModelingMode,
        fmmc12OlosSoakTime
    }
    STATUS     current
    DESCRIPTION
        " A collection of objects for managing a FMMC12 module"
    ::= { fmmcGroups 2 }



END

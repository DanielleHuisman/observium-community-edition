-- ***************************************************************
-- INFINERA-ENTITY-FMMF250-MIB
--   
-- Copyright (c) 2008-2015 by Infinera Inc.
-- All rights reserved.
-- ****************************************************************

INFINERA-ENTITY-FMMF250-MIB DEFINITIONS ::= BEGIN

IMPORTS
    OBJECT-TYPE, MODULE-IDENTITY, Integer32        FROM SNMPv2-SMI
    OBJECT-GROUP, MODULE-COMPLIANCE                FROM SNMPv2-CONF
    RowStatus, TruthValue, DisplayString           FROM SNMPv2-TC
    entPhysicalIndex                               FROM ENTITY-MIB
    equipment                                      FROM INFINERA-REG-MIB
    FloatHundredths, InfnEnableDisable, 
    InfnEqptType, InfnReporting, 
	InfnOAOperatingMode                            FROM INFINERA-TC-MIB;

fmmf250MIB MODULE-IDENTITY
    LAST-UPDATED  "201504030000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "
::= { equipment 42 }


-- Conformance Statements

fmmf250Conffrmance       OBJECT IDENTIFIER ::= { fmmf250MIB 3 }
fmmf250Compliances       OBJECT IDENTIFIER ::= { fmmf250Conffrmance 1 }
fmmf250Groups            OBJECT IDENTIFIER ::= { fmmf250Conffrmance 2 }

fmmf250Table  OBJECT-TYPE
    SYNTAX SEQUENCE OF FmmF250Entry 
    MAX-ACCESS not-accessible
    STATUS     current
    DESCRIPTION 
        "A list of FMMF250 entries. Each entry is uniquely identified by the value
                of entPhysicalIndex."
    ::= { fmmf250MIB 1 }

fmmf250Entry  OBJECT-TYPE
    SYNTAX     FmmF250Entry
    MAX-ACCESS not-accessible
    STATUS     current
    DESCRIPTION 
        "A FMMF250 entry containing information pertaining to
                Infinera FMMF250 modules. Entries will exist in this table for
                entPhysicalEntries of type FMMF250."
    INDEX { entPhysicalIndex }
    ::= { fmmf250Table 1 }

FmmF250Entry ::= SEQUENCE {
    fmmf250MoId                      DisplayString,
    fmmf250ProvEqptType              InfnEqptType,
	fmmf250AutomaticTiltControl		 InfnReporting,
	fmmf250EdfaPowerOffset			 FloatHundredths,
	fmmf250DisableGainControlLoop	 TruthValue,
	fmmf250RxPowerOffset			 FloatHundredths,
	fmmf250SpectrumTiltOffset		 FloatHundredths,
	fmmf250OperatingMode			 InfnOAOperatingMode,
	fmmf250ConfigurationOffset		 FloatHundredths
}

fmmf250MoId     OBJECT-TYPE
    SYNTAX      DisplayString
    MAX-ACCESS  read-write
    STATUS      current
    DESCRIPTION ""
    ::= { fmmf250Entry 1 }

fmmf250ProvEqptType OBJECT-TYPE
    SYNTAX      InfnEqptType
    MAX-ACCESS  read-write
    STATUS      current
    DESCRIPTION ""
    ::= { fmmf250Entry 2 }

fmmf250AutomaticTiltControl	OBJECT-TYPE
    SYNTAX      InfnReporting
    MAX-ACCESS  read-write
    STATUS      current
    DESCRIPTION ""
    ::= { fmmf250Entry  3 }

fmmf250EdfaPowerOffset	OBJECT-TYPE
    SYNTAX      FloatHundredths
    MAX-ACCESS  read-write
    STATUS      current
    DESCRIPTION ""
    ::= { fmmf250Entry  4 }

fmmf250DisableGainControlLoop	OBJECT-TYPE
    SYNTAX      TruthValue
    MAX-ACCESS  read-write
    STATUS      current
    DESCRIPTION ""
    ::= { fmmf250Entry  5 }

fmmf250RxPowerOffset	OBJECT-TYPE
    SYNTAX      FloatHundredths
    MAX-ACCESS  read-write
    STATUS      current
    DESCRIPTION ""
    ::= { fmmf250Entry  6 }

fmmf250SpectrumTiltOffset	OBJECT-TYPE
    SYNTAX      FloatHundredths 
    MAX-ACCESS  read-write
    STATUS      current
    DESCRIPTION ""
    ::= { fmmf250Entry  7 }

fmmf250OperatingMode	OBJECT-TYPE
    SYNTAX      InfnOAOperatingMode
    MAX-ACCESS  read-write
    STATUS      current
    DESCRIPTION ""
    ::= { fmmf250Entry 8 }

fmmf250ConfigurationOffset	OBJECT-TYPE
    SYNTAX      FloatHundredths 
    MAX-ACCESS  read-write
    STATUS      current
    DESCRIPTION ""
    ::= { fmmf250Entry  9 }

fmmf250Compliance  MODULE-COMPLIANCE
    STATUS     current
    DESCRIPTION 
        "Describes the requirements for conformance to the fmmf250-MIB"
    MODULE
        MANDATORY-GROUPS { fmmf250Group } 
    ::= { fmmf250Compliances 1 }

fmmf250Group  OBJECT-GROUP
    OBJECTS {
        fmmf250MoId,
        fmmf250ProvEqptType,
		fmmf250AutomaticTiltControl,  
		fmmf250EdfaPowerOffset,       
		fmmf250DisableGainControlLoop,
		fmmf250RxPowerOffset,         
		fmmf250SpectrumTiltOffset,    
		fmmf250OperatingMode,         
		fmmf250ConfigurationOffset   
    }
    STATUS     current
    DESCRIPTION 
        " A collection of objects for managing a FMMF250 module"
    ::= { fmmf250Groups 1 }
END

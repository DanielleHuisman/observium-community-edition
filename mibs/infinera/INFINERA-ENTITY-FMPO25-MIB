-- ***************************************************************
-- INFINERA-ENTITY-FMPO25-MIB
--   
-- Jan 2015, Kavitha Manjunatha
--   
--   
-- Copyright (c) 2010-2012 by Infinera Inc.
-- All rights reserved.
-- ****************************************************************

INFINERA-ENTITY-FMPO25-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    entLPPhysicalIndex                  FROM ENTITY-MIB
    equipment                           FROM INFINERA-REG-MIB
    InfnEqptType                        FROM INFINERA-TC-MIB;

fmpo25MIB MODULE-IDENTITY
    LAST-UPDATED  "201604220000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for FMPO25 equipment table."
        
::= { equipment 51 }

fmpo25Conformance       OBJECT IDENTIFIER ::= { fmpo25MIB 3 }
fmpo25Compliances       OBJECT IDENTIFIER ::= { fmpo25Conformance 1 }
fmpo25Groups            OBJECT IDENTIFIER ::= { fmpo25Conformance 2 }

fmpo25Table  OBJECT-TYPE
    SYNTAX SEQUENCE OF Fmpo25Entry
    MAX-ACCESS not-accessible
    STATUS     current
    DESCRIPTION 
        "This table contains all SCM modules that are currently present in a network element.
        "
    ::= { fmpo25MIB 1 }

fmpo25Entry  OBJECT-TYPE
    SYNTAX     Fmpo25Entry
    MAX-ACCESS not-accessible
    STATUS     current
    DESCRIPTION 
        "A row in the SCM table. Each row in the table is identified with a unique entPhysicalIndexID. 
        "
    INDEX { entLPPhysicalIndex }
    ::= { fmpo25Table 1 }


Fmpo25Entry ::= SEQUENCE {
    fmpo25MoId             DisplayString,
    fmpo25ProvEqptType     InfnEqptType,
    fmpo25ProvSerialNumber DisplayString
}

fmpo25MoId  OBJECT-TYPE
    SYNTAX     DisplayString
    MAX-ACCESS read-create
    STATUS     current
    DESCRIPTION 
        "This is the primary Key of the objects e.g 1-A-1"
    ::= { fmpo25Entry 1 }

fmpo25ProvEqptType  OBJECT-TYPE
    SYNTAX     InfnEqptType
    MAX-ACCESS read-create
    STATUS     current
    DESCRIPTION 
        "User provisioned SCM type."
    ::= { fmpo25Entry 2 }
 
fmpo25ProvSerialNumber OBJECT-TYPE
    SYNTAX      DisplayString
    MAX-ACCESS  read-write
    STATUS      current
    DESCRIPTION ""
    ::= { fmpo25Entry 3 }

fmpo25Compliance  MODULE-COMPLIANCE
    STATUS     current
    DESCRIPTION 
        "Describes the requirements for conformance to the FMPO25-MIB"
    MODULE
        MANDATORY-GROUPS { fmpo25Group } 
    ::= { fmpo25Compliances 1 }

fmpo25Group  OBJECT-GROUP
    OBJECTS { 
        fmpo25MoId, 
        fmpo25ProvEqptType,
        fmpo25ProvSerialNumber
    }
    STATUS     current
    DESCRIPTION 
        " A collection of objects for managing a BMM module"
    ::= { fmpo25Groups 1 }
END

-- ***************************************************************
-- INFINERA-ENTITY-FMPO50-MIB
--   
-- Jan 2015, Kavitha Manjunatha
--   
--   
-- Copyright (c) 2010-2012 by Infinera Inc.
-- All rights reserved.
-- ****************************************************************

INFINERA-ENTITY-FMPO50-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    entLPPhysicalIndex                  FROM ENTITY-MIB
    equipment                           FROM INFINERA-REG-MIB
    InfnEqptType                        FROM INFINERA-TC-MIB;

fmpo50MIB MODULE-IDENTITY
    LAST-UPDATED  "201501080000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for FMPO50 equipment table."
        
::= { equipment 52 }

fmpo50Conformance       OBJECT IDENTIFIER ::= { fmpo50MIB 3 }
fmpo50Compliances       OBJECT IDENTIFIER ::= { fmpo50Conformance 1 }
fmpo50Groups            OBJECT IDENTIFIER ::= { fmpo50Conformance 2 }

fmpo50Table  OBJECT-TYPE
    SYNTAX SEQUENCE OF Fmpo50Entry
    MAX-ACCESS not-accessible
    STATUS     current
    DESCRIPTION 
        "This table contains all SCM modules that are currently present in a network element.
        "
    ::= { fmpo50MIB 1 }

fmpo50Entry  OBJECT-TYPE
    SYNTAX     Fmpo50Entry
    MAX-ACCESS not-accessible
    STATUS     current
    DESCRIPTION 
        "A row in the SCM table. Each row in the table is identified with a unique entPhysicalIndexID. 
        "
    INDEX { entLPPhysicalIndex }
    ::= { fmpo50Table 1 }


Fmpo50Entry ::= SEQUENCE {
    fmpo50MoId             DisplayString,
    fmpo50ProvEqptType     InfnEqptType,
    fmpo50ProvSerialNumber DisplayString
}

fmpo50MoId  OBJECT-TYPE
    SYNTAX     DisplayString
    MAX-ACCESS read-create
    STATUS     current
    DESCRIPTION 
        "This is the primary Key of the objects e.g 1-A-1"
    ::= { fmpo50Entry 1 }

fmpo50ProvEqptType  OBJECT-TYPE
    SYNTAX     InfnEqptType
    MAX-ACCESS read-create
    STATUS     current
    DESCRIPTION 
        "User provisioned SCM type."
    ::= { fmpo50Entry 2 }
 
fmpo50ProvSerialNumber OBJECT-TYPE
    SYNTAX      DisplayString
    MAX-ACCESS  read-write
    STATUS      current
    DESCRIPTION ""
    ::= { fmpo50Entry 3 }

fmpo50Compliance  MODULE-COMPLIANCE
    STATUS     current
    DESCRIPTION 
        "Describes the requirements for conformance to the FMPO50-MIB"
    MODULE
        MANDATORY-GROUPS { fmpo50Group } 
    ::= { fmpo50Compliances 1 }

fmpo50Group  OBJECT-GROUP
    OBJECTS { 
        fmpo50MoId, 
        fmpo50ProvEqptType,
        fmpo50ProvSerialNumber
    }
    STATUS     current
    DESCRIPTION 
        " A collection of objects for managing a BMM module"
    ::= { fmpo50Groups 1 }
END

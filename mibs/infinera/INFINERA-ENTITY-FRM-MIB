-- ***************************************************************
-- INFINERA-ENTITY-FRM-MIB
--   
-- Copyright (c) 2008-2012 by Infinera Inc.
-- All rights reserved.
-- ****************************************************************

INFINERA-ENTITY-FRM-MIB DEFINITIONS ::= BEGIN

IMPORTS
    OBJECT-TYPE, MODULE-IDENTITY, Integer32        FROM SNMPv2-SMI
    OBJECT-GROUP, MODULE-COMPLIANCE                FROM SNMPv2-CONF
    RowStatus, TruthValue, DisplayString           FROM SNMPv2-TC
    entPhysicalIndex                               FROM ENTITY-MIB
    equipment                                      FROM INFINERA-REG-MIB
    FloatTenths, InfnEnableDisable, InfnEqptType,
    InfnOAOperatingMode,InfnSlotOperatingMode,
	InfnCBandOlosSoakTime, InfnAddDropCount        FROM INFINERA-TC-MIB;

frmMIB MODULE-IDENTITY
    LAST-UPDATED  "200810200000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "
::= { equipment 33 }


-- Conffrmance Statements

frmConffrmance       OBJECT IDENTIFIER ::= { frmMIB 3 }
frmCompliances       OBJECT IDENTIFIER ::= { frmConffrmance 1 }
frmGroups            OBJECT IDENTIFIER ::= { frmConffrmance 2 }

frmTable  OBJECT-TYPE
    SYNTAX SEQUENCE OF FrmEntry
    MAX-ACCESS not-accessible
    STATUS     current
    DESCRIPTION 
        "A list of FRM entries. Each entry is uniquely identified by the value
                of entPhysicalIndex."
    ::= { frmMIB 1 }

frmEntry  OBJECT-TYPE
    SYNTAX     FrmEntry
    MAX-ACCESS not-accessible
    STATUS     current
    DESCRIPTION 
        "A FRM entry containing inffrmation pertaining to
                Infinera FRM modules. Entries will exist in this table for
                entPhysicalEntries of type FRM."
    INDEX { entPhysicalIndex }
    ::= { frmTable 1 }

FrmEntry ::= SEQUENCE {
    frmMoId                      DisplayString,
    frmProvEqptType              InfnEqptType,
    frmAutomaticTiltControl      InfnEnableDisable,
    frmSpectrumTiltOffset        FloatTenths,
    frmMaxAddDropPorts           InfnAddDropCount,
    frmGainTiltOffset            FloatTenths,
    frmEdfaPowerOffset           FloatTenths,
    frmGainControlLoop           InfnEnableDisable,
    frmRxAmpDeviceSetpoint       FloatTenths,
    frmRxAmpDeviceTarget         FloatTenths,
    frmRxLastAmpDeviceCommitTs   Integer32,
    frmTxDampSeqNum              Integer32,
    frmRxDampSeqNum              Integer32,
    frmAdPwrTgtFailPortMask      Integer32,
    frmOlosSoakTime              InfnCBandOlosSoakTime,
    frmDampStatusString          DisplayString,
    frmDampNullSeqReason         DisplayString,
    frmRxPowerOffset             FloatTenths,
    frmIsPathLossCheckInvoked    TruthValue,
    frmPathLossInvokedPortAid    DisplayString,
    frmOperatingMode             InfnOAOperatingMode,
    frmDeploymentLabel1          DisplayString,
    frmDeploymentLabel2          DisplayString,
    frmDeploymentLabel3          DisplayString,
    frmSlotOperatingMode         InfnSlotOperatingMode,
    frmLaunchPowerOffset         FloatTenths,
    frmMaxLaunchPowerOffset      FloatTenths,
	frmTxAmpDeviceSetpoint		 FloatTenths,
	frmTxAmpDeviceTarget		 FloatTenths,
	frmTxLastAmpDeviceCommitTs	 Integer32,
	frmRamanGainSetPoint		 FloatTenths,
	frmTxVOASetPoint		     FloatTenths,
	frmSuccessfulAGCRunTime		 Integer32
}

frmMoId     OBJECT-TYPE
    SYNTAX      DisplayString
    MAX-ACCESS  read-write
    STATUS      current
    DESCRIPTION ""
    ::= { frmEntry 1 }

frmProvEqptType OBJECT-TYPE
    SYNTAX      InfnEqptType
    MAX-ACCESS  read-write
    STATUS      current
    DESCRIPTION ""
    ::= { frmEntry 2 }

frmAutomaticTiltControl OBJECT-TYPE
    SYNTAX      InfnEnableDisable
    MAX-ACCESS  read-write
    STATUS      current
    DESCRIPTION ""
    ::= { frmEntry 3 }

frmSpectrumTiltOffset OBJECT-TYPE
    SYNTAX      FloatTenths
    MAX-ACCESS  read-write
    STATUS      current
    DESCRIPTION ""
    ::= { frmEntry 4 }

frmMaxAddDropPorts  OBJECT-TYPE
    SYNTAX      InfnAddDropCount 
    MAX-ACCESS  read-write
    STATUS      current
    DESCRIPTION ""
    ::= { frmEntry 5 }

frmGainTiltOffset  OBJECT-TYPE
    SYNTAX      FloatTenths
    MAX-ACCESS  read-write
    STATUS      current
    DESCRIPTION ""
    ::= { frmEntry 6 }

frmEdfaPowerOffset  OBJECT-TYPE
    SYNTAX      FloatTenths 
    MAX-ACCESS  read-write
    STATUS      current
    DESCRIPTION ""
    ::= { frmEntry 7 }

frmGainControlLoop  OBJECT-TYPE
    SYNTAX      InfnEnableDisable 
    MAX-ACCESS  read-write
    STATUS      current
    DESCRIPTION ""
    ::= { frmEntry 8 }

frmRxPowerOffset  OBJECT-TYPE
    SYNTAX     FloatTenths
    MAX-ACCESS read-create
    STATUS     current
    DESCRIPTION ""
    ::= { frmEntry 9 }


frmRxAmpDeviceSetpoint  OBJECT-TYPE
    SYNTAX      FloatTenths
    MAX-ACCESS  read-only
    STATUS      current
    DESCRIPTION ""
    ::= { frmEntry  12 }

frmRxAmpDeviceTarget    OBJECT-TYPE
    SYNTAX      FloatTenths
    MAX-ACCESS  read-only
    STATUS      current
    DESCRIPTION ""
    ::= { frmEntry  13 }

frmRxLastAmpDeviceCommitTs  OBJECT-TYPE
    SYNTAX      Integer32
    MAX-ACCESS  read-only
    STATUS      current
    DESCRIPTION ""
    ::= { frmEntry  14 }

frmTxDampSeqNum OBJECT-TYPE
    SYNTAX      Integer32
    MAX-ACCESS  read-only
    STATUS      current
    DESCRIPTION ""
    ::= { frmEntry 15 }

frmRxDampSeqNum     OBJECT-TYPE
    SYNTAX      Integer32
    MAX-ACCESS  read-only
    STATUS      current
    DESCRIPTION ""
    ::= { frmEntry 16 }

frmAdPwrTgtFailPortMask OBJECT-TYPE
    SYNTAX      Integer32
    MAX-ACCESS  read-only
    STATUS      current
    DESCRIPTION ""
    ::= { frmEntry 17 }

frmOlosSoakTime OBJECT-TYPE
    SYNTAX      InfnCBandOlosSoakTime 
    MAX-ACCESS  read-write
    STATUS      current
    DESCRIPTION ""
    ::= { frmEntry 18 }

frmIsPathLossCheckInvoked OBJECT-TYPE
    SYNTAX      TruthValue
    MAX-ACCESS  read-only
    STATUS      current
    DESCRIPTION ""
    ::= { frmEntry 19 }

frmPathLossInvokedPortAid   OBJECT-TYPE
    SYNTAX      DisplayString
    MAX-ACCESS  read-only
    STATUS      current
    DESCRIPTION ""
    ::= { frmEntry 20 }

frmDampStatusString OBJECT-TYPE
    SYNTAX      DisplayString
    MAX-ACCESS  read-only
    STATUS      current
    DESCRIPTION ""
    ::= { frmEntry 21 }

frmDampNullSeqReason OBJECT-TYPE
    SYNTAX      DisplayString
    MAX-ACCESS  read-only
    STATUS      current
    DESCRIPTION ""
    ::= { frmEntry 22 }

frmOperatingMode OBJECT-TYPE
    SYNTAX      InfnOAOperatingMode
    MAX-ACCESS  read-write
    STATUS      current
    DESCRIPTION ""
    ::= { frmEntry 23 }

frmDeploymentLabel1 OBJECT-TYPE
    SYNTAX      DisplayString
    MAX-ACCESS  read-write
    STATUS      current
    DESCRIPTION ""
    ::= { frmEntry 24 }

frmDeploymentLabel2 OBJECT-TYPE
    SYNTAX      DisplayString
    MAX-ACCESS  read-write
    STATUS      current
    DESCRIPTION ""
    ::= { frmEntry 25 }

frmDeploymentLabel3 OBJECT-TYPE
    SYNTAX      DisplayString
    MAX-ACCESS  read-write
    STATUS      current
    DESCRIPTION ""
    ::= { frmEntry 26 }

frmSlotOperatingMode    OBJECT-TYPE
    SYNTAX      InfnSlotOperatingMode
    MAX-ACCESS  read-write
    STATUS      current
    DESCRIPTION ""
    ::= { frmEntry 27 }

frmLaunchPowerOffset    OBJECT-TYPE
    SYNTAX      FloatTenths
    MAX-ACCESS  read-write
    STATUS      current
    DESCRIPTION ""
    ::= { frmEntry 28 }

frmMaxLaunchPowerOffset OBJECT-TYPE
    SYNTAX      FloatTenths
    MAX-ACCESS  read-write
    STATUS      current
    DESCRIPTION ""
    ::= { frmEntry 29 }

frmTxAmpDeviceSetpoint	OBJECT-TYPE
    SYNTAX      FloatTenths
    MAX-ACCESS  read-only
    STATUS      current
    DESCRIPTION ""
    ::= { frmEntry 30 }

frmTxAmpDeviceTarget	OBJECT-TYPE
    SYNTAX      FloatTenths
    MAX-ACCESS  read-only
    STATUS      current
    DESCRIPTION ""
    ::= { frmEntry 31 }

frmTxLastAmpDeviceCommitTs	OBJECT-TYPE
    SYNTAX      Integer32 
    MAX-ACCESS  read-only
    STATUS      current
    DESCRIPTION ""
    ::= { frmEntry  32 }

frmRamanGainSetPoint OBJECT-TYPE
    SYNTAX      FloatTenths
    MAX-ACCESS  read-only
    STATUS      current
    DESCRIPTION ""
    ::= { frmEntry  33 }

frmTxVOASetPoint OBJECT-TYPE
    SYNTAX      FloatTenths
    MAX-ACCESS  read-only
    STATUS      current
    DESCRIPTION ""
    ::= { frmEntry 34 }

frmSuccessfulAGCRunTime	OBJECT-TYPE
    SYNTAX      Integer32
    MAX-ACCESS  read-only
    STATUS      current
    DESCRIPTION ""
    ::= { frmEntry 35 }


frmCompliance  MODULE-COMPLIANCE
    STATUS     current
    DESCRIPTION 
        "Describes the requirements for conffrmance to the FRM-MIB"
    MODULE
        MANDATORY-GROUPS { frmGroup } 
    ::= { frmCompliances 1 }

frmGroup  OBJECT-GROUP
    OBJECTS {
        frmMoId,
        frmProvEqptType,
        frmAutomaticTiltControl,
        frmSpectrumTiltOffset,
        frmMaxAddDropPorts,
        frmGainTiltOffset,
        frmEdfaPowerOffset,
        frmGainControlLoop,
        frmRxAmpDeviceSetpoint,
        frmRxAmpDeviceTarget,
        frmRxLastAmpDeviceCommitTs,
        frmTxDampSeqNum,
        frmRxDampSeqNum,
        frmAdPwrTgtFailPortMask,
        frmOlosSoakTime,
        frmDampStatusString,
        frmDampNullSeqReason,
        frmRxPowerOffset,
        frmIsPathLossCheckInvoked,
        frmPathLossInvokedPortAid,
        frmOperatingMode,
        frmDeploymentLabel1,
        frmDeploymentLabel2,
        frmDeploymentLabel3,
        frmSlotOperatingMode,
        frmLaunchPowerOffset,
        frmMaxLaunchPowerOffset,
		frmTxAmpDeviceSetpoint,    
		frmTxAmpDeviceTarget,      
		frmTxLastAmpDeviceCommitTs,
		frmRamanGainSetPoint,      
		frmTxVOASetPoint,
		frmSuccessfulAGCRunTime         
    }
    STATUS     current
    DESCRIPTION 
        " A collection of objects for managing a FRM module"
    ::= { frmGroups 1 }
END

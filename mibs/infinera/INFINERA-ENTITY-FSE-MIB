-- ***************************************************************
-- INFINERA-ENTITY-FSE-MIB
--   
-- Copyright (c) 2008-2012 by Infinera Inc.
-- All rights reserved.
-- ****************************************************************

INFINERA-ENTITY-FSE-MIB DEFINITIONS ::= BEGIN

IMPORTS
    OBJECT-TYPE, MODULE-IDENTITY, Integer32        FROM SNMPv2-SMI
    OBJECT-GROUP, MODULE-COMPLIANCE                FROM SNMPv2-CONF
    TruthValue, DisplayString                      FROM SNMPv2-TC
    entPhysicalIndex                               FROM ENTITY-MIB
    equipment                                      FROM INFINERA-REG-MIB
    InfnEqptType                                   FROM INFINERA-TC-MIB;

fseMIB MODULE-IDENTITY
    LAST-UPDATED  "200810200000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "
::= { equipment 38 }


-- Conformance Statements

fseConffseance       OBJECT IDENTIFIER ::= { fseMIB 3 }
fseCompliances       OBJECT IDENTIFIER ::= { fseConffseance 1 }
fseGroups            OBJECT IDENTIFIER ::= { fseConffseance 2 }

fseTable  OBJECT-TYPE
    SYNTAX SEQUENCE OF FseEntry
    MAX-ACCESS not-accessible
    STATUS     current
    DESCRIPTION 
        "A list of FSE entries. Each entry is uniquely identified by the value
                of entPhysicalIndex."
    ::= { fseMIB 1 }

fseEntry  OBJECT-TYPE
    SYNTAX     FseEntry
    MAX-ACCESS not-accessible
    STATUS     current
    DESCRIPTION 
        "A FSE entry containing information pertaining to
            Infinera FSE modules. Entries will exist in this table for
            entPhysicalEntries of type FSE."
    INDEX { entPhysicalIndex }
    ::= { fseTable 1 }

FseEntry ::= SEQUENCE {
    fseMoId                      DisplayString,
    fseProvEqptType              InfnEqptType,
    fseOlosSoakTime              INTEGER,
    fseIsPathLossCheckInvoked    TruthValue,
    fsePathLossInvokedPortAid    DisplayString
}

fseMoId     OBJECT-TYPE
    SYNTAX      DisplayString
    MAX-ACCESS  read-write
    STATUS      current
    DESCRIPTION ""
    ::= { fseEntry 1 }

fseProvEqptType OBJECT-TYPE
    SYNTAX      InfnEqptType
    MAX-ACCESS  read-write
    STATUS      current
    DESCRIPTION ""
    ::= { fseEntry 2 }
   
fseOlosSoakTime OBJECT-TYPE
    SYNTAX      INTEGER {
        fast(1),
        medium(2),
        long(3)
    }
    MAX-ACCESS  read-write
    STATUS      current
    DESCRIPTION ""
    ::= { fseEntry 3 } 

fseIsPathLossCheckInvoked OBJECT-TYPE
    SYNTAX      TruthValue
    MAX-ACCESS  read-only
    STATUS      current
    DESCRIPTION ""
    ::= { fseEntry  4 }

fsePathLossInvokedPortAid   OBJECT-TYPE
    SYNTAX      DisplayString
    MAX-ACCESS  read-only
    STATUS      current
    DESCRIPTION ""
    ::= { fseEntry  5 }


fseCompliance  MODULE-COMPLIANCE
    STATUS     current
    DESCRIPTION 
        "Describes the requirements for conffrmance to the FSE-MIB"
    MODULE
        MANDATORY-GROUPS { fseGroup } 
    ::= { fseCompliances 1 }

fseGroup  OBJECT-GROUP
    OBJECTS {
        fseMoId,
        fseProvEqptType,
        fseOlosSoakTime,
        fseIsPathLossCheckInvoked,
        fsePathLossInvokedPortAid
    }
    STATUS     current
    DESCRIPTION 
        " A collection of objects for managing a FSE module"
    ::= { fseGroups 1 }
END

-- ***************************************************************
-- INFINERA-ENTITY-GAM-MIB
--   
-- October 2008, Sharfuddin Syed / Narendra Gupta
--   
--   
-- Copyright (c) 2008-2012 by Infinera Inc.
-- All rights reserved.
-- ****************************************************************

INFINERA-ENTITY-GAM-MIB DEFINITIONS ::= BEGIN

IMPORTS
    OBJECT-TYPE, MODULE-IDENTITY           FROM SNMPv2-SMI
    OBJECT-GROUP, MODULE-COMPLIANCE        FROM SNMPv2-CONF
    RowStatus, DisplayString               FROM SNMPv2-TC
    entLPPhysicalIndex                     FROM ENTITY-MIB
    equipment                              FROM INFINERA-REG-MIB
    InfnEqptType                           FROM INFINERA-TC-MIB;

gamMIB MODULE-IDENTITY
    LAST-UPDATED  "200810200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for GAM equipment table."
::= { equipment 8 }

gamConformance       OBJECT IDENTIFIER ::= { gamMIB 3 }
gamCompliances       OBJECT IDENTIFIER ::= { gamConformance 1 }
gamGroups            OBJECT IDENTIFIER ::= { gamConformance 2 }

gamTable  OBJECT-TYPE
    SYNTAX SEQUENCE OF GamEntry
    MAX-ACCESS not-accessible
    STATUS     current
    DESCRIPTION 
        "This table contains all GAM modules that are currently present in a network element.
        "
    ::= { gamMIB 1 }

gamEntry  OBJECT-TYPE
    SYNTAX     GamEntry
    MAX-ACCESS not-accessible
    STATUS     current
    DESCRIPTION 
        "A row in the GAM table. Each row in the table is identified with a unique entPhysicalIndexID. 
        "
    INDEX { entLPPhysicalIndex }
    ::= { gamTable 1 }

GamEntry ::= SEQUENCE {
    gamMoId           DisplayString,
    gamProvEqptType   InfnEqptType,
    gamRowStatus      RowStatus,
    gamOperatingMode  INTEGER,
    gamInstOperatingMode INTEGER
}

gamMoId  OBJECT-TYPE
    SYNTAX     DisplayString
    MAX-ACCESS read-create
    STATUS     current
    DESCRIPTION 
        "This is the primary Key of the objects e.g 1-A-3-1"
    ::= { gamEntry 1 }

gamProvEqptType  OBJECT-TYPE
    SYNTAX     InfnEqptType
    MAX-ACCESS read-create
    STATUS     current
    DESCRIPTION 
        "The configured GAM type."
    ::= { gamEntry 2 }

gamRowStatus  OBJECT-TYPE
    SYNTAX     RowStatus
    MAX-ACCESS read-create
    STATUS     current
    DESCRIPTION 
        "The row status of this GAM entry.
                Because rows in this table are indexed by entPhysicalIndex, to create a new row one must
                choose a value of entPhysicalIndex that is not already in use.
        
                A side-effect of the creation of a row in this table is the creation of a corresponding
                row in the eqptTable and the entPhysicalTable.
        
                The status may not be set to active if the gamMoId and gamProvEqptType are not set to valid values.
        
                This row may only be deleted if it was a pre-provisioned row and the hardware is not present.
        
                If this row is deleted, the associated row in the Eqpt Table and entPhysicalTable will be
                deleted by the agent."
    ::= { gamEntry 3 }

gamOperatingMode  OBJECT-TYPE
    SYNTAX     INTEGER {
      none(1),
      gam(2), 
      aseSource(3), 
      aseGain(4)
    }
    MAX-ACCESS read-create
    STATUS     current
    DESCRIPTION 
        ""
    ::= { gamEntry 4 }

gamInstOperatingMode  OBJECT-TYPE
    SYNTAX     INTEGER {
      none(1),
      gam(2), 
      aseSource(3), 
      aseGain(4)
    }
    MAX-ACCESS read-only
    STATUS     current
    DESCRIPTION 
        ""
    ::= { gamEntry 5 }

gamCompliance  MODULE-COMPLIANCE
    STATUS     current
    DESCRIPTION 
        ""
    MODULE
        MANDATORY-GROUPS { gamGroup } 
    ::= { gamCompliances 1 }

gamGroup  OBJECT-GROUP
    OBJECTS { gamMoId, 
        gamProvEqptType, 
        gamRowStatus,
        gamOperatingMode,
        gamInstOperatingMode
    }
    STATUS     current
    DESCRIPTION 
        ""
    ::= { gamGroups 1 }
END

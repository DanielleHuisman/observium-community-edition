-- ***************************************************************
-- INFINERA-ENTITY-IAM-MIB
--   
-- Copyright (c) 2008-2012 by Infinera Inc.
-- All rights reserved.
-- ****************************************************************

INFINERA-ENTITY-IAM-MIB DEFINITIONS ::= BEGIN

IMPORTS
    OBJECT-TYPE, MODULE-IDENTITY        FROM SNMPv2-SMI
    OBJECT-GROUP, MODULE-COMPLIANCE     FROM SNMPv2-CONF
    DisplayString, TruthValue           FROM SNMPv2-TC
    entLPPhysicalIndex                  FROM ENTITY-MIB
    equipment                           FROM INFINERA-REG-MIB
    InfnEqptType, FloatTenths,
    InfnOAOperatingMode, InfnEnableDisable,
	InfnOTSGainType,InfnMidStageAccess, 
	InfnOASlotOperatingMode,InfnOlosSoakTime,
    InfnALSDisableMode, 
	InfnDeploymentConfig 				FROM INFINERA-TC-MIB;

iamMIB MODULE-IDENTITY
    LAST-UPDATED  "200810200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for IAM equipment table."
        
::= { equipment 28 }

iamConformance       OBJECT IDENTIFIER ::= { iamMIB 3 }
iamCompliances       OBJECT IDENTIFIER ::= { iamConformance 1 }
iamGroups            OBJECT IDENTIFIER ::= { iamConformance 2 }

iamTable  OBJECT-TYPE
    SYNTAX SEQUENCE OF IamEntry
    MAX-ACCESS not-accessible
    STATUS     current
    DESCRIPTION 
        "This table contains all IAM modules that are currently present in a network element.
        "
    ::= { iamMIB 1 }

iamEntry  OBJECT-TYPE
    SYNTAX     IamEntry
    MAX-ACCESS not-accessible
    STATUS     current
    DESCRIPTION 
        "A row in the IAM table. Each row in the table is identified with a unique entPhysicalIndexID. 
        "
    INDEX { entLPPhysicalIndex }
    ::= { iamTable 1 }

IamEntry ::= SEQUENCE {
    iamMoId                     DisplayString,
    iamProvEqptType             InfnEqptType,
    iamRxDampSeqNum             Integer32,
    iamTxDampSeqNum             Integer32,
    iamStaticVoaAttenuation     FloatTenths,
    iamOlosSoakTime             InfnOlosSoakTime,
    iamALSDisableMode           InfnALSDisableMode,
    iamRxEDFATargetOpt          FloatTenths,
    iamTargetLineOutputPower    FloatTenths,
    iamTxVOA                    FloatTenths,
    iamAssociatedDegree         DisplayString,
    iamLaunchPowerOffset        FloatTenths,
    iamGain                     FloatTenths,
    iamOperatingMode            InfnOAOperatingMode,
	iamGainType					InfnOTSGainType,
	iamMidStageAccess			InfnMidStageAccess,
	iamGainRangeLow				FloatTenths,
	iamGainRangeHigh			FloatTenths,
	iamisEqptMisMatchStateIsSet	TruthValue,
	iamSlotOperatingMode		InfnOASlotOperatingMode,
	iamRxAmpDeviceSetpoint		FloatTenths,
	iamRxAmpDeviceTarget		FloatTenths,
	iamRxLastAmpDeviceCommitTs	FloatTenths,
	iamIlRxLineInToEdfa			FloatTenths,
	iamGainTiltOffset			FloatTenths,
	iamCBandSoakCapableFW		TruthValue,
	iamDeploymentConfig			InfnDeploymentConfig,
	iamOSCState					InfnEnableDisable
}

iamMoId     OBJECT-TYPE
    SYNTAX      DisplayString
    MAX-ACCESS  read-create
    STATUS      current
    DESCRIPTION ""
    ::= {   iamEntry 1 }

iamProvEqptType     OBJECT-TYPE
    SYNTAX      InfnEqptType
    MAX-ACCESS  read-create
    STATUS      current
    DESCRIPTION ""
    ::= {   iamEntry 2 }


iamRxDampSeqNum  OBJECT-TYPE
    SYNTAX     Integer32
    MAX-ACCESS read-only
    STATUS     current
    DESCRIPTION ""
    ::= { iamEntry 3 }

iamTxDampSeqNum  OBJECT-TYPE
    SYNTAX     Integer32
    MAX-ACCESS read-only
    STATUS     current
    DESCRIPTION ""
    ::= { iamEntry 4 }

iamStaticVoaAttenuation  OBJECT-TYPE
    SYNTAX    FloatTenths 
    MAX-ACCESS read-create
    STATUS     current
    DESCRIPTION ""
    ::= { iamEntry 5 }

iamOlosSoakTime OBJECT-TYPE
    SYNTAX      InfnOlosSoakTime 
    MAX-ACCESS  read-write
    STATUS      current
    DESCRIPTION ""
    ::= { iamEntry 6 }

iamALSDisableMode   OBJECT-TYPE
    SYNTAX      InfnALSDisableMode
    MAX-ACCESS  read-write
    STATUS      current
    DESCRIPTION ""
    ::= { iamEntry 7 }

iamRxEDFATargetOpt  OBJECT-TYPE
    SYNTAX      FloatTenths
    MAX-ACCESS  read-write
    STATUS      current
    DESCRIPTION ""
    ::= { iamEntry 8 }

iamTargetLineOutputPower    OBJECT-TYPE
    SYNTAX      FloatTenths
    MAX-ACCESS  read-write
    STATUS      current
    DESCRIPTION ""
    ::= { iamEntry 9 }

iamTxVOA    OBJECT-TYPE
    SYNTAX      FloatTenths
    MAX-ACCESS  read-write
    STATUS      current
    DESCRIPTION  ""
    ::= { iamEntry 10 }

iamAssociatedDegree OBJECT-TYPE
    SYNTAX      DisplayString
    MAX-ACCESS  read-write
    STATUS      current
    DESCRIPTION ""
    ::= { iamEntry 11 }

iamLaunchPowerOffset    OBJECT-TYPE
    SYNTAX  FloatTenths
    MAX-ACCESS  read-write
    STATUS      current
    DESCRIPTION ""
    ::= { iamEntry 12 }

iamGain     OBJECT-TYPE
    SYNTAX      FloatTenths
    MAX-ACCESS  read-write
    STATUS      current
    DESCRIPTION ""
    ::= { iamEntry 13 }

iamOperatingMode    OBJECT-TYPE
    SYNTAX      InfnOAOperatingMode
    MAX-ACCESS  read-write
    STATUS      current
    DESCRIPTION ""
    ::= { iamEntry 14 }

iamGainType		OBJECT-TYPE
    SYNTAX      InfnOTSGainType
    MAX-ACCESS  read-only
    STATUS      current
    DESCRIPTION ""
    ::= { iamEntry 15}

iamMidStageAccess	OBJECT-TYPE
    SYNTAX      InfnMidStageAccess
    MAX-ACCESS  read-only
    STATUS      current
    DESCRIPTION ""
    ::= { iamEntry  16 }

iamGainRangeLow	OBJECT-TYPE
    SYNTAX      FloatTenths
    MAX-ACCESS  read-only
    STATUS      current
    DESCRIPTION ""
    ::= { iamEntry 17 }

iamGainRangeHigh	OBJECT-TYPE
    SYNTAX      FloatTenths
    MAX-ACCESS  read-only
    STATUS      current
    DESCRIPTION ""
    ::= { iamEntry 18 }

iamisEqptMisMatchStateIsSet	OBJECT-TYPE
    SYNTAX      TruthValue
    MAX-ACCESS  read-only
    STATUS      current
    DESCRIPTION ""
    ::= { iamEntry 19 }

iamSlotOperatingMode	OBJECT-TYPE
    SYNTAX      InfnOASlotOperatingMode
    MAX-ACCESS  read-write
    STATUS      current
    DESCRIPTION ""
    ::= { iamEntry 20 }

iamRxAmpDeviceSetpoint OBJECT-TYPE
    SYNTAX     FloatTenths
    MAX-ACCESS  read-only
    STATUS      current
    DESCRIPTION ""
    ::= { iamEntry 21 }

iamRxAmpDeviceTarget	OBJECT-TYPE
    SYNTAX      FloatTenths
    MAX-ACCESS  read-only
    STATUS      current
    DESCRIPTION ""
    ::= { iamEntry 22	}

iamRxLastAmpDeviceCommitTs	OBJECT-TYPE
    SYNTAX      FloatTenths
    MAX-ACCESS  read-only
    STATUS      current
    DESCRIPTION ""
    ::= { iamEntry 23 }

iamIlRxLineInToEdfa	OBJECT-TYPE
    SYNTAX      FloatTenths
    MAX-ACCESS  read-only
    STATUS      current
    DESCRIPTION ""
    ::= { iamEntry 24 }

iamGainTiltOffset	OBJECT-TYPE
    SYNTAX      FloatTenths
    MAX-ACCESS  read-write
    STATUS      current
    DESCRIPTION ""
    ::= { iamEntry 25 }

iamCBandSoakCapableFW	OBJECT-TYPE
    SYNTAX      TruthValue
    MAX-ACCESS  read-only
    STATUS      current
    DESCRIPTION ""
    ::= { iamEntry 26 }

iamDeploymentConfig OBJECT-TYPE
    SYNTAX     	InfnDeploymentConfig 
    MAX-ACCESS  read-write
    STATUS      current
    DESCRIPTION ""
    ::= { iamEntry 27 }

iamOSCState		OBJECT-TYPE
    SYNTAX      InfnEnableDisable
    MAX-ACCESS  read-write
    STATUS      current
    DESCRIPTION ""
    ::= { iamEntry 28 }

iamCompliance  MODULE-COMPLIANCE
    STATUS      current
    DESCRIPTION ""
    MODULE
        MANDATORY-GROUPS { iamGroup } 
    ::= { iamCompliances 1 }

iamGroup  OBJECT-GROUP
    OBJECTS {       
        iamMoId,
        iamProvEqptType,
        iamLaunchPowerOffset,
        iamRxDampSeqNum,
        iamStaticVoaAttenuation,
        iamTxDampSeqNum,
        iamOperatingMode,
        iamOlosSoakTime,
        iamALSDisableMode,
        iamRxEDFATargetOpt,
        iamTargetLineOutputPower,
        iamTxVOA,
        iamAssociatedDegree,
        iamGain,
		iamOperatingMode,           
		iamGainType,                
		iamMidStageAccess,          
		iamGainRangeLow,            
		iamGainRangeHigh,           
		iamisEqptMisMatchStateIsSet,
		iamSlotOperatingMode,       
		iamRxAmpDeviceSetpoint,     
		iamRxAmpDeviceTarget,       
		iamRxLastAmpDeviceCommitTs, 
		iamIlRxLineInToEdfa,        
		iamGainTiltOffset,          
		iamCBandSoakCapableFW,      
		iamDeploymentConfig,
		iamOSCState        
    }
    STATUS      current
    DESCRIPTION ""
    ::= { iamGroups 1 }

END

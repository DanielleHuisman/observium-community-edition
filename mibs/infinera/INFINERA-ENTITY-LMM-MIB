-- ***************************************************************
-- INFINERA-ENTITY-LMM-MIB
--   
-- Jan 2015, Kavitha Manjunatha
--   
--   
-- Copyright (c) 2010-2012 by Infinera Inc.
-- All rights reserved.
-- ****************************************************************

INFINERA-ENTITY-LMM-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    entLPPhysicalIndex                  FROM ENTITY-MIB
    equipment                           FROM INFINERA-REG-MIB
    InfnEqptType                        FROM INFINERA-TC-MIB;

lmmMIB MODULE-IDENTITY
    LAST-UPDATED  "201501080000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for LMM equipment table."
        
::= { equipment 41 }

lmmConformance       OBJECT IDENTIFIER ::= { lmmMIB 3 }
lmmCompliances       OBJECT IDENTIFIER ::= { lmmConformance 1 }
lmmGroups            OBJECT IDENTIFIER ::= { lmmConformance 2 }

lmmTable  OBJECT-TYPE
    SYNTAX SEQUENCE OF LmmEntry
    MAX-ACCESS not-accessible
    STATUS     current
    DESCRIPTION 
        "This table contains all SCM modules that are currently present in a network element.
        "
    ::= { lmmMIB 1 }

lmmEntry  OBJECT-TYPE
    SYNTAX     LmmEntry
    MAX-ACCESS not-accessible
    STATUS     current
    DESCRIPTION 
        "A row in the SCM table. Each row in the table is identified with a unique entPhysicalIndexID. 
        "
    INDEX { entLPPhysicalIndex }
    ::= { lmmTable 1 }


LmmEntry ::= SEQUENCE {
    lmmMoId             DisplayString,
    lmmProvEqptType     InfnEqptType,
    lmmProvSerialNumber DisplayString,
    lmmAssociatedDegree DisplayString
}

lmmMoId  OBJECT-TYPE
    SYNTAX     DisplayString
    MAX-ACCESS read-create
    STATUS     current
    DESCRIPTION 
        "This is the primary Key of the objects e.g 1-A-1"
    ::= { lmmEntry 1 }

lmmProvEqptType  OBJECT-TYPE
    SYNTAX     InfnEqptType
    MAX-ACCESS read-create
    STATUS     current
    DESCRIPTION 
        "User provisioned SCM type."
    ::= { lmmEntry 2 }
 
lmmProvSerialNumber OBJECT-TYPE
    SYNTAX      DisplayString
    MAX-ACCESS  read-write
    STATUS      current
    DESCRIPTION ""
    ::= { lmmEntry 3 }

lmmAssociatedDegree OBJECT-TYPE
    SYNTAX      DisplayString
    MAX-ACCESS  read-write
    STATUS      current
    DESCRIPTION ""
    ::= { lmmEntry 4 }

lmmCompliance  MODULE-COMPLIANCE
    STATUS     current
    DESCRIPTION 
        "Describes the requirements for conformance to the LMM-MIB"
    MODULE
        MANDATORY-GROUPS { lmmGroup } 
    ::= { lmmCompliances 1 }

lmmGroup  OBJECT-GROUP
    OBJECTS { 
        lmmMoId, 
        lmmProvEqptType,
        lmmProvSerialNumber,
        lmmAssociatedDegree
    }
    STATUS     current
    DESCRIPTION 
        " A collection of objects for managing a BMM module"
    ::= { lmmGroups 1 }
END

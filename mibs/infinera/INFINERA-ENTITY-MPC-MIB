-- ***************************************************************
-- INFINERA-ENTITY-MPC-MIB
--   
-- August 2015, Mithun Murthy 
--   
--   
-- Copyright (c) 2010-2012 by Infinera Inc.
-- All rights reserved.
-- ****************************************************************

INFINERA-ENTITY-MPC-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    entLPPhysicalIndex                  FROM ENTITY-MIB
    equipment                           FROM INFINERA-REG-MIB
    InfnEqptType                        FROM INFINERA-TC-MIB;

mpcMIB MODULE-IDENTITY
    LAST-UPDATED  "201501080000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for MPC equipment table."
        
::= { equipment 50 }

mpcConformance       OBJECT IDENTIFIER ::= { mpcMIB 3 }
mpcCompliances       OBJECT IDENTIFIER ::= { mpcConformance 1 }
mpcGroups            OBJECT IDENTIFIER ::= { mpcConformance 2 }

mpcTable  OBJECT-TYPE
    SYNTAX SEQUENCE OF MpcEntry
    MAX-ACCESS not-accessible
    STATUS     current
    DESCRIPTION 
        "This table contains all SCM modules that are currently present in a network element.
        "
    ::= { mpcMIB 1 }

mpcEntry  OBJECT-TYPE
    SYNTAX     MpcEntry
    MAX-ACCESS not-accessible
    STATUS     current
    DESCRIPTION 
        "A row in the SCM table. Each row in the table is identified with a unique entPhysicalIndexID. 
        "
    INDEX { entLPPhysicalIndex }
    ::= { mpcTable 1 }


MpcEntry ::= SEQUENCE {
    mpcProvEqptType     	InfnEqptType,
    mpcProvSerialNumber 	DisplayString,
    mpcLabel				DisplayString,
    mpcConnectedPassiveEqptList DisplayString
}

mpcProvEqptType  OBJECT-TYPE
    SYNTAX     InfnEqptType
    MAX-ACCESS read-create
    STATUS     current
    DESCRIPTION 
        "User provisioned eqpt type."
    ::= { mpcEntry 1 }
 
mpcProvSerialNumber OBJECT-TYPE
    SYNTAX      DisplayString
    MAX-ACCESS  read-write
    STATUS      current
    DESCRIPTION 
		"User provisioned serial number"
    ::= { mpcEntry 2 }

mpcLabel	OBJECT-TYPE
    SYNTAX      DisplayString
    MAX-ACCESS  read-write
    STATUS      current
    DESCRIPTION 
		"user provided label"
    ::= { mpcEntry 3 }

mpcConnectedPassiveEqptList	OBJECT-TYPE
    SYNTAX      DisplayString
    MAX-ACCESS  read-write
    STATUS      current
    DESCRIPTION 
		"List of connected passive equipments"
    ::= { mpcEntry 4 }

mpcCompliance  MODULE-COMPLIANCE
    STATUS     current
    DESCRIPTION 
        "Describes the requirements for conformance to the MPC-MIB"
    MODULE
        MANDATORY-GROUPS { mpcGroup } 
    ::= { mpcCompliances 1 }

mpcGroup  OBJECT-GROUP
    OBJECTS { 
        mpcProvEqptType,
        mpcProvSerialNumber,
        mpcLabel,
		mpcConnectedPassiveEqptList
    }
    STATUS     current
    DESCRIPTION 
        " A collection of objects for managing a MPC module"
    ::= { mpcGroups 1 }
END

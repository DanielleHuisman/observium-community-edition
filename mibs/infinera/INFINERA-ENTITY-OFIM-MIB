-- ***************************************************************
-- INFINERA-ENTITY-OFIM-MIB
--   
--   
-- Copyright (c) 2011-2012 by Infinera Inc.
-- All rights reserved.
-- ****************************************************************

INFINERA-ENTITY-OFIM-MIB DEFINITIONS ::= BEGIN

IMPORTS
    OBJECT-TYPE, MODULE-IDENTITY        	FROM SNMPv2-SMI
    OBJECT-GROUP, MODULE-COMPLIANCE     	FROM SNMPv2-CONF
    DisplayString            	            FROM SNMPv2-TC
    entLPPhysicalIndex                  	FROM ENTITY-MIB
    equipment                           	FROM INFINERA-REG-MIB
    InfnEqptType, InfnOtnOtuType,
	InfnEnforcementMode, 
	FloatTenths           					FROM INFINERA-TC-MIB;

ofimMIB MODULE-IDENTITY
    LAST-UPDATED  "201505270000Z"
    ORGANIZATION "INFINERA"
    CONTACT-INFO 
        "Infinera
        169 Java Drive
        Sunnyvale, CA - 94089
        
        Contact : Technical Support
        Email   : support@infinera.com
        Phone   : 1-877-INF-5288 "
        DESCRIPTION 
        "This MIB is modeling for OFIM equipment table"
        
::= { equipment 44 } 

ofimConformance       OBJECT IDENTIFIER ::= { ofimMIB 3 }
ofimCompliances       OBJECT IDENTIFIER ::= { ofimConformance 1 }
ofimGroups            OBJECT IDENTIFIER ::= { ofimConformance 2 }

ofimTable  OBJECT-TYPE
    SYNTAX SEQUENCE OF OfimEntry
    MAX-ACCESS not-accessible
    STATUS     current
    DESCRIPTION 
        "This table contains all OFIM modules that are currently present in a network element.
        "
    ::= { ofimMIB 1 }

ofimEntry  OBJECT-TYPE
    SYNTAX     OfimEntry
    MAX-ACCESS not-accessible
    STATUS     current
    DESCRIPTION 
        "A row in the OFIM table. Each row in the table is identified with a unique entPhysicalIndexID." 
    INDEX { entLPPhysicalIndex }
    ::= { ofimTable 1 }

OfimEntry ::= SEQUENCE {
   ofimMoId                                  DisplayString,
   ofimProvEqptType                          InfnEqptType,
   ofimOTNContainerRepresentation            InfnOtnOtuType,
   ofimPicDspVer                             DisplayString,
   ofimMaxFruGain                            FloatTenths,
   ofimRxEdfaOutputPowerTarget               FloatTenths,
   ofimRxEdfaGain                            FloatTenths,
   ofimRecommendedGain                       FloatTenths,
   ofimBwQmax                                FloatTenths,
   ofimBwQused                               FloatTenths,
   ofimBwBmax                                FloatTenths,
   ofimBwBused                               FloatTenths,
   ofimBwUsgWaterMarkGranularity             FloatTenths,
   ofimAvailableTunableSuperChNumbers        DisplayString
}

ofimMoId     OBJECT-TYPE
    SYNTAX      DisplayString
    MAX-ACCESS  read-write
    STATUS      current
    DESCRIPTION ""
    ::= { ofimEntry 1 }

ofimProvEqptType     OBJECT-TYPE
    SYNTAX      InfnEqptType
    MAX-ACCESS  read-write
    STATUS      current
    DESCRIPTION ""
    ::= { ofimEntry 2 }

ofimOTNContainerRepresentation OBJECT-TYPE
    SYNTAX      InfnOtnOtuType
    MAX-ACCESS  read-write
    STATUS      current
    DESCRIPTION ""
    ::= { ofimEntry  3 }

ofimPicDspVer    OBJECT-TYPE
    SYNTAX      DisplayString
    MAX-ACCESS  read-only
    STATUS      current
    DESCRIPTION ""
    ::= { ofimEntry  4 }

ofimMaxFruGain   OBJECT-TYPE
    SYNTAX      FloatTenths
    MAX-ACCESS  read-only
    STATUS      current
    DESCRIPTION ""
    ::= { ofimEntry  5 }

ofimRecommendedGain OBJECT-TYPE
    SYNTAX          FloatTenths  
    MAX-ACCESS      read-only
    STATUS          current
    DESCRIPTION     ""
    ::= { ofimEntry 6 }

ofimRxEdfaOutputPowerTarget  OBJECT-TYPE
    SYNTAX      FloatTenths
    MAX-ACCESS  read-only
    STATUS      current
    DESCRIPTION ""
    ::= { ofimEntry  7 }

ofimRxEdfaGain   OBJECT-TYPE
    SYNTAX      FloatTenths
    MAX-ACCESS  read-write
    STATUS      current
    DESCRIPTION ""
    ::= { ofimEntry  8 }

ofimBwQmax   OBJECT-TYPE
    SYNTAX      FloatTenths
    MAX-ACCESS  read-write
    STATUS      current
    DESCRIPTION ""
    ::= { ofimEntry 9 }

ofimBwQused      OBJECT-TYPE
    SYNTAX      FloatTenths
    MAX-ACCESS  read-write
    STATUS      current
    DESCRIPTION ""
    ::= { ofimEntry 10 }

ofimBwBmax       OBJECT-TYPE
    SYNTAX      FloatTenths
    MAX-ACCESS  read-write
    STATUS      current
    DESCRIPTION ""
    ::= { ofimEntry 11 }

ofimBwBused      OBJECT-TYPE
    SYNTAX      FloatTenths
    MAX-ACCESS  read-write
    STATUS      current
    DESCRIPTION ""
    ::= { ofimEntry 12 }

ofimBwUsgWaterMarkGranularity    OBJECT-TYPE
    SYNTAX      FloatTenths
    MAX-ACCESS  read-write
    STATUS      current
    DESCRIPTION ""
    ::= { ofimEntry 13 }

ofimAvailableTunableSuperChNumbers OBJECT-TYPE
    SYNTAX      DisplayString
    MAX-ACCESS  read-only
    STATUS      current
    DESCRIPTION ""
    ::= { ofimEntry  14 }

ofimCompliance  MODULE-COMPLIANCE
    STATUS      current
    DESCRIPTION ""
    MODULE
        MANDATORY-GROUPS { ofimGroup } 
    ::= { ofimCompliances 1 }

ofimGroup  OBJECT-GROUP
    OBJECTS { 
        ofimMoId,
        ofimProvEqptType,
        ofimPicDspVer,
        ofimMaxFruGain,
        ofimRxEdfaOutputPowerTarget,
        ofimRxEdfaGain,
        ofimOTNContainerRepresentation,
        ofimRecommendedGain,
        ofimBwQmax,
        ofimBwQused,
        ofimBwBmax,
        ofimBwBused,
        ofimBwUsgWaterMarkGranularity,
        ofimAvailableTunableSuperChNumbers
    }
    STATUS     current
    DESCRIPTION 
        ""
    ::= { ofimGroups 1 }
END

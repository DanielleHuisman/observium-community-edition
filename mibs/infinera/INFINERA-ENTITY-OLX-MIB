-- ***************************************************************
-- INFINERA-ENTITY-OLX-MIB
--   
-- Aug 2011, Sharfuddin Syed / Narendra Gupta
--   
--   
-- Copyright (c) 2011-2012 by Infinera Inc.
-- All rights reserved.
-- ****************************************************************

INFINERA-ENTITY-OLX-MIB DEFINITIONS ::= BEGIN

IMPORTS
    OBJECT-TYPE, MODULE-IDENTITY        	FROM SNMPv2-SMI
    OBJECT-GROUP, MODULE-COMPLIANCE     	FROM SNMPv2-CONF
    RowStatus, DisplayString            	FROM SNMPv2-TC
    entLPPhysicalIndex                  	FROM ENTITY-MIB
    equipment                           	FROM INFINERA-REG-MIB
    InfnEqptType,InfnSlteOpMode ,InfnChannelPlan,                       
    InfnOperatingMode,
       InfnOcgType,InfnAutoTunable		FROM INFINERA-TC-MIB;

olxMIB MODULE-IDENTITY
    LAST-UPDATED  "201110200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for OLX equipment table."
        
::= { equipment 26 }

olxConformance       OBJECT IDENTIFIER ::= { olxMIB 3 }
olxCompliances       OBJECT IDENTIFIER ::= { olxConformance 1 }
olxGroups            OBJECT IDENTIFIER ::= { olxConformance 2 }

olxTable  OBJECT-TYPE
    SYNTAX SEQUENCE OF OlxEntry
    MAX-ACCESS not-accessible
    STATUS     current
    DESCRIPTION 
        "This table contains all OLX modules that are currently present in a network element.
        "
    ::= { olxMIB 1 }

olxEntry  OBJECT-TYPE
    SYNTAX     OlxEntry
    MAX-ACCESS not-accessible
    STATUS     current
    DESCRIPTION 
        "A row in the OLX table. Each row in the table is identified with a unique entPhysicalIndexID." 
    INDEX { entLPPhysicalIndex }
    ::= { olxTable 1 }

OlxEntry ::= SEQUENCE {
    olxMoId                             	DisplayString,
    olxProvEqptType                     	InfnEqptType,   
    olxOperatingMode                    	InfnOperatingMode,   
    olxAvailableTunableOcgNumbers       	Integer32,  
    olxTunableOcgNumber   					Integer32,   
    olxCurOcgNumber							Integer32, 
    olxPicDspVer 							DisplayString,  
    olxOcgNumber							Integer32,
    olxRowStatus            				RowStatus,
    actvTimingSource						DisplayString,
    olxRxEdfaGain                           Integer32,
    olxRxEdfaOutputTargetPower               Integer32
}

olxMoId  OBJECT-TYPE
    SYNTAX     DisplayString
    MAX-ACCESS read-create
    STATUS     current
    DESCRIPTION 
        "This is the primary Key of the objects"
    ::= { olxEntry 1 }

olxProvEqptType  OBJECT-TYPE
    SYNTAX     InfnEqptType
    MAX-ACCESS read-create
    STATUS     current
    DESCRIPTION 
        "The configured OLX type."
    ::= { olxEntry 2 }

olxOperatingMode  OBJECT-TYPE
    SYNTAX     InfnOperatingMode
    MAX-ACCESS read-write
    STATUS     current
    DESCRIPTION 
        "This objects controls the operating mode for  OLX and DLM in Gen1 and Gen2 modes."
    DEFVAL  { gen2 }
    ::= { olxEntry 3 }

olxAvailableTunableOcgNumbers  OBJECT-TYPE
    SYNTAX     Integer32
    MAX-ACCESS read-only
    STATUS     current
    DESCRIPTION 
        ""
    ::= { olxEntry 4 }

olxTunableOcgNumber  OBJECT-TYPE
    SYNTAX     Integer32
    MAX-ACCESS read-write
    STATUS     current
    DESCRIPTION 
        ""
    ::= { olxEntry 5 }


olxCurOcgNumber  OBJECT-TYPE
    SYNTAX     Integer32
    MAX-ACCESS read-only
    STATUS     current
    DESCRIPTION 
        ""
    ::= { olxEntry 6 }



olxPicDspVer  OBJECT-TYPE
    SYNTAX     DisplayString
    MAX-ACCESS read-only
    STATUS     current
    DESCRIPTION 
        "The hardware version of the PIC on the OLX."
    ::= { olxEntry 7 }



olxOcgNumber  OBJECT-TYPE
    SYNTAX     Integer32
    MAX-ACCESS read-create
    STATUS     current
    DESCRIPTION 
        "This represents the OCG number for which tunable line module will be tuned."
    ::= { olxEntry 8 }


olxRowStatus  OBJECT-TYPE
    SYNTAX     RowStatus
    MAX-ACCESS read-create
    STATUS     current
    DESCRIPTION 
        "The row status of this OLX entry. 
        Because rows in this table are indexed by entPhysicalIndex, to create a new row one must
                choose a value of entPhysicalIndex that is not already in use.
        
                A side-effect of the creation of a row in this table is the creation of a corresponding
                row in the eqptTable and the entPhysicalTable.
        
                The status may not be set to active if the olxMoId and olxProvEqptType are not set to valid values.
        
                This row may only be deleted if it was a pre-provisioned row and the hardware is not present.
        
                If this row is deleted, the associated row in the Eqpt Table and entPhysicalTable will be  deleted by the agent."
    ::= { olxEntry 9 }

actvTimingSource OBJECT-TYPE 
		SYNTAX     DisplayString 
		MAX-ACCESS read-only
    	STATUS     current
    	DESCRIPTION "" 
        ::= { olxEntry 10 } 

olxRxEdfaGain  OBJECT-TYPE
    SYNTAX     Integer32
    MAX-ACCESS read-only
    STATUS     current
    DESCRIPTION 
        ""
    ::= { olxEntry 11 }

olxRxEdfaOutputTargetPower  OBJECT-TYPE
    SYNTAX     Integer32
    MAX-ACCESS read-only
    STATUS     current
    DESCRIPTION 
        ""
    ::= { olxEntry 12 }


olxCompliance  MODULE-COMPLIANCE
    STATUS     current
    DESCRIPTION 
        ""
    MODULE
        MANDATORY-GROUPS { olxGroup } 
    ::= { olxCompliances 1 }

olxGroup  OBJECT-GROUP
    OBJECTS {  
		olxMoId ,
    	olxProvEqptType ,   	
    	olxOperatingMode ,    
    	olxAvailableTunableOcgNumbers , 	 
    	olxTunableOcgNumber ,	
    	olxCurOcgNumber	 ,  	
    	olxPicDspVer 	 , 	
    	olxOcgNumber,
    	olxRowStatus,
    	actvTimingSource,
        olxRxEdfaGain,
        olxRxEdfaOutputTargetPower
         }
    STATUS     current
    DESCRIPTION 
        ""
    ::= { olxGroups 1 }
END

-- ***************************************************************
-- INFINERA-ENTITY-OTXM-MIB
--   
-- January 2015, Nikhil Shetty
--   
--   
-- Copyright (c) 2011-2012 by Infinera Inc.
-- All rights reserved.
-- ****************************************************************

INFINERA-ENTITY-OTXM-MIB DEFINITIONS ::= BEGIN

IMPORTS
 	OBJECT-TYPE, MODULE-IDENTITY      	FROM SNMPv2-SMI
 	OBJECT-GROUP, MODULE-COMPLIANCE   	FROM SNMPv2-CONF
 	RowStatus, DisplayString          	FROM SNMPv2-TC
 	entLPPhysicalIndex                	FROM ENTITY-MIB
 	equipment                         	FROM INFINERA-REG-MIB
 	InfnEqptType		 		FROM INFINERA-TC-MIB;

otxmMIB MODULE-IDENTITY
    LAST-UPDATED  "201110200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for OTXM equipment table."
        
::= { equipment 32 }

otxmConformance       OBJECT IDENTIFIER ::= { otxmMIB 3 }
otxmCompliances       OBJECT IDENTIFIER ::= { otxmConformance 1 }
otxmGroups            OBJECT IDENTIFIER ::= { otxmConformance 2 }

otxmTable  OBJECT-TYPE
    SYNTAX SEQUENCE OF OtxmEntry
    MAX-ACCESS not-accessible
    STATUS     current
    DESCRIPTION 
        "This table contains all OTXM modules that are currently present in a network element.
        "
    ::= { otxmMIB 1 }

otxmEntry  OBJECT-TYPE
    SYNTAX     OtxmEntry
    MAX-ACCESS not-accessible
    STATUS     current
    DESCRIPTION 
        "A row in the OTXM table. Each row in the table is identified with a unique entPhysicalIndexID. 
        "
    INDEX { entLPPhysicalIndex }
    ::= { otxmTable 1 }

OtxmEntry ::= SEQUENCE {
    	otxmMoId                        DisplayString,
	    otxmProvEqptType                InfnEqptType,      
    	otxmRowStatus                   RowStatus
}

otxmMoId  OBJECT-TYPE
    SYNTAX     DisplayString
    MAX-ACCESS read-create
    STATUS     current
    DESCRIPTION 
        "This is the primary Key of the objects"
    ::= { otxmEntry 1 }

otxmProvEqptType  OBJECT-TYPE
    SYNTAX     InfnEqptType
    MAX-ACCESS read-create
    STATUS     current
    DESCRIPTION 
        "The configured OTXM type."
    ::= { otxmEntry 2 }    


otxmRowStatus  OBJECT-TYPE
    SYNTAX     RowStatus
    MAX-ACCESS read-create
    STATUS     current
    DESCRIPTION 
        "The row status of this OTXM entry.
                Because rows in this table are indexed by entPhysicalIndex, to create a new row one must
                choose a value of entPhysicalIndex that is not already in use.
        
                A side-effect of the creation of a row in this table is the creation of a corresponding
                row in the eqptTable and the entPhysicalTable.
        
                The status may not be set to active if the otxmMoId, otxmProvEqptType,  objects are not set 
                to valid values.
        
                This row may only be deleted if it was a pre-provisioned row and the hardware is not present.
        
                If this row is deleted, the associated row in the Eqpt Table and entPhysicalTable will be
                deleted by the agent."
    ::= { otxmEntry 3 }


otxmCompliance  MODULE-COMPLIANCE
    STATUS     current
    DESCRIPTION 
        ""
    MODULE
        MANDATORY-GROUPS { otxmGroup } 
    ::= { otxmCompliances 1 }

otxmGroup  OBJECT-GROUP
    OBJECTS { 
      
        otxmMoId, 
	    otxmProvEqptType,      
        otxmRowStatus
}
    STATUS     current
    DESCRIPTION 
        ""
    ::= { otxmGroups 1 }
END

-- ***************************************************************
-- INFINERA-ENTITY-TAM-MIB
--   
-- October 2008, Sharfuddin Syed / Narendra Gupta
--   
--   
-- Copyright (c) 2008-2012 by Infinera Inc.
-- All rights reserved.
-- ****************************************************************

INFINERA-ENTITY-TAM-MIB DEFINITIONS ::= BEGIN

IMPORTS
    OBJECT-TYPE, MODULE-IDENTITY      FROM SNMPv2-SMI
    OBJECT-GROUP, MODULE-COMPLIANCE   FROM SNMPv2-CONF
    RowStatus, DisplayString          FROM SNMPv2-TC
    entLPPhysicalIndex                FROM ENTITY-MIB
    equipment                         FROM INFINERA-REG-MIB
    InfnEqptType                      FROM INFINERA-TC-MIB;

tamMIB MODULE-IDENTITY
    LAST-UPDATED  "200810200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for TAM equipment table."
        
::= { equipment 7 }

tamConformance       OBJECT IDENTIFIER ::= { tamMIB 3 }
tamCompliances       OBJECT IDENTIFIER ::= { tamConformance 1 }
tamGroups            OBJECT IDENTIFIER ::= { tamConformance 2 }

tamTable  OBJECT-TYPE
    SYNTAX SEQUENCE OF TamEntry
    MAX-ACCESS not-accessible
    STATUS     current
    DESCRIPTION 
        "This table contains all TAM modules that are currently present in a network element.
        "
    ::= { tamMIB 1 }

tamEntry  OBJECT-TYPE
    SYNTAX     TamEntry
    MAX-ACCESS not-accessible
    STATUS     current
    DESCRIPTION 
        "A row in the TAM table. Each row in the table is identified with a unique entPhysicalIndexID. 
        "
    INDEX { entLPPhysicalIndex }
    ::= { tamTable 1 }

TamEntry ::= SEQUENCE {
    tamMoId           DisplayString,
    tamProvEqptType   InfnEqptType,
    tamRowStatus      RowStatus
}

tamMoId  OBJECT-TYPE
    SYNTAX     DisplayString
    MAX-ACCESS read-create
    STATUS     current
    DESCRIPTION 
        "This is the primary Key of the objects e.g 1-A-3-1"
    ::= { tamEntry 1 }

tamProvEqptType  OBJECT-TYPE
    SYNTAX     InfnEqptType
    MAX-ACCESS read-create
    STATUS     current
    DESCRIPTION 
        "The configured TAM type."
    ::= { tamEntry 2 }

tamRowStatus  OBJECT-TYPE
    SYNTAX     RowStatus
    MAX-ACCESS read-create
    STATUS     current
    DESCRIPTION 
        "The row status of this TAM entry.
                Because rows in this table are indexed by entPhysicalIndex, to create a new row one must
                choose a value of entPhysicalIndex that is not already in use.
        
                A side-effect of the creation of a row in this table is the creation of a corresponding
                row in the eqptTable and the entPhysicalTable.
        
                The status may not be set to active if the tamMoId and tamProvEqptType are not set to valid values.
        
                This row may only be deleted if it was a pre-provisioned row and the hardware is not present.
        
                If this row is deleted, the associated row in the Eqpt Table and entPhysicalTable will be
                deleted by the agent."
    ::= { tamEntry 3 }

tamCompliance  MODULE-COMPLIANCE
    STATUS     current
    DESCRIPTION 
        ""
    MODULE
        MANDATORY-GROUPS { tamGroup } 
    ::= { tamCompliances 1 }

tamGroup  OBJECT-GROUP
    OBJECTS { tamMoId, 
        tamProvEqptType, 
        tamRowStatus }
    STATUS     current
    DESCRIPTION 
        ""
    ::= { tamGroups 1 }
END

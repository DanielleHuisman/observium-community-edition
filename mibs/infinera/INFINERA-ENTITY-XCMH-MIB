-- ***************************************************************
-- INFINERA-ENTITY-XCMH-MIB
--   
-- January 2015, Nikhil Shetty 
--   
-- 
-- Copyright (c) 2011-2012 by Infinera Inc.
-- All rights reserved.
-- ****************************************************************

INFINERA-ENTITY-XCMH-MIB DEFINITIONS ::= BEGIN

IMPORTS
    OBJECT-TYPE, MODULE-IDENTITY           FROM SNMPv2-SMI
    OBJECT-GROUP, MODULE-COMPLIANCE        FROM SNMPv2-CONF
    RowStatus, TruthValue, DisplayString   FROM SNMPv2-TC
    entLPPhysicalIndex                     FROM ENTITY-MIB
    equipment                              FROM INFINERA-REG-MIB
    InfnEqptType,
	InfnCorrelatedRedunStatus              FROM INFINERA-TC-MIB;

xcmhMIB MODULE-IDENTITY
    LAST-UPDATED  "201501200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for XCMH equipment table."

::= { equipment 31 }

xcmhConformance       OBJECT IDENTIFIER ::= { xcmhMIB 3 }
xcmhCompliances       OBJECT IDENTIFIER ::= { xcmhConformance 1 }
xcmhGroups            OBJECT IDENTIFIER ::= { xcmhConformance 2 }

xcmhTable  OBJECT-TYPE
    SYNTAX SEQUENCE OF XcmhEntry
    MAX-ACCESS not-accessible
    STATUS     current
    DESCRIPTION 
        "This table contains all XCMH modules that are currently present in a network element.
        "
    ::= { xcmhMIB 1 }

xcmhEntry  OBJECT-TYPE
    SYNTAX     XcmhEntry
    MAX-ACCESS not-accessible
    STATUS     current
    DESCRIPTION 
        "A row in the XCMH table. Each row in the table is identified with a unique entPhysicalIndexID. 
        "
    INDEX { entLPPhysicalIndex }
    ::= { xcmhTable 1 }

XcmhEntry ::= SEQUENCE {
    xcmhMoId                		DisplayString,
    xcmhProvType            		InfnEqptType,
    xcmhRedundancyStatus    		InfnCorrelatedRedunStatus,
    xcmhBrandingFault       		TruthValue,
    xcmhRowStatus           		RowStatus
}

xcmhMoId  OBJECT-TYPE
    SYNTAX     DisplayString
    MAX-ACCESS read-create
    STATUS     current
    DESCRIPTION 
        "The object identifier for XCMH"
    ::= { xcmhEntry 1 }

xcmhProvType  OBJECT-TYPE
    SYNTAX     InfnEqptType
    MAX-ACCESS read-create
    STATUS     current
    DESCRIPTION 
        "The configured XCMH type."
    ::= { xcmhEntry 2 }

xcmhRedundancyStatus  OBJECT-TYPE
    SYNTAX      InfnCorrelatedRedunStatus
    MAX-ACCESS read-only
    STATUS     current
    DESCRIPTION 
        "Indicates the status of the XCMH. Valid values:active, standby and makeStandbyInProgress"
    ::= { xcmhEntry 3 }

xcmhBrandingFault  OBJECT-TYPE
    SYNTAX     TruthValue
    MAX-ACCESS read-only
    STATUS     current
    DESCRIPTION 
        "This indiactes whether equpiment has branding faults."
    ::= { xcmhEntry 4 }

xcmhRowStatus  OBJECT-TYPE
    SYNTAX     RowStatus
    MAX-ACCESS read-create
    STATUS     current
    DESCRIPTION 
        "The row status of this XCMH entry.
                Because rows in this table are indexed by entPhysicalIndex, to create a new row one must
                choose a value of entPhysicalIndex that is not already in use.
        
                A side-effect of the creation of a row in this table is the creation of a corresponding
                row in the eqptTable and the entPhysicalTable.
        
                The status may not be set to active if the xcmhMoId and xcmhProvEqptType are not set to valid values.
        
                This row may only be deleted if it was a pre-provisioned row and the hardware is not present.
        
                If this row is deleted, the associated row in the Eqpt Table and entPhysicalTable will be
                deleted by the agent."
    ::= { xcmhEntry 5 }


xcmhCompliance  MODULE-COMPLIANCE
    STATUS     current
    DESCRIPTION 
        ""
    MODULE
        MANDATORY-GROUPS { xcmhGroup } 
    ::= { xcmhCompliances 1 }

xcmhGroup  OBJECT-GROUP
    OBJECTS 
	{ 
		xcmhBrandingFault, 
        xcmhMoId, 
        xcmhProvType, 
        xcmhRedundancyStatus,
		xcmhBrandingFault,
        xcmhRowStatus
	}
    STATUS     current
    DESCRIPTION 
        ""
    ::= { xcmhGroups 1 }
END

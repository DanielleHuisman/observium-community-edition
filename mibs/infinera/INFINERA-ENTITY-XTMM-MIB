-- ***************************************************************
-- INFINERA-ENTITY-XTMM-MIB
--   
-- September 2016, Anisha A
--   
--   
-- Copyright (c) 2016 by Infinera Inc.
-- All rights reserved.
-- ****************************************************************

INFINERA-ENTITY-XTMM-MIB DEFINITIONS ::= BEGIN

IMPORTS
    OBJECT-TYPE, MODULE-IDENTITY           FROM SNMPv2-SMI
    OBJECT-GROUP, MODULE-COMPLIANCE        FROM SNMPv2-CONF
    RowStatus, TruthValue, DisplayString   FROM SNMPv2-TC
    entLPPhysicalIndex                     FROM ENTITY-MIB
    equipment                              FROM INFINERA-REG-MIB
    InfnEqptType                           FROM INFINERA-TC-MIB;

xtmmMIB MODULE-IDENTITY
    LAST-UPDATED  "201608020000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for XTMM equipment table."

::= { equipment 54 } 

xtmmConformance       OBJECT IDENTIFIER ::= { xtmmMIB 3 }
xtmmCompliances       OBJECT IDENTIFIER ::= { xtmmConformance 1 }
xtmmGroups            OBJECT IDENTIFIER ::= { xtmmConformance 2 }

xtmmTable  OBJECT-TYPE
    SYNTAX SEQUENCE OF XtmmEntry
    MAX-ACCESS not-accessible
    STATUS     current
    DESCRIPTION 
        "This table contains all XTMM modules that are currently present in a network element.
        "
    ::= { xtmmMIB 1 }

xtmmEntry  OBJECT-TYPE
    SYNTAX     XtmmEntry
    MAX-ACCESS not-accessible
    STATUS     current
    DESCRIPTION 
        "A row in the XTMM table. Each row in the table is identified with a unique entPhysicalIndexID. 
        "
    INDEX { entLPPhysicalIndex }
    ::= { xtmmTable 1 }

XtmmEntry ::= SEQUENCE {
    xtmmMoId               DisplayString,
    xtmmProvType           InfnEqptType,
    xtmmBrandingFault      TruthValue,
    xtmmRowStatus          RowStatus
}

xtmmMoId  OBJECT-TYPE
    SYNTAX     DisplayString
    MAX-ACCESS read-create
    STATUS     current
    DESCRIPTION 
        "The object identifier."
    ::= { xtmmEntry 1 }

xtmmProvType  OBJECT-TYPE
    SYNTAX     InfnEqptType
    MAX-ACCESS read-create
    STATUS     current
    DESCRIPTION 
        "The configured XTMM type."
    ::= { xtmmEntry 2 }

xtmmBrandingFault  OBJECT-TYPE
    SYNTAX     TruthValue
    MAX-ACCESS read-only
    STATUS     current
    DESCRIPTION 
        "Indicates XTMM branding faults."
    ::= { xtmmEntry 3 }

xtmmRowStatus  OBJECT-TYPE
    SYNTAX     RowStatus
    MAX-ACCESS read-create
    STATUS     current
    DESCRIPTION 
        "The row status of this XTMM entry.
         Because rows in this table are indexed by entPhysicalIndex, to create a new row one must
         choose a value of entPhysicalIndex that is not already in use.
        
         A side-effect of the creation of a row in this table is the creation of a corresponding
         row in the eqptTable and the entPhysicalTable.
        
         The status may not be set to active if the xtmmMoId and xtmmProvEqptType are not set to valid values.
        
         This row may only be deleted if it was a pre-provisioned row and the hardware is not present.
        
         If this row is deleted, the associated row in the Eqpt Table and entPhysicalTable will be
         deleted by the agent."
    ::= { xtmmEntry 4 }

xtmmCompliance  MODULE-COMPLIANCE
    STATUS     current
    DESCRIPTION 
        ""
    MODULE
        MANDATORY-GROUPS { xtmmGroup } 
    ::= { xtmmCompliances 1 }

xtmmGroup  OBJECT-GROUP
    OBJECTS { xtmmBrandingFault, 
        xtmmMoId, 
        xtmmProvType, 
        xtmmRowStatus }
    STATUS     current
    DESCRIPTION 
        ""
    ::= { xtmmGroups 1 }
END

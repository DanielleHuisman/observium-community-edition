-- *****************************************************************
-- INFINERA-PM-CMMOCHPTP-MIB
-- 
-- October 2008, Sharfuddin Syed / Narendra Gupta
-- 
-- 
-- Copyright (c) 2008-2012 by Infinera Inc.
-- All rights reserved.
-- ****************************************************************

INFINERA-PM-CMMOCHPTP-MIB DEFINITIONS ::= BEGIN

IMPORTS
    MODULE-IDENTITY, OBJECT-TYPE,
    Integer32                                   FROM SNMPv2-SMI
    MODULE-COMPLIANCE, OBJECT-GROUP             FROM SNMPv2-CONF
    TruthValue                                  FROM SNMPv2-TC
    ifIndex                                     FROM IF-MIB
    FloatHundredths                                 FROM INFINERA-TC-MIB
    perfMon                                         FROM INFINERA-REG-MIB;


cmmOchPtpPmMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "200810200000Z" 
    DESCRIPTION
        "First Version"
    ::= { perfMon 26 }



cmmOchPtpPmTable OBJECT-TYPE
    SYNTAX      SEQUENCE OF CmmOchPtpPmEntry
    MAX-ACCESS  not-accessible
    STATUS      current
    DESCRIPTION
        "A list of CmmOchPtpPm entries. Each entry is uniquely identified by the value of ifIndex, Sample Duration and cmmOchPtpPmTimestamp."
    ::= { cmmOchPtpPmMIB 2 } 

cmmOchPtpPmEntry  OBJECT-TYPE
    SYNTAX      CmmOchPtpPmEntry
    MAX-ACCESS  not-accessible
    STATUS      current
    DESCRIPTION
        "A CmmOchPtp entry containing historical performance information pertaining to Infinera CMM OCG PTP interfaces.
        This table is a subclass of IfCommon. Entries will exist in this table only for interfaces
        of type CMM OCG PTP.
        Each interface may have a number of entries in this table, each with a different combination of timestamp
        and sample duration."
    INDEX { ifIndex, cmmOchPtpPmSampleDuration, cmmOchPtpPmTimestamp }
    ::= { cmmOchPtpPmTable 1 }


CmmOchPtpPmEntry  ::= SEQUENCE {
    cmmOchPtpPmTimestamp        Integer32,
    cmmOchPtpPmSampleDuration   INTEGER,
    cmmOchPtpPmValidity         TruthValue,
    cmmOchPtpPmCmmOchOptMin     FloatHundredths,
    cmmOchPtpPmCmmOchOptMax     FloatHundredths,
    cmmOchPtpPmCmmOchOptAve     FloatHundredths,
    cmmOchPtpPmCmmOchOprMin     FloatHundredths,
    cmmOchPtpPmCmmOchOprMax     FloatHundredths,
    cmmOchPtpPmCmmOchOprAve     FloatHundredths
}

cmmOchPtpPmTimestamp OBJECT-TYPE
    SYNTAX      Integer32 (0..2147483647)
    MAX-ACCESS  not-accessible
    STATUS      current
    DESCRIPTION
        "End Time stamp for this interval. If this time is later than the current time,
        then the data for this bucket is currently being collected."
    ::= { cmmOchPtpPmEntry  1 }


cmmOchPtpPmSampleDuration OBJECT-TYPE
    SYNTAX      INTEGER {
                    fifteenMinutes(1),
                    day(2)
                }
    MAX-ACCESS  not-accessible
    STATUS      current
    DESCRIPTION
        "The duration of this sample."
    ::= { cmmOchPtpPmEntry  2 }


cmmOchPtpPmValidity OBJECT-TYPE
    SYNTAX      TruthValue
    MAX-ACCESS  read-only
    STATUS      current
    DESCRIPTION "Flag indicating if data was valid for the entire interval"
    ::= { cmmOchPtpPmEntry  3 }


cmmOchPtpPmCmmOchOptMin OBJECT-TYPE
    SYNTAX      FloatHundredths
    MAX-ACCESS  read-only
    STATUS      current
    DESCRIPTION "Minimum OCG optical power leaving the CMM towards its attached XLM/DLM or GAM."
    ::= { cmmOchPtpPmEntry  4 }


cmmOchPtpPmCmmOchOptMax OBJECT-TYPE
    SYNTAX      FloatHundredths
    MAX-ACCESS  read-only
    STATUS      current
    DESCRIPTION "Maximum OCG optical power leaving the CMM towards its attached XLM/DLM or GAM."
    ::= { cmmOchPtpPmEntry  5 }


cmmOchPtpPmCmmOchOptAve OBJECT-TYPE
    SYNTAX      FloatHundredths
    MAX-ACCESS  read-only
    STATUS      current
    DESCRIPTION "Average OCG optical power leaving the CMM towards its attached XLM/DLM or GAM."
    ::= { cmmOchPtpPmEntry  6 }


cmmOchPtpPmCmmOchOprMin OBJECT-TYPE
    SYNTAX      FloatHundredths
    MAX-ACCESS  read-only
    STATUS      current
    DESCRIPTION "Minimum OCG optical power arriving at the CMM from the local XLM/DLM or GAM."
    ::= { cmmOchPtpPmEntry  7 }


cmmOchPtpPmCmmOchOprMax OBJECT-TYPE
    SYNTAX      FloatHundredths
    MAX-ACCESS  read-only
    STATUS      current
    DESCRIPTION "Maximum OCG optical power arriving at the CMM from the local XLM/DLM or GAM."
    ::= { cmmOchPtpPmEntry  8 }


cmmOchPtpPmCmmOchOprAve OBJECT-TYPE
    SYNTAX      FloatHundredths
    MAX-ACCESS  read-only
    STATUS      current
    DESCRIPTION "Average OCG optical power arriving at the CMM from the local XLM/DLM or GAM."
    ::= { cmmOchPtpPmEntry  9 }




cmmOchPtpPmRealTable OBJECT-TYPE
    SYNTAX      SEQUENCE OF CmmOchPtpPmRealEntry
    MAX-ACCESS  not-accessible
    STATUS      current
    DESCRIPTION
        "A list of CmmOchPtpPmReal entries. Each entry is uniquely identified by the value of ifIndex."
    ::= { cmmOchPtpPmMIB 1 } 

cmmOchPtpPmRealEntry  OBJECT-TYPE
    SYNTAX      CmmOchPtpPmRealEntry
    MAX-ACCESS  not-accessible
    STATUS      current
    DESCRIPTION
        "A CmmOchPtp entry containing real-time performance information pertaining to Infinera
        CMM OCG PTP interfaces. This table is a subclass of IfCommon. Entries will exist in this
        table only for interfaces of type CMM OCG PTP."
    INDEX { ifIndex }
    ::= { cmmOchPtpPmRealTable 1 }


CmmOchPtpPmRealEntry  ::= SEQUENCE {
    cmmOchPtpPmRealCmmOchOpt               FloatHundredths,
    cmmOchPtpPmRealCmmOchOpr               FloatHundredths
}

cmmOchPtpPmRealCmmOchOpt OBJECT-TYPE
    SYNTAX      FloatHundredths
    MAX-ACCESS  read-only
    STATUS      current
    DESCRIPTION "Total OCG optical power leaving the CMM towards its attached XLM/DLM or GAM. One attribute for each OCG."
    ::= { cmmOchPtpPmRealEntry  1 }


cmmOchPtpPmRealCmmOchOpr OBJECT-TYPE
    SYNTAX      FloatHundredths
    MAX-ACCESS  read-only
    STATUS      current
    DESCRIPTION "Total OCG optical power arriving at the CMM from the local XLM/DLM or GAM. One attribute for each OCG."
    ::= { cmmOchPtpPmRealEntry  2 }

-- Conformance Statements
cmmOchPtpPmConformance    OBJECT IDENTIFIER ::= { cmmOchPtpPmMIB 3 }
cmmOchPtpPmCompliances    OBJECT IDENTIFIER ::= { cmmOchPtpPmConformance 1 }
cmmOchPtpPmGroups         OBJECT IDENTIFIER ::= { cmmOchPtpPmConformance 2 }

cmmOchPtpPmCompliance MODULE-COMPLIANCE
    STATUS current
    DESCRIPTION
    "Describes the requirements for conformance to the CMMOCHPTP-MIB"
    MODULE
        MANDATORY-GROUPS { cmmOchPtpPmGroup }
    ::= { cmmOchPtpPmCompliances 1 }

cmmOchPtpPmRealCompliance MODULE-COMPLIANCE
    STATUS current
    DESCRIPTION
    "Describes the requirements for conformance to the cmmOchPtpPmReal-MIB"
    MODULE
        MANDATORY-GROUPS { cmmOchPtpPmRealGroup }
    ::= { cmmOchPtpPmCompliances 2 }

cmmOchPtpPmGroup OBJECT-GROUP
    OBJECTS {
        cmmOchPtpPmValidity,
        cmmOchPtpPmCmmOchOptMin,
        cmmOchPtpPmCmmOchOptMax,
        cmmOchPtpPmCmmOchOptAve,
        cmmOchPtpPmCmmOchOprMin,
        cmmOchPtpPmCmmOchOprMax,
        cmmOchPtpPmCmmOchOprAve
    }
    STATUS current
    DESCRIPTION
        " A collection of objects for reading the historical performance of the cmmOchPtp."
    ::= { cmmOchPtpPmGroups 1 }

cmmOchPtpPmRealGroup OBJECT-GROUP
    OBJECTS {
        cmmOchPtpPmRealCmmOchOpt,
        cmmOchPtpPmRealCmmOchOpr
    }
    STATUS current
    DESCRIPTION
        " A collection of objects for reading the real-time performance of the cmmOchPtp."
    ::= { cmmOchPtpPmGroups 2 }


END

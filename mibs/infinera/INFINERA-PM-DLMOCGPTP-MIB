-- *****************************************************************
-- INFINERA-PM-DLMOCGPTP-MIB
-- 
-- October 2008, Sharfuddin Syed / Narendra Gupta
-- 
-- 
-- Copyright (c) 2008-2012 by Infinera Inc.
-- All rights reserved.
-- ****************************************************************

INFINERA-PM-DLMOCGPTP-MIB DEFINITIONS ::= BEGIN

IMPORTS
    MODULE-IDENTITY, OBJECT-TYPE,
    Integer32                                   FROM SNMPv2-SMI
    MODULE-COMPLIANCE, OBJECT-GROUP             FROM SNMPv2-CONF
    DisplayString                               FROM SNMPv2-TC
    ifIndex                                     FROM IF-MIB
    FloatHundredths                                 FROM INFINERA-TC-MIB
    perfMon                                         FROM INFINERA-REG-MIB;


dlmOcgPtpPmMIB MODULE-IDENTITY
    LAST-UPDATED  "200810200000Z" 
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "200810200000Z" 
    DESCRIPTION
        "First Version"
    ::= { perfMon 5 }



dlmOcgPtpPmRealTable OBJECT-TYPE
    SYNTAX      SEQUENCE OF DlmOcgPtpPmRealEntry
    MAX-ACCESS  not-accessible
    STATUS      current
    DESCRIPTION
        "A list of DlmOcgPtpPmReal entries. Each entry is uniquely identified by the value of ifIndex."
    ::= { dlmOcgPtpPmMIB 1 } 

dlmOcgPtpPmRealEntry  OBJECT-TYPE
    SYNTAX      DlmOcgPtpPmRealEntry
    MAX-ACCESS  not-accessible
    STATUS      current
    DESCRIPTION
        "A DlmOcgPtpPmReal entry containing real-time performance information pertaining to Infinera DlmOcgPtp interfaces.
        This table is a subclass of IfCommon.
        Entries will exist in this table only for interfaces of type DlmOcgPtp."
    INDEX { ifIndex }
    ::= { dlmOcgPtpPmRealTable 1 }


DlmOcgPtpPmRealEntry  ::= SEQUENCE {
    dlmOcgPtpPmRealDlmOcgOpt    FloatHundredths,
    dlmOcgPtpPmRealDlmOcgOpr    FloatHundredths
}

dlmOcgPtpPmRealDlmOcgOpt OBJECT-TYPE
    SYNTAX      FloatHundredths
    MAX-ACCESS  read-only
    STATUS      current
    DESCRIPTION "OCG optical power transmitted."
    ::= { dlmOcgPtpPmRealEntry  1 }


dlmOcgPtpPmRealDlmOcgOpr OBJECT-TYPE
    SYNTAX      FloatHundredths
    MAX-ACCESS  read-only
    STATUS      current
    DESCRIPTION "OCG optical power received."
    ::= { dlmOcgPtpPmRealEntry  2 }

-- Conformance Statements
dlmOcgPtpPmConformance    OBJECT IDENTIFIER ::= { dlmOcgPtpPmMIB 3 }
dlmOcgPtpPmCompliances    OBJECT IDENTIFIER ::= { dlmOcgPtpPmConformance 1 }
dlmOcgPtpPmGroups         OBJECT IDENTIFIER ::= { dlmOcgPtpPmConformance 2 }

dlmOcgPtpPmRealCompliance MODULE-COMPLIANCE
    STATUS current
    DESCRIPTION
    "Describes the requirements for conformance to the PM-DLMOCGPTP-MIB"
    MODULE
        MANDATORY-GROUPS { dlmOcgPtpPmRealGroup }
    ::= { dlmOcgPtpPmCompliances 1 }

dlmOcgPtpPmRealGroup OBJECT-GROUP
    OBJECTS {
        dlmOcgPtpPmRealDlmOcgOpt,
        dlmOcgPtpPmRealDlmOcgOpr
    }
    STATUS current
    DESCRIPTION
        " A collection of objects for reading the current real-time performance of the dlmOcgPtp."
    ::= { dlmOcgPtpPmGroups 1 }


END

-- *****************************************************************
-- INFINERA-PM-FBMSCGPTP-MIB
-- February 2017, Mithun Murthy
--
-- Copyright (c) 2008-2015 by Infinera Inc.
-- All rights reserved.
-- ****************************************************************

INFINERA-PM-FBMSCGPTP-MIB DEFINITIONS ::= BEGIN

IMPORTS
    MODULE-IDENTITY, OBJECT-TYPE,
    Integer32                                   FROM SNMPv2-SMI
    MODULE-COMPLIANCE, OBJECT-GROUP             FROM SNMPv2-CONF
    TruthValue                                  FROM SNMPv2-TC
    ifIndex                                     FROM IF-MIB
    FloatArbitraryPrecision,
    InfnSampleDuration                          FROM INFINERA-TC-MIB
    perfMon                                     FROM INFINERA-REG-MIB;


fbmScgptpPmMIB MODULE-IDENTITY
    LAST-UPDATED  "201703230000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "201702130000Z"
    DESCRIPTION
        "First Version"
    ::= { perfMon 83 }

fbmScgptpPmTable OBJECT-TYPE
    SYNTAX      SEQUENCE OF FbmScgPtpPmEntry
    MAX-ACCESS  not-accessible
    STATUS      current
    DESCRIPTION
        "A list of FbmScgPtpPm entries. Each entry is uniquely identified by the value of ifIndex."
    ::= { fbmScgptpPmMIB 2 }

fbmScgptpPmEntry  OBJECT-TYPE
    SYNTAX      FbmScgPtpPmEntry
    MAX-ACCESS  not-accessible
    STATUS      current
    DESCRIPTION
        "A FbmScgPtp entry containing historical performance information pertaining to Infinera FBMSCGPTPPTP.
        This table is a subclass of IfCommon. Entries will exist in this table only for interfaces
        of type FBMSCGPTP."
    INDEX { ifIndex, fbmScgptpPmSampleDuration, fbmScgptpPmTimestamp}
    ::= { fbmScgptpPmTable 1 }


FbmScgPtpPmEntry  ::= SEQUENCE {
   fbmScgptpPmTimestamp          Integer32,
   fbmScgptpPmSampleDuration     INTEGER,
   fbmScgptpPmValidity           TruthValue,
   fbmScgptpPmCmnScgOptMin       FloatArbitraryPrecision,
   fbmScgptpPmCmnScgOptMax       FloatArbitraryPrecision,
   fbmScgptpPmCmnScgOptAve       FloatArbitraryPrecision,
   fbmScgptpPmCmnScgOprMin       FloatArbitraryPrecision,
   fbmScgptpPmCmnScgOprMax       FloatArbitraryPrecision,
   fbmScgptpPmCmnScgOprAve       FloatArbitraryPrecision
}


fbmScgptpPmTimestamp OBJECT-TYPE
    SYNTAX      Integer32 (0..2147483647)
    MAX-ACCESS  not-accessible
    STATUS      current
    DESCRIPTION
        "End Time stamp for this interval. If this time is later than the current time,then the data for this bucket is currently being collected."
    ::= { fbmScgptpPmEntry  1 }


fbmScgptpPmSampleDuration OBJECT-TYPE
    SYNTAX      InfnSampleDuration
    MAX-ACCESS  not-accessible
    STATUS      current
    DESCRIPTION
        "The duration of this sample."
    ::= { fbmScgptpPmEntry  2 }

fbmScgptpPmValidity OBJECT-TYPE
    SYNTAX      TruthValue
    MAX-ACCESS  read-only
    STATUS      current
    DESCRIPTION "Flag indicating if data was valid for the entire interval"
    ::= { fbmScgptpPmEntry  3 }

fbmScgptpPmCmnScgOptMin    OBJECT-TYPE
    SYNTAX          FloatArbitraryPrecision
    MAX-ACCESS      read-only
    STATUS          current
    DESCRIPTION     ""
    ::= { fbmScgptpPmEntry  4 }

 fbmScgptpPmCmnScgOptMax    OBJECT-TYPE
    SYNTAX          FloatArbitraryPrecision
    MAX-ACCESS      read-only
    STATUS          current
    DESCRIPTION     ""
    ::= { fbmScgptpPmEntry  5 }

fbmScgptpPmCmnScgOptAve     OBJECT-TYPE
    SYNTAX          FloatArbitraryPrecision
    MAX-ACCESS      read-only
    STATUS          current
    DESCRIPTION     ""
    ::= { fbmScgptpPmEntry  6 }

fbmScgptpPmCmnScgOprMin    OBJECT-TYPE
    SYNTAX          FloatArbitraryPrecision
    MAX-ACCESS      read-only
    STATUS          current
    DESCRIPTION     ""
    ::= { fbmScgptpPmEntry  7 }

 fbmScgptpPmCmnScgOprMax    OBJECT-TYPE
    SYNTAX          FloatArbitraryPrecision
    MAX-ACCESS      read-only
    STATUS          current
    DESCRIPTION     ""
    ::= { fbmScgptpPmEntry  8 }

fbmScgptpPmCmnScgOprAve     OBJECT-TYPE
    SYNTAX          FloatArbitraryPrecision
    MAX-ACCESS      read-only
    STATUS          current
    DESCRIPTION     ""
    ::= { fbmScgptpPmEntry  9 }

fbmScgptpPmRealTable OBJECT-TYPE
    SYNTAX      SEQUENCE OF FbmScgPtpPmRealEntry
    MAX-ACCESS  not-accessible
    STATUS      current
    DESCRIPTION
        "A list of FbmScgPtpPmReal entries. Each entry is uniquely identified by the value of ifIndex."
    ::= { fbmScgptpPmMIB 1 }

fbmScgptpPmRealEntry  OBJECT-TYPE
    SYNTAX      FbmScgPtpPmRealEntry
    MAX-ACCESS  not-accessible
    STATUS      current
    DESCRIPTION
        "A  fbmScgptp entry containing real-time performance information pertaining to Infinera
         fbmScgptp interfaces. This table is a subclass of IfCommon."
    INDEX { ifIndex }
    ::= { fbmScgptpPmRealTable 1 }


FbmScgPtpPmRealEntry  ::= SEQUENCE {
    fbmScgptpPmRealCmnScgOpt       FloatArbitraryPrecision,
    fbmScgptpPmRealCmnScgOpr       FloatArbitraryPrecision
}

fbmScgptpPmRealCmnScgOpt OBJECT-TYPE
    SYNTAX      FloatArbitraryPrecision
    MAX-ACCESS  read-only
    STATUS      current
    DESCRIPTION ""
    ::= { fbmScgptpPmRealEntry  1 }

fbmScgptpPmRealCmnScgOpr OBJECT-TYPE
    SYNTAX      FloatArbitraryPrecision
    MAX-ACCESS  read-only
    STATUS      current
    DESCRIPTION ""
    ::= { fbmScgptpPmRealEntry  2 }


-- Conformance Statements
fbmScgptpPmConformance    OBJECT IDENTIFIER ::= { fbmScgptpPmMIB 3 }
fbmScgptpPmCompliances    OBJECT IDENTIFIER ::= { fbmScgptpPmConformance 1 }
fbmScgptpPmGroups         OBJECT IDENTIFIER ::= { fbmScgptpPmConformance 2 }

fbmScgptpPmCompliance MODULE-COMPLIANCE
    STATUS current
    DESCRIPTION
    "Describes the requirements for conformance to the  fbmScgptp-MIB"
    MODULE
        MANDATORY-GROUPS { fbmScgptpPmGroup }
    ::= { fbmScgptpPmCompliances 1 }

fbmScgptpPmRealCompliance MODULE-COMPLIANCE
    STATUS current
    DESCRIPTION
    "Describes the requirements for conformance to the FbmScgPtpPmReal-MIB"
    MODULE
        MANDATORY-GROUPS { fbmScgptpPmRealGroup }
    ::= { fbmScgptpPmCompliances 2 }

fbmScgptpPmGroup OBJECT-GROUP
    OBJECTS {
        fbmScgptpPmTimestamp,
        fbmScgptpPmSampleDuration,
        fbmScgptpPmValidity,
        fbmScgptpPmCmnScgOptMin,
        fbmScgptpPmCmnScgOptMax,
        fbmScgptpPmCmnScgOptAve,
        fbmScgptpPmCmnScgOprMin,
        fbmScgptpPmCmnScgOprMax,
        fbmScgptpPmCmnScgOprAve
    }
    STATUS current
    DESCRIPTION
        " A collection of objects for reading the historical performance of the  fbmScgptp."
    ::= { fbmScgptpPmGroups 1 }

fbmScgptpPmRealGroup OBJECT-GROUP
    OBJECTS {
        fbmScgptpPmRealCmnScgOpt,
        fbmScgptpPmRealCmnScgOpr
    }
    STATUS current
    DESCRIPTION
        " A collection of objects for reading the real-time performance of the  fbmScgptp."
    ::= { fbmScgptpPmGroups 2 }

END

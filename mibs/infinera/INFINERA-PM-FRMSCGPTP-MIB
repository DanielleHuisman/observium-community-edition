-- *****************************************************************
-- INFINERA-PM-FRMSCGPTP-MIB
-- 
-- October 2013, Rishab Joshi
-- 
-- 
-- Copyright (c) 2008-2013 by Infinera Inc.
-- All rights reserved.
-- ****************************************************************

INFINERA-PM-FRMSCGPTP-MIB DEFINITIONS ::= BEGIN

IMPORTS
    MODULE-IDENTITY, OBJECT-TYPE,
    Integer32                                   FROM SNMPv2-SMI
    MODULE-COMPLIANCE, OBJECT-GROUP             FROM SNMPv2-CONF
    TruthValue                                  FROM SNMPv2-TC
    ifIndex                                     FROM IF-MIB
    FloatHundredths, InfnSampleDuration         FROM INFINERA-TC-MIB
    perfMon                                     FROM INFINERA-REG-MIB;


frmScgPtpPmMIB MODULE-IDENTITY
    LAST-UPDATED  "201310080000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "201310080000Z" 
    DESCRIPTION
        "First Version"
    ::= { perfMon 41 }


frmScgPtpPmTable OBJECT-TYPE
    SYNTAX      SEQUENCE OF FrmScgPtpPmEntry
    MAX-ACCESS  not-accessible
    STATUS      current
    DESCRIPTION
        "A list of FrmScgPtpPm entries. Each entry is uniquely identified by the value of ifIndex."
    ::= { frmScgPtpPmMIB 2 } 

frmScgPtpPmEntry  OBJECT-TYPE
    SYNTAX      FrmScgPtpPmEntry
    MAX-ACCESS  not-accessible
    STATUS      current
    DESCRIPTION
        "A FrmScgPtp entry containing historical performance information pertaining to Infinera OFXSCGPTP.
        This table is a subclass of IfCommon. Entries will exist in this table only for interfaces
        of type FRMSCGPTP."
    INDEX { ifIndex, frmScgPtpPmSampleDuration, frmScgPtpPmTimestamp}
    ::= { frmScgPtpPmTable 1 }


FrmScgPtpPmEntry  ::= SEQUENCE {
   frmScgPtpPmTimestamp        Integer32,
   frmScgPtpPmSampleDuration   INTEGER,
   frmScgPtpPmValidity         TruthValue,
   frmScgPtpPmCmnScgOptMin     FloatHundredths,
   frmScgPtpPmCmnScgOptMax     FloatHundredths,
   frmScgPtpPmCmnScgOptAve     FloatHundredths,
   frmScgPtpPmCmnScgOprMin     FloatHundredths,
   frmScgPtpPmCmnScgOprMax     FloatHundredths,
   frmScgPtpPmCmnScgOprAve     FloatHundredths
}


frmScgPtpPmTimestamp OBJECT-TYPE
    SYNTAX      Integer32 (0..2147483647)
    MAX-ACCESS  not-accessible
    STATUS      current
    DESCRIPTION
        "End Time stamp for this interval. If this time is later than the current time,then the data for this bucket is currently being collected."
    ::= { frmScgPtpPmEntry  1 }


frmScgPtpPmSampleDuration OBJECT-TYPE
    SYNTAX      INTEGER {
        fifteenMinutes(1),
        day(2)
    }
    MAX-ACCESS  not-accessible
    STATUS      current
    DESCRIPTION
        "The duration of this sample."
    ::= { frmScgPtpPmEntry  2 }

frmScgPtpPmValidity OBJECT-TYPE
    SYNTAX      TruthValue
    MAX-ACCESS  read-only
    STATUS      current
    DESCRIPTION "Flag indicating if data was valid for the entire interval"
    ::= { frmScgPtpPmEntry  3 }


frmScgPtpPmCmnScgOptMin OBJECT-TYPE
    SYNTAX      FloatHundredths
    MAX-ACCESS  read-only
    STATUS      current
    DESCRIPTION "Minimum FrmScg optical power min."
    ::= { frmScgPtpPmEntry  4 }


frmScgPtpPmCmnScgOptMax OBJECT-TYPE
    SYNTAX      FloatHundredths
    MAX-ACCESS  read-only
    STATUS      current
    DESCRIPTION "Maximum FrmScg optical power max."
    ::= { frmScgPtpPmEntry  5 }


frmScgPtpPmCmnScgOptAve OBJECT-TYPE
    SYNTAX      FloatHundredths
    MAX-ACCESS  read-only
    STATUS      current
    DESCRIPTION "Average FrmScg optical power ave."
    ::= { frmScgPtpPmEntry  6 }


frmScgPtpPmCmnScgOprMin OBJECT-TYPE
    SYNTAX      FloatHundredths
    MAX-ACCESS  read-only
    STATUS      current
    DESCRIPTION "Minimum FrmScg optical power min."
    ::= { frmScgPtpPmEntry  7}


frmScgPtpPmCmnScgOprMax OBJECT-TYPE
    SYNTAX      FloatHundredths
    MAX-ACCESS  read-only
    STATUS      current
    DESCRIPTION "Maximum FrmScg optical power max."
    ::= { frmScgPtpPmEntry  8}


frmScgPtpPmCmnScgOprAve OBJECT-TYPE
    SYNTAX      FloatHundredths
    MAX-ACCESS  read-only
    STATUS      current
    DESCRIPTION "Average FrmScg optical power ave."
    ::= { frmScgPtpPmEntry  9}




frmScgPtpPmRealTable OBJECT-TYPE
    SYNTAX      SEQUENCE OF FrmScgPtpPmRealEntry
    MAX-ACCESS  not-accessible
    STATUS      current
    DESCRIPTION
        "A list of FrmScgPtpPmReal entries. Each entry is uniquely identified by the value of ifIndex."
    ::= { frmScgPtpPmMIB 1 } 

frmScgPtpPmRealEntry  OBJECT-TYPE
    SYNTAX      FrmScgPtpPmRealEntry
    MAX-ACCESS  not-accessible
    STATUS      current
    DESCRIPTION
        "A  frmScgPtp entry containing real-time performance information pertaining to Infinera
         frmScgPtp interfaces. This table is a subclass of IfCommon."
    INDEX { ifIndex }
    ::= { frmScgPtpPmRealTable 1 }


FrmScgPtpPmRealEntry  ::= SEQUENCE {
    frmScgPtpPmRealCmnScgOpt       FloatHundredths,
    frmScgPtpPmRealCmnScgOpr       FloatHundredths
}

frmScgPtpPmRealCmnScgOpt OBJECT-TYPE
    SYNTAX      FloatHundredths
    MAX-ACCESS  read-only
    STATUS      current
    DESCRIPTION "Total FrmScg optical power trasmit."
    ::= { frmScgPtpPmRealEntry  1 }


frmScgPtpPmRealCmnScgOpr OBJECT-TYPE
    SYNTAX      FloatHundredths
    MAX-ACCESS  read-only
    STATUS      current
    DESCRIPTION "Total FrmScg optical power receive."
    ::= { frmScgPtpPmRealEntry  2 }



-- Conformance Statements
frmScgPtpPmConformance    OBJECT IDENTIFIER ::= { frmScgPtpPmMIB 3 }
frmScgPtpPmCompliances    OBJECT IDENTIFIER ::= { frmScgPtpPmConformance 1 }
frmScgPtpPmGroups         OBJECT IDENTIFIER ::= { frmScgPtpPmConformance 2 }

frmScgPtpPmCompliance MODULE-COMPLIANCE
    STATUS current
    DESCRIPTION
    "Describes the requirements for conformance to the  frmScgPtp-MIB"
    MODULE
        MANDATORY-GROUPS { frmScgPtpPmGroup }
    ::= { frmScgPtpPmCompliances 1 }

frmScgPtpPmRealCompliance MODULE-COMPLIANCE
    STATUS current
    DESCRIPTION
    "Describes the requirements for conformance to the FrmScgPtpPmReal-MIB"
    MODULE
        MANDATORY-GROUPS { frmScgPtpPmRealGroup }
    ::= { frmScgPtpPmCompliances 2 }

frmScgPtpPmGroup OBJECT-GROUP
    OBJECTS {
        frmScgPtpPmTimestamp,
        frmScgPtpPmSampleDuration,
        frmScgPtpPmValidity,     
        frmScgPtpPmCmnScgOptMin, 
        frmScgPtpPmCmnScgOptMax, 
        frmScgPtpPmCmnScgOptAve, 
        frmScgPtpPmCmnScgOprMin, 
        frmScgPtpPmCmnScgOprMax, 
        frmScgPtpPmCmnScgOprAve  
    }
    STATUS current
    DESCRIPTION
        " A collection of objects for reading the historical performance of the  frmScgPtp."
    ::= { frmScgPtpPmGroups 1 }

frmScgPtpPmRealGroup OBJECT-GROUP
    OBJECTS {
        frmScgPtpPmRealCmnScgOpt,
        frmScgPtpPmRealCmnScgOpr
    }
    STATUS current
    DESCRIPTION
        " A collection of objects for reading the real-time performance of the  frmScgPtp."
    ::= { frmScgPtpPmGroups 2 }

END

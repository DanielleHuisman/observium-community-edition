-- *****************************************************************
-- INFINERA-PM-GIGECLIENTCTP-MIB
-- 
-- Aug 2011, Sharfuddin Syed / Narendra Gupta
-- 
-- 
-- Copyright (c) 2011-2012 by Infinera Inc.
-- All rights reserved.
-- ****************************************************************

INFINERA-PM-GFPCLIENTCTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    HCPerfIntervalCount                         FROM HC-PerfHist-TC-MIB
    FloatHundredths,InfnServiceType             FROM INFINERA-TC-MIB
    perfMon                                     FROM INFINERA-REG-MIB;


gfpClientCtpPmMIB MODULE-IDENTITY
    LAST-UPDATED  "201110200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "201110200000Z" 
    DESCRIPTION
        "First Version"
    ::= { perfMon 28 }



gfpClientCtpPmTable OBJECT-TYPE
    SYNTAX      SEQUENCE OF GfpClientCtpPmEntry
    MAX-ACCESS  not-accessible
    STATUS      current
    DESCRIPTION
        "A list of GfpClientCtpPm entries. Each entry is uniquely identified by the value of ifIndex, sampleDuration and gfpClientCtpPmTimestamp."
    ::= { gfpClientCtpPmMIB 2 } 

gfpClientCtpPmEntry  OBJECT-TYPE
    SYNTAX      GfpClientCtpPmEntry
    MAX-ACCESS  not-accessible
    STATUS      current
    DESCRIPTION
        "A GfpClientCtp entry containing historical performance information pertaining to Infinera
        GfpClientCtp interfaces. This table is a subclass of IfCommon. Entries will exist in this
        table only for interfaces of type GfpClientCtp.
        Each interface may have a number of entries in this table, each with a different combination
        of timestamp and sample duration."
    INDEX { ifIndex, gfpClientCtpPmSampleDuration, gfpClientCtpPmTimestamp }
    ::= { gfpClientCtpPmTable 1 }


GfpClientCtpPmEntry  ::= SEQUENCE {
    gfpClientCtpPmTimestamp            		Integer32,
    gfpClientCtpPmSampleDuration       		INTEGER,
    gfpClientCtpPmDataFrames             	HCPerfIntervalCount,
    gfpClientCtpPmMgmtFrames             	HCPerfIntervalCount,
    gfpClientCtpPmIdleFrames             	HCPerfIntervalCount,
    gfpClientCtpPmOtherFrames           	HCPerfIntervalCount,
    gfpClientCtpPmFCSFrames           		HCPerfIntervalCount,
    gfpClientCtpPmErrFCSFrames            	HCPerfIntervalCount,
    gfpClientCtpPmLinearEXIFrames            	HCPerfIntervalCount,
    gfpClientCtpPmNullEXIFrames           	HCPerfIntervalCount,
    gfpClientCtpPmSBitCHECErrors           	HCPerfIntervalCount,
    gfpClientCtpPmMBitCHECErrors            	HCPerfIntervalCount,
    gfpClientCtpPmSBitTHECErrors             	HCPerfIntervalCount,
    gfpClientCtpPmMBitTHECErrors       		HCPerfIntervalCount,
    gfpClientCtpPmSBitEHECErrors        	HCPerfIntervalCount,
    gfpClientCtpPmMBitEHECErrors       		HCPerfIntervalCount,
    gfpClientCtpPmEXIInvalid     	 	HCPerfIntervalCount,
    gfpClientCtpPmUPIInvalid        	 	HCPerfIntervalCount,
    gfpClientCtpPmCSFRaised         	 	HCPerfIntervalCount,
    gfpClientCtpPmOversized        	  	HCPerfIntervalCount,
    gfpClientCtpPmUndersized              	HCPerfIntervalCount,
    gfpClientCtpPmIngressOverflow      		HCPerfIntervalCount,
    gfpClientCtpPmRxEgressOverflow      	HCPerfIntervalCount
    
}

gfpClientCtpPmTimestamp OBJECT-TYPE
    SYNTAX      Integer32 (0..2147483647)
    MAX-ACCESS  not-accessible
    STATUS      current
    DESCRIPTION
        "End Time stamp for this interval. If this time is later than the current time,
        then the data for this bucket is currently being collected."
    ::= { gfpClientCtpPmEntry  1 }


gfpClientCtpPmSampleDuration OBJECT-TYPE
    SYNTAX      INTEGER {
                    fifteenMinutes(1),
                    day(2)
                }
    MAX-ACCESS  not-accessible
    STATUS      current
    DESCRIPTION
        "The duration of this sample."
    ::= { gfpClientCtpPmEntry  2 }


gfpClientCtpPmDataFrames OBJECT-TYPE
    SYNTAX     	HCPerfIntervalCount
    MAX-ACCESS  read-only
    STATUS      current
    DESCRIPTION ""
    ::= { gfpClientCtpPmEntry  3 }


gfpClientCtpPmMgmtFrames OBJECT-TYPE
    SYNTAX      HCPerfIntervalCount
    MAX-ACCESS  read-only
    STATUS      current
    DESCRIPTION ""
    ::= { gfpClientCtpPmEntry  4 }


gfpClientCtpPmIdleFrames OBJECT-TYPE
    SYNTAX      HCPerfIntervalCount
    MAX-ACCESS  read-only
    STATUS      current
    DESCRIPTION
        ""
    ::= { gfpClientCtpPmEntry  5 }


gfpClientCtpPmOtherFrames OBJECT-TYPE
    SYNTAX      HCPerfIntervalCount
    MAX-ACCESS  read-only
    STATUS      current
    DESCRIPTION
        "."
    ::= { gfpClientCtpPmEntry  6 }

gfpClientCtpPmFCSFrames OBJECT-TYPE
    SYNTAX      HCPerfIntervalCount
    MAX-ACCESS  read-only
    STATUS      current
    DESCRIPTION
        ""
    ::= { gfpClientCtpPmEntry  7 }


gfpClientCtpPmErrFCSFrames OBJECT-TYPE
    SYNTAX      HCPerfIntervalCount
    MAX-ACCESS  read-only
    STATUS      current
    DESCRIPTION
        ""
    ::= { gfpClientCtpPmEntry  8 }


gfpClientCtpPmLinearEXIFrames OBJECT-TYPE
    SYNTAX      HCPerfIntervalCount
    MAX-ACCESS  read-only
    STATUS      current
    DESCRIPTION "."
    ::= { gfpClientCtpPmEntry  9 }





gfpClientCtpPmNullEXIFrames OBJECT-TYPE
    SYNTAX      HCPerfIntervalCount
    MAX-ACCESS  read-only
    STATUS      current
    DESCRIPTION
        "."
    ::= { gfpClientCtpPmEntry  10 }


gfpClientCtpPmSBitCHECErrors OBJECT-TYPE
    SYNTAX     HCPerfIntervalCount 
    MAX-ACCESS  read-only
    STATUS      current
    DESCRIPTION
        "."
    ::= { gfpClientCtpPmEntry  11 }


gfpClientCtpPmMBitCHECErrors OBJECT-TYPE
    SYNTAX      HCPerfIntervalCount
    MAX-ACCESS  read-only
    STATUS      current
    DESCRIPTION "."
    ::= { gfpClientCtpPmEntry  12 }


gfpClientCtpPmSBitTHECErrors OBJECT-TYPE
    SYNTAX      HCPerfIntervalCount
    MAX-ACCESS  read-only
    STATUS      current
    DESCRIPTION "."
    ::= { gfpClientCtpPmEntry  13 }


gfpClientCtpPmMBitTHECErrors OBJECT-TYPE
    SYNTAX      HCPerfIntervalCount
    MAX-ACCESS  read-only
    STATUS      current
    DESCRIPTION "."
    ::= { gfpClientCtpPmEntry  14 }


gfpClientCtpPmSBitEHECErrors OBJECT-TYPE
    SYNTAX      HCPerfIntervalCount
    MAX-ACCESS  read-only
    STATUS      current
    DESCRIPTION "."
    ::= { gfpClientCtpPmEntry  15 }


gfpClientCtpPmMBitEHECErrors OBJECT-TYPE
    SYNTAX      HCPerfIntervalCount
    MAX-ACCESS  read-only
    STATUS      current
    DESCRIPTION "."
    ::= { gfpClientCtpPmEntry  16 }


gfpClientCtpPmEXIInvalid OBJECT-TYPE
    SYNTAX      HCPerfIntervalCount
    MAX-ACCESS  read-only
    STATUS      current
    DESCRIPTION "."
    ::= { gfpClientCtpPmEntry  17 }


gfpClientCtpPmUPIInvalid OBJECT-TYPE
    SYNTAX      HCPerfIntervalCount
    MAX-ACCESS  read-only
    STATUS      current
    DESCRIPTION "."
    ::= { gfpClientCtpPmEntry  18 }



gfpClientCtpPmCSFRaised  OBJECT-TYPE
    SYNTAX      HCPerfIntervalCount
    MAX-ACCESS  read-only
    STATUS      current
    DESCRIPTION
        ""
    ::= { gfpClientCtpPmEntry  19 }


gfpClientCtpPmOversized OBJECT-TYPE
    SYNTAX      HCPerfIntervalCount
    MAX-ACCESS  read-only
    STATUS      current
    DESCRIPTION
        "."
    ::= { gfpClientCtpPmEntry  20 }


gfpClientCtpPmUndersized OBJECT-TYPE
    SYNTAX      HCPerfIntervalCount
    MAX-ACCESS  read-only
    STATUS      current
    DESCRIPTION "."
    ::= { gfpClientCtpPmEntry  21 }


gfpClientCtpPmIngressOverflow      	OBJECT-TYPE
    SYNTAX      HCPerfIntervalCount
    MAX-ACCESS  read-only
    STATUS      current
    DESCRIPTION ""
    ::= { gfpClientCtpPmEntry  22 }

gfpClientCtpPmRxEgressOverflow  OBJECT-TYPE
    SYNTAX      HCPerfIntervalCount
    MAX-ACCESS  read-only
    STATUS      current
    DESCRIPTION ""
    ::= { gfpClientCtpPmEntry  23 }





gfpClientCtpPmRealTable OBJECT-TYPE
    SYNTAX      SEQUENCE OF GfpClientCtpPmRealEntry
    MAX-ACCESS  not-accessible
    STATUS      current
    DESCRIPTION
        "A list of GfpClientCtpPmReal entries. Each entry is uniquely identified by the value of ifIndex."
    ::= { gfpClientCtpPmMIB 1 } 

gfpClientCtpPmRealEntry  OBJECT-TYPE
    SYNTAX      GfpClientCtpPmRealEntry
    MAX-ACCESS  not-accessible
    STATUS      current
    DESCRIPTION
        "A GfpClientCtp entry containing real-time performance information pertaining to Infinera GfpClientCtp interfaces.
        This table is a subclass of IfCommon. Entries will exist in this table only for interfaces of
        type GfpClientCtp."
    INDEX { ifIndex }
    ::= { gfpClientCtpPmRealTable 1 }



GfpClientCtpPmRealEntry  ::= SEQUENCE {
   
    gfpClientCtpPmRealDataFrames              	Counter64 ,
    gfpClientCtpPmRealMgmtFrames              	Counter64 ,
    gfpClientCtpPmRealIdleFrames              	Counter64 ,
    gfpClientCtpPmRealOtherFrames             	Counter64 ,
    gfpClientCtpPmRealFCSFrames           	Counter64 ,
    gfpClientCtpPmRealErrFCSFrames              Counter64 ,
    gfpClientCtpPmRealLinearEXIFrames           Counter64 ,
    gfpClientCtpPmRealNullEXIFrames             Counter64 ,
    gfpClientCtpPmRealSBitCHECErrors            Counter64 ,
    gfpClientCtpPmRealMBitCHECErrors            Counter64 ,
    gfpClientCtpPmRealSBitTHECErrors            Counter64 ,
    gfpClientCtpPmRealMBitTHECErrors        	Counter64 ,
    gfpClientCtpPmRealSBitEHECErrors         	Counter64 ,
    gfpClientCtpPmRealMBitEHECErrors       	Counter64 ,
    gfpClientCtpPmRealEXIInvalid     	  	Counter64 ,
    gfpClientCtpPmRealUPIInvalid        	Counter64 ,
    gfpClientCtpPmRealCSFRaised         	Counter64 ,
    gfpClientCtpPmRealOversized        	   	Counter64 ,
    gfpClientCtpPmRealUndersized               	Counter64 ,
    gfpClientCtpPmRealIngressOverflow      	Counter64 ,
    gfpClientCtpPmRealRxEgressOverflow       	Counter64  
}




gfpClientCtpPmRealDataFrames OBJECT-TYPE
    SYNTAX     	HCPerfIntervalCount
    MAX-ACCESS  read-only
    STATUS      current
    DESCRIPTION ""
    ::= { gfpClientCtpPmRealEntry  1 }


gfpClientCtpPmRealMgmtFrames OBJECT-TYPE
    SYNTAX      HCPerfIntervalCount
    MAX-ACCESS  read-only
    STATUS      current
    DESCRIPTION ""
    ::= { gfpClientCtpPmRealEntry  2 }


gfpClientCtpPmRealIdleFrames OBJECT-TYPE
    SYNTAX      HCPerfIntervalCount
    MAX-ACCESS  read-only
    STATUS      current
    DESCRIPTION
        ""
    ::= { gfpClientCtpPmRealEntry  3 }


gfpClientCtpPmRealOtherFrames OBJECT-TYPE
    SYNTAX      HCPerfIntervalCount
    MAX-ACCESS  read-only
    STATUS      current
    DESCRIPTION
        "."
    ::= { gfpClientCtpPmRealEntry  4 }


gfpClientCtpPmRealFCSFrames OBJECT-TYPE
    SYNTAX      HCPerfIntervalCount
    MAX-ACCESS  read-only
    STATUS      current
    DESCRIPTION
        ""
    ::= { gfpClientCtpPmRealEntry  5 }

gfpClientCtpPmRealErrFCSFrames OBJECT-TYPE
    SYNTAX     HCPerfIntervalCount 
    MAX-ACCESS  read-only
    STATUS      current
    DESCRIPTION
        "."
    ::= { gfpClientCtpPmRealEntry  6 }



gfpClientCtpPmRealLinearEXIFrames OBJECT-TYPE
    SYNTAX      HCPerfIntervalCount
    MAX-ACCESS  read-only
    STATUS      current
    DESCRIPTION "."
    ::= { gfpClientCtpPmRealEntry  7 }




gfpClientCtpPmRealNullEXIFrames OBJECT-TYPE
    SYNTAX     HCPerfIntervalCount 
    MAX-ACCESS  read-only
    STATUS      current
    DESCRIPTION
        "."
    ::= { gfpClientCtpPmRealEntry  8 }


gfpClientCtpPmRealSBitCHECErrors OBJECT-TYPE
    SYNTAX     HCPerfIntervalCount 
    MAX-ACCESS  read-only
    STATUS      current
    DESCRIPTION
        "."
    ::= { gfpClientCtpPmRealEntry  9 }


gfpClientCtpPmRealMBitCHECErrors OBJECT-TYPE
    SYNTAX      HCPerfIntervalCount
    MAX-ACCESS  read-only
    STATUS      current
    DESCRIPTION "."
    ::= { gfpClientCtpPmRealEntry  10 }


gfpClientCtpPmRealSBitTHECErrors OBJECT-TYPE
    SYNTAX      HCPerfIntervalCount
    MAX-ACCESS  read-only
    STATUS      current
    DESCRIPTION "."
    ::= { gfpClientCtpPmRealEntry  11 }


gfpClientCtpPmRealMBitTHECErrors OBJECT-TYPE
    SYNTAX      HCPerfIntervalCount
    MAX-ACCESS  read-only
    STATUS      current
    DESCRIPTION "."
    ::= { gfpClientCtpPmRealEntry  12 }


gfpClientCtpPmRealSBitEHECErrors OBJECT-TYPE
    SYNTAX      HCPerfIntervalCount
    MAX-ACCESS  read-only
    STATUS      current
    DESCRIPTION "."
    ::= { gfpClientCtpPmRealEntry  13 }


gfpClientCtpPmRealMBitEHECErrors OBJECT-TYPE
    SYNTAX      HCPerfIntervalCount
    MAX-ACCESS  read-only
    STATUS      current
    DESCRIPTION "."
    ::= { gfpClientCtpPmRealEntry  14 }


gfpClientCtpPmRealEXIInvalid OBJECT-TYPE
    SYNTAX      HCPerfIntervalCount
    MAX-ACCESS  read-only
    STATUS      current
    DESCRIPTION "."
    ::= { gfpClientCtpPmRealEntry  15 }


gfpClientCtpPmRealUPIInvalid OBJECT-TYPE
    SYNTAX      HCPerfIntervalCount
    MAX-ACCESS  read-only
    STATUS      current
    DESCRIPTION "."
    ::= { gfpClientCtpPmRealEntry  16 }


gfpClientCtpPmRealCSFRaised  OBJECT-TYPE
    SYNTAX      HCPerfIntervalCount
    MAX-ACCESS  read-only
    STATUS      current
    DESCRIPTION
        ""
    ::= { gfpClientCtpPmRealEntry  17 }




gfpClientCtpPmRealOversized OBJECT-TYPE
    SYNTAX      HCPerfIntervalCount
    MAX-ACCESS  read-only
    STATUS      current
    DESCRIPTION
        "."
    ::= { gfpClientCtpPmRealEntry  18 }


gfpClientCtpPmRealUndersized OBJECT-TYPE
    SYNTAX      HCPerfIntervalCount
    MAX-ACCESS  read-only
    STATUS      current
    DESCRIPTION "."
    ::= { gfpClientCtpPmRealEntry  19 }


gfpClientCtpPmRealIngressOverflow      	OBJECT-TYPE
    SYNTAX      HCPerfIntervalCount
    MAX-ACCESS  read-only
    STATUS      current
    DESCRIPTION ""
    ::= { gfpClientCtpPmRealEntry  20 }

gfpClientCtpPmRealRxEgressOverflow  OBJECT-TYPE
    SYNTAX      HCPerfIntervalCount
    MAX-ACCESS  read-only
    STATUS      current
    DESCRIPTION ""
    ::= { gfpClientCtpPmRealEntry  21 }






-- Conformance Statements
gfpClientCtpPmConformance    OBJECT IDENTIFIER ::= { gfpClientCtpPmMIB 3 }
gfpClientCtpPmCompliances    OBJECT IDENTIFIER ::= { gfpClientCtpPmConformance 1 }
gfpClientCtpPmGroups         OBJECT IDENTIFIER ::= { gfpClientCtpPmConformance 2 }

gfpClientCtpPmCompliance MODULE-COMPLIANCE
    STATUS current
    DESCRIPTION
    "Describes the requirements for conformance to the PM-GIGECLIENTCTP-MIB"
    MODULE
        MANDATORY-GROUPS { gfpClientCtpPmGroup }
    ::= { gfpClientCtpPmCompliances 1 }

gfpClientCtpPmRealCompliance MODULE-COMPLIANCE
    STATUS current
    DESCRIPTION
    "Describes the requirements for conformance to the gfpClientCtpPmReal-MIB"
    MODULE
        MANDATORY-GROUPS { gfpClientCtpPmRealGroup }
    ::= { gfpClientCtpPmCompliances 2 }

gfpClientCtpPmGroup OBJECT-GROUP
    OBJECTS {
    gfpClientCtpPmTimestamp ,          
    gfpClientCtpPmSampleDuration ,     
    gfpClientCtpPmDataFrames ,            
    gfpClientCtpPmMgmtFrames  ,          
    gfpClientCtpPmIdleFrames ,            
    gfpClientCtpPmOtherFrames ,          
    gfpClientCtpPmFCSFrames ,          	
    gfpClientCtpPmErrFCSFrames ,            
    gfpClientCtpPmLinearEXIFrames ,           
    gfpClientCtpPmNullEXIFrames ,           
    gfpClientCtpPmSBitCHECErrors ,         
    gfpClientCtpPmMBitCHECErrors  ,          
    gfpClientCtpPmSBitTHECErrors  ,         
    gfpClientCtpPmMBitTHECErrors  ,    
    gfpClientCtpPmSBitEHECErrors  ,     
    gfpClientCtpPmMBitEHECErrors  ,    
    gfpClientCtpPmEXIInvalid ,    	
    gfpClientCtpPmUPIInvalid  ,      	 
    gfpClientCtpPmCSFRaised ,        	 
    gfpClientCtpPmOversized  ,      	 
    gfpClientCtpPmUndersized  ,            
    gfpClientCtpPmIngressOverflow ,     	
    gfpClientCtpPmRxEgressOverflow     
             
    }
    STATUS current
    DESCRIPTION
        " A collection of objects for reading the performance of the gfpClientCtp."
    ::= { gfpClientCtpPmGroups 1 }

gfpClientCtpPmRealGroup OBJECT-GROUP
    OBJECTS {
    gfpClientCtpPmRealDataFrames,              
    gfpClientCtpPmRealMgmtFrames ,             
    gfpClientCtpPmRealIdleFrames  ,            
    gfpClientCtpPmRealOtherFrames  ,          
    gfpClientCtpPmRealFCSFrames  ,         	
    gfpClientCtpPmRealErrFCSFrames,              
    gfpClientCtpPmRealLinearEXIFrames,              
    gfpClientCtpPmRealNullEXIFrames,            
    gfpClientCtpPmRealSBitCHECErrors,             
    gfpClientCtpPmRealMBitCHECErrors ,            
    gfpClientCtpPmRealSBitTHECErrors ,            
    gfpClientCtpPmRealMBitTHECErrors ,       
    gfpClientCtpPmRealSBitEHECErrors ,        
    gfpClientCtpPmRealMBitEHECErrors ,      	 
    gfpClientCtpPmRealEXIInvalid,     	 
    gfpClientCtpPmRealUPIInvalid,        	 
    gfpClientCtpPmRealCSFRaised ,        	 
    gfpClientCtpPmRealOversized ,       	   
    gfpClientCtpPmRealUndersized,              
    gfpClientCtpPmRealIngressOverflow,      	
    gfpClientCtpPmRealRxEgressOverflow       
           
    }
    STATUS current
    DESCRIPTION
        " A collection of objects for reading the real-time performance of the gfpClientCtp."
    ::= { gfpClientCtpPmGroups 2 }

END

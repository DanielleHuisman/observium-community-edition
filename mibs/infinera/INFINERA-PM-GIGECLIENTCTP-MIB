-- *****************************************************************
-- INFINERA-PM-GIGECLIENTCTP-MIB
--
-- October 2008, Sharfuddin Syed / Narendra Gupta
--
--
-- Copyright (c) 2008-2012 by Infinera Inc.
-- All rights reserved.
-- ****************************************************************

INFINERA-PM-GIGECLIENTCTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    HCPerfIntervalCount                         FROM HC-PerfHist-TC-MIB
    FloatHundredths,InfnServiceType             FROM INFINERA-TC-MIB
    perfMon                                         FROM INFINERA-REG-MIB;


gigeClientCtpPmMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "200810200000Z"
    DESCRIPTION
        "First Version"
    ::= { perfMon 8 }



gigeClientCtpPmTable OBJECT-TYPE
    SYNTAX      SEQUENCE OF GigeClientCtpPmEntry
    MAX-ACCESS  not-accessible
    STATUS      current
    DESCRIPTION
        "A list of GigeClientCtpPm entries. Each entry is uniquely identified by the value of ifIndex, sampleDuration and gigeClientCtpPmTimestamp."
    ::= { gigeClientCtpPmMIB 2 }

gigeClientCtpPmEntry  OBJECT-TYPE
    SYNTAX      GigeClientCtpPmEntry
    MAX-ACCESS  not-accessible
    STATUS      current
    DESCRIPTION
        "A GigeClientCtp entry containing historical performance information pertaining to Infinera
        GigeClientCtp interfaces. This table is a subclass of IfCommon. Entries will exist in this
        table only for interfaces of type GigeClientCtp.
        Each interface may have a number of entries in this table, each with a different combination
        of timestamp and sample duration."
    INDEX { ifIndex, gigeClientCtpPmSampleDuration, gigeClientCtpPmTimestamp }
    ::= { gigeClientCtpPmTable 1 }


GigeClientCtpPmEntry  ::= SEQUENCE {
    gigeClientCtpPmTimestamp            Integer32,
    gigeClientCtpPmSampleDuration       INTEGER,
    gigeClientCtpPmValidity             TruthValue,
    gigeClientCtpPmRxPcsICG             HCPerfIntervalCount,
    gigeClientCtpPmRxPcsES              Integer32,
    gigeClientCtpPmRxPcsSES             Integer32,
    gigeClientCtpPmRxPcsSESS            Integer32,
    gigeClientCtpPmTxPcsICG             HCPerfIntervalCount,
    gigeClientCtpPmTxPcsES              Integer32,
    gigeClientCtpPmTxPcsSES             Integer32,
    gigeClientCtpPmTxPcsSESS            Integer32,
    gigeClientCtpPmRxPackets            HCPerfIntervalCount,
    gigeClientCtpPmRxOctets             HCPerfIntervalCount,
    gigeClientCtpPmRxErrOctets          HCPerfIntervalCount,
    gigeClientCtpPmRxJabbers            HCPerfIntervalCount,
    gigeClientCtpPmRxFragments          HCPerfIntervalCount,
    gigeClientCtpPmRxCrcAlignedErr      HCPerfIntervalCount,
    gigeClientCtpPmRxUndersized         HCPerfIntervalCount,
    gigeClientCtpPmRxOversized          HCPerfIntervalCount,
    gigeClientCtpPmRxJabberSecs         Integer32,
    gigeClientCtpPmRxMacSES             Integer32,
    gigeClientCtpPmRxBroadcastPkts      HCPerfIntervalCount,
    gigeClientCtpPmRxMulticastPkts      HCPerfIntervalCount,
    gigeClientCtpPmRxInPauseFrames      HCPerfIntervalCount,
    gigeClientCtpPmTxPackets            HCPerfIntervalCount,
    gigeClientCtpPmTxOctets             HCPerfIntervalCount,
    gigeClientCtpPmTxErrOctets          HCPerfIntervalCount,
    gigeClientCtpPmTxJabbers            HCPerfIntervalCount,
    gigeClientCtpPmTxFragments          HCPerfIntervalCount,
    gigeClientCtpPmTxCrcAlignedErr      HCPerfIntervalCount,
    gigeClientCtpPmTxUndersized         HCPerfIntervalCount,
    gigeClientCtpPmTxOversized          HCPerfIntervalCount,
    gigeClientCtpPmTxJabberSecs         Integer32,
    gigeClientCtpPmTxMacSES             Integer32,
    gigeClientCtpPmTxBroadcastPkts      HCPerfIntervalCount,
    gigeClientCtpPmTxMulticastPkts      HCPerfIntervalCount,
    gigeClientCtpPmTxOutPauseFrames     HCPerfIntervalCount,
    gigeClientCtpPmRxSize64             HCPerfIntervalCount,
    gigeClientCtpPmRxSize65to127        HCPerfIntervalCount,
    gigeClientCtpPmRxSize128to255       HCPerfIntervalCount,
    gigeClientCtpPmRxSize256to511       HCPerfIntervalCount,
    gigeClientCtpPmRxSize512to1023      HCPerfIntervalCount,
    gigeClientCtpPmRxSize1024to1518     HCPerfIntervalCount,
    gigeClientCtpPmRxSize1519toJumbo    HCPerfIntervalCount,
    gigeClientCtpPmTxSize64             HCPerfIntervalCount,
    gigeClientCtpPmTxSize65to127        HCPerfIntervalCount,
    gigeClientCtpPmTxSize128to255       HCPerfIntervalCount,
    gigeClientCtpPmTxSize256to511       HCPerfIntervalCount,
    gigeClientCtpPmTxSize512to1023      HCPerfIntervalCount,
    gigeClientCtpPmTxSize1024to1518     HCPerfIntervalCount,
    gigeClientCtpPmTxSize1519toJumbo    HCPerfIntervalCount,
    gigeClientCtpPmCktId                DisplayString,
    gigeClientCtpPmTribTestSigSyncErr      Integer32,
    gigeClientCtpPmTribTestSigErr          Integer32,
    gigeClientCtpPmPayloadType             InfnServiceType,
    gigeClientCtpPmRxSize1024to1522     HCPerfIntervalCount,
    gigeClientCtpPmRxSize1523toJumbo    HCPerfIntervalCount,
    gigeClientCtpPmTxSize1024to1522     HCPerfIntervalCount,
    gigeClientCtpPmTxSize1523toJumbo    HCPerfIntervalCount,
    gigeClientCtpPmTxCvsPcs01    Integer32,
    gigeClientCtpPmTxCvsPcs02    Integer32,
    gigeClientCtpPmTxCvsPcs03    Integer32,
    gigeClientCtpPmTxCvsPcs04    Integer32,
    gigeClientCtpPmTxCvsPcs05    Integer32,
    gigeClientCtpPmTxCvsPcs06    Integer32,
    gigeClientCtpPmTxCvsPcs07    Integer32,
    gigeClientCtpPmTxCvsPcs08    Integer32,
    gigeClientCtpPmTxCvsPcs09    Integer32,
    gigeClientCtpPmTxCvsPcs10    Integer32,
    gigeClientCtpPmTxCvsPcs11    Integer32,
    gigeClientCtpPmTxCvsPcs12    Integer32,
    gigeClientCtpPmTxCvsPcs13    Integer32,
    gigeClientCtpPmTxCvsPcs14    Integer32,
    gigeClientCtpPmTxCvsPcs15    Integer32,
    gigeClientCtpPmTxCvsPcs16    Integer32,
    gigeClientCtpPmTxCvsPcs17    Integer32,
    gigeClientCtpPmTxCvsPcs18    Integer32,
    gigeClientCtpPmTxCvsPcs19    Integer32,
    gigeClientCtpPmTxCvsPcs20    Integer32,
    gigeClientCtpPmRxCvsPcs01    Integer32,
    gigeClientCtpPmRxCvsPcs02    Integer32,
    gigeClientCtpPmRxCvsPcs03    Integer32,
    gigeClientCtpPmRxCvsPcs04    Integer32,
    gigeClientCtpPmRxCvsPcs05    Integer32,
    gigeClientCtpPmRxCvsPcs06    Integer32,
    gigeClientCtpPmRxCvsPcs07    Integer32,
    gigeClientCtpPmRxCvsPcs08    Integer32,
    gigeClientCtpPmRxCvsPcs09    Integer32,
    gigeClientCtpPmRxCvsPcs10    Integer32,
    gigeClientCtpPmRxCvsPcs11    Integer32,
    gigeClientCtpPmRxCvsPcs12    Integer32,
    gigeClientCtpPmRxCvsPcs13    Integer32,
    gigeClientCtpPmRxCvsPcs14    Integer32,
    gigeClientCtpPmRxCvsPcs15    Integer32,
    gigeClientCtpPmRxCvsPcs16    Integer32,
    gigeClientCtpPmRxCvsPcs17    Integer32,
    gigeClientCtpPmRxCvsPcs18    Integer32,
    gigeClientCtpPmRxCvsPcs19    Integer32,
    gigeClientCtpPmRxCvsPcs20    Integer32,
    gigeClientCtpPmRxErrPackets  HCPerfIntervalCount,
    gigeClientCtpPmRxDiscarded   HCPerfIntervalCount,
    gigeClientCtpPmRxCorrectedWords       Integer32,
    gigeClientCtpPmRxUncorrectedWords     Integer32,
    gigeClientCtpPmRxCorrectedBit         Integer32

}

gigeClientCtpPmTimestamp OBJECT-TYPE
    SYNTAX      Integer32 (0..2147483647)
    MAX-ACCESS  not-accessible
    STATUS      current
    DESCRIPTION
        "End Time stamp for this interval. If this time is later than the current time,
        then the data for this bucket is currently being collected."
    ::= { gigeClientCtpPmEntry  1 }


gigeClientCtpPmSampleDuration OBJECT-TYPE
    SYNTAX      INTEGER {
                    fifteenMinutes(1),
                    day(2)
                }
    MAX-ACCESS  not-accessible
    STATUS      current
    DESCRIPTION
        "The duration of this sample."
    ::= { gigeClientCtpPmEntry  2 }


gigeClientCtpPmValidity OBJECT-TYPE
    SYNTAX      TruthValue
    MAX-ACCESS  read-only
    STATUS      current
    DESCRIPTION "Flag indicating if data was valid for the entire interval"
    ::= { gigeClientCtpPmEntry  3 }


gigeClientCtpPmRxPcsICG OBJECT-TYPE
    SYNTAX      HCPerfIntervalCount
    MAX-ACCESS  read-only
    STATUS      current
    DESCRIPTION "Number of Invalid Code Group detected by the Physical Coding Sublayer."
    ::= { gigeClientCtpPmEntry  4 }


gigeClientCtpPmRxPcsES OBJECT-TYPE
    SYNTAX      Integer32
    MAX-ACCESS  read-only
    STATUS      current
    DESCRIPTION
        "Number of errored seconds detected by the Physical Coding Sublayer."
    ::= { gigeClientCtpPmEntry  5 }


gigeClientCtpPmRxPcsSES OBJECT-TYPE
    SYNTAX      Integer32
    MAX-ACCESS  read-only
    STATUS      current
    DESCRIPTION
        "Number of severely errored seconds detected by the Physical Coding Sublayer."
    ::= { gigeClientCtpPmEntry  6 }


gigeClientCtpPmRxPcsSESS OBJECT-TYPE
    SYNTAX      Integer32
    MAX-ACCESS  read-only
    STATUS      current
    DESCRIPTION
        "Number of Severely Errored Sync Seconds detected by the Physical Coding Sublayer."
    ::= { gigeClientCtpPmEntry  7 }


gigeClientCtpPmTxPcsICG OBJECT-TYPE
    SYNTAX      HCPerfIntervalCount
    MAX-ACCESS  read-only
    STATUS      current
    DESCRIPTION "Number of Invalid Code Group detected by the Physical Coding Sublayer."
    ::= { gigeClientCtpPmEntry  8 }


gigeClientCtpPmTxPcsES OBJECT-TYPE
    SYNTAX      Integer32
    MAX-ACCESS  read-only
    STATUS      current
    DESCRIPTION
        "Number of errored seconds detected by the Physical Coding Sublayer."
    ::= { gigeClientCtpPmEntry  9 }


gigeClientCtpPmTxPcsSES OBJECT-TYPE
    SYNTAX      Integer32
    MAX-ACCESS  read-only
    STATUS      current
    DESCRIPTION
        "Number of severely errored seconds detected by the Physical Coding Sublayer."
    ::= { gigeClientCtpPmEntry  10 }


gigeClientCtpPmTxPcsSESS OBJECT-TYPE
    SYNTAX      Integer32
    MAX-ACCESS  read-only
    STATUS      current
    DESCRIPTION
        "Number of Severely Errored Sync Seconds detected by the Physical Coding Sublayer."
    ::= { gigeClientCtpPmEntry  11 }


gigeClientCtpPmRxPackets OBJECT-TYPE
    SYNTAX      HCPerfIntervalCount
    MAX-ACCESS  read-only
    STATUS      current
    DESCRIPTION "Number of received data packets."
    ::= { gigeClientCtpPmEntry  12 }


gigeClientCtpPmRxOctets OBJECT-TYPE
    SYNTAX      HCPerfIntervalCount
    MAX-ACCESS  read-only
    STATUS      current
    DESCRIPTION "Number of received data octets."
    ::= { gigeClientCtpPmEntry  13 }


gigeClientCtpPmRxErrOctets OBJECT-TYPE
    SYNTAX      HCPerfIntervalCount
    MAX-ACCESS  read-only
    STATUS      current
    DESCRIPTION "Errored octet. Number of data octets that are part of an Errored Packet on the receive client interface."
    ::= { gigeClientCtpPmEntry  14 }


gigeClientCtpPmRxJabbers OBJECT-TYPE
    SYNTAX      HCPerfIntervalCount
    MAX-ACCESS  read-only
    STATUS      current
    DESCRIPTION "Jabber count. Number of packets received that are longer than the maximum frame length octets (excluding framing bits, but including FCS octets) and has either a bad FCS with an integral number of octets (FCS error) or a bad FCS with a non-integral number of octets (alignment error)."
    ::= { gigeClientCtpPmEntry  15 }


gigeClientCtpPmRxFragments OBJECT-TYPE
    SYNTAX      HCPerfIntervalCount
    MAX-ACCESS  read-only
    STATUS      current
    DESCRIPTION "Fragment packet count. Number of packets received that are less than 64 octets long (excluding framing bits, but including FCS octets) and have either a bad FCS with an integral number of octets (FCS error) or a bad FCS with a non-integral number of octets (alignment error), on the receive client interface."
    ::= { gigeClientCtpPmEntry  16 }


gigeClientCtpPmRxCrcAlignedErr OBJECT-TYPE
    SYNTAX      HCPerfIntervalCount
    MAX-ACCESS  read-only
    STATUS      current
    DESCRIPTION "Cyclical redundancy check align error count. Number of packets received that have a length (excluding framing bits, but including FCS octets) of between 64 and MaxFrameLength octets, inclusive, but have either a bad FCS with an integral number of octets (FCS Error) or a bad FCS with a non-integral number of octets (Alignment Error), on the receive client interface."
    ::= { gigeClientCtpPmEntry  17 }


gigeClientCtpPmRxUndersized OBJECT-TYPE
    SYNTAX      HCPerfIntervalCount
    MAX-ACCESS  read-only
    STATUS      current
    DESCRIPTION "Undersize packet count. Number of received packets that are less than 64 octets long (excluding framing bits, but including FCS octets) and are otherwise well formed, on the receive client interface."
    ::= { gigeClientCtpPmEntry  18 }


gigeClientCtpPmRxOversized OBJECT-TYPE
    SYNTAX      HCPerfIntervalCount
    MAX-ACCESS  read-only
    STATUS      current
    DESCRIPTION "Oversize packet count. Number of received packets that are longer than the maximum frame length (excluding framing bits, but including FCS octets) and are otherwise well formed, on the receive client interface."
    ::= { gigeClientCtpPmEntry  19 }


gigeClientCtpPmRxJabberSecs OBJECT-TYPE
    SYNTAX      Integer32
    MAX-ACCESS  read-only
    STATUS      current
    DESCRIPTION
        "Jabber Seconds. Number of seconds in which a jabber state was detected sometime in that second."
    ::= { gigeClientCtpPmEntry  20 }


gigeClientCtpPmRxMacSES OBJECT-TYPE
    SYNTAX      Integer32
    MAX-ACCESS  read-only
    STATUS      current
    DESCRIPTION
        "Severely Errored Seconds – Packet/Octet layer. Number of seconds in which at least 30% of observed Data Octets are Errored Data Octets, or the TP was in a Severely Errored Second - PCS."
    ::= { gigeClientCtpPmEntry  21 }


gigeClientCtpPmRxBroadcastPkts OBJECT-TYPE
    SYNTAX      HCPerfIntervalCount
    MAX-ACCESS  read-only
    STATUS      current
    DESCRIPTION "A count of frames that are successfully received and are directed to the broadcast group address. This does not include frames received with frame-too-long, FCS, length, or alignment errors, or frames lost due to internal MAC sublayer error."
    ::= { gigeClientCtpPmEntry  22 }


gigeClientCtpPmRxMulticastPkts OBJECT-TYPE
    SYNTAX      HCPerfIntervalCount
    MAX-ACCESS  read-only
    STATUS      current
    DESCRIPTION "A count of frames that are successfully received and are directed to an active nonbroadcast group address. This does not include frames received with frame-too-long, FCS, length, or alignment errors, or frames lost due to internal MAC sublayer error."
    ::= { gigeClientCtpPmEntry  23 }


gigeClientCtpPmRxInPauseFrames OBJECT-TYPE
    SYNTAX      HCPerfIntervalCount
    MAX-ACCESS  read-only
    STATUS      current
    DESCRIPTION "A count of MAC Control frames received on this interface with an opcode indicating the PAUSE operation. This counter does not increment when the interface is operating in half-duplex mode."
    ::= { gigeClientCtpPmEntry  24 }


gigeClientCtpPmTxPackets OBJECT-TYPE
    SYNTAX      HCPerfIntervalCount
    MAX-ACCESS  read-only
    STATUS      current
    DESCRIPTION "Number of transmitted data packets."
    ::= { gigeClientCtpPmEntry  25 }


gigeClientCtpPmTxOctets OBJECT-TYPE
    SYNTAX      HCPerfIntervalCount
    MAX-ACCESS  read-only
    STATUS      current
    DESCRIPTION "Number of transmitted data octets."
    ::= { gigeClientCtpPmEntry  26 }


gigeClientCtpPmTxErrOctets OBJECT-TYPE
    SYNTAX      HCPerfIntervalCount
    MAX-ACCESS  read-only
    STATUS      current
    DESCRIPTION "Errored octet. Number of data octets that are part of an Errored Packet (i.e., the FCS is in error, resulting in incrementing the Fragment counter, the Jabber counter, or the CRCAlignError counter), at the signal de-encapsulation point before the client-side transmit interface."
    ::= { gigeClientCtpPmEntry  27 }


gigeClientCtpPmTxJabbers OBJECT-TYPE
    SYNTAX      HCPerfIntervalCount
    MAX-ACCESS  read-only
    STATUS      current
    DESCRIPTION "Jabber count. Number of packets transmitted that are longer than the maximum frame length octets (excluding framing bits, but including FCS octets) and has either a bad FCS with an integral number of octets (FCS error) or a bad FCS with a non-integral number of octets (alignment error)."
    ::= { gigeClientCtpPmEntry  28 }


gigeClientCtpPmTxFragments OBJECT-TYPE
    SYNTAX      HCPerfIntervalCount
    MAX-ACCESS  read-only
    STATUS      current
    DESCRIPTION "Fragment packet count. Number of packets transmitted that are less than 64 octets long (excluding framing bits, but including FCS octets) and have either a bad FCS with an integral number of octets (FCS error) or a bad FCS with a non-integral number of octets (alignment error), on the receive client interface."
    ::= { gigeClientCtpPmEntry  29 }


gigeClientCtpPmTxCrcAlignedErr OBJECT-TYPE
    SYNTAX      HCPerfIntervalCount
    MAX-ACCESS  read-only
    STATUS      current
    DESCRIPTION "Cyclical redundancy check align error count. Number of packets transmitted that have a length (excluding framing bits, but including FCS octets) of between 64 and MaxFrameLength octets, inclusive, but have either a bad FCS with an integral number of octets (FCS Error) or a bad FCS with a non-integral number of octets (Alignment Error), on the receive client interface."
    ::= { gigeClientCtpPmEntry  30 }


gigeClientCtpPmTxUndersized OBJECT-TYPE
    SYNTAX      HCPerfIntervalCount
    MAX-ACCESS  read-only
    STATUS      current
    DESCRIPTION "Undersize packet count. Number of transmitted packets that are less than 64 octets long (excluding framing bits, but including FCS octets) and are otherwise well formed."
    ::= { gigeClientCtpPmEntry  31 }


gigeClientCtpPmTxOversized OBJECT-TYPE
    SYNTAX      HCPerfIntervalCount
    MAX-ACCESS  read-only
    STATUS      current
    DESCRIPTION "Oversize packet count. Number of transmitted packets that are longer than the maximum frame length (excluding framing bits, but including FCS octets) and are otherwise well formed, on the receive client interface."
    ::= { gigeClientCtpPmEntry  32 }


gigeClientCtpPmTxJabberSecs OBJECT-TYPE
    SYNTAX      Integer32
    MAX-ACCESS  read-only
    STATUS      current
    DESCRIPTION
        "Jabber Seconds. Number of seconds in which a jabber state was detected sometime in that second on the de-encapsulated signal."
    ::= { gigeClientCtpPmEntry  33 }


gigeClientCtpPmTxMacSES OBJECT-TYPE
    SYNTAX      Integer32
    MAX-ACCESS  read-only
    STATUS      current
    DESCRIPTION
        "Severely Errored Seconds – Packet/Octet layer. Number of seconds in which at least 30% of observed de-encap Data Octets are Errored Data Octets, or the TP was in a de-encap Severely Errored Second - PCS."
    ::= { gigeClientCtpPmEntry  34 }


gigeClientCtpPmTxBroadcastPkts OBJECT-TYPE
    SYNTAX      HCPerfIntervalCount
    MAX-ACCESS  read-only
    STATUS      current
    DESCRIPTION "A count of the frames that were successfully transmitted, as indicated by the transmit status “transmit OK”, to the broadcast address. Frames transmitted to multicast addresses are not broadcast frames and are excluded."
    ::= { gigeClientCtpPmEntry  35 }


gigeClientCtpPmTxMulticastPkts OBJECT-TYPE
    SYNTAX      HCPerfIntervalCount
    MAX-ACCESS  read-only
    STATUS      current
    DESCRIPTION "A count of frames that are successfully transmitted, as indicated by the status value “transmit OK”, to a group destination address other than broadcast."
    ::= { gigeClientCtpPmEntry  36 }


gigeClientCtpPmTxOutPauseFrames OBJECT-TYPE
    SYNTAX      HCPerfIntervalCount
    MAX-ACCESS  read-only
    STATUS      current
    DESCRIPTION "A count of MAC Control frames transmitted on this interface with an opcode indicating the PAUSE operation. This counter does not increment when the interface is operating in half-duplex mode. This counter can roll over in less than 5 minutes if it is incrementing at its maximum rate. Since that amount of time could be less than a management station's poll cycle time, in order to avoid a loss of information, a management station is advised to poll the dot3HCOutPauseFrames object for 10 Gb/s or faster interfaces."
    ::= { gigeClientCtpPmEntry  37 }


gigeClientCtpPmRxSize64 OBJECT-TYPE
    SYNTAX      HCPerfIntervalCount
    MAX-ACCESS  read-only
    STATUS      current
    DESCRIPTION "Received packets (including bad packets) of 64 or less octets."
    ::= { gigeClientCtpPmEntry  38 }


gigeClientCtpPmRxSize65to127 OBJECT-TYPE
    SYNTAX      HCPerfIntervalCount
    MAX-ACCESS  read-only
    STATUS      current
    DESCRIPTION "Received packets (including bad packets) from 65 to 127 octets."
    ::= { gigeClientCtpPmEntry  39 }


gigeClientCtpPmRxSize128to255 OBJECT-TYPE
    SYNTAX      HCPerfIntervalCount
    MAX-ACCESS  read-only
    STATUS      current
    DESCRIPTION "Received packets (including bad packets) from 128 to 255 octets."
    ::= { gigeClientCtpPmEntry  40 }


gigeClientCtpPmRxSize256to511 OBJECT-TYPE
    SYNTAX      HCPerfIntervalCount
    MAX-ACCESS  read-only
    STATUS      current
    DESCRIPTION "Received packets (including bad packets) from 256 to 511 octets."
    ::= { gigeClientCtpPmEntry  41 }


gigeClientCtpPmRxSize512to1023 OBJECT-TYPE
    SYNTAX      HCPerfIntervalCount
    MAX-ACCESS  read-only
    STATUS      current
    DESCRIPTION "Received packets (including bad packets) from 512 to 1023 octets."
    ::= { gigeClientCtpPmEntry  42 }


gigeClientCtpPmRxSize1024to1518 OBJECT-TYPE
    SYNTAX      HCPerfIntervalCount
    MAX-ACCESS  read-only
    STATUS      current
    DESCRIPTION "Received packets (including bad packets) from 1024 to 1518 octets."
    ::= { gigeClientCtpPmEntry  43 }


gigeClientCtpPmRxSize1519toJumbo OBJECT-TYPE
    SYNTAX      HCPerfIntervalCount
    MAX-ACCESS  read-only
    STATUS      current
    DESCRIPTION "Received packets (including bad packets) of 1519 or more octets."
    ::= { gigeClientCtpPmEntry  44 }


gigeClientCtpPmTxSize64 OBJECT-TYPE
    SYNTAX      HCPerfIntervalCount
    MAX-ACCESS  read-only
    STATUS      current
    DESCRIPTION "Transmitted packets of 64 or less octets."
    ::= { gigeClientCtpPmEntry  45 }


gigeClientCtpPmTxSize65to127 OBJECT-TYPE
    SYNTAX      HCPerfIntervalCount
    MAX-ACCESS  read-only
    STATUS      current
    DESCRIPTION "Transmitted packets from 65 to 127 octets."
    ::= { gigeClientCtpPmEntry  46 }


gigeClientCtpPmTxSize128to255 OBJECT-TYPE
    SYNTAX      HCPerfIntervalCount
    MAX-ACCESS  read-only
    STATUS      current
    DESCRIPTION "Transmitted packets from 128 to 255 octets."
    ::= { gigeClientCtpPmEntry  47 }


gigeClientCtpPmTxSize256to511 OBJECT-TYPE
    SYNTAX      HCPerfIntervalCount
    MAX-ACCESS  read-only
    STATUS      current
    DESCRIPTION "Transmitted packets from 256 to 511 octets."
    ::= { gigeClientCtpPmEntry  48 }


gigeClientCtpPmTxSize512to1023 OBJECT-TYPE
    SYNTAX      HCPerfIntervalCount
    MAX-ACCESS  read-only
    STATUS      current
    DESCRIPTION "Transmitted packets from 512 to 1023 octets."
    ::= { gigeClientCtpPmEntry  49 }


gigeClientCtpPmTxSize1024to1518 OBJECT-TYPE
    SYNTAX      HCPerfIntervalCount
    MAX-ACCESS  read-only
    STATUS      current
    DESCRIPTION "Transmitted packets from 1024 to 1518 octets."
    ::= { gigeClientCtpPmEntry  50 }


gigeClientCtpPmTxSize1519toJumbo OBJECT-TYPE
    SYNTAX      HCPerfIntervalCount
    MAX-ACCESS  read-only
    STATUS      current
    DESCRIPTION "Transmitted packets of 1519 or more octets."
    ::= { gigeClientCtpPmEntry  51 }


gigeClientCtpPmCktId OBJECT-TYPE
    SYNTAX      DisplayString
    MAX-ACCESS  read-only
    STATUS      current
    DESCRIPTION "Circuit ID(s) of the connection created on the gige termination point."
    ::= { gigeClientCtpPmEntry  52 }


gigeClientCtpPmTribTestSigSyncErr OBJECT-TYPE
    SYNTAX      Integer32
    MAX-ACCESS  read-only
    STATUS      current
    DESCRIPTION
        "Count of the number of times re-sync has been attempted after the initial test signal synch was achieved."
    ::= { gigeClientCtpPmEntry  53 }


gigeClientCtpPmTribTestSigErr OBJECT-TYPE
    SYNTAX      Integer32
    MAX-ACCESS  read-only
    STATUS      current
    DESCRIPTION
        "Count of the number of bits not matching the expected pattern (whether synch has been achieved or not)."
    ::= { gigeClientCtpPmEntry  54 }

 gigeClientCtpPmPayloadType OBJECT-TYPE
      SYNTAX      InfnServiceType
      MAX-ACCESS  read-only
      STATUS      current
      DESCRIPTION "The configured service type."
      ::= { gigeClientCtpPmEntry  55 }

gigeClientCtpPmRxSize1024to1522 OBJECT-TYPE
    SYNTAX      HCPerfIntervalCount
    MAX-ACCESS  read-only
    STATUS      current
    DESCRIPTION "Received packets (including bad packets) from 1024 to 1522 octets."
    ::= { gigeClientCtpPmEntry  56 }


gigeClientCtpPmRxSize1523toJumbo OBJECT-TYPE
    SYNTAX      HCPerfIntervalCount
    MAX-ACCESS  read-only
    STATUS      current
    DESCRIPTION "Received packets (including bad packets) of 1523 or more octets."
    ::= { gigeClientCtpPmEntry  57 }


gigeClientCtpPmTxSize1024to1522 OBJECT-TYPE
    SYNTAX      HCPerfIntervalCount
    MAX-ACCESS  read-only
    STATUS      current
    DESCRIPTION "Transmitted packets from 1024 to 1522 octets."
    ::= { gigeClientCtpPmEntry  58 }



gigeClientCtpPmTxSize1523toJumbo OBJECT-TYPE
    SYNTAX      HCPerfIntervalCount
    MAX-ACCESS  read-only
    STATUS      current
    DESCRIPTION "Transmitted packets of 1523 or more octets."
    ::= { gigeClientCtpPmEntry  59 }



gigeClientCtpPmTxCvsPcs01 OBJECT-TYPE
    SYNTAX      Integer32
    MAX-ACCESS  read-only
    STATUS      current
    DESCRIPTION "Coding Violations Section-Bip Error Lane 01."
    ::= { gigeClientCtpPmEntry  60 }

gigeClientCtpPmTxCvsPcs02 OBJECT-TYPE
    SYNTAX      Integer32
    MAX-ACCESS  read-only
    STATUS      current
    DESCRIPTION "Coding Violations Section-Bip Error Lane 02."
    ::= { gigeClientCtpPmEntry  61 }

gigeClientCtpPmTxCvsPcs03 OBJECT-TYPE
    SYNTAX      Integer32
    MAX-ACCESS  read-only
    STATUS      current
    DESCRIPTION "Coding Violations Section-Bip Error Lane 03."
    ::= { gigeClientCtpPmEntry  62 }

gigeClientCtpPmTxCvsPcs04 OBJECT-TYPE
    SYNTAX      Integer32
    MAX-ACCESS  read-only
    STATUS      current
    DESCRIPTION "Coding Violations Section-Bip Error Lane 04."
    ::= { gigeClientCtpPmEntry  63 }

gigeClientCtpPmTxCvsPcs05 OBJECT-TYPE
    SYNTAX      Integer32
    MAX-ACCESS  read-only
    STATUS      current
    DESCRIPTION "Coding Violations Section-Bip Error Lane 05."
    ::= { gigeClientCtpPmEntry  64 }

gigeClientCtpPmTxCvsPcs06 OBJECT-TYPE
    SYNTAX      Integer32
    MAX-ACCESS  read-only
    STATUS      current
    DESCRIPTION "Coding Violations Section-Bip Error Lane 06."
    ::= { gigeClientCtpPmEntry  65 }

gigeClientCtpPmTxCvsPcs07 OBJECT-TYPE
    SYNTAX      Integer32
    MAX-ACCESS  read-only
    STATUS      current
    DESCRIPTION "Coding Violations Section-Bip Error Lane 07."
    ::= { gigeClientCtpPmEntry  66 }

gigeClientCtpPmTxCvsPcs08 OBJECT-TYPE
    SYNTAX      Integer32
    MAX-ACCESS  read-only
    STATUS      current
    DESCRIPTION "Coding Violations Section-Bip Error Lane 08."
    ::= { gigeClientCtpPmEntry  67 }

gigeClientCtpPmTxCvsPcs09 OBJECT-TYPE
    SYNTAX      Integer32
    MAX-ACCESS  read-only
    STATUS      current
    DESCRIPTION "Coding Violations Section-Bip Error Lane 09."
    ::= { gigeClientCtpPmEntry  68 }

gigeClientCtpPmTxCvsPcs10 OBJECT-TYPE
    SYNTAX      Integer32
    MAX-ACCESS  read-only
    STATUS      current
    DESCRIPTION "Coding Violations Section-Bip Error Lane 10."
    ::= { gigeClientCtpPmEntry  69 }

gigeClientCtpPmTxCvsPcs11 OBJECT-TYPE
    SYNTAX      Integer32
    MAX-ACCESS  read-only
    STATUS      current
    DESCRIPTION "Coding Violations Section-Bip Error Lane 11."
    ::= { gigeClientCtpPmEntry  70 }

gigeClientCtpPmTxCvsPcs12 OBJECT-TYPE
    SYNTAX      Integer32
    MAX-ACCESS  read-only
    STATUS      current
    DESCRIPTION "Coding Violations Section-Bip Error Lane 12."
    ::= { gigeClientCtpPmEntry  71 }

gigeClientCtpPmTxCvsPcs13 OBJECT-TYPE
    SYNTAX      Integer32
    MAX-ACCESS  read-only
    STATUS      current
    DESCRIPTION "Coding Violations Section-Bip Error Lane 13."
    ::= { gigeClientCtpPmEntry  72 }

gigeClientCtpPmTxCvsPcs14 OBJECT-TYPE
    SYNTAX      Integer32
    MAX-ACCESS  read-only
    STATUS      current
    DESCRIPTION "Coding Violations Section-Bip Error Lane 14."
    ::= { gigeClientCtpPmEntry  73 }

gigeClientCtpPmTxCvsPcs15 OBJECT-TYPE
    SYNTAX      Integer32
    MAX-ACCESS  read-only
    STATUS      current
    DESCRIPTION "Coding Violations Section-Bip Error Lane 15."
    ::= { gigeClientCtpPmEntry  74 }

gigeClientCtpPmTxCvsPcs16 OBJECT-TYPE
    SYNTAX      Integer32
    MAX-ACCESS  read-only
    STATUS      current
    DESCRIPTION "Coding Violations Section-Bip Error Lane 16."
    ::= { gigeClientCtpPmEntry  75 }

gigeClientCtpPmTxCvsPcs17 OBJECT-TYPE
    SYNTAX      Integer32
    MAX-ACCESS  read-only
    STATUS      current
    DESCRIPTION "Coding Violations Section-Bip Error Lane 17."
    ::= { gigeClientCtpPmEntry  76 }

gigeClientCtpPmTxCvsPcs18 OBJECT-TYPE
    SYNTAX      Integer32
    MAX-ACCESS  read-only
    STATUS      current
    DESCRIPTION "Coding Violations Section-Bip Error Lane 18."
    ::= { gigeClientCtpPmEntry  77 }

gigeClientCtpPmTxCvsPcs19 OBJECT-TYPE
    SYNTAX      Integer32
    MAX-ACCESS  read-only
    STATUS      current
    DESCRIPTION "Coding Violations Section-Bip Error Lane 19."
    ::= { gigeClientCtpPmEntry  78 }

gigeClientCtpPmTxCvsPcs20 OBJECT-TYPE
    SYNTAX      Integer32
    MAX-ACCESS  read-only
    STATUS      current
    DESCRIPTION "Coding Violations Section-Bip Error Lane 20."
    ::= { gigeClientCtpPmEntry  79 }

gigeClientCtpPmRxCvsPcs01 OBJECT-TYPE
    SYNTAX      Integer32
    MAX-ACCESS  read-only
    STATUS      current
    DESCRIPTION "Coding Violations Section-Bip Error Lane 01."
    ::= { gigeClientCtpPmEntry  80 }

gigeClientCtpPmRxCvsPcs02 OBJECT-TYPE
    SYNTAX      Integer32
    MAX-ACCESS  read-only
    STATUS      current
    DESCRIPTION "Coding Violations Section-Bip Error Lane 02."
    ::= { gigeClientCtpPmEntry  81 }

gigeClientCtpPmRxCvsPcs03 OBJECT-TYPE
    SYNTAX      Integer32
    MAX-ACCESS  read-only
    STATUS      current
    DESCRIPTION "Coding Violations Section-Bip Error Lane 03."
    ::= { gigeClientCtpPmEntry  82 }

gigeClientCtpPmRxCvsPcs04 OBJECT-TYPE
    SYNTAX      Integer32
    MAX-ACCESS  read-only
    STATUS      current
    DESCRIPTION "Coding Violations Section-Bip Error Lane 04."
    ::= { gigeClientCtpPmEntry  83 }

gigeClientCtpPmRxCvsPcs05 OBJECT-TYPE
    SYNTAX      Integer32
    MAX-ACCESS  read-only
    STATUS      current
    DESCRIPTION "Coding Violations Section-Bip Error Lane 05."
    ::= { gigeClientCtpPmEntry  84 }

gigeClientCtpPmRxCvsPcs06 OBJECT-TYPE
    SYNTAX      Integer32
    MAX-ACCESS  read-only
    STATUS      current
    DESCRIPTION "Coding Violations Section-Bip Error Lane 06."
    ::= { gigeClientCtpPmEntry  85 }

gigeClientCtpPmRxCvsPcs07 OBJECT-TYPE
    SYNTAX      Integer32
    MAX-ACCESS  read-only
    STATUS      current
    DESCRIPTION "Coding Violations Section-Bip Error Lane 07."
    ::= { gigeClientCtpPmEntry  86 }

gigeClientCtpPmRxCvsPcs08 OBJECT-TYPE
    SYNTAX      Integer32
    MAX-ACCESS  read-only
    STATUS      current
    DESCRIPTION "Coding Violations Section-Bip Error Lane 08."
    ::= { gigeClientCtpPmEntry  87 }

gigeClientCtpPmRxCvsPcs09 OBJECT-TYPE
    SYNTAX      Integer32
    MAX-ACCESS  read-only
    STATUS      current
    DESCRIPTION "Coding Violations Section-Bip Error Lane 09."
    ::= { gigeClientCtpPmEntry  88 }

gigeClientCtpPmRxCvsPcs10 OBJECT-TYPE
    SYNTAX      Integer32
    MAX-ACCESS  read-only
    STATUS      current
    DESCRIPTION "Coding Violations Section-Bip Error Lane 10."
    ::= { gigeClientCtpPmEntry  89 }

gigeClientCtpPmRxCvsPcs11 OBJECT-TYPE
    SYNTAX      Integer32
    MAX-ACCESS  read-only
    STATUS      current
    DESCRIPTION "Coding Violations Section-Bip Error Lane 11."
    ::= { gigeClientCtpPmEntry  90 }

gigeClientCtpPmRxCvsPcs12 OBJECT-TYPE
    SYNTAX      Integer32
    MAX-ACCESS  read-only
    STATUS      current
    DESCRIPTION "Coding Violations Section-Bip Error Lane 12."
    ::= { gigeClientCtpPmEntry  91 }

gigeClientCtpPmRxCvsPcs13 OBJECT-TYPE
    SYNTAX      Integer32
    MAX-ACCESS  read-only
    STATUS      current
    DESCRIPTION "Coding Violations Section-Bip Error Lane 13."
    ::= { gigeClientCtpPmEntry  92 }

gigeClientCtpPmRxCvsPcs14 OBJECT-TYPE
    SYNTAX      Integer32
    MAX-ACCESS  read-only
    STATUS      current
    DESCRIPTION "Coding Violations Section-Bip Error Lane 14."
    ::= { gigeClientCtpPmEntry  93 }

gigeClientCtpPmRxCvsPcs15 OBJECT-TYPE
    SYNTAX      Integer32
    MAX-ACCESS  read-only
    STATUS      current
    DESCRIPTION "Coding Violations Section-Bip Error Lane 15."
    ::= { gigeClientCtpPmEntry  94 }

gigeClientCtpPmRxCvsPcs16 OBJECT-TYPE
    SYNTAX      Integer32
    MAX-ACCESS  read-only
    STATUS      current
    DESCRIPTION "Coding Violations Section-Bip Error Lane 16."
    ::= { gigeClientCtpPmEntry  95 }

gigeClientCtpPmRxCvsPcs17 OBJECT-TYPE
    SYNTAX      Integer32
    MAX-ACCESS  read-only
    STATUS      current
    DESCRIPTION "Coding Violations Section-Bip Error Lane 17."
    ::= { gigeClientCtpPmEntry  96 }

gigeClientCtpPmRxCvsPcs18 OBJECT-TYPE
    SYNTAX      Integer32
    MAX-ACCESS  read-only
    STATUS      current
    DESCRIPTION "Coding Violations Section-Bip Error Lane 18."
    ::= { gigeClientCtpPmEntry  97 }

gigeClientCtpPmRxCvsPcs19 OBJECT-TYPE
    SYNTAX      Integer32
    MAX-ACCESS  read-only
    STATUS      current
    DESCRIPTION "Coding Violations Section-Bip Error Lane 19."
    ::= { gigeClientCtpPmEntry  98 }

gigeClientCtpPmRxCvsPcs20 OBJECT-TYPE
    SYNTAX      Integer32
    MAX-ACCESS  read-only
    STATUS      current
    DESCRIPTION "Coding Violations Section-Bip Error Lane 20."
    ::= { gigeClientCtpPmEntry  99 }


gigeClientCtpPmRxErrPackets OBJECT-TYPE
    SYNTAX      HCPerfIntervalCount
    MAX-ACCESS  read-only
    STATUS      current
    DESCRIPTION ""
    ::= { gigeClientCtpPmEntry  100}

gigeClientCtpPmRxDiscarded  OBJECT-TYPE
    SYNTAX      HCPerfIntervalCount
    MAX-ACCESS  read-only
    STATUS      current
    DESCRIPTION ""
    ::= { gigeClientCtpPmEntry  101}

gigeClientCtpPmRxCorrectedWords OBJECT-TYPE
    SYNTAX      Integer32
    MAX-ACCESS  read-only
    STATUS      current
    DESCRIPTION "Number of corrected words"
    ::= { gigeClientCtpPmEntry  102 }

gigeClientCtpPmRxUncorrectedWords OBJECT-TYPE
    SYNTAX      Integer32
    MAX-ACCESS  read-only
    STATUS      current
    DESCRIPTION "Number of uncorrected words"
    ::= { gigeClientCtpPmEntry  103 }

gigeClientCtpPmRxCorrectedBit OBJECT-TYPE
    SYNTAX      Integer32
    MAX-ACCESS  read-only
    STATUS      current
    DESCRIPTION "Number of corrected bits"
    ::= { gigeClientCtpPmEntry  104 }

gigeClientCtpPmRealTable OBJECT-TYPE
    SYNTAX      SEQUENCE OF GigeClientCtpPmRealEntry
    MAX-ACCESS  not-accessible
    STATUS      current
    DESCRIPTION
        "A list of GigeClientCtpPmReal entries. Each entry is uniquely identified by the value of ifIndex."
    ::= { gigeClientCtpPmMIB 1 }

gigeClientCtpPmRealEntry  OBJECT-TYPE
    SYNTAX      GigeClientCtpPmRealEntry
    MAX-ACCESS  not-accessible
    STATUS      current
    DESCRIPTION
        "A GigeClientCtp entry containing real-time performance information pertaining to Infinera GigeClientCtp interfaces.
        This table is a subclass of IfCommon. Entries will exist in this table only for interfaces of
        type GigeClientCtp."
    INDEX { ifIndex }
    ::= { gigeClientCtpPmRealTable 1 }



GigeClientCtpPmRealEntry  ::= SEQUENCE {
    gigeClientCtpPmRealRxLU                 FloatHundredths,
    gigeClientCtpPmRealRxPcsICG             Counter64,
    gigeClientCtpPmRealRxPcsES              Integer32,
    gigeClientCtpPmRealRxPcsSES             Integer32,
    gigeClientCtpPmRealRxPcsSESS            Integer32,
    gigeClientCtpPmRealTxPcsICG             Counter64,
    gigeClientCtpPmRealTxPcsES              Integer32,
    gigeClientCtpPmRealTxPcsSES             Integer32,
    gigeClientCtpPmRealTxPcsSESS            Integer32,
    gigeClientCtpPmRealRxPackets            Counter64,
    gigeClientCtpPmRealRxOctets             Counter64,
    gigeClientCtpPmRealRxErrOctets          Counter64,
    gigeClientCtpPmRealRxJabbers            Counter64,
    gigeClientCtpPmRealRxFragments          Counter64,
    gigeClientCtpPmRealRxCrcAlignedErr      Counter64,
    gigeClientCtpPmRealRxUndersized         Counter64,
    gigeClientCtpPmRealRxOversized          Counter64,
    gigeClientCtpPmRealRxJabberSecs         Integer32,
    gigeClientCtpPmRealRxMacSES             Integer32,
    gigeClientCtpPmRealRxBroadcastPkts      Counter64,
    gigeClientCtpPmRealRxMulticastPkts      Counter64,
    gigeClientCtpPmRealRxInPauseFrames      Counter64,
    gigeClientCtpPmRealTxLU                 FloatHundredths,
    gigeClientCtpPmRealTxPackets            Counter64,
    gigeClientCtpPmRealTxOctets             Counter64,
    gigeClientCtpPmRealTxErrOctets          Counter64,
    gigeClientCtpPmRealTxJabbers            Counter64,
    gigeClientCtpPmRealTxFragments          Counter64,
    gigeClientCtpPmRealTxCrcAlignedErr      Counter64,
    gigeClientCtpPmRealTxUndersized         Counter64,
    gigeClientCtpPmRealTxOversized          Counter64,
    gigeClientCtpPmRealTxJabberSecs         Integer32,
    gigeClientCtpPmRealTxMacSES             Integer32,
    gigeClientCtpPmRealTxBroadcastPkts      Counter64,
    gigeClientCtpPmRealTxMulticastPkts      Counter64,
    gigeClientCtpPmRealTxOutPauseFrames     Counter64,
    gigeClientCtpPmRealRxSize64             Counter64,
    gigeClientCtpPmRealRxSize65to127        Counter64,
    gigeClientCtpPmRealRxSize128to255       Counter64,
    gigeClientCtpPmRealRxSize256to511       Counter64,
    gigeClientCtpPmRealRxSize512to1023      Counter64,
    gigeClientCtpPmRealRxSize1024to1518     Counter64,
    gigeClientCtpPmRealRxSize1519toJumbo    Counter64,
    gigeClientCtpPmRealTxSize64             Counter64,
    gigeClientCtpPmRealTxSize65to127        Counter64,
    gigeClientCtpPmRealTxSize128to255       Counter64,
    gigeClientCtpPmRealTxSize256to511       Counter64,
    gigeClientCtpPmRealTxSize512to1023      Counter64,
    gigeClientCtpPmRealTxSize1024to1518     Counter64,
    gigeClientCtpPmRealTxSize1519toJumbo    Counter64,
    gigeClientCtpPmRealCktId                DisplayString,
    gigeClientCtpPmRealLineTestSigSyncErr    Integer32,
    gigeClientCtpPmRealLineTestSigErr        Integer32,
    gigeClientCtpPmRealTribTestSigSyncErr    Integer32,
    gigeClientCtpPmRealTribTestSigErr        Integer32,
    gigeClientCtpPmRealRxSize1024to1522     Counter64,
    gigeClientCtpPmRealRxSize1523toJumbo    Counter64,
    gigeClientCtpPmRealTxSize1024to1522     Counter64,
    gigeClientCtpPmRealTxSize1523toJumbo    Counter64,
    gigeClientCtpPmRealTxCvsPcs01           Integer32,
    gigeClientCtpPmRealTxCvsPcs02           Integer32,
    gigeClientCtpPmRealTxCvsPcs03           Integer32,
    gigeClientCtpPmRealTxCvsPcs04           Integer32,
    gigeClientCtpPmRealTxCvsPcs05           Integer32,
    gigeClientCtpPmRealTxCvsPcs06           Integer32,
    gigeClientCtpPmRealTxCvsPcs07           Integer32,
    gigeClientCtpPmRealTxCvsPcs08           Integer32,
    gigeClientCtpPmRealTxCvsPcs09           Integer32,
    gigeClientCtpPmRealTxCvsPcs10           Integer32,
    gigeClientCtpPmRealTxCvsPcs11           Integer32,
    gigeClientCtpPmRealTxCvsPcs12           Integer32,
    gigeClientCtpPmRealTxCvsPcs13           Integer32,
    gigeClientCtpPmRealTxCvsPcs14           Integer32,
    gigeClientCtpPmRealTxCvsPcs15           Integer32,
    gigeClientCtpPmRealTxCvsPcs16           Integer32,
    gigeClientCtpPmRealTxCvsPcs17           Integer32,
    gigeClientCtpPmRealTxCvsPcs18           Integer32,
    gigeClientCtpPmRealTxCvsPcs19           Integer32,
    gigeClientCtpPmRealTxCvsPcs20           Integer32,
    gigeClientCtpPmRealRxCvsPcs01           Integer32,
    gigeClientCtpPmRealRxCvsPcs02           Integer32,
    gigeClientCtpPmRealRxCvsPcs03           Integer32,
    gigeClientCtpPmRealRxCvsPcs04           Integer32,
    gigeClientCtpPmRealRxCvsPcs05           Integer32,
    gigeClientCtpPmRealRxCvsPcs06           Integer32,
    gigeClientCtpPmRealRxCvsPcs07           Integer32,
    gigeClientCtpPmRealRxCvsPcs08           Integer32,
    gigeClientCtpPmRealRxCvsPcs09           Integer32,
    gigeClientCtpPmRealRxCvsPcs10           Integer32,
    gigeClientCtpPmRealRxCvsPcs11           Integer32,
    gigeClientCtpPmRealRxCvsPcs12           Integer32,
    gigeClientCtpPmRealRxCvsPcs13           Integer32,
    gigeClientCtpPmRealRxCvsPcs14           Integer32,
    gigeClientCtpPmRealRxCvsPcs15           Integer32,
    gigeClientCtpPmRealRxCvsPcs16           Integer32,
    gigeClientCtpPmRealRxCvsPcs17           Integer32,
    gigeClientCtpPmRealRxCvsPcs18           Integer32,
    gigeClientCtpPmRealRxCvsPcs19           Integer32,
    gigeClientCtpPmRealRxCvsPcs20           Integer32,
    gigeClientCtpPmRealRxErrPackets         Counter64,
    gigeClientCtpPmRealRxDiscarded          Counter64,
    gigeClientCtpPmRealRxCorrectedWords      Integer32,
    gigeClientCtpPmRealRxUncorrectedWords    Integer32,
    gigeClientCtpPmRealRxCorrectedBit        Integer32

}

gigeClientCtpPmRealRxLU OBJECT-TYPE
    SYNTAX      FloatHundredths
    MAX-ACCESS  read-only
    STATUS      current
    DESCRIPTION "Receive Link utilization."
    ::= { gigeClientCtpPmRealEntry  1 }


gigeClientCtpPmRealRxPcsICG OBJECT-TYPE
    SYNTAX      Counter64
    MAX-ACCESS  read-only
    STATUS      current
    DESCRIPTION "Number of Invalid Code Group detected by the Physical Coding Sublayer."
    ::= { gigeClientCtpPmRealEntry  2 }


gigeClientCtpPmRealRxPcsES OBJECT-TYPE
    SYNTAX      Integer32
    MAX-ACCESS  read-only
    STATUS      current
    DESCRIPTION "Number of errored seconds detected by the Physical Coding Sublayer."
    ::= { gigeClientCtpPmRealEntry  3 }


gigeClientCtpPmRealRxPcsSES OBJECT-TYPE
    SYNTAX      Integer32
    MAX-ACCESS  read-only
    STATUS      current
    DESCRIPTION "Number of severely errored seconds detected by the Physical Coding Sublayer."
    ::= { gigeClientCtpPmRealEntry  4 }


gigeClientCtpPmRealRxPcsSESS OBJECT-TYPE
    SYNTAX      Integer32
    MAX-ACCESS  read-only
    STATUS      current
    DESCRIPTION "Number of Severely Errored Sync Seconds detected by the Physical Coding Sublayer."
    ::= { gigeClientCtpPmRealEntry  5 }


gigeClientCtpPmRealTxPcsICG OBJECT-TYPE
    SYNTAX      Counter64
    MAX-ACCESS  read-only
    STATUS      current
    DESCRIPTION "Number of Invalid Code Group detected by the Physical Coding Sublayer."
    ::= { gigeClientCtpPmRealEntry  6 }


gigeClientCtpPmRealTxPcsES OBJECT-TYPE
    SYNTAX      Integer32
    MAX-ACCESS  read-only
    STATUS      current
    DESCRIPTION "Number of errored seconds detected by the Physical Coding Sublayer."
    ::= { gigeClientCtpPmRealEntry  7 }


gigeClientCtpPmRealTxPcsSES OBJECT-TYPE
    SYNTAX      Integer32
    MAX-ACCESS  read-only
    STATUS      current
    DESCRIPTION "Number of severely errored seconds detected by the Physical Coding Sublayer."
    ::= { gigeClientCtpPmRealEntry  8 }


gigeClientCtpPmRealTxPcsSESS OBJECT-TYPE
    SYNTAX      Integer32
    MAX-ACCESS  read-only
    STATUS      current
    DESCRIPTION "Number of Severely Errored Sync Seconds detected by the Physical Coding Sublayer."
    ::= { gigeClientCtpPmRealEntry  9 }


gigeClientCtpPmRealRxPackets OBJECT-TYPE
    SYNTAX      Counter64
    MAX-ACCESS  read-only
    STATUS      current
    DESCRIPTION "Number of received data packets."
    ::= { gigeClientCtpPmRealEntry  10 }


gigeClientCtpPmRealRxOctets OBJECT-TYPE
    SYNTAX      Counter64
    MAX-ACCESS  read-only
    STATUS      current
    DESCRIPTION "Number of received data octets."
    ::= { gigeClientCtpPmRealEntry  11 }


gigeClientCtpPmRealRxErrOctets OBJECT-TYPE
    SYNTAX      Counter64
    MAX-ACCESS  read-only
    STATUS      current
    DESCRIPTION "Errored octet. Number of data octets that are part of an Errored Packet (i.e., the FCS is in error, resulting in incrementing the Fragment counter, the Jabber counter, or the CRCAlignError counter), on the receive client interface."
    ::= { gigeClientCtpPmRealEntry  12 }


gigeClientCtpPmRealRxJabbers OBJECT-TYPE
    SYNTAX      Counter64
    MAX-ACCESS  read-only
    STATUS      current
    DESCRIPTION "Jabber count. Number of packets received that are longer than the maximum frame length octets (excluding framing bits, but including FCS octets) and has either a bad FCS with an integral number of octets (FCS error) or a bad FCS with a non-integral number of octets (alignment error)."
    ::= { gigeClientCtpPmRealEntry  13 }


gigeClientCtpPmRealRxFragments OBJECT-TYPE
    SYNTAX      Counter64
    MAX-ACCESS  read-only
    STATUS      current
    DESCRIPTION "Fragment packet count. Number of packets received that are less than 64 octets long (excluding framing bits, but including FCS octets) and have either a bad FCS with an integral number of octets (FCS error) or a bad FCS with a non-integral number of octets (alignment error), on the receive client interface."
    ::= { gigeClientCtpPmRealEntry  14 }


gigeClientCtpPmRealRxCrcAlignedErr OBJECT-TYPE
    SYNTAX      Counter64
    MAX-ACCESS  read-only
    STATUS      current
    DESCRIPTION "Cyclical redundancy check align error count. Number of packets received that have a length (excluding framing bits, but including FCS octets) of between 64 and MaxFrameLength octets, inclusive, but have either a bad FCS with an integral number of octets (FCS Error) or a bad FCS with a non-integral number of octets (Alignment Error), on the receive client interface."
    ::= { gigeClientCtpPmRealEntry  15 }


gigeClientCtpPmRealRxUndersized OBJECT-TYPE
    SYNTAX      Counter64
    MAX-ACCESS  read-only
    STATUS      current
    DESCRIPTION "Undersize packet count. Number of received packets that are less than 64 octets long (excluding framing bits, but including FCS octets) and are otherwise well formed, on the receive client interface."
    ::= { gigeClientCtpPmRealEntry  16 }


gigeClientCtpPmRealRxOversized OBJECT-TYPE
    SYNTAX      Counter64
    MAX-ACCESS  read-only
    STATUS      current
    DESCRIPTION "Oversize packet count. Number of received packets that are longer than the maximum frame length (excluding framing bits, but including FCS octets) and are otherwise well formed, on the receive client interface."
    ::= { gigeClientCtpPmRealEntry  17 }


gigeClientCtpPmRealRxJabberSecs OBJECT-TYPE
    SYNTAX      Integer32
    MAX-ACCESS  read-only
    STATUS      current
    DESCRIPTION "Jabber Seconds. Number of seconds in which a jabber state was detected sometime in that second."
    ::= { gigeClientCtpPmRealEntry  18 }


gigeClientCtpPmRealRxMacSES OBJECT-TYPE
    SYNTAX      Integer32
    MAX-ACCESS  read-only
    STATUS      current
    DESCRIPTION "Severely Errored Seconds – Packet/Octet layer. Number of seconds in which at least 30% of observed Data Octets are Errored Data Octets, or the TP was in a Severely Errored Second - PCS."
    ::= { gigeClientCtpPmRealEntry  19 }


gigeClientCtpPmRealRxBroadcastPkts OBJECT-TYPE
    SYNTAX      Counter64
    MAX-ACCESS  read-only
    STATUS      current
    DESCRIPTION "A count of frames that are successfully received and are directed to the broadcast group address. This does not include frames received with frame-too-long, FCS, length, or alignment errors, or frames lost due to internal MAC sublayer error."
    ::= { gigeClientCtpPmRealEntry  20 }


gigeClientCtpPmRealRxMulticastPkts OBJECT-TYPE
    SYNTAX      Counter64
    MAX-ACCESS  read-only
    STATUS      current
    DESCRIPTION "A count of frames that are successfully received and are directed to an active nonbroadcast group address. This does not include frames received with frame-too-long, FCS, length, or alignment errors, or frames lost due to internal MAC sublayer error."
    ::= { gigeClientCtpPmRealEntry  21 }


gigeClientCtpPmRealRxInPauseFrames OBJECT-TYPE
    SYNTAX      Counter64
    MAX-ACCESS  read-only
    STATUS      current
    DESCRIPTION "A count of MAC Control frames received on this interface with an opcode indicating the PAUSE operation. This counter does not increment when the interface is operating in half-duplex mode."
    ::= { gigeClientCtpPmRealEntry  22 }


gigeClientCtpPmRealTxLU OBJECT-TYPE
    SYNTAX      FloatHundredths
    MAX-ACCESS  read-only
    STATUS      current
    DESCRIPTION "Transmit Link utilization."
    ::= { gigeClientCtpPmRealEntry  23 }


gigeClientCtpPmRealTxPackets OBJECT-TYPE
    SYNTAX      Counter64
    MAX-ACCESS  read-only
    STATUS      current
    DESCRIPTION "Number of transmitted data packets."
    ::= { gigeClientCtpPmRealEntry  24 }


gigeClientCtpPmRealTxOctets OBJECT-TYPE
    SYNTAX      Counter64
    MAX-ACCESS  read-only
    STATUS      current
    DESCRIPTION "Number of transmitted data octets."
    ::= { gigeClientCtpPmRealEntry  25 }


gigeClientCtpPmRealTxErrOctets OBJECT-TYPE
    SYNTAX      Counter64
    MAX-ACCESS  read-only
    STATUS      current
    DESCRIPTION "Errored octet. Number of data octets that are part of an Errored Packet (i.e., the FCS is in error, resulting in incrementing the Fragment counter, the Jabber counter, or the CRCAlignError counter), at the signal de-encapsulation point before the client-side transmit interface."
    ::= { gigeClientCtpPmRealEntry  26 }


gigeClientCtpPmRealTxJabbers OBJECT-TYPE
    SYNTAX      Counter64
    MAX-ACCESS  read-only
    STATUS      current
    DESCRIPTION "Jabber count. Number of packets transmitted that are longer than the maximum frame length octets (excluding framing bits, but including FCS octets) and has either a bad FCS with an integral number of octets (FCS error) or a bad FCS with a non-integral number of octets (alignment error)."
    ::= { gigeClientCtpPmRealEntry  27 }


gigeClientCtpPmRealTxFragments OBJECT-TYPE
    SYNTAX      Counter64
    MAX-ACCESS  read-only
    STATUS      current
    DESCRIPTION "Fragment packet count. Number of packets transmitted that are less than 64 octets long (excluding framing bits, but including FCS octets) and have either a bad FCS with an integral number of octets (FCS error) or a bad FCS with a non-integral number of octets (alignment error), on the receive client interface."
    ::= { gigeClientCtpPmRealEntry  28 }


gigeClientCtpPmRealTxCrcAlignedErr OBJECT-TYPE
    SYNTAX      Counter64
    MAX-ACCESS  read-only
    STATUS      current
    DESCRIPTION "Cyclical redundancy check align error count. Number of packets transmitted that have a length (excluding framing bits, but including FCS octets) of between 64 and MaxFrameLength octets, inclusive, but have either a bad FCS with an integral number of octets (FCS Error) or a bad FCS with a non-integral number of octets (Alignment Error), on the receive client interface."
    ::= { gigeClientCtpPmRealEntry  29 }


gigeClientCtpPmRealTxUndersized OBJECT-TYPE
    SYNTAX      Counter64
    MAX-ACCESS  read-only
    STATUS      current
    DESCRIPTION "Undersize packet count. Number of transmitted packets that are less than 64 octets long (excluding framing bits, but including FCS octets) and are otherwise well formed."
    ::= { gigeClientCtpPmRealEntry  30 }


gigeClientCtpPmRealTxOversized OBJECT-TYPE
    SYNTAX      Counter64
    MAX-ACCESS  read-only
    STATUS      current
    DESCRIPTION "Oversize packet count. Number of transmitted packets that are longer than the maximum frame length (excluding framing bits, but including FCS octets) and are otherwise well formed, on the receive client interface."
    ::= { gigeClientCtpPmRealEntry  31 }


gigeClientCtpPmRealTxJabberSecs OBJECT-TYPE
    SYNTAX      Integer32
    MAX-ACCESS  read-only
    STATUS      current
    DESCRIPTION "Jabber Seconds. Number of seconds in which a jabber state was detected sometime in that second on the de-encapsulated signal."
    ::= { gigeClientCtpPmRealEntry  32 }


gigeClientCtpPmRealTxMacSES OBJECT-TYPE
    SYNTAX      Integer32
    MAX-ACCESS  read-only
    STATUS      current
    DESCRIPTION "Severely Errored Seconds – Packet/Octet layer. Number of seconds in which at least 30% of observed de-encap Data Octets are Errored Data Octets, or the TP was in a de-encap Severely Errored Second - PCS."
    ::= { gigeClientCtpPmRealEntry  33 }


gigeClientCtpPmRealTxBroadcastPkts OBJECT-TYPE
    SYNTAX      Counter64
    MAX-ACCESS  read-only
    STATUS      current
    DESCRIPTION "A count of the frames that were successfully transmitted, as indicated by the transmit status “transmit OK”, to the broadcast address. Frames transmitted to multicast addresses are not broadcast frames and are excluded."
    ::= { gigeClientCtpPmRealEntry  34 }


gigeClientCtpPmRealTxMulticastPkts OBJECT-TYPE
    SYNTAX      Counter64
    MAX-ACCESS  read-only
    STATUS      current
    DESCRIPTION "A count of frames that are successfully transmitted, as indicated by the status value “transmit OK”, to a group destination address other than broadcast."
    ::= { gigeClientCtpPmRealEntry  35 }


gigeClientCtpPmRealTxOutPauseFrames OBJECT-TYPE
    SYNTAX      Counter64
    MAX-ACCESS  read-only
    STATUS      current
    DESCRIPTION "A count of MAC Control frames transmitted on this interface with an opcode indicating the PAUSE operation. This counter does not increment when the interface is operating in half-duplex mode. This counter can roll over in less than 5 minutes if it is incrementing at its maximum rate. Since that amount of time could be less than a management station's poll cycle time, in order to avoid a loss of information, a management station is advised to poll the dot3HCOutPauseFrames object for 10 Gb/s or faster interfaces."
    ::= { gigeClientCtpPmRealEntry  36 }


gigeClientCtpPmRealRxSize64 OBJECT-TYPE
    SYNTAX      Counter64
    MAX-ACCESS  read-only
    STATUS      current
    DESCRIPTION "Received packets (including bad packets) of 64 or less octets."
    ::= { gigeClientCtpPmRealEntry  37 }


gigeClientCtpPmRealRxSize65to127 OBJECT-TYPE
    SYNTAX      Counter64
    MAX-ACCESS  read-only
    STATUS      current
    DESCRIPTION "Received packets (including bad packets) from 65 to 127 octets."
    ::= { gigeClientCtpPmRealEntry  38 }


gigeClientCtpPmRealRxSize128to255 OBJECT-TYPE
    SYNTAX      Counter64
    MAX-ACCESS  read-only
    STATUS      current
    DESCRIPTION "Received packets (including bad packets) from 128 to 255 octets."
    ::= { gigeClientCtpPmRealEntry  39 }


gigeClientCtpPmRealRxSize256to511 OBJECT-TYPE
    SYNTAX      Counter64
    MAX-ACCESS  read-only
    STATUS      current
    DESCRIPTION "Received packets (including bad packets) from 256 to 511 octets."
    ::= { gigeClientCtpPmRealEntry  40 }


gigeClientCtpPmRealRxSize512to1023 OBJECT-TYPE
    SYNTAX      Counter64
    MAX-ACCESS  read-only
    STATUS      current
    DESCRIPTION "Received packets (including bad packets) from 512 to 1023 octets."
    ::= { gigeClientCtpPmRealEntry  41 }


gigeClientCtpPmRealRxSize1024to1518 OBJECT-TYPE
    SYNTAX      Counter64
    MAX-ACCESS  read-only
    STATUS      current
    DESCRIPTION "Received packets (including bad packets) from 1024 to 1518 octets."
    ::= { gigeClientCtpPmRealEntry  42 }


gigeClientCtpPmRealRxSize1519toJumbo OBJECT-TYPE
    SYNTAX      Counter64
    MAX-ACCESS  read-only
    STATUS      current
    DESCRIPTION "Received packets (including bad packets) of 1519 or more octets."
    ::= { gigeClientCtpPmRealEntry  43 }


gigeClientCtpPmRealTxSize64 OBJECT-TYPE
    SYNTAX      Counter64
    MAX-ACCESS  read-only
    STATUS      current
    DESCRIPTION "Transmitted packets of 64 or less octets."
    ::= { gigeClientCtpPmRealEntry  44 }


gigeClientCtpPmRealTxSize65to127 OBJECT-TYPE
    SYNTAX      Counter64
    MAX-ACCESS  read-only
    STATUS      current
    DESCRIPTION "Transmitted packets from 65 to 127 octets."
    ::= { gigeClientCtpPmRealEntry  45 }


gigeClientCtpPmRealTxSize128to255 OBJECT-TYPE
    SYNTAX      Counter64
    MAX-ACCESS  read-only
    STATUS      current
    DESCRIPTION "Transmitted packets from 128 to 255 octets."
    ::= { gigeClientCtpPmRealEntry  46 }


gigeClientCtpPmRealTxSize256to511 OBJECT-TYPE
    SYNTAX      Counter64
    MAX-ACCESS  read-only
    STATUS      current
    DESCRIPTION "Transmitted packets from 256 to 511 octets."
    ::= { gigeClientCtpPmRealEntry  47 }


gigeClientCtpPmRealTxSize512to1023 OBJECT-TYPE
    SYNTAX      Counter64
    MAX-ACCESS  read-only
    STATUS      current
    DESCRIPTION "Transmitted packets from 512 to 1023 octets."
    ::= { gigeClientCtpPmRealEntry  48 }


gigeClientCtpPmRealTxSize1024to1518 OBJECT-TYPE
    SYNTAX      Counter64
    MAX-ACCESS  read-only
    STATUS      current
    DESCRIPTION "Transmitted packets from 1024 to 1518 octets."
    ::= { gigeClientCtpPmRealEntry  49 }


gigeClientCtpPmRealTxSize1519toJumbo OBJECT-TYPE
    SYNTAX      Counter64
    MAX-ACCESS  read-only
    STATUS      current
    DESCRIPTION "Transmitted packets of 1519 or more octets."
    ::= { gigeClientCtpPmRealEntry  50 }


gigeClientCtpPmRealCktId OBJECT-TYPE
    SYNTAX      DisplayString
    MAX-ACCESS  read-only
    STATUS      current
    DESCRIPTION "Circuit ID(s) of the connection "
    ::= { gigeClientCtpPmRealEntry  51 }


gigeClientCtpPmRealLineTestSigSyncErr OBJECT-TYPE
    SYNTAX      Integer32
    MAX-ACCESS  read-only
    STATUS      current
    DESCRIPTION "Count of the number of times re-sync has been attempted after initial sync was achieved. Incremented only when PRBS monitoring is enabled."
    ::= { gigeClientCtpPmRealEntry  52 }


gigeClientCtpPmRealLineTestSigErr OBJECT-TYPE
    SYNTAX      Integer32
    MAX-ACCESS  read-only
    STATUS      current
    DESCRIPTION "Count of the number of bits not matching the expected pattern (whether synch has been achieved or not). Incremented only when PRBS monitoring is enabled."
    ::= { gigeClientCtpPmRealEntry  53 }


gigeClientCtpPmRealTribTestSigSyncErr OBJECT-TYPE
    SYNTAX      Integer32
    MAX-ACCESS  read-only
    STATUS      current
    DESCRIPTION "Count of the number of times re-sync has been attempted after initial sync was achieved. Incremented only when PRBS monitoring is enabled."
    ::= { gigeClientCtpPmRealEntry  54 }


gigeClientCtpPmRealTribTestSigErr OBJECT-TYPE
    SYNTAX      Integer32
    MAX-ACCESS  read-only
    STATUS      current
    DESCRIPTION "Count of the number of bits not matching the expected pattern (whether synch has been achieved or not). Incremented only when PRBS monitoring is enabled."
    ::= { gigeClientCtpPmRealEntry  55 }

gigeClientCtpPmRealRxSize1024to1522 OBJECT-TYPE
    SYNTAX      Counter64
    MAX-ACCESS  read-only
    STATUS      current
    DESCRIPTION "Received packets (including bad packets) from 1024 to 1522 octets."
    ::= { gigeClientCtpPmRealEntry  56 }



gigeClientCtpPmRealRxSize1523toJumbo OBJECT-TYPE
    SYNTAX      Counter64
    MAX-ACCESS  read-only
    STATUS      current
    DESCRIPTION "Received packets (including bad packets) of 1523 or more octets."
    ::= { gigeClientCtpPmRealEntry  57 }


gigeClientCtpPmRealTxSize1024to1522 OBJECT-TYPE
    SYNTAX      Counter64
    MAX-ACCESS  read-only
    STATUS      current
    DESCRIPTION "Transmitted packets from 1024 to 1522 octets."
    ::= { gigeClientCtpPmRealEntry  58 }


gigeClientCtpPmRealTxSize1523toJumbo OBJECT-TYPE
    SYNTAX      Counter64
    MAX-ACCESS  read-only
    STATUS      current
    DESCRIPTION "Transmitted packets of 1523 or more octets."
    ::= { gigeClientCtpPmRealEntry  59 }

gigeClientCtpPmRealTxCvsPcs01 OBJECT-TYPE
    SYNTAX      Integer32
    MAX-ACCESS  read-only
    STATUS      current
    DESCRIPTION "Coding Violations Section-Bip Error Lane 01."
    ::= { gigeClientCtpPmRealEntry  60 }

gigeClientCtpPmRealTxCvsPcs02 OBJECT-TYPE
    SYNTAX      Integer32
    MAX-ACCESS  read-only
    STATUS      current
    DESCRIPTION "Coding Violations Section-Bip Error Lane 02."
    ::= { gigeClientCtpPmRealEntry  61 }

gigeClientCtpPmRealTxCvsPcs03 OBJECT-TYPE
    SYNTAX      Integer32
    MAX-ACCESS  read-only
    STATUS      current
    DESCRIPTION "Coding Violations Section-Bip Error Lane 03."
    ::= { gigeClientCtpPmRealEntry  62 }

gigeClientCtpPmRealTxCvsPcs04 OBJECT-TYPE
    SYNTAX      Integer32
    MAX-ACCESS  read-only
    STATUS      current
    DESCRIPTION "Coding Violations Section-Bip Error Lane 04."
    ::= { gigeClientCtpPmRealEntry  63 }

gigeClientCtpPmRealTxCvsPcs05 OBJECT-TYPE
    SYNTAX      Integer32
    MAX-ACCESS  read-only
    STATUS      current
    DESCRIPTION "Coding Violations Section-Bip Error Lane 05."
    ::= { gigeClientCtpPmRealEntry  64 }

gigeClientCtpPmRealTxCvsPcs06 OBJECT-TYPE
    SYNTAX      Integer32
    MAX-ACCESS  read-only
    STATUS      current
    DESCRIPTION "Coding Violations Section-Bip Error Lane 06."
    ::= { gigeClientCtpPmRealEntry  65 }

gigeClientCtpPmRealTxCvsPcs07 OBJECT-TYPE
    SYNTAX      Integer32
    MAX-ACCESS  read-only
    STATUS      current
    DESCRIPTION "Coding Violations Section-Bip Error Lane 07."
    ::= { gigeClientCtpPmRealEntry  66 }

gigeClientCtpPmRealTxCvsPcs08 OBJECT-TYPE
    SYNTAX      Integer32
    MAX-ACCESS  read-only
    STATUS      current
    DESCRIPTION "Coding Violations Section-Bip Error Lane 08."
    ::= { gigeClientCtpPmRealEntry  67 }

gigeClientCtpPmRealTxCvsPcs09 OBJECT-TYPE
    SYNTAX      Integer32
    MAX-ACCESS  read-only
    STATUS      current
    DESCRIPTION "Coding Violations Section-Bip Error Lane 09."
    ::= { gigeClientCtpPmRealEntry  68 }

gigeClientCtpPmRealTxCvsPcs10 OBJECT-TYPE
    SYNTAX      Integer32
    MAX-ACCESS  read-only
    STATUS      current
    DESCRIPTION "Coding Violations Section-Bip Error Lane 10."
    ::= { gigeClientCtpPmRealEntry  69 }

gigeClientCtpPmRealTxCvsPcs11 OBJECT-TYPE
    SYNTAX      Integer32
    MAX-ACCESS  read-only
    STATUS      current
    DESCRIPTION "Coding Violations Section-Bip Error Lane 11."
    ::= { gigeClientCtpPmRealEntry  70 }

gigeClientCtpPmRealTxCvsPcs12 OBJECT-TYPE
    SYNTAX      Integer32
    MAX-ACCESS  read-only
    STATUS      current
    DESCRIPTION "Coding Violations Section-Bip Error Lane 12."
    ::= { gigeClientCtpPmRealEntry  71 }

gigeClientCtpPmRealTxCvsPcs13 OBJECT-TYPE
    SYNTAX      Integer32
    MAX-ACCESS  read-only
    STATUS      current
    DESCRIPTION "Coding Violations Section-Bip Error Lane 13."
    ::= { gigeClientCtpPmRealEntry  72 }

gigeClientCtpPmRealTxCvsPcs14 OBJECT-TYPE
    SYNTAX      Integer32
    MAX-ACCESS  read-only
    STATUS      current
    DESCRIPTION "Coding Violations Section-Bip Error Lane 14."
    ::= { gigeClientCtpPmRealEntry  73 }

gigeClientCtpPmRealTxCvsPcs15 OBJECT-TYPE
    SYNTAX      Integer32
    MAX-ACCESS  read-only
    STATUS      current
    DESCRIPTION "Coding Violations Section-Bip Error Lane 15."
    ::= { gigeClientCtpPmRealEntry  74 }

gigeClientCtpPmRealTxCvsPcs16 OBJECT-TYPE
    SYNTAX      Integer32
    MAX-ACCESS  read-only
    STATUS      current
    DESCRIPTION "Coding Violations Section-Bip Error Lane 16."
    ::= { gigeClientCtpPmRealEntry  75 }

gigeClientCtpPmRealTxCvsPcs17 OBJECT-TYPE
    SYNTAX      Integer32
    MAX-ACCESS  read-only
    STATUS      current
    DESCRIPTION "Coding Violations Section-Bip Error Lane 17."
    ::= { gigeClientCtpPmRealEntry  76 }

gigeClientCtpPmRealTxCvsPcs18 OBJECT-TYPE
    SYNTAX      Integer32
    MAX-ACCESS  read-only
    STATUS      current
    DESCRIPTION "Coding Violations Section-Bip Error Lane 18."
    ::= { gigeClientCtpPmRealEntry  77 }

gigeClientCtpPmRealTxCvsPcs19 OBJECT-TYPE
    SYNTAX      Integer32
    MAX-ACCESS  read-only
    STATUS      current
    DESCRIPTION "Coding Violations Section-Bip Error Lane 19."
    ::= { gigeClientCtpPmRealEntry  78 }

gigeClientCtpPmRealTxCvsPcs20 OBJECT-TYPE
    SYNTAX      Integer32
    MAX-ACCESS  read-only
    STATUS      current
    DESCRIPTION "Coding Violations Section-Bip Error Lane 20."
    ::= { gigeClientCtpPmRealEntry  79 }

gigeClientCtpPmRealRxCvsPcs01 OBJECT-TYPE
    SYNTAX      Integer32
    MAX-ACCESS  read-only
    STATUS      current
    DESCRIPTION "Coding Violations Section-Bip Error Lane 01."
    ::= { gigeClientCtpPmRealEntry  80 }

gigeClientCtpPmRealRxCvsPcs02 OBJECT-TYPE
    SYNTAX      Integer32
    MAX-ACCESS  read-only
    STATUS      current
    DESCRIPTION "Coding Violations Section-Bip Error Lane 02."
    ::= { gigeClientCtpPmRealEntry  81 }

gigeClientCtpPmRealRxCvsPcs03 OBJECT-TYPE
    SYNTAX      Integer32
    MAX-ACCESS  read-only
    STATUS      current
    DESCRIPTION "Coding Violations Section-Bip Error Lane 03."
    ::= { gigeClientCtpPmRealEntry  82 }

gigeClientCtpPmRealRxCvsPcs04 OBJECT-TYPE
    SYNTAX      Integer32
    MAX-ACCESS  read-only
    STATUS      current
    DESCRIPTION "Coding Violations Section-Bip Error Lane 04."
    ::= { gigeClientCtpPmRealEntry  83 }

gigeClientCtpPmRealRxCvsPcs05 OBJECT-TYPE
    SYNTAX      Integer32
    MAX-ACCESS  read-only
    STATUS      current
    DESCRIPTION "Coding Violations Section-Bip Error Lane 05."
    ::= { gigeClientCtpPmRealEntry  84 }

gigeClientCtpPmRealRxCvsPcs06 OBJECT-TYPE
    SYNTAX      Integer32
    MAX-ACCESS  read-only
    STATUS      current
    DESCRIPTION "Coding Violations Section-Bip Error Lane 06."
    ::= { gigeClientCtpPmRealEntry  85 }

gigeClientCtpPmRealRxCvsPcs07 OBJECT-TYPE
    SYNTAX      Integer32
    MAX-ACCESS  read-only
    STATUS      current
    DESCRIPTION "Coding Violations Section-Bip Error Lane 07."
    ::= { gigeClientCtpPmRealEntry  86 }

gigeClientCtpPmRealRxCvsPcs08 OBJECT-TYPE
    SYNTAX      Integer32
    MAX-ACCESS  read-only
    STATUS      current
    DESCRIPTION "Coding Violations Section-Bip Error Lane 08."
    ::= { gigeClientCtpPmRealEntry  87 }

gigeClientCtpPmRealRxCvsPcs09 OBJECT-TYPE
    SYNTAX      Integer32
    MAX-ACCESS  read-only
    STATUS      current
    DESCRIPTION "Coding Violations Section-Bip Error Lane 09."
    ::= { gigeClientCtpPmRealEntry  88 }

gigeClientCtpPmRealRxCvsPcs10 OBJECT-TYPE
    SYNTAX      Integer32
    MAX-ACCESS  read-only
    STATUS      current
    DESCRIPTION "Coding Violations Section-Bip Error Lane 10."
    ::= { gigeClientCtpPmRealEntry  89 }

gigeClientCtpPmRealRxCvsPcs11 OBJECT-TYPE
    SYNTAX      Integer32
    MAX-ACCESS  read-only
    STATUS      current
    DESCRIPTION "Coding Violations Section-Bip Error Lane 11."
    ::= { gigeClientCtpPmRealEntry  90 }

gigeClientCtpPmRealRxCvsPcs12 OBJECT-TYPE
    SYNTAX      Integer32
    MAX-ACCESS  read-only
    STATUS      current
    DESCRIPTION "Coding Violations Section-Bip Error Lane 12."
    ::= { gigeClientCtpPmRealEntry  91 }

gigeClientCtpPmRealRxCvsPcs13 OBJECT-TYPE
    SYNTAX      Integer32
    MAX-ACCESS  read-only
    STATUS      current
    DESCRIPTION "Coding Violations Section-Bip Error Lane 13."
    ::= { gigeClientCtpPmRealEntry  92 }

gigeClientCtpPmRealRxCvsPcs14 OBJECT-TYPE
    SYNTAX      Integer32
    MAX-ACCESS  read-only
    STATUS      current
    DESCRIPTION "Coding Violations Section-Bip Error Lane 14."
    ::= { gigeClientCtpPmRealEntry  93 }

gigeClientCtpPmRealRxCvsPcs15 OBJECT-TYPE
    SYNTAX      Integer32
    MAX-ACCESS  read-only
    STATUS      current
    DESCRIPTION "Coding Violations Section-Bip Error Lane 15."
    ::= { gigeClientCtpPmRealEntry  94 }

gigeClientCtpPmRealRxCvsPcs16 OBJECT-TYPE
    SYNTAX      Integer32
    MAX-ACCESS  read-only
    STATUS      current
    DESCRIPTION "Coding Violations Section-Bip Error Lane 16."
    ::= { gigeClientCtpPmRealEntry  95 }

gigeClientCtpPmRealRxCvsPcs17 OBJECT-TYPE
    SYNTAX      Integer32
    MAX-ACCESS  read-only
    STATUS      current
    DESCRIPTION "Coding Violations Section-Bip Error Lane 17."
    ::= { gigeClientCtpPmRealEntry  96 }

gigeClientCtpPmRealRxCvsPcs18 OBJECT-TYPE
    SYNTAX      Integer32
    MAX-ACCESS  read-only
    STATUS      current
    DESCRIPTION "Coding Violations Section-Bip Error Lane 18."
    ::= { gigeClientCtpPmRealEntry  97 }

gigeClientCtpPmRealRxCvsPcs19 OBJECT-TYPE
    SYNTAX      Integer32
    MAX-ACCESS  read-only
    STATUS      current
    DESCRIPTION "Coding Violations Section-Bip Error Lane 19."
    ::= { gigeClientCtpPmRealEntry  98 }

gigeClientCtpPmRealRxCvsPcs20 OBJECT-TYPE
    SYNTAX      Integer32
    MAX-ACCESS  read-only
    STATUS      current
    DESCRIPTION "Coding Violations Section-Bip Error Lane 20."
    ::= { gigeClientCtpPmRealEntry  99 }

gigeClientCtpPmRealRxErrPackets OBJECT-TYPE
    SYNTAX      Counter64
    MAX-ACCESS  read-only
    STATUS      current
    DESCRIPTION ""
    ::= { gigeClientCtpPmRealEntry  100 }

gigeClientCtpPmRealRxDiscarded OBJECT-TYPE
    SYNTAX      Counter64
    MAX-ACCESS  read-only
    STATUS      current
    DESCRIPTION ""
    ::= { gigeClientCtpPmRealEntry  101 }

gigeClientCtpPmRealRxCorrectedWords OBJECT-TYPE
    SYNTAX      Integer32
    MAX-ACCESS  read-only
    STATUS      current
    DESCRIPTION "Number of corrected words"
    ::= { gigeClientCtpPmRealEntry  102 }

gigeClientCtpPmRealRxUncorrectedWords OBJECT-TYPE
    SYNTAX      Integer32
    MAX-ACCESS  read-only
    STATUS      current
    DESCRIPTION "Number of uncorrected words"
    ::= { gigeClientCtpPmRealEntry  103 }

gigeClientCtpPmRealRxCorrectedBit OBJECT-TYPE
    SYNTAX      Integer32
    MAX-ACCESS  read-only
    STATUS      current
    DESCRIPTION "Number of corrected bits received"
    ::= { gigeClientCtpPmRealEntry  104 }

-- Conformance Statements
gigeClientCtpPmConformance    OBJECT IDENTIFIER ::= { gigeClientCtpPmMIB 3 }
gigeClientCtpPmCompliances    OBJECT IDENTIFIER ::= { gigeClientCtpPmConformance 1 }
gigeClientCtpPmGroups         OBJECT IDENTIFIER ::= { gigeClientCtpPmConformance 2 }

gigeClientCtpPmCompliance MODULE-COMPLIANCE
    STATUS current
    DESCRIPTION
    "Describes the requirements for conformance to the PM-GIGECLIENTCTP-MIB"
    MODULE
        MANDATORY-GROUPS { gigeClientCtpPmGroup }
    ::= { gigeClientCtpPmCompliances 1 }

gigeClientCtpPmRealCompliance MODULE-COMPLIANCE
    STATUS current
    DESCRIPTION
    "Describes the requirements for conformance to the gigeClientCtpPmReal-MIB"
    MODULE
        MANDATORY-GROUPS { gigeClientCtpPmRealGroup }
    ::= { gigeClientCtpPmCompliances 2 }

gigeClientCtpPmGroup OBJECT-GROUP
    OBJECTS {
        gigeClientCtpPmValidity,
        gigeClientCtpPmRxPcsICG,
        gigeClientCtpPmRxPcsES,
        gigeClientCtpPmRxPcsSES,
        gigeClientCtpPmRxPcsSESS,
        gigeClientCtpPmTxPcsICG,
        gigeClientCtpPmTxPcsES,
        gigeClientCtpPmTxPcsSES,
        gigeClientCtpPmTxPcsSESS,
        gigeClientCtpPmRxPackets,
        gigeClientCtpPmRxOctets,
        gigeClientCtpPmRxErrOctets,
        gigeClientCtpPmRxJabbers,
        gigeClientCtpPmRxFragments,
        gigeClientCtpPmRxCrcAlignedErr,
        gigeClientCtpPmRxUndersized,
        gigeClientCtpPmRxOversized,
        gigeClientCtpPmRxJabberSecs,
        gigeClientCtpPmRxMacSES,
        gigeClientCtpPmRxBroadcastPkts,
        gigeClientCtpPmRxMulticastPkts,
        gigeClientCtpPmRxInPauseFrames,
        gigeClientCtpPmTxPackets,
        gigeClientCtpPmTxOctets,
        gigeClientCtpPmTxErrOctets,
        gigeClientCtpPmTxJabbers,
        gigeClientCtpPmTxFragments,
        gigeClientCtpPmTxCrcAlignedErr,
        gigeClientCtpPmTxUndersized,
        gigeClientCtpPmTxOversized,
        gigeClientCtpPmTxJabberSecs,
        gigeClientCtpPmTxMacSES,
        gigeClientCtpPmTxBroadcastPkts,
        gigeClientCtpPmTxMulticastPkts,
        gigeClientCtpPmTxOutPauseFrames,
        gigeClientCtpPmRxSize64,
        gigeClientCtpPmRxSize65to127,
        gigeClientCtpPmRxSize128to255,
        gigeClientCtpPmRxSize256to511,
        gigeClientCtpPmRxSize512to1023,
        gigeClientCtpPmRxSize1024to1518,
        gigeClientCtpPmRxSize1519toJumbo,
        gigeClientCtpPmTxSize64,
        gigeClientCtpPmTxSize65to127,
        gigeClientCtpPmTxSize128to255,
        gigeClientCtpPmTxSize256to511,
        gigeClientCtpPmTxSize512to1023,
        gigeClientCtpPmTxSize1024to1518,
        gigeClientCtpPmTxSize1519toJumbo,
        gigeClientCtpPmCktId,
        gigeClientCtpPmTribTestSigErr,
        gigeClientCtpPmTribTestSigErr,
        gigeClientCtpPmPayloadType,
        gigeClientCtpPmRxSize1024to1522,
        gigeClientCtpPmRxSize1523toJumbo,
        gigeClientCtpPmTxSize1024to1522,
        gigeClientCtpPmTxSize1523toJumbo,
        gigeClientCtpPmTxCvsPcs01,
        gigeClientCtpPmTxCvsPcs02,
        gigeClientCtpPmTxCvsPcs03,
        gigeClientCtpPmTxCvsPcs04,
        gigeClientCtpPmTxCvsPcs05,
        gigeClientCtpPmTxCvsPcs06,
        gigeClientCtpPmTxCvsPcs07,
        gigeClientCtpPmTxCvsPcs08,
        gigeClientCtpPmTxCvsPcs09,
        gigeClientCtpPmTxCvsPcs10,
        gigeClientCtpPmTxCvsPcs11,
        gigeClientCtpPmTxCvsPcs12,
        gigeClientCtpPmTxCvsPcs13,
        gigeClientCtpPmTxCvsPcs14,
        gigeClientCtpPmTxCvsPcs15,
        gigeClientCtpPmTxCvsPcs16,
        gigeClientCtpPmTxCvsPcs17,
        gigeClientCtpPmTxCvsPcs18,
        gigeClientCtpPmTxCvsPcs19,
        gigeClientCtpPmTxCvsPcs20,
        gigeClientCtpPmRxCvsPcs01,
        gigeClientCtpPmRxCvsPcs02,
        gigeClientCtpPmRxCvsPcs03,
        gigeClientCtpPmRxCvsPcs04,
        gigeClientCtpPmRxCvsPcs05,
        gigeClientCtpPmRxCvsPcs06,
        gigeClientCtpPmRxCvsPcs07,
        gigeClientCtpPmRxCvsPcs08,
        gigeClientCtpPmRxCvsPcs09,
        gigeClientCtpPmRxCvsPcs10,
        gigeClientCtpPmRxCvsPcs11,
        gigeClientCtpPmRxCvsPcs12,
        gigeClientCtpPmRxCvsPcs13,
        gigeClientCtpPmRxCvsPcs14,
        gigeClientCtpPmRxCvsPcs15,
        gigeClientCtpPmRxCvsPcs16,
        gigeClientCtpPmRxCvsPcs17,
        gigeClientCtpPmRxCvsPcs18,
        gigeClientCtpPmRxCvsPcs19,
        gigeClientCtpPmRxCvsPcs20,
        gigeClientCtpPmRxErrPackets,
        gigeClientCtpPmRxDiscarded,
        gigeClientCtpPmRxCorrectedWords,
        gigeClientCtpPmRxUncorrectedWords,
        gigeClientCtpPmRxCorrectedBit
    }
    STATUS current
    DESCRIPTION
        " A collection of objects for reading the performance of the gigeClientCtp."
    ::= { gigeClientCtpPmGroups 1 }

gigeClientCtpPmRealGroup OBJECT-GROUP
    OBJECTS {
        gigeClientCtpPmRealRxLU,
        gigeClientCtpPmRealRxPcsICG,
        gigeClientCtpPmRealRxPcsES,
        gigeClientCtpPmRealRxPcsSES,
        gigeClientCtpPmRealRxPcsSESS,
        gigeClientCtpPmRealTxPcsICG,
        gigeClientCtpPmRealTxPcsES,
        gigeClientCtpPmRealTxPcsSES,
        gigeClientCtpPmRealTxPcsSESS,
        gigeClientCtpPmRealRxPackets,
        gigeClientCtpPmRealRxOctets,
        gigeClientCtpPmRealRxErrOctets,
        gigeClientCtpPmRealRxJabbers,
        gigeClientCtpPmRealRxFragments,
        gigeClientCtpPmRealRxCrcAlignedErr,
        gigeClientCtpPmRealRxUndersized,
        gigeClientCtpPmRealRxOversized,
        gigeClientCtpPmRealRxJabberSecs,
        gigeClientCtpPmRealRxMacSES,
        gigeClientCtpPmRealRxBroadcastPkts,
        gigeClientCtpPmRealRxMulticastPkts,
        gigeClientCtpPmRealRxInPauseFrames,
        gigeClientCtpPmRealTxLU,
        gigeClientCtpPmRealTxPackets,
        gigeClientCtpPmRealTxOctets,
        gigeClientCtpPmRealTxErrOctets,
        gigeClientCtpPmRealTxJabbers,
        gigeClientCtpPmRealTxFragments,
        gigeClientCtpPmRealTxCrcAlignedErr,
        gigeClientCtpPmRealTxUndersized,
        gigeClientCtpPmRealTxOversized,
        gigeClientCtpPmRealTxJabberSecs,
        gigeClientCtpPmRealTxMacSES,
        gigeClientCtpPmRealTxBroadcastPkts,
        gigeClientCtpPmRealTxMulticastPkts,
        gigeClientCtpPmRealTxOutPauseFrames,
        gigeClientCtpPmRealRxSize64,
        gigeClientCtpPmRealRxSize65to127,
        gigeClientCtpPmRealRxSize128to255,
        gigeClientCtpPmRealRxSize256to511,
        gigeClientCtpPmRealRxSize512to1023,
        gigeClientCtpPmRealRxSize1024to1518,
        gigeClientCtpPmRealRxSize1519toJumbo,
        gigeClientCtpPmRealTxSize64,
        gigeClientCtpPmRealTxSize65to127,
        gigeClientCtpPmRealTxSize128to255,
        gigeClientCtpPmRealTxSize256to511,
        gigeClientCtpPmRealTxSize512to1023,
        gigeClientCtpPmRealTxSize1024to1518,
        gigeClientCtpPmRealTxSize1519toJumbo,
        gigeClientCtpPmRealCktId,
        gigeClientCtpPmRealLineTestSigErr,
        gigeClientCtpPmRealLineTestSigErr,
        gigeClientCtpPmRealTribTestSigErr,
        gigeClientCtpPmRealTribTestSigErr,
        gigeClientCtpPmRealRxSize1024to1522,
        gigeClientCtpPmRealRxSize1523toJumbo,
        gigeClientCtpPmRealTxSize1024to1522,
        gigeClientCtpPmRealTxSize1523toJumbo,
        gigeClientCtpPmRealTxCvsPcs01,
        gigeClientCtpPmRealTxCvsPcs02,
        gigeClientCtpPmRealTxCvsPcs03,
        gigeClientCtpPmRealTxCvsPcs04,
        gigeClientCtpPmRealTxCvsPcs05,
        gigeClientCtpPmRealTxCvsPcs06,
        gigeClientCtpPmRealTxCvsPcs07,
        gigeClientCtpPmRealTxCvsPcs08,
        gigeClientCtpPmRealTxCvsPcs09,
        gigeClientCtpPmRealTxCvsPcs10,
        gigeClientCtpPmRealTxCvsPcs11,
        gigeClientCtpPmRealTxCvsPcs12,
        gigeClientCtpPmRealTxCvsPcs13,
        gigeClientCtpPmRealTxCvsPcs14,
        gigeClientCtpPmRealTxCvsPcs15,
        gigeClientCtpPmRealTxCvsPcs16,
        gigeClientCtpPmRealTxCvsPcs17,
        gigeClientCtpPmRealTxCvsPcs18,
        gigeClientCtpPmRealTxCvsPcs19,
        gigeClientCtpPmRealTxCvsPcs20,
        gigeClientCtpPmRealRxCvsPcs01,
        gigeClientCtpPmRealRxCvsPcs02,
        gigeClientCtpPmRealRxCvsPcs03,
        gigeClientCtpPmRealRxCvsPcs04,
        gigeClientCtpPmRealRxCvsPcs05,
        gigeClientCtpPmRealRxCvsPcs06,
        gigeClientCtpPmRealRxCvsPcs07,
        gigeClientCtpPmRealRxCvsPcs08,
        gigeClientCtpPmRealRxCvsPcs09,
        gigeClientCtpPmRealRxCvsPcs10,
        gigeClientCtpPmRealRxCvsPcs11,
        gigeClientCtpPmRealRxCvsPcs12,
        gigeClientCtpPmRealRxCvsPcs13,
        gigeClientCtpPmRealRxCvsPcs14,
        gigeClientCtpPmRealRxCvsPcs15,
        gigeClientCtpPmRealRxCvsPcs16,
        gigeClientCtpPmRealRxCvsPcs17,
        gigeClientCtpPmRealRxCvsPcs18,
        gigeClientCtpPmRealRxCvsPcs19,
        gigeClientCtpPmRealRxCvsPcs20,
        gigeClientCtpPmRealRxErrPackets,
        gigeClientCtpPmRealRxDiscarded,
        gigeClientCtpPmRealRxCorrectedWords,
        gigeClientCtpPmRealRxUncorrectedWords,
        gigeClientCtpPmRealRxCorrectedBit
    }
    STATUS current
    DESCRIPTION
        " A collection of objects for reading the real-time performance of the gigeClientCtp."
    ::= { gigeClientCtpPmGroups 2 }

END

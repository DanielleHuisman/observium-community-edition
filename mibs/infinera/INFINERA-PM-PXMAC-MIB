-- *****************************************************************
-- INFINERA-PM-PXMAC-MIB
-- 
-- February 2015, Kavitha Manjunatha / Narendra Gupta
-- 
-- 
-- Copyright (c) 2008-2012 by Infinera Inc.
-- All rights reserved.
-- ****************************************************************

INFINERA-PM-PXMAC-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    HCPerfIntervalCount                         FROM HC-PerfHist-TC-MIB
    perfMon                                     FROM INFINERA-REG-MIB;

pxmAcPmMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "200810200000Z" 
    DESCRIPTION
        "First Version"
    ::= { perfMon 95 }

pxmAcRmonPm     OBJECT IDENTIFIER ::= { pxmAcPmMIB 1 }

pxmAcPmTable OBJECT-TYPE
    SYNTAX      SEQUENCE OF PxmAcPmEntry
    MAX-ACCESS  not-accessible
    STATUS      current
    DESCRIPTION
        "A list of PxmAcPm entries. Each entry is uniquely identified by the value of ifIndex, sampleDuration and pxmAcPmTimestamp."
    ::= { pxmAcRmonPm 2 } 

pxmAcPmEntry  OBJECT-TYPE
    SYNTAX      PxmAcPmEntry
    MAX-ACCESS  not-accessible
    STATUS      current
    DESCRIPTION
        "A PxmAc entry containing historical performance information pertaining to Infinera
        PxmAc interfaces. This table is a subclass of IfCommon. Entries will exist in this
        table only for interfaces of type PxmAc.
        Each interface may have a number of entries in this table, each with a different combination
        of timestamp and sample duration."
    INDEX { ifIndex, pxmAcPmSampleDuration, pxmAcPmTimestamp }
    ::= { pxmAcPmTable 1 }

PxmAcPmEntry  ::= SEQUENCE {
    pxmAcPmTimestamp            Integer32,
    pxmAcPmSampleDuration       INTEGER,
    pxmAcPmValidity             TruthValue,
    pxmAcPmRxPackets		HCPerfIntervalCount,
    pxmAcPmRxOctets		HCPerfIntervalCount,
    pxmAcPmTxPackets            HCPerfIntervalCount,
    pxmAcPmTxOctets             HCPerfIntervalCount
}

pxmAcPmTimestamp OBJECT-TYPE
    SYNTAX      Integer32 (0..2147483647)
    MAX-ACCESS  not-accessible
    STATUS      current
    DESCRIPTION
        "End Time stamp for this interval. If this time is later than the current time,
        then the data for this bucket is currently being collected."
    ::= { pxmAcPmEntry  1 }

pxmAcPmSampleDuration OBJECT-TYPE
    SYNTAX      INTEGER {
                    fifteenMinutes(1),
                    day(2)
                }
    MAX-ACCESS  not-accessible
    STATUS      current
    DESCRIPTION
        "The duration of this sample."
    ::= { pxmAcPmEntry  2 }

pxmAcPmValidity OBJECT-TYPE
    SYNTAX      TruthValue
    MAX-ACCESS  read-only
    STATUS      current
    DESCRIPTION "Flag indicating if data was valid for the entire interval"
    ::= { pxmAcPmEntry  3 }

pxmAcPmRxPackets OBJECT-TYPE
    SYNTAX      HCPerfIntervalCount
    MAX-ACCESS  read-only
    STATUS      current
    DESCRIPTION ""
    ::= { pxmAcPmEntry  4 }

pxmAcPmRxOctets OBJECT-TYPE
    SYNTAX      HCPerfIntervalCount
    MAX-ACCESS  read-only
    STATUS      current
    DESCRIPTION ""
    ::= { pxmAcPmEntry  5 }

pxmAcPmTxPackets OBJECT-TYPE
    SYNTAX      HCPerfIntervalCount
    MAX-ACCESS  read-only
    STATUS      current
    DESCRIPTION ""
    ::= { pxmAcPmEntry  6 }

pxmAcPmTxOctets OBJECT-TYPE
    SYNTAX      HCPerfIntervalCount
    MAX-ACCESS  read-only
    STATUS      current
    DESCRIPTION ""
    ::= { pxmAcPmEntry  7 }

--
pxmAcPmRealTable OBJECT-TYPE
    SYNTAX      SEQUENCE OF PxmAcPmRealEntry
    MAX-ACCESS  not-accessible
    STATUS      current
    DESCRIPTION
        "A list of PxmAcPmReal entries. Each entry is uniquely identified by the value of ifIndex."
    ::= { pxmAcRmonPm 1 } 

pxmAcPmRealEntry  OBJECT-TYPE
    SYNTAX      PxmAcPmRealEntry
    MAX-ACCESS  not-accessible
    STATUS      current
    DESCRIPTION
        "A PxmAcPm entry containing real-time performance information pertaining to Infinera PxmAcPm interfaces.
        This table is a subclass of IfCommon. Entries will exist in this table only for interfaces of
        type PxmAcPm."
    INDEX { ifIndex }
    ::= { pxmAcPmRealTable 1 }

PxmAcPmRealEntry  ::= SEQUENCE {
    pxmAcPmRealRxPackets             Counter64,
    pxmAcPmRealRxOctets              Counter64,
    pxmAcPmRealTxPackets             Counter64,
    pxmAcPmRealTxOctets              Counter64
}

pxmAcPmRealRxPackets OBJECT-TYPE
    SYNTAX      Counter64
    MAX-ACCESS  read-only
    STATUS      current
    DESCRIPTION ""
    ::= { pxmAcPmRealEntry  1 }

pxmAcPmRealRxOctets OBJECT-TYPE
    SYNTAX      Counter64
    MAX-ACCESS  read-only
    STATUS      current
    DESCRIPTION ""
    ::= { pxmAcPmRealEntry  2 }

pxmAcPmRealTxPackets OBJECT-TYPE
    SYNTAX      Counter64
    MAX-ACCESS  read-only
    STATUS      current
    DESCRIPTION ""
    ::= { pxmAcPmRealEntry  3 }

pxmAcPmRealTxOctets OBJECT-TYPE
    SYNTAX      Counter64
    MAX-ACCESS  read-only
    STATUS      current
    DESCRIPTION ""
    ::= { pxmAcPmRealEntry  4 }

-- BWP
pxmAcBwpPm     OBJECT IDENTIFIER ::= { pxmAcPmMIB 2 }

pxmBwpAcPmTable OBJECT-TYPE
    SYNTAX      SEQUENCE OF PxmBwpAcPmEntry
    MAX-ACCESS  not-accessible
    STATUS      current
    DESCRIPTION
        "A list of PxmBwpAcPm entries. Each entry is uniquely identified by the value of ifIndex, sampleDuration and pxmAcPmTimestamp."
    ::= { pxmAcBwpPm 2 } 

pxmBwpAcPmEntry  OBJECT-TYPE
    SYNTAX      PxmBwpAcPmEntry
    MAX-ACCESS  not-accessible
    STATUS      current
    DESCRIPTION
        "A PxmBwpAc entry containing historical performance information pertaining to Infinera
        PxmAc interfaces. This table is a subclass of IfCommon. Entries will exist in this
        table only for interfaces of type PxmAc.
        Each interface may have a number of entries in this table, each with a different combination
        of timestamp and sample duration."
    INDEX { ifIndex, pxmBwpAcPmSampleDuration, pxmBwpAcPmTimestamp }
    ::= { pxmBwpAcPmTable 1 }

PxmBwpAcPmEntry  ::= SEQUENCE {
    pxmBwpAcPmTimestamp            Integer32,
    pxmBwpAcPmSampleDuration       INTEGER,
    pxmBwpAcPmValidity             TruthValue,
    pxmBwpAcPmPolicerConformedPkts         HCPerfIntervalCount,
    pxmBwpAcPmPolicerConformedOctets       HCPerfIntervalCount,
    pxmBwpAcPmPolicerExceededPkts          HCPerfIntervalCount,
    pxmBwpAcPmPolicerExceededOctets        HCPerfIntervalCount,
    pxmBwpAcPmPolicerViolatedPkts          HCPerfIntervalCount,
    pxmBwpAcPmPolicerViolatedOctets        HCPerfIntervalCount
}

pxmBwpAcPmTimestamp OBJECT-TYPE
    SYNTAX      Integer32 (0..2147483647)
    MAX-ACCESS  not-accessible
    STATUS      current
    DESCRIPTION
        "End Time stamp for this interval. If this time is later than the current time,
        then the data for this bucket is currently being collected."
    ::= { pxmBwpAcPmEntry  1 }

pxmBwpAcPmSampleDuration OBJECT-TYPE
    SYNTAX      INTEGER {
                    fifteenMinutes(1),
                    day(2)
                }
    MAX-ACCESS  not-accessible
    STATUS      current
    DESCRIPTION
        "The duration of this sample."
    ::= { pxmBwpAcPmEntry  2 }

pxmBwpAcPmValidity OBJECT-TYPE
    SYNTAX      TruthValue
    MAX-ACCESS  read-only
    STATUS      current
    DESCRIPTION "Flag indicating if data was valid for the entire interval"
    ::= { pxmBwpAcPmEntry  3 }

pxmBwpAcPmPolicerConformedPkts OBJECT-TYPE
    SYNTAX      HCPerfIntervalCount
    MAX-ACCESS  read-only
    STATUS      current
    DESCRIPTION ""
    ::= { pxmBwpAcPmEntry  4 }

pxmBwpAcPmPolicerConformedOctets OBJECT-TYPE
    SYNTAX      HCPerfIntervalCount
    MAX-ACCESS  read-only
    STATUS      current
    DESCRIPTION ""
    ::= { pxmBwpAcPmEntry  5 }

pxmBwpAcPmPolicerExceededPkts OBJECT-TYPE
    SYNTAX      HCPerfIntervalCount
    MAX-ACCESS  read-only
    STATUS      current
    DESCRIPTION ""
    ::= { pxmBwpAcPmEntry  6 }

pxmBwpAcPmPolicerExceededOctets OBJECT-TYPE
    SYNTAX      HCPerfIntervalCount
    MAX-ACCESS  read-only
    STATUS      current
    DESCRIPTION ""
    ::= { pxmBwpAcPmEntry  7 }

pxmBwpAcPmPolicerViolatedPkts OBJECT-TYPE
    SYNTAX      HCPerfIntervalCount
    MAX-ACCESS  read-only
    STATUS      current
    DESCRIPTION ""
    ::= { pxmBwpAcPmEntry  8 }

pxmBwpAcPmPolicerViolatedOctets OBJECT-TYPE
    SYNTAX      HCPerfIntervalCount
    MAX-ACCESS  read-only
    STATUS      current
    DESCRIPTION ""
    ::= { pxmBwpAcPmEntry  9 }

-- BWP Real
pxmBwpAcPmRealTable OBJECT-TYPE
    SYNTAX      SEQUENCE OF PxmBwpAcPmRealEntry
    MAX-ACCESS  not-accessible
    STATUS      current
    DESCRIPTION
        "A list of PxmBwpAcPmReal entries. Each entry is uniquely identified by the value of ifIndex."
    ::= { pxmAcBwpPm 1 } 

pxmBwpAcPmRealEntry  OBJECT-TYPE
    SYNTAX      PxmBwpAcPmRealEntry
    MAX-ACCESS  not-accessible
    STATUS      current
    DESCRIPTION
        "A PxmBwpAcPm entry containing real-time performance information pertaining to Infinera PxmAcPm interfaces.
        This table is a subclass of IfCommon. Entries will exist in this table only for interfaces of
        type PxmAcPm."
    INDEX { ifIndex }
    ::= { pxmBwpAcPmRealTable 1 }

PxmBwpAcPmRealEntry  ::= SEQUENCE {
    pxmBwpAcPmRealPolicerConformedPkts    Counter64,
    pxmBwpAcPmRealPolicerConformedOctets  Counter64,
    pxmBwpAcPmRealPolicerExceededPkts     Counter64,
    pxmBwpAcPmRealPolicerExceededOctets   Counter64,
    pxmBwpAcPmRealPolicerViolatedPkts     Counter64,
    pxmBwpAcPmRealPolicerViolatedOctets   Counter64
}

pxmBwpAcPmRealPolicerConformedPkts OBJECT-TYPE
    SYNTAX      Counter64
    MAX-ACCESS  read-only
    STATUS      current
    DESCRIPTION ""
    ::= { pxmBwpAcPmRealEntry  1 }

pxmBwpAcPmRealPolicerConformedOctets OBJECT-TYPE
    SYNTAX      Counter64
    MAX-ACCESS  read-only
    STATUS      current
    DESCRIPTION ""
    ::= { pxmBwpAcPmRealEntry  2 }

pxmBwpAcPmRealPolicerExceededPkts OBJECT-TYPE
    SYNTAX      Counter64
    MAX-ACCESS  read-only
    STATUS      current
    DESCRIPTION ""
    ::= { pxmBwpAcPmRealEntry  3 }

pxmBwpAcPmRealPolicerExceededOctets OBJECT-TYPE
    SYNTAX      Counter64
    MAX-ACCESS  read-only
    STATUS      current
    DESCRIPTION ""
    ::= { pxmBwpAcPmRealEntry  4 }

pxmBwpAcPmRealPolicerViolatedPkts OBJECT-TYPE
    SYNTAX      Counter64
    MAX-ACCESS  read-only
    STATUS      current
    DESCRIPTION ""
    ::= { pxmBwpAcPmRealEntry  5 }

pxmBwpAcPmRealPolicerViolatedOctets OBJECT-TYPE
    SYNTAX      Counter64
    MAX-ACCESS  read-only
    STATUS      current
    DESCRIPTION ""
    ::= { pxmBwpAcPmRealEntry  6 }

-- CM OID
pxmCmAcPmObjects         OBJECT IDENTIFIER ::= { pxmAcPmMIB 3 }

-- CM Real
pxmCmAcRealPm          OBJECT IDENTIFIER ::= { pxmCmAcPmObjects 1 }

-- CM - TC0, TC2, TC4, TC6, TC7
-- pxmTC0AcPm         OBJECT IDENTIFIER ::= { pxmCmAcPmTable 1 }

pxmTC0AcPmRealTable OBJECT-TYPE
    SYNTAX      SEQUENCE OF PxmTC0AcPmRealEntry
    MAX-ACCESS  not-accessible
    STATUS      current
    DESCRIPTION
        "A list of PxmBwpAcPmReal entries. Each entry is uniquely identified by the value of ifIndex."
    ::= { pxmCmAcRealPm 1 } 

pxmTC0AcPmRealEntry  OBJECT-TYPE
    SYNTAX      PxmTC0AcPmRealEntry
    MAX-ACCESS  not-accessible
    STATUS      current
    DESCRIPTION
        "A PxmTC0AcPm entry containing real-time performance information pertaining to Infinera PxmAcPm interfaces.
        This table is a subclass of IfCommon. Entries will exist in this table only for interfaces of
        type PxmAcPm."
    INDEX { ifIndex }
    ::= { pxmTC0AcPmRealTable 1 }

PxmTC0AcPmRealEntry  ::= SEQUENCE {
    pxmTC0AcPmRealTCNum                     Integer32,
    pxmTC0AcPmRealTDQueuingCurrentQDepth    Integer32,
    pxmTC0AcPmRealQueueingDiscardOctets     Counter64,
    pxmTC0AcPmRealQueueingDiscardPkts       Integer32,
    pxmTC0AcPmRealRandomGreenDropPkts       Counter64,
    pxmTC0AcPmRealRandomGreenDropOctets     Counter64,
    pxmTC0AcPmRealRandomYellowDropPkts      Counter64,
    pxmTC0AcPmRealRandomYellowDropOctets    Counter64,
    pxmTC0AcPmRealQueueingTransmitPkts      Counter64,
    pxmTC0AcPmRealQueueingTransmitOctets    Counter64,
    pxmTC0AcPmRealQueueingMeanQSizeUnit     Integer32,
    pxmTC0AcPmRealMeanQSize                 Integer32
}

pxmTC0AcPmRealTCNum OBJECT-TYPE
    SYNTAX      Integer32
    MAX-ACCESS  read-only
    STATUS      current
    DESCRIPTION "TCNum Real PM of traffic class - 0 (TC0) on PxmAC"
    ::= { pxmTC0AcPmRealEntry  1 }

pxmTC0AcPmRealTDQueuingCurrentQDepth OBJECT-TYPE
    SYNTAX      Integer32
    MAX-ACCESS  read-only
    STATUS      current
    DESCRIPTION "TDQueuingCurrentQDepth Real PM of traffic class - 0 (TC0) on PxmAC"
    ::= { pxmTC0AcPmRealEntry  2 }

pxmTC0AcPmRealQueueingDiscardOctets OBJECT-TYPE
    SYNTAX      Counter64
    MAX-ACCESS  read-only
    STATUS      current
    DESCRIPTION "QueueingDiscardOctets Real PM of traffic class - 0 (TC0) on PxmAC"
    ::= { pxmTC0AcPmRealEntry  3 }

pxmTC0AcPmRealQueueingDiscardPkts OBJECT-TYPE
    SYNTAX      Integer32
    MAX-ACCESS  read-only
    STATUS      current
    DESCRIPTION "QueueingDiscardPkts Real PM of traffic class - 0 (TC0) on PxmAC"
    ::= { pxmTC0AcPmRealEntry  4 }

pxmTC0AcPmRealRandomGreenDropPkts OBJECT-TYPE
    SYNTAX      Counter64
    MAX-ACCESS  read-only
    STATUS      current
    DESCRIPTION "RandomGreenDropPkts Real PM of traffic class - 0 (TC0) on PxmAC"
    ::= { pxmTC0AcPmRealEntry  5 }

pxmTC0AcPmRealRandomGreenDropOctets OBJECT-TYPE
    SYNTAX      Counter64
    MAX-ACCESS  read-only
    STATUS      current
    DESCRIPTION "RandomGreenDropOctets Real PM of traffic class - 0 (TC0) on PxmAC"
    ::= { pxmTC0AcPmRealEntry  6 }

pxmTC0AcPmRealRandomYellowDropPkts OBJECT-TYPE
    SYNTAX      Counter64
    MAX-ACCESS  read-only
    STATUS      current
    DESCRIPTION "RandomYellowDropPkts Real PM of traffic class - 0 (TC0) on PxmAC"
    ::= { pxmTC0AcPmRealEntry  7 }

pxmTC0AcPmRealRandomYellowDropOctets OBJECT-TYPE
    SYNTAX      Counter64
    MAX-ACCESS  read-only
    STATUS      current
    DESCRIPTION "RandomYellowDropOctets Real PM of traffic class - 0 (TC0) on PxmAC"
    ::= { pxmTC0AcPmRealEntry  8 }

pxmTC0AcPmRealQueueingTransmitPkts OBJECT-TYPE
    SYNTAX      Counter64
    MAX-ACCESS  read-only
    STATUS      current
    DESCRIPTION "QueueingTransmitPkts Real PM of traffic class - 0 (TC0) on PxmAC"
    ::= { pxmTC0AcPmRealEntry  9 }

pxmTC0AcPmRealQueueingTransmitOctets OBJECT-TYPE
    SYNTAX      Counter64
    MAX-ACCESS  read-only
    STATUS      current
    DESCRIPTION "QueueingTransmitOctets Real PM of traffic class - 0 (TC0) on PxmAC"
    ::= { pxmTC0AcPmRealEntry  10 }

pxmTC0AcPmRealQueueingMeanQSizeUnit OBJECT-TYPE
    SYNTAX      Integer32
    MAX-ACCESS  read-only
    STATUS      current
    DESCRIPTION "QueueingMeanQSizeUnit Real PM of traffic class - 0 (TC0) on PxmAC"
    ::= { pxmTC0AcPmRealEntry  11 }

pxmTC0AcPmRealMeanQSize OBJECT-TYPE
    SYNTAX      Integer32
    MAX-ACCESS  read-only
    STATUS      current
    DESCRIPTION "MeanQSize Real PM of traffic class - 0 (TC0) on PxmAC"
    ::= { pxmTC0AcPmRealEntry  12 }

-- CM Historical
pxmCmAcPm             OBJECT IDENTIFIER ::= { pxmCmAcPmObjects 2 }

pxmTC0AcPmTable OBJECT-TYPE
    SYNTAX      SEQUENCE OF PxmTC0AcPmEntry
    MAX-ACCESS  not-accessible
    STATUS      current
    DESCRIPTION
        "A list of PxmBwpAcPmReal entries. Each entry is uniquely identified by the value of ifIndex."
    ::= { pxmCmAcPm 1 } 

pxmTC0AcPmEntry  OBJECT-TYPE
    SYNTAX      PxmTC0AcPmEntry
    MAX-ACCESS  not-accessible
    STATUS      current
    DESCRIPTION
        "A PxmTC0AcPm entry containing historical performance information pertaining to Infinera
        Congestion management PMs on PxmAc interfaces. This table is a subclass of IfCommon.
        Entries will exist in this table only for interfaces of type PxmAc.
        Each interface may have a number of entries in this table, each with a different combination
        of timestamp and sample duration."
    INDEX { ifIndex, pxmTC0AcPmSampleDuration, pxmTC0AcPmTimestamp }
    ::= { pxmTC0AcPmTable 1 }

PxmTC0AcPmEntry  ::= SEQUENCE {
    pxmTC0AcPmTimestamp                 Integer32,
    pxmTC0AcPmSampleDuration            INTEGER,
    pxmTC0AcPmValidity                  TruthValue,
    pxmTC0AcPmTCNum                     Integer32,
    pxmTC0AcPmQueueingDiscardOctets     Counter64,
    pxmTC0AcPmQueueingDiscardPkts       Integer32,
    pxmTC0AcPmRandomGreenDropPkts       Counter64,
    pxmTC0AcPmRandomGreenDropOctets     Counter64,
    pxmTC0AcPmRandomYellowDropPkts      Counter64,
    pxmTC0AcPmRandomYellowDropOctets    Counter64,
    pxmTC0AcPmQueueingTransmitPkts      Counter64,
    pxmTC0AcPmQueueingTransmitOctets    Counter64
}

pxmTC0AcPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC0AcPmEntry  1 }

pxmTC0AcPmSampleDuration OBJECT-TYPE
    SYNTAX      INTEGER {
                    fifteenMinutes(1),
                    day(2)
                }
    MAX-ACCESS  not-accessible
    STATUS      current
    DESCRIPTION
        "The duration of this sample."
    ::= { pxmTC0AcPmEntry  2 }

pxmTC0AcPmValidity OBJECT-TYPE
    SYNTAX      TruthValue
    MAX-ACCESS  read-only
    STATUS      current
    DESCRIPTION "Flag indicating if data was valid for the entire interval"
    ::= { pxmTC0AcPmEntry  3 }

pxmTC0AcPmTCNum OBJECT-TYPE
    SYNTAX      Integer32
    MAX-ACCESS  read-only
    STATUS      current
    DESCRIPTION "TCNum Historical PM of traffic class - 0 (TC0) on PxmAC"
    ::= { pxmTC0AcPmEntry  4 }

pxmTC0AcPmQueueingDiscardOctets OBJECT-TYPE
    SYNTAX      Counter64
    MAX-ACCESS  read-only
    STATUS      current
    DESCRIPTION "QueueingDiscardOctets Historical PM of traffic class - 0 (TC0) on PxmAC"
    ::= { pxmTC0AcPmEntry  5 }

pxmTC0AcPmQueueingDiscardPkts OBJECT-TYPE
    SYNTAX      Integer32
    MAX-ACCESS  read-only
    STATUS      current
    DESCRIPTION "QueueingDiscardPkts Historical PM of traffic class - 0 (TC0) on PxmAC"
    ::= { pxmTC0AcPmEntry  6 }

pxmTC0AcPmRandomGreenDropPkts OBJECT-TYPE
    SYNTAX      Counter64
    MAX-ACCESS  read-only
    STATUS      current
    DESCRIPTION "RandomGreenDropPkts Historical PM of traffic class - 0 (TC0) on PxmAC"
    ::= { pxmTC0AcPmEntry  7 }

pxmTC0AcPmRandomGreenDropOctets OBJECT-TYPE
    SYNTAX      Counter64
    MAX-ACCESS  read-only
    STATUS      current
    DESCRIPTION "RandomGreenDropOctets Historical PM of traffic class - 0 (TC0) on PxmAC"
    ::= { pxmTC0AcPmEntry  8 }

pxmTC0AcPmRandomYellowDropPkts OBJECT-TYPE
    SYNTAX      Counter64
    MAX-ACCESS  read-only
    STATUS      current
    DESCRIPTION "RandomYellowDropPkts Historical PM of traffic class - 0 (TC0) on PxmAC"
    ::= { pxmTC0AcPmEntry  9 }

pxmTC0AcPmRandomYellowDropOctets OBJECT-TYPE
    SYNTAX      Counter64
    MAX-ACCESS  read-only
    STATUS      current
    DESCRIPTION "RandomYellowDropOctets Historical PM of traffic class - 0 (TC0) on PxmAC"
    ::= { pxmTC0AcPmEntry  10 }

pxmTC0AcPmQueueingTransmitPkts OBJECT-TYPE
    SYNTAX      Counter64
    MAX-ACCESS  read-only
    STATUS      current
    DESCRIPTION "QueueingTransmitPkts Historical PM of traffic class - 0 (TC0) on PxmAC"
    ::= { pxmTC0AcPmEntry  11 }

pxmTC0AcPmQueueingTransmitOctets OBJECT-TYPE
    SYNTAX      Counter64
    MAX-ACCESS  read-only
    STATUS      current
    DESCRIPTION "QueueingTransmitOctets Historical PM of traffic class - 0 (TC0) on PxmAC"
    ::= { pxmTC0AcPmEntry  12 }

-- TC2 Real

pxmTC2AcPmTable OBJECT-TYPE
    SYNTAX      SEQUENCE OF PxmTC2AcPmEntry
    MAX-ACCESS  not-accessible
    STATUS      current
    DESCRIPTION
        "A list of PxmBwpAcPmReal entries. Each entry is uniquely identified by the value of ifIndex."
    ::= { pxmCmAcPm 2 } 

pxmTC2AcPmEntry  OBJECT-TYPE
    SYNTAX      PxmTC2AcPmEntry
    MAX-ACCESS  not-accessible
    STATUS      current
    DESCRIPTION ""
    INDEX { ifIndex, pxmTC2AcPmSampleDuration, pxmTC2AcPmTimestamp }
    ::= { pxmTC2AcPmTable 1 }

PxmTC2AcPmEntry  ::= SEQUENCE {
    pxmTC2AcPmTimestamp                 Integer32,
    pxmTC2AcPmSampleDuration            INTEGER,
    pxmTC2AcPmValidity                  TruthValue,
    pxmTC2AcPmTCNum                     Integer32,
    pxmTC2AcPmQueueingDiscardOctets     Counter64,
    pxmTC2AcPmQueueingDiscardPkts       Integer32,
    pxmTC2AcPmRandomGreenDropPkts       Counter64,
    pxmTC2AcPmRandomGreenDropOctets     Counter64,
    pxmTC2AcPmRandomYellowDropPkts      Counter64,
    pxmTC2AcPmRandomYellowDropOctets    Counter64,
    pxmTC2AcPmQueueingTransmitPkts      Counter64,
    pxmTC2AcPmQueueingTransmitOctets    Counter64
}

pxmTC2AcPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC2AcPmEntry  1 }

pxmTC2AcPmSampleDuration OBJECT-TYPE
    SYNTAX      INTEGER {
                    fifteenMinutes(1),
                    day(2)
                }
    MAX-ACCESS  not-accessible
    STATUS      current
    DESCRIPTION
        "The duration of this sample."
    ::= { pxmTC2AcPmEntry  2 }

pxmTC2AcPmValidity OBJECT-TYPE
    SYNTAX      TruthValue
    MAX-ACCESS  read-only
    STATUS      current
    DESCRIPTION "Flag indicating if data was valid for the entire interval"
    ::= { pxmTC2AcPmEntry  3 }

pxmTC2AcPmTCNum OBJECT-TYPE
    SYNTAX      Integer32
    MAX-ACCESS  read-only
    STATUS      current
    DESCRIPTION "TCNum Historical PM of traffic class - 2 (TC2) on PxmAC"
    ::= { pxmTC2AcPmEntry  4 }

pxmTC2AcPmQueueingDiscardOctets OBJECT-TYPE
    SYNTAX      Counter64
    MAX-ACCESS  read-only
    STATUS      current
    DESCRIPTION "QueueingDiscardOctets Historical PM of traffic class - 2 (TC2) on PxmAC"
    ::= { pxmTC2AcPmEntry  5 }

pxmTC2AcPmQueueingDiscardPkts OBJECT-TYPE
    SYNTAX      Integer32
    MAX-ACCESS  read-only
    STATUS      current
    DESCRIPTION "QueueingDiscardPkts Historical PM of traffic class - 2 (TC2) on PxmAC"
    ::= { pxmTC2AcPmEntry  6 }

pxmTC2AcPmRandomGreenDropPkts OBJECT-TYPE
    SYNTAX      Counter64
    MAX-ACCESS  read-only
    STATUS      current
    DESCRIPTION "RandomGreenDropPkts Historical PM of traffic class - 2 (TC2) on PxmAC"
    ::= { pxmTC2AcPmEntry  7 }

pxmTC2AcPmRandomGreenDropOctets OBJECT-TYPE
    SYNTAX      Counter64
    MAX-ACCESS  read-only
    STATUS      current
    DESCRIPTION "RandomGreenDropOctets Historical PM of traffic class - 2 (TC2) on PxmAC"
    ::= { pxmTC2AcPmEntry  8 }

pxmTC2AcPmRandomYellowDropPkts OBJECT-TYPE
    SYNTAX      Counter64
    MAX-ACCESS  read-only
    STATUS      current
    DESCRIPTION "RandomYellowDropPkts Historical PM of traffic class - 2 (TC2) on PxmAC"
    ::= { pxmTC2AcPmEntry  9 }

pxmTC2AcPmRandomYellowDropOctets OBJECT-TYPE
    SYNTAX      Counter64
    MAX-ACCESS  read-only
    STATUS      current
    DESCRIPTION "RandomYellowDropOctets Historical PM of traffic class - 2 (TC2) on PxmAC"
    ::= { pxmTC2AcPmEntry  10 }

pxmTC2AcPmQueueingTransmitPkts OBJECT-TYPE
    SYNTAX      Counter64
    MAX-ACCESS  read-only
    STATUS      current
    DESCRIPTION "QueueingTransmitPkts Historical PM of traffic class - 2 (TC2) on PxmAC"
    ::= { pxmTC2AcPmEntry  11 }

pxmTC2AcPmQueueingTransmitOctets OBJECT-TYPE
    SYNTAX      Counter64
    MAX-ACCESS  read-only
    STATUS      current
    DESCRIPTION "QueueingTransmitOctets Historical PM of traffic class - 4 (TC4) on PxmAC"
    ::= { pxmTC2AcPmEntry  12 }

-- TC2 Real
pxmTC2AcPmRealTable OBJECT-TYPE
    SYNTAX      SEQUENCE OF PxmTC2AcPmRealEntry
    MAX-ACCESS  not-accessible
    STATUS      current
    DESCRIPTION
        "A list of PxmBwpAcPmReal entries. Each entry is uniquely identified by the value of ifIndex."
    ::= { pxmCmAcRealPm 2 } 

pxmTC2AcPmRealEntry  OBJECT-TYPE
    SYNTAX      PxmTC2AcPmRealEntry
    MAX-ACCESS  not-accessible
    STATUS      current
    DESCRIPTION
        "A PxmTC0AcPm entry containing real-time performance information pertaining to Infinera PxmAcPm interfaces.
        This table is a subclass of IfCommon. Entries will exist in this table only for interfaces of
        type PxmAcPm."
    INDEX { ifIndex }
    ::= { pxmTC2AcPmRealTable 1 }

PxmTC2AcPmRealEntry  ::= SEQUENCE {
    pxmTC2AcPmRealTCNum                     Integer32,
    pxmTC2AcPmRealTDQueuingCurrentQDepth    Integer32,
    pxmTC2AcPmRealQueueingDiscardOctets     Counter64,
    pxmTC2AcPmRealQueueingDiscardPkts       Integer32,
    pxmTC2AcPmRealRandomGreenDropPkts       Counter64,
    pxmTC2AcPmRealRandomGreenDropOctets     Counter64,
    pxmTC2AcPmRealRandomYellowDropPkts      Counter64,
    pxmTC2AcPmRealRandomYellowDropOctets    Counter64,
    pxmTC2AcPmRealQueueingTransmitPkts      Counter64,
    pxmTC2AcPmRealQueueingTransmitOctets    Counter64,
    pxmTC2AcPmRealQueueingMeanQSizeUnit     Integer32,
    pxmTC2AcPmRealMeanQSize                 Integer32
}

pxmTC2AcPmRealTCNum OBJECT-TYPE
    SYNTAX      Integer32
    MAX-ACCESS  read-only
    STATUS      current
    DESCRIPTION "TCNum Real PM of traffic class - 2 (TC2) on PxmAC"
    ::= { pxmTC2AcPmRealEntry  1 }

pxmTC2AcPmRealTDQueuingCurrentQDepth OBJECT-TYPE
    SYNTAX      Integer32
    MAX-ACCESS  read-only
    STATUS      current
    DESCRIPTION "TDQueuingCurrentQDepth Real PM of traffic class - 2 (TC2) on PxmAC"
    ::= { pxmTC2AcPmRealEntry  2 }

pxmTC2AcPmRealQueueingDiscardOctets OBJECT-TYPE
    SYNTAX      Counter64
    MAX-ACCESS  read-only
    STATUS      current
    DESCRIPTION "QueueingDiscardOctets Real PM of traffic class - 2 (TC2) on PxmAC"
    ::= { pxmTC2AcPmRealEntry  3 }

pxmTC2AcPmRealQueueingDiscardPkts OBJECT-TYPE
    SYNTAX      Integer32
    MAX-ACCESS  read-only
    STATUS      current
    DESCRIPTION "QueueingDiscardPkts Real PM of traffic class - 2 (TC2) on PxmAC"
    ::= { pxmTC2AcPmRealEntry  4 }

pxmTC2AcPmRealRandomGreenDropPkts OBJECT-TYPE
    SYNTAX      Counter64
    MAX-ACCESS  read-only
    STATUS      current
    DESCRIPTION "RandomGreenDropPkts Real PM of traffic class - 2 (TC2) on PxmAC"
    ::= { pxmTC2AcPmRealEntry  5 }

pxmTC2AcPmRealRandomGreenDropOctets OBJECT-TYPE
    SYNTAX      Counter64
    MAX-ACCESS  read-only
    STATUS      current
    DESCRIPTION "RandomGreenDropOctets Real PM of traffic class - 2 (TC2) on PxmAC"
    ::= { pxmTC2AcPmRealEntry  6 }

pxmTC2AcPmRealRandomYellowDropPkts OBJECT-TYPE
    SYNTAX      Counter64
    MAX-ACCESS  read-only
    STATUS      current
    DESCRIPTION "RandomYellowDropPkts Real PM of traffic class - 2 (TC2) on PxmAC"
    ::= { pxmTC2AcPmRealEntry  7 }

pxmTC2AcPmRealRandomYellowDropOctets OBJECT-TYPE
    SYNTAX      Counter64
    MAX-ACCESS  read-only
    STATUS      current
    DESCRIPTION "RandomYellowDropOctets Real PM of traffic class - 2 (TC2) on PxmAC"
    ::= { pxmTC2AcPmRealEntry  8 }

pxmTC2AcPmRealQueueingTransmitPkts OBJECT-TYPE
    SYNTAX      Counter64
    MAX-ACCESS  read-only
    STATUS      current
    DESCRIPTION "QueueingTransmitPkts Real PM of traffic class - 2 (TC2) on PxmAC"
    ::= { pxmTC2AcPmRealEntry  9 }

pxmTC2AcPmRealQueueingTransmitOctets OBJECT-TYPE
    SYNTAX      Counter64
    MAX-ACCESS  read-only
    STATUS      current
    DESCRIPTION "QueueingTransmitOctets Real PM of traffic class - 2 (TC2) on PxmAC"
    ::= { pxmTC2AcPmRealEntry  10 }

pxmTC2AcPmRealQueueingMeanQSizeUnit OBJECT-TYPE
    SYNTAX      Integer32
    MAX-ACCESS  read-only
    STATUS      current
    DESCRIPTION "QueueingMeanQSizeUnit Real PM of traffic class - 2 (TC2) on PxmAC"
    ::= { pxmTC2AcPmRealEntry  11 }

pxmTC2AcPmRealMeanQSize OBJECT-TYPE
    SYNTAX      Integer32
    MAX-ACCESS  read-only
    STATUS      current
    DESCRIPTION "MeanQSize Real PM of traffic class - 2 (TC2) on PxmAC"
    ::= { pxmTC2AcPmRealEntry  12 }

-- TC4 Historical
pxmTC4AcPmTable OBJECT-TYPE
    SYNTAX      SEQUENCE OF PxmTC4AcPmEntry
    MAX-ACCESS  not-accessible
    STATUS      current
    DESCRIPTION
        "A list of PxmBwpAcPmReal entries. Each entry is uniquely identified by the value of ifIndex."
    ::= { pxmCmAcPm 3 } 

pxmTC4AcPmEntry  OBJECT-TYPE
    SYNTAX      PxmTC4AcPmEntry
    MAX-ACCESS  not-accessible
    STATUS      current
    DESCRIPTION ""
    INDEX { ifIndex, pxmTC4AcPmSampleDuration, pxmTC4AcPmTimestamp }
    ::= { pxmTC4AcPmTable 1 }

PxmTC4AcPmEntry  ::= SEQUENCE {
    pxmTC4AcPmTimestamp                 Integer32,
    pxmTC4AcPmSampleDuration            INTEGER,
    pxmTC4AcPmValidity                  TruthValue,
    pxmTC4AcPmTCNum                     Integer32,
    pxmTC4AcPmQueueingDiscardOctets     Counter64,
    pxmTC4AcPmQueueingDiscardPkts       Integer32,
    pxmTC4AcPmRandomGreenDropPkts       Counter64,
    pxmTC4AcPmRandomGreenDropOctets     Counter64,
    pxmTC4AcPmRandomYellowDropPkts      Counter64,
    pxmTC4AcPmRandomYellowDropOctets    Counter64,
    pxmTC4AcPmQueueingTransmitPkts      Counter64,
    pxmTC4AcPmQueueingTransmitOctets    Counter64
}

pxmTC4AcPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC4AcPmEntry  1 }

pxmTC4AcPmSampleDuration OBJECT-TYPE
    SYNTAX      INTEGER {
                    fifteenMinutes(1),
                    day(2)
                }
    MAX-ACCESS  not-accessible
    STATUS      current
    DESCRIPTION
        "The duration of this sample."
    ::= { pxmTC4AcPmEntry  2 }

pxmTC4AcPmValidity OBJECT-TYPE
    SYNTAX      TruthValue
    MAX-ACCESS  read-only
    STATUS      current
    DESCRIPTION "Flag indicating if data was valid for the entire interval"
    ::= { pxmTC4AcPmEntry  3 }

pxmTC4AcPmTCNum OBJECT-TYPE
    SYNTAX      Integer32
    MAX-ACCESS  read-only
    STATUS      current
    DESCRIPTION "TCNum Historical PM of traffic class - 4 (TC4) on PxmAC"
    ::= { pxmTC4AcPmEntry  4 }

pxmTC4AcPmQueueingDiscardOctets OBJECT-TYPE
    SYNTAX      Counter64
    MAX-ACCESS  read-only
    STATUS      current
    DESCRIPTION "QueueingDiscardOctets Historical PM of traffic class - 4 (TC4) on PxmAC"
    ::= { pxmTC4AcPmEntry  5 }

pxmTC4AcPmQueueingDiscardPkts OBJECT-TYPE
    SYNTAX      Integer32
    MAX-ACCESS  read-only
    STATUS      current
    DESCRIPTION "QueueingDiscardPkts Historical PM of traffic class - 4 (TC4) on PxmAC"
    ::= { pxmTC4AcPmEntry  6 }

pxmTC4AcPmRandomGreenDropPkts OBJECT-TYPE
    SYNTAX      Counter64
    MAX-ACCESS  read-only
    STATUS      current
    DESCRIPTION "RandomGreenDropPkts Historical PM of traffic class - 4 (TC4) on PxmAC"
    ::= { pxmTC4AcPmEntry  7 }

pxmTC4AcPmRandomGreenDropOctets OBJECT-TYPE
    SYNTAX      Counter64
    MAX-ACCESS  read-only
    STATUS      current
    DESCRIPTION "RandomGreenDropOctets Historical PM of traffic class - 4 (TC4) on PxmAC"
    ::= { pxmTC4AcPmEntry  8 }

pxmTC4AcPmRandomYellowDropPkts OBJECT-TYPE
    SYNTAX      Counter64
    MAX-ACCESS  read-only
    STATUS      current
    DESCRIPTION "RandomYellowDropPkts Historical PM of traffic class - 4 (TC4) on PxmAC"
    ::= { pxmTC4AcPmEntry  9 }

pxmTC4AcPmRandomYellowDropOctets OBJECT-TYPE
    SYNTAX      Counter64
    MAX-ACCESS  read-only
    STATUS      current
    DESCRIPTION "RandomYellowDropOctets Historical PM of traffic class - 4 (TC4) on PxmAC"
    ::= { pxmTC4AcPmEntry  10 }

pxmTC4AcPmQueueingTransmitPkts OBJECT-TYPE
    SYNTAX      Counter64
    MAX-ACCESS  read-only
    STATUS      current
    DESCRIPTION "QueueingTransmitPkts Historical PM of traffic class - 4 (TC4) on PxmAC"
    ::= { pxmTC4AcPmEntry  11 }

pxmTC4AcPmQueueingTransmitOctets OBJECT-TYPE
    SYNTAX      Counter64
    MAX-ACCESS  read-only
    STATUS      current
    DESCRIPTION "QueueingTransmitOctets Historical PM of traffic class - 4 (TC4) on PxmAC"
    ::= { pxmTC4AcPmEntry  12 }

-- TC4 Real
pxmTC4AcPmRealTable OBJECT-TYPE
    SYNTAX      SEQUENCE OF PxmTC4AcPmRealEntry
    MAX-ACCESS  not-accessible
    STATUS      current
    DESCRIPTION
        "A list of PxmBwpAcPmReal entries. Each entry is uniquely identified by the value of ifIndex."
    ::= { pxmCmAcRealPm 3 } 

pxmTC4AcPmRealEntry  OBJECT-TYPE
    SYNTAX      PxmTC4AcPmRealEntry
    MAX-ACCESS  not-accessible
    STATUS      current
    DESCRIPTION
        "A PxmTC0AcPm entry containing real-time performance information pertaining to Infinera PxmAcPm interfaces.
        This table is a subclass of IfCommon. Entries will exist in this table only for interfaces of
        type PxmAcPm."
    INDEX { ifIndex }
    ::= { pxmTC4AcPmRealTable 1 }

PxmTC4AcPmRealEntry  ::= SEQUENCE {
    pxmTC4AcPmRealTCNum                     Integer32,
    pxmTC4AcPmRealTDQueuingCurrentQDepth    Integer32,
    pxmTC4AcPmRealQueueingDiscardOctets     Counter64,
    pxmTC4AcPmRealQueueingDiscardPkts       Integer32,
    pxmTC4AcPmRealRandomGreenDropPkts       Counter64,
    pxmTC4AcPmRealRandomGreenDropOctets     Counter64,
    pxmTC4AcPmRealRandomYellowDropPkts      Counter64,
    pxmTC4AcPmRealRandomYellowDropOctets    Counter64,
    pxmTC4AcPmRealQueueingTransmitPkts      Counter64,
    pxmTC4AcPmRealQueueingTransmitOctets    Counter64,
    pxmTC4AcPmRealQueueingMeanQSizeUnit     Integer32,
    pxmTC4AcPmRealMeanQSize                 Integer32
}

pxmTC4AcPmRealTCNum OBJECT-TYPE
    SYNTAX      Integer32
    MAX-ACCESS  read-only
    STATUS      current
    DESCRIPTION "TCNum Real PM of traffic class - 4 (TC4) on PxmAC"
    ::= { pxmTC4AcPmRealEntry  1 }

pxmTC4AcPmRealTDQueuingCurrentQDepth OBJECT-TYPE
    SYNTAX      Integer32
    MAX-ACCESS  read-only
    STATUS      current
    DESCRIPTION "TDQueuingCurrentQDepth Real PM of traffic class - 4 (TC4) on PxmAC"
    ::= { pxmTC4AcPmRealEntry  2 }

pxmTC4AcPmRealQueueingDiscardOctets OBJECT-TYPE
    SYNTAX      Counter64
    MAX-ACCESS  read-only
    STATUS      current
    DESCRIPTION "QueueingDiscardOctets Real PM of traffic class - 4 (TC4) on PxmAC"
    ::= { pxmTC4AcPmRealEntry  3 }

pxmTC4AcPmRealQueueingDiscardPkts OBJECT-TYPE
    SYNTAX      Integer32
    MAX-ACCESS  read-only
    STATUS      current
    DESCRIPTION "QueueingDiscardPkts Real PM of traffic class - 4 (TC4) on PxmAC"
    ::= { pxmTC4AcPmRealEntry  4 }

pxmTC4AcPmRealRandomGreenDropPkts OBJECT-TYPE
    SYNTAX      Counter64
    MAX-ACCESS  read-only
    STATUS      current
    DESCRIPTION "RandomGreenDropPkts Real PM of traffic class - 4 (TC4) on PxmAC"
    ::= { pxmTC4AcPmRealEntry  5 }

pxmTC4AcPmRealRandomGreenDropOctets OBJECT-TYPE
    SYNTAX      Counter64
    MAX-ACCESS  read-only
    STATUS      current
    DESCRIPTION "RandomGreenDropOctets Real PM of traffic class - 4 (TC4) on PxmAC"
    ::= { pxmTC4AcPmRealEntry  6 }

pxmTC4AcPmRealRandomYellowDropPkts OBJECT-TYPE
    SYNTAX      Counter64
    MAX-ACCESS  read-only
    STATUS      current
    DESCRIPTION "RandomYellowDropPkts Real PM of traffic class - 4 (TC4) on PxmAC"
    ::= { pxmTC4AcPmRealEntry  7 }

pxmTC4AcPmRealRandomYellowDropOctets OBJECT-TYPE
    SYNTAX      Counter64
    MAX-ACCESS  read-only
    STATUS      current
    DESCRIPTION "RandomYellowDropOctets Real PM of traffic class - 4 (TC4) on PxmAC"
    ::= { pxmTC4AcPmRealEntry  8 }

pxmTC4AcPmRealQueueingTransmitPkts OBJECT-TYPE
    SYNTAX      Counter64
    MAX-ACCESS  read-only
    STATUS      current
    DESCRIPTION "QueueingTransmitPkts Real PM of traffic class - 4 (TC4) on PxmAC"
    ::= { pxmTC4AcPmRealEntry  9 }

pxmTC4AcPmRealQueueingTransmitOctets OBJECT-TYPE
    SYNTAX      Counter64
    MAX-ACCESS  read-only
    STATUS      current
    DESCRIPTION "QueueingTransmitOctets Real PM of traffic class - 4 (TC4) on PxmAC"
    ::= { pxmTC4AcPmRealEntry  10 }

pxmTC4AcPmRealQueueingMeanQSizeUnit OBJECT-TYPE
    SYNTAX      Integer32
    MAX-ACCESS  read-only
    STATUS      current
    DESCRIPTION "QueueingMeanQSizeUnit Real PM of traffic class - 4 (TC4) on PxmAC"
    ::= { pxmTC4AcPmRealEntry  11 }

pxmTC4AcPmRealMeanQSize OBJECT-TYPE
    SYNTAX      Integer32
    MAX-ACCESS  read-only
    STATUS      current
    DESCRIPTION "MeanQSize Real PM of traffic class - 4 (TC4) on PxmAC"
    ::= { pxmTC4AcPmRealEntry  12 }

-- TC6 Historical
pxmTC6AcPmTable OBJECT-TYPE
    SYNTAX      SEQUENCE OF PxmTC6AcPmEntry
    MAX-ACCESS  not-accessible
    STATUS      current
    DESCRIPTION
        "A list of PxmBwpAcPmReal entries. Each entry is uniquely identified by the value of ifIndex."
    ::= { pxmCmAcPm 4 } 

pxmTC6AcPmEntry  OBJECT-TYPE
    SYNTAX      PxmTC6AcPmEntry
    MAX-ACCESS  not-accessible
    STATUS      current
    DESCRIPTION ""
    INDEX { ifIndex, pxmTC6AcPmSampleDuration, pxmTC6AcPmTimestamp }
    ::= { pxmTC6AcPmTable 1 }

PxmTC6AcPmEntry  ::= SEQUENCE {
    pxmTC6AcPmTimestamp                 Integer32,
    pxmTC6AcPmSampleDuration            INTEGER,
    pxmTC6AcPmValidity                  TruthValue,
    pxmTC6AcPmTCNum                     Integer32,
    pxmTC6AcPmQueueingDiscardOctets     Counter64,
    pxmTC6AcPmQueueingDiscardPkts       Integer32,
    pxmTC6AcPmRandomGreenDropPkts       Counter64,
    pxmTC6AcPmRandomGreenDropOctets     Counter64,
    pxmTC6AcPmRandomYellowDropPkts      Counter64,
    pxmTC6AcPmRandomYellowDropOctets    Counter64,
    pxmTC6AcPmQueueingTransmitPkts      Counter64,
    pxmTC6AcPmQueueingTransmitOctets    Counter64
}

pxmTC6AcPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC6AcPmEntry  1 }

pxmTC6AcPmSampleDuration OBJECT-TYPE
    SYNTAX      INTEGER {
                    fifteenMinutes(1),
                    day(2)
                }
    MAX-ACCESS  not-accessible
    STATUS      current
    DESCRIPTION
        "The duration of this sample."
    ::= { pxmTC6AcPmEntry  2 }

pxmTC6AcPmValidity OBJECT-TYPE
    SYNTAX      TruthValue
    MAX-ACCESS  read-only
    STATUS      current
    DESCRIPTION "Flag indicating if data was valid for the entire interval"
    ::= { pxmTC6AcPmEntry  3 }

pxmTC6AcPmTCNum OBJECT-TYPE
    SYNTAX      Integer32
    MAX-ACCESS  read-only
    STATUS      current
    DESCRIPTION "TCNum Historical PM of traffic class - 6 (TC6) on PxmAC"
    ::= { pxmTC6AcPmEntry  4 }

pxmTC6AcPmQueueingDiscardOctets OBJECT-TYPE
    SYNTAX      Counter64
    MAX-ACCESS  read-only
    STATUS      current
    DESCRIPTION "QueueingDiscardOctets Historical PM of traffic class - 6 (TC6) on PxmAC"
    ::= { pxmTC6AcPmEntry  5 }

pxmTC6AcPmQueueingDiscardPkts OBJECT-TYPE
    SYNTAX      Integer32
    MAX-ACCESS  read-only
    STATUS      current
    DESCRIPTION "QueueingDiscardPkts Historical PM of traffic class - 6 (TC6) on PxmAC"
    ::= { pxmTC6AcPmEntry  6 }

pxmTC6AcPmRandomGreenDropPkts OBJECT-TYPE
    SYNTAX      Counter64
    MAX-ACCESS  read-only
    STATUS      current
    DESCRIPTION "RandomGreenDropPkts Historical PM of traffic class - 6 (TC6) on PxmAC"
    ::= { pxmTC6AcPmEntry  7 }

pxmTC6AcPmRandomGreenDropOctets OBJECT-TYPE
    SYNTAX      Counter64
    MAX-ACCESS  read-only
    STATUS      current
    DESCRIPTION "RandomGreenDropOctets Historical PM of traffic class - 6 (TC6) on PxmAC"
    ::= { pxmTC6AcPmEntry  8 }

pxmTC6AcPmRandomYellowDropPkts OBJECT-TYPE
    SYNTAX      Counter64
    MAX-ACCESS  read-only
    STATUS      current
    DESCRIPTION "RandomYellowDropPkts Historical PM of traffic class - 6 (TC6) on PxmAC"
    ::= { pxmTC6AcPmEntry  9 }

pxmTC6AcPmRandomYellowDropOctets OBJECT-TYPE
    SYNTAX      Counter64
    MAX-ACCESS  read-only
    STATUS      current
    DESCRIPTION "RandomYellowDropOctets Historical PM of traffic class - 6 (TC6) on PxmAC"
    ::= { pxmTC6AcPmEntry  10 }

pxmTC6AcPmQueueingTransmitPkts OBJECT-TYPE
    SYNTAX      Counter64
    MAX-ACCESS  read-only
    STATUS      current
    DESCRIPTION "QueueingTransmitPkts Historical PM of traffic class - 6 (TC6) on PxmAC"
    ::= { pxmTC6AcPmEntry  11 }

pxmTC6AcPmQueueingTransmitOctets OBJECT-TYPE
    SYNTAX      Counter64
    MAX-ACCESS  read-only
    STATUS      current
    DESCRIPTION "QueueingTransmitOctets Historical PM of traffic class - 6 (TC6) on PxmAC"
    ::= { pxmTC6AcPmEntry  12 }

-- TC6 Real
pxmTC6AcPmRealTable OBJECT-TYPE
    SYNTAX      SEQUENCE OF PxmTC6AcPmRealEntry
    MAX-ACCESS  not-accessible
    STATUS      current
    DESCRIPTION
        "A list of PxmBwpAcPmReal entries. Each entry is uniquely identified by the value of ifIndex."
    ::= { pxmCmAcRealPm 4 } 

pxmTC6AcPmRealEntry  OBJECT-TYPE
    SYNTAX      PxmTC6AcPmRealEntry
    MAX-ACCESS  not-accessible
    STATUS      current
    DESCRIPTION
        "A PxmTC0AcPm entry containing real-time performance information pertaining to Infinera PxmAcPm interfaces.
        This table is a subclass of IfCommon. Entries will exist in this table only for interfaces of
        type PxmAcPm."
    INDEX { ifIndex }
    ::= { pxmTC6AcPmRealTable 1 }

PxmTC6AcPmRealEntry  ::= SEQUENCE {
    pxmTC6AcPmRealTCNum                     Integer32,
    pxmTC6AcPmRealTDQueuingCurrentQDepth    Integer32,
    pxmTC6AcPmRealQueueingDiscardOctets     Counter64,
    pxmTC6AcPmRealQueueingDiscardPkts       Integer32,
    pxmTC6AcPmRealRandomGreenDropPkts       Counter64,
    pxmTC6AcPmRealRandomGreenDropOctets     Counter64,
    pxmTC6AcPmRealRandomYellowDropPkts      Counter64,
    pxmTC6AcPmRealRandomYellowDropOctets    Counter64,
    pxmTC6AcPmRealQueueingTransmitPkts      Counter64,
    pxmTC6AcPmRealQueueingTransmitOctets    Counter64,
    pxmTC6AcPmRealQueueingMeanQSizeUnit     Integer32,
    pxmTC6AcPmRealMeanQSize                 Integer32
}

pxmTC6AcPmRealTCNum OBJECT-TYPE
    SYNTAX      Integer32
    MAX-ACCESS  read-only
    STATUS      current
    DESCRIPTION "TCNum Real PM of traffic class - 6 (TC6) on PxmAC"
    ::= { pxmTC6AcPmRealEntry  1 }

pxmTC6AcPmRealTDQueuingCurrentQDepth OBJECT-TYPE
    SYNTAX      Integer32
    MAX-ACCESS  read-only
    STATUS      current
    DESCRIPTION "TDQueuingCurrentQDepth Real PM of traffic class - 6 (TC6) on PxmAC"
    ::= { pxmTC6AcPmRealEntry  2 }

pxmTC6AcPmRealQueueingDiscardOctets OBJECT-TYPE
    SYNTAX      Counter64
    MAX-ACCESS  read-only
    STATUS      current
    DESCRIPTION "QueueingDiscardOctets Real PM of traffic class - 6 (TC6) on PxmAC"
    ::= { pxmTC6AcPmRealEntry  3 }

pxmTC6AcPmRealQueueingDiscardPkts OBJECT-TYPE
    SYNTAX      Integer32
    MAX-ACCESS  read-only
    STATUS      current
    DESCRIPTION "QueueingDiscardPkts Real PM of traffic class - 6 (TC6) on PxmAC"
    ::= { pxmTC6AcPmRealEntry  4 }

pxmTC6AcPmRealRandomGreenDropPkts OBJECT-TYPE
    SYNTAX      Counter64
    MAX-ACCESS  read-only
    STATUS      current
    DESCRIPTION "RandomGreenDropPkts Real PM of traffic class - 6 (TC6) on PxmAC"
    ::= { pxmTC6AcPmRealEntry  5 }

pxmTC6AcPmRealRandomGreenDropOctets OBJECT-TYPE
    SYNTAX      Counter64
    MAX-ACCESS  read-only
    STATUS      current
    DESCRIPTION "RandomGreenDropOctets Real PM of traffic class - 6 (TC6) on PxmAC"
    ::= { pxmTC6AcPmRealEntry  6 }

pxmTC6AcPmRealRandomYellowDropPkts OBJECT-TYPE
    SYNTAX      Counter64
    MAX-ACCESS  read-only
    STATUS      current
    DESCRIPTION "RandomYellowDropPkts Real PM of traffic class - 6 (TC6) on PxmAC"
    ::= { pxmTC6AcPmRealEntry  7 }

pxmTC6AcPmRealRandomYellowDropOctets OBJECT-TYPE
    SYNTAX      Counter64
    MAX-ACCESS  read-only
    STATUS      current
    DESCRIPTION "RandomYellowDropOctets Real PM of traffic class - 6 (TC6) on PxmAC"
    ::= { pxmTC6AcPmRealEntry  8 }

pxmTC6AcPmRealQueueingTransmitPkts OBJECT-TYPE
    SYNTAX      Counter64
    MAX-ACCESS  read-only
    STATUS      current
    DESCRIPTION "QueueingTransmitPkts Real PM of traffic class - 6 (TC6) on PxmAC"
    ::= { pxmTC6AcPmRealEntry  9 }

pxmTC6AcPmRealQueueingTransmitOctets OBJECT-TYPE
    SYNTAX      Counter64
    MAX-ACCESS  read-only
    STATUS      current
    DESCRIPTION "QueueingTransmitOctets Real PM of traffic class - 6 (TC6) on PxmAC"
    ::= { pxmTC6AcPmRealEntry  10 }

pxmTC6AcPmRealQueueingMeanQSizeUnit OBJECT-TYPE
    SYNTAX      Integer32
    MAX-ACCESS  read-only
    STATUS      current
    DESCRIPTION "QueueingMeanQSizeUnit Real PM of traffic class - 6 (TC6) on PxmAC"
    ::= { pxmTC6AcPmRealEntry  11 }

pxmTC6AcPmRealMeanQSize OBJECT-TYPE
    SYNTAX      Integer32
    MAX-ACCESS  read-only
    STATUS      current
    DESCRIPTION "MeanQSize Real PM of traffic class - 6 (TC6) on PxmAC"
    ::= { pxmTC6AcPmRealEntry  12 }

-- TC7 Historical
pxmTC7AcPmTable OBJECT-TYPE
    SYNTAX      SEQUENCE OF PxmTC7AcPmEntry
    MAX-ACCESS  not-accessible
    STATUS      current
    DESCRIPTION
        "A list of PxmBwpAcPmReal entries. Each entry is uniquely identified by the value of ifIndex."
    ::= { pxmCmAcPm 5 } 

pxmTC7AcPmEntry  OBJECT-TYPE
    SYNTAX      PxmTC7AcPmEntry
    MAX-ACCESS  not-accessible
    STATUS      current
    DESCRIPTION ""
    INDEX { ifIndex, pxmTC7AcPmSampleDuration, pxmTC7AcPmTimestamp }
    ::= { pxmTC7AcPmTable 1 }

PxmTC7AcPmEntry  ::= SEQUENCE {
    pxmTC7AcPmTimestamp                 Integer32,
    pxmTC7AcPmSampleDuration            INTEGER,
    pxmTC7AcPmValidity                  TruthValue,
    pxmTC7AcPmTCNum                     Integer32,
    pxmTC7AcPmQueueingDiscardOctets     Counter64,
    pxmTC7AcPmQueueingDiscardPkts       Integer32,
    pxmTC7AcPmRandomGreenDropPkts       Counter64,
    pxmTC7AcPmRandomGreenDropOctets     Counter64,
    pxmTC7AcPmRandomYellowDropPkts      Counter64,
    pxmTC7AcPmRandomYellowDropOctets    Counter64,
    pxmTC7AcPmQueueingTransmitPkts      Counter64,
    pxmTC7AcPmQueueingTransmitOctets    Counter64
}

pxmTC7AcPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC7AcPmEntry  1 }

pxmTC7AcPmSampleDuration OBJECT-TYPE
    SYNTAX      INTEGER {
                    fifteenMinutes(1),
                    day(2)
                }
    MAX-ACCESS  not-accessible
    STATUS      current
    DESCRIPTION
        "The duration of this sample."
    ::= { pxmTC7AcPmEntry  2 }

pxmTC7AcPmValidity OBJECT-TYPE
    SYNTAX      TruthValue
    MAX-ACCESS  read-only
    STATUS      current
    DESCRIPTION "Flag indicating if data was valid for the entire interval"
    ::= { pxmTC7AcPmEntry  3 }

pxmTC7AcPmTCNum OBJECT-TYPE
    SYNTAX      Integer32
    MAX-ACCESS  read-only
    STATUS      current
    DESCRIPTION "TCNum Historical PM of traffic class - 7 (TC7) on PxmAC"
    ::= { pxmTC7AcPmEntry  4 }

pxmTC7AcPmQueueingDiscardOctets OBJECT-TYPE
    SYNTAX      Counter64
    MAX-ACCESS  read-only
    STATUS      current
    DESCRIPTION "QueueingDiscardOctets Historical PM of traffic class - 7 (TC7) on PxmAC"
    ::= { pxmTC7AcPmEntry  5 }

pxmTC7AcPmQueueingDiscardPkts OBJECT-TYPE
    SYNTAX      Integer32
    MAX-ACCESS  read-only
    STATUS      current
    DESCRIPTION "QueueingDiscardPkts Historical PM of traffic class - 7 (TC7) on PxmAC"
    ::= { pxmTC7AcPmEntry  6 }

pxmTC7AcPmRandomGreenDropPkts OBJECT-TYPE
    SYNTAX      Counter64
    MAX-ACCESS  read-only
    STATUS      current
    DESCRIPTION "RandomGreenDropPkts Historical PM of traffic class - 7 (TC7) on PxmAC"
    ::= { pxmTC7AcPmEntry  7 }

pxmTC7AcPmRandomGreenDropOctets OBJECT-TYPE
    SYNTAX      Counter64
    MAX-ACCESS  read-only
    STATUS      current
    DESCRIPTION "RandomGreenDropOctets Historical PM of traffic class - 7 (TC7) on PxmAC"
    ::= { pxmTC7AcPmEntry  8 }

pxmTC7AcPmRandomYellowDropPkts OBJECT-TYPE
    SYNTAX      Counter64
    MAX-ACCESS  read-only
    STATUS      current
    DESCRIPTION "RandomYellowDropPkts Historical PM of traffic class - 7 (TC7) on PxmAC"
    ::= { pxmTC7AcPmEntry  9 }

pxmTC7AcPmRandomYellowDropOctets OBJECT-TYPE
    SYNTAX      Counter64
    MAX-ACCESS  read-only
    STATUS      current
    DESCRIPTION "RandomYellowDropOctets Historical PM of traffic class - 7 (TC7) on PxmAC"
    ::= { pxmTC7AcPmEntry  10 }

pxmTC7AcPmQueueingTransmitPkts OBJECT-TYPE
    SYNTAX      Counter64
    MAX-ACCESS  read-only
    STATUS      current
    DESCRIPTION "QueueingTransmitPkts Historical PM of traffic class - 7 (TC7) on PxmAC"
    ::= { pxmTC7AcPmEntry  11 }

pxmTC7AcPmQueueingTransmitOctets OBJECT-TYPE
    SYNTAX      Counter64
    MAX-ACCESS  read-only
    STATUS      current
    DESCRIPTION "QueueingTransmitOctets Historical PM of traffic class - 7 (TC7) on PxmAC"
    ::= { pxmTC7AcPmEntry  12 }

-- TC7 Real
pxmTC7AcPmRealTable OBJECT-TYPE
    SYNTAX      SEQUENCE OF PxmTC7AcPmRealEntry
    MAX-ACCESS  not-accessible
    STATUS      current
    DESCRIPTION
        "A list of PxmBwpAcPmReal entries. Each entry is uniquely identified by the value of ifIndex."
    ::= { pxmCmAcRealPm 5 } 

pxmTC7AcPmRealEntry  OBJECT-TYPE
    SYNTAX      PxmTC7AcPmRealEntry
    MAX-ACCESS  not-accessible
    STATUS      current
    DESCRIPTION
        "A PxmTC0AcPm entry containing real-time performance information pertaining to Infinera PxmAcPm interfaces.
        This table is a subclass of IfCommon. Entries will exist in this table only for interfaces of
        type PxmAcPm."
    INDEX { ifIndex }
    ::= { pxmTC7AcPmRealTable 1 }

PxmTC7AcPmRealEntry  ::= SEQUENCE {
    pxmTC7AcPmRealTCNum                     Integer32,
    pxmTC7AcPmRealTDQueuingCurrentQDepth    Integer32,
    pxmTC7AcPmRealQueueingDiscardOctets     Counter64,
    pxmTC7AcPmRealQueueingDiscardPkts       Integer32,
    pxmTC7AcPmRealRandomGreenDropPkts       Counter64,
    pxmTC7AcPmRealRandomGreenDropOctets     Counter64,
    pxmTC7AcPmRealRandomYellowDropPkts      Counter64,
    pxmTC7AcPmRealRandomYellowDropOctets    Counter64,
    pxmTC7AcPmRealQueueingTransmitPkts      Counter64,
    pxmTC7AcPmRealQueueingTransmitOctets    Counter64,
    pxmTC7AcPmRealQueueingMeanQSizeUnit     Integer32,
    pxmTC7AcPmRealMeanQSize                 Integer32
}

pxmTC7AcPmRealTCNum OBJECT-TYPE
    SYNTAX      Integer32
    MAX-ACCESS  read-only
    STATUS      current
    DESCRIPTION "TCNum Real PM of traffic class - 7 (TC7) on PxmAC"
    ::= { pxmTC7AcPmRealEntry  1 }

pxmTC7AcPmRealTDQueuingCurrentQDepth OBJECT-TYPE
    SYNTAX      Integer32
    MAX-ACCESS  read-only
    STATUS      current
    DESCRIPTION "TDQueuingCurrentQDepth Real PM of traffic class - 7 (TC7) on PxmAC"
    ::= { pxmTC7AcPmRealEntry  2 }

pxmTC7AcPmRealQueueingDiscardOctets OBJECT-TYPE
    SYNTAX      Counter64
    MAX-ACCESS  read-only
    STATUS      current
    DESCRIPTION "QueueingDiscardOctets Real PM of traffic class - 7 (TC7) on PxmAC"
    ::= { pxmTC7AcPmRealEntry  3 }

pxmTC7AcPmRealQueueingDiscardPkts OBJECT-TYPE
    SYNTAX      Integer32
    MAX-ACCESS  read-only
    STATUS      current
    DESCRIPTION "QueueingDiscardPkts Real PM of traffic class - 7 (TC7) on PxmAC"
    ::= { pxmTC7AcPmRealEntry  4 }

pxmTC7AcPmRealRandomGreenDropPkts OBJECT-TYPE
    SYNTAX      Counter64
    MAX-ACCESS  read-only
    STATUS      current
    DESCRIPTION "RandomGreenDropPkts Real PM of traffic class - 7 (TC7) on PxmAC"
    ::= { pxmTC7AcPmRealEntry  5 }

pxmTC7AcPmRealRandomGreenDropOctets OBJECT-TYPE
    SYNTAX      Counter64
    MAX-ACCESS  read-only
    STATUS      current
    DESCRIPTION "RandomGreenDropOctets Real PM of traffic class - 7 (TC7) on PxmAC"
    ::= { pxmTC7AcPmRealEntry  6 }

pxmTC7AcPmRealRandomYellowDropPkts OBJECT-TYPE
    SYNTAX      Counter64
    MAX-ACCESS  read-only
    STATUS      current
    DESCRIPTION "RandomYellowDropPkts Real PM of traffic class - 7 (TC7) on PxmAC"
    ::= { pxmTC7AcPmRealEntry  7 }

pxmTC7AcPmRealRandomYellowDropOctets OBJECT-TYPE
    SYNTAX      Counter64
    MAX-ACCESS  read-only
    STATUS      current
    DESCRIPTION "RandomYellowDropOctets Real PM of traffic class - 7 (TC7) on PxmAC"
    ::= { pxmTC7AcPmRealEntry  8 }

pxmTC7AcPmRealQueueingTransmitPkts OBJECT-TYPE
    SYNTAX      Counter64
    MAX-ACCESS  read-only
    STATUS      current
    DESCRIPTION "QueueingTransmitPkts Real PM of traffic class - 7 (TC7) on PxmAC"
    ::= { pxmTC7AcPmRealEntry  9 }

pxmTC7AcPmRealQueueingTransmitOctets OBJECT-TYPE
    SYNTAX      Counter64
    MAX-ACCESS  read-only
    STATUS      current
    DESCRIPTION "QueueingTransmitOctets Real PM of traffic class - 7 (TC7) on PxmAC"
    ::= { pxmTC7AcPmRealEntry  10 }

pxmTC7AcPmRealQueueingMeanQSizeUnit OBJECT-TYPE
    SYNTAX      Integer32
    MAX-ACCESS  read-only
    STATUS      current
    DESCRIPTION "QueueingMeanQSizeUnit Real PM of traffic class - 7 (TC7) on PxmAC"
    ::= { pxmTC7AcPmRealEntry  11 }

pxmTC7AcPmRealMeanQSize OBJECT-TYPE
    SYNTAX      Integer32
    MAX-ACCESS  read-only
    STATUS      current
    DESCRIPTION "MeanQSize Real PM of traffic class - 7 (TC7) on PxmAC"
    ::= { pxmTC7AcPmRealEntry  12 }

-- TCANY Historical
pxmTCANYAcPmTable OBJECT-TYPE
    SYNTAX      SEQUENCE OF PxmTCANYAcPmEntry
    MAX-ACCESS  not-accessible
    STATUS      current
    DESCRIPTION
        "A list of PxmBwpAcPmReal entries. Each entry is uniquely identified by the value of ifIndex."
    ::= { pxmCmAcPm 6 } 

pxmTCANYAcPmEntry  OBJECT-TYPE
    SYNTAX      PxmTCANYAcPmEntry
    MAX-ACCESS  not-accessible
    STATUS      current
    DESCRIPTION ""
    INDEX { ifIndex, pxmTCANYAcPmSampleDuration, pxmTCANYAcPmTimestamp }
    ::= { pxmTCANYAcPmTable 1 }

PxmTCANYAcPmEntry  ::= SEQUENCE {
    pxmTCANYAcPmTimestamp                 Integer32,
    pxmTCANYAcPmSampleDuration            INTEGER,
    pxmTCANYAcPmValidity                  TruthValue,
    pxmTCANYAcPmTCNum                     Integer32,
    pxmTCANYAcPmQueueingDiscardOctets     Counter64,
    pxmTCANYAcPmQueueingDiscardPkts       Integer32,
    pxmTCANYAcPmRandomGreenDropPkts       Counter64,
    pxmTCANYAcPmRandomGreenDropOctets     Counter64,
    pxmTCANYAcPmRandomYellowDropPkts      Counter64,
    pxmTCANYAcPmRandomYellowDropOctets    Counter64,
    pxmTCANYAcPmQueueingTransmitPkts      Counter64,
    pxmTCANYAcPmQueueingTransmitOctets    Counter64
}

pxmTCANYAcPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTCANYAcPmEntry  1 }

pxmTCANYAcPmSampleDuration OBJECT-TYPE
    SYNTAX      INTEGER {
                    fifteenMinutes(1),
                    day(2)
                }
    MAX-ACCESS  not-accessible
    STATUS      current
    DESCRIPTION
        "The duration of this sample."
    ::= { pxmTCANYAcPmEntry  2 }

pxmTCANYAcPmValidity OBJECT-TYPE
    SYNTAX      TruthValue
    MAX-ACCESS  read-only
    STATUS      current
    DESCRIPTION "Flag indicating if data was valid for the entire interval"
    ::= { pxmTCANYAcPmEntry  3 }

pxmTCANYAcPmTCNum OBJECT-TYPE
    SYNTAX      Integer32
    MAX-ACCESS  read-only
    STATUS      current
    DESCRIPTION "TCNum Historical PM of traffic class - ANY (TCANY) on PxmAC"
    ::= { pxmTCANYAcPmEntry  4 }

pxmTCANYAcPmQueueingDiscardOctets OBJECT-TYPE
    SYNTAX      Counter64
    MAX-ACCESS  read-only
    STATUS      current
    DESCRIPTION "QueueingDiscardOctets Historical PM of traffic class - ANY (TCANY) on PxmAC"
    ::= { pxmTCANYAcPmEntry  5 }

pxmTCANYAcPmQueueingDiscardPkts OBJECT-TYPE
    SYNTAX      Integer32
    MAX-ACCESS  read-only
    STATUS      current
    DESCRIPTION "QueueingDiscardPkts Historical PM of traffic class - ANY (TCANY) on PxmAC"
    ::= { pxmTCANYAcPmEntry  6 }

pxmTCANYAcPmRandomGreenDropPkts OBJECT-TYPE
    SYNTAX      Counter64
    MAX-ACCESS  read-only
    STATUS      current
    DESCRIPTION "RandomGreenDropPkts Historical PM of traffic class - ANY (TCANY) on PxmAC"
    ::= { pxmTCANYAcPmEntry  7 }

pxmTCANYAcPmRandomGreenDropOctets OBJECT-TYPE
    SYNTAX      Counter64
    MAX-ACCESS  read-only
    STATUS      current
    DESCRIPTION "RandomGreenDropOctets Historical PM of traffic class - ANY (TCANY) on PxmAC"
    ::= { pxmTCANYAcPmEntry  8 }

pxmTCANYAcPmRandomYellowDropPkts OBJECT-TYPE
    SYNTAX      Counter64
    MAX-ACCESS  read-only
    STATUS      current
    DESCRIPTION "RandomYellowDropPkts Historical PM of traffic class - ANY (TCANY) on PxmAC"
    ::= { pxmTCANYAcPmEntry  9 }

pxmTCANYAcPmRandomYellowDropOctets OBJECT-TYPE
    SYNTAX      Counter64
    MAX-ACCESS  read-only
    STATUS      current
    DESCRIPTION "RandomYellowDropOctets Historical PM of traffic class - ANY (TCANY) on PxmAC"
    ::= { pxmTCANYAcPmEntry  10 }

pxmTCANYAcPmQueueingTransmitPkts OBJECT-TYPE
    SYNTAX      Counter64
    MAX-ACCESS  read-only
    STATUS      current
    DESCRIPTION "QueueingTransmitPkts Historical PM of traffic class - ANY (TCANY) on PxmAC"
    ::= { pxmTCANYAcPmEntry  11 }

pxmTCANYAcPmQueueingTransmitOctets OBJECT-TYPE
    SYNTAX      Counter64
    MAX-ACCESS  read-only
    STATUS      current
    DESCRIPTION "QueueingTransmitOctets Historical PM of traffic class - ANY (TCANY) on PxmAC"
    ::= { pxmTCANYAcPmEntry  12 }

-- TCANY Real
pxmTCANYAcPmRealTable OBJECT-TYPE
    SYNTAX      SEQUENCE OF PxmTCANYAcPmRealEntry
    MAX-ACCESS  not-accessible
    STATUS      current
    DESCRIPTION
        "A list of PxmBwpAcPmReal entries. Each entry is uniquely identified by the value of ifIndex."
    ::= { pxmCmAcRealPm 6 } 

pxmTCANYAcPmRealEntry  OBJECT-TYPE
    SYNTAX      PxmTCANYAcPmRealEntry
    MAX-ACCESS  not-accessible
    STATUS      current
    DESCRIPTION
        "A PxmTC0AcPm entry containing real-time performance information pertaining to Infinera PxmAcPm interfaces.
        This table is a subclass of IfCommon. Entries will exist in this table only for interfaces of
        type PxmAcPm."
    INDEX { ifIndex }
    ::= { pxmTCANYAcPmRealTable 1 }

PxmTCANYAcPmRealEntry  ::= SEQUENCE {
    pxmTCANYAcPmRealTCNum                     Integer32,
    pxmTCANYAcPmRealTDQueuingCurrentQDepth    Integer32,
    pxmTCANYAcPmRealQueueingDiscardOctets     Counter64,
    pxmTCANYAcPmRealQueueingDiscardPkts       Integer32,
    pxmTCANYAcPmRealRandomGreenDropPkts       Counter64,
    pxmTCANYAcPmRealRandomGreenDropOctets     Counter64,
    pxmTCANYAcPmRealRandomYellowDropPkts      Counter64,
    pxmTCANYAcPmRealRandomYellowDropOctets    Counter64,
    pxmTCANYAcPmRealQueueingTransmitPkts      Counter64,
    pxmTCANYAcPmRealQueueingTransmitOctets    Counter64,
    pxmTCANYAcPmRealQueueingMeanQSizeUnit     Integer32,
    pxmTCANYAcPmRealMeanQSize                 Integer32
}

pxmTCANYAcPmRealTCNum OBJECT-TYPE
    SYNTAX      Integer32
    MAX-ACCESS  read-only
    STATUS      current
    DESCRIPTION "TCNum Real PM of traffic class - ANY (TCANY) on PxmAC"
    ::= { pxmTCANYAcPmRealEntry  1 }

pxmTCANYAcPmRealTDQueuingCurrentQDepth OBJECT-TYPE
    SYNTAX      Integer32
    MAX-ACCESS  read-only
    STATUS      current
    DESCRIPTION "TDQueuingCurrentQDepth Real PM of traffic class - ANY (TCANY) on PxmAC"
    ::= { pxmTCANYAcPmRealEntry  2 }

pxmTCANYAcPmRealQueueingDiscardOctets OBJECT-TYPE
    SYNTAX      Counter64
    MAX-ACCESS  read-only
    STATUS      current
    DESCRIPTION "QueueingDiscardOctets Real PM of traffic class - ANY (TCANY) on PxmAC"
    ::= { pxmTCANYAcPmRealEntry  3 }

pxmTCANYAcPmRealQueueingDiscardPkts OBJECT-TYPE
    SYNTAX      Integer32
    MAX-ACCESS  read-only
    STATUS      current
    DESCRIPTION "QueueingDiscardPkts Real PM of traffic class - ANY (TCANY) on PxmAC"
    ::= { pxmTCANYAcPmRealEntry  4 }

pxmTCANYAcPmRealRandomGreenDropPkts OBJECT-TYPE
    SYNTAX      Counter64
    MAX-ACCESS  read-only
    STATUS      current
    DESCRIPTION "RandomGreenDropPkts Real PM of traffic class - ANY (TCANY) on PxmAC"
    ::= { pxmTCANYAcPmRealEntry  5 }

pxmTCANYAcPmRealRandomGreenDropOctets OBJECT-TYPE
    SYNTAX      Counter64
    MAX-ACCESS  read-only
    STATUS      current
    DESCRIPTION "RandomGreenDropOctets Real PM of traffic class - ANY (TCANY) on PxmAC"
    ::= { pxmTCANYAcPmRealEntry  6 }

pxmTCANYAcPmRealRandomYellowDropPkts OBJECT-TYPE
    SYNTAX      Counter64
    MAX-ACCESS  read-only
    STATUS      current
    DESCRIPTION "RandomYellowDropPkts Real PM of traffic class - ANY (TCANY) on PxmAC"
    ::= { pxmTCANYAcPmRealEntry  7 }

pxmTCANYAcPmRealRandomYellowDropOctets OBJECT-TYPE
    SYNTAX      Counter64
    MAX-ACCESS  read-only
    STATUS      current
    DESCRIPTION "RandomYellowDropOctets Real PM of traffic class - ANY (TCANY) on PxmAC"
    ::= { pxmTCANYAcPmRealEntry  8 }

pxmTCANYAcPmRealQueueingTransmitPkts OBJECT-TYPE
    SYNTAX      Counter64
    MAX-ACCESS  read-only
    STATUS      current
    DESCRIPTION "QueueingTransmitPkts Real PM of traffic class - ANY (TCANY) on PxmAC"
    ::= { pxmTCANYAcPmRealEntry  9 }

pxmTCANYAcPmRealQueueingTransmitOctets OBJECT-TYPE
    SYNTAX      Counter64
    MAX-ACCESS  read-only
    STATUS      current
    DESCRIPTION "QueueingTransmitOctets Real PM of traffic class - ANY (TCANY) on PxmAC"
    ::= { pxmTCANYAcPmRealEntry  10 }

pxmTCANYAcPmRealQueueingMeanQSizeUnit OBJECT-TYPE
    SYNTAX      Integer32
    MAX-ACCESS  read-only
    STATUS      current
    DESCRIPTION "QueueingMeanQSizeUnit Real PM of traffic class - ANY (TCANY) on PxmAC"
    ::= { pxmTCANYAcPmRealEntry  11 }

pxmTCANYAcPmRealMeanQSize OBJECT-TYPE
    SYNTAX      Integer32
    MAX-ACCESS  read-only
    STATUS      current
    DESCRIPTION "MeanQSize Real PM of traffic class - ANY (TCANY) on PxmAC"
    ::= { pxmTCANYAcPmRealEntry  12 }
-- End of CM PMs

-- Conformance Statements
pxmAcPmConformance    OBJECT IDENTIFIER ::= { pxmAcPmMIB 4 }
pxmAcPmCompliances    OBJECT IDENTIFIER ::= { pxmAcPmConformance 1 }
pxmAcPmGroups         OBJECT IDENTIFIER ::= { pxmAcPmConformance 2 }

pxmAcPmCompliance MODULE-COMPLIANCE
    STATUS current
    DESCRIPTION
    "Describes the requirements for conformance to the PM-PXMAC-MIB"
    MODULE
        MANDATORY-GROUPS { pxmAcPmGroup }
    ::= { pxmAcPmCompliances 1 }

pxmAcPmRealCompliance MODULE-COMPLIANCE
    STATUS current
    DESCRIPTION
    "Describes the requirements for conformance to the pxmAcPmReal-MIB"
    MODULE
        MANDATORY-GROUPS { pxmAcPmRealGroup }
    ::= { pxmAcPmCompliances 2 }

pxmAcPmGroup OBJECT-GROUP
    OBJECTS {
        pxmAcPmValidity,
        pxmAcPmRxPackets,
        pxmAcPmRxOctets,
        pxmAcPmTxPackets,
        pxmAcPmTxOctets
    }
    STATUS current
    DESCRIPTION
        " A collection of objects for reading the performance of the pxmAc."
    ::= { pxmAcPmGroups 1 }

pxmAcPmRealGroup OBJECT-GROUP
    OBJECTS {
        pxmAcPmRealRxPackets,
        pxmAcPmRealRxOctets,
        pxmAcPmRealTxPackets,
        pxmAcPmRealTxOctets
    }
    STATUS current
    DESCRIPTION
        " A collection of objects for reading the real-time performance of the pxmAc."
    ::= { pxmAcPmGroups 2 }

pxmBwpAcPmGroup OBJECT-GROUP
    OBJECTS {
        pxmBwpAcPmValidity,
        pxmBwpAcPmPolicerConformedPkts,
        pxmBwpAcPmPolicerConformedOctets,
        pxmBwpAcPmPolicerExceededPkts,
        pxmBwpAcPmPolicerExceededOctets,
        pxmBwpAcPmPolicerViolatedPkts,
        pxmBwpAcPmPolicerViolatedOctets
    }
    STATUS current
    DESCRIPTION
        " A collection of objects for reading the performance of the pxmAc."
    ::= { pxmAcPmGroups 3 }

pxmBwpAcPmRealGroup OBJECT-GROUP
    OBJECTS {
        pxmBwpAcPmRealPolicerConformedPkts,
        pxmBwpAcPmRealPolicerConformedOctets,
        pxmBwpAcPmRealPolicerExceededPkts,
        pxmBwpAcPmRealPolicerExceededOctets,
        pxmBwpAcPmRealPolicerViolatedPkts,
        pxmBwpAcPmRealPolicerViolatedOctets
    }
    STATUS current
    DESCRIPTION
        " A collection of objects for reading the real-time performance of the pxmAc."
    ::= { pxmAcPmGroups 4 }

pxmTC0AcPmGroup OBJECT-GROUP
    OBJECTS {
        pxmTC0AcPmValidity,
        pxmTC0AcPmTCNum,
        pxmTC0AcPmQueueingDiscardOctets,
        pxmTC0AcPmQueueingDiscardPkts,
        pxmTC0AcPmRandomGreenDropPkts,
        pxmTC0AcPmRandomGreenDropOctets,
        pxmTC0AcPmRandomYellowDropPkts,
        pxmTC0AcPmRandomYellowDropOctets,
        pxmTC0AcPmQueueingTransmitPkts,
        pxmTC0AcPmQueueingTransmitOctets
    }
    STATUS current
    DESCRIPTION
        " A collection of objects for reading the real-time performance of the pxmAc."
    ::= { pxmAcPmGroups 5 }

pxmTC0AcPmRealGroup OBJECT-GROUP
    OBJECTS {
        pxmTC0AcPmRealTCNum,
        pxmTC0AcPmRealTDQueuingCurrentQDepth,
        pxmTC0AcPmRealQueueingDiscardOctets,
        pxmTC0AcPmRealQueueingDiscardPkts,
        pxmTC0AcPmRealRandomGreenDropPkts,
        pxmTC0AcPmRealRandomGreenDropOctets,
        pxmTC0AcPmRealRandomYellowDropPkts,
        pxmTC0AcPmRealRandomYellowDropOctets,
        pxmTC0AcPmRealQueueingTransmitPkts,
        pxmTC0AcPmRealQueueingTransmitOctets,
    --    pxmTC0AcPmRealQueueingMeanQSizeUnit,
        pxmTC0AcPmRealMeanQSize
    }
    STATUS current
    DESCRIPTION
        " A collection of objects for reading the real-time performance of the pxmAc."
    ::= { pxmAcPmGroups 6 }

pxmTC2AcPmGroup OBJECT-GROUP
    OBJECTS {
        pxmTC2AcPmValidity,
        pxmTC2AcPmTCNum,
        pxmTC2AcPmQueueingDiscardOctets,
        pxmTC2AcPmQueueingDiscardPkts,
        pxmTC2AcPmRandomGreenDropPkts,
        pxmTC2AcPmRandomGreenDropOctets,
        pxmTC2AcPmRandomYellowDropPkts,
        pxmTC2AcPmRandomYellowDropOctets,
        pxmTC2AcPmQueueingTransmitPkts,
        pxmTC2AcPmQueueingTransmitOctets
    }
    STATUS current
    DESCRIPTION
        " A collection of objects for reading the real-time performance of the pxmAc."
    ::= { pxmAcPmGroups 7 }

pxmTC2AcPmRealGroup OBJECT-GROUP
    OBJECTS {
        pxmTC2AcPmRealTCNum,
        pxmTC2AcPmRealTDQueuingCurrentQDepth,
        pxmTC2AcPmRealQueueingDiscardOctets,
        pxmTC2AcPmRealQueueingDiscardPkts,
        pxmTC2AcPmRealRandomGreenDropPkts,
        pxmTC2AcPmRealRandomGreenDropOctets,
        pxmTC2AcPmRealRandomYellowDropPkts,
        pxmTC2AcPmRealRandomYellowDropOctets,
        pxmTC2AcPmRealQueueingTransmitPkts,
        pxmTC2AcPmRealQueueingTransmitOctets,
    --    pxmTC2AcPmRealQueueingMeanQSizeUnit,
        pxmTC2AcPmRealMeanQSize
    }
    STATUS current
    DESCRIPTION
        " A collection of objects for reading the real-time performance of the pxmAc."
    ::= { pxmAcPmGroups 8 }

pxmTC4AcPmGroup OBJECT-GROUP
    OBJECTS {
        pxmTC4AcPmValidity,
        pxmTC4AcPmTCNum,
        pxmTC4AcPmQueueingDiscardOctets,
        pxmTC4AcPmQueueingDiscardPkts,
        pxmTC4AcPmRandomGreenDropPkts,
        pxmTC4AcPmRandomGreenDropOctets,
        pxmTC4AcPmRandomYellowDropPkts,
        pxmTC4AcPmRandomYellowDropOctets,
        pxmTC4AcPmQueueingTransmitPkts,
        pxmTC4AcPmQueueingTransmitOctets
    }
    STATUS current
    DESCRIPTION
        " A collection of objects for reading the real-time performance of the pxmAc."
    ::= { pxmAcPmGroups 9 }

pxmTC4AcPmRealGroup OBJECT-GROUP
    OBJECTS {
        pxmTC4AcPmRealTCNum,
        pxmTC4AcPmRealTDQueuingCurrentQDepth,
        pxmTC4AcPmRealQueueingDiscardOctets,
        pxmTC4AcPmRealQueueingDiscardPkts,
        pxmTC4AcPmRealRandomGreenDropPkts,
        pxmTC4AcPmRealRandomGreenDropOctets,
        pxmTC4AcPmRealRandomYellowDropPkts,
        pxmTC4AcPmRealRandomYellowDropOctets,
        pxmTC4AcPmRealQueueingTransmitPkts,
        pxmTC4AcPmRealQueueingTransmitOctets,
        pxmTC4AcPmRealQueueingMeanQSizeUnit,
        pxmTC4AcPmRealMeanQSize
    }
    STATUS current
    DESCRIPTION
        " A collection of objects for reading the real-time performance of the pxmAc."
    ::= { pxmAcPmGroups 10 }

pxmTC6AcPmGroup OBJECT-GROUP
    OBJECTS {
        pxmTC6AcPmValidity,
        pxmTC6AcPmTCNum,
        pxmTC6AcPmQueueingDiscardOctets,
        pxmTC6AcPmQueueingDiscardPkts,
        pxmTC6AcPmRandomGreenDropPkts,
        pxmTC6AcPmRandomGreenDropOctets,
        pxmTC6AcPmRandomYellowDropPkts,
        pxmTC6AcPmRandomYellowDropOctets,
        pxmTC6AcPmQueueingTransmitPkts,
        pxmTC6AcPmQueueingTransmitOctets
    }
    STATUS current
    DESCRIPTION
        " A collection of objects for reading the real-time performance of the pxmAc."
    ::= { pxmAcPmGroups 11 }

pxmTC6AcPmRealGroup OBJECT-GROUP
    OBJECTS {
        pxmTC6AcPmRealTCNum,
        pxmTC6AcPmRealTDQueuingCurrentQDepth,
        pxmTC6AcPmRealQueueingDiscardOctets,
        pxmTC6AcPmRealQueueingDiscardPkts,
        pxmTC6AcPmRealRandomGreenDropPkts,
        pxmTC6AcPmRealRandomGreenDropOctets,
        pxmTC6AcPmRealRandomYellowDropPkts,
        pxmTC6AcPmRealRandomYellowDropOctets,
        pxmTC6AcPmRealQueueingTransmitPkts,
        pxmTC6AcPmRealQueueingTransmitOctets,
        pxmTC6AcPmRealQueueingMeanQSizeUnit,
        pxmTC6AcPmRealMeanQSize
    }
    STATUS current
    DESCRIPTION
        " A collection of objects for reading the real-time performance of the pxmAc."
    ::= { pxmAcPmGroups 12 }

pxmTC7AcPmGroup OBJECT-GROUP
    OBJECTS {
        pxmTC7AcPmValidity,
        pxmTC7AcPmTCNum,
        pxmTC7AcPmQueueingDiscardOctets,
        pxmTC7AcPmQueueingDiscardPkts,
        pxmTC7AcPmRandomGreenDropPkts,
        pxmTC7AcPmRandomGreenDropOctets,
        pxmTC7AcPmRandomYellowDropPkts,
        pxmTC7AcPmRandomYellowDropOctets,
        pxmTC7AcPmQueueingTransmitPkts,
        pxmTC7AcPmQueueingTransmitOctets
    }
    STATUS current
    DESCRIPTION
        " A collection of objects for reading the real-time performance of the pxmAc."
    ::= { pxmAcPmGroups 13 }

pxmTC7AcPmRealGroup OBJECT-GROUP
    OBJECTS {
        pxmTC7AcPmRealTCNum,
        pxmTC7AcPmRealTDQueuingCurrentQDepth,
        pxmTC7AcPmRealQueueingDiscardOctets,
        pxmTC7AcPmRealQueueingDiscardPkts,
        pxmTC7AcPmRealRandomGreenDropPkts,
        pxmTC7AcPmRealRandomGreenDropOctets,
        pxmTC7AcPmRealRandomYellowDropPkts,
        pxmTC7AcPmRealRandomYellowDropOctets,
        pxmTC7AcPmRealQueueingTransmitPkts,
        pxmTC7AcPmRealQueueingTransmitOctets,
        pxmTC7AcPmRealQueueingMeanQSizeUnit,
        pxmTC7AcPmRealMeanQSize
    }
    STATUS current
    DESCRIPTION
        " A collection of objects for reading the real-time performance of the pxmAc."
    ::= { pxmAcPmGroups 14 }

pxmTCANYAcPmGroup OBJECT-GROUP
    OBJECTS {
        pxmTCANYAcPmValidity,
        pxmTCANYAcPmTCNum,
        pxmTCANYAcPmQueueingDiscardOctets,
        pxmTCANYAcPmQueueingDiscardPkts,
        pxmTCANYAcPmRandomGreenDropPkts,
        pxmTCANYAcPmRandomGreenDropOctets,
        pxmTCANYAcPmRandomYellowDropPkts,
        pxmTCANYAcPmRandomYellowDropOctets,
        pxmTCANYAcPmQueueingTransmitPkts,
        pxmTCANYAcPmQueueingTransmitOctets
    }
    STATUS current
    DESCRIPTION
        " A collection of objects for reading the real-time performance of the pxmAc."
    ::= { pxmAcPmGroups 15 }

pxmTCANYAcPmRealGroup OBJECT-GROUP
    OBJECTS {
        pxmTCANYAcPmRealTCNum,
        pxmTCANYAcPmRealTDQueuingCurrentQDepth,
        pxmTCANYAcPmRealQueueingDiscardOctets,
        pxmTCANYAcPmRealQueueingDiscardPkts,
        pxmTCANYAcPmRealRandomGreenDropPkts,
        pxmTCANYAcPmRealRandomGreenDropOctets,
        pxmTCANYAcPmRealRandomYellowDropPkts,
        pxmTCANYAcPmRealRandomYellowDropOctets,
        pxmTCANYAcPmRealQueueingTransmitPkts,
        pxmTCANYAcPmRealQueueingTransmitOctets,
        pxmTCANYAcPmRealQueueingMeanQSizeUnit,
        pxmTCANYAcPmRealMeanQSize
    }
    STATUS current
    DESCRIPTION
        " A collection of objects for reading the real-time performance of the pxmAc."
    ::= { pxmAcPmGroups 16 }

END

-- *****************************************************************
-- INFINERA-PM-PXMNWINTF-MIB
-- 
-- October 2015, Mithun Murthy  / Narendra Gupta
-- 
-- 
-- Copyright (c) 2008-2012 by Infinera Inc.
-- All rights reserved.
-- ****************************************************************

INFINERA-PM-PXMNWINTF-MIB DEFINITIONS ::= BEGIN

IMPORTS
MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    HCPerfIntervalCount                         FROM HC-PerfHist-TC-MIB
    FloatHundredths,InfnServiceType             FROM INFINERA-TC-MIB
    perfMon                                     FROM INFINERA-REG-MIB;

pxmNwIntfPmMIB MODULE-IDENTITY
    LAST-UPDATED  "201402190000Z"
    ORGANIZATION  "Infinera"
    CONTACT-INFO
        "Infinera
        1322 Bordeaux Drive
        Sunnyvale, CA - 94089

        Contact : Technical Support
        Email   : support@infinera.com
        Phone   : 1-877-INF-5288"
    DESCRIPTION
    " "
    REVISION      "201402190000Z"
    DESCRIPTION
        "First Version"
    ::= { perfMon 98}

pxmNwIntfRmonPm      OBJECT IDENTIFIER ::= { pxmNwIntfPmMIB 1 }

pxmNwIntfPmTable OBJECT-TYPE
    SYNTAX      SEQUENCE OF PxmNwIntfPmEntry
    MAX-ACCESS  not-accessible
    STATUS      current
    DESCRIPTION
    "A list of PxmNwIntfPm entries. Each entry is uniquely identified by the value of ifIndex, sampleDuration and
    pxmNwIntfPmTimestamp."
    ::= { pxmNwIntfRmonPm 2 }

pxmNwIntfPmEntry  OBJECT-TYPE
    SYNTAX      PxmNwIntfPmEntry
    MAX-ACCESS  not-accessible
    STATUS      current
    DESCRIPTION
    "A PxmNwIntf entry containing historical performance information pertaining to Infinera
    PxmNwIntf interfaces. This table is a subclass of IfCommon. Entries will exist in this
    table only for interfaces of type PxmNwIntf.
    Each interface may have a number of entries in this table, each with a different combination
    of timestamp and sample duration."
    INDEX { ifIndex, pxmNwIntfPmSampleDuration, pxmNwIntfPmTimestamp }
    ::= { pxmNwIntfPmTable 1 }

PxmNwIntfPmEntry  ::= SEQUENCE {
    pxmNwIntfPmTimestamp            Integer32,
    pxmNwIntfPmSampleDuration       INTEGER,
    pxmNwIntfPmValidity             TruthValue,
    pxmNwIntfPmRxPackets            HCPerfIntervalCount,
    pxmNwIntfPmTxPackets            HCPerfIntervalCount,
    pxmNwIntfPmRxOctets             HCPerfIntervalCount,
    pxmNwIntfPmTxOctets             HCPerfIntervalCount
}

pxmNwIntfPmTimestamp OBJECT-TYPE
SYNTAX      Integer32 (0..2147483647)
    MAX-ACCESS  not-accessible
    STATUS      current
    DESCRIPTION
    "End Time stamp for this interval. If this time is later than the current time,
    then the data for this bucket is currently being collected."
    ::= { pxmNwIntfPmEntry  1 }


pxmNwIntfPmSampleDuration OBJECT-TYPE
    SYNTAX      INTEGER {
        fifteenMinutes(1),
        day(2)
    }
    MAX-ACCESS  not-accessible
    STATUS      current
    DESCRIPTION
        "The duration of this sample."
    ::= { pxmNwIntfPmEntry  2 }

pxmNwIntfPmValidity OBJECT-TYPE
    SYNTAX      TruthValue
    MAX-ACCESS  read-only
    STATUS      current
    DESCRIPTION "Flag indicating if data was valid for the entire interval"
    ::= { pxmNwIntfPmEntry  3 }

pxmNwIntfPmRxPackets OBJECT-TYPE
    SYNTAX      HCPerfIntervalCount 
    MAX-ACCESS  read-only
    STATUS      current
    DESCRIPTION "Number of received data packets."
    ::= { pxmNwIntfPmEntry  4 }

pxmNwIntfPmTxPackets OBJECT-TYPE
    SYNTAX      HCPerfIntervalCount 
    MAX-ACCESS  read-only
    STATUS      current
    DESCRIPTION "Number of transmitted data packets."
    ::= { pxmNwIntfPmEntry  5 }

pxmNwIntfPmRxOctets OBJECT-TYPE
    SYNTAX      HCPerfIntervalCount
    MAX-ACCESS  read-only
    STATUS      current
    DESCRIPTION "Number of recieved data octets."
    ::= { pxmNwIntfPmEntry  6 }

pxmNwIntfPmTxOctets OBJECT-TYPE
    SYNTAX      HCPerfIntervalCount
    MAX-ACCESS  read-only
    STATUS      current
    DESCRIPTION "Number of transmitted data octets."
    ::= { pxmNwIntfPmEntry  7 }

pxmNwIntfPmRealTable OBJECT-TYPE
    SYNTAX      SEQUENCE OF PxmNwIntfPmRealEntry
    MAX-ACCESS  not-accessible
    STATUS      current
    DESCRIPTION
        "A list of PxmNwIntfPmReal entries. Each entry is uniquely identified by the value of ifIndex."
    ::= { pxmNwIntfRmonPm 1 }

pxmNwIntfPmRealEntry  OBJECT-TYPE
    SYNTAX      PxmNwIntfPmRealEntry
    MAX-ACCESS  not-accessible
    STATUS      current
    DESCRIPTION
        "A PxmNwIntf entry containing real-time performance information pertaining to Infinera PxmNwIntf 
        interfaces.This table is a subclass of IfCommon. Entries will exist in this table only for interfaces of
        type PxmNwIntf."
    INDEX { ifIndex }
    ::= { pxmNwIntfPmRealTable 1 }


PxmNwIntfPmRealEntry  ::= SEQUENCE {
    pxmNwIntfPmRealRxPackets        Counter64,
    pxmNwIntfPmRealTxPackets        Counter64,
    pxmNwIntfPmRealRxOctets         Counter64,
    pxmNwIntfPmRealTxOctets         Counter64,
    pxmNwIntfPmRealRxLU             FloatHundredths,
    pxmNwIntfPmRealTxLU             FloatHundredths
}
        
pxmNwIntfPmRealRxPackets OBJECT-TYPE
    SYNTAX      Counter64 
    MAX-ACCESS  read-only
    STATUS      current
    DESCRIPTION "Number of received data packets."
    ::= { pxmNwIntfPmRealEntry  1 }

pxmNwIntfPmRealTxPackets OBJECT-TYPE
    SYNTAX      Counter64
    MAX-ACCESS  read-only
    STATUS      current
    DESCRIPTION "Number of transmitted data packets."
    ::= { pxmNwIntfPmRealEntry  2 }

pxmNwIntfPmRealRxOctets OBJECT-TYPE
    SYNTAX      Counter64
    MAX-ACCESS  read-only
    STATUS      current
    DESCRIPTION "Number of recieved data octets."
    ::= { pxmNwIntfPmRealEntry  3 }

pxmNwIntfPmRealTxOctets OBJECT-TYPE
    SYNTAX      Counter64
    MAX-ACCESS  read-only
    STATUS      current
    DESCRIPTION "Number of transmitted data octets."
    ::= { pxmNwIntfPmRealEntry  4 }

pxmNwIntfPmRealRxLU OBJECT-TYPE
    SYNTAX      FloatHundredths
    MAX-ACCESS  read-only
    STATUS      current
    DESCRIPTION "Receive Link utilization."
    ::= { pxmNwIntfPmRealEntry  5 }

pxmNwIntfPmRealTxLU OBJECT-TYPE
    SYNTAX      FloatHundredths
    MAX-ACCESS  read-only
    STATUS      current
    DESCRIPTION "Transmit Link utilization."
    ::= { pxmNwIntfPmRealEntry  6 }

-- CM Real
pxmCmNwIntfPmObjects      OBJECT IDENTIFIER ::= { pxmNwIntfPmMIB 2 }

pxmCmNwIntfRealPm         OBJECT IDENTIFIER ::= { pxmCmNwIntfPmObjects 1 }

-- CM - TC0, TC2, TC4, TC6, TC7
pxmTC0NwIntfPmRealTable OBJECT-TYPE
    SYNTAX      SEQUENCE OF PxmTC0NwIntfPmRealEntry
    MAX-ACCESS  not-accessible
    STATUS      current
    DESCRIPTION
        "A list of PxmBwpNwIntfPmReal entries. Each entry is uniquely identified by the value of ifIndex."
    ::= { pxmCmNwIntfRealPm 1 } 

pxmTC0NwIntfPmRealEntry  OBJECT-TYPE
    SYNTAX      PxmTC0NwIntfPmRealEntry
    MAX-ACCESS  not-accessible
    STATUS      current
    DESCRIPTION
        "A PxmTC0NwIntfPm entry containing real-time performance information pertaining to Infinera PxmNwIntfPm interfaces.
        This table is a subclass of IfCommon. Entries will exist in this table only for interfaces of
        type PxmNwIntfPm."
    INDEX { ifIndex }
    ::= { pxmTC0NwIntfPmRealTable 1 }

PxmTC0NwIntfPmRealEntry  ::= SEQUENCE {
    pxmTC0NwIntfPmRealTCNum                     Integer32,
    pxmTC0NwIntfPmRealTDQueuingCurrentQDepth    Integer32,
    pxmTC0NwIntfPmRealQueueingDiscardOctets     Counter64,
    pxmTC0NwIntfPmRealQueueingDiscardPkts       Integer32,
    pxmTC0NwIntfPmRealRandomGreenDropPkts       Counter64,
    pxmTC0NwIntfPmRealRandomGreenDropOctets     Counter64,
    pxmTC0NwIntfPmRealRandomYellowDropPkts      Counter64,
    pxmTC0NwIntfPmRealRandomYellowDropOctets    Counter64,
    pxmTC0NwIntfPmRealQueueingTransmitPkts      Counter64,
    pxmTC0NwIntfPmRealQueueingTransmitOctets    Counter64,
    pxmTC0NwIntfPmRealQueueingMeanQSizeUnit     Integer32,
    pxmTC0NwIntfPmRealMeanQSize                 Integer32
}

pxmTC0NwIntfPmRealTCNum OBJECT-TYPE
    SYNTAX      Integer32
    MAX-ACCESS  read-only
    STATUS      current
    DESCRIPTION "TCNum Real PM of traffic class - 0 (TC0) on PxmNwIntf"
    ::= { pxmTC0NwIntfPmRealEntry  1 }

pxmTC0NwIntfPmRealTDQueuingCurrentQDepth OBJECT-TYPE
    SYNTAX      Integer32
    MAX-ACCESS  read-only
    STATUS      current
    DESCRIPTION "TDQueuingCurrentQDepth Real PM of traffic class - 0 (TC0) on PxmNwIntf"
    ::= { pxmTC0NwIntfPmRealEntry  2 }

pxmTC0NwIntfPmRealQueueingDiscardOctets OBJECT-TYPE
    SYNTAX      Counter64
    MAX-ACCESS  read-only
    STATUS      current
    DESCRIPTION "QueueingDiscardOctets Real PM of traffic class - 0 (TC0) on PxmNwIntf"
    ::= { pxmTC0NwIntfPmRealEntry  3 }

pxmTC0NwIntfPmRealQueueingDiscardPkts OBJECT-TYPE
    SYNTAX      Integer32
    MAX-ACCESS  read-only
    STATUS      current
    DESCRIPTION "QueueingDiscardPkts Real PM of traffic class - 0 (TC0) on PxmNwIntf"
    ::= { pxmTC0NwIntfPmRealEntry  4 }

pxmTC0NwIntfPmRealRandomGreenDropPkts OBJECT-TYPE
    SYNTAX      Counter64
    MAX-ACCESS  read-only
    STATUS      current
    DESCRIPTION "RandomGreenDropPkts Real PM of traffic class - 0 (TC0) on PxmNwIntf"
    ::= { pxmTC0NwIntfPmRealEntry  5 }

pxmTC0NwIntfPmRealRandomGreenDropOctets OBJECT-TYPE
    SYNTAX      Counter64
    MAX-ACCESS  read-only
    STATUS      current
    DESCRIPTION "RandomGreenDropOctets Real PM of traffic class - 0 (TC0) on PxmNwIntf"
    ::= { pxmTC0NwIntfPmRealEntry  6 }

pxmTC0NwIntfPmRealRandomYellowDropPkts OBJECT-TYPE
    SYNTAX      Counter64
    MAX-ACCESS  read-only
    STATUS      current
    DESCRIPTION "RandomYellowDropPkts Real PM of traffic class - 0 (TC0) on PxmNwIntf"
    ::= { pxmTC0NwIntfPmRealEntry  7 }

pxmTC0NwIntfPmRealRandomYellowDropOctets OBJECT-TYPE
    SYNTAX      Counter64
    MAX-ACCESS  read-only
    STATUS      current
    DESCRIPTION "RandomYellowDropOctets Real PM of traffic class - 0 (TC0) on PxmNwIntf"
    ::= { pxmTC0NwIntfPmRealEntry  8 }

pxmTC0NwIntfPmRealQueueingTransmitPkts OBJECT-TYPE
    SYNTAX      Counter64
    MAX-ACCESS  read-only
    STATUS      current
    DESCRIPTION "QueueingTransmitPkts Real PM of traffic class - 0 (TC0) on PxmNwIntf"
    ::= { pxmTC0NwIntfPmRealEntry  9 }

pxmTC0NwIntfPmRealQueueingTransmitOctets OBJECT-TYPE
    SYNTAX      Counter64
    MAX-ACCESS  read-only
    STATUS      current
    DESCRIPTION "QueueingTransmitOctets Real PM of traffic class - 0 (TC0) on PxmNwIntf"
    ::= { pxmTC0NwIntfPmRealEntry  10 }

pxmTC0NwIntfPmRealQueueingMeanQSizeUnit OBJECT-TYPE
    SYNTAX      Integer32
    MAX-ACCESS  read-only
    STATUS      current
    DESCRIPTION "QueueingMeanQSizeUnit Real PM of traffic class - 0 (TC0) on PxmNwIntf"
    ::= { pxmTC0NwIntfPmRealEntry  11 }

pxmTC0NwIntfPmRealMeanQSize OBJECT-TYPE
    SYNTAX      Integer32
    MAX-ACCESS  read-only
    STATUS      current
    DESCRIPTION "MeanQSize Real PM of traffic class - 0 (TC0) on PxmNwIntf"
    ::= { pxmTC0NwIntfPmRealEntry  12 }

-- CM Historical
pxmCmNwIntfPm             OBJECT IDENTIFIER ::= { pxmCmNwIntfPmObjects 2 }

pxmTC0NwIntfPmTable OBJECT-TYPE
    SYNTAX      SEQUENCE OF PxmTC0NwIntfPmEntry
    MAX-ACCESS  not-accessible
    STATUS      current
    DESCRIPTION
        "A list of PxmBwpNwIntfPmReal entries. Each entry is uniquely identified by the value of ifIndex."
    ::= { pxmCmNwIntfPm 1 } 

pxmTC0NwIntfPmEntry  OBJECT-TYPE
    SYNTAX      PxmTC0NwIntfPmEntry
    MAX-ACCESS  not-accessible
    STATUS      current
    DESCRIPTION ""
    INDEX { ifIndex, pxmTC0NwIntfPmSampleDuration, pxmTC0NwIntfPmTimestamp }
    ::= { pxmTC0NwIntfPmTable 1 }

PxmTC0NwIntfPmEntry  ::= SEQUENCE {
    pxmTC0NwIntfPmTimestamp                 Integer32,
    pxmTC0NwIntfPmSampleDuration            INTEGER,
    pxmTC0NwIntfPmValidity                  TruthValue,
    pxmTC0NwIntfPmTCNum                     Integer32,
    pxmTC0NwIntfPmQueueingDiscardOctets     Counter64,
    pxmTC0NwIntfPmQueueingDiscardPkts       Integer32,
    pxmTC0NwIntfPmRandomGreenDropPkts       Counter64,
    pxmTC0NwIntfPmRandomGreenDropOctets     Counter64,
    pxmTC0NwIntfPmRandomYellowDropPkts      Counter64,
    pxmTC0NwIntfPmRandomYellowDropOctets    Counter64,
    pxmTC0NwIntfPmQueueingTransmitPkts      Counter64,
    pxmTC0NwIntfPmQueueingTransmitOctets    Counter64
}

pxmTC0NwIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC0NwIntfPmEntry  1 }

pxmTC0NwIntfPmSampleDuration OBJECT-TYPE
    SYNTAX      INTEGER {
                    fifteenMinutes(1),
                    day(2)
                }
    MAX-ACCESS  not-accessible
    STATUS      current
    DESCRIPTION
        "The duration of this sample."
    ::= { pxmTC0NwIntfPmEntry  2 }

pxmTC0NwIntfPmValidity OBJECT-TYPE
    SYNTAX      TruthValue
    MAX-ACCESS  read-only
    STATUS      current
    DESCRIPTION "Flag indicating if data was valid for the entire interval"
    ::= { pxmTC0NwIntfPmEntry  3 }

pxmTC0NwIntfPmTCNum OBJECT-TYPE
    SYNTAX      Integer32
    MAX-ACCESS  read-only
    STATUS      current
    DESCRIPTION "TCNum Historical PM of traffic class - 0 (TC0) on PxmNwIntf"
    ::= { pxmTC0NwIntfPmEntry  4 }

pxmTC0NwIntfPmQueueingDiscardOctets OBJECT-TYPE
    SYNTAX      Counter64
    MAX-ACCESS  read-only
    STATUS      current
    DESCRIPTION "QueueingDiscardOctets Historical PM of traffic class - 0 (TC0) on PxmNwIntf"
    ::= { pxmTC0NwIntfPmEntry  5 }

pxmTC0NwIntfPmQueueingDiscardPkts OBJECT-TYPE
    SYNTAX      Integer32
    MAX-ACCESS  read-only
    STATUS      current
    DESCRIPTION "QueueingDiscardPkts Historical PM of traffic class - 0 (TC0) on PxmNwIntf"
    ::= { pxmTC0NwIntfPmEntry  6 }

pxmTC0NwIntfPmRandomGreenDropPkts OBJECT-TYPE
    SYNTAX      Counter64
    MAX-ACCESS  read-only
    STATUS      current
    DESCRIPTION "RandomGreenDropPkts Historical PM of traffic class - 0 (TC0) on PxmNwIntf"
    ::= { pxmTC0NwIntfPmEntry  7 }

pxmTC0NwIntfPmRandomGreenDropOctets OBJECT-TYPE
    SYNTAX      Counter64
    MAX-ACCESS  read-only
    STATUS      current
    DESCRIPTION "RandomGreenDropOctets Historical PM of traffic class - 0 (TC0) on PxmNwIntf"
    ::= { pxmTC0NwIntfPmEntry  8 }

pxmTC0NwIntfPmRandomYellowDropPkts OBJECT-TYPE
    SYNTAX      Counter64
    MAX-ACCESS  read-only
    STATUS      current
    DESCRIPTION "RandomYellowDropPkts Historical PM of traffic class - 0 (TC0) on PxmNwIntf"
    ::= { pxmTC0NwIntfPmEntry  9 }

pxmTC0NwIntfPmRandomYellowDropOctets OBJECT-TYPE
    SYNTAX      Counter64
    MAX-ACCESS  read-only
    STATUS      current
    DESCRIPTION "RandomYellowDropOctets Historical PM of traffic class - 0 (TC0) on PxmNwIntf"
    ::= { pxmTC0NwIntfPmEntry  10 }

pxmTC0NwIntfPmQueueingTransmitPkts OBJECT-TYPE
    SYNTAX      Counter64
    MAX-ACCESS  read-only
    STATUS      current
    DESCRIPTION "QueueingTransmitPkts Historical PM of traffic class - 0 (TC0) on PxmNwIntf"
    ::= { pxmTC0NwIntfPmEntry  11 }

pxmTC0NwIntfPmQueueingTransmitOctets OBJECT-TYPE
    SYNTAX      Counter64
    MAX-ACCESS  read-only
    STATUS      current
    DESCRIPTION "QueueingTransmitOctets Historical PM of traffic class - 0 (TC0) on PxmNwIntf"
    ::= { pxmTC0NwIntfPmEntry  12 }

-- TC2 Historical
pxmTC2NwIntfPmTable OBJECT-TYPE
    SYNTAX      SEQUENCE OF PxmTC2NwIntfPmEntry
    MAX-ACCESS  not-accessible
    STATUS      current
    DESCRIPTION
        "A list of PxmBwpNwIntfPmReal entries. Each entry is uniquely identified by the value of ifIndex."
    ::= { pxmCmNwIntfPm 2 } 

pxmTC2NwIntfPmEntry  OBJECT-TYPE
    SYNTAX      PxmTC2NwIntfPmEntry
    MAX-ACCESS  not-accessible
    STATUS      current
    DESCRIPTION ""
    INDEX { ifIndex, pxmTC2NwIntfPmSampleDuration, pxmTC2NwIntfPmTimestamp }
    ::= { pxmTC2NwIntfPmTable 1 }

PxmTC2NwIntfPmEntry  ::= SEQUENCE {
    pxmTC2NwIntfPmTimestamp                 Integer32,
    pxmTC2NwIntfPmSampleDuration            INTEGER,
    pxmTC2NwIntfPmValidity                  TruthValue,
    pxmTC2NwIntfPmTCNum                     Integer32,
    pxmTC2NwIntfPmQueueingDiscardOctets     Counter64,
    pxmTC2NwIntfPmQueueingDiscardPkts       Integer32,
    pxmTC2NwIntfPmRandomGreenDropPkts       Counter64,
    pxmTC2NwIntfPmRandomGreenDropOctets     Counter64,
    pxmTC2NwIntfPmRandomYellowDropPkts      Counter64,
    pxmTC2NwIntfPmRandomYellowDropOctets    Counter64,
    pxmTC2NwIntfPmQueueingTransmitPkts      Counter64,
    pxmTC2NwIntfPmQueueingTransmitOctets    Counter64
}

pxmTC2NwIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC2NwIntfPmEntry  1 }

pxmTC2NwIntfPmSampleDuration OBJECT-TYPE
    SYNTAX      INTEGER {
                    fifteenMinutes(1),
                    day(2)
                }
    MAX-ACCESS  not-accessible
    STATUS      current
    DESCRIPTION
        "The duration of this sample."
    ::= { pxmTC2NwIntfPmEntry  2 }

pxmTC2NwIntfPmValidity OBJECT-TYPE
    SYNTAX      TruthValue
    MAX-ACCESS  read-only
    STATUS      current
    DESCRIPTION "Flag indicating if data was valid for the entire interval"
    ::= { pxmTC2NwIntfPmEntry  3 }

pxmTC2NwIntfPmTCNum OBJECT-TYPE
    SYNTAX      Integer32
    MAX-ACCESS  read-only
    STATUS      current
    DESCRIPTION "TCNum Historical PM of traffic class - 2 (TC2) on PxmNwIntf"
    ::= { pxmTC2NwIntfPmEntry  4 }

pxmTC2NwIntfPmQueueingDiscardOctets OBJECT-TYPE
    SYNTAX      Counter64
    MAX-ACCESS  read-only
    STATUS      current
    DESCRIPTION "QueueingDiscardOctets Historical PM of traffic class - 2 (TC2) on PxmNwIntf"
    ::= { pxmTC2NwIntfPmEntry  5 }

pxmTC2NwIntfPmQueueingDiscardPkts OBJECT-TYPE
    SYNTAX      Integer32
    MAX-ACCESS  read-only
    STATUS      current
    DESCRIPTION "QueueingDiscardPkts Historical PM of traffic class - 2 (TC2) on PxmNwIntf"
    ::= { pxmTC2NwIntfPmEntry  6 }

pxmTC2NwIntfPmRandomGreenDropPkts OBJECT-TYPE
    SYNTAX      Counter64
    MAX-ACCESS  read-only
    STATUS      current
    DESCRIPTION "RandomGreenDropPkts Historical PM of traffic class - 2 (TC2) on PxmNwIntf"
    ::= { pxmTC2NwIntfPmEntry  7 }

pxmTC2NwIntfPmRandomGreenDropOctets OBJECT-TYPE
    SYNTAX      Counter64
    MAX-ACCESS  read-only
    STATUS      current
    DESCRIPTION "RandomGreenDropOctets Historical PM of traffic class - 2 (TC2) on PxmNwIntf"
    ::= { pxmTC2NwIntfPmEntry  8 }

pxmTC2NwIntfPmRandomYellowDropPkts OBJECT-TYPE
    SYNTAX      Counter64
    MAX-ACCESS  read-only
    STATUS      current
    DESCRIPTION "RandomYellowDropPkts Historical PM of traffic class - 2 (TC2) on PxmNwIntf"
    ::= { pxmTC2NwIntfPmEntry  9 }

pxmTC2NwIntfPmRandomYellowDropOctets OBJECT-TYPE
    SYNTAX      Counter64
    MAX-ACCESS  read-only
    STATUS      current
    DESCRIPTION "RandomYellowDropOctets Historical PM of traffic class - 2 (TC2) on PxmNwIntf"
    ::= { pxmTC2NwIntfPmEntry  10 }

pxmTC2NwIntfPmQueueingTransmitPkts OBJECT-TYPE
    SYNTAX      Counter64
    MAX-ACCESS  read-only
    STATUS      current
    DESCRIPTION "QueueingTransmitPkts Historical PM of traffic class - 2 (TC2) on PxmNwIntf"
    ::= { pxmTC2NwIntfPmEntry  11 }

pxmTC2NwIntfPmQueueingTransmitOctets OBJECT-TYPE
    SYNTAX      Counter64
    MAX-ACCESS  read-only
    STATUS      current
    DESCRIPTION "QueueingTransmitOctets Historical PM of traffic class - 2 (TC2) on PxmNwIntf"
    ::= { pxmTC2NwIntfPmEntry  12 }

-- TC2 Real
pxmTC2NwIntfPmRealTable OBJECT-TYPE
    SYNTAX      SEQUENCE OF PxmTC2NwIntfPmRealEntry
    MAX-ACCESS  not-accessible
    STATUS      current
    DESCRIPTION
        "A list of PxmBwpNwIntfPmReal entries. Each entry is uniquely identified by the value of ifIndex."
    ::= { pxmCmNwIntfRealPm 2 } 

pxmTC2NwIntfPmRealEntry  OBJECT-TYPE
    SYNTAX      PxmTC2NwIntfPmRealEntry
    MAX-ACCESS  not-accessible
    STATUS      current
    DESCRIPTION
        "A PxmTC0NwIntfPm entry containing real-time performance information pertaining to Infinera PxmNwIntfPm interfaces.
        This table is a subclass of IfCommon. Entries will exist in this table only for interfaces of
        type PxmNwIntfPm."
    INDEX { ifIndex }
    ::= { pxmTC2NwIntfPmRealTable 1 }

PxmTC2NwIntfPmRealEntry  ::= SEQUENCE {
    pxmTC2NwIntfPmRealTCNum                     Integer32,
    pxmTC2NwIntfPmRealTDQueuingCurrentQDepth    Integer32,
    pxmTC2NwIntfPmRealQueueingDiscardOctets     Counter64,
    pxmTC2NwIntfPmRealQueueingDiscardPkts       Integer32,
    pxmTC2NwIntfPmRealRandomGreenDropPkts       Counter64,
    pxmTC2NwIntfPmRealRandomGreenDropOctets     Counter64,
    pxmTC2NwIntfPmRealRandomYellowDropPkts      Counter64,
    pxmTC2NwIntfPmRealRandomYellowDropOctets    Counter64,
    pxmTC2NwIntfPmRealQueueingTransmitPkts      Counter64,
    pxmTC2NwIntfPmRealQueueingTransmitOctets    Counter64,
    pxmTC2NwIntfPmRealQueueingMeanQSizeUnit     Integer32,
    pxmTC2NwIntfPmRealMeanQSize                 Integer32
}

pxmTC2NwIntfPmRealTCNum OBJECT-TYPE
    SYNTAX      Integer32
    MAX-ACCESS  read-only
    STATUS      current
    DESCRIPTION "TCNum Real PM of traffic class - 2 (TC2) on PxmNwIntf"
    ::= { pxmTC2NwIntfPmRealEntry  1 }

pxmTC2NwIntfPmRealTDQueuingCurrentQDepth OBJECT-TYPE
    SYNTAX      Integer32
    MAX-ACCESS  read-only
    STATUS      current
    DESCRIPTION "TDQueuingCurrentQDepth Real PM of traffic class - 2 (TC2) on PxmNwIntf"
    ::= { pxmTC2NwIntfPmRealEntry  2 }

pxmTC2NwIntfPmRealQueueingDiscardOctets OBJECT-TYPE
    SYNTAX      Counter64
    MAX-ACCESS  read-only
    STATUS      current
    DESCRIPTION "QueueingDiscardOctets Real PM of traffic class - 2 (TC2) on PxmNwIntf"
    ::= { pxmTC2NwIntfPmRealEntry  3 }

pxmTC2NwIntfPmRealQueueingDiscardPkts OBJECT-TYPE
    SYNTAX      Integer32
    MAX-ACCESS  read-only
    STATUS      current
    DESCRIPTION "QueueingDiscardPkts Real PM of traffic class - 2 (TC2) on PxmNwIntf"
    ::= { pxmTC2NwIntfPmRealEntry  4 }

pxmTC2NwIntfPmRealRandomGreenDropPkts OBJECT-TYPE
    SYNTAX      Counter64
    MAX-ACCESS  read-only
    STATUS      current
    DESCRIPTION "RandomGreenDropPkts Real PM of traffic class - 2 (TC2) on PxmNwIntf"
    ::= { pxmTC2NwIntfPmRealEntry  5 }

pxmTC2NwIntfPmRealRandomGreenDropOctets OBJECT-TYPE
    SYNTAX      Counter64
    MAX-ACCESS  read-only
    STATUS      current
    DESCRIPTION "RandomGreenDropOctets Real PM of traffic class - 2 (TC2) on PxmNwIntf"
    ::= { pxmTC2NwIntfPmRealEntry  6 }

pxmTC2NwIntfPmRealRandomYellowDropPkts OBJECT-TYPE
    SYNTAX      Counter64
    MAX-ACCESS  read-only
    STATUS      current
    DESCRIPTION "RandomYellowDropPkts Real PM of traffic class - 2 (TC2) on PxmNwIntf"
    ::= { pxmTC2NwIntfPmRealEntry  7 }

pxmTC2NwIntfPmRealRandomYellowDropOctets OBJECT-TYPE
    SYNTAX      Counter64
    MAX-ACCESS  read-only
    STATUS      current
    DESCRIPTION "RandomYellowDropOctets Real PM of traffic class - 2 (TC2) on PxmNwIntf"
    ::= { pxmTC2NwIntfPmRealEntry  8 }

pxmTC2NwIntfPmRealQueueingTransmitPkts OBJECT-TYPE
    SYNTAX      Counter64
    MAX-ACCESS  read-only
    STATUS      current
    DESCRIPTION "QueueingTransmitPkts Real PM of traffic class - 2 (TC2) on PxmNwIntf"
    ::= { pxmTC2NwIntfPmRealEntry  9 }

pxmTC2NwIntfPmRealQueueingTransmitOctets OBJECT-TYPE
    SYNTAX      Counter64
    MAX-ACCESS  read-only
    STATUS      current
    DESCRIPTION "QueueingTransmitOctets Real PM of traffic class - 2 (TC2) on PxmNwIntf"
    ::= { pxmTC2NwIntfPmRealEntry  10 }

pxmTC2NwIntfPmRealQueueingMeanQSizeUnit OBJECT-TYPE
    SYNTAX      Integer32
    MAX-ACCESS  read-only
    STATUS      current
    DESCRIPTION "QueueingMeanQSizeUnit Real PM of traffic class - 2 (TC2) on PxmNwIntf"
    ::= { pxmTC2NwIntfPmRealEntry  11 }

pxmTC2NwIntfPmRealMeanQSize OBJECT-TYPE
    SYNTAX      Integer32
    MAX-ACCESS  read-only
    STATUS      current
    DESCRIPTION "MeanQSize Real PM of traffic class - 2 (TC2) on PxmNwIntf"
    ::= { pxmTC2NwIntfPmRealEntry  12 }

-- TC4 Historical
pxmTC4NwIntfPmTable OBJECT-TYPE
    SYNTAX      SEQUENCE OF PxmTC4NwIntfPmEntry
    MAX-ACCESS  not-accessible
    STATUS      current
    DESCRIPTION
        "A list of PxmBwpNwIntfPmReal entries. Each entry is uniquely identified by the value of ifIndex."
    ::= { pxmCmNwIntfPm 3 } 

pxmTC4NwIntfPmEntry  OBJECT-TYPE
    SYNTAX      PxmTC4NwIntfPmEntry
    MAX-ACCESS  not-accessible
    STATUS      current
    DESCRIPTION ""
    INDEX { ifIndex, pxmTC4NwIntfPmSampleDuration, pxmTC4NwIntfPmTimestamp }
    ::= { pxmTC4NwIntfPmTable 1 }

PxmTC4NwIntfPmEntry  ::= SEQUENCE {
    pxmTC4NwIntfPmTimestamp                 Integer32,
    pxmTC4NwIntfPmSampleDuration            INTEGER,
    pxmTC4NwIntfPmValidity                  TruthValue,
    pxmTC4NwIntfPmTCNum                     Integer32,
    pxmTC4NwIntfPmQueueingDiscardOctets     Counter64,
    pxmTC4NwIntfPmQueueingDiscardPkts       Integer32,
    pxmTC4NwIntfPmRandomGreenDropPkts       Counter64,
    pxmTC4NwIntfPmRandomGreenDropOctets     Counter64,
    pxmTC4NwIntfPmRandomYellowDropPkts      Counter64,
    pxmTC4NwIntfPmRandomYellowDropOctets    Counter64,
    pxmTC4NwIntfPmQueueingTransmitPkts      Counter64,
    pxmTC4NwIntfPmQueueingTransmitOctets    Counter64
}

pxmTC4NwIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC4NwIntfPmEntry  1 }

pxmTC4NwIntfPmSampleDuration OBJECT-TYPE
    SYNTAX      INTEGER {
                    fifteenMinutes(1),
                    day(2)
                }
    MAX-ACCESS  not-accessible
    STATUS      current
    DESCRIPTION
        "The duration of this sample."
    ::= { pxmTC4NwIntfPmEntry  2 }

pxmTC4NwIntfPmValidity OBJECT-TYPE
    SYNTAX      TruthValue
    MAX-ACCESS  read-only
    STATUS      current
    DESCRIPTION "Flag indicating if data was valid for the entire interval"
    ::= { pxmTC4NwIntfPmEntry  3 }

pxmTC4NwIntfPmTCNum OBJECT-TYPE
    SYNTAX      Integer32
    MAX-ACCESS  read-only
    STATUS      current
    DESCRIPTION "TCNum Historical PM of traffic class - 4 (TC4) on PxmNwIntf"
    ::= { pxmTC4NwIntfPmEntry  4 }

pxmTC4NwIntfPmQueueingDiscardOctets OBJECT-TYPE
    SYNTAX      Counter64
    MAX-ACCESS  read-only
    STATUS      current
    DESCRIPTION "QueueingDiscardOctets Historical PM of traffic class - 4 (TC4) on PxmNwIntf"
    ::= { pxmTC4NwIntfPmEntry  5 }

pxmTC4NwIntfPmQueueingDiscardPkts OBJECT-TYPE
    SYNTAX      Integer32
    MAX-ACCESS  read-only
    STATUS      current
    DESCRIPTION "QueueingDiscardPkts Historical PM of traffic class - 4 (TC4) on PxmNwIntf"
    ::= { pxmTC4NwIntfPmEntry  6 }

pxmTC4NwIntfPmRandomGreenDropPkts OBJECT-TYPE
    SYNTAX      Counter64
    MAX-ACCESS  read-only
    STATUS      current
    DESCRIPTION "RandomGreenDropPkts Historical PM of traffic class - 4 (TC4) on PxmNwIntf"
    ::= { pxmTC4NwIntfPmEntry  7 }

pxmTC4NwIntfPmRandomGreenDropOctets OBJECT-TYPE
    SYNTAX      Counter64
    MAX-ACCESS  read-only
    STATUS      current
    DESCRIPTION "RandomGreenDropOctets Historical PM of traffic class - 4 (TC4) on PxmNwIntf"
    ::= { pxmTC4NwIntfPmEntry  8 }

pxmTC4NwIntfPmRandomYellowDropPkts OBJECT-TYPE
    SYNTAX      Counter64
    MAX-ACCESS  read-only
    STATUS      current
    DESCRIPTION "RandomYellowDropPkts Historical PM of traffic class - 4 (TC4) on PxmNwIntf"
    ::= { pxmTC4NwIntfPmEntry  9 }

pxmTC4NwIntfPmRandomYellowDropOctets OBJECT-TYPE
    SYNTAX      Counter64
    MAX-ACCESS  read-only
    STATUS      current
    DESCRIPTION "RandomYellowDropOctets Historical PM of traffic class - 4 (TC4) on PxmNwIntf"
    ::= { pxmTC4NwIntfPmEntry  10 }

pxmTC4NwIntfPmQueueingTransmitPkts OBJECT-TYPE
    SYNTAX      Counter64
    MAX-ACCESS  read-only
    STATUS      current
    DESCRIPTION "QueueingTransmitPkts Historical PM of traffic class - 4 (TC4) on PxmNwIntf"
    ::= { pxmTC4NwIntfPmEntry  11 }

pxmTC4NwIntfPmQueueingTransmitOctets OBJECT-TYPE
    SYNTAX      Counter64
    MAX-ACCESS  read-only
    STATUS      current
    DESCRIPTION "QueueingTransmitOctets Historical PM of traffic class - 4 (TC4) on PxmNwIntf"
    ::= { pxmTC4NwIntfPmEntry  12 }

-- TC4 Real
pxmTC4NwIntfPmRealTable OBJECT-TYPE
    SYNTAX      SEQUENCE OF PxmTC4NwIntfPmRealEntry
    MAX-ACCESS  not-accessible
    STATUS      current
    DESCRIPTION
        "A list of PxmBwpNwIntfPmReal entries. Each entry is uniquely identified by the value of ifIndex."
    ::= { pxmCmNwIntfRealPm 3 } 

pxmTC4NwIntfPmRealEntry  OBJECT-TYPE
    SYNTAX      PxmTC4NwIntfPmRealEntry
    MAX-ACCESS  not-accessible
    STATUS      current
    DESCRIPTION
        "A PxmTC0NwIntfPm entry containing real-time performance information pertaining to Infinera PxmNwIntfPm interfaces.
        This table is a subclass of IfCommon. Entries will exist in this table only for interfaces of
        type PxmNwIntfPm."
    INDEX { ifIndex }
    ::= { pxmTC4NwIntfPmRealTable 1 }

PxmTC4NwIntfPmRealEntry  ::= SEQUENCE {
    pxmTC4NwIntfPmRealTCNum                     Integer32,
    pxmTC4NwIntfPmRealTDQueuingCurrentQDepth    Integer32,
    pxmTC4NwIntfPmRealQueueingDiscardOctets     Counter64,
    pxmTC4NwIntfPmRealQueueingDiscardPkts       Integer32,
    pxmTC4NwIntfPmRealRandomGreenDropPkts       Counter64,
    pxmTC4NwIntfPmRealRandomGreenDropOctets     Counter64,
    pxmTC4NwIntfPmRealRandomYellowDropPkts      Counter64,
    pxmTC4NwIntfPmRealRandomYellowDropOctets    Counter64,
    pxmTC4NwIntfPmRealQueueingTransmitPkts      Counter64,
    pxmTC4NwIntfPmRealQueueingTransmitOctets    Counter64,
    pxmTC4NwIntfPmRealQueueingMeanQSizeUnit     Integer32,
    pxmTC4NwIntfPmRealMeanQSize                 Integer32
}

pxmTC4NwIntfPmRealTCNum OBJECT-TYPE
    SYNTAX      Integer32
    MAX-ACCESS  read-only
    STATUS      current
    DESCRIPTION "TCNum Real PM of traffic class - 4 (TC4) on PxmNwIntf"
    ::= { pxmTC4NwIntfPmRealEntry  1 }

pxmTC4NwIntfPmRealTDQueuingCurrentQDepth OBJECT-TYPE
    SYNTAX      Integer32
    MAX-ACCESS  read-only
    STATUS      current
    DESCRIPTION "TDQueuingCurrentQDepth Real PM of traffic class - 4 (TC4) on PxmNwIntf"
    ::= { pxmTC4NwIntfPmRealEntry  2 }

pxmTC4NwIntfPmRealQueueingDiscardOctets OBJECT-TYPE
    SYNTAX      Counter64
    MAX-ACCESS  read-only
    STATUS      current
    DESCRIPTION "QueueingDiscardOctets Real PM of traffic class - 4 (TC4) on PxmNwIntf"
    ::= { pxmTC4NwIntfPmRealEntry  3 }

pxmTC4NwIntfPmRealQueueingDiscardPkts OBJECT-TYPE
    SYNTAX      Integer32
    MAX-ACCESS  read-only
    STATUS      current
    DESCRIPTION "QueueingDiscardPkts Real PM of traffic class - 4 (TC4) on PxmNwIntf"
    ::= { pxmTC4NwIntfPmRealEntry  4 }

pxmTC4NwIntfPmRealRandomGreenDropPkts OBJECT-TYPE
    SYNTAX      Counter64
    MAX-ACCESS  read-only
    STATUS      current
    DESCRIPTION "RandomGreenDropPkts Real PM of traffic class - 4 (TC4) on PxmNwIntf"
    ::= { pxmTC4NwIntfPmRealEntry  5 }

pxmTC4NwIntfPmRealRandomGreenDropOctets OBJECT-TYPE
    SYNTAX      Counter64
    MAX-ACCESS  read-only
    STATUS      current
    DESCRIPTION "RandomGreenDropOctets Real PM of traffic class - 4 (TC4) on PxmNwIntf"
    ::= { pxmTC4NwIntfPmRealEntry  6 }

pxmTC4NwIntfPmRealRandomYellowDropPkts OBJECT-TYPE
    SYNTAX      Counter64
    MAX-ACCESS  read-only
    STATUS      current
    DESCRIPTION "RandomYellowDropPkts Real PM of traffic class - 4 (TC4) on PxmNwIntf"
    ::= { pxmTC4NwIntfPmRealEntry  7 }

pxmTC4NwIntfPmRealRandomYellowDropOctets OBJECT-TYPE
    SYNTAX      Counter64
    MAX-ACCESS  read-only
    STATUS      current
    DESCRIPTION "RandomYellowDropOctets Real PM of traffic class - 4 (TC4) on PxmNwIntf"
    ::= { pxmTC4NwIntfPmRealEntry  8 }

pxmTC4NwIntfPmRealQueueingTransmitPkts OBJECT-TYPE
    SYNTAX      Counter64
    MAX-ACCESS  read-only
    STATUS      current
    DESCRIPTION "QueueingTransmitPkts Real PM of traffic class - 4 (TC4) on PxmNwIntf"
    ::= { pxmTC4NwIntfPmRealEntry  9 }

pxmTC4NwIntfPmRealQueueingTransmitOctets OBJECT-TYPE
    SYNTAX      Counter64
    MAX-ACCESS  read-only
    STATUS      current
    DESCRIPTION "QueueingTransmitOctets Real PM of traffic class - 4 (TC4) on PxmNwIntf"
    ::= { pxmTC4NwIntfPmRealEntry  10 }

pxmTC4NwIntfPmRealQueueingMeanQSizeUnit OBJECT-TYPE
    SYNTAX      Integer32
    MAX-ACCESS  read-only
    STATUS      current
    DESCRIPTION "QueueingMeanQSizeUnit Real PM of traffic class - 4 (TC4) on PxmNwIntf"
    ::= { pxmTC4NwIntfPmRealEntry  11 }

pxmTC4NwIntfPmRealMeanQSize OBJECT-TYPE
    SYNTAX      Integer32
    MAX-ACCESS  read-only
    STATUS      current
    DESCRIPTION "MeanQSize Real PM of traffic class - 4 (TC4) on PxmNwIntf"
    ::= { pxmTC4NwIntfPmRealEntry  12 }

-- TC6 Historical
pxmTC6NwIntfPmTable OBJECT-TYPE
    SYNTAX      SEQUENCE OF PxmTC6NwIntfPmEntry
    MAX-ACCESS  not-accessible
    STATUS      current
    DESCRIPTION
        "A list of PxmBwpNwIntfPmReal entries. Each entry is uniquely identified by the value of ifIndex."
    ::= { pxmCmNwIntfPm 4 } 

pxmTC6NwIntfPmEntry  OBJECT-TYPE
    SYNTAX      PxmTC6NwIntfPmEntry
    MAX-ACCESS  not-accessible
    STATUS      current
    DESCRIPTION ""
    INDEX { ifIndex, pxmTC6NwIntfPmSampleDuration, pxmTC6NwIntfPmTimestamp }
    ::= { pxmTC6NwIntfPmTable 1 }

PxmTC6NwIntfPmEntry  ::= SEQUENCE {
    pxmTC6NwIntfPmTimestamp                 Integer32,
    pxmTC6NwIntfPmSampleDuration            INTEGER,
    pxmTC6NwIntfPmValidity                  TruthValue,
    pxmTC6NwIntfPmTCNum                     Integer32,
    pxmTC6NwIntfPmQueueingDiscardOctets     Counter64,
    pxmTC6NwIntfPmQueueingDiscardPkts       Integer32,
    pxmTC6NwIntfPmRandomGreenDropPkts       Counter64,
    pxmTC6NwIntfPmRandomGreenDropOctets     Counter64,
    pxmTC6NwIntfPmRandomYellowDropPkts      Counter64,
    pxmTC6NwIntfPmRandomYellowDropOctets    Counter64,
    pxmTC6NwIntfPmQueueingTransmitPkts      Counter64,
    pxmTC6NwIntfPmQueueingTransmitOctets    Counter64
}

pxmTC6NwIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC6NwIntfPmEntry  1 }

pxmTC6NwIntfPmSampleDuration OBJECT-TYPE
    SYNTAX      INTEGER {
                    fifteenMinutes(1),
                    day(2)
                }
    MAX-ACCESS  not-accessible
    STATUS      current
    DESCRIPTION
        "The duration of this sample."
    ::= { pxmTC6NwIntfPmEntry  2 }

pxmTC6NwIntfPmValidity OBJECT-TYPE
    SYNTAX      TruthValue
    MAX-ACCESS  read-only
    STATUS      current
    DESCRIPTION "Flag indicating if data was valid for the entire interval"
    ::= { pxmTC6NwIntfPmEntry  3 }

pxmTC6NwIntfPmTCNum OBJECT-TYPE
    SYNTAX      Integer32
    MAX-ACCESS  read-only
    STATUS      current
    DESCRIPTION "TCNum Historical PM of traffic class - 6 (TC6) on PxmNwIntf"
    ::= { pxmTC6NwIntfPmEntry  4 }

pxmTC6NwIntfPmQueueingDiscardOctets OBJECT-TYPE
    SYNTAX      Counter64
    MAX-ACCESS  read-only
    STATUS      current
    DESCRIPTION "QueueingDiscardOctets Historical PM of traffic class - 6 (TC6) on PxmNwIntf"
    ::= { pxmTC6NwIntfPmEntry  5 }

pxmTC6NwIntfPmQueueingDiscardPkts OBJECT-TYPE
    SYNTAX      Integer32
    MAX-ACCESS  read-only
    STATUS      current
    DESCRIPTION "QueueingDiscardPkts Historical PM of traffic class - 6 (TC6) on PxmNwIntf"
    ::= { pxmTC6NwIntfPmEntry  6 }

pxmTC6NwIntfPmRandomGreenDropPkts OBJECT-TYPE
    SYNTAX      Counter64
    MAX-ACCESS  read-only
    STATUS      current
    DESCRIPTION "RandomGreenDropPkts Historical PM of traffic class - 6 (TC6) on PxmNwIntf"
    ::= { pxmTC6NwIntfPmEntry  7 }

pxmTC6NwIntfPmRandomGreenDropOctets OBJECT-TYPE
    SYNTAX      Counter64
    MAX-ACCESS  read-only
    STATUS      current
    DESCRIPTION "RandomGreenDropOctets Historical PM of traffic class - 6 (TC6) on PxmNwIntf"
    ::= { pxmTC6NwIntfPmEntry  8 }

pxmTC6NwIntfPmRandomYellowDropPkts OBJECT-TYPE
    SYNTAX      Counter64
    MAX-ACCESS  read-only
    STATUS      current
    DESCRIPTION "RandomYellowDropPkts Historical PM of traffic class - 6 (TC6) on PxmNwIntf"
    ::= { pxmTC6NwIntfPmEntry  9 }

pxmTC6NwIntfPmRandomYellowDropOctets OBJECT-TYPE
    SYNTAX      Counter64
    MAX-ACCESS  read-only
    STATUS      current
    DESCRIPTION "RandomYellowDropOctets Historical PM of traffic class - 6 (TC6) on PxmNwIntf"
    ::= { pxmTC6NwIntfPmEntry  10 }

pxmTC6NwIntfPmQueueingTransmitPkts OBJECT-TYPE
    SYNTAX      Counter64
    MAX-ACCESS  read-only
    STATUS      current
    DESCRIPTION "QueueingTransmitPkts Historical PM of traffic class - 6 (TC6) on PxmNwIntf"
    ::= { pxmTC6NwIntfPmEntry  11 }

pxmTC6NwIntfPmQueueingTransmitOctets OBJECT-TYPE
    SYNTAX      Counter64
    MAX-ACCESS  read-only
    STATUS      current
    DESCRIPTION "QueueingTransmitOctets Historical PM of traffic class - 6 (TC6) on PxmNwIntf"
    ::= { pxmTC6NwIntfPmEntry  12 }

-- TC6 Real
pxmTC6NwIntfPmRealTable OBJECT-TYPE
    SYNTAX      SEQUENCE OF PxmTC6NwIntfPmRealEntry
    MAX-ACCESS  not-accessible
    STATUS      current
    DESCRIPTION
        "A list of PxmBwpNwIntfPmReal entries. Each entry is uniquely identified by the value of ifIndex."
    ::= { pxmCmNwIntfRealPm 4 } 

pxmTC6NwIntfPmRealEntry  OBJECT-TYPE
    SYNTAX      PxmTC6NwIntfPmRealEntry
    MAX-ACCESS  not-accessible
    STATUS      current
    DESCRIPTION
        "A PxmTC0NwIntfPm entry containing real-time performance information pertaining to Infinera PxmNwIntfPm interfaces.
        This table is a subclass of IfCommon. Entries will exist in this table only for interfaces of
        type PxmNwIntfPm."
    INDEX { ifIndex }
    ::= { pxmTC6NwIntfPmRealTable 1 }

PxmTC6NwIntfPmRealEntry  ::= SEQUENCE {
    pxmTC6NwIntfPmRealTCNum                     Integer32,
    pxmTC6NwIntfPmRealTDQueuingCurrentQDepth    Integer32,
    pxmTC6NwIntfPmRealQueueingDiscardOctets     Counter64,
    pxmTC6NwIntfPmRealQueueingDiscardPkts       Integer32,
    pxmTC6NwIntfPmRealRandomGreenDropPkts       Counter64,
    pxmTC6NwIntfPmRealRandomGreenDropOctets     Counter64,
    pxmTC6NwIntfPmRealRandomYellowDropPkts      Counter64,
    pxmTC6NwIntfPmRealRandomYellowDropOctets    Counter64,
    pxmTC6NwIntfPmRealQueueingTransmitPkts      Counter64,
    pxmTC6NwIntfPmRealQueueingTransmitOctets    Counter64,
    pxmTC6NwIntfPmRealQueueingMeanQSizeUnit     Integer32,
    pxmTC6NwIntfPmRealMeanQSize                 Integer32
}

pxmTC6NwIntfPmRealTCNum OBJECT-TYPE
    SYNTAX      Integer32
    MAX-ACCESS  read-only
    STATUS      current
    DESCRIPTION "TCNum Real PM of traffic class - 6 (TC6) on PxmNwIntf"
    ::= { pxmTC6NwIntfPmRealEntry  1 }

pxmTC6NwIntfPmRealTDQueuingCurrentQDepth OBJECT-TYPE
    SYNTAX      Integer32
    MAX-ACCESS  read-only
    STATUS      current
    DESCRIPTION "TDQueuingCurrentQDepth Real PM of traffic class - 6 (TC6) on PxmNwIntf"
    ::= { pxmTC6NwIntfPmRealEntry  2 }

pxmTC6NwIntfPmRealQueueingDiscardOctets OBJECT-TYPE
    SYNTAX      Counter64
    MAX-ACCESS  read-only
    STATUS      current
    DESCRIPTION "QueueingDiscardOctets Real PM of traffic class - 6 (TC6) on PxmNwIntf"
    ::= { pxmTC6NwIntfPmRealEntry  3 }

pxmTC6NwIntfPmRealQueueingDiscardPkts OBJECT-TYPE
    SYNTAX      Integer32
    MAX-ACCESS  read-only
    STATUS      current
    DESCRIPTION "QueueingDiscardPkts Real PM of traffic class - 6 (TC6) on PxmNwIntf"
    ::= { pxmTC6NwIntfPmRealEntry  4 }

pxmTC6NwIntfPmRealRandomGreenDropPkts OBJECT-TYPE
    SYNTAX      Counter64
    MAX-ACCESS  read-only
    STATUS      current
    DESCRIPTION "RandomGreenDropPkts Real PM of traffic class - 6 (TC6) on PxmNwIntf"
    ::= { pxmTC6NwIntfPmRealEntry  5 }

pxmTC6NwIntfPmRealRandomGreenDropOctets OBJECT-TYPE
    SYNTAX      Counter64
    MAX-ACCESS  read-only
    STATUS      current
    DESCRIPTION "RandomGreenDropOctets Real PM of traffic class - 6 (TC6) on PxmNwIntf"
    ::= { pxmTC6NwIntfPmRealEntry  6 }

pxmTC6NwIntfPmRealRandomYellowDropPkts OBJECT-TYPE
    SYNTAX      Counter64
    MAX-ACCESS  read-only
    STATUS      current
    DESCRIPTION "RandomYellowDropPkts Real PM of traffic class - 6 (TC6) on PxmNwIntf"
    ::= { pxmTC6NwIntfPmRealEntry  7 }

pxmTC6NwIntfPmRealRandomYellowDropOctets OBJECT-TYPE
    SYNTAX      Counter64
    MAX-ACCESS  read-only
    STATUS      current
    DESCRIPTION "RandomYellowDropOctets Real PM of traffic class - 6 (TC6) on PxmNwIntf"
    ::= { pxmTC6NwIntfPmRealEntry  8 }

pxmTC6NwIntfPmRealQueueingTransmitPkts OBJECT-TYPE
    SYNTAX      Counter64
    MAX-ACCESS  read-only
    STATUS      current
    DESCRIPTION "QueueingTransmitPkts Real PM of traffic class - 6 (TC6) on PxmNwIntf"
    ::= { pxmTC6NwIntfPmRealEntry  9 }

pxmTC6NwIntfPmRealQueueingTransmitOctets OBJECT-TYPE
    SYNTAX      Counter64
    MAX-ACCESS  read-only
    STATUS      current
    DESCRIPTION "QueueingTransmitOctets Real PM of traffic class - 6 (TC6) on PxmNwIntf"
    ::= { pxmTC6NwIntfPmRealEntry  10 }

pxmTC6NwIntfPmRealQueueingMeanQSizeUnit OBJECT-TYPE
    SYNTAX      Integer32
    MAX-ACCESS  read-only
    STATUS      current
    DESCRIPTION "QueueingMeanQSizeUnit Real PM of traffic class - 6 (TC6) on PxmNwIntf"
    ::= { pxmTC6NwIntfPmRealEntry  11 }

pxmTC6NwIntfPmRealMeanQSize OBJECT-TYPE
    SYNTAX      Integer32
    MAX-ACCESS  read-only
    STATUS      current
    DESCRIPTION "MeanQSize Real PM of traffic class - 6 (TC6) on PxmNwIntf"
    ::= { pxmTC6NwIntfPmRealEntry  12 }

-- TC7 Historical
pxmTC7NwIntfPmTable OBJECT-TYPE
    SYNTAX      SEQUENCE OF PxmTC7NwIntfPmEntry
    MAX-ACCESS  not-accessible
    STATUS      current
    DESCRIPTION
        "A list of PxmBwpNwIntfPmReal entries. Each entry is uniquely identified by the value of ifIndex."
    ::= { pxmCmNwIntfPm 5 } 

pxmTC7NwIntfPmEntry  OBJECT-TYPE
    SYNTAX      PxmTC7NwIntfPmEntry
    MAX-ACCESS  not-accessible
    STATUS      current
    DESCRIPTION ""
    INDEX { ifIndex, pxmTC7NwIntfPmSampleDuration, pxmTC7NwIntfPmTimestamp }
    ::= { pxmTC7NwIntfPmTable 1 }

PxmTC7NwIntfPmEntry  ::= SEQUENCE {
    pxmTC7NwIntfPmTimestamp                 Integer32,
    pxmTC7NwIntfPmSampleDuration            INTEGER,
    pxmTC7NwIntfPmValidity                  TruthValue,
    pxmTC7NwIntfPmTCNum                     Integer32,
    pxmTC7NwIntfPmQueueingDiscardOctets     Counter64,
    pxmTC7NwIntfPmQueueingDiscardPkts       Integer32,
    pxmTC7NwIntfPmRandomGreenDropPkts       Counter64,
    pxmTC7NwIntfPmRandomGreenDropOctets     Counter64,
    pxmTC7NwIntfPmRandomYellowDropPkts      Counter64,
    pxmTC7NwIntfPmRandomYellowDropOctets    Counter64,
    pxmTC7NwIntfPmQueueingTransmitPkts      Counter64,
    pxmTC7NwIntfPmQueueingTransmitOctets    Counter64
}

pxmTC7NwIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC7NwIntfPmEntry  1 }

pxmTC7NwIntfPmSampleDuration OBJECT-TYPE
    SYNTAX      INTEGER {
                    fifteenMinutes(1),
                    day(2)
                }
    MAX-ACCESS  not-accessible
    STATUS      current
    DESCRIPTION
        "The duration of this sample."
    ::= { pxmTC7NwIntfPmEntry  2 }

pxmTC7NwIntfPmValidity OBJECT-TYPE
    SYNTAX      TruthValue
    MAX-ACCESS  read-only
    STATUS      current
    DESCRIPTION "Flag indicating if data was valid for the entire interval"
    ::= { pxmTC7NwIntfPmEntry  3 }

pxmTC7NwIntfPmTCNum OBJECT-TYPE
    SYNTAX      Integer32
    MAX-ACCESS  read-only
    STATUS      current
    DESCRIPTION "TCNum Historical PM of traffic class - 7 (TC7) on PxmNwIntf"
    ::= { pxmTC7NwIntfPmEntry  4 }

pxmTC7NwIntfPmQueueingDiscardOctets OBJECT-TYPE
    SYNTAX      Counter64
    MAX-ACCESS  read-only
    STATUS      current
    DESCRIPTION "QueueingDiscardOctets Historical PM of traffic class - 7 (TC7) on PxmNwIntf"
    ::= { pxmTC7NwIntfPmEntry  5 }

pxmTC7NwIntfPmQueueingDiscardPkts OBJECT-TYPE
    SYNTAX      Integer32
    MAX-ACCESS  read-only
    STATUS      current
    DESCRIPTION "QueueingDiscardPkts Historical PM of traffic class - 7 (TC7) on PxmNwIntf"
    ::= { pxmTC7NwIntfPmEntry  6 }

pxmTC7NwIntfPmRandomGreenDropPkts OBJECT-TYPE
    SYNTAX      Counter64
    MAX-ACCESS  read-only
    STATUS      current
    DESCRIPTION "RandomGreenDropPkts Historical PM of traffic class - 7 (TC7) on PxmNwIntf"
    ::= { pxmTC7NwIntfPmEntry  7 }

pxmTC7NwIntfPmRandomGreenDropOctets OBJECT-TYPE
    SYNTAX      Counter64
    MAX-ACCESS  read-only
    STATUS      current
    DESCRIPTION "RandomGreenDropOctets Historical PM of traffic class - 7 (TC7) on PxmNwIntf"
    ::= { pxmTC7NwIntfPmEntry  8 }

pxmTC7NwIntfPmRandomYellowDropPkts OBJECT-TYPE
    SYNTAX      Counter64
    MAX-ACCESS  read-only
    STATUS      current
    DESCRIPTION "RandomYellowDropPkts Historical PM of traffic class - 7 (TC7) on PxmNwIntf"
    ::= { pxmTC7NwIntfPmEntry  9 }

pxmTC7NwIntfPmRandomYellowDropOctets OBJECT-TYPE
    SYNTAX      Counter64
    MAX-ACCESS  read-only
    STATUS      current
    DESCRIPTION "RandomYellowDropOctets Historical PM of traffic class - 7 (TC7) on PxmNwIntf"
    ::= { pxmTC7NwIntfPmEntry  10 }

pxmTC7NwIntfPmQueueingTransmitPkts OBJECT-TYPE
    SYNTAX      Counter64
    MAX-ACCESS  read-only
    STATUS      current
    DESCRIPTION "QueueingTransmitPkts Historical PM of traffic class - 7 (TC7) on PxmNwIntf"
    ::= { pxmTC7NwIntfPmEntry  11 }

pxmTC7NwIntfPmQueueingTransmitOctets OBJECT-TYPE
    SYNTAX      Counter64
    MAX-ACCESS  read-only
    STATUS      current
    DESCRIPTION "QueueingTransmitOctets Historical PM of traffic class - 7 (TC7) on PxmNwIntf"
    ::= { pxmTC7NwIntfPmEntry  12 }

-- TC7 Real
pxmTC7NwIntfPmRealTable OBJECT-TYPE
    SYNTAX      SEQUENCE OF PxmTC7NwIntfPmRealEntry
    MAX-ACCESS  not-accessible
    STATUS      current
    DESCRIPTION
        "A list of PxmBwpNwIntfPmReal entries. Each entry is uniquely identified by the value of ifIndex."
    ::= { pxmCmNwIntfRealPm 5 } 

pxmTC7NwIntfPmRealEntry  OBJECT-TYPE
    SYNTAX      PxmTC7NwIntfPmRealEntry
    MAX-ACCESS  not-accessible
    STATUS      current
    DESCRIPTION
        "A PxmTC0NwIntfPm entry containing real-time performance information pertaining to Infinera PxmNwIntfPm interfaces.
        This table is a subclass of IfCommon. Entries will exist in this table only for interfaces of
        type PxmNwIntfPm."
    INDEX { ifIndex }
    ::= { pxmTC7NwIntfPmRealTable 1 }

PxmTC7NwIntfPmRealEntry  ::= SEQUENCE {
    pxmTC7NwIntfPmRealTCNum                     Integer32,
    pxmTC7NwIntfPmRealTDQueuingCurrentQDepth    Integer32,
    pxmTC7NwIntfPmRealQueueingDiscardOctets     Counter64,
    pxmTC7NwIntfPmRealQueueingDiscardPkts       Integer32,
    pxmTC7NwIntfPmRealRandomGreenDropPkts       Counter64,
    pxmTC7NwIntfPmRealRandomGreenDropOctets     Counter64,
    pxmTC7NwIntfPmRealRandomYellowDropPkts      Counter64,
    pxmTC7NwIntfPmRealRandomYellowDropOctets    Counter64,
    pxmTC7NwIntfPmRealQueueingTransmitPkts      Counter64,
    pxmTC7NwIntfPmRealQueueingTransmitOctets    Counter64,
    pxmTC7NwIntfPmRealQueueingMeanQSizeUnit     Integer32,
    pxmTC7NwIntfPmRealMeanQSize                 Integer32
}

pxmTC7NwIntfPmRealTCNum OBJECT-TYPE
    SYNTAX      Integer32
    MAX-ACCESS  read-only
    STATUS      current
    DESCRIPTION "TCNum Real PM of traffic class - 7 (TC7) on PxmNwIntf"
    ::= { pxmTC7NwIntfPmRealEntry  1 }

pxmTC7NwIntfPmRealTDQueuingCurrentQDepth OBJECT-TYPE
    SYNTAX      Integer32
    MAX-ACCESS  read-only
    STATUS      current
    DESCRIPTION "TDQueuingCurrentQDepth Real PM of traffic class - 7 (TC7) on PxmNwIntf"
    ::= { pxmTC7NwIntfPmRealEntry  2 }

pxmTC7NwIntfPmRealQueueingDiscardOctets OBJECT-TYPE
    SYNTAX      Counter64
    MAX-ACCESS  read-only
    STATUS      current
    DESCRIPTION "QueueingDiscardOctets Real PM of traffic class - 7 (TC7) on PxmNwIntf"
    ::= { pxmTC7NwIntfPmRealEntry  3 }

pxmTC7NwIntfPmRealQueueingDiscardPkts OBJECT-TYPE
    SYNTAX      Integer32
    MAX-ACCESS  read-only
    STATUS      current
    DESCRIPTION "QueueingDiscardPkts Real PM of traffic class - 7 (TC7) on PxmNwIntf"
    ::= { pxmTC7NwIntfPmRealEntry  4 }

pxmTC7NwIntfPmRealRandomGreenDropPkts OBJECT-TYPE
    SYNTAX      Counter64
    MAX-ACCESS  read-only
    STATUS      current
    DESCRIPTION "RandomGreenDropPkts Real PM of traffic class - 7 (TC7) on PxmNwIntf"
    ::= { pxmTC7NwIntfPmRealEntry  5 }

pxmTC7NwIntfPmRealRandomGreenDropOctets OBJECT-TYPE
    SYNTAX      Counter64
    MAX-ACCESS  read-only
    STATUS      current
    DESCRIPTION "RandomGreenDropOctets Real PM of traffic class - 7 (TC7) on PxmNwIntf"
    ::= { pxmTC7NwIntfPmRealEntry  6 }

pxmTC7NwIntfPmRealRandomYellowDropPkts OBJECT-TYPE
    SYNTAX      Counter64
    MAX-ACCESS  read-only
    STATUS      current
    DESCRIPTION "RandomYellowDropPkts Real PM of traffic class - 7 (TC7) on PxmNwIntf"
    ::= { pxmTC7NwIntfPmRealEntry  7 }

pxmTC7NwIntfPmRealRandomYellowDropOctets OBJECT-TYPE
    SYNTAX      Counter64
    MAX-ACCESS  read-only
    STATUS      current
    DESCRIPTION "RandomYellowDropOctets Real PM of traffic class - 7 (TC7) on PxmNwIntf"
    ::= { pxmTC7NwIntfPmRealEntry  8 }

pxmTC7NwIntfPmRealQueueingTransmitPkts OBJECT-TYPE
    SYNTAX      Counter64
    MAX-ACCESS  read-only
    STATUS      current
    DESCRIPTION "QueueingTransmitPkts Real PM of traffic class - 7 (TC7) on PxmNwIntf"
    ::= { pxmTC7NwIntfPmRealEntry  9 }

pxmTC7NwIntfPmRealQueueingTransmitOctets OBJECT-TYPE
    SYNTAX      Counter64
    MAX-ACCESS  read-only
    STATUS      current
    DESCRIPTION "QueueingTransmitOctets Real PM of traffic class - 7 (TC7) on PxmNwIntf"
    ::= { pxmTC7NwIntfPmRealEntry  10 }

pxmTC7NwIntfPmRealQueueingMeanQSizeUnit OBJECT-TYPE
    SYNTAX      Integer32
    MAX-ACCESS  read-only
    STATUS      current
    DESCRIPTION "QueueingMeanQSizeUnit Real PM of traffic class - 7 (TC7) on PxmNwIntf"
    ::= { pxmTC7NwIntfPmRealEntry  11 }

pxmTC7NwIntfPmRealMeanQSize OBJECT-TYPE
    SYNTAX      Integer32
    MAX-ACCESS  read-only
    STATUS      current
    DESCRIPTION "MeanQSize Real PM of traffic class - 7 (TC7) on PxmNwIntf"
    ::= { pxmTC7NwIntfPmRealEntry  12 }

-- TCANY Historical
pxmTCANYNwIntfPmTable OBJECT-TYPE
    SYNTAX      SEQUENCE OF PxmTCANYNwIntfPmEntry
    MAX-ACCESS  not-accessible
    STATUS      current
    DESCRIPTION
        "A list of PxmBwpNwIntfPmReal entries. Each entry is uniquely identified by the value of ifIndex."
    ::= { pxmCmNwIntfPm 6 } 

pxmTCANYNwIntfPmEntry  OBJECT-TYPE
    SYNTAX      PxmTCANYNwIntfPmEntry
    MAX-ACCESS  not-accessible
    STATUS      current
    DESCRIPTION ""
    INDEX { ifIndex, pxmTCANYNwIntfPmSampleDuration, pxmTCANYNwIntfPmTimestamp }
    ::= { pxmTCANYNwIntfPmTable 1 }

PxmTCANYNwIntfPmEntry  ::= SEQUENCE {
    pxmTCANYNwIntfPmTimestamp                 Integer32,
    pxmTCANYNwIntfPmSampleDuration            INTEGER,
    pxmTCANYNwIntfPmValidity                  TruthValue,
    pxmTCANYNwIntfPmTCNum                     Integer32,
    pxmTCANYNwIntfPmQueueingDiscardOctets     Counter64,
    pxmTCANYNwIntfPmQueueingDiscardPkts       Integer32,
    pxmTCANYNwIntfPmRandomGreenDropPkts       Counter64,
    pxmTCANYNwIntfPmRandomGreenDropOctets     Counter64,
    pxmTCANYNwIntfPmRandomYellowDropPkts      Counter64,
    pxmTCANYNwIntfPmRandomYellowDropOctets    Counter64,
    pxmTCANYNwIntfPmQueueingTransmitPkts      Counter64,
    pxmTCANYNwIntfPmQueueingTransmitOctets    Counter64
}

pxmTCANYNwIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTCANYNwIntfPmEntry  1 }

pxmTCANYNwIntfPmSampleDuration OBJECT-TYPE
    SYNTAX      INTEGER {
                    fifteenMinutes(1),
                    day(2)
                }
    MAX-ACCESS  not-accessible
    STATUS      current
    DESCRIPTION
        "The duration of this sample."
    ::= { pxmTCANYNwIntfPmEntry  2 }

pxmTCANYNwIntfPmValidity OBJECT-TYPE
    SYNTAX      TruthValue
    MAX-ACCESS  read-only
    STATUS      current
    DESCRIPTION "Flag indicating if data was valid for the entire interval"
    ::= { pxmTCANYNwIntfPmEntry  3 }

pxmTCANYNwIntfPmTCNum OBJECT-TYPE
    SYNTAX      Integer32
    MAX-ACCESS  read-only
    STATUS      current
    DESCRIPTION "TCNum Historical PM of traffic class - ANY (TCANY) on PxmNwIntf"
    ::= { pxmTCANYNwIntfPmEntry  4 }

pxmTCANYNwIntfPmQueueingDiscardOctets OBJECT-TYPE
    SYNTAX      Counter64
    MAX-ACCESS  read-only
    STATUS      current
    DESCRIPTION "QueueingDiscardOctets Historical PM of traffic class - ANY (TCANY) on PxmNwIntf"
    ::= { pxmTCANYNwIntfPmEntry  5 }

pxmTCANYNwIntfPmQueueingDiscardPkts OBJECT-TYPE
    SYNTAX      Integer32
    MAX-ACCESS  read-only
    STATUS      current
    DESCRIPTION "QueueingDiscardPkts Historical PM of traffic class - ANY (TCANY) on PxmNwIntf"
    ::= { pxmTCANYNwIntfPmEntry  6 }

pxmTCANYNwIntfPmRandomGreenDropPkts OBJECT-TYPE
    SYNTAX      Counter64
    MAX-ACCESS  read-only
    STATUS      current
    DESCRIPTION "RandomGreenDropPkts Historical PM of traffic class - ANY (TCANY) on PxmNwIntf"
    ::= { pxmTCANYNwIntfPmEntry  7 }

pxmTCANYNwIntfPmRandomGreenDropOctets OBJECT-TYPE
    SYNTAX      Counter64
    MAX-ACCESS  read-only
    STATUS      current
    DESCRIPTION "RandomGreenDropOctets Historical PM of traffic class - ANY (TCANY) on PxmNwIntf"
    ::= { pxmTCANYNwIntfPmEntry  8 }

pxmTCANYNwIntfPmRandomYellowDropPkts OBJECT-TYPE
    SYNTAX      Counter64
    MAX-ACCESS  read-only
    STATUS      current
    DESCRIPTION "RandomYellowDropPkts Historical PM of traffic class - ANY (TCANY) on PxmNwIntf"
    ::= { pxmTCANYNwIntfPmEntry  9 }

pxmTCANYNwIntfPmRandomYellowDropOctets OBJECT-TYPE
    SYNTAX      Counter64
    MAX-ACCESS  read-only
    STATUS      current
    DESCRIPTION "RandomYellowDropOctets Historical PM of traffic class - ANY (TCANY) on PxmNwIntf"
    ::= { pxmTCANYNwIntfPmEntry  10 }

pxmTCANYNwIntfPmQueueingTransmitPkts OBJECT-TYPE
    SYNTAX      Counter64
    MAX-ACCESS  read-only
    STATUS      current
    DESCRIPTION "QueueingTransmitPkts Historical PM of traffic class - ANY (TCANY) on PxmNwIntf"
    ::= { pxmTCANYNwIntfPmEntry  11 }

pxmTCANYNwIntfPmQueueingTransmitOctets OBJECT-TYPE
    SYNTAX      Counter64
    MAX-ACCESS  read-only
    STATUS      current
    DESCRIPTION "QueueingTransmitOctets Historical PM of traffic class - ANY (TCANY) on PxmNwIntf"
    ::= { pxmTCANYNwIntfPmEntry  12 }

-- TCANY Real
pxmTCANYNwIntfPmRealTable OBJECT-TYPE
    SYNTAX      SEQUENCE OF PxmTCANYNwIntfPmRealEntry
    MAX-ACCESS  not-accessible
    STATUS      current
    DESCRIPTION
        "A list of PxmBwpNwIntfPmReal entries. Each entry is uniquely identified by the value of ifIndex."
    ::= { pxmCmNwIntfRealPm 6 } 

pxmTCANYNwIntfPmRealEntry  OBJECT-TYPE
    SYNTAX      PxmTCANYNwIntfPmRealEntry
    MAX-ACCESS  not-accessible
    STATUS      current
    DESCRIPTION
        "A PxmTC0NwIntfPm entry containing real-time performance information pertaining to Infinera PxmNwIntfPm interfaces.
        This table is a subclass of IfCommon. Entries will exist in this table only for interfaces of
        type PxmNwIntfPm."
    INDEX { ifIndex }
    ::= { pxmTCANYNwIntfPmRealTable 1 }

PxmTCANYNwIntfPmRealEntry  ::= SEQUENCE {
    pxmTCANYNwIntfPmRealTCNum                     Integer32,
    pxmTCANYNwIntfPmRealTDQueuingCurrentQDepth    Integer32,
    pxmTCANYNwIntfPmRealQueueingDiscardOctets     Counter64,
    pxmTCANYNwIntfPmRealQueueingDiscardPkts       Integer32,
    pxmTCANYNwIntfPmRealRandomGreenDropPkts       Counter64,
    pxmTCANYNwIntfPmRealRandomGreenDropOctets     Counter64,
    pxmTCANYNwIntfPmRealRandomYellowDropPkts      Counter64,
    pxmTCANYNwIntfPmRealRandomYellowDropOctets    Counter64,
    pxmTCANYNwIntfPmRealQueueingTransmitPkts      Counter64,
    pxmTCANYNwIntfPmRealQueueingTransmitOctets    Counter64,
    pxmTCANYNwIntfPmRealQueueingMeanQSizeUnit     Integer32,
    pxmTCANYNwIntfPmRealMeanQSize                 Integer32
}

pxmTCANYNwIntfPmRealTCNum OBJECT-TYPE
    SYNTAX      Integer32
    MAX-ACCESS  read-only
    STATUS      current
    DESCRIPTION "TCNum Real PM of traffic class - ANY (TCANY) on PxmNwIntf"
    ::= { pxmTCANYNwIntfPmRealEntry  1 }

pxmTCANYNwIntfPmRealTDQueuingCurrentQDepth OBJECT-TYPE
    SYNTAX      Integer32
    MAX-ACCESS  read-only
    STATUS      current
    DESCRIPTION "TDQueuingCurrentQDepth Real PM of traffic class - ANY (TCANY) on PxmNwIntf"
    ::= { pxmTCANYNwIntfPmRealEntry  2 }

pxmTCANYNwIntfPmRealQueueingDiscardOctets OBJECT-TYPE
    SYNTAX      Counter64
    MAX-ACCESS  read-only
    STATUS      current
    DESCRIPTION "QueueingDiscardOctets Real PM of traffic class - ANY (TCANY) on PxmNwIntf"
    ::= { pxmTCANYNwIntfPmRealEntry  3 }

pxmTCANYNwIntfPmRealQueueingDiscardPkts OBJECT-TYPE
    SYNTAX      Integer32
    MAX-ACCESS  read-only
    STATUS      current
    DESCRIPTION "QueueingDiscardPkts Real PM of traffic class - ANY (TCANY) on PxmNwIntf"
    ::= { pxmTCANYNwIntfPmRealEntry  4 }

pxmTCANYNwIntfPmRealRandomGreenDropPkts OBJECT-TYPE
    SYNTAX      Counter64
    MAX-ACCESS  read-only
    STATUS      current
    DESCRIPTION "RandomGreenDropPkts Real PM of traffic class - ANY (TCANY) on PxmNwIntf"
    ::= { pxmTCANYNwIntfPmRealEntry  5 }

pxmTCANYNwIntfPmRealRandomGreenDropOctets OBJECT-TYPE
    SYNTAX      Counter64
    MAX-ACCESS  read-only
    STATUS      current
    DESCRIPTION "RandomGreenDropOctets Real PM of traffic class - ANY (TCANY) on PxmNwIntf"
    ::= { pxmTCANYNwIntfPmRealEntry  6 }

pxmTCANYNwIntfPmRealRandomYellowDropPkts OBJECT-TYPE
    SYNTAX      Counter64
    MAX-ACCESS  read-only
    STATUS      current
    DESCRIPTION "RandomYellowDropPkts Real PM of traffic class - ANY (TCANY) on PxmNwIntf"
    ::= { pxmTCANYNwIntfPmRealEntry  7 }

pxmTCANYNwIntfPmRealRandomYellowDropOctets OBJECT-TYPE
    SYNTAX      Counter64
    MAX-ACCESS  read-only
    STATUS      current
    DESCRIPTION "RandomYellowDropOctets Real PM of traffic class - ANY (TCANY) on PxmNwIntf"
    ::= { pxmTCANYNwIntfPmRealEntry  8 }

pxmTCANYNwIntfPmRealQueueingTransmitPkts OBJECT-TYPE
    SYNTAX      Counter64
    MAX-ACCESS  read-only
    STATUS      current
    DESCRIPTION "QueueingTransmitPkts Real PM of traffic class - ANY (TCANY) on PxmNwIntf"
    ::= { pxmTCANYNwIntfPmRealEntry  9 }

pxmTCANYNwIntfPmRealQueueingTransmitOctets OBJECT-TYPE
    SYNTAX      Counter64
    MAX-ACCESS  read-only
    STATUS      current
    DESCRIPTION "QueueingTransmitOctets Real PM of traffic class - ANY (TCANY) on PxmNwIntf"
    ::= { pxmTCANYNwIntfPmRealEntry  10 }

pxmTCANYNwIntfPmRealQueueingMeanQSizeUnit OBJECT-TYPE
    SYNTAX      Integer32
    MAX-ACCESS  read-only
    STATUS      current
    DESCRIPTION "QueueingMeanQSizeUnit Real PM of traffic class - ANY (TCANY) on PxmNwIntf"
    ::= { pxmTCANYNwIntfPmRealEntry  11 }

pxmTCANYNwIntfPmRealMeanQSize OBJECT-TYPE
    SYNTAX      Integer32
    MAX-ACCESS  read-only
    STATUS      current
    DESCRIPTION "MeanQSize Real PM of traffic class - ANY (TCANY) on PxmNwIntf"
    ::= { pxmTCANYNwIntfPmRealEntry  12 }

-- End of CM PMs
    
-- Conformance Statements
pxmNwIntfPmConformance    OBJECT IDENTIFIER ::= { pxmNwIntfPmMIB 3 }
pxmNwIntfPmCompliances    OBJECT IDENTIFIER ::= { pxmNwIntfPmConformance 1 }
pxmNwIntfPmGroups         OBJECT IDENTIFIER ::= { pxmNwIntfPmConformance 2 }

pxmNwIntfPmCompliance MODULE-COMPLIANCE
    STATUS current
    DESCRIPTION
        "Describes the requirements for conformance to the PM-PXMNWINTF-MIB"
    MODULE
    MANDATORY-GROUPS { pxmNwIntfPmGroup }
    ::= { pxmNwIntfPmCompliances 1 }

pxmNwIntfPmRealCompliance MODULE-COMPLIANCE
    STATUS current
    DESCRIPTION
        "Describes the requirements for conformance to the pxmNwIntfPmReal-MIB"
    MODULE
    MANDATORY-GROUPS { pxmNwIntfPmRealGroup }
    ::= { pxmNwIntfPmCompliances 2 }

pxmNwIntfPmGroup OBJECT-GROUP
    OBJECTS {
        pxmNwIntfPmValidity,
        pxmNwIntfPmRxPackets,
        pxmNwIntfPmTxPackets,
        pxmNwIntfPmRxOctets,
        pxmNwIntfPmTxOctets             
    }
    STATUS current
    DESCRIPTION
        " A collection of objects for reading the performance of the pxmNwIntf."
    ::= { pxmNwIntfPmGroups 1 }


pxmNwIntfPmRealGroup OBJECT-GROUP
    OBJECTS {
        pxmNwIntfPmRealRxPackets,
        pxmNwIntfPmRealTxPackets,
        pxmNwIntfPmRealRxOctets,
        pxmNwIntfPmRealTxOctets,
        pxmNwIntfPmRealRxLU,
        pxmNwIntfPmRealTxLU   
    }
    STATUS current
    DESCRIPTION
        " A collection of objects for reading the real-time performance of the pxmNwIntf."
    ::= { pxmNwIntfPmGroups 2 }

pxmTC0NwIntfPmGroup OBJECT-GROUP
    OBJECTS {
        pxmTC0NwIntfPmValidity,
        pxmTC0NwIntfPmTCNum,
        pxmTC0NwIntfPmQueueingDiscardOctets,
        pxmTC0NwIntfPmQueueingDiscardPkts,
        pxmTC0NwIntfPmRandomGreenDropPkts,
        pxmTC0NwIntfPmRandomGreenDropOctets,
        pxmTC0NwIntfPmRandomYellowDropPkts,
        pxmTC0NwIntfPmRandomYellowDropOctets,
        pxmTC0NwIntfPmQueueingTransmitPkts,
        pxmTC0NwIntfPmQueueingTransmitOctets
    }
    STATUS current
    DESCRIPTION
        " A collection of objects for reading the real-time performance of the pxmNwIntf."
    ::= { pxmNwIntfPmGroups 3 }

pxmTC0NwIntfPmRealGroup OBJECT-GROUP
    OBJECTS {
        pxmTC0NwIntfPmRealTCNum,
        pxmTC0NwIntfPmRealTDQueuingCurrentQDepth,
        pxmTC0NwIntfPmRealQueueingDiscardOctets,
        pxmTC0NwIntfPmRealQueueingDiscardPkts,
        pxmTC0NwIntfPmRealRandomGreenDropPkts,
        pxmTC0NwIntfPmRealRandomGreenDropOctets,
        pxmTC0NwIntfPmRealRandomYellowDropPkts,
        pxmTC0NwIntfPmRealRandomYellowDropOctets,
        pxmTC0NwIntfPmRealQueueingTransmitPkts,
        pxmTC0NwIntfPmRealQueueingTransmitOctets,
        pxmTC0NwIntfPmRealQueueingMeanQSizeUnit,
        pxmTC0NwIntfPmRealMeanQSize
    }
    STATUS current
    DESCRIPTION
        " A collection of objects for reading the real-time performance of the pxmNwIntf."
    ::= { pxmNwIntfPmGroups 4 }

pxmTC2NwIntfPmGroup OBJECT-GROUP
    OBJECTS {
        pxmTC2NwIntfPmValidity,
        pxmTC2NwIntfPmTCNum,
        pxmTC2NwIntfPmQueueingDiscardOctets,
        pxmTC2NwIntfPmQueueingDiscardPkts,
        pxmTC2NwIntfPmRandomGreenDropPkts,
        pxmTC2NwIntfPmRandomGreenDropOctets,
        pxmTC2NwIntfPmRandomYellowDropPkts,
        pxmTC2NwIntfPmRandomYellowDropOctets,
        pxmTC2NwIntfPmQueueingTransmitPkts,
        pxmTC2NwIntfPmQueueingTransmitOctets
    }
    STATUS current
    DESCRIPTION
        " A collection of objects for reading the real-time performance of the pxmNwIntf."
    ::= { pxmNwIntfPmGroups 5 }

pxmTC2NwIntfPmRealGroup OBJECT-GROUP
    OBJECTS {
        pxmTC2NwIntfPmRealTCNum,
        pxmTC2NwIntfPmRealTDQueuingCurrentQDepth,
        pxmTC2NwIntfPmRealQueueingDiscardOctets,
        pxmTC2NwIntfPmRealQueueingDiscardPkts,
        pxmTC2NwIntfPmRealRandomGreenDropPkts,
        pxmTC2NwIntfPmRealRandomGreenDropOctets,
        pxmTC2NwIntfPmRealRandomYellowDropPkts,
        pxmTC2NwIntfPmRealRandomYellowDropOctets,
        pxmTC2NwIntfPmRealQueueingTransmitPkts,
        pxmTC2NwIntfPmRealQueueingTransmitOctets,
        pxmTC2NwIntfPmRealQueueingMeanQSizeUnit,
        pxmTC2NwIntfPmRealMeanQSize
    }
    STATUS current
    DESCRIPTION
        " A collection of objects for reading the real-time performance of the pxmNwIntf."
    ::= { pxmNwIntfPmGroups 6 }

pxmTC4NwIntfPmGroup OBJECT-GROUP
    OBJECTS {
        pxmTC4NwIntfPmValidity,
        pxmTC4NwIntfPmTCNum,
        pxmTC4NwIntfPmQueueingDiscardOctets,
        pxmTC4NwIntfPmQueueingDiscardPkts,
        pxmTC4NwIntfPmRandomGreenDropPkts,
        pxmTC4NwIntfPmRandomGreenDropOctets,
        pxmTC4NwIntfPmRandomYellowDropPkts,
        pxmTC4NwIntfPmRandomYellowDropOctets,
        pxmTC4NwIntfPmQueueingTransmitPkts,
        pxmTC4NwIntfPmQueueingTransmitOctets
    }
    STATUS current
    DESCRIPTION
        " A collection of objects for reading the real-time performance of the pxmNwIntf."
    ::= { pxmNwIntfPmGroups 7 }

pxmTC4NwIntfPmRealGroup OBJECT-GROUP
    OBJECTS {
        pxmTC4NwIntfPmRealTCNum,
        pxmTC4NwIntfPmRealTDQueuingCurrentQDepth,
        pxmTC4NwIntfPmRealQueueingDiscardOctets,
        pxmTC4NwIntfPmRealQueueingDiscardPkts,
        pxmTC4NwIntfPmRealRandomGreenDropPkts,
        pxmTC4NwIntfPmRealRandomGreenDropOctets,
        pxmTC4NwIntfPmRealRandomYellowDropPkts,
        pxmTC4NwIntfPmRealRandomYellowDropOctets,
        pxmTC4NwIntfPmRealQueueingTransmitPkts,
        pxmTC4NwIntfPmRealQueueingTransmitOctets,
        pxmTC4NwIntfPmRealQueueingMeanQSizeUnit,
        pxmTC4NwIntfPmRealMeanQSize
    }
    STATUS current
    DESCRIPTION
        " A collection of objects for reading the real-time performance of the pxmNwIntf."
    ::= { pxmNwIntfPmGroups 8 }

pxmTC6NwIntfPmGroup OBJECT-GROUP
    OBJECTS {
        pxmTC6NwIntfPmValidity,
        pxmTC6NwIntfPmTCNum,
        pxmTC6NwIntfPmQueueingDiscardOctets,
        pxmTC6NwIntfPmQueueingDiscardPkts,
        pxmTC6NwIntfPmRandomGreenDropPkts,
        pxmTC6NwIntfPmRandomGreenDropOctets,
        pxmTC6NwIntfPmRandomYellowDropPkts,
        pxmTC6NwIntfPmRandomYellowDropOctets,
        pxmTC6NwIntfPmQueueingTransmitPkts,
        pxmTC6NwIntfPmQueueingTransmitOctets
    }
    STATUS current
    DESCRIPTION
        " A collection of objects for reading the real-time performance of the pxmNwIntf."
    ::= { pxmNwIntfPmGroups 9 }

pxmTC6NwIntfPmRealGroup OBJECT-GROUP
    OBJECTS {
        pxmTC6NwIntfPmRealTCNum,
        pxmTC6NwIntfPmRealTDQueuingCurrentQDepth,
        pxmTC6NwIntfPmRealQueueingDiscardOctets,
        pxmTC6NwIntfPmRealQueueingDiscardPkts,
        pxmTC6NwIntfPmRealRandomGreenDropPkts,
        pxmTC6NwIntfPmRealRandomGreenDropOctets,
        pxmTC6NwIntfPmRealRandomYellowDropPkts,
        pxmTC6NwIntfPmRealRandomYellowDropOctets,
        pxmTC6NwIntfPmRealQueueingTransmitPkts,
        pxmTC6NwIntfPmRealQueueingTransmitOctets,
        pxmTC6NwIntfPmRealQueueingMeanQSizeUnit,
        pxmTC6NwIntfPmRealMeanQSize
    }
    STATUS current
    DESCRIPTION
        " A collection of objects for reading the real-time performance of the pxmNwIntf."
    ::= { pxmNwIntfPmGroups 10 }

pxmTC7NwIntfPmGroup OBJECT-GROUP
    OBJECTS {
        pxmTC7NwIntfPmValidity,
        pxmTC7NwIntfPmTCNum,
        pxmTC7NwIntfPmQueueingDiscardOctets,
        pxmTC7NwIntfPmQueueingDiscardPkts,
        pxmTC7NwIntfPmRandomGreenDropPkts,
        pxmTC7NwIntfPmRandomGreenDropOctets,
        pxmTC7NwIntfPmRandomYellowDropPkts,
        pxmTC7NwIntfPmRandomYellowDropOctets,
        pxmTC7NwIntfPmQueueingTransmitPkts,
        pxmTC7NwIntfPmQueueingTransmitOctets
    }
    STATUS current
    DESCRIPTION
        " A collection of objects for reading the real-time performance of the pxmNwIntf."
    ::= { pxmNwIntfPmGroups 11 }

pxmTC7NwIntfPmRealGroup OBJECT-GROUP
    OBJECTS {
        pxmTC7NwIntfPmRealTCNum,
        pxmTC7NwIntfPmRealTDQueuingCurrentQDepth,
        pxmTC7NwIntfPmRealQueueingDiscardOctets,
        pxmTC7NwIntfPmRealQueueingDiscardPkts,
        pxmTC7NwIntfPmRealRandomGreenDropPkts,
        pxmTC7NwIntfPmRealRandomGreenDropOctets,
        pxmTC7NwIntfPmRealRandomYellowDropPkts,
        pxmTC7NwIntfPmRealRandomYellowDropOctets,
        pxmTC7NwIntfPmRealQueueingTransmitPkts,
        pxmTC7NwIntfPmRealQueueingTransmitOctets,
        pxmTC7NwIntfPmRealQueueingMeanQSizeUnit,
        pxmTC7NwIntfPmRealMeanQSize
    }
    STATUS current
    DESCRIPTION
        " A collection of objects for reading the real-time performance of the pxmNwIntf."
    ::= { pxmNwIntfPmGroups 12 }

pxmTCANYNwIntfPmGroup OBJECT-GROUP
    OBJECTS {
        pxmTCANYNwIntfPmValidity,
        pxmTCANYNwIntfPmTCNum,
        pxmTCANYNwIntfPmQueueingDiscardOctets,
        pxmTCANYNwIntfPmQueueingDiscardPkts,
        pxmTCANYNwIntfPmRandomGreenDropPkts,
        pxmTCANYNwIntfPmRandomGreenDropOctets,
        pxmTCANYNwIntfPmRandomYellowDropPkts,
        pxmTCANYNwIntfPmRandomYellowDropOctets,
        pxmTCANYNwIntfPmQueueingTransmitPkts,
        pxmTCANYNwIntfPmQueueingTransmitOctets
    }
    STATUS current
    DESCRIPTION
        " A collection of objects for reading the real-time performance of the pxmNwIntf."
    ::= { pxmNwIntfPmGroups 13 }

pxmTCANYNwIntfPmRealGroup OBJECT-GROUP
    OBJECTS {
        pxmTCANYNwIntfPmRealTCNum,
        pxmTCANYNwIntfPmRealTDQueuingCurrentQDepth,
        pxmTCANYNwIntfPmRealQueueingDiscardOctets,
        pxmTCANYNwIntfPmRealQueueingDiscardPkts,
        pxmTCANYNwIntfPmRealRandomGreenDropPkts,
        pxmTCANYNwIntfPmRealRandomGreenDropOctets,
        pxmTCANYNwIntfPmRealRandomYellowDropPkts,
        pxmTCANYNwIntfPmRealRandomYellowDropOctets,
        pxmTCANYNwIntfPmRealQueueingTransmitPkts,
        pxmTCANYNwIntfPmRealQueueingTransmitOctets,
        pxmTCANYNwIntfPmRealQueueingMeanQSizeUnit,
        pxmTCANYNwIntfPmRealMeanQSize
    }
    STATUS current
    DESCRIPTION
        " A collection of objects for reading the real-time performance of the pxmNwIntf."
    ::= { pxmNwIntfPmGroups 14 }

END

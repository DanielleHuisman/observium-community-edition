-- *****************************************************************
-- INFINERA-PM-PXMPW-MIB
-- 
-- February 2015, Kavitha Manjunatha / Narendra Gupta
-- 
-- 
-- Copyright (c) 2008-2012 by Infinera Inc.
-- All rights reserved.
-- ****************************************************************

INFINERA-PM-PXMPW-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    HCPerfIntervalCount                         FROM HC-PerfHist-TC-MIB
    perfMon                                     FROM INFINERA-REG-MIB;


pxmPwPmMIB MODULE-IDENTITY
    LAST-UPDATED  "201502030000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "201502030000Z" 
    DESCRIPTION
        "First Version"
    ::= { perfMon 96 }

pxmPwRmonPm      OBJECT IDENTIFIER ::= { pxmPwPmMIB 1 }

pxmPwPmTable OBJECT-TYPE
    SYNTAX      SEQUENCE OF PxmPwPmEntry
    MAX-ACCESS  not-accessible
    STATUS      current
    DESCRIPTION
        "A list of PxmPwPm entries. Each entry is uniquely identified by the value of ifIndex, sampleDuration and pxmPwPmTimestamp."
    ::= { pxmPwRmonPm 2 } 

pxmPwPmEntry  OBJECT-TYPE
    SYNTAX      PxmPwPmEntry
    MAX-ACCESS  not-accessible
    STATUS      current
    DESCRIPTION
        "A PxmPwPm entry containing historical performance information pertaining to Infinera PxmPw interfaces.
        This table is a subclass of IfCommon.
        Entries will exist in this table only for interfaces of type PxmPw.
        Each interface may have a number of entries in this table, each with a different combination of timestamp
        and sample duration."
    INDEX { ifIndex, pxmPwPmSampleDuration, pxmPwPmTimestamp }
    ::= { pxmPwPmTable 1 }


PxmPwPmEntry  ::= SEQUENCE {
    pxmPwPmTimestamp             Integer32,
    pxmPwPmSampleDuration        INTEGER,
    pxmPwPmValidity              TruthValue,
    pxmPwPmRxPackets             HCPerfIntervalCount,
    pxmPwPmRxOctets              HCPerfIntervalCount,
    pxmPwPmTxPackets             HCPerfIntervalCount,
    pxmPwPmTxOctets              HCPerfIntervalCount
}

pxmPwPmTimestamp OBJECT-TYPE
    SYNTAX      Integer32 (0..2147483647)
    MAX-ACCESS  not-accessible
    STATUS      current
    DESCRIPTION
        "End Time stamp for this interval. If this time is later than the current time,
        then the data for this bucket is currently being collected."
    ::= { pxmPwPmEntry  1 }


pxmPwPmSampleDuration OBJECT-TYPE
    SYNTAX      INTEGER {
                    fifteenMinutes(1),
                    day(2)
                }
    MAX-ACCESS  not-accessible
    STATUS      current
    DESCRIPTION
        "The duration of this sample."
    ::= { pxmPwPmEntry  2 }


pxmPwPmValidity OBJECT-TYPE
    SYNTAX      TruthValue
    MAX-ACCESS  read-only
    STATUS      current
    DESCRIPTION "Flag indicating if data was valid for the entire interval"
    ::= { pxmPwPmEntry  3 }


pxmPwPmRxPackets OBJECT-TYPE
    SYNTAX      HCPerfIntervalCount
    MAX-ACCESS  read-only
    STATUS      current
    DESCRIPTION ""
    ::= { pxmPwPmEntry  4 }


pxmPwPmRxOctets OBJECT-TYPE
    SYNTAX      HCPerfIntervalCount
    MAX-ACCESS  read-only
    STATUS      current
    DESCRIPTION ""
    ::= { pxmPwPmEntry  5 }


pxmPwPmTxPackets OBJECT-TYPE
    SYNTAX      HCPerfIntervalCount
    MAX-ACCESS  read-only
    STATUS      current
    DESCRIPTION ""
    ::= { pxmPwPmEntry  6 }


pxmPwPmTxOctets OBJECT-TYPE
    SYNTAX      HCPerfIntervalCount
    MAX-ACCESS  read-only
    STATUS      current
    DESCRIPTION ""
    ::= { pxmPwPmEntry  7 }


pxmPwPmRealTable OBJECT-TYPE
    SYNTAX      SEQUENCE OF PxmPwPmRealEntry
    MAX-ACCESS  not-accessible
    STATUS      current
    DESCRIPTION
        "A list of PxmPwPmReal entries. Each entry is uniquely identified by the value of ifIndex."
    ::= { pxmPwRmonPm 1 } 

pxmPwPmRealEntry  OBJECT-TYPE
    SYNTAX      PxmPwPmRealEntry
    MAX-ACCESS  not-accessible
    STATUS      current
    DESCRIPTION
        "A PxmPwPm entry containing real-time performance information pertaining to Infinera PxmPw interfaces.
        This table is a subclass of IfCommon.
        Entries will exist in this table only for interfaces of type PxmPw."
    INDEX { ifIndex }
    ::= { pxmPwPmRealTable 1 }


PxmPwPmRealEntry  ::= SEQUENCE {
    pxmPwPmRealRxPackets         Counter64,
    pxmPwPmRealRxOctets          Counter64,
    pxmPwPmRealTxPackets         Counter64,
    pxmPwPmRealTxOctets          Counter64
}

pxmPwPmRealRxPackets OBJECT-TYPE
    SYNTAX      Counter64
    MAX-ACCESS  read-only
    STATUS      current
    DESCRIPTION ""
    ::= { pxmPwPmRealEntry  1 }


pxmPwPmRealRxOctets OBJECT-TYPE
    SYNTAX      Counter64
    MAX-ACCESS  read-only
    STATUS      current
    DESCRIPTION ""
    ::= { pxmPwPmRealEntry  2 }


pxmPwPmRealTxPackets OBJECT-TYPE
    SYNTAX      Counter64
    MAX-ACCESS  read-only
    STATUS      current
    DESCRIPTION ""
    ::= { pxmPwPmRealEntry  3 }


pxmPwPmRealTxOctets OBJECT-TYPE
    SYNTAX      Counter64
    MAX-ACCESS  read-only
    STATUS      current
    DESCRIPTION ""
    ::= { pxmPwPmRealEntry  4 }

-- CM Historical
pxmCmPwPmObjects      OBJECT IDENTIFIER ::= { pxmPwPmMIB 2 }

pxmCmPwRealPm         OBJECT IDENTIFIER ::= { pxmCmPwPmObjects 1 }
pxmCmPwPm             OBJECT IDENTIFIER ::= { pxmCmPwPmObjects 2 }

pxmTC0PwPmRealTable OBJECT-TYPE
    SYNTAX      SEQUENCE OF PxmTC0PwPmRealEntry
    MAX-ACCESS  not-accessible
    STATUS      current
    DESCRIPTION
        "A list of PxmBwpPwPmReal entries. Each entry is uniquely identified by the value of ifIndex."
    ::= { pxmCmPwRealPm 1 } 

pxmTC0PwPmRealEntry  OBJECT-TYPE
    SYNTAX      PxmTC0PwPmRealEntry
    MAX-ACCESS  not-accessible
    STATUS      current
    DESCRIPTION
        "A PxmTC0PwPm entry containing real-time performance information pertaining to Infinera PxmPwPm interfaces.
        This table is a subclass of IfCommon. Entries will exist in this table only for interfaces of
        type PxmPwPm."
    INDEX { ifIndex }
    ::= { pxmTC0PwPmRealTable 1 }

PxmTC0PwPmRealEntry  ::= SEQUENCE {
    pxmTC0PwPmRealTCNum                     Integer32,
    pxmTC0PwPmRealTDQueuingCurrentQDepth    Integer32,
    pxmTC0PwPmRealQueueingDiscardOctets     Counter64,
    pxmTC0PwPmRealQueueingDiscardPkts       Integer32,
    pxmTC0PwPmRealRandomGreenDropPkts       Counter64,
    pxmTC0PwPmRealRandomGreenDropOctets     Counter64,
    pxmTC0PwPmRealRandomYellowDropPkts      Counter64,
    pxmTC0PwPmRealRandomYellowDropOctets    Counter64,
    pxmTC0PwPmRealQueueingTransmitPkts      Counter64,
    pxmTC0PwPmRealQueueingTransmitOctets    Counter64,
    pxmTC0PwPmRealQueueingMeanQSizeUnit     Integer32,
    pxmTC0PwPmRealMeanQSize                 Integer32
}

pxmTC0PwPmRealTCNum OBJECT-TYPE
    SYNTAX      Integer32
    MAX-ACCESS  read-only
    STATUS      current
    DESCRIPTION "TCNum Real PM of traffic class - 0 (TC0) on PxmPW"
    ::= { pxmTC0PwPmRealEntry  1 }

pxmTC0PwPmRealTDQueuingCurrentQDepth OBJECT-TYPE
    SYNTAX      Integer32
    MAX-ACCESS  read-only
    STATUS      current
    DESCRIPTION "TDQueuingCurrentQDepth Real PM of traffic class - 0 (TC0) on PxmPW"
    ::= { pxmTC0PwPmRealEntry  2 }

pxmTC0PwPmRealQueueingDiscardOctets OBJECT-TYPE
    SYNTAX      Counter64
    MAX-ACCESS  read-only
    STATUS      current
    DESCRIPTION "QueueingDiscardOctets Real PM of traffic class - 0 (TC0) on PxmPW"
    ::= { pxmTC0PwPmRealEntry  3 }

pxmTC0PwPmRealQueueingDiscardPkts OBJECT-TYPE
    SYNTAX      Integer32
    MAX-ACCESS  read-only
    STATUS      current
    DESCRIPTION "QueueingDiscardPkts Real PM of traffic class - 0 (TC0) on PxmPW"
    ::= { pxmTC0PwPmRealEntry  4 }

pxmTC0PwPmRealRandomGreenDropPkts OBJECT-TYPE
    SYNTAX      Counter64
    MAX-ACCESS  read-only
    STATUS      current
    DESCRIPTION "RandomGreenDropPkts Real PM of traffic class - 0 (TC0) on PxmPW"
    ::= { pxmTC0PwPmRealEntry  5 }

pxmTC0PwPmRealRandomGreenDropOctets OBJECT-TYPE
    SYNTAX      Counter64
    MAX-ACCESS  read-only
    STATUS      current
    DESCRIPTION "RandomGreenDropOctets Real PM of traffic class - 0 (TC0) on PxmPW"
    ::= { pxmTC0PwPmRealEntry  6 }

pxmTC0PwPmRealRandomYellowDropPkts OBJECT-TYPE
    SYNTAX      Counter64
    MAX-ACCESS  read-only
    STATUS      current
    DESCRIPTION "RandomYellowDropPkts Real PM of traffic class - 0 (TC0) on PxmPW"
    ::= { pxmTC0PwPmRealEntry  7 }

pxmTC0PwPmRealRandomYellowDropOctets OBJECT-TYPE
    SYNTAX      Counter64
    MAX-ACCESS  read-only
    STATUS      current
    DESCRIPTION "RandomYellowDropOctets Real PM of traffic class - 0 (TC0) on PxmPW"
    ::= { pxmTC0PwPmRealEntry  8 }

pxmTC0PwPmRealQueueingTransmitPkts OBJECT-TYPE
    SYNTAX      Counter64
    MAX-ACCESS  read-only
    STATUS      current
    DESCRIPTION "QueueingTransmitPkts Real PM of traffic class - 0 (TC0) on PxmPW"
    ::= { pxmTC0PwPmRealEntry  9 }

pxmTC0PwPmRealQueueingTransmitOctets OBJECT-TYPE
    SYNTAX      Counter64
    MAX-ACCESS  read-only
    STATUS      current
    DESCRIPTION "QueueingTransmitOctets Real PM of traffic class - 0 (TC0) on PxmPW"
    ::= { pxmTC0PwPmRealEntry  10 }

pxmTC0PwPmRealQueueingMeanQSizeUnit OBJECT-TYPE
    SYNTAX      Integer32
    MAX-ACCESS  read-only
    STATUS      current
    DESCRIPTION "QueueingMeanQSizeUnit Real PM of traffic class - 0 (TC0) on PxmPW"
    ::= { pxmTC0PwPmRealEntry  11 }

pxmTC0PwPmRealMeanQSize OBJECT-TYPE
    SYNTAX      Integer32
    MAX-ACCESS  read-only
    STATUS      current
    DESCRIPTION "MeanQSize Real PM of traffic class - 0 (TC0) on PxmPW"
    ::= { pxmTC0PwPmRealEntry  12 }

-- CM Historical

pxmTC0PwPmTable OBJECT-TYPE
    SYNTAX      SEQUENCE OF PxmTC0PwPmEntry
    MAX-ACCESS  not-accessible
    STATUS      current
    DESCRIPTION
        "A list of PxmBwpPwPmReal entries. Each entry is uniquely identified by the value of ifIndex."
    ::= { pxmCmPwPm 1 } 

pxmTC0PwPmEntry  OBJECT-TYPE
    SYNTAX      PxmTC0PwPmEntry
    MAX-ACCESS  not-accessible
    STATUS      current
    DESCRIPTION ""
    INDEX { ifIndex, pxmTC0PwPmSampleDuration, pxmTC0PwPmTimestamp }
    ::= { pxmTC0PwPmTable 1 }

PxmTC0PwPmEntry  ::= SEQUENCE {
    pxmTC0PwPmTimestamp                 Integer32,
    pxmTC0PwPmSampleDuration            INTEGER,
    pxmTC0PwPmValidity                  TruthValue,
    pxmTC0PwPmTCNum                     Integer32,
    pxmTC0PwPmQueueingDiscardOctets     Counter64,
    pxmTC0PwPmQueueingDiscardPkts       Integer32,
    pxmTC0PwPmRandomGreenDropPkts       Counter64,
    pxmTC0PwPmRandomGreenDropOctets     Counter64,
    pxmTC0PwPmRandomYellowDropPkts      Counter64,
    pxmTC0PwPmRandomYellowDropOctets    Counter64,
    pxmTC0PwPmQueueingTransmitPkts      Counter64,
    pxmTC0PwPmQueueingTransmitOctets    Counter64
}

pxmTC0PwPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC0PwPmEntry  1 }

pxmTC0PwPmSampleDuration OBJECT-TYPE
    SYNTAX      INTEGER {
                    fifteenMinutes(1),
                    day(2)
                }
    MAX-ACCESS  not-accessible
    STATUS      current
    DESCRIPTION
        "The duration of this sample."
    ::= { pxmTC0PwPmEntry  2 }

pxmTC0PwPmValidity OBJECT-TYPE
    SYNTAX      TruthValue
    MAX-ACCESS  read-only
    STATUS      current
    DESCRIPTION "Flag indicating if data was valid for the entire interval"
    ::= { pxmTC0PwPmEntry  3 }

pxmTC0PwPmTCNum OBJECT-TYPE
    SYNTAX      Integer32
    MAX-ACCESS  read-only
    STATUS      current
    DESCRIPTION "TCNum Historical PM of traffic class - 0 (TC0) on PxmPW"
    ::= { pxmTC0PwPmEntry  4 }

pxmTC0PwPmQueueingDiscardOctets OBJECT-TYPE
    SYNTAX      Counter64
    MAX-ACCESS  read-only
    STATUS      current
    DESCRIPTION "QueueingDiscardOctets Historical PM of traffic class - 0 (TC0) on PxmPW"
    ::= { pxmTC0PwPmEntry  5 }

pxmTC0PwPmQueueingDiscardPkts OBJECT-TYPE
    SYNTAX      Integer32
    MAX-ACCESS  read-only
    STATUS      current
    DESCRIPTION "QueueingDiscardPkts Historical PM of traffic class - 0 (TC0) on PxmPW"
    ::= { pxmTC0PwPmEntry  6 }

pxmTC0PwPmRandomGreenDropPkts OBJECT-TYPE
    SYNTAX      Counter64
    MAX-ACCESS  read-only
    STATUS      current
    DESCRIPTION "RandomGreenDropPkts Historical PM of traffic class - 0 (TC0) on PxmPW"
    ::= { pxmTC0PwPmEntry  7 }

pxmTC0PwPmRandomGreenDropOctets OBJECT-TYPE
    SYNTAX      Counter64
    MAX-ACCESS  read-only
    STATUS      current
    DESCRIPTION "RandomGreenDropOctets Historical PM of traffic class - 0 (TC0) on PxmPW"
    ::= { pxmTC0PwPmEntry  8 }

pxmTC0PwPmRandomYellowDropPkts OBJECT-TYPE
    SYNTAX      Counter64
    MAX-ACCESS  read-only
    STATUS      current
    DESCRIPTION "RandomYellowDropPkts Historical PM of traffic class - 0 (TC0) on PxmPW"
    ::= { pxmTC0PwPmEntry  9 }

pxmTC0PwPmRandomYellowDropOctets OBJECT-TYPE
    SYNTAX      Counter64
    MAX-ACCESS  read-only
    STATUS      current
    DESCRIPTION "RandomYellowDropOctets Historical PM of traffic class - 0 (TC0) on PxmPW"
    ::= { pxmTC0PwPmEntry  10 }

pxmTC0PwPmQueueingTransmitPkts OBJECT-TYPE
    SYNTAX      Counter64
    MAX-ACCESS  read-only
    STATUS      current
    DESCRIPTION "QueueingTransmitPkts Historical PM of traffic class - 0 (TC0) on PxmPW"
    ::= { pxmTC0PwPmEntry  11 }

pxmTC0PwPmQueueingTransmitOctets OBJECT-TYPE
    SYNTAX      Counter64
    MAX-ACCESS  read-only
    STATUS      current
    DESCRIPTION "QueueingTransmitOctets Historical PM of traffic class - 0 (TC0) on PxmPW"
    ::= { pxmTC0PwPmEntry  12 }

-- TC2 Historical
pxmTC2PwPmTable OBJECT-TYPE
    SYNTAX      SEQUENCE OF PxmTC2PwPmEntry
    MAX-ACCESS  not-accessible
    STATUS      current
    DESCRIPTION
        "A list of PxmBwpPwPmReal entries. Each entry is uniquely identified by the value of ifIndex."
    ::= { pxmCmPwPm 2 } 

pxmTC2PwPmEntry  OBJECT-TYPE
    SYNTAX      PxmTC2PwPmEntry
    MAX-ACCESS  not-accessible
    STATUS      current
    DESCRIPTION ""
    INDEX { ifIndex, pxmTC2PwPmSampleDuration, pxmTC2PwPmTimestamp }
    ::= { pxmTC2PwPmTable 1 }

PxmTC2PwPmEntry  ::= SEQUENCE {
    pxmTC2PwPmTimestamp                 Integer32,
    pxmTC2PwPmSampleDuration            INTEGER,
    pxmTC2PwPmValidity                  TruthValue,
    pxmTC2PwPmTCNum                     Integer32,
    pxmTC2PwPmQueueingDiscardOctets     Counter64,
    pxmTC2PwPmQueueingDiscardPkts       Integer32,
    pxmTC2PwPmRandomGreenDropPkts       Counter64,
    pxmTC2PwPmRandomGreenDropOctets     Counter64,
    pxmTC2PwPmRandomYellowDropPkts      Counter64,
    pxmTC2PwPmRandomYellowDropOctets    Counter64,
    pxmTC2PwPmQueueingTransmitPkts      Counter64,
    pxmTC2PwPmQueueingTransmitOctets    Counter64
}

pxmTC2PwPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC2PwPmEntry  1 }

pxmTC2PwPmSampleDuration OBJECT-TYPE
    SYNTAX      INTEGER {
                    fifteenMinutes(1),
                    day(2)
                }
    MAX-ACCESS  not-accessible
    STATUS      current
    DESCRIPTION
        "The duration of this sample."
    ::= { pxmTC2PwPmEntry  2 }

pxmTC2PwPmValidity OBJECT-TYPE
    SYNTAX      TruthValue
    MAX-ACCESS  read-only
    STATUS      current
    DESCRIPTION "Flag indicating if data was valid for the entire interval"
    ::= { pxmTC2PwPmEntry  3 }

pxmTC2PwPmTCNum OBJECT-TYPE
    SYNTAX      Integer32
    MAX-ACCESS  read-only
    STATUS      current
    DESCRIPTION "TCNum Historical PM of traffic class - 2 (TC2) on PxmPW"
    ::= { pxmTC2PwPmEntry  4 }

pxmTC2PwPmQueueingDiscardOctets OBJECT-TYPE
    SYNTAX      Counter64
    MAX-ACCESS  read-only
    STATUS      current
    DESCRIPTION "QueueingDiscardOctets Historical PM of traffic class - 2 (TC2) on PxmPW"
    ::= { pxmTC2PwPmEntry  5 }

pxmTC2PwPmQueueingDiscardPkts OBJECT-TYPE
    SYNTAX      Integer32
    MAX-ACCESS  read-only
    STATUS      current
    DESCRIPTION "QueueingDiscardPkts Historical PM of traffic class - 2 (TC2) on PxmPW"
    ::= { pxmTC2PwPmEntry  6 }

pxmTC2PwPmRandomGreenDropPkts OBJECT-TYPE
    SYNTAX      Counter64
    MAX-ACCESS  read-only
    STATUS      current
    DESCRIPTION "RandomGreenDropPkts Historical PM of traffic class - 2 (TC2) on PxmPW"
    ::= { pxmTC2PwPmEntry  7 }

pxmTC2PwPmRandomGreenDropOctets OBJECT-TYPE
    SYNTAX      Counter64
    MAX-ACCESS  read-only
    STATUS      current
    DESCRIPTION "RandomGreenDropOctets Historical PM of traffic class - 2 (TC2) on PxmPW"
    ::= { pxmTC2PwPmEntry  8 }

pxmTC2PwPmRandomYellowDropPkts OBJECT-TYPE
    SYNTAX      Counter64
    MAX-ACCESS  read-only
    STATUS      current
    DESCRIPTION "RandomYellowDropPkts Historical PM of traffic class - 2 (TC2) on PxmPW"
    ::= { pxmTC2PwPmEntry  9 }

pxmTC2PwPmRandomYellowDropOctets OBJECT-TYPE
    SYNTAX      Counter64
    MAX-ACCESS  read-only
    STATUS      current
    DESCRIPTION "RandomYellowDropOctets Historical PM of traffic class - 2 (TC2) on PxmPW"
    ::= { pxmTC2PwPmEntry  10 }

pxmTC2PwPmQueueingTransmitPkts OBJECT-TYPE
    SYNTAX      Counter64
    MAX-ACCESS  read-only
    STATUS      current
    DESCRIPTION "QueueingTransmitPkts Historical PM of traffic class - 2 (TC2) on PxmPW"
    ::= { pxmTC2PwPmEntry  11 }

pxmTC2PwPmQueueingTransmitOctets OBJECT-TYPE
    SYNTAX      Counter64
    MAX-ACCESS  read-only
    STATUS      current
    DESCRIPTION "QueueingTransmitOctets Historical PM of traffic class - 2 (TC2) on PxmPW"
    ::= { pxmTC2PwPmEntry  12 }

-- TC2 Real
pxmTC2PwPmRealTable OBJECT-TYPE
    SYNTAX      SEQUENCE OF PxmTC2PwPmRealEntry
    MAX-ACCESS  not-accessible
    STATUS      current
    DESCRIPTION
        "A list of PxmBwpPwPmReal entries. Each entry is uniquely identified by the value of ifIndex."
    ::= { pxmCmPwRealPm 2 } 

pxmTC2PwPmRealEntry  OBJECT-TYPE
    SYNTAX      PxmTC2PwPmRealEntry
    MAX-ACCESS  not-accessible
    STATUS      current
    DESCRIPTION
        "A PxmTC0PwPm entry containing real-time performance information pertaining to Infinera PxmPwPm interfaces.
        This table is a subclass of IfCommon. Entries will exist in this table only for interfaces of
        type PxmPwPm."
    INDEX { ifIndex }
    ::= { pxmTC2PwPmRealTable 1 }

PxmTC2PwPmRealEntry  ::= SEQUENCE {
    pxmTC2PwPmRealTCNum                     Integer32,
    pxmTC2PwPmRealTDQueuingCurrentQDepth    Integer32,
    pxmTC2PwPmRealQueueingDiscardOctets     Counter64,
    pxmTC2PwPmRealQueueingDiscardPkts       Integer32,
    pxmTC2PwPmRealRandomGreenDropPkts       Counter64,
    pxmTC2PwPmRealRandomGreenDropOctets     Counter64,
    pxmTC2PwPmRealRandomYellowDropPkts      Counter64,
    pxmTC2PwPmRealRandomYellowDropOctets    Counter64,
    pxmTC2PwPmRealQueueingTransmitPkts      Counter64,
    pxmTC2PwPmRealQueueingTransmitOctets    Counter64,
    pxmTC2PwPmRealQueueingMeanQSizeUnit     Integer32,
    pxmTC2PwPmRealMeanQSize                 Integer32
}

pxmTC2PwPmRealTCNum OBJECT-TYPE
    SYNTAX      Integer32
    MAX-ACCESS  read-only
    STATUS      current
    DESCRIPTION "TCNum Real PM of traffic class - 2 (TC2) on PxmPW"
    ::= { pxmTC2PwPmRealEntry  1 }

pxmTC2PwPmRealTDQueuingCurrentQDepth OBJECT-TYPE
    SYNTAX      Integer32
    MAX-ACCESS  read-only
    STATUS      current
    DESCRIPTION "TDQueuingCurrentQDepth Real PM of traffic class - 2 (TC2) on PxmPW"
    ::= { pxmTC2PwPmRealEntry  2 }

pxmTC2PwPmRealQueueingDiscardOctets OBJECT-TYPE
    SYNTAX      Counter64
    MAX-ACCESS  read-only
    STATUS      current
    DESCRIPTION "QueueingDiscardOctets Real PM of traffic class - 2 (TC2) on PxmPW"
    ::= { pxmTC2PwPmRealEntry  3 }

pxmTC2PwPmRealQueueingDiscardPkts OBJECT-TYPE
    SYNTAX      Integer32
    MAX-ACCESS  read-only
    STATUS      current
    DESCRIPTION "QueueingDiscardPkts Real PM of traffic class - 2 (TC2) on PxmPW"
    ::= { pxmTC2PwPmRealEntry  4 }

pxmTC2PwPmRealRandomGreenDropPkts OBJECT-TYPE
    SYNTAX      Counter64
    MAX-ACCESS  read-only
    STATUS      current
    DESCRIPTION "RandomGreenDropPkts Real PM of traffic class - 2 (TC2) on PxmPW"
    ::= { pxmTC2PwPmRealEntry  5 }

pxmTC2PwPmRealRandomGreenDropOctets OBJECT-TYPE
    SYNTAX      Counter64
    MAX-ACCESS  read-only
    STATUS      current
    DESCRIPTION "RandomGreenDropOctets Real PM of traffic class - 2 (TC2) on PxmPW"
    ::= { pxmTC2PwPmRealEntry  6 }

pxmTC2PwPmRealRandomYellowDropPkts OBJECT-TYPE
    SYNTAX      Counter64
    MAX-ACCESS  read-only
    STATUS      current
    DESCRIPTION "RandomYellowDropPkts Real PM of traffic class - 2 (TC2) on PxmPW"
    ::= { pxmTC2PwPmRealEntry  7 }

pxmTC2PwPmRealRandomYellowDropOctets OBJECT-TYPE
    SYNTAX      Counter64
    MAX-ACCESS  read-only
    STATUS      current
    DESCRIPTION "RandomYellowDropOctets Real PM of traffic class - 2 (TC2) on PxmPW"
    ::= { pxmTC2PwPmRealEntry  8 }

pxmTC2PwPmRealQueueingTransmitPkts OBJECT-TYPE
    SYNTAX      Counter64
    MAX-ACCESS  read-only
    STATUS      current
    DESCRIPTION "QueueingTransmitPkts Real PM of traffic class - 2 (TC2) on PxmPW"
    ::= { pxmTC2PwPmRealEntry  9 }

pxmTC2PwPmRealQueueingTransmitOctets OBJECT-TYPE
    SYNTAX      Counter64
    MAX-ACCESS  read-only
    STATUS      current
    DESCRIPTION "QueueingTransmitOctets Real PM of traffic class - 2 (TC2) on PxmPW"
    ::= { pxmTC2PwPmRealEntry  10 }

pxmTC2PwPmRealQueueingMeanQSizeUnit OBJECT-TYPE
    SYNTAX      Integer32
    MAX-ACCESS  read-only
    STATUS      current
    DESCRIPTION "QueueingMeanQSizeUnit Real PM of traffic class - 2 (TC2) on PxmPW"
    ::= { pxmTC2PwPmRealEntry  11 }

pxmTC2PwPmRealMeanQSize OBJECT-TYPE
    SYNTAX      Integer32
    MAX-ACCESS  read-only
    STATUS      current
    DESCRIPTION "MeanQSize Real PM of traffic class - 2 (TC2) on PxmPW"
    ::= { pxmTC2PwPmRealEntry  12 }

-- TC4 Historical
pxmTC4PwPmTable OBJECT-TYPE
    SYNTAX      SEQUENCE OF PxmTC4PwPmEntry
    MAX-ACCESS  not-accessible
    STATUS      current
    DESCRIPTION
        "A list of PxmBwpPwPmReal entries. Each entry is uniquely identified by the value of ifIndex."
    ::= { pxmCmPwPm 3 } 

pxmTC4PwPmEntry  OBJECT-TYPE
    SYNTAX      PxmTC4PwPmEntry
    MAX-ACCESS  not-accessible
    STATUS      current
    DESCRIPTION ""
    INDEX { ifIndex, pxmTC4PwPmSampleDuration, pxmTC4PwPmTimestamp }
    ::= { pxmTC4PwPmTable 1 }

PxmTC4PwPmEntry  ::= SEQUENCE {
    pxmTC4PwPmTimestamp                 Integer32,
    pxmTC4PwPmSampleDuration            INTEGER,
    pxmTC4PwPmValidity                  TruthValue,
    pxmTC4PwPmTCNum                     Integer32,
    pxmTC4PwPmQueueingDiscardOctets     Counter64,
    pxmTC4PwPmQueueingDiscardPkts       Integer32,
    pxmTC4PwPmRandomGreenDropPkts       Counter64,
    pxmTC4PwPmRandomGreenDropOctets     Counter64,
    pxmTC4PwPmRandomYellowDropPkts      Counter64,
    pxmTC4PwPmRandomYellowDropOctets    Counter64,
    pxmTC4PwPmQueueingTransmitPkts      Counter64,
    pxmTC4PwPmQueueingTransmitOctets    Counter64
}

pxmTC4PwPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC4PwPmEntry  1 }

pxmTC4PwPmSampleDuration OBJECT-TYPE
    SYNTAX      INTEGER {
                    fifteenMinutes(1),
                    day(2)
                }
    MAX-ACCESS  not-accessible
    STATUS      current
    DESCRIPTION
        "The duration of this sample."
    ::= { pxmTC4PwPmEntry  2 }

pxmTC4PwPmValidity OBJECT-TYPE
    SYNTAX      TruthValue
    MAX-ACCESS  read-only
    STATUS      current
    DESCRIPTION "Flag indicating if data was valid for the entire interval"
    ::= { pxmTC4PwPmEntry  3 }

pxmTC4PwPmTCNum OBJECT-TYPE
    SYNTAX      Integer32
    MAX-ACCESS  read-only
    STATUS      current
    DESCRIPTION "TCNum Historical PM of traffic class - 4 (TC4) on PxmPW"
    ::= { pxmTC4PwPmEntry  4 }

pxmTC4PwPmQueueingDiscardOctets OBJECT-TYPE
    SYNTAX      Counter64
    MAX-ACCESS  read-only
    STATUS      current
    DESCRIPTION "QueueingDiscardOctets Historical PM of traffic class - 4 (TC4) on PxmPW"
    ::= { pxmTC4PwPmEntry  5 }

pxmTC4PwPmQueueingDiscardPkts OBJECT-TYPE
    SYNTAX      Integer32
    MAX-ACCESS  read-only
    STATUS      current
    DESCRIPTION "QueueingDiscardPkts Historical PM of traffic class - 4 (TC4) on PxmPW"
    ::= { pxmTC4PwPmEntry  6 }

pxmTC4PwPmRandomGreenDropPkts OBJECT-TYPE
    SYNTAX      Counter64
    MAX-ACCESS  read-only
    STATUS      current
    DESCRIPTION "RandomGreenDropPkts Historical PM of traffic class - 4 (TC4) on PxmPW"
    ::= { pxmTC4PwPmEntry  7 }

pxmTC4PwPmRandomGreenDropOctets OBJECT-TYPE
    SYNTAX      Counter64
    MAX-ACCESS  read-only
    STATUS      current
    DESCRIPTION "RandomGreenDropOctets Historical PM of traffic class - 4 (TC4) on PxmPW"
    ::= { pxmTC4PwPmEntry  8 }

pxmTC4PwPmRandomYellowDropPkts OBJECT-TYPE
    SYNTAX      Counter64
    MAX-ACCESS  read-only
    STATUS      current
    DESCRIPTION "RandomYellowDropPkts Historical PM of traffic class - 4 (TC4) on PxmPW"
    ::= { pxmTC4PwPmEntry  9 }

pxmTC4PwPmRandomYellowDropOctets OBJECT-TYPE
    SYNTAX      Counter64
    MAX-ACCESS  read-only
    STATUS      current
    DESCRIPTION "RandomYellowDropOctets Historical PM of traffic class - 4 (TC4) on PxmPW"
    ::= { pxmTC4PwPmEntry  10 }

pxmTC4PwPmQueueingTransmitPkts OBJECT-TYPE
    SYNTAX      Counter64
    MAX-ACCESS  read-only
    STATUS      current
    DESCRIPTION "QueueingTransmitPkts Historical PM of traffic class - 4 (TC4) on PxmPW"
    ::= { pxmTC4PwPmEntry  11 }

pxmTC4PwPmQueueingTransmitOctets OBJECT-TYPE
    SYNTAX      Counter64
    MAX-ACCESS  read-only
    STATUS      current
    DESCRIPTION "QueueingTransmitOctets Historical PM of traffic class - 4 (TC4) on PxmPW"
    ::= { pxmTC4PwPmEntry  12 }

-- TC4 Real
pxmTC4PwPmRealTable OBJECT-TYPE
    SYNTAX      SEQUENCE OF PxmTC4PwPmRealEntry
    MAX-ACCESS  not-accessible
    STATUS      current
    DESCRIPTION
        "A list of PxmBwpPwPmReal entries. Each entry is uniquely identified by the value of ifIndex."
    ::= { pxmCmPwRealPm 3 } 

pxmTC4PwPmRealEntry  OBJECT-TYPE
    SYNTAX      PxmTC4PwPmRealEntry
    MAX-ACCESS  not-accessible
    STATUS      current
    DESCRIPTION
        "A PxmTC0PwPm entry containing real-time performance information pertaining to Infinera PxmPwPm interfaces.
        This table is a subclass of IfCommon. Entries will exist in this table only for interfaces of
        type PxmPwPm."
    INDEX { ifIndex }
    ::= { pxmTC4PwPmRealTable 1 }

PxmTC4PwPmRealEntry  ::= SEQUENCE {
    pxmTC4PwPmRealTCNum                     Integer32,
    pxmTC4PwPmRealTDQueuingCurrentQDepth    Integer32,
    pxmTC4PwPmRealQueueingDiscardOctets     Counter64,
    pxmTC4PwPmRealQueueingDiscardPkts       Integer32,
    pxmTC4PwPmRealRandomGreenDropPkts       Counter64,
    pxmTC4PwPmRealRandomGreenDropOctets     Counter64,
    pxmTC4PwPmRealRandomYellowDropPkts      Counter64,
    pxmTC4PwPmRealRandomYellowDropOctets    Counter64,
    pxmTC4PwPmRealQueueingTransmitPkts      Counter64,
    pxmTC4PwPmRealQueueingTransmitOctets    Counter64,
    pxmTC4PwPmRealQueueingMeanQSizeUnit     Integer32,
    pxmTC4PwPmRealMeanQSize                 Integer32
}

pxmTC4PwPmRealTCNum OBJECT-TYPE
    SYNTAX      Integer32
    MAX-ACCESS  read-only
    STATUS      current
    DESCRIPTION "TCNum Real PM of traffic class - 4 (TC4) on PxmPW"
    ::= { pxmTC4PwPmRealEntry  1 }

pxmTC4PwPmRealTDQueuingCurrentQDepth OBJECT-TYPE
    SYNTAX      Integer32
    MAX-ACCESS  read-only
    STATUS      current
    DESCRIPTION "TDQueuingCurrentQDepth Real PM of traffic class - 4 (TC4) on PxmPW"
    ::= { pxmTC4PwPmRealEntry  2 }

pxmTC4PwPmRealQueueingDiscardOctets OBJECT-TYPE
    SYNTAX      Counter64
    MAX-ACCESS  read-only
    STATUS      current
    DESCRIPTION "QueueingDiscardOctets Real PM of traffic class - 4 (TC4) on PxmPW"
    ::= { pxmTC4PwPmRealEntry  3 }

pxmTC4PwPmRealQueueingDiscardPkts OBJECT-TYPE
    SYNTAX      Integer32
    MAX-ACCESS  read-only
    STATUS      current
    DESCRIPTION "QueueingDiscardPkts Real PM of traffic class - 4 (TC4) on PxmPW"
    ::= { pxmTC4PwPmRealEntry  4 }

pxmTC4PwPmRealRandomGreenDropPkts OBJECT-TYPE
    SYNTAX      Counter64
    MAX-ACCESS  read-only
    STATUS      current
    DESCRIPTION "RandomGreenDropPkts Real PM of traffic class - 4 (TC4) on PxmPW"
    ::= { pxmTC4PwPmRealEntry  5 }

pxmTC4PwPmRealRandomGreenDropOctets OBJECT-TYPE
    SYNTAX      Counter64
    MAX-ACCESS  read-only
    STATUS      current
    DESCRIPTION "RandomGreenDropOctets Real PM of traffic class - 4 (TC4) on PxmPW"
    ::= { pxmTC4PwPmRealEntry  6 }

pxmTC4PwPmRealRandomYellowDropPkts OBJECT-TYPE
    SYNTAX      Counter64
    MAX-ACCESS  read-only
    STATUS      current
    DESCRIPTION "RandomYellowDropPkts Real PM of traffic class - 4 (TC4) on PxmPW"
    ::= { pxmTC4PwPmRealEntry  7 }

pxmTC4PwPmRealRandomYellowDropOctets OBJECT-TYPE
    SYNTAX      Counter64
    MAX-ACCESS  read-only
    STATUS      current
    DESCRIPTION "RandomYellowDropOctets Real PM of traffic class - 4 (TC4) on PxmPW"
    ::= { pxmTC4PwPmRealEntry  8 }

pxmTC4PwPmRealQueueingTransmitPkts OBJECT-TYPE
    SYNTAX      Counter64
    MAX-ACCESS  read-only
    STATUS      current
    DESCRIPTION "QueueingTransmitPkts Real PM of traffic class - 4 (TC4) on PxmPW"
    ::= { pxmTC4PwPmRealEntry  9 }

pxmTC4PwPmRealQueueingTransmitOctets OBJECT-TYPE
    SYNTAX      Counter64
    MAX-ACCESS  read-only
    STATUS      current
    DESCRIPTION "QueueingTransmitOctets Real PM of traffic class - 4 (TC4) on PxmPW"
    ::= { pxmTC4PwPmRealEntry  10 }

pxmTC4PwPmRealQueueingMeanQSizeUnit OBJECT-TYPE
    SYNTAX      Integer32
    MAX-ACCESS  read-only
    STATUS      current
    DESCRIPTION "QueueingMeanQSizeUnit Real PM of traffic class - 4 (TC4) on PxmPW"
    ::= { pxmTC4PwPmRealEntry  11 }

pxmTC4PwPmRealMeanQSize OBJECT-TYPE
    SYNTAX      Integer32
    MAX-ACCESS  read-only
    STATUS      current
    DESCRIPTION "MeanQSize Real PM of traffic class - 4 (TC4) on PxmPW"
    ::= { pxmTC4PwPmRealEntry  12 }

-- TC6 Historical
pxmTC6PwPmTable OBJECT-TYPE
    SYNTAX      SEQUENCE OF PxmTC6PwPmEntry
    MAX-ACCESS  not-accessible
    STATUS      current
    DESCRIPTION
        "A list of PxmBwpPwPmReal entries. Each entry is uniquely identified by the value of ifIndex."
    ::= { pxmCmPwPm 4 } 

pxmTC6PwPmEntry  OBJECT-TYPE
    SYNTAX      PxmTC6PwPmEntry
    MAX-ACCESS  not-accessible
    STATUS      current
    DESCRIPTION ""
    INDEX { ifIndex, pxmTC6PwPmSampleDuration, pxmTC6PwPmTimestamp }
    ::= { pxmTC6PwPmTable 1 }

PxmTC6PwPmEntry  ::= SEQUENCE {
    pxmTC6PwPmTimestamp                 Integer32,
    pxmTC6PwPmSampleDuration            INTEGER,
    pxmTC6PwPmValidity                  TruthValue,
    pxmTC6PwPmTCNum                     Integer32,
    pxmTC6PwPmQueueingDiscardOctets     Counter64,
    pxmTC6PwPmQueueingDiscardPkts       Integer32,
    pxmTC6PwPmRandomGreenDropPkts       Counter64,
    pxmTC6PwPmRandomGreenDropOctets     Counter64,
    pxmTC6PwPmRandomYellowDropPkts      Counter64,
    pxmTC6PwPmRandomYellowDropOctets    Counter64,
    pxmTC6PwPmQueueingTransmitPkts      Counter64,
    pxmTC6PwPmQueueingTransmitOctets    Counter64
}

pxmTC6PwPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC6PwPmEntry  1 }

pxmTC6PwPmSampleDuration OBJECT-TYPE
    SYNTAX      INTEGER {
                    fifteenMinutes(1),
                    day(2)
                }
    MAX-ACCESS  not-accessible
    STATUS      current
    DESCRIPTION
        "The duration of this sample."
    ::= { pxmTC6PwPmEntry  2 }

pxmTC6PwPmValidity OBJECT-TYPE
    SYNTAX      TruthValue
    MAX-ACCESS  read-only
    STATUS      current
    DESCRIPTION "Flag indicating if data was valid for the entire interval"
    ::= { pxmTC6PwPmEntry  3 }

pxmTC6PwPmTCNum OBJECT-TYPE
    SYNTAX      Integer32
    MAX-ACCESS  read-only
    STATUS      current
    DESCRIPTION "TCNum Historical PM of traffic class - 6 (TC6) on PxmPW"
    ::= { pxmTC6PwPmEntry  4 }

pxmTC6PwPmQueueingDiscardOctets OBJECT-TYPE
    SYNTAX      Counter64
    MAX-ACCESS  read-only
    STATUS      current
    DESCRIPTION "QueueingDiscardOctets Historical PM of traffic class - 6 (TC6) on PxmPW"
    ::= { pxmTC6PwPmEntry  5 }

pxmTC6PwPmQueueingDiscardPkts OBJECT-TYPE
    SYNTAX      Integer32
    MAX-ACCESS  read-only
    STATUS      current
    DESCRIPTION "QueueingDiscardPkts Historical PM of traffic class - 6 (TC6) on PxmPW"
    ::= { pxmTC6PwPmEntry  6 }

pxmTC6PwPmRandomGreenDropPkts OBJECT-TYPE
    SYNTAX      Counter64
    MAX-ACCESS  read-only
    STATUS      current
    DESCRIPTION "RandomGreenDropPkts Historical PM of traffic class - 6 (TC6) on PxmPW"
    ::= { pxmTC6PwPmEntry  7 }

pxmTC6PwPmRandomGreenDropOctets OBJECT-TYPE
    SYNTAX      Counter64
    MAX-ACCESS  read-only
    STATUS      current
    DESCRIPTION "RandomGreenDropOctets Historical PM of traffic class - 6 (TC6) on PxmPW"
    ::= { pxmTC6PwPmEntry  8 }

pxmTC6PwPmRandomYellowDropPkts OBJECT-TYPE
    SYNTAX      Counter64
    MAX-ACCESS  read-only
    STATUS      current
    DESCRIPTION "RandomYellowDropPkts Historical PM of traffic class - 6 (TC6) on PxmPW"
    ::= { pxmTC6PwPmEntry  9 }

pxmTC6PwPmRandomYellowDropOctets OBJECT-TYPE
    SYNTAX      Counter64
    MAX-ACCESS  read-only
    STATUS      current
    DESCRIPTION "RandomYellowDropOctets Historical PM of traffic class - 6 (TC6) on PxmPW"
    ::= { pxmTC6PwPmEntry  10 }

pxmTC6PwPmQueueingTransmitPkts OBJECT-TYPE
    SYNTAX      Counter64
    MAX-ACCESS  read-only
    STATUS      current
    DESCRIPTION "QueueingTransmitPkts Historical PM of traffic class - 6 (TC6) on PxmPW"
    ::= { pxmTC6PwPmEntry  11 }

pxmTC6PwPmQueueingTransmitOctets OBJECT-TYPE
    SYNTAX      Counter64
    MAX-ACCESS  read-only
    STATUS      current
    DESCRIPTION "QueueingTransmitOctets Historical PM of traffic class - 6 (TC6) on PxmPW"
    ::= { pxmTC6PwPmEntry  12 }

-- TC6 Real
pxmTC6PwPmRealTable OBJECT-TYPE
    SYNTAX      SEQUENCE OF PxmTC6PwPmRealEntry
    MAX-ACCESS  not-accessible
    STATUS      current
    DESCRIPTION
        "A list of PxmBwpPwPmReal entries. Each entry is uniquely identified by the value of ifIndex."
    ::= { pxmCmPwRealPm 4 } 

pxmTC6PwPmRealEntry  OBJECT-TYPE
    SYNTAX      PxmTC6PwPmRealEntry
    MAX-ACCESS  not-accessible
    STATUS      current
    DESCRIPTION
        "A PxmTC0PwPm entry containing real-time performance information pertaining to Infinera PxmPwPm interfaces.
        This table is a subclass of IfCommon. Entries will exist in this table only for interfaces of
        type PxmPwPm."
    INDEX { ifIndex }
    ::= { pxmTC6PwPmRealTable 1 }

PxmTC6PwPmRealEntry  ::= SEQUENCE {
    pxmTC6PwPmRealTCNum                     Integer32,
    pxmTC6PwPmRealTDQueuingCurrentQDepth    Integer32,
    pxmTC6PwPmRealQueueingDiscardOctets     Counter64,
    pxmTC6PwPmRealQueueingDiscardPkts       Integer32,
    pxmTC6PwPmRealRandomGreenDropPkts       Counter64,
    pxmTC6PwPmRealRandomGreenDropOctets     Counter64,
    pxmTC6PwPmRealRandomYellowDropPkts      Counter64,
    pxmTC6PwPmRealRandomYellowDropOctets    Counter64,
    pxmTC6PwPmRealQueueingTransmitPkts      Counter64,
    pxmTC6PwPmRealQueueingTransmitOctets    Counter64,
    pxmTC6PwPmRealQueueingMeanQSizeUnit     Integer32,
    pxmTC6PwPmRealMeanQSize                 Integer32
}

pxmTC6PwPmRealTCNum OBJECT-TYPE
    SYNTAX      Integer32
    MAX-ACCESS  read-only
    STATUS      current
    DESCRIPTION "TCNum Real PM of traffic class - 6 (TC6) on PxmPW"
    ::= { pxmTC6PwPmRealEntry  1 }

pxmTC6PwPmRealTDQueuingCurrentQDepth OBJECT-TYPE
    SYNTAX      Integer32
    MAX-ACCESS  read-only
    STATUS      current
    DESCRIPTION "TDQueuingCurrentQDepth Real PM of traffic class - 6 (TC6) on PxmPW"
    ::= { pxmTC6PwPmRealEntry  2 }

pxmTC6PwPmRealQueueingDiscardOctets OBJECT-TYPE
    SYNTAX      Counter64
    MAX-ACCESS  read-only
    STATUS      current
    DESCRIPTION "QueueingDiscardOctets Real PM of traffic class - 6 (TC6) on PxmPW"
    ::= { pxmTC6PwPmRealEntry  3 }

pxmTC6PwPmRealQueueingDiscardPkts OBJECT-TYPE
    SYNTAX      Integer32
    MAX-ACCESS  read-only
    STATUS      current
    DESCRIPTION "QueueingDiscardPkts Real PM of traffic class - 6 (TC6) on PxmPW"
    ::= { pxmTC6PwPmRealEntry  4 }

pxmTC6PwPmRealRandomGreenDropPkts OBJECT-TYPE
    SYNTAX      Counter64
    MAX-ACCESS  read-only
    STATUS      current
    DESCRIPTION "RandomGreenDropPkts Real PM of traffic class - 6 (TC6) on PxmPW"
    ::= { pxmTC6PwPmRealEntry  5 }

pxmTC6PwPmRealRandomGreenDropOctets OBJECT-TYPE
    SYNTAX      Counter64
    MAX-ACCESS  read-only
    STATUS      current
    DESCRIPTION "RandomGreenDropOctets Real PM of traffic class - 6 (TC6) on PxmPW"
    ::= { pxmTC6PwPmRealEntry  6 }

pxmTC6PwPmRealRandomYellowDropPkts OBJECT-TYPE
    SYNTAX      Counter64
    MAX-ACCESS  read-only
    STATUS      current
    DESCRIPTION "RandomYellowDropPkts Real PM of traffic class - 6 (TC6) on PxmPW"
    ::= { pxmTC6PwPmRealEntry  7 }

pxmTC6PwPmRealRandomYellowDropOctets OBJECT-TYPE
    SYNTAX      Counter64
    MAX-ACCESS  read-only
    STATUS      current
    DESCRIPTION "RandomYellowDropOctets Real PM of traffic class - 6 (TC6) on PxmPW"
    ::= { pxmTC6PwPmRealEntry  8 }

pxmTC6PwPmRealQueueingTransmitPkts OBJECT-TYPE
    SYNTAX      Counter64
    MAX-ACCESS  read-only
    STATUS      current
    DESCRIPTION "QueueingTransmitPkts Real PM of traffic class - 6 (TC6) on PxmPW"
    ::= { pxmTC6PwPmRealEntry  9 }

pxmTC6PwPmRealQueueingTransmitOctets OBJECT-TYPE
    SYNTAX      Counter64
    MAX-ACCESS  read-only
    STATUS      current
    DESCRIPTION "QueueingTransmitOctets Real PM of traffic class - 6 (TC6) on PxmPW"
    ::= { pxmTC6PwPmRealEntry  10 }

pxmTC6PwPmRealQueueingMeanQSizeUnit OBJECT-TYPE
    SYNTAX      Integer32
    MAX-ACCESS  read-only
    STATUS      current
    DESCRIPTION "QueueingMeanQSizeUnit Real PM of traffic class - 6 (TC6) on PxmPW"
    ::= { pxmTC6PwPmRealEntry  11 }

pxmTC6PwPmRealMeanQSize OBJECT-TYPE
    SYNTAX      Integer32
    MAX-ACCESS  read-only
    STATUS      current
    DESCRIPTION "MeanQSize Real PM of traffic class - 6 (TC6) on PxmPW"
    ::= { pxmTC6PwPmRealEntry  12 }

-- TC7 Historical
pxmTC7PwPmTable OBJECT-TYPE
    SYNTAX      SEQUENCE OF PxmTC7PwPmEntry
    MAX-ACCESS  not-accessible
    STATUS      current
    DESCRIPTION
        "A list of PxmBwpPwPmReal entries. Each entry is uniquely identified by the value of ifIndex."
    ::= { pxmCmPwPm 5 } 

pxmTC7PwPmEntry  OBJECT-TYPE
    SYNTAX      PxmTC7PwPmEntry
    MAX-ACCESS  not-accessible
    STATUS      current
    DESCRIPTION ""
    INDEX { ifIndex, pxmTC7PwPmSampleDuration, pxmTC7PwPmTimestamp }
    ::= { pxmTC7PwPmTable 1 }

PxmTC7PwPmEntry  ::= SEQUENCE {
    pxmTC7PwPmTimestamp                 Integer32,
    pxmTC7PwPmSampleDuration            INTEGER,
    pxmTC7PwPmValidity                  TruthValue,
    pxmTC7PwPmTCNum                     Integer32,
    pxmTC7PwPmQueueingDiscardOctets     Counter64,
    pxmTC7PwPmQueueingDiscardPkts       Integer32,
    pxmTC7PwPmRandomGreenDropPkts       Counter64,
    pxmTC7PwPmRandomGreenDropOctets     Counter64,
    pxmTC7PwPmRandomYellowDropPkts      Counter64,
    pxmTC7PwPmRandomYellowDropOctets    Counter64,
    pxmTC7PwPmQueueingTransmitPkts      Counter64,
    pxmTC7PwPmQueueingTransmitOctets    Counter64
}

pxmTC7PwPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC7PwPmEntry  1 }

pxmTC7PwPmSampleDuration OBJECT-TYPE
    SYNTAX      INTEGER {
                    fifteenMinutes(1),
                    day(2)
                }
    MAX-ACCESS  not-accessible
    STATUS      current
    DESCRIPTION
        "The duration of this sample."
    ::= { pxmTC7PwPmEntry  2 }

pxmTC7PwPmValidity OBJECT-TYPE
    SYNTAX      TruthValue
    MAX-ACCESS  read-only
    STATUS      current
    DESCRIPTION "Flag indicating if data was valid for the entire interval"
    ::= { pxmTC7PwPmEntry  3 }

pxmTC7PwPmTCNum OBJECT-TYPE
    SYNTAX      Integer32
    MAX-ACCESS  read-only
    STATUS      current
    DESCRIPTION "TCNum Historical PM of traffic class - 7 (TC7) on PxmPW"
    ::= { pxmTC7PwPmEntry  4 }

pxmTC7PwPmQueueingDiscardOctets OBJECT-TYPE
    SYNTAX      Counter64
    MAX-ACCESS  read-only
    STATUS      current
    DESCRIPTION "QueueingDiscardOctets Historical PM of traffic class - 7 (TC7) on PxmPW"
    ::= { pxmTC7PwPmEntry  5 }

pxmTC7PwPmQueueingDiscardPkts OBJECT-TYPE
    SYNTAX      Integer32
    MAX-ACCESS  read-only
    STATUS      current
    DESCRIPTION "QueueingDiscardPkts Historical PM of traffic class - 7 (TC7) on PxmPW"
    ::= { pxmTC7PwPmEntry  6 }

pxmTC7PwPmRandomGreenDropPkts OBJECT-TYPE
    SYNTAX      Counter64
    MAX-ACCESS  read-only
    STATUS      current
    DESCRIPTION "RandomGreenDropPkts Historical PM of traffic class - 7 (TC7) on PxmPW"
    ::= { pxmTC7PwPmEntry  7 }

pxmTC7PwPmRandomGreenDropOctets OBJECT-TYPE
    SYNTAX      Counter64
    MAX-ACCESS  read-only
    STATUS      current
    DESCRIPTION "RandomGreenDropOctets Historical PM of traffic class - 7 (TC7) on PxmPW"
    ::= { pxmTC7PwPmEntry  8 }

pxmTC7PwPmRandomYellowDropPkts OBJECT-TYPE
    SYNTAX      Counter64
    MAX-ACCESS  read-only
    STATUS      current
    DESCRIPTION "RandomYellowDropPkts Historical PM of traffic class - 7 (TC7) on PxmPW"
    ::= { pxmTC7PwPmEntry  9 }

pxmTC7PwPmRandomYellowDropOctets OBJECT-TYPE
    SYNTAX      Counter64
    MAX-ACCESS  read-only
    STATUS      current
    DESCRIPTION "RandomYellowDropOctets Historical PM of traffic class - 7 (TC7) on PxmPW"
    ::= { pxmTC7PwPmEntry  10 }

pxmTC7PwPmQueueingTransmitPkts OBJECT-TYPE
    SYNTAX      Counter64
    MAX-ACCESS  read-only
    STATUS      current
    DESCRIPTION "QueueingTransmitPkts Historical PM of traffic class - 7 (TC7) on PxmPW"
    ::= { pxmTC7PwPmEntry  11 }

pxmTC7PwPmQueueingTransmitOctets OBJECT-TYPE
    SYNTAX      Counter64
    MAX-ACCESS  read-only
    STATUS      current
    DESCRIPTION "QueueingTransmitOctets Historical PM of traffic class - 7 (TC7) on PxmPW"
    ::= { pxmTC7PwPmEntry  12 }

-- TC7 Real
pxmTC7PwPmRealTable OBJECT-TYPE
    SYNTAX      SEQUENCE OF PxmTC7PwPmRealEntry
    MAX-ACCESS  not-accessible
    STATUS      current
    DESCRIPTION
        "A list of PxmBwpPwPmReal entries. Each entry is uniquely identified by the value of ifIndex."
    ::= { pxmCmPwRealPm 5 } 

pxmTC7PwPmRealEntry  OBJECT-TYPE
    SYNTAX      PxmTC7PwPmRealEntry
    MAX-ACCESS  not-accessible
    STATUS      current
    DESCRIPTION
        "A PxmTC0PwPm entry containing real-time performance information pertaining to Infinera PxmPwPm interfaces.
        This table is a subclass of IfCommon. Entries will exist in this table only for interfaces of
        type PxmPwPm."
    INDEX { ifIndex }
    ::= { pxmTC7PwPmRealTable 1 }

PxmTC7PwPmRealEntry  ::= SEQUENCE {
    pxmTC7PwPmRealTCNum                     Integer32,
    pxmTC7PwPmRealTDQueuingCurrentQDepth    Integer32,
    pxmTC7PwPmRealQueueingDiscardOctets     Counter64,
    pxmTC7PwPmRealQueueingDiscardPkts       Integer32,
    pxmTC7PwPmRealRandomGreenDropPkts       Counter64,
    pxmTC7PwPmRealRandomGreenDropOctets     Counter64,
    pxmTC7PwPmRealRandomYellowDropPkts      Counter64,
    pxmTC7PwPmRealRandomYellowDropOctets    Counter64,
    pxmTC7PwPmRealQueueingTransmitPkts      Counter64,
    pxmTC7PwPmRealQueueingTransmitOctets    Counter64,
    pxmTC7PwPmRealQueueingMeanQSizeUnit     Integer32,
    pxmTC7PwPmRealMeanQSize                 Integer32
}

pxmTC7PwPmRealTCNum OBJECT-TYPE
    SYNTAX      Integer32
    MAX-ACCESS  read-only
    STATUS      current
    DESCRIPTION "TCNum Real PM of traffic class - 7 (TC7) on PxmPW"
    ::= { pxmTC7PwPmRealEntry  1 }

pxmTC7PwPmRealTDQueuingCurrentQDepth OBJECT-TYPE
    SYNTAX      Integer32
    MAX-ACCESS  read-only
    STATUS      current
    DESCRIPTION "TDQueuingCurrentQDepth Real PM of traffic class - 7 (TC7) on PxmPW"
    ::= { pxmTC7PwPmRealEntry  2 }

pxmTC7PwPmRealQueueingDiscardOctets OBJECT-TYPE
    SYNTAX      Counter64
    MAX-ACCESS  read-only
    STATUS      current
    DESCRIPTION "QueueingDiscardOctets Real PM of traffic class - 7 (TC7) on PxmPW"
    ::= { pxmTC7PwPmRealEntry  3 }

pxmTC7PwPmRealQueueingDiscardPkts OBJECT-TYPE
    SYNTAX      Integer32
    MAX-ACCESS  read-only
    STATUS      current
    DESCRIPTION "QueueingDiscardPkts Real PM of traffic class - 7 (TC7) on PxmPW"
    ::= { pxmTC7PwPmRealEntry  4 }

pxmTC7PwPmRealRandomGreenDropPkts OBJECT-TYPE
    SYNTAX      Counter64
    MAX-ACCESS  read-only
    STATUS      current
    DESCRIPTION "RandomGreenDropPkts Real PM of traffic class - 7 (TC7) on PxmPW"
    ::= { pxmTC7PwPmRealEntry  5 }

pxmTC7PwPmRealRandomGreenDropOctets OBJECT-TYPE
    SYNTAX      Counter64
    MAX-ACCESS  read-only
    STATUS      current
    DESCRIPTION "RandomGreenDropOctets Real PM of traffic class - 7 (TC7) on PxmPW"
    ::= { pxmTC7PwPmRealEntry  6 }

pxmTC7PwPmRealRandomYellowDropPkts OBJECT-TYPE
    SYNTAX      Counter64
    MAX-ACCESS  read-only
    STATUS      current
    DESCRIPTION "RandomYellowDropPkts Real PM of traffic class - 7 (TC7) on PxmPW"
    ::= { pxmTC7PwPmRealEntry  7 }

pxmTC7PwPmRealRandomYellowDropOctets OBJECT-TYPE
    SYNTAX      Counter64
    MAX-ACCESS  read-only
    STATUS      current
    DESCRIPTION "RandomYellowDropOctets Real PM of traffic class - 7 (TC7) on PxmPW"
    ::= { pxmTC7PwPmRealEntry  8 }

pxmTC7PwPmRealQueueingTransmitPkts OBJECT-TYPE
    SYNTAX      Counter64
    MAX-ACCESS  read-only
    STATUS      current
    DESCRIPTION "QueueingTransmitPkts Real PM of traffic class - 7 (TC7) on PxmPW"
    ::= { pxmTC7PwPmRealEntry  9 }

pxmTC7PwPmRealQueueingTransmitOctets OBJECT-TYPE
    SYNTAX      Counter64
    MAX-ACCESS  read-only
    STATUS      current
    DESCRIPTION "QueueingTransmitOctets Real PM of traffic class - 7 (TC7) on PxmPW"
    ::= { pxmTC7PwPmRealEntry  10 }

pxmTC7PwPmRealQueueingMeanQSizeUnit OBJECT-TYPE
    SYNTAX      Integer32
    MAX-ACCESS  read-only
    STATUS      current
    DESCRIPTION "QueueingMeanQSizeUnit Real PM of traffic class - 7 (TC7) on PxmPW"
    ::= { pxmTC7PwPmRealEntry  11 }

pxmTC7PwPmRealMeanQSize OBJECT-TYPE
    SYNTAX      Integer32
    MAX-ACCESS  read-only
    STATUS      current
    DESCRIPTION "MeanQSize Real PM of traffic class - 7 (TC7) on PxmPW"
    ::= { pxmTC7PwPmRealEntry  12 }

-- TCANY Historical
pxmTCANYPwPmTable OBJECT-TYPE
    SYNTAX      SEQUENCE OF PxmTCANYPwPmEntry
    MAX-ACCESS  not-accessible
    STATUS      current
    DESCRIPTION
        "A list of PxmBwpPwPmReal entries. Each entry is uniquely identified by the value of ifIndex."
    ::= { pxmCmPwPm 6 } 

pxmTCANYPwPmEntry  OBJECT-TYPE
    SYNTAX      PxmTCANYPwPmEntry
    MAX-ACCESS  not-accessible
    STATUS      current
    DESCRIPTION ""
    INDEX { ifIndex, pxmTCANYPwPmSampleDuration, pxmTCANYPwPmTimestamp }
    ::= { pxmTCANYPwPmTable 1 }

PxmTCANYPwPmEntry  ::= SEQUENCE {
    pxmTCANYPwPmTimestamp                 Integer32,
    pxmTCANYPwPmSampleDuration            INTEGER,
    pxmTCANYPwPmValidity                  TruthValue,
    pxmTCANYPwPmTCNum                     Integer32,
    pxmTCANYPwPmQueueingDiscardOctets     Counter64,
    pxmTCANYPwPmQueueingDiscardPkts       Integer32,
    pxmTCANYPwPmRandomGreenDropPkts       Counter64,
    pxmTCANYPwPmRandomGreenDropOctets     Counter64,
    pxmTCANYPwPmRandomYellowDropPkts      Counter64,
    pxmTCANYPwPmRandomYellowDropOctets    Counter64,
    pxmTCANYPwPmQueueingTransmitPkts      Counter64,
    pxmTCANYPwPmQueueingTransmitOctets    Counter64
}

pxmTCANYPwPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTCANYPwPmEntry  1 }

pxmTCANYPwPmSampleDuration OBJECT-TYPE
    SYNTAX      INTEGER {
                    fifteenMinutes(1),
                    day(2)
                }
    MAX-ACCESS  not-accessible
    STATUS      current
    DESCRIPTION
        "The duration of this sample."
    ::= { pxmTCANYPwPmEntry  2 }

pxmTCANYPwPmValidity OBJECT-TYPE
    SYNTAX      TruthValue
    MAX-ACCESS  read-only
    STATUS      current
    DESCRIPTION "Flag indicating if data was valid for the entire interval"
    ::= { pxmTCANYPwPmEntry  3 }

pxmTCANYPwPmTCNum OBJECT-TYPE
    SYNTAX      Integer32
    MAX-ACCESS  read-only
    STATUS      current
    DESCRIPTION "TCNum Historical PM of traffic class - ANY (TCANY) on PxmPW"
    ::= { pxmTCANYPwPmEntry  4 }

pxmTCANYPwPmQueueingDiscardOctets OBJECT-TYPE
    SYNTAX      Counter64
    MAX-ACCESS  read-only
    STATUS      current
    DESCRIPTION "QueueingDiscardOctets Historical PM of traffic class - ANY (TCANY) on PxmPW"
    ::= { pxmTCANYPwPmEntry  5 }

pxmTCANYPwPmQueueingDiscardPkts OBJECT-TYPE
    SYNTAX      Integer32
    MAX-ACCESS  read-only
    STATUS      current
    DESCRIPTION "QueueingDiscardPkts Historical PM of traffic class - ANY (TCANY) on PxmPW"
    ::= { pxmTCANYPwPmEntry  6 }

pxmTCANYPwPmRandomGreenDropPkts OBJECT-TYPE
    SYNTAX      Counter64
    MAX-ACCESS  read-only
    STATUS      current
    DESCRIPTION "RandomGreenDropPkts Historical PM of traffic class - ANY (TCANY) on PxmPW"
    ::= { pxmTCANYPwPmEntry  7 }

pxmTCANYPwPmRandomGreenDropOctets OBJECT-TYPE
    SYNTAX      Counter64
    MAX-ACCESS  read-only
    STATUS      current
    DESCRIPTION "RandomGreenDropOctets Historical PM of traffic class - ANY (TCANY) on PxmPW"
    ::= { pxmTCANYPwPmEntry  8 }

pxmTCANYPwPmRandomYellowDropPkts OBJECT-TYPE
    SYNTAX      Counter64
    MAX-ACCESS  read-only
    STATUS      current
    DESCRIPTION "RandomYellowDropPkts Historical PM of traffic class - ANY (TCANY) on PxmPW"
    ::= { pxmTCANYPwPmEntry  9 }

pxmTCANYPwPmRandomYellowDropOctets OBJECT-TYPE
    SYNTAX      Counter64
    MAX-ACCESS  read-only
    STATUS      current
    DESCRIPTION "RandomYellowDropOctets Historical PM of traffic class - ANY (TCANY) on PxmPW"
    ::= { pxmTCANYPwPmEntry  10 }

pxmTCANYPwPmQueueingTransmitPkts OBJECT-TYPE
    SYNTAX      Counter64
    MAX-ACCESS  read-only
    STATUS      current
    DESCRIPTION "QueueingTransmitPkts Historical PM of traffic class - ANY (TCANY) on PxmPW"
    ::= { pxmTCANYPwPmEntry  11 }

pxmTCANYPwPmQueueingTransmitOctets OBJECT-TYPE
    SYNTAX      Counter64
    MAX-ACCESS  read-only
    STATUS      current
    DESCRIPTION "QueueingTransmitOctets Historical PM of traffic class - ANY (TCANY) on PxmPW"
    ::= { pxmTCANYPwPmEntry  12 }

-- TCANY Real
pxmTCANYPwPmRealTable OBJECT-TYPE
    SYNTAX      SEQUENCE OF PxmTCANYPwPmRealEntry
    MAX-ACCESS  not-accessible
    STATUS      current
    DESCRIPTION
        "A list of PxmBwpPwPmReal entries. Each entry is uniquely identified by the value of ifIndex."
    ::= { pxmCmPwRealPm 6 } 

pxmTCANYPwPmRealEntry  OBJECT-TYPE
    SYNTAX      PxmTCANYPwPmRealEntry
    MAX-ACCESS  not-accessible
    STATUS      current
    DESCRIPTION
        "A PxmTC0PwPm entry containing real-time performance information pertaining to Infinera PxmPwPm interfaces.
        This table is a subclass of IfCommon. Entries will exist in this table only for interfaces of
        type PxmPwPm."
    INDEX { ifIndex }
    ::= { pxmTCANYPwPmRealTable 1 }

PxmTCANYPwPmRealEntry  ::= SEQUENCE {
    pxmTCANYPwPmRealTCNum                     Integer32,
    pxmTCANYPwPmRealTDQueuingCurrentQDepth    Integer32,
    pxmTCANYPwPmRealQueueingDiscardOctets     Counter64,
    pxmTCANYPwPmRealQueueingDiscardPkts       Integer32,
    pxmTCANYPwPmRealRandomGreenDropPkts       Counter64,
    pxmTCANYPwPmRealRandomGreenDropOctets     Counter64,
    pxmTCANYPwPmRealRandomYellowDropPkts      Counter64,
    pxmTCANYPwPmRealRandomYellowDropOctets    Counter64,
    pxmTCANYPwPmRealQueueingTransmitPkts      Counter64,
    pxmTCANYPwPmRealQueueingTransmitOctets    Counter64,
    pxmTCANYPwPmRealQueueingMeanQSizeUnit     Integer32,
    pxmTCANYPwPmRealMeanQSize                 Integer32
}

pxmTCANYPwPmRealTCNum OBJECT-TYPE
    SYNTAX      Integer32
    MAX-ACCESS  read-only
    STATUS      current
    DESCRIPTION "TCNum Real PM of traffic class - ANY (TCANY) on PxmPW"
    ::= { pxmTCANYPwPmRealEntry  1 }

pxmTCANYPwPmRealTDQueuingCurrentQDepth OBJECT-TYPE
    SYNTAX      Integer32
    MAX-ACCESS  read-only
    STATUS      current
    DESCRIPTION "TDQueuingCurrentQDepth Real PM of traffic class - ANY (TCANY) on PxmPW"
    ::= { pxmTCANYPwPmRealEntry  2 }

pxmTCANYPwPmRealQueueingDiscardOctets OBJECT-TYPE
    SYNTAX      Counter64
    MAX-ACCESS  read-only
    STATUS      current
    DESCRIPTION "QueueingDiscardOctets Real PM of traffic class - ANY (TCANY) on PxmPW"
    ::= { pxmTCANYPwPmRealEntry  3 }

pxmTCANYPwPmRealQueueingDiscardPkts OBJECT-TYPE
    SYNTAX      Integer32
    MAX-ACCESS  read-only
    STATUS      current
    DESCRIPTION "QueueingDiscardPkts Real PM of traffic class - ANY (TCANY) on PxmPW"
    ::= { pxmTCANYPwPmRealEntry  4 }

pxmTCANYPwPmRealRandomGreenDropPkts OBJECT-TYPE
    SYNTAX      Counter64
    MAX-ACCESS  read-only
    STATUS      current
    DESCRIPTION "RandomGreenDropPkts Real PM of traffic class - ANY (TCANY) on PxmPW"
    ::= { pxmTCANYPwPmRealEntry  5 }

pxmTCANYPwPmRealRandomGreenDropOctets OBJECT-TYPE
    SYNTAX      Counter64
    MAX-ACCESS  read-only
    STATUS      current
    DESCRIPTION "RandomGreenDropOctets Real PM of traffic class - ANY (TCANY) on PxmPW"
    ::= { pxmTCANYPwPmRealEntry  6 }

pxmTCANYPwPmRealRandomYellowDropPkts OBJECT-TYPE
    SYNTAX      Counter64
    MAX-ACCESS  read-only
    STATUS      current
    DESCRIPTION "RandomYellowDropPkts Real PM of traffic class - ANY (TCANY) on PxmPW"
    ::= { pxmTCANYPwPmRealEntry  7 }

pxmTCANYPwPmRealRandomYellowDropOctets OBJECT-TYPE
    SYNTAX      Counter64
    MAX-ACCESS  read-only
    STATUS      current
    DESCRIPTION "RandomYellowDropOctets Real PM of traffic class - ANY (TCANY) on PxmPW"
    ::= { pxmTCANYPwPmRealEntry  8 }

pxmTCANYPwPmRealQueueingTransmitPkts OBJECT-TYPE
    SYNTAX      Counter64
    MAX-ACCESS  read-only
    STATUS      current
    DESCRIPTION "QueueingTransmitPkts Real PM of traffic class - ANY (TCANY) on PxmPW"
    ::= { pxmTCANYPwPmRealEntry  9 }

pxmTCANYPwPmRealQueueingTransmitOctets OBJECT-TYPE
    SYNTAX      Counter64
    MAX-ACCESS  read-only
    STATUS      current
    DESCRIPTION "QueueingTransmitOctets Real PM of traffic class - ANY (TCANY) on PxmPW"
    ::= { pxmTCANYPwPmRealEntry  10 }

pxmTCANYPwPmRealQueueingMeanQSizeUnit OBJECT-TYPE
    SYNTAX      Integer32
    MAX-ACCESS  read-only
    STATUS      current
    DESCRIPTION "QueueingMeanQSizeUnit Real PM of traffic class - ANY (TCANY) on PxmPW"
    ::= { pxmTCANYPwPmRealEntry  11 }

pxmTCANYPwPmRealMeanQSize OBJECT-TYPE
    SYNTAX      Integer32
    MAX-ACCESS  read-only
    STATUS      current
    DESCRIPTION "MeanQSize Real PM of traffic class - ANY (TCANY) on PxmPW"
    ::= { pxmTCANYPwPmRealEntry  12 }

-- End of CM PMs

-- Conformance Statements
pxmPwPmConformance    OBJECT IDENTIFIER ::= { pxmPwPmMIB 3 }
pxmPwPmCompliances    OBJECT IDENTIFIER ::= { pxmPwPmConformance 1 }
pxmPwPmGroups         OBJECT IDENTIFIER ::= { pxmPwPmConformance 2 }

pxmPwPmCompliance MODULE-COMPLIANCE
    STATUS current
    DESCRIPTION
    "Describes the requirements for conformance to the PM-PXMPW-MIB"
    MODULE
        MANDATORY-GROUPS { pxmPwPmGroup }
    ::= { pxmPwPmCompliances 1 }

pxmPwPmRealCompliance MODULE-COMPLIANCE
    STATUS current
    DESCRIPTION
    "Describes the requirements for conformance to the pxmPwPmReal-MIB"
    MODULE
        MANDATORY-GROUPS { pxmPwPmRealGroup }
    ::= { pxmPwPmCompliances 2 }

pxmPwPmGroup OBJECT-GROUP
    OBJECTS {
        pxmPwPmValidity,
        pxmPwPmRxPackets,
        pxmPwPmRxOctets,
        pxmPwPmTxPackets,
        pxmPwPmTxOctets
    }
    STATUS current
    DESCRIPTION
        " A collection of objects for reading the historical performance of the pxmPw."
    ::= { pxmPwPmGroups 1 }

pxmPwPmRealGroup OBJECT-GROUP
    OBJECTS {
        pxmPwPmRealRxPackets,
        pxmPwPmRealRxOctets,
        pxmPwPmRealTxPackets,
        pxmPwPmRealTxOctets
    }
    STATUS current
    DESCRIPTION
        " A collection of objects for reading the real-time performance of the pxmPw."
    ::= { pxmPwPmGroups 2 }

pxmTC0PwPmGroup OBJECT-GROUP
    OBJECTS {
        pxmTC0PwPmValidity,
        pxmTC0PwPmTCNum,
        pxmTC0PwPmQueueingDiscardOctets,
        pxmTC0PwPmQueueingDiscardPkts,
        pxmTC0PwPmRandomGreenDropPkts,
        pxmTC0PwPmRandomGreenDropOctets,
        pxmTC0PwPmRandomYellowDropPkts,
        pxmTC0PwPmRandomYellowDropOctets,
        pxmTC0PwPmQueueingTransmitPkts,
        pxmTC0PwPmQueueingTransmitOctets
    }
    STATUS current
    DESCRIPTION
        " A collection of objects for reading the real-time performance of the pxmPw."
    ::= { pxmPwPmGroups 3 }

pxmTC0PwPmRealGroup OBJECT-GROUP
    OBJECTS {
        pxmTC0PwPmRealTCNum,
        pxmTC0PwPmRealTDQueuingCurrentQDepth,
        pxmTC0PwPmRealQueueingDiscardOctets,
        pxmTC0PwPmRealQueueingDiscardPkts,
        pxmTC0PwPmRealRandomGreenDropPkts,
        pxmTC0PwPmRealRandomGreenDropOctets,
        pxmTC0PwPmRealRandomYellowDropPkts,
        pxmTC0PwPmRealRandomYellowDropOctets,
        pxmTC0PwPmRealQueueingTransmitPkts,
        pxmTC0PwPmRealQueueingTransmitOctets,
        pxmTC0PwPmRealQueueingMeanQSizeUnit,
        pxmTC0PwPmRealMeanQSize
    }
    STATUS current
    DESCRIPTION
        " A collection of objects for reading the real-time performance of the pxmPw."
    ::= { pxmPwPmGroups 4 }

pxmTC2PwPmGroup OBJECT-GROUP
    OBJECTS {
        pxmTC2PwPmValidity,
        pxmTC2PwPmTCNum,
        pxmTC2PwPmQueueingDiscardOctets,
        pxmTC2PwPmQueueingDiscardPkts,
        pxmTC2PwPmRandomGreenDropPkts,
        pxmTC2PwPmRandomGreenDropOctets,
        pxmTC2PwPmRandomYellowDropPkts,
        pxmTC2PwPmRandomYellowDropOctets,
        pxmTC2PwPmQueueingTransmitPkts,
        pxmTC2PwPmQueueingTransmitOctets
    }
    STATUS current
    DESCRIPTION
        " A collection of objects for reading the real-time performance of the pxmPw."
    ::= { pxmPwPmGroups 5 }

pxmTC2PwPmRealGroup OBJECT-GROUP
    OBJECTS {
        pxmTC2PwPmRealTCNum,
        pxmTC2PwPmRealTDQueuingCurrentQDepth,
        pxmTC2PwPmRealQueueingDiscardOctets,
        pxmTC2PwPmRealQueueingDiscardPkts,
        pxmTC2PwPmRealRandomGreenDropPkts,
        pxmTC2PwPmRealRandomGreenDropOctets,
        pxmTC2PwPmRealRandomYellowDropPkts,
        pxmTC2PwPmRealRandomYellowDropOctets,
        pxmTC2PwPmRealQueueingTransmitPkts,
        pxmTC2PwPmRealQueueingTransmitOctets,
        pxmTC2PwPmRealQueueingMeanQSizeUnit,
        pxmTC2PwPmRealMeanQSize
    }
    STATUS current
    DESCRIPTION
        " A collection of objects for reading the real-time performance of the pxmPw."
    ::= { pxmPwPmGroups 6 }

pxmTC4PwPmGroup OBJECT-GROUP
    OBJECTS {
        pxmTC4PwPmValidity,
        pxmTC4PwPmTCNum,
        pxmTC4PwPmQueueingDiscardOctets,
        pxmTC4PwPmQueueingDiscardPkts,
        pxmTC4PwPmRandomGreenDropPkts,
        pxmTC4PwPmRandomGreenDropOctets,
        pxmTC4PwPmRandomYellowDropPkts,
        pxmTC4PwPmRandomYellowDropOctets,
        pxmTC4PwPmQueueingTransmitPkts,
        pxmTC4PwPmQueueingTransmitOctets
    }
    STATUS current
    DESCRIPTION
        " A collection of objects for reading the real-time performance of the pxmPw."
    ::= { pxmPwPmGroups 7 }

pxmTC4PwPmRealGroup OBJECT-GROUP
    OBJECTS {
        pxmTC4PwPmRealTCNum,
        pxmTC4PwPmRealTDQueuingCurrentQDepth,
        pxmTC4PwPmRealQueueingDiscardOctets,
        pxmTC4PwPmRealQueueingDiscardPkts,
        pxmTC4PwPmRealRandomGreenDropPkts,
        pxmTC4PwPmRealRandomGreenDropOctets,
        pxmTC4PwPmRealRandomYellowDropPkts,
        pxmTC4PwPmRealRandomYellowDropOctets,
        pxmTC4PwPmRealQueueingTransmitPkts,
        pxmTC4PwPmRealQueueingTransmitOctets,
        pxmTC4PwPmRealQueueingMeanQSizeUnit,
        pxmTC4PwPmRealMeanQSize
    }
    STATUS current
    DESCRIPTION
        " A collection of objects for reading the real-time performance of the pxmPw."
    ::= { pxmPwPmGroups 8 }

pxmTC6PwPmGroup OBJECT-GROUP
    OBJECTS {
        pxmTC6PwPmValidity,
        pxmTC6PwPmTCNum,
        pxmTC6PwPmQueueingDiscardOctets,
        pxmTC6PwPmQueueingDiscardPkts,
        pxmTC6PwPmRandomGreenDropPkts,
        pxmTC6PwPmRandomGreenDropOctets,
        pxmTC6PwPmRandomYellowDropPkts,
        pxmTC6PwPmRandomYellowDropOctets,
        pxmTC6PwPmQueueingTransmitPkts,
        pxmTC6PwPmQueueingTransmitOctets
    }
    STATUS current
    DESCRIPTION
        " A collection of objects for reading the real-time performance of the pxmPw."
    ::= { pxmPwPmGroups 9 }

pxmTC6PwPmRealGroup OBJECT-GROUP
    OBJECTS {
        pxmTC6PwPmRealTCNum,
        pxmTC6PwPmRealTDQueuingCurrentQDepth,
        pxmTC6PwPmRealQueueingDiscardOctets,
        pxmTC6PwPmRealQueueingDiscardPkts,
        pxmTC6PwPmRealRandomGreenDropPkts,
        pxmTC6PwPmRealRandomGreenDropOctets,
        pxmTC6PwPmRealRandomYellowDropPkts,
        pxmTC6PwPmRealRandomYellowDropOctets,
        pxmTC6PwPmRealQueueingTransmitPkts,
        pxmTC6PwPmRealQueueingTransmitOctets,
        pxmTC6PwPmRealQueueingMeanQSizeUnit,
        pxmTC6PwPmRealMeanQSize
    }
    STATUS current
    DESCRIPTION
        " A collection of objects for reading the real-time performance of the pxmPw."
    ::= { pxmPwPmGroups 10 }

pxmTC7PwPmGroup OBJECT-GROUP
    OBJECTS {
        pxmTC7PwPmValidity,
        pxmTC7PwPmTCNum,
        pxmTC7PwPmQueueingDiscardOctets,
        pxmTC7PwPmQueueingDiscardPkts,
        pxmTC7PwPmRandomGreenDropPkts,
        pxmTC7PwPmRandomGreenDropOctets,
        pxmTC7PwPmRandomYellowDropPkts,
        pxmTC7PwPmRandomYellowDropOctets,
        pxmTC7PwPmQueueingTransmitPkts,
        pxmTC7PwPmQueueingTransmitOctets
    }
    STATUS current
    DESCRIPTION
        " A collection of objects for reading the real-time performance of the pxmPw."
    ::= { pxmPwPmGroups 11 }

pxmTC7PwPmRealGroup OBJECT-GROUP
    OBJECTS {
        pxmTC7PwPmRealTCNum,
        pxmTC7PwPmRealTDQueuingCurrentQDepth,
        pxmTC7PwPmRealQueueingDiscardOctets,
        pxmTC7PwPmRealQueueingDiscardPkts,
        pxmTC7PwPmRealRandomGreenDropPkts,
        pxmTC7PwPmRealRandomGreenDropOctets,
        pxmTC7PwPmRealRandomYellowDropPkts,
        pxmTC7PwPmRealRandomYellowDropOctets,
        pxmTC7PwPmRealQueueingTransmitPkts,
        pxmTC7PwPmRealQueueingTransmitOctets,
        pxmTC7PwPmRealQueueingMeanQSizeUnit,
        pxmTC7PwPmRealMeanQSize
    }
    STATUS current
    DESCRIPTION
        " A collection of objects for reading the real-time performance of the pxmPw."
    ::= { pxmPwPmGroups 12 }

pxmTCANYPwPmGroup OBJECT-GROUP
    OBJECTS {
        pxmTCANYPwPmValidity,
        pxmTCANYPwPmTCNum,
        pxmTCANYPwPmQueueingDiscardOctets,
        pxmTCANYPwPmQueueingDiscardPkts,
        pxmTCANYPwPmRandomGreenDropPkts,
        pxmTCANYPwPmRandomGreenDropOctets,
        pxmTCANYPwPmRandomYellowDropPkts,
        pxmTCANYPwPmRandomYellowDropOctets,
        pxmTCANYPwPmQueueingTransmitPkts,
        pxmTCANYPwPmQueueingTransmitOctets
    }
    STATUS current
    DESCRIPTION
        " A collection of objects for reading the real-time performance of the pxmPw."
    ::= { pxmPwPmGroups 13 }

pxmTCANYPwPmRealGroup OBJECT-GROUP
    OBJECTS {
        pxmTCANYPwPmRealTCNum,
        pxmTCANYPwPmRealTDQueuingCurrentQDepth,
        pxmTCANYPwPmRealQueueingDiscardOctets,
        pxmTCANYPwPmRealQueueingDiscardPkts,
        pxmTCANYPwPmRealRandomGreenDropPkts,
        pxmTCANYPwPmRealRandomGreenDropOctets,
        pxmTCANYPwPmRealRandomYellowDropPkts,
        pxmTCANYPwPmRealRandomYellowDropOctets,
        pxmTCANYPwPmRealQueueingTransmitPkts,
        pxmTCANYPwPmRealQueueingTransmitOctets,
        pxmTCANYPwPmRealQueueingMeanQSizeUnit,
        pxmTCANYPwPmRealMeanQSize
    }
    STATUS current
    DESCRIPTION
        " A collection of objects for reading the real-time performance of the pxmPw."
    ::= { pxmPwPmGroups 14 }

END

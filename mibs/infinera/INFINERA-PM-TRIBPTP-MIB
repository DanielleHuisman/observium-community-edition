-- *****************************************************************
-- INFINERA-PM-TRIBPTP-MIB
-- 
-- October 2008, Sharfuddin Syed / Narendra Gupta
-- 
-- 
-- Copyright (c) 2008-2012 by Infinera Inc.
-- All rights reserved.
-- ****************************************************************

INFINERA-PM-TRIBPTP-MIB DEFINITIONS ::= BEGIN

IMPORTS
    MODULE-IDENTITY, OBJECT-TYPE,
    Integer32                                   FROM SNMPv2-SMI
    MODULE-COMPLIANCE, OBJECT-GROUP             FROM SNMPv2-CONF
    TruthValue                                  FROM SNMPv2-TC
    ifIndex                                     FROM IF-MIB
    FloatHundredths                             FROM INFINERA-TC-MIB
    commonPerfMon                               FROM INFINERA-REG-MIB;


tribPtpPmMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "200810200000Z" 
    DESCRIPTION
        "First Version"
    ::= { commonPerfMon 3 }



tribPtpPmTable OBJECT-TYPE
    SYNTAX      SEQUENCE OF TribPtpPmEntry
    MAX-ACCESS  not-accessible
    STATUS      current
    DESCRIPTION
        "A list of TribPtpPm entries. Each entry is uniquely identified by the value of ifIndex, sampleDuration and tribPtpPmTimestamp."
    ::= { tribPtpPmMIB 2 } 

tribPtpPmEntry  OBJECT-TYPE
    SYNTAX      TribPtpPmEntry
    MAX-ACCESS  not-accessible
    STATUS      current
    DESCRIPTION
        "A TribPtp entry containing historical performance information pertaining to
        Infinera TribPtp interfaces. . This table is a subclass of IfCommon.
        Entries will exist in this table only for interfaces of type TribPtp.
        Each interface may have a number of entries in this table, each with a different combination
        of timestamp and sample duration."
    INDEX { ifIndex, tribPtpPmSampleDuration, tribPtpPmTimestamp }
    ::= { tribPtpPmTable 1 }


TribPtpPmEntry  ::= SEQUENCE {
    tribPtpPmTimestamp        Integer32,
    tribPtpPmSampleDuration   INTEGER,
    tribPtpPmValidity         TruthValue,
    tribPtpPmTomTxLBCMin      FloatHundredths,
    tribPtpPmTomTxLBCMax      FloatHundredths,
    tribPtpPmTomTxLBCAve      FloatHundredths,
    tribPtpPmTomOptMin        FloatHundredths,
    tribPtpPmTomOptMax        FloatHundredths,
    tribPtpPmTomOptAve        FloatHundredths,
    tribPtpPmTomOprMin        FloatHundredths,
    tribPtpPmTomOprMax        FloatHundredths,
    tribPtpPmTomOprAve        FloatHundredths,
    tribPtpPmTomTxLBC02Min      FloatHundredths,
    tribPtpPmTomTxLBC02Max      FloatHundredths,
    tribPtpPmTomTxLBC02Ave      FloatHundredths,    
    tribPtpPmTomOpt02Min        FloatHundredths,
    tribPtpPmTomOpt02Max        FloatHundredths,
    tribPtpPmTomOpt02Ave        FloatHundredths,
    tribPtpPmTomOpr02Min        FloatHundredths,
    tribPtpPmTomOpr02Max        FloatHundredths,
    tribPtpPmTomOpr02Ave        FloatHundredths,
    tribPtpPmTomTxLBC03Min      FloatHundredths,
    tribPtpPmTomTxLBC03Max      FloatHundredths,
    tribPtpPmTomTxLBC03Ave      FloatHundredths,
    tribPtpPmTomOpt03Min        FloatHundredths,
    tribPtpPmTomOpt03Max        FloatHundredths,
    tribPtpPmTomOpt03Ave        FloatHundredths,
    tribPtpPmTomOpr03Min        FloatHundredths,
    tribPtpPmTomOpr03Max        FloatHundredths,
    tribPtpPmTomOpr03Ave        FloatHundredths,
    tribPtpPmTomTxLBC04Min      FloatHundredths,
    tribPtpPmTomTxLBC04Max      FloatHundredths,
    tribPtpPmTomTxLBC04Ave      FloatHundredths,
    tribPtpPmTomOpt04Min        FloatHundredths,
    tribPtpPmTomOpt04Max        FloatHundredths,
    tribPtpPmTomOpt04Ave        FloatHundredths,
    tribPtpPmTomOpr04Min        FloatHundredths,
    tribPtpPmTomOpr04Max        FloatHundredths,
    tribPtpPmTomOpr04Ave        FloatHundredths,
    tribPtpPmTomOptTotalMin     FloatHundredths,
    tribPtpPmTomOptTotalMax     FloatHundredths,
    tribPtpPmTomOptTotalAve     FloatHundredths,
    tribPtpPmTomOprTotalMin     FloatHundredths,
    tribPtpPmTomOprTotalMax     FloatHundredths,
    tribPtpPmTomOprTotalAve     FloatHundredths
}

tribPtpPmTimestamp OBJECT-TYPE
    SYNTAX      Integer32 (0..2147483647)
    MAX-ACCESS  not-accessible
    STATUS      current
    DESCRIPTION
        "End Time stamp for this interval. If this time is later than the current time,
        then the data for this bucket is currently being collected."
    ::= { tribPtpPmEntry  1 }


tribPtpPmSampleDuration OBJECT-TYPE
    SYNTAX      INTEGER {
                    fifteenMinutes(1),
                    day(2)
                }
    MAX-ACCESS  not-accessible
    STATUS      current
    DESCRIPTION
        "The duration of this sample."
    ::= { tribPtpPmEntry  2 }


tribPtpPmValidity OBJECT-TYPE
    SYNTAX      TruthValue
    MAX-ACCESS  read-only
    STATUS      current
    DESCRIPTION "Flag indicating if data was valid for the entire interval"
    ::= { tribPtpPmEntry  3 }


tribPtpPmTomTxLBCMin OBJECT-TYPE
    SYNTAX      FloatHundredths
    MAX-ACCESS  read-only
    STATUS      current
    DESCRIPTION "TOM Transmitted Laser Bias Current, minimum (mA)"
    ::= { tribPtpPmEntry  4 }


tribPtpPmTomTxLBCMax OBJECT-TYPE
    SYNTAX      FloatHundredths
    MAX-ACCESS  read-only
    STATUS      current
    DESCRIPTION "TOM Transmitted Laser Bias Current, maximum (mA)"
    ::= { tribPtpPmEntry  5 }


tribPtpPmTomTxLBCAve OBJECT-TYPE
    SYNTAX      FloatHundredths
    MAX-ACCESS  read-only
    STATUS      current
    DESCRIPTION "TOM Transmitted Laser Bias Current, average (mA)"
    ::= { tribPtpPmEntry  6 }


tribPtpPmTomOptMin OBJECT-TYPE
    SYNTAX      FloatHundredths
    MAX-ACCESS  read-only
    STATUS      current
    DESCRIPTION "TOM Optical Power Transmitted, minimum (dBm)"
    ::= { tribPtpPmEntry  7 }


tribPtpPmTomOptMax OBJECT-TYPE
    SYNTAX      FloatHundredths
    MAX-ACCESS  read-only
    STATUS      current
    DESCRIPTION "TOM Optical Power Transmitted, maximum (dBm)"
    ::= { tribPtpPmEntry  8 }


tribPtpPmTomOptAve OBJECT-TYPE
    SYNTAX      FloatHundredths
    MAX-ACCESS  read-only
    STATUS      current
    DESCRIPTION "TOM Optical Power Transmitted, average (dBm)"
    ::= { tribPtpPmEntry  9 }


tribPtpPmTomOprMin OBJECT-TYPE
    SYNTAX      FloatHundredths
    MAX-ACCESS  read-only
    STATUS      current
    DESCRIPTION "Tom Optical Power Received, minimum (dBm)"
    ::= { tribPtpPmEntry  10 }


tribPtpPmTomOprMax OBJECT-TYPE
    SYNTAX      FloatHundredths
    MAX-ACCESS  read-only
    STATUS      current
    DESCRIPTION "Tom Optical Power Received, maximum (dBm)"
    ::= { tribPtpPmEntry  11 }


tribPtpPmTomOprAve OBJECT-TYPE
    SYNTAX      FloatHundredths
    MAX-ACCESS  read-only
    STATUS      current
    DESCRIPTION "Tom Optical Power Received, average (dBm)"
    ::= { tribPtpPmEntry  12 }


tribPtpPmTomTxLBC02Min OBJECT-TYPE
    SYNTAX      FloatHundredths
    MAX-ACCESS  read-only
    STATUS      current
    DESCRIPTION "TOM Transmitted Laser Bias Current, minimum (mA)"
    ::= { tribPtpPmEntry  13 }


tribPtpPmTomTxLBC02Max OBJECT-TYPE
    SYNTAX      FloatHundredths
    MAX-ACCESS  read-only
    STATUS      current
    DESCRIPTION "TOM Transmitted Laser Bias Current, maximum (mA)"
    ::= { tribPtpPmEntry  14 }


tribPtpPmTomTxLBC02Ave OBJECT-TYPE
    SYNTAX      FloatHundredths
    MAX-ACCESS  read-only
    STATUS      current
    DESCRIPTION "TOM Transmitted Laser Bias Current, average (mA)"
    ::= { tribPtpPmEntry  15 }


tribPtpPmTomOpt02Min OBJECT-TYPE
    SYNTAX      FloatHundredths
    MAX-ACCESS  read-only
    STATUS      current
    DESCRIPTION "TOM Optical Power Transmitted, minimum (dBm)"
    ::= { tribPtpPmEntry  16 }


tribPtpPmTomOpt02Max OBJECT-TYPE
    SYNTAX      FloatHundredths
    MAX-ACCESS  read-only
    STATUS      current
    DESCRIPTION "TOM Optical Power Transmitted, maximum (dBm)"
    ::= { tribPtpPmEntry  17 }


tribPtpPmTomOpt02Ave OBJECT-TYPE
    SYNTAX      FloatHundredths
    MAX-ACCESS  read-only
    STATUS      current
    DESCRIPTION "TOM Optical Power Transmitted, average (dBm)"
    ::= { tribPtpPmEntry  18 }


tribPtpPmTomOpr02Min OBJECT-TYPE
    SYNTAX      FloatHundredths
    MAX-ACCESS  read-only
    STATUS      current
    DESCRIPTION "Tom Optical Power Received, minimum (dBm)"
    ::= { tribPtpPmEntry  19 }


tribPtpPmTomOpr02Max OBJECT-TYPE
    SYNTAX      FloatHundredths
    MAX-ACCESS  read-only
    STATUS      current
    DESCRIPTION "Tom Optical Power Received, maximum (dBm)"
    ::= { tribPtpPmEntry  20 }


tribPtpPmTomOpr02Ave OBJECT-TYPE
    SYNTAX      FloatHundredths
    MAX-ACCESS  read-only
    STATUS      current
    DESCRIPTION "Tom Optical Power Received, average (dBm)"
    ::= { tribPtpPmEntry  21 }


tribPtpPmTomTxLBC03Min OBJECT-TYPE
    SYNTAX      FloatHundredths
    MAX-ACCESS  read-only
    STATUS      current
    DESCRIPTION "TOM Transmitted Laser Bias Current, minimum (mA)"
    ::= { tribPtpPmEntry  22 }


tribPtpPmTomTxLBC03Max OBJECT-TYPE
    SYNTAX      FloatHundredths
    MAX-ACCESS  read-only
    STATUS      current
    DESCRIPTION "TOM Transmitted Laser Bias Current, maximum (mA)"
    ::= { tribPtpPmEntry  23 }


tribPtpPmTomTxLBC03Ave OBJECT-TYPE
    SYNTAX      FloatHundredths
    MAX-ACCESS  read-only
    STATUS      current
    DESCRIPTION "TOM Transmitted Laser Bias Current, average (mA)"
    ::= { tribPtpPmEntry  24 }

tribPtpPmTomOpt03Min OBJECT-TYPE
    SYNTAX      FloatHundredths
    MAX-ACCESS  read-only
    STATUS      current
    DESCRIPTION "TOM Optical Power Transmitted, minimum (dBm)"
    ::= { tribPtpPmEntry  25 }


tribPtpPmTomOpt03Max OBJECT-TYPE
    SYNTAX      FloatHundredths
    MAX-ACCESS  read-only
    STATUS      current
    DESCRIPTION "TOM Optical Power Transmitted, maximum (dBm)"
    ::= { tribPtpPmEntry  26 }


tribPtpPmTomOpt03Ave OBJECT-TYPE
    SYNTAX      FloatHundredths
    MAX-ACCESS  read-only
    STATUS      current
    DESCRIPTION "TOM Optical Power Transmitted, average (dBm)"
    ::= { tribPtpPmEntry  27 }


tribPtpPmTomOpr03Min OBJECT-TYPE
    SYNTAX      FloatHundredths
    MAX-ACCESS  read-only
    STATUS      current
    DESCRIPTION "Tom Optical Power Received, minimum (dBm)"
    ::= { tribPtpPmEntry  28 }


tribPtpPmTomOpr03Max OBJECT-TYPE
    SYNTAX      FloatHundredths
    MAX-ACCESS  read-only
    STATUS      current
    DESCRIPTION "Tom Optical Power Received, maximum (dBm)"
    ::= { tribPtpPmEntry  29 }


tribPtpPmTomOpr03Ave OBJECT-TYPE
    SYNTAX      FloatHundredths
    MAX-ACCESS  read-only
    STATUS      current
    DESCRIPTION "Tom Optical Power Received, average (dBm)"
    ::= { tribPtpPmEntry  30 }


tribPtpPmTomTxLBC04Min OBJECT-TYPE
    SYNTAX      FloatHundredths
    MAX-ACCESS  read-only
    STATUS      current
    DESCRIPTION "TOM Transmitted Laser Bias Current, minimum (mA)"
    ::= { tribPtpPmEntry  31 }


tribPtpPmTomTxLBC04Max OBJECT-TYPE
    SYNTAX      FloatHundredths
    MAX-ACCESS  read-only
    STATUS      current
    DESCRIPTION "TOM Transmitted Laser Bias Current, maximum (mA)"
    ::= { tribPtpPmEntry  32 }


tribPtpPmTomTxLBC04Ave OBJECT-TYPE
    SYNTAX      FloatHundredths
    MAX-ACCESS  read-only
    STATUS      current
    DESCRIPTION "TOM Transmitted Laser Bias Current, average (mA)"
    ::= { tribPtpPmEntry  33 }


tribPtpPmTomOpt04Min OBJECT-TYPE
    SYNTAX      FloatHundredths
    MAX-ACCESS  read-only
    STATUS      current
    DESCRIPTION "TOM Optical Power Transmitted, minimum (dBm)"
    ::= { tribPtpPmEntry  34 }


tribPtpPmTomOpt04Max OBJECT-TYPE
    SYNTAX      FloatHundredths
    MAX-ACCESS  read-only
    STATUS      current
    DESCRIPTION "TOM Optical Power Transmitted, maximum (dBm)"
    ::= { tribPtpPmEntry  35 }


tribPtpPmTomOpt04Ave OBJECT-TYPE
    SYNTAX      FloatHundredths
    MAX-ACCESS  read-only
    STATUS      current
    DESCRIPTION "TOM Optical Power Transmitted, average (dBm)"
    ::= { tribPtpPmEntry  36 }


tribPtpPmTomOpr04Min OBJECT-TYPE
    SYNTAX      FloatHundredths
    MAX-ACCESS  read-only
    STATUS      current
    DESCRIPTION "Tom Optical Power Received, minimum (dBm)"
    ::= { tribPtpPmEntry  37 }


tribPtpPmTomOpr04Max OBJECT-TYPE
    SYNTAX      FloatHundredths
    MAX-ACCESS  read-only
    STATUS      current
    DESCRIPTION "Tom Optical Power Received, maximum (dBm)"
    ::= { tribPtpPmEntry  38 }


tribPtpPmTomOpr04Ave OBJECT-TYPE
    SYNTAX      FloatHundredths
    MAX-ACCESS  read-only
    STATUS      current
    DESCRIPTION "Tom Optical Power Received, average (dBm)"
    ::= { tribPtpPmEntry  39 }


tribPtpPmTomOptTotalMin OBJECT-TYPE
    SYNTAX      FloatHundredths
    MAX-ACCESS  read-only
    STATUS      current
    DESCRIPTION ""
    ::= { tribPtpPmEntry 40 }



tribPtpPmTomOptTotalMax OBJECT-TYPE
    SYNTAX      FloatHundredths
    MAX-ACCESS  read-only
    STATUS      current
    DESCRIPTION ""
    ::= { tribPtpPmEntry 41 }

tribPtpPmTomOptTotalAve OBJECT-TYPE
    SYNTAX      FloatHundredths
    MAX-ACCESS  read-only
    STATUS      current
    DESCRIPTION ""
    ::= { tribPtpPmEntry 42 }


tribPtpPmTomOprTotalMin OBJECT-TYPE
    SYNTAX      FloatHundredths
    MAX-ACCESS  read-only
    STATUS      current
    DESCRIPTION ""
    ::= { tribPtpPmEntry 43 }



tribPtpPmTomOprTotalMax OBJECT-TYPE
    SYNTAX      FloatHundredths
    MAX-ACCESS  read-only
    STATUS      current
    DESCRIPTION ""
    ::= { tribPtpPmEntry 44 }

tribPtpPmTomOprTotalAve OBJECT-TYPE
    SYNTAX      FloatHundredths
    MAX-ACCESS  read-only
    STATUS      current
    DESCRIPTION ""
    ::= { tribPtpPmEntry 45 }


tribPtpPmRealTable OBJECT-TYPE
    SYNTAX      SEQUENCE OF TribPtpPmRealEntry
    MAX-ACCESS  not-accessible
    STATUS      current
    DESCRIPTION
        "A list of TribPtpPmReal entries. Each entry is uniquely identified by the value of ifIndex."
    ::= { tribPtpPmMIB 1 } 

tribPtpPmRealEntry  OBJECT-TYPE
    SYNTAX      TribPtpPmRealEntry
    MAX-ACCESS  not-accessible
    STATUS      current
    DESCRIPTION
        "A TribPtp entry containing real-time performance information pertaining to
        Infinera TribPtp interfaces. . This table is a subclass of IfCommon.
        Entries will exist in this table only for interfaces of type TribPtp."
    INDEX { ifIndex }
    ::= { tribPtpPmRealTable 1 }


TribPtpPmRealEntry  ::= SEQUENCE {
    tribPtpPmRealTomTxLBC    FloatHundredths,
    tribPtpPmRealTomOpt      FloatHundredths,
    tribPtpPmRealTomOpr      FloatHundredths,
    tribPtpPmRealTomTxLBC02    FloatHundredths,
	tribPtpPmRealTomOpt02    FloatHundredths,
    tribPtpPmRealTomOpr02    FloatHundredths,
    tribPtpPmRealTomTxLBC03    FloatHundredths,
    tribPtpPmRealTomOpt03    FloatHundredths,
    tribPtpPmRealTomOpr03    FloatHundredths,
    tribPtpPmRealTomTxLBC04    FloatHundredths,
    tribPtpPmRealTomOpt04    FloatHundredths,
    tribPtpPmRealTomOpr04    FloatHundredths,
    tribPtpPmRealTomOptTotal FloatHundredths,
    tribPtpPmRealTomOprTotal FloatHundredths
}

tribPtpPmRealTomTxLBC OBJECT-TYPE
    SYNTAX      FloatHundredths
    MAX-ACCESS  read-only
    STATUS      current
    DESCRIPTION "TOM Transmitted Laser Bias Current"
    ::= { tribPtpPmRealEntry  1 }


tribPtpPmRealTomOpt OBJECT-TYPE
    SYNTAX      FloatHundredths
    MAX-ACCESS  read-only
    STATUS      current
    DESCRIPTION "TOM Optical Power Transmitted"
    ::= { tribPtpPmRealEntry  2 }


tribPtpPmRealTomOpr OBJECT-TYPE
    SYNTAX      FloatHundredths
    MAX-ACCESS  read-only
    STATUS      current
    DESCRIPTION "Tom Optical Power Received"
    ::= { tribPtpPmRealEntry  3 }

tribPtpPmRealTomTxLBC02 OBJECT-TYPE
    SYNTAX      FloatHundredths
    MAX-ACCESS  read-only
    STATUS      current
    DESCRIPTION "TOM Transmitted Laser Bias Current"
    ::= { tribPtpPmRealEntry  4 }

tribPtpPmRealTomOpt02 OBJECT-TYPE
    SYNTAX      FloatHundredths
    MAX-ACCESS  read-only
    STATUS      current
    DESCRIPTION "TOM Optical Power Transmitted"
    ::= { tribPtpPmRealEntry  5 }

tribPtpPmRealTomOpr02 OBJECT-TYPE
    SYNTAX      FloatHundredths
    MAX-ACCESS  read-only
    STATUS      current
    DESCRIPTION "Tom Optical Power Received"
    ::= { tribPtpPmRealEntry  6 }

tribPtpPmRealTomTxLBC03 OBJECT-TYPE
    SYNTAX      FloatHundredths
    MAX-ACCESS  read-only
    STATUS      current
    DESCRIPTION "TOM Transmitted Laser Bias Current"
    ::= { tribPtpPmRealEntry  7 }

tribPtpPmRealTomOpt03 OBJECT-TYPE
    SYNTAX      FloatHundredths
    MAX-ACCESS  read-only
    STATUS      current
    DESCRIPTION "TOM Optical Power Transmitted"
    ::= { tribPtpPmRealEntry  8 }


tribPtpPmRealTomOpr03 OBJECT-TYPE
    SYNTAX      FloatHundredths
    MAX-ACCESS  read-only
    STATUS      current
    DESCRIPTION "Tom Optical Power Received"
    ::= { tribPtpPmRealEntry  9 }

tribPtpPmRealTomTxLBC04 OBJECT-TYPE
    SYNTAX      FloatHundredths
    MAX-ACCESS  read-only
    STATUS      current
    DESCRIPTION "TOM Transmitted Laser Bias Current"
    ::= { tribPtpPmRealEntry  10 }

tribPtpPmRealTomOpt04 OBJECT-TYPE
    SYNTAX      FloatHundredths
    MAX-ACCESS  read-only
    STATUS      current
    DESCRIPTION "TOM Optical Power Transmitted"
    ::= { tribPtpPmRealEntry  11 }


tribPtpPmRealTomOpr04 OBJECT-TYPE
    SYNTAX      FloatHundredths
    MAX-ACCESS  read-only
    STATUS      current
    DESCRIPTION "Tom Optical Power Received"
    ::= { tribPtpPmRealEntry  12 }

tribPtpPmRealTomOptTotal OBJECT-TYPE
    SYNTAX      FloatHundredths
    MAX-ACCESS  read-only
    STATUS      current
    DESCRIPTION ""
    ::= { tribPtpPmRealEntry  13 }

tribPtpPmRealTomOprTotal OBJECT-TYPE
    SYNTAX      FloatHundredths
    MAX-ACCESS  read-only
    STATUS      current
    DESCRIPTION ""
    ::= { tribPtpPmRealEntry  14 }



-- Conformance Statements
tribPtpPmConformance    OBJECT IDENTIFIER ::= { tribPtpPmMIB 3 }
tribPtpPmCompliances    OBJECT IDENTIFIER ::= { tribPtpPmConformance 1 }
tribPtpPmGroups         OBJECT IDENTIFIER ::= { tribPtpPmConformance 2 }

tribPtpPmCompliance MODULE-COMPLIANCE
    STATUS current
    DESCRIPTION
    "Describes the requirements for conformance to the PM-TRIBPTP-MIB"
    MODULE
        MANDATORY-GROUPS { tribPtpPmGroup }
    ::= { tribPtpPmCompliances 1 }

tribPtpPmRealCompliance MODULE-COMPLIANCE
    STATUS current
    DESCRIPTION
    "Describes the requirements for conformance to the tribPtpPmReal-MIB"
    MODULE
        MANDATORY-GROUPS { tribPtpPmRealGroup }
    ::= { tribPtpPmCompliances 2 }

tribPtpPmGroup OBJECT-GROUP
    OBJECTS {
	    tribPtpPmValidity,         
	    tribPtpPmTomTxLBCMin,
	    tribPtpPmTomTxLBCMax,
	    tribPtpPmTomTxLBCAve,
	    tribPtpPmTomOptMin,
	    tribPtpPmTomOptMax,
	    tribPtpPmTomOptAve,
	    tribPtpPmTomOprMin,
	    tribPtpPmTomOprMax,
	    tribPtpPmTomOprAve,
	    tribPtpPmTomTxLBC02Min,
	    tribPtpPmTomTxLBC02Max,
	    tribPtpPmTomTxLBC02Ave,    
	    tribPtpPmTomOpt02Min,
	    tribPtpPmTomOpt02Max,
	    tribPtpPmTomOpt02Ave,
	    tribPtpPmTomOpr02Min,
	    tribPtpPmTomOpr02Max,
	    tribPtpPmTomOpr02Ave,
	    tribPtpPmTomTxLBC03Min,
	    tribPtpPmTomTxLBC03Max,
	    tribPtpPmTomTxLBC03Ave,
	    tribPtpPmTomOpt03Min,
	    tribPtpPmTomOpt03Max,
	    tribPtpPmTomOpt03Ave,
	    tribPtpPmTomOpr03Min,
	    tribPtpPmTomOpr03Max,
	    tribPtpPmTomOpr03Ave,
	    tribPtpPmTomTxLBC04Min,
	    tribPtpPmTomTxLBC04Max,
	    tribPtpPmTomTxLBC04Ave,
	    tribPtpPmTomOpt04Min,
	    tribPtpPmTomOpt04Max,
	    tribPtpPmTomOpt04Ave,
	    tribPtpPmTomOpr04Min,
	    tribPtpPmTomOpr04Max,
	    tribPtpPmTomOpr04Ave,
        tribPtpPmTomOptTotalMin,
        tribPtpPmTomOptTotalMax,
        tribPtpPmTomOptTotalAve,
        tribPtpPmTomOprTotalMin,
        tribPtpPmTomOprTotalMax,
        tribPtpPmTomOprTotalAve
    }                       
    STATUS current          
    DESCRIPTION             
        " A collection of objects for reading the performance of the tribPtp."
    ::= { tribPtpPmGroups 1 }

tribPtpPmRealGroup OBJECT-GROUP
    OBJECTS {
    tribPtpPmRealTomTxLBC,
    tribPtpPmRealTomOpt,
    tribPtpPmRealTomOpr,
    tribPtpPmRealTomTxLBC02,
		tribPtpPmRealTomOpt02,
    tribPtpPmRealTomOpr02,
    tribPtpPmRealTomTxLBC03,
    tribPtpPmRealTomOpt03,
    tribPtpPmRealTomOpr03,
    tribPtpPmRealTomTxLBC04,
    tribPtpPmRealTomOpt04,
    tribPtpPmRealTomOpr04,
    tribPtpPmRealTomOptTotal,
    tribPtpPmRealTomOprTotal
    }
    STATUS current
    DESCRIPTION
        " A collection of objects for reading the performance of the tribPtp."
    ::= { tribPtpPmGroups 2 }

END

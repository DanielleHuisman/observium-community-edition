-- *****************************************************************
-- INFINERA-PM-XSCGPTP-MIB
-- 
-- December 2015, Kavitha Manjunatha
-- 
-- 
-- Copyright (c) 2008-2013 by Infinera Inc.
-- All rights reserved.
-- ****************************************************************

INFINERA-PM-XSCGPTP-MIB DEFINITIONS ::= BEGIN

IMPORTS
    MODULE-IDENTITY, OBJECT-TYPE,
    Integer32                                   FROM SNMPv2-SMI
    MODULE-COMPLIANCE, OBJECT-GROUP             FROM SNMPv2-CONF
    TruthValue                                  FROM SNMPv2-TC
    ifIndex                                     FROM IF-MIB
    FloatHundredths                             FROM INFINERA-TC-MIB
    perfMon                                     FROM INFINERA-REG-MIB;


xScgPtpPmMIB MODULE-IDENTITY
    LAST-UPDATED  "201512280000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "201512280000Z" 
    DESCRIPTION
        "First Version"
    ::= { perfMon 33 }


xScgPtpPmTable OBJECT-TYPE
    SYNTAX      SEQUENCE OF XScgPtpPmEntry
    MAX-ACCESS  not-accessible
    STATUS      current
    DESCRIPTION
        "A list of XScgPtpPm entries. Each entry is uniquely identified by the value of ifIndex."
    ::= { xScgPtpPmMIB 2 } 

xScgPtpPmEntry  OBJECT-TYPE
    SYNTAX      XScgPtpPmEntry
    MAX-ACCESS  not-accessible
    STATUS      current
    DESCRIPTION
        "A XScgPtp entry containing historical performance information pertaining to Infinera XSCGPTP.
        This table is a subclass of IfCommon. Entries will exist in this table only for interfaces
        of type XSCGPTP."
    INDEX { ifIndex, xScgPtpPmSampleDuration, xScgPtpPmTimestamp }
    ::= { xScgPtpPmTable 1 }


XScgPtpPmEntry  ::= SEQUENCE {
   xScgPtpPmTimestamp        Integer32,
   xScgPtpPmSampleDuration   INTEGER,
   xScgPtpPmValidity         TruthValue,
   xScgPtpPmTxEdfaOprMin     FloatHundredths,
   xScgPtpPmTxEdfaOprMax     FloatHundredths,
   xScgPtpPmTxEdfaOprAve     FloatHundredths,
   xScgPtpPmTxEdfaOptMin     FloatHundredths,
   xScgPtpPmTxEdfaOptMax     FloatHundredths,
   xScgPtpPmTxEdfaOptAve     FloatHundredths,
   xScgPtpPmTxEdfaLbcMin     FloatHundredths,
   xScgPtpPmTxEdfaLbcMax     FloatHundredths,
   xScgPtpPmTxEdfaLbcAve     FloatHundredths,
   xScgPtpPmRxEdfaOprMin     FloatHundredths,
   xScgPtpPmRxEdfaOprMax     FloatHundredths,
   xScgPtpPmRxEdfaOprAve     FloatHundredths,
   xScgPtpPmRxEdfaOptMin     FloatHundredths,
   xScgPtpPmRxEdfaOptMax     FloatHundredths,
   xScgPtpPmRxEdfaOptAve     FloatHundredths,
   xScgPtpPmRxEdfaLbcMin     FloatHundredths,
   xScgPtpPmRxEdfaLbcMax     FloatHundredths,
   xScgPtpPmRxEdfaLbcAve     FloatHundredths,
   xScgPtpPmChanScgOptMin    FloatHundredths,
   xScgPtpPmChanScgOptMax    FloatHundredths,
   xScgPtpPmChanScgOptAve    FloatHundredths,
   xScgPtpPmChanScgOprMin    FloatHundredths,
   xScgPtpPmChanScgOprMax    FloatHundredths,
   xScgPtpPmChanScgOprAve    FloatHundredths
}

xScgPtpPmTimestamp OBJECT-TYPE
    SYNTAX      Integer32 (0..2147483647)
    MAX-ACCESS  not-accessible
    STATUS      current
    DESCRIPTION
        "End Time stamp for this interval. If this time is later than the current time,
        then the data for this bucket is currently being collected."
    ::= { xScgPtpPmEntry  1 }

xScgPtpPmSampleDuration OBJECT-TYPE
    SYNTAX      INTEGER {
                    fifteenMinutes(1),
                    day(2)
                }
    MAX-ACCESS  not-accessible
    STATUS      current
    DESCRIPTION
        "The duration of this sample."
    ::= { xScgPtpPmEntry  2 }

xScgPtpPmValidity OBJECT-TYPE
    SYNTAX      TruthValue
    MAX-ACCESS  read-only
    STATUS      current
    DESCRIPTION "Flag indicating if data was valid for the entire interval"
    ::= { xScgPtpPmEntry  3 }


xScgPtpPmTxEdfaOprMin OBJECT-TYPE
    SYNTAX      FloatHundredths
    MAX-ACCESS  read-only
    STATUS      current
    DESCRIPTION "Minimum XScg optical power receive."
    ::= { xScgPtpPmEntry  4}


xScgPtpPmTxEdfaOprMax OBJECT-TYPE
    SYNTAX      FloatHundredths
    MAX-ACCESS  read-only
    STATUS      current
    DESCRIPTION "Maximum XScg optical power receive."
    ::= { xScgPtpPmEntry  5}


xScgPtpPmTxEdfaOprAve OBJECT-TYPE
    SYNTAX      FloatHundredths
    MAX-ACCESS  read-only
    STATUS      current
    DESCRIPTION "Average XScg optical power receive."
    ::= { xScgPtpPmEntry  6}


xScgPtpPmTxEdfaOptMin OBJECT-TYPE
    SYNTAX      FloatHundredths
    MAX-ACCESS  read-only
    STATUS      current
    DESCRIPTION "Minimum XScg optical power transmit."
    ::= { xScgPtpPmEntry  7 }


xScgPtpPmTxEdfaOptMax OBJECT-TYPE
    SYNTAX      FloatHundredths
    MAX-ACCESS  read-only
    STATUS      current
    DESCRIPTION "Maximum XScg optical power transmit."
    ::= { xScgPtpPmEntry  8 }


xScgPtpPmTxEdfaOptAve OBJECT-TYPE
    SYNTAX      FloatHundredths
    MAX-ACCESS  read-only
    STATUS      current
    DESCRIPTION "Average XScg optical power transmit."
    ::= { xScgPtpPmEntry  9 }


xScgPtpPmTxEdfaLbcMin OBJECT-TYPE
    SYNTAX      FloatHundredths
    MAX-ACCESS  read-only
    STATUS      current
    DESCRIPTION "Minimum EDFA LBC transmit."
    ::= { xScgPtpPmEntry  10 }


xScgPtpPmTxEdfaLbcMax OBJECT-TYPE
    SYNTAX      FloatHundredths
    MAX-ACCESS  read-only
    STATUS      current
    DESCRIPTION "Maxmimum EDFA LBC transmit."
    ::= { xScgPtpPmEntry  11 }


xScgPtpPmTxEdfaLbcAve OBJECT-TYPE
    SYNTAX      FloatHundredths
    MAX-ACCESS  read-only
    STATUS      current
    DESCRIPTION "Average EDFA LBC transmit."
    ::= { xScgPtpPmEntry  12 }

xScgPtpPmRxEdfaOprMin OBJECT-TYPE
    SYNTAX      FloatHundredths
    MAX-ACCESS  read-only
    STATUS      current
    DESCRIPTION "Minimum EDFA power receive."
    ::= { xScgPtpPmEntry  13 }

xScgPtpPmRxEdfaOprMax OBJECT-TYPE
    SYNTAX      FloatHundredths
    MAX-ACCESS  read-only
    STATUS      current
    DESCRIPTION "Maximum EDFA power receive."
    ::= { xScgPtpPmEntry  14 }

xScgPtpPmRxEdfaOprAve OBJECT-TYPE
    SYNTAX      FloatHundredths
    MAX-ACCESS  read-only
    STATUS      current
    DESCRIPTION "Average EDFA power receive."
    ::= { xScgPtpPmEntry  15 }

xScgPtpPmRxEdfaOptMin OBJECT-TYPE
    SYNTAX      FloatHundredths
    MAX-ACCESS  read-only
    STATUS      current
    DESCRIPTION "Minimum EDFA power trasmit."
    ::= { xScgPtpPmEntry  16 }

xScgPtpPmRxEdfaOptMax OBJECT-TYPE
    SYNTAX      FloatHundredths
    MAX-ACCESS  read-only
    STATUS      current
    DESCRIPTION "Maximum EDFA power trasmit."
    ::= { xScgPtpPmEntry  17 }

xScgPtpPmRxEdfaOptAve OBJECT-TYPE
    SYNTAX      FloatHundredths
    MAX-ACCESS  read-only
    STATUS      current
    DESCRIPTION "Average EDFA power transmit."
    ::= { xScgPtpPmEntry  18 }

xScgPtpPmRxEdfaLbcMin OBJECT-TYPE
    SYNTAX      FloatHundredths
    MAX-ACCESS  read-only
    STATUS      current
    DESCRIPTION "Minimum EDFA LBC receive."
    ::= { xScgPtpPmEntry  19 }


xScgPtpPmRxEdfaLbcMax OBJECT-TYPE
    SYNTAX      FloatHundredths
    MAX-ACCESS  read-only
    STATUS      current
    DESCRIPTION "Maxmimum EDFA LBC receive."
    ::= { xScgPtpPmEntry  20 }


xScgPtpPmRxEdfaLbcAve OBJECT-TYPE
    SYNTAX      FloatHundredths
    MAX-ACCESS  read-only
    STATUS      current
    DESCRIPTION "Average EDFA LBC receive."
    ::= { xScgPtpPmEntry  21 }

xScgPtpPmChanScgOptMin OBJECT-TYPE
    SYNTAX      FloatHundredths
    MAX-ACCESS  read-only
    STATUS      current
    DESCRIPTION ""
    ::= { xScgPtpPmEntry  22}

xScgPtpPmChanScgOptMax OBJECT-TYPE
    SYNTAX      FloatHundredths
    MAX-ACCESS  read-only
    STATUS      current
    DESCRIPTION ""
    ::= { xScgPtpPmEntry  23}

xScgPtpPmChanScgOptAve OBJECT-TYPE
    SYNTAX      FloatHundredths
    MAX-ACCESS  read-only
    STATUS      current
    DESCRIPTION ""
    ::= { xScgPtpPmEntry  24}

xScgPtpPmChanScgOprMin OBJECT-TYPE
    SYNTAX      FloatHundredths
    MAX-ACCESS  read-only
    STATUS      current
    DESCRIPTION ""
    ::= { xScgPtpPmEntry  25}

xScgPtpPmChanScgOprMax OBJECT-TYPE
    SYNTAX      FloatHundredths
    MAX-ACCESS  read-only
    STATUS      current
    DESCRIPTION ""
    ::= { xScgPtpPmEntry  26}

xScgPtpPmChanScgOprAve OBJECT-TYPE
    SYNTAX      FloatHundredths
    MAX-ACCESS  read-only
    STATUS      current
    DESCRIPTION ""
    ::= { xScgPtpPmEntry  27}

xScgPtpPmRealTable OBJECT-TYPE
    SYNTAX      SEQUENCE OF XScgPtpPmRealEntry
    MAX-ACCESS  not-accessible
    STATUS      current
    DESCRIPTION
        "A list of XScgPtpPmReal entries. Each entry is uniquely identified by the value of ifIndex."
    ::= { xScgPtpPmMIB 1 } 

xScgPtpPmRealEntry  OBJECT-TYPE
    SYNTAX      XScgPtpPmRealEntry
    MAX-ACCESS  not-accessible
    STATUS      current
    DESCRIPTION
        "A  xScgPtp entry containing real-time performance information pertaining to Infinera
         xScgPtp interfaces. This table is a subclass of IfCommon."
    INDEX { ifIndex }
    ::= { xScgPtpPmRealTable 1 }


XScgPtpPmRealEntry  ::= SEQUENCE {
    xScgPtpPmRealChanScgOpt       FloatHundredths,
    xScgPtpPmRealChanScgOpr       FloatHundredths,
    xScgPtpPmRealTxEdfaOpr        FloatHundredths,
    xScgPtpPmRealTxEdfaOpt        FloatHundredths,
    xScgPtpPmRealTxEdfaLbc        FloatHundredths,
    xScgPtpPmRealRxEdfaOpr        FloatHundredths,
    xScgPtpPmRealRxEdfaOpt        FloatHundredths,
    xScgPtpPmRealRxEdfaLbc        FloatHundredths
}

xScgPtpPmRealChanScgOpt OBJECT-TYPE
    SYNTAX      FloatHundredths
    MAX-ACCESS  read-only
    STATUS      current
    DESCRIPTION "Total XScg optical power trasmit."
    ::= { xScgPtpPmRealEntry  1 }


xScgPtpPmRealChanScgOpr OBJECT-TYPE
    SYNTAX      FloatHundredths
    MAX-ACCESS  read-only
    STATUS      current
    DESCRIPTION "Total XScg optical power receive."
    ::= { xScgPtpPmRealEntry  2 }

xScgPtpPmRealTxEdfaOpr OBJECT-TYPE
    SYNTAX      FloatHundredths
    MAX-ACCESS  read-only
    STATUS      current
    DESCRIPTION "Total Edfa power transmit."
    ::= { xScgPtpPmRealEntry  3 }

xScgPtpPmRealTxEdfaOpt OBJECT-TYPE
    SYNTAX      FloatHundredths
    MAX-ACCESS  read-only
    STATUS      current
    DESCRIPTION "Total Edfa power receive."
    ::= { xScgPtpPmRealEntry  4 }

xScgPtpPmRealTxEdfaLbc OBJECT-TYPE
    SYNTAX      FloatHundredths
    MAX-ACCESS  read-only
    STATUS      current
    DESCRIPTION "EdfaLbc."
    ::= { xScgPtpPmRealEntry  5 }

xScgPtpPmRealRxEdfaOpr OBJECT-TYPE
    SYNTAX      FloatHundredths
    MAX-ACCESS  read-only
    STATUS      current
    DESCRIPTION "EdfaOpr."
    ::= { xScgPtpPmRealEntry  6 }


xScgPtpPmRealRxEdfaOpt OBJECT-TYPE
    SYNTAX      FloatHundredths
    MAX-ACCESS  read-only
    STATUS      current
    DESCRIPTION "Total Edfa power trasmit."
    ::= { xScgPtpPmRealEntry  7 }

xScgPtpPmRealRxEdfaLbc OBJECT-TYPE
    SYNTAX      FloatHundredths
    MAX-ACCESS  read-only
    STATUS      current
    DESCRIPTION "Total EdfaLBC."
    ::= { xScgPtpPmRealEntry  8 }

-- Conformance Statements
xScgPtpPmConformance    OBJECT IDENTIFIER ::= { xScgPtpPmMIB 3 }
xScgPtpPmCompliances    OBJECT IDENTIFIER ::= { xScgPtpPmConformance 1 }
xScgPtpPmGroups         OBJECT IDENTIFIER ::= { xScgPtpPmConformance 2 }

xScgPtpPmCompliance MODULE-COMPLIANCE
    STATUS current
    DESCRIPTION
    "Describes the requirements for conformance to the  xScgPtp-MIB"
    MODULE
        MANDATORY-GROUPS { xScgPtpPmGroup }
    ::= { xScgPtpPmCompliances 1 }

xScgPtpPmRealCompliance MODULE-COMPLIANCE
    STATUS current
    DESCRIPTION
    "Describes the requirements for conformance to the XScgPtpPmReal-MIB"
    MODULE
        MANDATORY-GROUPS { xScgPtpPmRealGroup }
    ::= { xScgPtpPmCompliances 2 }

xScgPtpPmGroup OBJECT-GROUP
    OBJECTS {
        xScgPtpPmTimestamp,
        xScgPtpPmSampleDuration,
        xScgPtpPmValidity,
        xScgPtpPmTxEdfaOprMin,
        xScgPtpPmTxEdfaOprMax,
        xScgPtpPmTxEdfaOprAve,
        xScgPtpPmTxEdfaOptMin,
        xScgPtpPmTxEdfaOptMax,
        xScgPtpPmTxEdfaOptAve,
        xScgPtpPmTxEdfaLbcMin,
        xScgPtpPmTxEdfaLbcMax,
        xScgPtpPmTxEdfaLbcAve,
        xScgPtpPmRxEdfaOprMin,
        xScgPtpPmRxEdfaOprMax,
        xScgPtpPmRxEdfaOprAve,
        xScgPtpPmRxEdfaOptMin,
        xScgPtpPmRxEdfaOptMax,
        xScgPtpPmRxEdfaOptAve,
        xScgPtpPmRxEdfaLbcMin,
        xScgPtpPmRxEdfaLbcMax,
        xScgPtpPmRxEdfaLbcAve,
        xScgPtpPmChanScgOptMin,
        xScgPtpPmChanScgOptMax,
        xScgPtpPmChanScgOptAve,
        xScgPtpPmChanScgOprMin,
        xScgPtpPmChanScgOprMax,
        xScgPtpPmChanScgOprAve
    }
    STATUS current
    DESCRIPTION
        " A collection of objects for reading the historical performance of the  xScgPtp."
    ::= { xScgPtpPmGroups 1 }

xScgPtpPmRealGroup OBJECT-GROUP
    OBJECTS {
        xScgPtpPmRealChanScgOpt,
        xScgPtpPmRealChanScgOpr,
        xScgPtpPmRealTxEdfaOpr,
        xScgPtpPmRealTxEdfaOpt,
        xScgPtpPmRealTxEdfaLbc,
        xScgPtpPmRealRxEdfaOpr,
        xScgPtpPmRealRxEdfaOpt,
        xScgPtpPmRealRxEdfaLbc
    }
    STATUS current
    DESCRIPTION
        " A collection of objects for reading the real-time performance of the  xScgPtp."
    ::= { xScgPtpPmGroups 2 }

END

-- *****************************************************************
-- INFINERA-PROFILE-PXMCOSVALUEMAP-MIB
--   
-- Mithun Murthy/ Divyank Rastogi
--   
--   
-- Copyright (c) 2008-2016 by Infinera Inc.
-- All rights reserved.
-- ****************************************************************

INFINERA-PROFILE-PXMCOSVALUEMAP-MIB DEFINITIONS ::= BEGIN

IMPORTS
    MODULE-IDENTITY, OBJECT-TYPE, Integer32     FROM SNMPv2-SMI
    MODULE-COMPLIANCE, OBJECT-GROUP             FROM SNMPv2-CONF
    TruthValue,	DisplayString                   FROM SNMPv2-TC
    ifIndex                                     FROM IF-MIB
	InfnCosType, InfnDP							FROM INFINERA-TC-MIB
    commonProfile								FROM INFINERA-REG-MIB;

pxmCosValueMapMIB MODULE-IDENTITY
    LAST-UPDATED  "201605200000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "

    REVISION  "201605200000Z"
    DESCRIPTION 
        " "
::= { commonProfile 5}


pxmCosValueMapConformance   OBJECT IDENTIFIER ::= { pxmCosValueMapMIB 3 }
pxmCosValueMapCompliances   OBJECT IDENTIFIER ::= { pxmCosValueMapConformance 1 }
pxmCosValueMapGroups        OBJECT IDENTIFIER ::= { pxmCosValueMapConformance 2 }

pxmCosValueMapTable  OBJECT-TYPE
    SYNTAX SEQUENCE OF PxmCosValueMapEntry
    MAX-ACCESS not-accessible
    STATUS     current
    DESCRIPTION 
        "A list of PxmCosValueMap entries. Each entry is uniquely identified by
                the value of ifIndex."
    ::= { pxmCosValueMapMIB 1 }

pxmCosValueMapEntry  OBJECT-TYPE
    SYNTAX     PxmCosValueMapEntry
    MAX-ACCESS not-accessible
    STATUS     current
    DESCRIPTION 
        "A PxmCosValueMap entry containing information pertaining to
                Infinera PxmCosValueMap interfaces. This table is a subclass of IfCommon.
                Entries will exist in this table only for interfaces of type PxmCosValueMap."
    INDEX { ifIndex }
    ::= { pxmCosValueMapTable 1 }

PxmCosValueMapEntry  ::= SEQUENCE { 
	pxmCosValueMapCosMapProfile	DisplayString,
    pxmCosValueMapFromCosType	InfnCosType,
    pxmCosValueMapToCosType		InfnCosType,
	pxmCosValueMapPcp			Integer32,
	pxmCosValueMapDei			Integer32,
	pxmCosValueMapTc			Integer32,	
	pxmCosValueMapDp			InfnDP,
	pxmCosValueMapProfileInUse	TruthValue
}

pxmCosValueMapCosMapProfile		OBJECT-TYPE
    SYNTAX     DisplayString
    MAX-ACCESS read-only
    STATUS     current
    DESCRIPTION 
		""
    ::= { pxmCosValueMapEntry 1 }

pxmCosValueMapFromCosType		OBJECT-TYPE
    SYNTAX     InfnCosType
    MAX-ACCESS read-only
    STATUS     current
    DESCRIPTION 
        "PXM from cos type"
    ::= { pxmCosValueMapEntry 2 }

pxmCosValueMapToCosType	OBJECT-TYPE
    SYNTAX     InfnCosType 
    MAX-ACCESS read-only
    STATUS     current
    DESCRIPTION 
        ""
    ::= { pxmCosValueMapEntry 3 }

pxmCosValueMapPcp		OBJECT-TYPE
    SYNTAX     Integer32 
    MAX-ACCESS read-write
    STATUS     current
    DESCRIPTION 
        ""
    ::= { pxmCosValueMapEntry 4 }

pxmCosValueMapDei		OBJECT-TYPE
    SYNTAX     Integer32 
    MAX-ACCESS read-write
    STATUS     current
    DESCRIPTION 
        ""
    ::= { pxmCosValueMapEntry 5 }

pxmCosValueMapTc		OBJECT-TYPE
    SYNTAX     Integer32 
    MAX-ACCESS read-write
    STATUS     current
    DESCRIPTION 
        ""
    ::= { pxmCosValueMapEntry 6 }

pxmCosValueMapDp		OBJECT-TYPE
    SYNTAX     InfnDP 
    MAX-ACCESS read-write
    STATUS     current
    DESCRIPTION 
        ""
    ::= { pxmCosValueMapEntry 7 }

pxmCosValueMapProfileInUse OBJECT-TYPE
    SYNTAX     TruthValue
    MAX-ACCESS read-only
    STATUS     current
    DESCRIPTION 
        ""
    ::= { pxmCosValueMapEntry 8 }

pxmCosValueMapCompliance  MODULE-COMPLIANCE
    STATUS     current
    DESCRIPTION 
        "Describes the requirements for conformance to the TRIBPTP-MIB"
    MODULE
        MANDATORY-GROUPS { pxmCosValueMapGroup } 
    ::= { pxmCosValueMapCompliances 1 }

pxmCosValueMapGroup  OBJECT-GROUP
    OBJECTS { 
		pxmCosValueMapCosMapProfile,
        pxmCosValueMapFromCosType,
        pxmCosValueMapToCosType,
		pxmCosValueMapPcp,
		pxmCosValueMapDei,
		pxmCosValueMapTc, 
		pxmCosValueMapDp,
		pxmCosValueMapProfileInUse
    }
    STATUS     current
    DESCRIPTION 
        " A collection of objects for managing pxmCosValueMap interfaces."
    ::= { pxmCosValueMapGroups 1 }
END

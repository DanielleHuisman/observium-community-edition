-- ***************************************************************
-- INFINERA-PROFILE-PXML2CP-MIB
--   
-- May 2016, Kavitha Manjunatha / Divyank Rastogi
--   
--   
-- Copyright (c) 2008-2012 by Infinera Inc.
-- All rights reserved.
-- ****************************************************************
INFINERA-PROFILE-PXML2CP-MIB DEFINITIONS ::= BEGIN

IMPORTS
    OBJECT-TYPE, MODULE-IDENTITY, Unsigned32    FROM SNMPv2-SMI
    OBJECT-GROUP, MODULE-COMPLIANCE             FROM SNMPv2-CONF
    DisplayString, TruthValue                   FROM SNMPv2-TC
    ifIndex                                     FROM IF-MIB
    commonProfile                               FROM INFINERA-REG-MIB
    InfnEnableDisable, InfnL2CpAction           FROM INFINERA-TC-MIB;

l2CpProfileMIB MODULE-IDENTITY
    LAST-UPDATED  "201605050000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for PXML2CP profile table."
::= { commonProfile 4 }

l2CpProfileConformance       OBJECT IDENTIFIER ::= { l2CpProfileMIB 3 }
l2CpProfileCompliances       OBJECT IDENTIFIER ::= { l2CpProfileConformance 1 }
l2CpProfileGroups            OBJECT IDENTIFIER ::= { l2CpProfileConformance 2 }

l2CpTable  OBJECT-TYPE
    SYNTAX SEQUENCE OF L2CpProfileEntry
    MAX-ACCESS not-accessible
    STATUS     current
    DESCRIPTION 
        "This table contains all PXM Congestion Mgmt profiles that are currently present in a network element.
        "
    ::= { l2CpProfileMIB 1 }

l2CpProfileEntry  OBJECT-TYPE
    SYNTAX     L2CpProfileEntry
    MAX-ACCESS not-accessible
    STATUS     current
    DESCRIPTION 
        "A row in the PXM Congestion Mgmt table. Each row in the table is identified with a unique ifIndex."
    INDEX { ifIndex }
    ::= { l2CpTable 1 }

L2CpProfileEntry ::= SEQUENCE {
    l2CpProfileInUse                    TruthValue,
    l2CpProfXStp                        InfnL2CpAction,
    l2CpProfPause                       InfnL2CpAction,
    l2CpProfLacpLamp                    InfnL2CpAction,
    l2CpProfLinkOam                     InfnL2CpAction,
    l2CpProfPortAuth                    InfnL2CpAction,
    l2CpProfELmi                        InfnL2CpAction,
    l2CpProfLLDP                        InfnL2CpAction,
    l2CpProfPtpPeerDelay                InfnL2CpAction,
    l2CpProfESMC                        InfnL2CpAction,
    l2CpProfGarpGmrp                    InfnL2CpAction,
    l2CpProfMacControl                  InfnL2CpAction,
    l2CpProfProviderBridgeGroup         InfnL2CpAction,
    l2CpProfProviderBridgeMvrp          InfnL2CpAction,
    l2CpProfReserved05                  InfnL2CpAction,
    l2CpProfReserved06                  InfnL2CpAction,
    l2CpProfReserved09                  InfnL2CpAction,
    l2CpProfReserved0A                  InfnL2CpAction,
    l2CpProfReserved0B                  InfnL2CpAction,
    l2CpProfReserved0C                  InfnL2CpAction,
    l2CpProfReserved0F                  InfnL2CpAction
}

l2CpProfileInUse  OBJECT-TYPE
    SYNTAX     TruthValue
    MAX-ACCESS read-only
    STATUS     current
    DESCRIPTION 
        "Profile In use"
    ::= { l2CpProfileEntry 1 }

l2CpProfXStp    OBJECT-TYPE    
    SYNTAX     InfnL2CpAction
    MAX-ACCESS read-write
    STATUS     current
    DESCRIPTION 
        "Profile In use"
    ::= { l2CpProfileEntry 2 }

l2CpProfPause   OBJECT-TYPE
    SYNTAX     InfnL2CpAction
    MAX-ACCESS read-write
    STATUS     current
    DESCRIPTION 
        "Profile In use"
    ::= { l2CpProfileEntry 3 }

l2CpProfLacpLamp    OBJECT-TYPE
    SYNTAX     InfnL2CpAction
    MAX-ACCESS read-write
    STATUS     current
    DESCRIPTION 
        "Profile In use"
    ::= { l2CpProfileEntry 4 }

l2CpProfLinkOam OBJECT-TYPE
    SYNTAX     InfnL2CpAction
    MAX-ACCESS read-write
    STATUS     current
    DESCRIPTION 
        "Profile In use"
    ::= { l2CpProfileEntry 5 }

l2CpProfPortAuth    OBJECT-TYPE
    SYNTAX     InfnL2CpAction
    MAX-ACCESS read-write
    STATUS     current
    DESCRIPTION 
        "Profile In use"
    ::= { l2CpProfileEntry 6 }

l2CpProfELmi    OBJECT-TYPE
    SYNTAX     InfnL2CpAction
    MAX-ACCESS read-write
    STATUS     current
    DESCRIPTION 
        "Profile In use"
    ::= { l2CpProfileEntry 7 }

l2CpProfLLDP    OBJECT-TYPE
    SYNTAX     InfnL2CpAction
    MAX-ACCESS read-write
    STATUS     current
    DESCRIPTION 
        "Profile In use"
    ::= { l2CpProfileEntry 8 }

l2CpProfPtpPeerDelay    OBJECT-TYPE
    SYNTAX     InfnL2CpAction
    MAX-ACCESS read-write
    STATUS     current
    DESCRIPTION 
        "Profile In use"
    ::= { l2CpProfileEntry 9 }

l2CpProfESMC    OBJECT-TYPE
    SYNTAX     InfnL2CpAction
    MAX-ACCESS read-write
    STATUS     current
    DESCRIPTION 
        "Profile In use"
    ::= { l2CpProfileEntry 10 }

l2CpProfGarpGmrp    OBJECT-TYPE
    SYNTAX     InfnL2CpAction
    MAX-ACCESS read-write
    STATUS     current
    DESCRIPTION 
        "Profile In use"
    ::= { l2CpProfileEntry 11 }

l2CpProfMacControl  OBJECT-TYPE
    SYNTAX     InfnL2CpAction
    MAX-ACCESS read-write
    STATUS     current
    DESCRIPTION 
        "Profile In use"
    ::= { l2CpProfileEntry 12 }

l2CpProfProviderBridgeGroup OBJECT-TYPE
    SYNTAX     InfnL2CpAction
    MAX-ACCESS read-write
    STATUS     current
    DESCRIPTION 
        "Profile In use"
    ::= { l2CpProfileEntry 13 }

l2CpProfProviderBridgeMvrp  OBJECT-TYPE
    SYNTAX     InfnL2CpAction
    MAX-ACCESS read-write
    STATUS     current
    DESCRIPTION 
        "Profile In use"
    ::= { l2CpProfileEntry 14 }

l2CpProfReserved05  OBJECT-TYPE
    SYNTAX     InfnL2CpAction
    MAX-ACCESS read-write
    STATUS     current
    DESCRIPTION 
        "Profile In use"
    ::= { l2CpProfileEntry 15 }

l2CpProfReserved06  OBJECT-TYPE
    SYNTAX     InfnL2CpAction
    MAX-ACCESS read-write
    STATUS     current
    DESCRIPTION 
        "Profile In use"
    ::= { l2CpProfileEntry 16 }

l2CpProfReserved09  OBJECT-TYPE
    SYNTAX     InfnL2CpAction
    MAX-ACCESS read-write
    STATUS     current
    DESCRIPTION 
        "Profile In use"
    ::= { l2CpProfileEntry 17 }

l2CpProfReserved0A  OBJECT-TYPE
    SYNTAX     InfnL2CpAction
    MAX-ACCESS read-write
    STATUS     current
    DESCRIPTION 
        "Profile In use"
    ::= { l2CpProfileEntry 18 }

l2CpProfReserved0B  OBJECT-TYPE
    SYNTAX     InfnL2CpAction
    MAX-ACCESS read-write
    STATUS     current
    DESCRIPTION 
        "Profile In use"
    ::= { l2CpProfileEntry 19 }

l2CpProfReserved0C  OBJECT-TYPE
    SYNTAX     InfnL2CpAction
    MAX-ACCESS read-write
    STATUS     current
    DESCRIPTION 
        "Profile In use"
    ::= { l2CpProfileEntry 20 }

l2CpProfReserved0F  OBJECT-TYPE
    SYNTAX     InfnL2CpAction
    MAX-ACCESS read-write
    STATUS     current
    DESCRIPTION 
        "Profile In use"
    ::= { l2CpProfileEntry 21 }

l2CpProfileCompliance  MODULE-COMPLIANCE
    STATUS     current
    DESCRIPTION ""
    MODULE
        MANDATORY-GROUPS { l2CpProfileGroup } 
    ::= { l2CpProfileCompliances 1 }

l2CpProfileGroup  OBJECT-GROUP
    OBJECTS { 
        l2CpProfileInUse,
        l2CpProfXStp,
        l2CpProfPause,
        l2CpProfLacpLamp,
        l2CpProfLinkOam,
        l2CpProfPortAuth,
        l2CpProfELmi,
        l2CpProfLLDP,
        l2CpProfPtpPeerDelay,
        l2CpProfESMC,
        l2CpProfGarpGmrp,
        l2CpProfMacControl,
        l2CpProfProviderBridgeGroup,
        l2CpProfProviderBridgeMvrp,
        l2CpProfReserved05,
        l2CpProfReserved06,
        l2CpProfReserved09,
        l2CpProfReserved0A,
        l2CpProfReserved0B,
        l2CpProfReserved0C,
        l2CpProfReserved0F
    }
    STATUS     current
    DESCRIPTION ""
    ::= { l2CpProfileGroups 1 }
END

-- *****************************************************************
-- INFINERA-SECURITY-IKE-MIB
--
-- October 2016, Kavitha Manjunatha
--
-- Copyright (c) 2008-2012 by Infinera Inc.
--
-- All rights reserved.
-- ****************************************************************

INFINERA-SECURITY-IKE-MIB DEFINITIONS ::= BEGIN

IMPORTS
    MODULE-IDENTITY, OBJECT-TYPE                FROM SNMPv2-SMI
    MODULE-COMPLIANCE, OBJECT-GROUP             FROM SNMPv2-CONF
    ike                                         FROM INFINERA-REG-MIB
    ifIndex                                     FROM IF-MIB
    DisplayString                               FROM SNMPv2-TC
    InfnAuthScheme, InfnFailPolicy              FROM INFINERA-TC-MIB
    ;

ikeMIB MODULE-IDENTITY
    LAST-UPDATED  "201608200000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "201702220000Z"
    DESCRIPTION
        " "
::= { ike 1 }

ikeTable  OBJECT-TYPE
    SYNTAX SEQUENCE OF IkeEntry
    MAX-ACCESS not-accessible
    STATUS     current
    DESCRIPTION
        "A list of Ike entries. Each entry is uniquely identified by
                the value of ifIndex."
    ::= { ikeMIB 1 }

ikeEntry  OBJECT-TYPE
    SYNTAX     IkeEntry
    MAX-ACCESS not-accessible
    STATUS     current
    DESCRIPTION
        "A Ike entry containing information pertaining to Infinera Ikes"
    INDEX { ifIndex }
    ::= { ikeTable 1 }

IkeEntry  ::= SEQUENCE {
    ikePeerMoId                     DisplayString,
    ikePeerID                       DisplayString,
    ikeLocalPeerID                  DisplayString,
    ikePeerControlChannel           DisplayString,
    ikePeerAuthScheme               InfnAuthScheme,
    ikePeerAuthFrequency            Integer32,
    ikePeerAuthFailPolicy           InfnFailPolicy,
    ikePeerRekeyIKESAFrequency      Integer32,
    ikePeerRekeyIKESAFailPolicy     InfnFailPolicy,
    ikePeerAssociatedSecEntity      DisplayString,
    ikePeerTrafficKillOffset        Integer32,
    ikePeerLocalCertificate         DisplayString,
    ikePeerReceivedPeerCertificate  DisplayString,
    ikePeerLocalPeerIPAddress       DisplayString,
    ikePeerRemotePeerIPAddress      DisplayString,
    ikePeerRemotePeerName           DisplayString
}

ikePeerMoId   OBJECT-TYPE
    SYNTAX      DisplayString
    MAX-ACCESS  read-only
    STATUS      current
    DESCRIPTION "Peer Name"
    ::= { ikeEntry 1 }

ikePeerID   OBJECT-TYPE
    SYNTAX      DisplayString
    MAX-ACCESS  read-only
    STATUS      current
    DESCRIPTION "Peer ID"
    ::= { ikeEntry 2 }

ikeLocalPeerID   OBJECT-TYPE
    SYNTAX      DisplayString
    MAX-ACCESS  read-only
    STATUS      current
    DESCRIPTION "Local Peer ID"
    ::= { ikeEntry 3 }

ikePeerControlChannel   OBJECT-TYPE
    SYNTAX      DisplayString
    MAX-ACCESS  read-only
    STATUS      deprecated
    DESCRIPTION ""
    ::= { ikeEntry 4 }

ikePeerAuthScheme   OBJECT-TYPE
    SYNTAX      InfnAuthScheme
    MAX-ACCESS  read-only
    STATUS      current
    DESCRIPTION ""
    ::= { ikeEntry 5 }

ikePeerAuthFrequency   OBJECT-TYPE
    SYNTAX      Integer32
    MAX-ACCESS  read-only
    STATUS      current
    DESCRIPTION ""
    ::= { ikeEntry 6 }

ikePeerAuthFailPolicy   OBJECT-TYPE
    SYNTAX      InfnFailPolicy
    MAX-ACCESS  read-only
    STATUS      current
    DESCRIPTION ""
    ::= { ikeEntry 7 }

ikePeerRekeyIKESAFrequency   OBJECT-TYPE
    SYNTAX      Integer32
    MAX-ACCESS  read-only
    STATUS      current
    DESCRIPTION ""
    ::= { ikeEntry 8 }

ikePeerRekeyIKESAFailPolicy   OBJECT-TYPE
    SYNTAX      InfnFailPolicy
    MAX-ACCESS  read-only
    STATUS      current
    DESCRIPTION ""
    ::= { ikeEntry 9 }

ikePeerAssociatedSecEntity   OBJECT-TYPE
    SYNTAX      DisplayString
    MAX-ACCESS  read-only
    STATUS      current
    DESCRIPTION ""
    ::= { ikeEntry 10 }

ikePeerTrafficKillOffset   OBJECT-TYPE
    SYNTAX      Integer32
    MAX-ACCESS  read-only
    STATUS      current
    DESCRIPTION ""
    ::= { ikeEntry 11 }

ikePeerLocalCertificate   OBJECT-TYPE
    SYNTAX      DisplayString
    MAX-ACCESS  read-write
    STATUS      current
    DESCRIPTION ""
    ::= { ikeEntry 12 }

ikePeerReceivedPeerCertificate   OBJECT-TYPE
    SYNTAX      DisplayString
    MAX-ACCESS  read-only
    STATUS      current
    DESCRIPTION ""
    ::= { ikeEntry 13 }

ikePeerLocalPeerIPAddress   OBJECT-TYPE
    SYNTAX      DisplayString
    MAX-ACCESS  read-only
    STATUS      current
    DESCRIPTION ""
    ::= { ikeEntry 14 }

ikePeerRemotePeerIPAddress   OBJECT-TYPE
    SYNTAX      DisplayString
    MAX-ACCESS  read-only
    STATUS      current
    DESCRIPTION ""
    ::= { ikeEntry 15 }

ikePeerRemotePeerName   OBJECT-TYPE
    SYNTAX      DisplayString
    MAX-ACCESS  read-create
    STATUS      current
    DESCRIPTION ""
    ::= { ikeEntry 16 }

ikeConformance   OBJECT IDENTIFIER ::= { ikeMIB 2 }
ikeCompliances   OBJECT IDENTIFIER ::= { ikeConformance 1 }
ikeGroups        OBJECT IDENTIFIER ::= { ikeConformance 2 }

ikeCompliance MODULE-COMPLIANCE
    STATUS current
    DESCRIPTION
    "Describes the requirements for conformance to the BPP-MIB"
    MODULE
        MANDATORY-GROUPS { ikeGroup }
    ::= { ikeCompliances 1 }

ikeGroup OBJECT-GROUP
    OBJECTS {
        ikePeerMoId,
        ikePeerID,
        ikeLocalPeerID,
        ikePeerControlChannel,
        ikePeerAuthScheme,
        ikePeerAuthFrequency,
        ikePeerAuthFailPolicy,
        ikePeerRekeyIKESAFrequency,
        ikePeerRekeyIKESAFailPolicy,
        ikePeerAssociatedSecEntity,
        ikePeerTrafficKillOffset,
        ikePeerLocalCertificate,
        ikePeerReceivedPeerCertificate,
        ikePeerLocalPeerIPAddress,
        ikePeerRemotePeerIPAddress,
        ikePeerRemotePeerName
}
    STATUS current
    DESCRIPTION
        " A collection of objects for managing the IKE objects"
    ::= { ikeGroups 1 }

END

-- *****************************************************************
-- INFINERA-SECY-SECUREENTITY-MIB
-- Copyright (c) 2008-2012 by Infinera Inc
-- All rights reserved.
-- ****************************************************************

INFINERA-SECY-SECUREENTITY-MIB DEFINITIONS ::= BEGIN

IMPORTS
    MODULE-IDENTITY, OBJECT-TYPE, Integer32     FROM SNMPv2-SMI
    MODULE-COMPLIANCE, OBJECT-GROUP             FROM SNMPv2-CONF
    DisplayString                               FROM SNMPv2-TC
    ifIndex                                     FROM IF-MIB
    InfnEnableDisable                           FROM INFINERA-TC-MIB
    macsecTP                                    FROM INFINERA-REG-MIB;

secureEntityMIB MODULE-IDENTITY
    LAST-UPDATED  "201609290000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201609290000Z"
    DESCRIPTION
        "First Version"
    ::= { macsecTP  1 }

secureEntityTable OBJECT-TYPE
    SYNTAX      SEQUENCE OF SecureEntityEntry
    MAX-ACCESS  not-accessible
    STATUS      current
    DESCRIPTION
        "A list of SecureEntity entries. Each entry is uniquely identified by the value of ifIndex."
    ::= { secureEntityMIB 1 }

secureEntityEntry  OBJECT-TYPE
    SYNTAX      SecureEntityEntry
    MAX-ACCESS  not-accessible
    STATUS      current
    DESCRIPTION
        "A SecureEntity entry containing information pertaining to Infinera SecureEntity Interfaces.
        This table is a subclass of IfCommon. Entries will exist in this table only for
        interfaces of type DLM OCG PSECY."
    INDEX { ifIndex }
    ::= { secureEntityTable 1 }


SecureEntityEntry  ::= SEQUENCE {
	moId            DisplayString,
	historicalPm    InfnEnableDisable
}

moId    OBJECT-TYPE
    SYNTAX      DisplayString
    MAX-ACCESS  read-only
    STATUS      current
    DESCRIPTION ""
    ::= { secureEntityEntry 1 }

historicalPm    OBJECT-TYPE
    SYNTAX      InfnEnableDisable
    MAX-ACCESS  read-write
    STATUS      current
    DESCRIPTION ""
    ::= { secureEntityEntry 2 }

-- Conformance Statements
secureEntityConformance    OBJECT IDENTIFIER ::= { secureEntityMIB 3 }
secureEntityCompliances    OBJECT IDENTIFIER ::= { secureEntityConformance 1 }
secureEntityGroups         OBJECT IDENTIFIER ::= { secureEntityConformance 2 }

secureEntityCompliance MODULE-COMPLIANCE
    STATUS current
    DESCRIPTION
    "Describes the requirements for conformance to the SECUREENTITY-MIB"
    MODULE
        MANDATORY-GROUPS { secureEntityGroup }
    ::= { secureEntityCompliances 1 }

secureEntityGroup OBJECT-GROUP
    OBJECTS {
		moId,
		historicalPm
}
    STATUS current
    DESCRIPTION
        " A collection of objects for managing the secureEntity"
    ::= { secureEntityGroups 1 }
END

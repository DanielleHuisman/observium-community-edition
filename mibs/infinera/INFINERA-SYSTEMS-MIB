-- *****************************************************************
-- INFINERA-SYSTEMS-MIB
--
-- January 2008, <Author>
--
--
-- Copyright (c) 2008-2012 by Infinera Inc.
-- All rights reserved.
-- ****************************************************************

INFINERA-SYSTEMS-MIB DEFINITIONS ::= BEGIN

IMPORTS
    OBJECT-TYPE, MODULE-IDENTITY, Integer32        FROM SNMPv2-SMI
    TruthValue, DisplayString                      FROM SNMPv2-TC
    infnNE                                         FROM INFINERA-REG-MIB
    InetAddressIPv4                                FROM INET-ADDRESS-MIB
    InetAddressIPv6                                FROM INET-ADDRESS-MIB
    InfnAdminState, InfnArc, InfnCurrentDcnGatewayType,
	InfnPhyConnDcnGwType,InfnEnableDisable,
	InfnALSAdminPolicy,InfnUpgradePrepStatus,
    InfnNeType,InfnSysArcBehaviour, InfnMigrationStatus,
    InfnSysEnableAuxTosByteAlteration,
    InfnSysTermLoopBackBehaviour,InfnSyslogFeature FROM INFINERA-TC-MIB;

infnSystem MODULE-IDENTITY
    LAST-UPDATED "200801110000Z"
    ORGANIZATION
        "Infinera"
    CONTACT-INFO
                "Infinera
                1322 Bordeaux Drive
                Sunnyvale, CA - 94089

                Contact : Technical Support
                Email   : support@infinera.com
                Phone   : 1-877-INF-5288"
    DESCRIPTION
        " "
::= { infnNE 1 }


-- Confirmance Statements

infnSystemMoId  OBJECT-TYPE
    SYNTAX     DisplayString
    MAX-ACCESS read-only
    STATUS     current
    DESCRIPTION
        "MO identifier for this object"
    ::= { infnSystem 1 }

infnSystemLabel  OBJECT-TYPE
    SYNTAX     DisplayString (SIZE(0..128))
    MAX-ACCESS read-write
    STATUS     current
    DESCRIPTION
        "Label"
    ::= { infnSystem 2 }

infnSystemAlarmReportControl  OBJECT-TYPE
    SYNTAX     InfnArc
    MAX-ACCESS read-write
    STATUS     current
    DESCRIPTION
        "AlarmReportControl"
    DEFVAL  { allowed }
    ::= { infnSystem 3 }

infnSystemAlarmInhibitState  OBJECT-TYPE
    SYNTAX     InfnArc
    MAX-ACCESS read-only
    STATUS     current
    DESCRIPTION
        "AlarmInhibitState"
    ::= { infnSystem 4 }

infnSystemNodeId  OBJECT-TYPE
    SYNTAX     DisplayString
    MAX-ACCESS read-only
    STATUS     current
    DESCRIPTION
        "NodeId"
    ::= { infnSystem 5 }

infnSystemNeName  OBJECT-TYPE
    SYNTAX     DisplayString (SIZE(1..20))
    MAX-ACCESS read-write
    STATUS     current
    DESCRIPTION
        "NeName"
    ::= { infnSystem 6 }

infnSystemNeType  OBJECT-TYPE
    SYNTAX     InfnNeType
    MAX-ACCESS read-write
    STATUS     current
    DESCRIPTION
        "NeType"
    ::= { infnSystem 7 }

infnSystemArcBehaviour  OBJECT-TYPE
    SYNTAX     InfnSysArcBehaviour
    MAX-ACCESS read-write
    STATUS     current
    DESCRIPTION
        "ArcBehaviour"
    DEFVAL  { leaveAlarms }
    ::= { infnSystem 8 }

infnSystemLocation  OBJECT-TYPE
    SYNTAX     DisplayString (SIZE(0..255))
    MAX-ACCESS read-write
    STATUS     current
    DESCRIPTION
        "Location1"
    ::= { infnSystem 9 }

infnSystemLatitude  OBJECT-TYPE
    SYNTAX     DisplayString (SIZE(0..255))
    MAX-ACCESS read-write
    STATUS     current
    DESCRIPTION
        "Latitude"
    ::= { infnSystem 10 }

infnSystemLongitude  OBJECT-TYPE
    SYNTAX     DisplayString (SIZE(0..255))
    MAX-ACCESS read-write
    STATUS     current
    DESCRIPTION
        "Longitude"
    ::= { infnSystem 11 }

infnSystemTime  OBJECT-TYPE
    SYNTAX     DisplayString
    MAX-ACCESS read-only
    STATUS     current
    DESCRIPTION
        "This object represents the systems date and time expressed in format YYYY-MM-DD<space>hh:mm:ss."
    ::= { infnSystem 12 }

infnSystemTimeZoneOffset  OBJECT-TYPE
    SYNTAX     Integer32
    MAX-ACCESS read-only
    STATUS     current
    DESCRIPTION
        "System Time Zone Offset"
    ::= { infnSystem 13 }

infnSystemActiveTime  OBJECT-TYPE
    SYNTAX     DisplayString
    MAX-ACCESS read-only
    STATUS     current
    DESCRIPTION
        "System Active Time time of this node expressed in format YYYY-MM-DD<space>hh:mm:ss."
    ::= { infnSystem 14 }

infnSystemDbVer  OBJECT-TYPE
    SYNTAX     DisplayString
    MAX-ACCESS read-only
    STATUS     current
    DESCRIPTION
        "DbVer"
    ::= { infnSystem 15 }

infnSystemSwGenVer  OBJECT-TYPE
    SYNTAX     DisplayString
    MAX-ACCESS read-only
    STATUS     current
    DESCRIPTION
        "SwGenVer"
    ::= { infnSystem 16 }

infnSystemRouterId  OBJECT-TYPE
    SYNTAX     InetAddressIPv4
    MAX-ACCESS read-only
    STATUS     current
    DESCRIPTION
        "RouterId"
    ::= { infnSystem 17 }

infnSystemDcnIp  OBJECT-TYPE
    SYNTAX     InetAddressIPv4
    MAX-ACCESS read-only
    STATUS     current
    DESCRIPTION
        "DcnIp"
    ::= { infnSystem 18 }

infnSystemDcnIpNetMask  OBJECT-TYPE
    SYNTAX     InetAddressIPv4
    MAX-ACCESS read-only
    STATUS     current
    DESCRIPTION
        "DcnIpNetMask"
    ::= { infnSystem 19 }

infnSystemDcnDestination  OBJECT-TYPE
    SYNTAX     InetAddressIPv4
    MAX-ACCESS read-only
    STATUS     current
    DESCRIPTION
        "DcnDestination"
    ::= { infnSystem 20 }

infnSystemDcnGateway  OBJECT-TYPE
    SYNTAX     InetAddressIPv4
    MAX-ACCESS read-only
    STATUS     current
    DESCRIPTION
        "DcnGateway"
    ::= { infnSystem 21 }

infnSystemDcnPrefixLen  OBJECT-TYPE
    SYNTAX     Integer32
    MAX-ACCESS read-only
    STATUS     current
    DESCRIPTION
        "DcnPrefixLen"
    ::= { infnSystem 22 }

infnSystemDcnGlobalRoute  OBJECT-TYPE
    SYNTAX     TruthValue
    MAX-ACCESS read-only
    STATUS     current
    DESCRIPTION
        "DcnGlobalRoute"
    ::= { infnSystem 23 }

infnSystemSwBuildInfo  OBJECT-TYPE
    SYNTAX     DisplayString
    MAX-ACCESS read-only
    STATUS     current
    DESCRIPTION
        "SwBuildInfo"
    ::= { infnSystem 24 }

infnSystemCraftIp  OBJECT-TYPE
    SYNTAX     InetAddressIPv4
    MAX-ACCESS read-write
    STATUS     current
    DESCRIPTION
        "CraftIp"
    ::= { infnSystem 25 }

infnSystemCraftIpNetMask  OBJECT-TYPE
    SYNTAX     InetAddressIPv4
    MAX-ACCESS read-write
    STATUS     current
    DESCRIPTION
        "CraftIpNetMask"
    ::= { infnSystem 26 }

infnSystemCraftIPInterfaceAdministrativeState  OBJECT-TYPE
    SYNTAX     InfnAdminState
    MAX-ACCESS read-write
    STATUS     current
    DESCRIPTION
        "CraftIPInterfaceAdministrativeState"
    ::= { infnSystem 27 }

infnSystemAuxIp  OBJECT-TYPE
    SYNTAX     InetAddressIPv4
    MAX-ACCESS read-write
    STATUS     current
    DESCRIPTION
        "AuxIp"
    ::= { infnSystem 28 }

infnSystemAuxIpNetMask  OBJECT-TYPE
    SYNTAX     InetAddressIPv4
    MAX-ACCESS read-write
    STATUS     current
    DESCRIPTION
        "AuxIpNetMask"
    ::= { infnSystem 29 }

infnSystemAuxIPInterfaceAdministrativeState  OBJECT-TYPE
    SYNTAX     InfnAdminState
    MAX-ACCESS read-write
    STATUS     current
    DESCRIPTION
        "AuxIPInterfaceAdministrativeState"
    ::= { infnSystem 30 }

infnSystemDetectedSerialNumberList  OBJECT-TYPE
    SYNTAX     DisplayString
    MAX-ACCESS read-only
    STATUS     current
    DESCRIPTION
        "Detected Serial Number of chassis seprated by ;"
    ::= { infnSystem 31 }

infnSystemAvailPersistentSpace  OBJECT-TYPE
    SYNTAX     DisplayString
    UNITS     "Bytes"
    MAX-ACCESS read-only
    STATUS     current
    DESCRIPTION
        "AvailPersistentInBytes"
    ::= { infnSystem 32 }

infnSystemTotalPersistentSpace  OBJECT-TYPE
    SYNTAX     DisplayString
    UNITS     "Bytes"
    MAX-ACCESS read-only
    STATUS     current
    DESCRIPTION
        "TotalPersistentSpace"
    ::= { infnSystem 33 }

infnSystemGatewayProxyEnabled  OBJECT-TYPE
    SYNTAX     TruthValue
    MAX-ACCESS read-write
    STATUS     current
    DESCRIPTION
        "GatewayProxyEnabled"
    ::= { infnSystem 34 }

infnSystemPrimaryGneIp  OBJECT-TYPE
    SYNTAX     InetAddressIPv4
    MAX-ACCESS read-write
    STATUS     current
    DESCRIPTION
        "PrimaryGneIp"
    ::= { infnSystem 35 }

infnSystemSecondaryGneIp  OBJECT-TYPE
    SYNTAX     InetAddressIPv4
    MAX-ACCESS read-write
    STATUS     current
    DESCRIPTION
        "SecondaryGneIp"
    ::= { infnSystem 36 }

infnSystemMaxNoOfChassisSupported  OBJECT-TYPE
    SYNTAX     Integer32
    MAX-ACCESS read-only
    STATUS     current
    DESCRIPTION
        "MaxNoOfChassisSupported"
    ::= { infnSystem 37 }

infnSystemIsForcedSyncNeeded  OBJECT-TYPE
    SYNTAX     TruthValue
    MAX-ACCESS read-only
    STATUS     current
    DESCRIPTION
        "IsForcedSyncNeeded"
    ::= { infnSystem 38 }

infnSystemEnableAuxTosByteAlteration  OBJECT-TYPE
    SYNTAX   InfnSysEnableAuxTosByteAlteration
    MAX-ACCESS read-write
    STATUS     current
    DESCRIPTION
        "EnableAuxTosByteAlteration"
    ::= { infnSystem 39 }

infnSystemAuxPortRate  OBJECT-TYPE
    SYNTAX     Integer32
    MAX-ACCESS read-write
    STATUS     current
    DESCRIPTION
        "AuxPortRate"
    ::= { infnSystem 40 }

infnSystemClli  OBJECT-TYPE
	SYNTAX          DisplayString  ( SIZE ( 0 .. 128  ) )
	MAX-ACCESS      read-write
	STATUS          current
	DESCRIPTION     "Clli this is appliacble only to ATN nodes."
	::=  {  infnSystem  41  }

infnSystemLocation2 OBJECT-TYPE
	SYNTAX          DisplayString  ( SIZE ( 0 .. 255  ) )
	MAX-ACCESS      read-write
	STATUS          current
	DESCRIPTION     "Location2"
	::=  {  infnSystem  42  }

infnSystemCliPortId OBJECT-TYPE
	SYNTAX          Integer32
	MAX-ACCESS      read-only
	STATUS          current
	DESCRIPTION     "Clli this is appliacble only to ATN nodes."
	::=  {  infnSystem  43  }

infnSystemLayer2Enabled OBJECT-TYPE
	SYNTAX          TruthValue
	MAX-ACCESS      read-write
	STATUS          current
	DESCRIPTION     "Whether L2 switching is enabled or not"
	::=  {  infnSystem  44  }



infnSystemSecondaryDcnIp  OBJECT-TYPE
    SYNTAX     InetAddressIPv4
    MAX-ACCESS read-only
    STATUS     current
    DESCRIPTION
        "infnSystemSecondaryDcnIp"
    ::= { infnSystem 45 }

infnSystemSecondaryDcnIpNetMask  OBJECT-TYPE
    SYNTAX     InetAddressIPv4
    MAX-ACCESS read-only
    STATUS     current
    DESCRIPTION
        "infnSystemSecondaryDcnIpNetMask"
    ::= { infnSystem 46 }

infnSystemSecondaryDcnGateway  OBJECT-TYPE
    SYNTAX     InetAddressIPv4
    MAX-ACCESS read-only
    STATUS     current
    DESCRIPTION
        "infnSystemSecondaryDcnGateway"
    ::= { infnSystem 47 }

infnSystemCurrentDcnGateway  OBJECT-TYPE
    SYNTAX     InfnCurrentDcnGatewayType
    MAX-ACCESS read-only
    STATUS     current
    DESCRIPTION
        "infnSystemCurrentDcnGateway"
    ::= { infnSystem 48 }

infnSystemPhyConnDcnGw  OBJECT-TYPE
    SYNTAX     InfnPhyConnDcnGwType
    MAX-ACCESS read-write
    STATUS     current
    DESCRIPTION
        "infnSystemPhyConnDcnGw"
    ::= { infnSystem 49 }

infnSystemTermLoopBackBehaviour  OBJECT-TYPE
    SYNTAX     InfnSysTermLoopBackBehaviour
    MAX-ACCESS read-write
    STATUS     current
    DESCRIPTION
        "Terminal Loopback Behaviour"
    ::= { infnSystem 50 }

infnSystemOscOobEnable OBJECT-TYPE
    SYNTAX     DisplayString  ( SIZE ( 0 .. 255  ) )
    MAX-ACCESS read-write
    STATUS     current
    DESCRIPTION
        "OSC OOB "
    ::= { infnSystem 51 }

infnLastUpgradeTime  OBJECT-TYPE
    SYNTAX     DisplayString
    MAX-ACCESS read-only
    STATUS     current
    DESCRIPTION
        "This object represents the Last upgrade time."
    ::= { infnSystem 52 }

infnRestHoldOffTimer0 OBJECT-TYPE
    SYNTAX     INTEGER
    MAX-ACCESS read-write
    STATUS     current
    DESCRIPTION
        "RestHoldOffTimer0."
    ::= { infnSystem 53 }

infnRestHoldOffTimer1 OBJECT-TYPE
    SYNTAX     INTEGER
    MAX-ACCESS read-write
    STATUS     current
    DESCRIPTION
        "RestHoldOffTimer1."
    ::= { infnSystem 54 }


infnRestHoldOffTimer2 OBJECT-TYPE
    SYNTAX     INTEGER
    MAX-ACCESS read-write
    STATUS     current
    DESCRIPTION
        "RestHoldOffTimer2."
    ::= { infnSystem 55 }


infnRestHoldOffTimer3 OBJECT-TYPE
    SYNTAX     INTEGER
    MAX-ACCESS read-write
    STATUS     current
    DESCRIPTION
        "RestHoldOffTimer3."
    ::= { infnSystem 56 }


infnRestHoldOffTimer4 OBJECT-TYPE
    SYNTAX     INTEGER
    MAX-ACCESS read-write
    STATUS     current
    DESCRIPTION
        "RestHoldOffTimer4."
    ::= { infnSystem 57 }

infnRestHoldOffTimer5 OBJECT-TYPE
    SYNTAX     INTEGER
    MAX-ACCESS read-write
    STATUS     current
    DESCRIPTION
        "RestHoldOffTimer5."
    ::= { infnSystem 58 }

infnRestHoldOffTimer6 OBJECT-TYPE
    SYNTAX     INTEGER
    MAX-ACCESS read-write
    STATUS     current
    DESCRIPTION
        "RestHoldOffTimer6."
    ::= { infnSystem 59 }

infnRestHoldOffTimer7 OBJECT-TYPE
    SYNTAX     INTEGER
    MAX-ACCESS read-write
    STATUS     current
    DESCRIPTION
        "RestHoldOffTimer7."
    ::= { infnSystem 60 }

infnEnhProtSw OBJECT-TYPE
    SYNTAX     InfnEnableDisable
    MAX-ACCESS read-write
    STATUS     current
    DESCRIPTION
        "EnhProtSw."
    ::= { infnSystem 61 }

infnALSAdministrationPolicy OBJECT-TYPE
    SYNTAX     InfnALSAdminPolicy
    MAX-ACCESS read-write
    STATUS     current
    DESCRIPTION
        "ALSAdministrationPolicy."
    ::= { infnSystem 62 }

infnOpticalGmplsMscId OBJECT-TYPE
    SYNTAX      INTEGER
    MAX-ACCESS  read-write
    STATUS      current
    DESCRIPTION ""
    ::= {infnSystem 63 }

infnPrepareUpgradeStatus OBJECT-TYPE
    SYNTAX     InfnUpgradePrepStatus
    MAX-ACCESS  read-write
    STATUS      current
    DESCRIPTION "Prepare Upgrade status"
    ::= {infnSystem 64 }

infnPreUpgradeLastAttemptedTime OBJECT-TYPE
    SYNTAX      DisplayString
    MAX-ACCESS  read-write
    STATUS      current
    DESCRIPTION "Upgrade last attempted time"
    ::= {infnSystem 65 }

infnPreUpgradeLastSuccessfulTime OBJECT-TYPE
    SYNTAX      DisplayString
    MAX-ACCESS  read-write
    STATUS      current
    DESCRIPTION "Last successful upgrade time"
    ::= {infnSystem 66 }

infnSystemDcnIp6  OBJECT-TYPE
    SYNTAX     InetAddressIPv6
    MAX-ACCESS read-only
    STATUS     current
    DESCRIPTION
        "DcnIp6"
    ::= { infnSystem 67 }

infnSystemDcnIpNetMask6  OBJECT-TYPE
    SYNTAX     Integer32
    MAX-ACCESS read-only
    STATUS     current
    DESCRIPTION
        "DcnIpNetMask6"
    ::= { infnSystem 68 }

infnSystemDcnDestination6  OBJECT-TYPE
    SYNTAX     InetAddressIPv6
    MAX-ACCESS read-only
    STATUS     current
    DESCRIPTION
        "DcnDestination6"
    ::= { infnSystem 69 }

infnSystemDcnGateway6  OBJECT-TYPE
    SYNTAX     InetAddressIPv6
    MAX-ACCESS read-only
    STATUS     current
    DESCRIPTION
        "DcnGateway6"
    ::= { infnSystem 70 }

infnSystemDcnPrefixLen6  OBJECT-TYPE
    SYNTAX     Integer32
    MAX-ACCESS read-only
    STATUS     current
    DESCRIPTION
        "DcnPrefixLen6"
    ::= { infnSystem 71 }

infnSystemCraftIp6  OBJECT-TYPE
    SYNTAX     InetAddressIPv6
    MAX-ACCESS read-only
    STATUS     current
    DESCRIPTION
        "CraftIp6"
    ::= { infnSystem 72 }

infnSystemDcnLinkLocal  OBJECT-TYPE
    SYNTAX     InetAddressIPv6
    MAX-ACCESS read-only
    STATUS     current
    DESCRIPTION
        "DcnIpLinkLocal"
    ::= { infnSystem 73 }

infnSystemMigrationStatus OBJECT-TYPE
    SYNTAX    InfnMigrationStatus
    MAX-ACCESS read-write
    STATUS     current
    DESCRIPTION
        "Node migration status"
    ::= { infnSystem 74 }

infnSystemSysLogFeature OBJECT-TYPE
    SYNTAX    InfnSyslogFeature
    MAX-ACCESS read-write
    STATUS     current
    DESCRIPTION
        "Syslog Feature Disable/Enable"
    ::= { infnSystem 75 }

END

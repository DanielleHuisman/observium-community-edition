-- *****************************************************************
-- INFINERA-TOPONODE-MIB
-- 
-- October 2008, Sharfuddin Syed / Narendra Gupta
-- 
-- 
-- Copyright (c) 2008-2012 by Infinera Inc.
-- All rights reserved.
-- ****************************************************************

INFINERA-TOPONODE-MIB DEFINITIONS ::= BEGIN

IMPORTS
    OBJECT-TYPE, MODULE-IDENTITY, Integer32        FROM SNMPv2-SMI
    OBJECT-GROUP, MODULE-COMPLIANCE                FROM SNMPv2-CONF
    TruthValue, DisplayString                      FROM SNMPv2-TC
    InetAddressIPv4,InetAddressIPv6                FROM INET-ADDRESS-MIB
    SnmpEngineID                                   FROM SNMP-FRAMEWORK-MIB
    infnNE                                         FROM INFINERA-REG-MIB
    InfnNeType                                     FROM INFINERA-TC-MIB;

topoNodeMIB MODULE-IDENTITY
    LAST-UPDATED "200801110000Z"
    ORGANIZATION 
        "Infinera"
    CONTACT-INFO 
        "Infinera
                 169 Java DR
                 Sunnyvale, CA - 94089
                
                 Contact : Technical Support
                 Email   : support@infinera.com
                 Phone   : 1-877-INF-5288"
    DESCRIPTION 
        " "
::= { infnNE 2 }


-- Confirmance Statements 

topoNodeConformance  OBJECT IDENTIFIER ::= { topoNodeMIB 3 }
topoNodeCompliances  OBJECT IDENTIFIER ::= { topoNodeConformance 1 }
topoNodeGroups       OBJECT IDENTIFIER ::= { topoNodeConformance 2 }

topoNodeTable  OBJECT-TYPE
    SYNTAX SEQUENCE OF TopoNodeEntry
    MAX-ACCESS not-accessible
    STATUS     current
    DESCRIPTION 
        " A list of TopoNode entries. The number of entries is give by value of MOId."
    ::= { topoNodeMIB 1 }

topoNodeEntry  OBJECT-TYPE
    SYNTAX     TopoNodeEntry
    MAX-ACCESS not-accessible
    STATUS     current
    DESCRIPTION 
        " A  TopoNode entry containing all the information
                 pertaining to Infinera TopoNode."
    INDEX { topoNodeRouterId }
    ::= { topoNodeTable 1 }

TopoNodeEntry ::= SEQUENCE {
    topoNodeMeName          DisplayString,
    topoNodeNodeId          DisplayString,
    topoNodeNeType          InfnNeType,
    topoNodeRouterId        InetAddressIPv4,
    topoNodeDcnIp           InetAddressIPv4,
    topoNodeDcnIpNetMask    InetAddressIPv4,
    topoNodeDcnEnabled      TruthValue,
    topoNodeGatewayProxyEnabled        TruthValue,
    topoNodeXmlPortId       Integer32,
    topoNodeTl1PortId       Integer32,
    topoNodeXmlProxyPort    Integer32,
    topoNodeFtpProxyPort    Integer32,
    topoNodeTelnetProxyPort Integer32,
    topoNodeHttpProxyPort   Integer32,
    topoNodePrimaryGneIp    InetAddressIPv4,
    topoNodeSecondaryGneIp  InetAddressIPv4,
    topoNodeEnableAuxTosByteAlteration  TruthValue,
    topoNodeSnmpEngineId     SnmpEngineID,
    topoNodeSecondaryDcnIp   InetAddressIPv4,
    topoNodeDcnIp6	     InetAddressIPv6,
    topoNodeDcnIpNetMask6    Integer32,
    topoNodeDcnLinkLocal     InetAddressIPv6
}

topoNodeMeName  OBJECT-TYPE
    SYNTAX     DisplayString
    MAX-ACCESS read-only
    STATUS     current
    DESCRIPTION 
        "NeName of the Node represented by it"
    ::= { topoNodeEntry 1 }

topoNodeNodeId  OBJECT-TYPE
    SYNTAX     DisplayString
    MAX-ACCESS read-only
    STATUS     current
    DESCRIPTION 
        "Same as the NodeId of the ME object for the represented node"
    ::= { topoNodeEntry 2 }

topoNodeNeType  OBJECT-TYPE
    SYNTAX     InfnNeType
    MAX-ACCESS read-only
    STATUS     current
    DESCRIPTION 
        "The type of NE possible values are ADM/DA/DT/DA/HA/OA"
    ::= { topoNodeEntry 3 }

topoNodeRouterId  OBJECT-TYPE
    SYNTAX     InetAddressIPv4
    MAX-ACCESS read-only
    STATUS     current
    DESCRIPTION 
        "The RouterId configured in the syscfg.rc of the represented node"
    ::= { topoNodeEntry 4 }

topoNodeDcnIp  OBJECT-TYPE
    SYNTAX     InetAddressIPv4
    MAX-ACCESS read-only
    STATUS     current
    DESCRIPTION 
        "The DCN IP address to be used for connecting to the represented node"
    ::= { topoNodeEntry 5 }

topoNodeDcnIpNetMask  OBJECT-TYPE
    SYNTAX     InetAddressIPv4
    MAX-ACCESS read-only
    STATUS     current
    DESCRIPTION 
        "The netmask to be used with the DCN IP for connecting to the represented node"
    ::= { topoNodeEntry 6 }

topoNodeDcnEnabled  OBJECT-TYPE
    SYNTAX     TruthValue
    MAX-ACCESS read-only
    STATUS     current
    DESCRIPTION 
        "Indicates DCN is enabled if True and disbaled if False"
    ::= { topoNodeEntry 7 }

topoNodeGatewayProxyEnabled  OBJECT-TYPE
    SYNTAX     TruthValue
    MAX-ACCESS read-only
    STATUS     current
    DESCRIPTION 
        "Indicated that the node is capable of behaving as a GNE if true not capable if False"
    ::= { topoNodeEntry 8 }

topoNodeXmlPortId  OBJECT-TYPE
    SYNTAX     Integer32
    MAX-ACCESS read-only
    STATUS     current
    DESCRIPTION 
        "XML port number to be used for starting a XML session with the represented node"
    ::= { topoNodeEntry 9 }

topoNodeTl1PortId  OBJECT-TYPE
    SYNTAX     Integer32
    MAX-ACCESS read-only
    STATUS     current
    DESCRIPTION 
        "TL1 port number to be used for starting a session with the represented node"
    ::= { topoNodeEntry 10 }

topoNodeXmlProxyPort  OBJECT-TYPE
    SYNTAX     Integer32
    MAX-ACCESS read-only
    STATUS     current
    DESCRIPTION 
        "Xml Proxy Port to access node"
    ::= { topoNodeEntry 11 }

topoNodeFtpProxyPort  OBJECT-TYPE
    SYNTAX     Integer32
    MAX-ACCESS read-only
    STATUS     current
    DESCRIPTION 
        "Ftp Proxy Port"
    ::= { topoNodeEntry 12 }

topoNodeTelnetProxyPort  OBJECT-TYPE
    SYNTAX     Integer32
    MAX-ACCESS read-only
    STATUS     current
    DESCRIPTION 
        "Telnet Proxy Port"
    ::= { topoNodeEntry 13 }

topoNodeHttpProxyPort  OBJECT-TYPE
    SYNTAX     Integer32
    MAX-ACCESS read-only
    STATUS     current
    DESCRIPTION 
        "Http Proxy Port"
    ::= { topoNodeEntry 14 }

topoNodePrimaryGneIp  OBJECT-TYPE
    SYNTAX     InetAddressIPv4
    MAX-ACCESS read-only
    STATUS     current
    DESCRIPTION 
        "Primary Gne IP for this node"
    ::= { topoNodeEntry 15 }

topoNodeSecondaryGneIp  OBJECT-TYPE
    SYNTAX     InetAddressIPv4
    MAX-ACCESS read-only
    STATUS     current
    DESCRIPTION 
        "Secondary Gne IP for this node"
    ::= { topoNodeEntry 16 }

topoNodeEnableAuxTosByteAlteration  OBJECT-TYPE
    SYNTAX     TruthValue
    MAX-ACCESS read-only
    STATUS     current
    DESCRIPTION 
        "Enable AuxTos Byte Alteration"
    ::= { topoNodeEntry 17 }

topoNodeSnmpEngineId  OBJECT-TYPE
    SYNTAX     SnmpEngineID
    MAX-ACCESS read-only
    STATUS     current
    DESCRIPTION 
        "An SNMP engine's administratively-unique identifier."
    ::= { topoNodeEntry 18 }
    
topoNodeSecondaryDcnIp  OBJECT-TYPE
	SYNTAX     InetAddressIPv4
	MAX-ACCESS read-only
	STATUS     current
	DESCRIPTION 
		""
	::= { topoNodeEntry 19 }

topoNodeDcnIp6  OBJECT-TYPE
	SYNTAX     InetAddressIPv6
	MAX-ACCESS read-only
	STATUS     current
	DESCRIPTION 
		"The DCN IPV6 address to be used for connecting to the represented node"
	::= { topoNodeEntry 20 }

topoNodeDcnIpNetMask6  OBJECT-TYPE
    SYNTAX     Integer32
    MAX-ACCESS read-only
    STATUS     current
    DESCRIPTION 
        "The netmask to be used with the DCN IPV6 for connecting to the represented node"
    ::= { topoNodeEntry 21 }

topoNodeDcnLinkLocal  OBJECT-TYPE
    SYNTAX     InetAddressIPv6
    MAX-ACCESS read-only
    STATUS     current
    DESCRIPTION 
        "The DCN Link Local IPV6 address "
    ::= { topoNodeEntry 22 }



topoNodeCompliance  MODULE-COMPLIANCE
    STATUS     current
    DESCRIPTION 
        "Describes the requirements for conformance to the TOPONODE-MIB"
    MODULE
        MANDATORY-GROUPS { topoNodeGroup } 
    ::= { topoNodeCompliances 1 }

topoNodeGroup  OBJECT-GROUP
    OBJECTS { topoNodeRouterId, 
        topoNodeMeName, 
        topoNodeNodeId, 
        topoNodeNeType, 
        topoNodeDcnIp, 
        topoNodeDcnIpNetMask, 
        topoNodeDcnIp6,
        topoNodeDcnIpNetMask6,
	topoNodeDcnLinkLocal,
        topoNodeDcnEnabled, 
        topoNodeGatewayProxyEnabled, 
		topoNodeSecondaryDcnIp, 
        topoNodeXmlPortId, 
        topoNodeTl1PortId, 
        topoNodeXmlProxyPort, 
        topoNodeFtpProxyPort, 
        topoNodeTelnetProxyPort, 
        topoNodeHttpProxyPort, 
        topoNodePrimaryGneIp, 
        topoNodeSecondaryGneIp, 
        topoNodeEnableAuxTosByteAlteration,
        topoNodeSnmpEngineId }
    STATUS     current
    DESCRIPTION 
        " A collection of objects for managing the topoNode"
    ::= { topoNodeGroups 1 }
END

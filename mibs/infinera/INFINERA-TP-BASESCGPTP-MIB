-- *****************************************************************
-- INFINERA-TP-BASESCGPTP-MIB
-- Copyright (c) 2008-2013 by Infinera Inc
-- All rights reserved.
-- ****************************************************************

INFINERA-TP-BASESCGPTP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths, InfnEnableDisable          FROM INFINERA-TC-MIB
    terminationPoint                            FROM INFINERA-REG-MIB;

baseScgPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 46 }

baseScgPtpTable OBJECT-TYPE
    SYNTAX      SEQUENCE OF BaseScgPtpEntry
    MAX-ACCESS  not-accessible
    STATUS      current
    DESCRIPTION
        "A list of BaseScgPtp entries. Each entry is uniquely identified by the value of ifIndex."
    ::= { baseScgPtpMIB 1 } 

baseScgPtpEntry  OBJECT-TYPE
    SYNTAX      BaseScgPtpEntry
    MAX-ACCESS  not-accessible
    STATUS      current
    DESCRIPTION
        "A BaseScgPtp entry containing information pertaining to Infinera BaseScgPtp Interfaces.
        This table is a subclass of IfCommon. Entries will exist in this table only for
        interfaces of type DLM OCG PTP."
    INDEX { ifIndex }
    ::= { baseScgPtpTable 1 }


BaseScgPtpEntry  ::= SEQUENCE {
    baseScgPtpScgNumber                         Integer32,
    baseScgPtpMPOAID                            DisplayString,
    baseScgPtpPathLossCheckControlStatus        INTEGER,
    baseScgPtpLastSuccessfullPathLossCheckTS    Integer32,
    baseScgPtpPathLoss                          FloatHundredths,
    baseScgPtpPathLossCheckDetectedPort         DisplayString,
    baseScgPtpLastPathLossCheckAttemptTS        Integer32,
    baseScgPtpLastPathLossCheckAttemptStatus    INTEGER,
    baseScgPtpLastPathLossCheckFailedReason     INTEGER,
    baseScgPtpPathLossHigh                      INTEGER
}

baseScgPtpScgNumber    OBJECT-TYPE
    SYNTAX      Integer32
    MAX-ACCESS  read-only
    STATUS      current
    DESCRIPTION ""
    ::= { baseScgPtpEntry  1 }

baseScgPtpMPOAID OBJECT-TYPE
    SYNTAX      DisplayString
    MAX-ACCESS  read-only
    STATUS      current
    DESCRIPTION ""
    ::= { baseScgPtpEntry  2 }

baseScgPtpPathLossCheckControlStatus OBJECT-TYPE
    SYNTAX      INTEGER {
        inProgress(1),
        idle(2)
    }
    MAX-ACCESS  read-only
    STATUS      current
    DESCRIPTION ""
    ::= { baseScgPtpEntry 3 }

baseScgPtpLastSuccessfullPathLossCheckTS OBJECT-TYPE
    SYNTAX      Integer32
    MAX-ACCESS  read-only
    STATUS      current
    DESCRIPTION ""
    ::= { baseScgPtpEntry 4 }

baseScgPtpPathLoss OBJECT-TYPE
    SYNTAX      FloatHundredths
    MAX-ACCESS  read-only
    STATUS      current
    DESCRIPTION ""
    ::= { baseScgPtpEntry 5 }

baseScgPtpPathLossCheckDetectedPort OBJECT-TYPE
    SYNTAX      DisplayString
    MAX-ACCESS  read-only
    STATUS      current
    DESCRIPTION ""
    ::= { baseScgPtpEntry 6 }

baseScgPtpLastPathLossCheckAttemptTS OBJECT-TYPE
    SYNTAX      Integer32
    MAX-ACCESS  read-only
    STATUS      current
    DESCRIPTION ""
    ::= { baseScgPtpEntry 7 }

baseScgPtpLastPathLossCheckAttemptStatus OBJECT-TYPE
    SYNTAX      INTEGER {
        successfull (1),
        unsuccessfull(2),
        notAttempted(3)
    }
    MAX-ACCESS  read-only
    STATUS      current
    DESCRIPTION ""
    ::= { baseScgPtpEntry 8 }

baseScgPtpLastPathLossCheckFailedReason OBJECT-TYPE
    SYNTAX      INTEGER {
        na (1),
        timedOut(2),
        interruptedbyAD(3),
        interruptedbyReset(4),
        portInService(5)
    }
    MAX-ACCESS  read-only
    STATUS      current
    DESCRIPTION ""
    ::= { baseScgPtpEntry 9 }

baseScgPtpPathLossHigh OBJECT-TYPE
    SYNTAX      INTEGER {
        true(1),
        false(2)
    }
    MAX-ACCESS  read-only
    STATUS      current
    DESCRIPTION ""
    ::= { baseScgPtpEntry 10 }



-- Conformance Statements
baseScgPtpConformance    OBJECT IDENTIFIER ::= { baseScgPtpMIB 3 }
baseScgPtpCompliances    OBJECT IDENTIFIER ::= { baseScgPtpConformance 1 }
baseScgPtpGroups         OBJECT IDENTIFIER ::= { baseScgPtpConformance 2 }

baseScgPtpCompliance MODULE-COMPLIANCE
    STATUS current
    DESCRIPTION
    "Describes the requirements for conformance to the BASESCGPTP-MIB"
    MODULE
        MANDATORY-GROUPS { baseScgPtpGroup }
    ::= { baseScgPtpCompliances 1 }

baseScgPtpGroup OBJECT-GROUP
    OBJECTS {
        baseScgPtpScgNumber,        
        baseScgPtpMPOAID        , 
        baseScgPtpPathLossCheckControlStatus   , 
        baseScgPtpLastSuccessfullPathLossCheckTS,
        baseScgPtpPathLoss                      ,
        baseScgPtpPathLossCheckDetectedPort     ,
        baseScgPtpLastPathLossCheckAttemptTS    ,
        baseScgPtpLastPathLossCheckAttemptStatus,
        baseScgPtpLastPathLossCheckFailedReason ,
        baseScgPtpPathLossHigh
    }
    STATUS current
    DESCRIPTION
        " A collection of objects for managing the baseScgPtp"
    ::= { baseScgPtpGroups 1 }
END

-- *****************************************************************
-- INFINERA-TP-BPP-MIB
-- Copyright (c) 2008-2012 by Infinera Inc
-- All rights reserved.
-- ****************************************************************

INFINERA-TP-BPP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths,InfnEnableDisable           FROM INFINERA-TC-MIB
    terminationPoint                            FROM INFINERA-REG-MIB;

bppPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 66 }

bppPtpTable OBJECT-TYPE
    SYNTAX      SEQUENCE OF BppPtpEntry
    MAX-ACCESS  not-accessible
    STATUS      current
    DESCRIPTION
        "A list of BppPtp entries. Each entry is uniquely identified by the value of ifIndex."
    ::= { bppPtpMIB 1 } 

bppPtpEntry  OBJECT-TYPE
    SYNTAX      BppPtpEntry
    MAX-ACCESS  not-accessible
    STATUS      current
    DESCRIPTION
        "A BppPtp entry containing information pertaining to Infinera BppPtp Interfaces.
        This table is a subclass of IfCommon. Entries will exist in this table only for
        interfaces of type DLM OCG PTP."
    INDEX { ifIndex }
    ::= { bppPtpTable 1 }


BppPtpEntry  ::= SEQUENCE {
    bppPtpProvNbrTP           DisplayString
}

bppPtpProvNbrTP   OBJECT-TYPE
    SYNTAX      DisplayString
    MAX-ACCESS  read-write
    STATUS      current
    DESCRIPTION ""
    ::= { bppPtpEntry 1 }

-- Conformance Statements
bppPtpConformance    OBJECT IDENTIFIER ::= { bppPtpMIB 3 }
bppPtpCompliances    OBJECT IDENTIFIER ::= { bppPtpConformance 1 }
bppPtpGroups         OBJECT IDENTIFIER ::= { bppPtpConformance 2 }

bppPtpCompliance MODULE-COMPLIANCE
    STATUS current
    DESCRIPTION
    "Describes the requirements for conformance to the BPP-MIB"
    MODULE
        MANDATORY-GROUPS { bppPtpGroup }
    ::= { bppPtpCompliances 1 }

bppPtpGroup OBJECT-GROUP
    OBJECTS {

        bppPtpProvNbrTP
}
    STATUS current
    DESCRIPTION
        " A collection of objects for managing the bppPtp"
    ::= { bppPtpGroups 1 }
END

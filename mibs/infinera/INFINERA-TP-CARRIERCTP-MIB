-- ***************************************************************
-- INFINERA-TP-CARRIERCTP-MIB
--
-- Copyright (c) 2008-2012 by Infinera Inc.
-- All rights reserved.
-- ****************************************************************

INFINERA-TP-CARRIERCTP-MIB DEFINITIONS ::= BEGIN

IMPORTS
    Integer32, Counter64, Unsigned32,
    OBJECT-TYPE, MODULE-IDENTITY        FROM SNMPv2-SMI
    OBJECT-GROUP, MODULE-COMPLIANCE     FROM SNMPv2-CONF
    RowStatus, DisplayString            FROM SNMPv2-TC
    ifIndex                             FROM IF-MIB
    terminationPoint                    FROM INFINERA-REG-MIB
    InfnLatencyMode, InfnOpticalSignal,
    InfnOperationalState,
    InfnTuningStatus, InfnProvBaudRate,
    InfnFFCRAveraging,
    InfnEnableDisableType,
    InfnEqptType, FloatHundredths,
    InfnEnableDisable,InfnEncoding,
    InfnCDCompType, InfnCDRange,
    InfnFFCRMode, InfnCarrierType,
    FloatArbitraryPrecision,
    FloatTenths                         FROM INFINERA-TC-MIB;

carrierCtpMIB MODULE-IDENTITY
    LAST-UPDATED  "201310200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for CARRIERCTP terminationPoint table."

::= { terminationPoint 38 }

carrierCtpTable  OBJECT-TYPE
    SYNTAX SEQUENCE OF CarrierCtpEntry
    MAX-ACCESS not-accessible
    STATUS     current
    DESCRIPTION
        "This table contains all CARRIERCTP modules that are currently present in a network element."
    ::= { carrierCtpMIB 1 }

carrierCtpEntry  OBJECT-TYPE
    SYNTAX     CarrierCtpEntry
    MAX-ACCESS not-accessible
    STATUS     current
    DESCRIPTION
        "A row in the CARRIERCTP table. Each row in the table is identified with a unique entPhysicalIndexID.
        "
    INDEX { ifIndex }
    ::= { carrierCtpTable 1 }

CarrierCtpEntry ::= SEQUENCE {
      carrierCtpPmHistStatsEnable      INTEGER,
      carrierCtpModulation             INTEGER,
      carrierCtpCarrierRate            FloatTenths,
      carrierCtpEncodingMode           InfnEncoding,
      carrierCtpPMDHighThreshold       FloatTenths,
      carrierCtpPMDHighTCAReporting    INTEGER,
      carrierCtpCDCompMode             InfnCDCompType,
      carrierCtpCDSet                  Integer32,
      carrierCtpCDRange                InfnCDRange,
      carrierCtpFFCRMode               InfnCDCompType,
      carrierCtpFFCRBlockSize          FloatTenths,
      carrierCtpFFCRXYAveraging          Integer32,
      carrierCtpPreFecBerSigDegTcaRept InfnEnableDisable,
      carrierCtpPreFecQSigDegTcaRept   InfnEnableDisable,
      carrierCtpPreFecBerSigDegTh      FloatArbitraryPrecision,
      carrierCtpPreFecQSigDegTh        FloatArbitraryPrecision,
      carrierCtpPreFecQSigDegHysteresis FloatTenths,
      carrierCtpPreFecBERSigDegHysteresis FloatTenths,
      carrierCtpFineGranularPreFecQ        InfnEnableDisable,
      carrierCtpFineGranularPreFecQSampling Integer32,
      carrierCtpRapidRecovery           InfnEnableDisable,
      carrierCtpAggresivePolarizationTracking  InfnEnableDisable,
      carrierCtpFrequency               DisplayString,
      carrierCtpFFCRAveraging           InfnFFCRAveraging,
      carrierCtpBaudRate                InfnProvBaudRate,
      carrierCtpProvGainSharing         InfnOperationalState,
      carrierCtpGainSharing             InfnOperationalState,
      carrierCtpProvFecIterations       Integer32,
      carrierCtpFecIterations           Integer32,
      carrierCtpTxCD                    Integer32,
      carrierCtpProvTxCD                Integer32,
      carrierCtpLatency                 InfnLatencyMode,
      carrierCtpOpticalSignal           InfnOpticalSignal,
      carrierCtpTuningStatus            InfnTuningStatus,
      carrierCtpBwResilientSsLoopControl InfnEnableDisableType,
      carrierCtpBwResilientCtLoopControl InfnEnableDisableType,
      carrierCtpProvLatency             InfnLatencyMode,
      carrierCtpInstCDSet               Integer32,
      carrierCtpClockMode               Unsigned32,
      carrierCtpNLCSetting              Unsigned32,
      carrierCtpNLCStatus               Unsigned32
 }

carrierCtpPmHistStatsEnable OBJECT-TYPE
    SYNTAX  INTEGER {
        enabled(1),
        disabled(2)
    }
    MAX-ACCESS  read-create
    STATUS      current
    DESCRIPTION ""
    ::= { carrierCtpEntry 1 }

carrierCtpModulation OBJECT-TYPE
    SYNTAX      INTEGER {
        pmQPSK(1),
        pmBPSK(2),
        pmEnhancedBPSK(3),
        pm3QAM(4),
        pm8QAM(5),
        pm16QAM(6),
        pmNONE(101)
    }
    MAX-ACCESS  read-only
    STATUS      current
    DESCRIPTION ""
    ::= { carrierCtpEntry 2 }

carrierCtpCarrierRate OBJECT-TYPE
    SYNTAX      FloatTenths
    MAX-ACCESS  read-only
    STATUS      current
    DESCRIPTION ""
    ::= {   carrierCtpEntry 3 }

carrierCtpEncodingMode  OBJECT-TYPE
    SYNTAX      InfnEncoding
    MAX-ACCESS  read-only
    STATUS      current
    DESCRIPTION ""
    ::= { carrierCtpEntry  4 }

carrierCtpPMDHighThreshold   OBJECT-TYPE
    SYNTAX      FloatTenths
    MAX-ACCESS  read-write
    STATUS      current
    DESCRIPTION ""
    ::= { carrierCtpEntry  5 }

carrierCtpPMDHighTCAReporting  OBJECT-TYPE
    SYNTAX      InfnEnableDisable
    MAX-ACCESS  read-write
    STATUS      current
    DESCRIPTION ""
    ::= { carrierCtpEntry  6 }

carrierCtpCDCompMode  OBJECT-TYPE
    SYNTAX     InfnCDCompType
    MAX-ACCESS  read-write
    STATUS      current
    DESCRIPTION ""
    ::= { carrierCtpEntry  7 }

carrierCtpCDSet  OBJECT-TYPE
    SYNTAX      Integer32
    MAX-ACCESS  read-write
    STATUS      current
    DESCRIPTION ""
    ::= { carrierCtpEntry  8 }

carrierCtpCDRange  OBJECT-TYPE
    SYNTAX     InfnCDRange
    MAX-ACCESS  read-write
    STATUS      current
    DESCRIPTION ""
    ::= { carrierCtpEntry  9 }


carrierCtpFFCRMode  OBJECT-TYPE
    SYNTAX     InfnFFCRMode
    MAX-ACCESS  read-write
    STATUS      current
    DESCRIPTION ""
    ::= { carrierCtpEntry  10 }

carrierCtpFFCRBlockSize  OBJECT-TYPE
    SYNTAX     FloatTenths
    MAX-ACCESS  read-write
    STATUS      current
    DESCRIPTION ""
    ::= { carrierCtpEntry  11 }

carrierCtpFFCRXYAveraging OBJECT-TYPE
    SYNTAX          Integer32
    MAX-ACCESS      read-only
    STATUS          current
    DESCRIPTION     ""
    ::= { carrierCtpEntry 12 }

carrierCtpPreFecBerSigDegTcaRept  OBJECT-TYPE
    SYNTAX     InfnEnableDisable
    MAX-ACCESS  read-write
    STATUS      current
    DESCRIPTION ""
    ::= { carrierCtpEntry  13 }

carrierCtpPreFecQSigDegTcaRept  OBJECT-TYPE
    SYNTAX     InfnEnableDisable
    MAX-ACCESS  read-write
    STATUS      current
    DESCRIPTION ""
    ::= { carrierCtpEntry  14 }

carrierCtpPreFecBerSigDegTh  OBJECT-TYPE
    SYNTAX      FloatArbitraryPrecision
    MAX-ACCESS  read-only
    STATUS      current
    DESCRIPTION ""
    ::= { carrierCtpEntry  15 }

carrierCtpPreFecQSigDegTh  OBJECT-TYPE
    SYNTAX      FloatArbitraryPrecision
    MAX-ACCESS  read-write
    STATUS      current
    DESCRIPTION ""
    ::= { carrierCtpEntry  16 }

carrierCtpPreFecQSigDegHysteresis OBJECT-TYPE
    SYNTAX      FloatTenths
    MAX-ACCESS  read-write
    STATUS      current
    DESCRIPTION ""
    ::= { carrierCtpEntry 17 }

carrierCtpPreFecBERSigDegHysteresis OBJECT-TYPE
    SYNTAX      FloatTenths
    MAX-ACCESS  read-only
    STATUS      current
    DESCRIPTION ""
    ::= { carrierCtpEntry 18 }


carrierCtpFineGranularPreFecQ OBJECT-TYPE
    SYNTAX     InfnEnableDisable
    MAX-ACCESS read-write
    STATUS     current
    DESCRIPTION ""
    ::= { carrierCtpEntry 19 }

carrierCtpFineGranularPreFecQSampling OBJECT-TYPE
    SYNTAX     Integer32
    MAX-ACCESS read-only
    STATUS     current
    DESCRIPTION ""
    ::= { carrierCtpEntry 20 }

carrierCtpRapidRecovery OBJECT-TYPE
    SYNTAX     InfnEnableDisable
    MAX-ACCESS read-write
    STATUS     current
    DESCRIPTION ""
    ::= { carrierCtpEntry 21 }

carrierCtpAggresivePolarizationTracking OBJECT-TYPE
    SYNTAX     InfnEnableDisable
    MAX-ACCESS read-write
    STATUS     current
    DESCRIPTION ""
    ::= { carrierCtpEntry 22 }

carrierCtpFrequency OBJECT-TYPE
    SYNTAX     DisplayString
    MAX-ACCESS read-only
    STATUS     current
    DESCRIPTION ""
    ::= { carrierCtpEntry 23 }

carrierCtpFFCRAveraging OBJECT-TYPE
    SYNTAX     InfnFFCRAveraging
    MAX-ACCESS read-write
    STATUS     current
    DESCRIPTION ""
    ::= { carrierCtpEntry 24 }

carrierCtpBaudRate OBJECT-TYPE
    SYNTAX     InfnProvBaudRate
    MAX-ACCESS read-only
    STATUS     current
    DESCRIPTION ""
    ::= { carrierCtpEntry 25 }

carrierCtpProvGainSharing OBJECT-TYPE
    SYNTAX     InfnOperationalState
    MAX-ACCESS read-write
    STATUS     current
    DESCRIPTION ""
    ::= { carrierCtpEntry 26 }

carrierCtpGainSharing OBJECT-TYPE
    SYNTAX     InfnOperationalState
    MAX-ACCESS read-only
    STATUS     current
    DESCRIPTION ""
    ::= { carrierCtpEntry 27 }

carrierCtpProvFecIterations OBJECT-TYPE
    SYNTAX     Integer32
    MAX-ACCESS read-write
    STATUS     current
    DESCRIPTION ""
    ::= { carrierCtpEntry 28 }

carrierCtpFecIterations OBJECT-TYPE
    SYNTAX     Integer32
    MAX-ACCESS read-only
    STATUS     current
    DESCRIPTION ""
    ::= { carrierCtpEntry 29 }

carrierCtpTxCD OBJECT-TYPE
    SYNTAX     Integer32
    MAX-ACCESS read-only
    STATUS     current
    DESCRIPTION ""
    ::= { carrierCtpEntry 30 }

carrierCtpProvTxCD OBJECT-TYPE
    SYNTAX     Integer32
    MAX-ACCESS read-write
    STATUS     current
    DESCRIPTION ""
    ::= { carrierCtpEntry 31 }

carrierCtpLatency OBJECT-TYPE
    SYNTAX     InfnLatencyMode
    MAX-ACCESS read-only
    STATUS     current
    DESCRIPTION ""
    ::= { carrierCtpEntry 32 }

carrierCtpOpticalSignal OBJECT-TYPE
    SYNTAX     InfnOpticalSignal
    MAX-ACCESS read-write
    STATUS     current
    DESCRIPTION ""
    ::= { carrierCtpEntry 33 }

carrierCtpTuningStatus OBJECT-TYPE
    SYNTAX     InfnTuningStatus
    MAX-ACCESS read-only
    STATUS     current
    DESCRIPTION ""
    ::= { carrierCtpEntry 34 }

carrierCtpBwResilientSsLoopControl OBJECT-TYPE
    SYNTAX     InfnEnableDisableType
    MAX-ACCESS read-write
    STATUS     current
    DESCRIPTION ""
    ::= { carrierCtpEntry 35 }

carrierCtpBwResilientCtLoopControl OBJECT-TYPE
    SYNTAX     InfnEnableDisableType
    MAX-ACCESS read-write
    STATUS     current
    DESCRIPTION ""
    ::= { carrierCtpEntry 36 }

carrierCtpProvLatency OBJECT-TYPE
    SYNTAX     InfnLatencyMode
    MAX-ACCESS read-write
    STATUS     current
    DESCRIPTION ""
    ::= { carrierCtpEntry 37 }

carrierCtpInstCDSet OBJECT-TYPE
    SYNTAX     Integer32
    MAX-ACCESS read-only
    STATUS     current
    DESCRIPTION ""
    ::= { carrierCtpEntry 38 }

carrierCtpClockMode OBJECT-TYPE
    SYNTAX     Unsigned32
    MAX-ACCESS read-write
    STATUS     current
    DESCRIPTION ""
    ::= { carrierCtpEntry 39 }

carrierCtpNLCSetting OBJECT-TYPE
    SYNTAX     Unsigned32
    MAX-ACCESS read-write
    STATUS     current
    DESCRIPTION ""
    ::= { carrierCtpEntry 40 }

carrierCtpNLCStatus OBJECT-TYPE
    SYNTAX     Unsigned32
    MAX-ACCESS read-only
    STATUS     current
    DESCRIPTION ""
    ::= { carrierCtpEntry 41 }

-- Conformance Statements
carrierCtpConformance    OBJECT IDENTIFIER ::= { carrierCtpMIB 37 }
carrierCtpCompliances    OBJECT IDENTIFIER ::= { carrierCtpConformance 1 }
carrierCtpGroups         OBJECT IDENTIFIER ::= { carrierCtpConformance 2 }

carrierCtpCompliance  MODULE-COMPLIANCE
    STATUS      current
    DESCRIPTION ""
    MODULE
        MANDATORY-GROUPS { carrierCtpGroup }
    ::= { carrierCtpCompliances 1 }

carrierCtpGroup  OBJECT-GROUP
    OBJECTS {
    carrierCtpPmHistStatsEnable,
    carrierCtpModulation,
    carrierCtpCarrierRate,
    carrierCtpEncodingMode,
    carrierCtpPMDHighThreshold,
    carrierCtpPMDHighTCAReporting,
    carrierCtpCDCompMode,
    carrierCtpCDRange,
    carrierCtpFFCRMode,
    carrierCtpFFCRBlockSize,
    carrierCtpPreFecBerSigDegTcaRept,
    carrierCtpPreFecQSigDegTcaRept,
    carrierCtpPreFecBerSigDegTh,
    carrierCtpPreFecQSigDegTh,
    carrierCtpPreFecQSigDegHysteresis,
    carrierCtpPreFecBERSigDegHysteresis,
    carrierCtpFFCRXYAveraging,
    carrierCtpCDSet,

    carrierCtpFineGranularPreFecQ,
    carrierCtpFineGranularPreFecQSampling,
    carrierCtpRapidRecovery,
    carrierCtpAggresivePolarizationTracking,
    carrierCtpFrequency,
    carrierCtpFFCRAveraging,
    carrierCtpBaudRate,
    carrierCtpProvGainSharing,
    carrierCtpGainSharing,
    carrierCtpProvFecIterations,
    carrierCtpFecIterations,
    carrierCtpTxCD,
    carrierCtpProvTxCD,
    carrierCtpLatency,
    carrierCtpOpticalSignal,
    carrierCtpTuningStatus,
    carrierCtpBwResilientSsLoopControl,
    carrierCtpBwResilientCtLoopControl,
    carrierCtpProvLatency,
    carrierCtpInstCDSet,
    carrierCtpClockMode,
    carrierCtpNLCSetting,
    carrierCtpNLCStatus
    }
    STATUS      current
    DESCRIPTION ""
    ::= { carrierCtpGroups 1 }
END

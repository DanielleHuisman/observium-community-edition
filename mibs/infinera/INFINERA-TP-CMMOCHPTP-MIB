-- *****************************************************************
-- INFINERA-TP-CMMOCHPTP-MIB
-- Copyright (c) 2008-2012 by Infinera Inc.
-- All rights reserved.
-- ****************************************************************

INFINERA-TP-CMMOCHPTP-MIB DEFINITIONS ::= BEGIN

IMPORTS
    MODULE-IDENTITY, OBJECT-TYPE                FROM SNMPv2-SMI
    MODULE-COMPLIANCE, OBJECT-GROUP             FROM SNMPv2-CONF
    DisplayString, TruthValue                   FROM SNMPv2-TC
    ifIndex                                     FROM IF-MIB
    InfnModulationCategory, InfnWaveInterfaceType,
    InfnEnableDisableType, InfnPmHistStatsControl,
    FloatHundredths,InfnServiceType             FROM INFINERA-TC-MIB
    terminationPoint                            FROM INFINERA-REG-MIB;


cmmOchPtpMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 29 }

cmmOchPtpTable OBJECT-TYPE
    SYNTAX      SEQUENCE OF CmmOchPtpEntry
    MAX-ACCESS  not-accessible
    STATUS      current
    DESCRIPTION
        "A list of CmmOchPtp entries. Each entry is uniquely identified by the value of ifIndex."
    ::= { cmmOchPtpMIB 1 }

cmmOchPtpEntry  OBJECT-TYPE
    SYNTAX      CmmOchPtpEntry
    MAX-ACCESS  not-accessible
    STATUS      current
    DESCRIPTION
        "A CmmOchPtp entry containing information pertaining to Infinera CmmOchPtp Interfaces.
        This table is a subclass of IfCommon. Entries will exist in this table only for
        interfaces of type CMM OCH PTP."
    INDEX { ifIndex }
    ::= { cmmOchPtpTable 1 }


CmmOchPtpEntry  ::= SEQUENCE {
    cmmOchPtpProvisionedOchOWPortId         INTEGER,
    cmmOchPtpPmHistStatsEnable          InfnPmHistStatsControl,
    cmmOchPtpProvisionedOchPort         DisplayString,
    cmmOchPtpDiscoveredOchPortId        DisplayString,
    cmmOchPtpDiscoveredWavelength       FloatHundredths,
    cmmOchPtpWavelengthDetectedState    INTEGER,
    cmmOchPtpInterfaceType              InfnWaveInterfaceType,
    cmmOchPtpTargetPowerOffset          FloatHundredths,
    cmmOchPtpPowerControlLoop           InfnEnableDisableType,
    cmmOchPtpModulationCatagory         InfnModulationCategory
}

cmmOchPtpProvisionedOchOWPortId OBJECT-TYPE
    SYNTAX      INTEGER
    MAX-ACCESS  read-only
    STATUS      current
    DESCRIPTION
        "This refers to the name of the CMM OCH PTP to which this fiber is connected."
    ::= { cmmOchPtpEntry  1 }

cmmOchPtpPmHistStatsEnable OBJECT-TYPE
    SYNTAX  InfnPmHistStatsControl
    MAX-ACCESS  read-write
    STATUS      current
    DESCRIPTION "Flag to enable or disable PM collection."
    DEFVAL      { enabled }
    ::= { cmmOchPtpEntry  2 }


cmmOchPtpProvisionedOchPort  OBJECT-TYPE
    SYNTAX      DisplayString
    MAX-ACCESS  read-write
    STATUS      current
    DESCRIPTION
        "Provisioned OCH TP."
    ::= { cmmOchPtpEntry  3 }

cmmOchPtpDiscoveredOchPortId OBJECT-TYPE
    SYNTAX      DisplayString
    MAX-ACCESS  read-only
    STATUS      current
    DESCRIPTION
        "DisplayString OCH TP"
    ::= { cmmOchPtpEntry  4 }

cmmOchPtpDiscoveredWavelength OBJECT-TYPE
    SYNTAX      FloatHundredths
    MAX-ACCESS  read-only
    STATUS      current
    DESCRIPTION "Discovered wavelength for CmmOchPtp"
    ::= { cmmOchPtpEntry  5 }

cmmOchPtpWavelengthDetectedState OBJECT-TYPE
    SYNTAX  INTEGER {
        unknown(1),
        notStarted(2),
        failed(3),
        notValid(4),
        shutdown(5),
        inprogress(6),
        completed(7)
    }
    MAX-ACCESS  read-only
    STATUS      current
    DESCRIPTION
        "State of the Detected wavelength."
    ::= { cmmOchPtpEntry  6 }


cmmOchPtpInterfaceType OBJECT-TYPE
    SYNTAX  InfnWaveInterfaceType
    MAX-ACCESS  read-write
    STATUS      current
    DESCRIPTION
        "This attribute describes the type of interface attached to a CMM OCH PTP port."
    ::= { cmmOchPtpEntry  7 }

cmmOchPtpTargetPowerOffset  OBJECT-TYPE
    SYNTAX      FloatHundredths
    MAX-ACCESS  read-only
    STATUS      current
    DESCRIPTION "OCH Target power offset "
    DEFVAL      { 0 }
    ::= { cmmOchPtpEntry  8 }

cmmOchPtpPowerControlLoop OBJECT-TYPE
    SYNTAX  InfnEnableDisableType
    MAX-ACCESS  read-write
    STATUS      current
    DESCRIPTION "Parameter that indicates whether OCH Control Loop is enabled or disabled."
    DEFVAL      { enabled }
    ::= { cmmOchPtpEntry  9 }

cmmOchPtpModulationCatagory OBJECT-TYPE
    SYNTAX  InfnModulationCategory
    MAX-ACCESS  read-write
    STATUS      current
    DESCRIPTION "Modulation Category"
    DEFVAL      { notset }
    ::= { cmmOchPtpEntry  10 }

-- Conformance Statements
cmmOchPtpConformance    OBJECT IDENTIFIER ::= { cmmOchPtpMIB 3 }
cmmOchPtpCompliances    OBJECT IDENTIFIER ::= { cmmOchPtpConformance 1 }
cmmOchPtpGroups         OBJECT IDENTIFIER ::= { cmmOchPtpConformance 2 }

cmmOchPtpCompliance MODULE-COMPLIANCE
    STATUS current
    DESCRIPTION
    "Describes the requirements for conformance to the CMMOCHPTP-MIB"
    MODULE
        MANDATORY-GROUPS { cmmOchPtpGroup }
    ::= { cmmOchPtpCompliances 1 }

cmmOchPtpGroup OBJECT-GROUP
    OBJECTS {
    cmmOchPtpProvisionedOchOWPortId,
    cmmOchPtpPmHistStatsEnable,
    cmmOchPtpProvisionedOchPort,
    cmmOchPtpDiscoveredOchPortId,
    cmmOchPtpDiscoveredWavelength,
    cmmOchPtpWavelengthDetectedState,
    cmmOchPtpInterfaceType,
    cmmOchPtpTargetPowerOffset,
    cmmOchPtpPowerControlLoop,
    cmmOchPtpModulationCatagory
    }
    STATUS current
    DESCRIPTION
        " A collection of objects for managing the cmmOchPtp"
    ::= { cmmOchPtpGroups 1 }


END

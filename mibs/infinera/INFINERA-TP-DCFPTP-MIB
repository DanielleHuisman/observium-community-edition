-- *****************************************************************
-- INFINERA-TP-DCFPTP-MIB
-- 
-- October 2008, Sharfuddin Syed / Narendra Gupta
-- 
-- 
-- Copyright (c) 2008-2012 by Infinera Inc.
-- All rights reserved.
-- ****************************************************************

INFINERA-TP-DCFPTP-MIB DEFINITIONS ::= BEGIN

IMPORTS
    MODULE-IDENTITY, OBJECT-TYPE,
    Integer32                                   FROM SNMPv2-SMI
    MODULE-COMPLIANCE, OBJECT-GROUP             FROM SNMPv2-CONF
    DisplayString                               FROM SNMPv2-TC
    ifIndex                                     FROM IF-MIB
    FloatTenths, InfnDcmType                    FROM INFINERA-TC-MIB
    terminationPoint                            FROM INFINERA-REG-MIB;


dcfPtpMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 5 }



dcfPtpTable OBJECT-TYPE
    SYNTAX      SEQUENCE OF DcfPtpEntry
    MAX-ACCESS  not-accessible
    STATUS      current
    DESCRIPTION
        "A list of DcfPtp entries. Each entry is uniquely identified by the value of ifIndex."
    ::= { dcfPtpMIB 1 } 

dcfPtpEntry  OBJECT-TYPE
    SYNTAX      DcfPtpEntry
    MAX-ACCESS  not-accessible
    STATUS      current
    DESCRIPTION
        "A DcfPtp entry containing information pertaining to Infinera DcfPtp interfaces. This
        table is a subclass of IfCommon. Entries will exist in this table only for interfaces of type dcfPtP.
        A DCF PTP interface represents the endpoint of the Dispersion Compensating Fiber."
    INDEX { ifIndex }
    ::= { dcfPtpTable 1 }


DcfPtpEntry  ::= SEQUENCE {
    dcfPtpDcmType                 INTEGER,
    dcfPtpExpectedDcfLoss         FloatTenths,
    dcfPtpExpectedDispersion      Integer32,
    dcfPtpDcfLossReporting        INTEGER,
    dcfPtpPmHistStatsEnable       INTEGER,
    dcfPtpProvisionedRemoteTP     DisplayString
}

dcfPtpDcmType OBJECT-TYPE
    SYNTAX  InfnDcmType 
    MAX-ACCESS  read-write
    STATUS      current
    DESCRIPTION "The DCM Type."
    DEFVAL      { unspecified }
    ::= { dcfPtpEntry  1 }


dcfPtpExpectedDcfLoss OBJECT-TYPE
    SYNTAX      FloatTenths
    UNITS       "0.1 dB"
    MAX-ACCESS  read-only
    STATUS      current
    DESCRIPTION
        "The expected DCF loss in dB."
    DEFVAL      { 0 }
    ::= { dcfPtpEntry  2 }


dcfPtpExpectedDispersion OBJECT-TYPE
    SYNTAX      Integer32
    UNITS       "100 ps/nm"
    MAX-ACCESS  read-only
    STATUS      current
    DESCRIPTION
        "The amount of DCF in between the MidStage. Measured in ps/nm units."
    DEFVAL      { 0 }
    ::= { dcfPtpEntry  3 }


dcfPtpDcfLossReporting OBJECT-TYPE
    SYNTAX  INTEGER {
        disabled(1),
        enabled(2)
    }
    MAX-ACCESS  read-write
    STATUS      current
    DESCRIPTION
        "If enabled, the DCF compensation mismatch alarm/TCC will be reported."
    DEFVAL      { disabled }
    ::= { dcfPtpEntry  4 }


dcfPtpPmHistStatsEnable OBJECT-TYPE
    SYNTAX  INTEGER {
        enabled(1),
        disabled(2)
    }
    MAX-ACCESS  read-write
    STATUS      current
    DESCRIPTION "Flag to enable or disable PM collection."
    DEFVAL      { enabled }
    ::= { dcfPtpEntry  5 }

dcfPtpProvisionedRemoteTP  OBJECT-TYPE
    SYNTAX     DisplayString
    MAX-ACCESS read-only
    STATUS     current
    DESCRIPTION 
        "This objects refers to the peer DSE module where fiber is connected"
    ::= { dcfPtpEntry 6 }
    
-- Conformance Statements
dcfPtpConformance    OBJECT IDENTIFIER ::= { dcfPtpMIB 3 }
dcfPtpCompliances    OBJECT IDENTIFIER ::= { dcfPtpConformance 1 }
dcfPtpGroups         OBJECT IDENTIFIER ::= { dcfPtpConformance 2 }

dcfPtpCompliance MODULE-COMPLIANCE
    STATUS current
    DESCRIPTION
    "Describes the requirements for conformance to the DCFPTP-MIB"
    MODULE
        MANDATORY-GROUPS { dcfPtpGroup }
    ::= { dcfPtpCompliances 1 }

dcfPtpGroup OBJECT-GROUP
    OBJECTS {
        dcfPtpDcmType,
        dcfPtpExpectedDcfLoss,
        dcfPtpExpectedDispersion,
        dcfPtpDcfLossReporting,
        dcfPtpPmHistStatsEnable
    }
    STATUS current
    DESCRIPTION
        " A collection of objects for managing the dcfPtp"
    ::= { dcfPtpGroups 1 }


END

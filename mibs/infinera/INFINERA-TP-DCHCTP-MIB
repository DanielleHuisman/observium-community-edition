-- *****************************************************************
-- INFINERA-TP-DCHCTP-MIB
--   
-- October 2008, Sharfuddin Syed / Narendra Gupta
--   
--   
-- Copyright (c) 2008-2012 by Infinera Inc.
-- All rights reserved.
-- ****************************************************************

INFINERA-TP-DCHCTP-MIB DEFINITIONS ::= BEGIN


IMPORTS
    MODULE-IDENTITY, OBJECT-TYPE, 
    NOTIFICATION-TYPE, Unsigned32, Integer32, Counter64        FROM SNMPv2-SMI
    MODULE-COMPLIANCE, OBJECT-GROUP, NOTIFICATION-GROUP        FROM SNMPv2-CONF
    TEXTUAL-CONVENTION, DisplayString,TimeStamp, TruthValue    FROM SNMPv2-TC
    ifIndex                                                    FROM IF-MIB
    InetAddressType,  InetAddress                              FROM INET-ADDRESS-MIB
    InfnLoopbackType, InfnServiceType                          FROM INFINERA-TC-MIB
    terminationPoint                                           FROM INFINERA-REG-MIB;


dchCtpMIB MODULE-IDENTITY
    LAST-UPDATED  "200802180000Z"
    ORGANIZATION "Infinera"
    CONTACT-INFO
        "Infinera
        1322 Bordeaux Drive
        Sunnyvale, CA - 94089

        Contact : Technical Support
        Email   : support@infinera.com
        Phone   : 1-877-INF-5288"
    DESCRIPTION
        " "
    ::= { terminationPoint 18 }


dchCtpTable  OBJECT-TYPE  
    SYNTAX SEQUENCE OF DchCtpEntry
    MAX-ACCESS not-accessible
    STATUS current
    DESCRIPTION 
        " A list of DchCtp entries. The number of entries is give by value of MOId."
::= { dchCtpMIB 1 } 


dchCtpEntry  OBJECT-TYPE  
    SYNTAX DchCtpEntry
    MAX-ACCESS not-accessible
    STATUS current
    DESCRIPTION 
        " A  DchCtp entry containing all the information
             pertaining to Infinera DchCtp."
    INDEX { ifIndex } 
::= { dchCtpTable 1 }



DchCtpEntry  ::= SEQUENCE { 
    dchCtpTribPrbsGenMode                  INTEGER,
    dchCtpTribPrbsMonMode                  INTEGER,
    dchCtpSupportingCircuitIdList          DisplayString,
    dchCtpLoopback                         INTEGER,
    dchCtpConfiguredServiceType            INTEGER,
    dchCtpExpectedDtsTTI                   DisplayString,
    dchCtpDtsTTIMismatchReporting          INTEGER,
    dchCtpTxDtsTTI                         DisplayString,
    dchCtpRxDtsTTI                         DisplayString,
    dchCtpPreFecThresholdOrder             Integer32,
    dchCtpDataPlaneTransparency            INTEGER,
    dchCtpSignalDegradeReportingControl    INTEGER,
    dchCtpDtsFecSupport                    INTEGER,
    dchCtpPreFecThresholdMantissa          Integer32,
    dchCtpDtsCv15MinutesTce                Counter64,
    dchCtpDtsEs15MinutesTce                Integer32,
    dchCtpDtsSes15MinutesTce               Integer32,
    dchCtpDtsCvDayTce                      Counter64,
    dchCtpDtsEsDayTce                      Integer32,
    dchCtpDtsSesDayTce                     Integer32,
    dchCtpDtsCv15MinutesTceReporting       TruthValue,
    dchCtpDtsEs15MinutesTceReporting       TruthValue,
    dchCtpDtsSes15MinutesTceReporting      TruthValue,
    dchCtpDtsCvDayTceReporting             TruthValue,
    dchCtpDtsEsDayTceReporting             TruthValue,
    dchCtpDtsSesDayTceReporting            TruthValue,
    dchCtpPmHistStatsEnable                INTEGER,
    dchCtpConnectivityVerification         INTEGER
}

dchCtpTribPrbsGenMode OBJECT-TYPE
    SYNTAX    INTEGER {
        disabled( 1),
        enabled( 2),
        unknown( 3)
        }
    MAX-ACCESS    read-write
    STATUS     current
    DESCRIPTION    "Flag which enables the generation of PRBS data on the transmit side."
::= { dchCtpEntry  1    }



dchCtpTribPrbsMonMode OBJECT-TYPE
    SYNTAX    INTEGER {
        disabled( 1),
        enabled( 2),
        unknown( 3)
        }
    MAX-ACCESS    read-write
    STATUS     current
    DESCRIPTION    "Flag which enables the monitoring of bit errors."
::= { dchCtpEntry  2    }



dchCtpSupportingCircuitIdList OBJECT-TYPE
    SYNTAX    DisplayString
    MAX-ACCESS    read-only
    STATUS     current
    DESCRIPTION    "An unordered list of the CircuitId's associated with DchCtp.
     This string contains the string representation of each supporting CircuitId,
      separated by a ' ' (space) if there is more than one."
::= { dchCtpEntry  3    }


dchCtpLoopback OBJECT-TYPE
    SYNTAX    InfnLoopbackType
    MAX-ACCESS    read-write
    STATUS     current
    DESCRIPTION    "Flag to enable the loopback."
::= { dchCtpEntry  4    }

dchCtpConfiguredServiceType OBJECT-TYPE
    SYNTAX  InfnServiceType
    MAX-ACCESS    read-only
    STATUS     current
    DESCRIPTION    "The configured service type."
::= { dchCtpEntry  5    }

dchCtpExpectedDtsTTI OBJECT-TYPE
    SYNTAX    DisplayString
    MAX-ACCESS    read-write
    STATUS     current
    DESCRIPTION    "The expected Dts trail trace  identifier."
::= { dchCtpEntry  6    }



dchCtpDtsTTIMismatchReporting OBJECT-TYPE
    SYNTAX    INTEGER {
        disabled( 1),
        enabled( 2)
        }
    MAX-ACCESS    read-write
    STATUS     current
    DESCRIPTION    "Flag that indicates if TTI alarm should be reported or not."
::= { dchCtpEntry  7    }



dchCtpTxDtsTTI OBJECT-TYPE
    SYNTAX    DisplayString
    MAX-ACCESS    read-write
    STATUS     current
    DESCRIPTION    "The transmitted Dts trail trace identifier."
::= { dchCtpEntry  8    }



dchCtpRxDtsTTI OBJECT-TYPE
    SYNTAX    DisplayString
    MAX-ACCESS    read-only
    STATUS     current
    DESCRIPTION    "The received Dts trail trace identifier."
::= { dchCtpEntry  9    }



dchCtpPreFecThresholdOrder OBJECT-TYPE
    SYNTAX    Integer32
    MAX-ACCESS    read-write
    STATUS     current
    DESCRIPTION    "Pre-FEC BER threshold. "
::= { dchCtpEntry  10    }



dchCtpDataPlaneTransparency OBJECT-TYPE
    SYNTAX    INTEGER {
        disabled( 1),
        enabled( 2),
        unknown( 3)
        }
    MAX-ACCESS    read-write
    STATUS     current
    DESCRIPTION    "This attribute captures whether or not the data traffic
     arriving via this DchCTP is transported transparently by the receiving 
     network element."
::= { dchCtpEntry  11    }



dchCtpSignalDegradeReportingControl OBJECT-TYPE
    SYNTAX    INTEGER {
        disabled( 1),
        enabled( 2),
        unknown( 3)
        }
    MAX-ACCESS    read-write
    STATUS     current
    DESCRIPTION    "Controls whether or not the signal degrade condition is reported."
::= { dchCtpEntry  12    }



dchCtpDtsFecSupport OBJECT-TYPE
    SYNTAX    INTEGER {
        disabled( 1),
        enabled( 2),
        unknown( 3)
        }
    MAX-ACCESS    read-write
    STATUS     current
    DESCRIPTION    "This attribute controls whether or not the High Gain 
    Infinera FEC is enabled for this DTS."
::= { dchCtpEntry  13    }



dchCtpPreFecThresholdMantissa OBJECT-TYPE
    SYNTAX    Integer32
    MAX-ACCESS    read-write
    STATUS     current
    DESCRIPTION    "The mantissa for the BER threshold used to declare PRE-FEC-BER-SD. 
    This parameter, together with the attribute preFecThreshold-Order, completely 
    specifies the BER threshold."
::= { dchCtpEntry  14    }



dchCtpDtsCv15MinutesTce OBJECT-TYPE
    SYNTAX    Counter64
    MAX-ACCESS    read-write
    STATUS     current
    DESCRIPTION    "Count of BIP errors detected at the DTF Path layer. Up to 8
     path BIP errors can be detected per frame, with each error incrementing 
     the DTFDLM- CV-S current register."
::= { dchCtpEntry  15    }



dchCtpDtsEs15MinutesTce OBJECT-TYPE
    SYNTAX    Integer32
    MAX-ACCESS    read-write
    STATUS     current
    DESCRIPTION    "Count of the number of seconds during which (at any point 
    during the second) at least one DTF Path layer BIP error was detected or 
    an AISP, DTPLOF or POST FEC SF BER defect was present."
::= { dchCtpEntry  16    }



dchCtpDtsSes15MinutesTce OBJECT-TYPE
    SYNTAX    Integer32
    MAX-ACCESS    read-write
    STATUS     current
    DESCRIPTION    "Count of the seconds during which K (= 2,400 as specified 
    in GR-253-CORE Issue 3 specification) or more DTF Path layer BIP errors were 
    detected or an AIS-P, DTPLOF or POST FEC SF BER defect was present."
::= { dchCtpEntry  17    }



dchCtpDtsCvDayTce OBJECT-TYPE
    SYNTAX    Counter64
    MAX-ACCESS    read-write
    STATUS     current
    DESCRIPTION    "Count of BIP errors detected at the DTF Path layer. Up to 
    8 path BIP errors can be detected per frame, with each error incrementing 
    the DTFDLM-CV-S current register."
::= { dchCtpEntry  18    }



dchCtpDtsEsDayTce OBJECT-TYPE
    SYNTAX    Integer32
    MAX-ACCESS    read-write
    STATUS     current
    DESCRIPTION    "Count of the number of seconds during which (at any point
     during the second) at least one DTF Path layer BIP error was detected or
      an AIS-P, DTPLOF or POST FEC SF BER defect was present."
::= { dchCtpEntry  19    }



dchCtpDtsSesDayTce OBJECT-TYPE
    SYNTAX    Integer32
    MAX-ACCESS    read-write
    STATUS     current
    DESCRIPTION    "Count of the seconds during which K (= 2,400 as specified
     in GR-253-CORE Issue 3 specification) or more DTF Path layer BIP errors 
     were detected or an AIS-P, DTP-LOF or POST FEC SF BER defect was present."
::= { dchCtpEntry  20    }



dchCtpDtsCv15MinutesTceReporting OBJECT-TYPE
    SYNTAX    TruthValue
    MAX-ACCESS    read-write
    STATUS     current
    DESCRIPTION    "Flag that enables the reporting of DtsCv15MinutesTce crossing."
::= { dchCtpEntry  21    }



dchCtpDtsEs15MinutesTceReporting OBJECT-TYPE
    SYNTAX    TruthValue
    MAX-ACCESS    read-write
    STATUS     current
    DESCRIPTION    "Flag that enables the reporting of DtsEs15MinutesTce crossing."
::= { dchCtpEntry  22    }



dchCtpDtsSes15MinutesTceReporting OBJECT-TYPE
    SYNTAX    TruthValue
    MAX-ACCESS    read-write
    STATUS     current
    DESCRIPTION    "Flag that enables the reporting of DtsSes15MinutesTce crossing."
::= { dchCtpEntry  23    }



dchCtpDtsCvDayTceReporting OBJECT-TYPE
    SYNTAX    TruthValue
    MAX-ACCESS    read-write
    STATUS     current
    DESCRIPTION    "Flag that enables the reporting of DtsCvDayTce crossing."
::= { dchCtpEntry  24    }



dchCtpDtsEsDayTceReporting OBJECT-TYPE
    SYNTAX    TruthValue
    MAX-ACCESS    read-write
    STATUS     current
    DESCRIPTION    "Flag that enables the reporting of DtsEsDayTce crossing."
::= { dchCtpEntry  25    }



dchCtpDtsSesDayTceReporting OBJECT-TYPE
    SYNTAX    TruthValue
    MAX-ACCESS    read-write
    STATUS     current
    DESCRIPTION    "Flag that enables the reporting of DtsSesDayTce crossing."
::= { dchCtpEntry  26    }

dchCtpPmHistStatsEnable OBJECT-TYPE
    SYNTAX  INTEGER {
        enabled(1),
        disabled(2)
    }
    MAX-ACCESS  read-write
    STATUS      current
    DESCRIPTION "This objects control the historical PM collection."
    DEFVAL      { enabled }
    ::= { dchCtpEntry  27 }
 
 dchCtpConnectivityVerification OBJECT-TYPE
    SYNTAX  INTEGER {
        disabled(1),
        enabled(2)        
    }
    MAX-ACCESS  read-write
    STATUS      current
    DESCRIPTION "This objects control the reporting of connectivity verification alarm."
    DEFVAL      { disabled }
    ::= { dchCtpEntry  28 }
          
-- Confirmance Statements 
    dchCtpConformance     OBJECT IDENTIFIER ::= { dchCtpMIB 3 } 
    dchCtpCompliances     OBJECT IDENTIFIER ::= { dchCtpConformance 1 } 
    dchCtpGroups     OBJECT IDENTIFIER ::= { dchCtpConformance 2 } 

dchCtpCompliance MODULE-COMPLIANCE
    STATUS current
    DESCRIPTION
        "Describes the requirements for conformance to the DCHCTP-MIB"
    MODULE
        MANDATORY-GROUPS {dchCtpGroup }
        ::= { dchCtpCompliances 1 }

dchCtpGroup OBJECT-GROUP
    OBJECTS { 
        dchCtpTribPrbsGenMode,
        dchCtpTribPrbsMonMode,
        dchCtpSupportingCircuitIdList,
        dchCtpLoopback,
        dchCtpConfiguredServiceType,
        dchCtpExpectedDtsTTI,
        dchCtpDtsTTIMismatchReporting,
        dchCtpTxDtsTTI,
        dchCtpRxDtsTTI,
        dchCtpPreFecThresholdOrder,
        dchCtpDataPlaneTransparency,
        dchCtpSignalDegradeReportingControl,
        dchCtpDtsFecSupport,
        dchCtpPreFecThresholdMantissa,
        dchCtpDtsCv15MinutesTce,
        dchCtpDtsEs15MinutesTce,
        dchCtpDtsSes15MinutesTce,
        dchCtpDtsCvDayTce,
        dchCtpDtsEsDayTce,
        dchCtpDtsSesDayTce,
        dchCtpDtsCv15MinutesTceReporting,
        dchCtpDtsEs15MinutesTceReporting,
        dchCtpDtsSes15MinutesTceReporting,
        dchCtpDtsCvDayTceReporting,
        dchCtpDtsEsDayTceReporting,
        dchCtpDtsSesDayTceReporting,
        dchCtpPmHistStatsEnable,
        dchCtpConnectivityVerification
     } 
    STATUS current
    DESCRIPTION
        " A collection of objects for managing the dchCtp"
::= { dchCtpGroups 1 }



END

-- *****************************************************************
-- INFINERA-TP-DLMOCGPTP-MIB
-- 
-- October 2008, Sharfuddin Syed / Narendra Gupta
-- 
-- 
-- Copyright (c) 2008-2012 by Infinera Inc.
-- All rights reserved.
-- ****************************************************************

INFINERA-TP-DLMOCGPTP-MIB DEFINITIONS ::= BEGIN

IMPORTS
    MODULE-IDENTITY, OBJECT-TYPE                FROM SNMPv2-SMI
    MODULE-COMPLIANCE, OBJECT-GROUP             FROM SNMPv2-CONF
    DisplayString, TruthValue                   FROM SNMPv2-TC
    ifIndex                                     FROM IF-MIB
    FloatTenths, InfnAutoDiscoveryState,
	InfnPmHistStatsControl,
	InfnOperationalState, InfnLineSystemMode    FROM INFINERA-TC-MIB
    terminationPoint                            FROM INFINERA-REG-MIB;


dlmOcgPtpMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 6 }

dlmOcgPtpTable OBJECT-TYPE
    SYNTAX      SEQUENCE OF DlmOcgPtpEntry
    MAX-ACCESS  not-accessible
    STATUS      current
    DESCRIPTION
        "A list of DlmOcgPtp entries. Each entry is uniquely identified by the value of ifIndex."
    ::= { dlmOcgPtpMIB 1 } 

dlmOcgPtpEntry  OBJECT-TYPE
    SYNTAX      DlmOcgPtpEntry
    MAX-ACCESS  not-accessible
    STATUS      current
    DESCRIPTION
        "A DlmOcgPtp entry containing information pertaining to Infinera DlmOcgPtp Interfaces.
        This table is a subclass of IfCommon. Entries will exist in this table only for
        interfaces of type DLM OCG PTP."
    INDEX { ifIndex }
    ::= { dlmOcgPtpTable 1 }


DlmOcgPtpEntry  ::= SEQUENCE {
    dlmOcgPtpDiscoveredRemoteTP      	DisplayString,
    dlmOcgPtpAutoDiscoveryState      	InfnAutoDiscoveryState,
    dlmOcgPtpPmHistStatsEnable       	InfnPmHistStatsControl,
    dlmOcgPtpIsBorderOCG             	TruthValue,
    dlmOcgPtpOcgPowerControlLoop     	InfnOperationalState,
    dlmOcgPtpProvisionedOcgTP      	 	DisplayString,
    dlmOcgPtpDiscoveredOcgTP      	 	DisplayString,
    dlmOcgPtpLineSystemMode          	InfnLineSystemMode,
    dlmOcgPtpProvisionedPeerTP       	DisplayString,
    dlmOcgPtpOpenwaveTargetTxOcgPower   FloatTenths,
    dlmOcgPtpChannelCount            	FloatTenths,
	dlmOcgPtpAggregateRate			 	FloatTenths
}

dlmOcgPtpDiscoveredRemoteTP OBJECT-TYPE
    SYNTAX      DisplayString
    MAX-ACCESS  read-only
    STATUS      current
    DESCRIPTION
        "This refers to the name of the BMM OCG PTP to which this fiber is connected."
    ::= { dlmOcgPtpEntry  1 }


dlmOcgPtpAutoDiscoveryState OBJECT-TYPE
    SYNTAX		InfnAutoDiscoveryState  
    MAX-ACCESS  read-only
    STATUS      current
    DESCRIPTION
        "State of the auto discovery. Completed indicates that the exchange of ID with corresponding
        BMM was successful. It does not tell whether there is a mismatch or not."
    DEFVAL      { notValid }
    ::= { dlmOcgPtpEntry  2 }


dlmOcgPtpPmHistStatsEnable OBJECT-TYPE
    SYNTAX  	InfnPmHistStatsControl 
    MAX-ACCESS  read-write
    STATUS      obsolete
    DESCRIPTION "Flag to enable or disable PM collection."
    DEFVAL      { enabled }
    ::= { dlmOcgPtpEntry  3 }


dlmOcgPtpIsBorderOCG OBJECT-TYPE
    SYNTAX      TruthValue
    MAX-ACCESS  read-write
    STATUS      obsolete
    DESCRIPTION "Field that indicates if the OCG exists at the border of two 
    GMPLS domains, and is thus eligible for selection of Line-side DTPCTP 
    endpoints for circuit termination."
    DEFVAL      { false }
    ::= { dlmOcgPtpEntry  4 }


dlmOcgPtpOcgPowerControlLoop OBJECT-TYPE
    SYNTAX 		InfnOperationalState 
    MAX-ACCESS  read-write
    STATUS      current
    DESCRIPTION "Parameter that indicates whether OCG Control Loop is enabled or disabled."
    DEFVAL      { enabled }
    ::= { dlmOcgPtpEntry  5 }

dlmOcgPtpProvisionedOcgTP  OBJECT-TYPE
    SYNTAX      DisplayString
    MAX-ACCESS  read-write
    STATUS      current
    DESCRIPTION
        "Provisioned OCG TP."
    ::= { dlmOcgPtpEntry  6 }

dlmOcgPtpDiscoveredOcgTP  OBJECT-TYPE
    SYNTAX      DisplayString
    MAX-ACCESS  read-only
    STATUS      current
    DESCRIPTION
        "DisplayString OCG TP"
    ::= { dlmOcgPtpEntry  7 }

dlmOcgPtpLineSystemMode OBJECT-TYPE
    SYNTAX  	InfnLineSystemMode
    MAX-ACCESS  read-write
    STATUS      current
    DESCRIPTION "Line System Mode"
    DEFVAL      { modeOcg }
    ::= { dlmOcgPtpEntry  8 }

dlmOcgPtpProvisionedPeerTP  OBJECT-TYPE
    SYNTAX      DisplayString
    MAX-ACCESS  read-write
    STATUS      current
    DESCRIPTION
        "Provisioned Peer TP"
    ::= { dlmOcgPtpEntry  9 }

dlmOcgPtpOpenwaveTargetTxOcgPower OBJECT-TYPE
    SYNTAX      FloatTenths
    MAX-ACCESS  read-write
    STATUS      current
    DESCRIPTION
        "Target Tx OCG Power"
    DEFVAL      { 50 }
    ::= { dlmOcgPtpEntry  10 }

dlmOcgPtpChannelCount OBJECT-TYPE
    SYNTAX      FloatTenths
    MAX-ACCESS  read-write
    STATUS      current
    DESCRIPTION
        "Channel Count"
    DEFVAL      { 100 }
    ::= { dlmOcgPtpEntry  11 }

dlmOcgPtpAggregateRate	OBJECT-TYPE
    SYNTAX      FloatTenths
    MAX-ACCESS  read-only
    STATUS      current
    DESCRIPTION
        "Aggregate Rate"
    DEFVAL      { 500 }
    ::= { dlmOcgPtpEntry  12 }

-- Conformance Statements
dlmOcgPtpConformance    OBJECT IDENTIFIER ::= { dlmOcgPtpMIB 3 }
dlmOcgPtpCompliances    OBJECT IDENTIFIER ::= { dlmOcgPtpConformance 1 }
dlmOcgPtpGroups         OBJECT IDENTIFIER ::= { dlmOcgPtpConformance 2 }

dlmOcgPtpCompliance MODULE-COMPLIANCE
    STATUS current
    DESCRIPTION
    "Describes the requirements for conformance to the DLMOCGPTP-MIB"
    MODULE
        MANDATORY-GROUPS { dlmOcgPtpGroup }
    ::= { dlmOcgPtpCompliances 1 }

dlmOcgPtpGroup OBJECT-GROUP
    OBJECTS {
        dlmOcgPtpDiscoveredRemoteTP,
        dlmOcgPtpAutoDiscoveryState,
        dlmOcgPtpPmHistStatsEnable,
        dlmOcgPtpIsBorderOCG,
        dlmOcgPtpOcgPowerControlLoop,
        dlmOcgPtpProvisionedOcgTP,
        dlmOcgPtpDiscoveredOcgTP,
        dlmOcgPtpLineSystemMode,
        dlmOcgPtpProvisionedPeerTP,
        dlmOcgPtpOpenwaveTargetTxOcgPower,
        dlmOcgPtpChannelCount,
		dlmOcgPtpAggregateRate
    }
    STATUS current
    DESCRIPTION
        " A collection of objects for managing the dlmOcgPtp"
    ::= { dlmOcgPtpGroups 1 }


END

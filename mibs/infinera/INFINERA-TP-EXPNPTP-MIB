-- *****************************************************************
-- INFINERA-TP-EXPNPTP-MIB
-- Copyright (c) 2008-2012 by Infinera Inc
-- All rights reserved.
-- ****************************************************************

INFINERA-TP-EXPNPTP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths,InfnExpnPtpMode             FROM INFINERA-TC-MIB
    terminationPoint                            FROM INFINERA-REG-MIB;

expnPtpMIB MODULE-IDENTITY
    LAST-UPDATED  "201702020000Z"
    ORGANIZATION  "Infinera"
    CONTACT-INFO
        "Infinera
        1322 Bordeaux Drive
        Sunnyvale, CA - 94089
        Contact : Technical Support
        Email   : support@infinera.com
        Phone   : 1-877-INF-5288"
    DESCRIPTION
        " "
    REVISION  "201702020000Z"
    DESCRIPTION
        "First Version"
    ::= { terminationPoint 82 }

expnPtpTable OBJECT-TYPE
    SYNTAX      SEQUENCE OF ExpnPtpEntry
    MAX-ACCESS  not-accessible
    STATUS      current
    DESCRIPTION
        "A list of ExpnPtp entries. Each entry is uniquely identified by the value of ifIndex."
    ::= { expnPtpMIB 1 }

expnPtpEntry  OBJECT-TYPE
    SYNTAX      ExpnPtpEntry
    MAX-ACCESS  not-accessible
    STATUS      current
    DESCRIPTION
        "A ExpnPtp entry containing information pertaining to Infinera ExpnPtp Interfaces.
        This table is a subclass of IfCommon. Entries will exist in this table only for
        interfaces of type DLM OCG PTP."
    INDEX { ifIndex }
    ::= { expnPtpTable 1 }


ExpnPtpEntry  ::= SEQUENCE {
    expnPtpMoId                     DisplayString,
    expnPtpExpectedNeighborPtp      DisplayString,
    expnPtpMode                     InfnExpnPtpMode
}

expnPtpMoId    OBJECT-TYPE
    SYNTAX      DisplayString
    MAX-ACCESS  read-only
    STATUS      current
    DESCRIPTION ""
    ::= { expnPtpEntry 1 }

expnPtpExpectedNeighborPtp  OBJECT-TYPE
    SYNTAX      DisplayString
    MAX-ACCESS  read-only
    STATUS      current
    DESCRIPTION ""
    ::= { expnPtpEntry 2 }

expnPtpMode     OBJECT-TYPE
    SYNTAX      InfnExpnPtpMode
    MAX-ACCESS  read-write
    STATUS      current
    DESCRIPTION ""
    ::= { expnPtpEntry 3 }

-- Conformance Statements
expnPtpConformance    OBJECT IDENTIFIER ::= { expnPtpMIB 3 }
expnPtpCompliances    OBJECT IDENTIFIER ::= { expnPtpConformance 1 }
expnPtpGroups         OBJECT IDENTIFIER ::= { expnPtpConformance 2 }

expnPtpCompliance MODULE-COMPLIANCE
    STATUS current
    DESCRIPTION
    "Describes the requirements for conformance to the EXPNPTP-MIB"
    MODULE
        MANDATORY-GROUPS { expnPtpGroup }
    ::= { expnPtpCompliances 1 }

expnPtpGroup OBJECT-GROUP
    OBJECTS {
        expnPtpMoId,
        expnPtpExpectedNeighborPtp,
        expnPtpMode
}
    STATUS current
    DESCRIPTION
        " A collection of objects for managing the expnPtp"
    ::= { expnPtpGroups 1 }
END

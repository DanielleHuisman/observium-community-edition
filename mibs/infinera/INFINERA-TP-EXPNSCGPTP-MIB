-- *****************************************************************
-- INFINERA-TP-EXPNSCGPTP-MIB
-- Copyright (c) 2008-2013 by Infinera Inc
-- All rights reserved.
-- ****************************************************************

INFINERA-TP-EXPNSCGPTP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths, InfnEnableDisable          FROM INFINERA-TC-MIB
    terminationPoint                            FROM INFINERA-REG-MIB;

expnScgPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 47 }

expnScgPtpTable OBJECT-TYPE
    SYNTAX      SEQUENCE OF ExpnScgPtpEntry
    MAX-ACCESS  not-accessible
    STATUS      current
    DESCRIPTION
        "A list of ExpnScgPtp entries. Each entry is uniquely identified by the value of ifIndex."
    ::= { expnScgPtpMIB 1 } 

expnScgPtpEntry  OBJECT-TYPE
    SYNTAX      ExpnScgPtpEntry
    MAX-ACCESS  not-accessible
    STATUS      current
    DESCRIPTION
        "A expnScgPtp entry containing information pertaining to Infinera expnScgPtp Interfaces.
        This table is a subclass of IfCommon. Entries will exist in this table only for
        interfaces of type DLM OCG PTP."
    INDEX { ifIndex }
    ::= { expnScgPtpTable 1 }


ExpnScgPtpEntry  ::= SEQUENCE {
    expnScgPtpScgNumber                    Integer32,
    expnScgPtpMPOAID                       DisplayString,
    expnScgPtpPathLossCheckControlStatus        INTEGER,
    expnScgPtpLastSuccessfullPathLossCheckTS    Integer32,
    expnScgPtpPathLoss                          FloatHundredths,
    expnScgPtpPathLossCheckDetectedPort         DisplayString,
    expnScgPtpLastPathLossCheckAttemptTS        Integer32,
    expnScgPtpLastPathLossCheckAttemptStatus    INTEGER,
    expnScgPtpLastPathLossCheckFailedReason     INTEGER,
    expnScgPtpPathLossHigh                      INTEGER

}

expnScgPtpScgNumber    OBJECT-TYPE
    SYNTAX      Integer32 
    MAX-ACCESS  read-only
    STATUS      current
    DESCRIPTION ""
    ::= { expnScgPtpEntry  1 }


expnScgPtpMPOAID OBJECT-TYPE
    SYNTAX      DisplayString
    MAX-ACCESS  read-write
    STATUS      current
    DESCRIPTION ""
    ::= { expnScgPtpEntry  2 }

expnScgPtpPathLossCheckControlStatus OBJECT-TYPE
    SYNTAX      INTEGER {
        inProgress(1),
        idle(2)
    }
    MAX-ACCESS  read-only
    STATUS      current
    DESCRIPTION ""
    ::= { expnScgPtpEntry 3 }

expnScgPtpLastSuccessfullPathLossCheckTS OBJECT-TYPE
    SYNTAX      Integer32
    MAX-ACCESS  read-only
    STATUS      current
    DESCRIPTION ""
    ::= { expnScgPtpEntry 4 }

expnScgPtpPathLoss OBJECT-TYPE
    SYNTAX      FloatHundredths
    MAX-ACCESS  read-only
    STATUS      current
    DESCRIPTION ""
    ::= { expnScgPtpEntry 5 }

expnScgPtpPathLossCheckDetectedPort OBJECT-TYPE
    SYNTAX      DisplayString
    MAX-ACCESS  read-only
    STATUS      current
    DESCRIPTION ""
    ::= { expnScgPtpEntry 6 }

expnScgPtpLastPathLossCheckAttemptTS OBJECT-TYPE
    SYNTAX      Integer32
    MAX-ACCESS  read-only
    STATUS      current
    DESCRIPTION ""
    ::= { expnScgPtpEntry 7 }

expnScgPtpLastPathLossCheckAttemptStatus OBJECT-TYPE
    SYNTAX      INTEGER {
        successfull (1),
        unsuccessfull(2),
        notAttempted(3)
    }
    MAX-ACCESS  read-only
    STATUS      current
    DESCRIPTION ""
    ::= { expnScgPtpEntry 8 }

expnScgPtpLastPathLossCheckFailedReason OBJECT-TYPE
    SYNTAX      INTEGER {
        na (1),
        timedOut(2),
        interruptedbyAD(3),
        interruptedbyReset(4),
        portInService(5)
    }
    MAX-ACCESS  read-only
    STATUS      current
    DESCRIPTION ""
    ::= { expnScgPtpEntry 9 }

expnScgPtpPathLossHigh OBJECT-TYPE
    SYNTAX      INTEGER {
        true(1),
        false(2)
    }
    MAX-ACCESS  read-only
    STATUS      current
    DESCRIPTION ""
    ::= { expnScgPtpEntry 10 }

-- Conformance Statements
expnScgPtpConformance    OBJECT IDENTIFIER ::= { expnScgPtpMIB 3 }
expnScgPtpCompliances    OBJECT IDENTIFIER ::= { expnScgPtpConformance 1 }
expnScgPtpGroups         OBJECT IDENTIFIER ::= { expnScgPtpConformance 2 }

expnScgPtpCompliance MODULE-COMPLIANCE
    STATUS current
    DESCRIPTION
    "Describes the requirements for conformance to the EXPNSCGPTP-MIB"
    MODULE
        MANDATORY-GROUPS { expnScgPtpGroup }
    ::= { expnScgPtpCompliances 1 }

expnScgPtpGroup OBJECT-GROUP
    OBJECTS {
        expnScgPtpScgNumber,        
        expnScgPtpMPOAID,
        expnScgPtpPathLossCheckControlStatus   , 
        expnScgPtpLastSuccessfullPathLossCheckTS,
        expnScgPtpPathLoss                      ,
        expnScgPtpPathLossCheckDetectedPort     ,
        expnScgPtpLastPathLossCheckAttemptTS    ,
        expnScgPtpLastPathLossCheckAttemptStatus,
        expnScgPtpLastPathLossCheckFailedReason ,
        expnScgPtpPathLossHigh

    }
    STATUS current
    DESCRIPTION
        " A collection of objects for managing the expnScgPtp"
    ::= { expnScgPtpGroups 1 }
END

-- *****************************************************************
-- INFINERA-TP-FBMSCGPTP-MIB
-- Copyright (c) 2008-2017 by Infinera Inc
-- All rights reserved.
-- ****************************************************************

INFINERA-TP-FBMSCGPTP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths, InfnEnableDisableType,
    InfnEqptType, FloatArbitraryPrecision,
	InfnAdTpType,InfnPmHistStatsControl,
	InfnWaveInterfaceType,
    InfnLineOperatingMode,
    InfnPathLossCheckControlStatus,
    InfnLastPathLossCheckAttemptStatus,
    InfnLastPathLossCheckFailedReason           FROM INFINERA-TC-MIB
    terminationPoint                            FROM INFINERA-REG-MIB;

fbmScgPtpMIB MODULE-IDENTITY
    LAST-UPDATED  "201601230000Z"
    ORGANIZATION  "Infinera"
    CONTACT-INFO
        "Infinera
        1322 Bordeaux Drive
        Sunnyvale, CA - 94089
        Contact : Technical Support
        Email   : support@infinera.com
        Phone   : 1-877-INF-5288"
    DESCRIPTION
        " "
    REVISION  "201601230000Z"
    DESCRIPTION
        "First Version"
    ::= { terminationPoint 81 }

fbmScgPtpTable OBJECT-TYPE
    SYNTAX      SEQUENCE OF FbmScgPtpEntry
    MAX-ACCESS  not-accessible
    STATUS      current
    DESCRIPTION
        "A list of FmmCScgPtp entries. Each entry is uniquely identified by the value of ifIndex."
    ::= { fbmScgPtpMIB 1 }

fbmScgPtpEntry  OBJECT-TYPE
    SYNTAX      FbmScgPtpEntry
    MAX-ACCESS  not-accessible
    STATUS      current
    DESCRIPTION
        "A FbmScgPtp entry containing information pertaining to Infinera FbmScgPtp Interfaces.
        This table is a subclass of IfCommon. Entries will exist in this table only for
        interfaces of type SCG PTP."
    INDEX { ifIndex }
    ::= { fbmScgPtpTable 1 }


FbmScgPtpEntry  ::= SEQUENCE {
    fbmScgPtpMoId                           DisplayString,
    fbmScgPtpScgNumber                      Integer32,
    fbmScgPtpScgSupEqptType                 InfnEqptType,
	fbmScgPtpMPOAID                         DisplayString,
	fbmScgPtpProvisionedFPMPO               DisplayString,
    fbmScgPtpDiscoveredNeighborTP           DisplayString,
    fbmScgPtpProvisionedNeighborTP          DisplayString,
    fbmScgPtpProvisionedNeighborAdTpType    InfnAdTpType,
    fbmScgPtpInterfaceType                  InfnWaveInterfaceType,
	fbmScgPtpProvisionedOpenWaveRemotePtp   DisplayString,
    fbmScgPtpPmHistStatsEnable              InfnPmHistStatsControl,
    fbmScgPtpUsedFreqSlotList               DisplayString,
    fbmScgPtpAvailableFreqSlotList          DisplayString,
    fbmScgPtpLineOperatingMode              InfnLineOperatingMode,
    fbmScgPtpPathLossCheckControlStatus     InfnPathLossCheckControlStatus,
    fbmScgPtpLastSuccessfullPathLossCheckTS Integer32,
    fbmScgPtpPathLoss                       FloatArbitraryPrecision,
    fbmScgPtpPathLossCheckDetectedPort      DisplayString,
    fbmScgPtpLastPathLossCheckAttemptTS     Integer32,
    fbmScgPtpLastPathLossCheckAttemptStatus InfnLastPathLossCheckAttemptStatus,
    fbmScgPtpLastPathLossCheckFailedReason  InfnLastPathLossCheckFailedReason
}

fbmScgPtpMoId   OBJECT-TYPE
    SYNTAX      DisplayString
    MAX-ACCESS  read-write
    STATUS      current
    DESCRIPTION ""
    ::= { fbmScgPtpEntry 1 }

fbmScgPtpScgNumber OBJECT-TYPE
    SYNTAX      Integer32
    MAX-ACCESS  read-only
    STATUS      current
    DESCRIPTION ""
    ::= { fbmScgPtpEntry 2 }

fbmScgPtpScgSupEqptType OBJECT-TYPE
    SYNTAX      InfnEqptType
    MAX-ACCESS  read-write
    STATUS      current
    DESCRIPTION ""
    ::= { fbmScgPtpEntry 3 }

fbmScgPtpMPOAID OBJECT-TYPE
    SYNTAX      DisplayString
    MAX-ACCESS  read-write
    STATUS      current
    DESCRIPTION ""
    ::= { fbmScgPtpEntry 4 }

fbmScgPtpProvisionedFPMPO  OBJECT-TYPE
    SYNTAX      DisplayString
    MAX-ACCESS  read-write
    STATUS      current
    DESCRIPTION ""
    ::= { fbmScgPtpEntry 5 }

fbmScgPtpDiscoveredNeighborTP OBJECT-TYPE
    SYNTAX      DisplayString
    MAX-ACCESS  read-only
    STATUS      current
    DESCRIPTION ""
    ::= { fbmScgPtpEntry 6 }

fbmScgPtpProvisionedNeighborTP OBJECT-TYPE
    SYNTAX      DisplayString
    MAX-ACCESS  read-only
    STATUS      current
    DESCRIPTION ""
    ::= { fbmScgPtpEntry 7 }

fbmScgPtpProvisionedNeighborAdTpType OBJECT-TYPE
    SYNTAX      InfnAdTpType
    MAX-ACCESS  read-only
    STATUS      current
    DESCRIPTION ""
    ::= { fbmScgPtpEntry 8 }

fbmScgPtpInterfaceType OBJECT-TYPE
    SYNTAX      InfnWaveInterfaceType
    MAX-ACCESS  read-write
    STATUS      current
    DESCRIPTION ""
    ::= { fbmScgPtpEntry 9 }

fbmScgPtpProvisionedOpenWaveRemotePtp OBJECT-TYPE
    SYNTAX          DisplayString
    MAX-ACCESS      read-write
    STATUS          current
    DESCRIPTION     ""
    ::= { fbmScgPtpEntry 10 }

fbmScgPtpPmHistStatsEnable OBJECT-TYPE
    SYNTAX          InfnPmHistStatsControl
    MAX-ACCESS      read-write
    STATUS          current
    DESCRIPTION     ""
    ::= { fbmScgPtpEntry 11 }

fbmScgPtpUsedFreqSlotList OBJECT-TYPE
    SYNTAX      DisplayString
    MAX-ACCESS  read-only
    STATUS      current
    DESCRIPTION ""
    ::= { fbmScgPtpEntry 12 }

fbmScgPtpAvailableFreqSlotList  OBJECT-TYPE
    SYNTAX      DisplayString
    MAX-ACCESS  read-only
    STATUS      current
    DESCRIPTION ""
    ::= { fbmScgPtpEntry 13 }

fbmScgPtpLineOperatingMode  OBJECT-TYPE
    SYNTAX      InfnLineOperatingMode
    MAX-ACCESS  read-write
    STATUS      current
    DESCRIPTION ""
    ::= { fbmScgPtpEntry 14 }

fbmScgPtpPathLossCheckControlStatus OBJECT-TYPE
    SYNTAX      InfnPathLossCheckControlStatus
    MAX-ACCESS  read-only
    STATUS      current
    DESCRIPTION ""
    ::= { fbmScgPtpEntry 15 }

fbmScgPtpLastSuccessfullPathLossCheckTS OBJECT-TYPE
    SYNTAX      Integer32
    MAX-ACCESS  read-only
    STATUS      current
    DESCRIPTION ""
    ::= { fbmScgPtpEntry 16 }

fbmScgPtpPathLoss OBJECT-TYPE
    SYNTAX      FloatArbitraryPrecision
    MAX-ACCESS  read-only
    STATUS      current
    DESCRIPTION ""
    ::= { fbmScgPtpEntry 17 }

fbmScgPtpPathLossCheckDetectedPort OBJECT-TYPE
    SYNTAX      DisplayString
    MAX-ACCESS  read-only
    STATUS      current
    DESCRIPTION ""
    ::= { fbmScgPtpEntry 18 }

fbmScgPtpLastPathLossCheckAttemptTS OBJECT-TYPE
    SYNTAX      Integer32
    MAX-ACCESS  read-only
    STATUS      current
    DESCRIPTION ""
    ::= { fbmScgPtpEntry 19 }

fbmScgPtpLastPathLossCheckAttemptStatus OBJECT-TYPE
    SYNTAX      InfnLastPathLossCheckAttemptStatus
    MAX-ACCESS  read-only
    STATUS      current
    DESCRIPTION ""
    ::= { fbmScgPtpEntry 20 }

fbmScgPtpLastPathLossCheckFailedReason OBJECT-TYPE
    SYNTAX      InfnLastPathLossCheckFailedReason
    MAX-ACCESS  read-only
    STATUS      current
    DESCRIPTION ""
    ::= { fbmScgPtpEntry 21 }

-- Conformance Statements
fbmScgPtpConformance    OBJECT IDENTIFIER ::= { fbmScgPtpMIB 3 }
fbmScgPtpCompliances    OBJECT IDENTIFIER ::= { fbmScgPtpConformance 1 }
fbmScgPtpGroups         OBJECT IDENTIFIER ::= { fbmScgPtpConformance 2 }

fbmScgPtpCompliance MODULE-COMPLIANCE
    STATUS current
    DESCRIPTION
    "Describes the requirements for conformance to the FBMSCGPTP-MIB"
    MODULE
        MANDATORY-GROUPS { fbmScgPtpGroup }
    ::= { fbmScgPtpCompliances 1 }

fbmScgPtpGroup OBJECT-GROUP
    OBJECTS {
	fbmScgPtpMoId,
        fbmScgPtpScgNumber,
        fbmScgPtpScgSupEqptType,
		fbmScgPtpMPOAID,
		fbmScgPtpProvisionedFPMPO,
        fbmScgPtpDiscoveredNeighborTP,
        fbmScgPtpInterfaceType,
        fbmScgPtpProvisionedNeighborTP,
        fbmScgPtpProvisionedNeighborAdTpType,
		fbmScgPtpProvisionedOpenWaveRemotePtp,
        fbmScgPtpPmHistStatsEnable,
        fbmScgPtpUsedFreqSlotList,
		fbmScgPtpAvailableFreqSlotList,
        fbmScgPtpLineOperatingMode,
        fbmScgPtpPathLossCheckControlStatus,
        fbmScgPtpLastSuccessfullPathLossCheckTS,
        fbmScgPtpPathLoss,
        fbmScgPtpPathLossCheckDetectedPort,
        fbmScgPtpLastPathLossCheckAttemptTS,
        fbmScgPtpLastPathLossCheckAttemptStatus,
        fbmScgPtpLastPathLossCheckFailedReason
    }
    STATUS current
    DESCRIPTION
        " A collection of objects for managing the fbmScgPtp"
    ::= { fbmScgPtpGroups 1 }

END

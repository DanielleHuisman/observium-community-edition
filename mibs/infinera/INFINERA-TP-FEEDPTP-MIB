-- *****************************************************************
-- INFINERA-TP-FEEDPTP-MIB
-- ****************************************************************

INFINERA-TP-FEEDPTP-MIB DEFINITIONS ::= BEGIN

IMPORTS
    MODULE-IDENTITY, OBJECT-TYPE, Integer32     FROM SNMPv2-SMI
    MODULE-COMPLIANCE, OBJECT-GROUP             FROM SNMPv2-CONF
    DisplayString                               FROM SNMPv2-TC
    ifIndex                                     FROM IF-MIB
    terminationPoint                            FROM INFINERA-REG-MIB;

feedPtpMIB MODULE-IDENTITY
    LAST-UPDATED  "200810200000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "

    REVISION  "200810200000Z"
    DESCRIPTION 
        " "
::= { terminationPoint 52 }


feedPtpConformance   OBJECT IDENTIFIER ::= { feedPtpMIB 3 }
feedPtpCompliances   OBJECT IDENTIFIER ::= { feedPtpConformance 1 }
feedPtpGroups        OBJECT IDENTIFIER ::= { feedPtpConformance 2 }

feedPtpTable  OBJECT-TYPE
    SYNTAX SEQUENCE OF FeedPtpEntry
    MAX-ACCESS not-accessible
    STATUS     current
    DESCRIPTION 
        "A list of FeedPtp entries. Each entry is uniquely identified by
                the value of ifIndex."
    ::= { feedPtpMIB 1 }

feedPtpEntry  OBJECT-TYPE
    SYNTAX     FeedPtpEntry
    MAX-ACCESS not-accessible
    STATUS     current
    DESCRIPTION 
        "A FeedPtp entry containing information pertaining to
                Infinera FeedPtp interfaces. . This table is a subclass of IfCommon.
                Entries will exist in this table only for interfaces of type FeedPtp."
    INDEX { ifIndex }
    ::= { feedPtpTable 1 }

FeedPtpEntry  ::= SEQUENCE { 
    feedPtpPmHistStatsEnable   INTEGER
}

feedPtpPmHistStatsEnable    OBJECT-TYPE
    SYNTAX      INTEGER { 
        enabled(1),
        disabled(2)
    }
    MAX-ACCESS  read-only
    STATUS      current
    DESCRIPTION ""
    ::= { feedPtpEntry 1 } 


feedPtpCompliance  MODULE-COMPLIANCE
    STATUS     current
    DESCRIPTION 
        "Describes the requirements for conformance to the FEEDPTP-MIB"
    MODULE
        MANDATORY-GROUPS { feedPtpGroup } 
    ::= { feedPtpCompliances 1 }

feedPtpGroup  OBJECT-GROUP
    OBJECTS { 
        feedPtpPmHistStatsEnable
        }
    STATUS     current
    DESCRIPTION 
        " A collection of objects for managing feedPtp interfaces."
    ::= { feedPtpGroups 1 }
END

-- This MIB was created using NuDesign Team's Visual MIBuilder (Ver 4.7).

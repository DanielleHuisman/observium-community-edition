-- ***************************************************************
-- INFINERA-TP-FLEXCARRIERCTP-MIB
--   
-- Copyright (c) 2008-2012 by Infinera Inc.
-- All rights reserved.
-- ****************************************************************

INFINERA-TP-FLEXCARRIERCTP-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    ifIndex                             FROM IF-MIB
    terminationPoint                    FROM INFINERA-REG-MIB
    FloatHundredths,FloatTenths,  
	InfnPmHistStatsControl,InfnModulation FROM INFINERA-TC-MIB;

flexCarrierCtpMIB MODULE-IDENTITY
    LAST-UPDATED  "201506170000Z"
    ORGANIZATION 
        "INFINERA"
    CONTACT-INFO 
        "Infinera
        169 Java Drive
        Sunnyvale, CA - 94089
        
        Contact : Technical Support
        Email   : support@infinera.com 
        Phone   : 1-877-INF-5288"
    DESCRIPTION 
        "This MIB is modeling for FLEXCARRIERCTP terminationPoint table."
        
::= { terminationPoint 59 }

flexCarrierCtpTable  OBJECT-TYPE
    SYNTAX SEQUENCE OF FlexCarrierCtpEntry
    MAX-ACCESS not-accessible
    STATUS     current
    DESCRIPTION 
        "This table contains all FLEXCARRIERCTP modules that are currently present in a network element."
    ::= { flexCarrierCtpMIB 1 }

flexCarrierCtpEntry  OBJECT-TYPE
    SYNTAX     FlexCarrierCtpEntry
    MAX-ACCESS not-accessible
    STATUS     current
    DESCRIPTION 
        "A row in the FLEXCARRIERCTP table. Each row in the table is identified with a unique entPhysicalIndexID. 
        "
    INDEX { ifIndex }
    ::= { flexCarrierCtpTable 1 }

FlexCarrierCtpEntry ::= SEQUENCE {
      flexCarrierCtpPmHistStatsEnable      InfnPmHistStatsControl,
      flexCarrierCtpFreqSlotList           DisplayString
 }

flexCarrierCtpPmHistStatsEnable OBJECT-TYPE
    SYNTAX 		 InfnPmHistStatsControl 
    MAX-ACCESS  read-write
    STATUS      current
    DESCRIPTION "Flag to enable or disable PM collection."
    ::= { flexCarrierCtpEntry 1 }
    
flexCarrierCtpFreqSlotList OBJECT-TYPE
    SYNTAX 		DisplayString 
    MAX-ACCESS  read-write
    STATUS      current
    DESCRIPTION "Specifies carrier frequency slots"
    ::= { flexCarrierCtpEntry 2 }

-- Conformance Statements
flexCarrierCtpConformance    OBJECT IDENTIFIER ::= { flexCarrierCtpMIB 59 }
flexCarrierCtpCompliances    OBJECT IDENTIFIER ::= { flexCarrierCtpConformance 1 }
flexCarrierCtpGroups         OBJECT IDENTIFIER ::= { flexCarrierCtpConformance 2 }

flexCarrierCtpCompliance  MODULE-COMPLIANCE
    STATUS      current
    DESCRIPTION ""
    MODULE
        MANDATORY-GROUPS { flexCarrierCtpGroup } 
    ::= { flexCarrierCtpCompliances 1 }

flexCarrierCtpGroup  OBJECT-GROUP
    OBJECTS {       
    flexCarrierCtpPmHistStatsEnable,
    flexCarrierCtpFreqSlotList
    }
    STATUS      current
    DESCRIPTION ""
    ::= { flexCarrierCtpGroups 1 }
END

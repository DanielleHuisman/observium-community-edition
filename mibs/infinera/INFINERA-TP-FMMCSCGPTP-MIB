-- *****************************************************************
-- INFINERA-TP-FMMCSCGPTP-MIB
-- Copyright (c) 2008-2015 by Infinera Inc
-- All rights reserved.
-- ****************************************************************

INFINERA-TP-FMMCSCGPTP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths, InfnEnableDisable,
    InfnEqptType, InfnAutoDiscoveryState,
	InfnAdTpType,InfnPmHistStatsControl, 
	InfnWaveInterfaceType, FloatTenths			FROM INFINERA-TC-MIB
    terminationPoint                            FROM INFINERA-REG-MIB;

fmmCScgPtpMIB MODULE-IDENTITY
    LAST-UPDATED  "201505200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201505200000Z"
    DESCRIPTION
        "First Version"
    ::= { terminationPoint 63 }

fmmC5ScgPtpTable OBJECT-TYPE
    SYNTAX      SEQUENCE OF FmmC5ScgPtpEntry
    MAX-ACCESS  not-accessible
    STATUS      current
    DESCRIPTION
        "A list of FmmCScgPtp entries. Each entry is uniquely identified by the value of ifIndex."
    ::= { fmmCScgPtpMIB 1 }

fmmC5ScgPtpEntry  OBJECT-TYPE
    SYNTAX      FmmC5ScgPtpEntry
    MAX-ACCESS  not-accessible
    STATUS      current
    DESCRIPTION
        "A FmmCScgPtp entry containing information pertaining to Infinera FmmCScgPtp Interfaces.
        This table is a subclass of IfCommon. Entries will exist in this table only for
        interfaces of type DLM OCG PTP."
    INDEX { ifIndex }
    ::= { fmmC5ScgPtpTable 1 }


FmmC5ScgPtpEntry  ::= SEQUENCE {
    fmmC5ScgPtpScgNumber                     Integer32,
    fmmC5ScgPtpScgSupEqptType                InfnEqptType,
    fmmC5ScgPtpAutoDiscoveryState            InfnAutoDiscoveryState,
    fmmC5ScgPtpDiscoveredNeighborTP          DisplayString,
    fmmC5ScgPtpInterfaceType                 InfnWaveInterfaceType,
    fmmC5ScgPtpProvisionedNeighborTP         DisplayString,
    fmmC5ScgPtpProvisionedNeighborAdTpType   InfnAdTpType,
    fmmC5ScgPtpPmHistStatsEnable             InfnPmHistStatsControl,
    fmmC5ScgPtpUsedFreqSlotList              DisplayString,
    fmmC5ScgPtpAvailableFreqSlotList         DisplayString,
	fmmC5ScgPtpAutoDiscSoakTime 			 Integer32,
	fmmC5ScgPtpTxPowerOffset				 FloatTenths,
    fmmC5ScgPtpAllowedPassBandList			 DisplayString,
	fmmC5ScgPtpPassiveMirrorProvNeighborTP   DisplayString,
	fmmC5ScgPtpRxPowerOffset				 FloatTenths
}

fmmC5ScgPtpScgNumber OBJECT-TYPE
    SYNTAX      Integer32
    MAX-ACCESS  read-only
    STATUS      current
    DESCRIPTION ""
    ::= { fmmC5ScgPtpEntry 1 }

fmmC5ScgPtpScgSupEqptType OBJECT-TYPE
    SYNTAX      InfnEqptType
    MAX-ACCESS  read-write
    STATUS      current
    DESCRIPTION ""
    ::= { fmmC5ScgPtpEntry 2 }

fmmC5ScgPtpAutoDiscoveryState OBJECT-TYPE
    SYNTAX      InfnAutoDiscoveryState
    MAX-ACCESS  read-only
    STATUS      current
    DESCRIPTION ""
    ::= { fmmC5ScgPtpEntry 3 }

fmmC5ScgPtpDiscoveredNeighborTP OBJECT-TYPE
    SYNTAX      DisplayString
    MAX-ACCESS  read-only
    STATUS      current
    DESCRIPTION ""
    ::= { fmmC5ScgPtpEntry 4 }

fmmC5ScgPtpProvisionedNeighborTP OBJECT-TYPE
    SYNTAX      DisplayString
    MAX-ACCESS  read-only
    STATUS      current
    DESCRIPTION ""
    ::= { fmmC5ScgPtpEntry 5 }

fmmC5ScgPtpProvisionedNeighborAdTpType OBJECT-TYPE
    SYNTAX      InfnAdTpType
    MAX-ACCESS  read-only
    STATUS      current
    DESCRIPTION ""
    ::= { fmmC5ScgPtpEntry 6 }

fmmC5ScgPtpInterfaceType OBJECT-TYPE
    SYNTAX      InfnWaveInterfaceType
    MAX-ACCESS  read-write
    STATUS      current
    DESCRIPTION ""
    ::= { fmmC5ScgPtpEntry 7 }

fmmC5ScgPtpPmHistStatsEnable OBJECT-TYPE
    SYNTAX          InfnPmHistStatsControl
    MAX-ACCESS      read-write
    STATUS          current
    DESCRIPTION     ""
    ::= { fmmC5ScgPtpEntry 8 }

fmmC5ScgPtpUsedFreqSlotList OBJECT-TYPE
    SYNTAX      DisplayString
    MAX-ACCESS  read-only
    STATUS      current
    DESCRIPTION ""
    ::= { fmmC5ScgPtpEntry 9 }

fmmC5ScgPtpAvailableFreqSlotList	OBJECT-TYPE
    SYNTAX      DisplayString
    MAX-ACCESS  read-only
    STATUS      current
    DESCRIPTION ""
    ::= { fmmC5ScgPtpEntry 10 }

fmmC5ScgPtpAutoDiscSoakTime	OBJECT-TYPE
    SYNTAX      Integer32
    MAX-ACCESS  read-write
    STATUS      current
    DESCRIPTION ""
    ::= { fmmC5ScgPtpEntry 11 }

fmmC5ScgPtpTxPowerOffset	OBJECT-TYPE
    SYNTAX      FloatTenths 
    MAX-ACCESS  read-write
    STATUS      current
    DESCRIPTION ""
    ::= { fmmC5ScgPtpEntry 12 }

fmmC5ScgPtpAllowedPassBandList	OBJECT-TYPE
    SYNTAX      DisplayString
    MAX-ACCESS  read-only
    STATUS      current
    DESCRIPTION ""
    ::= { fmmC5ScgPtpEntry 13 }

fmmC5ScgPtpPassiveMirrorProvNeighborTP OBJECT-TYPE
    SYNTAX      DisplayString
    MAX-ACCESS  read-only
    STATUS      current
    DESCRIPTION ""
    ::= { fmmC5ScgPtpEntry 14 }

fmmC5ScgPtpRxPowerOffset OBJECT-TYPE
    SYNTAX      FloatTenths 
    MAX-ACCESS  read-write
    STATUS      current
    DESCRIPTION ""
    ::= { fmmC5ScgPtpEntry 15 }

----------------------------------------------------------------------------------------------------
----	FMMC12	----
----------------------------------------------------------------------------------------------------

fmmC12ScgPtpTable OBJECT-TYPE
    SYNTAX      SEQUENCE OF FmmC12ScgPtpEntry
    MAX-ACCESS  not-accessible
    STATUS      current
    DESCRIPTION
        "A list of FmmC12ScgPtp entries. Each entry is uniquely identified by the value of ifIndex."
    ::= { fmmCScgPtpMIB 2 }

fmmC12ScgPtpEntry  OBJECT-TYPE
    SYNTAX      FmmC12ScgPtpEntry
    MAX-ACCESS  not-accessible
    STATUS      current
    DESCRIPTION
        "A FmmC12ScgPtp entry containing information pertaining to Infinera FmmC12ScgPtp Interfaces.
        This table is a subclass of IfCommon. Entries will exist in this table only for
        interfaces of type DLM OCG PTP."
    INDEX { ifIndex }
    ::= { fmmC12ScgPtpTable 1 }

FmmC12ScgPtpEntry  ::= SEQUENCE {
    fmmC12ScgPtpScgNumber                      Integer32,
    fmmC12ScgPtpScgSupEqptType                 InfnEqptType,
    fmmC12ScgPtpAutoDiscoveryState             InfnAutoDiscoveryState,
    fmmC12ScgPtpDiscoveredNeighborTP           DisplayString,
    fmmC12ScgPtpInterfaceType                  InfnWaveInterfaceType,
    fmmC12ScgPtpProvisionedNeighborTP          DisplayString,
    fmmC12ScgPtpProvisionedNeighborAdTpType    InfnAdTpType,
    fmmC12ScgPtpPmHistStatsEnable              InfnPmHistStatsControl,
    fmmC12ScgPtpUsedFreqSlotList               DisplayString,
    fmmC12ScgPtpAvailableFreqSlotList          DisplayString,
    fmmC12ScgPtpAllowedPassBandList            DisplayString,
    fmmC12ScgPtpPassiveMirrorProvNeighborTP    DisplayString,
    fmmC12ScgPtpRxPowerOffset                  FloatTenths
}

fmmC12ScgPtpScgNumber OBJECT-TYPE
    SYNTAX      Integer32
    MAX-ACCESS  read-only
    STATUS      current
    DESCRIPTION ""
    ::= { fmmC12ScgPtpEntry 1 }

fmmC12ScgPtpScgSupEqptType OBJECT-TYPE
    SYNTAX      InfnEqptType
    MAX-ACCESS  read-write
    STATUS      current
    DESCRIPTION ""
    ::= { fmmC12ScgPtpEntry 2 }

fmmC12ScgPtpAutoDiscoveryState OBJECT-TYPE
    SYNTAX      InfnAutoDiscoveryState
    MAX-ACCESS  read-only
    STATUS      current
    DESCRIPTION ""
    ::= { fmmC12ScgPtpEntry 3 }

fmmC12ScgPtpDiscoveredNeighborTP OBJECT-TYPE
    SYNTAX      DisplayString
    MAX-ACCESS  read-only
    STATUS      current
    DESCRIPTION ""
    ::= { fmmC12ScgPtpEntry 4 }
fmmC12ScgPtpProvisionedNeighborTP OBJECT-TYPE
    SYNTAX      DisplayString
    MAX-ACCESS  read-only
    STATUS      current
    DESCRIPTION ""
    ::= { fmmC12ScgPtpEntry 5 }

fmmC12ScgPtpProvisionedNeighborAdTpType OBJECT-TYPE
    SYNTAX      InfnAdTpType
    MAX-ACCESS  read-only
    STATUS      current
    DESCRIPTION ""
    ::= { fmmC12ScgPtpEntry 6 }

fmmC12ScgPtpInterfaceType OBJECT-TYPE
    SYNTAX      InfnWaveInterfaceType
    MAX-ACCESS  read-write
    STATUS      current
    DESCRIPTION ""
    ::= { fmmC12ScgPtpEntry 7 }

fmmC12ScgPtpPmHistStatsEnable OBJECT-TYPE
    SYNTAX          InfnPmHistStatsControl
    MAX-ACCESS      read-write
    STATUS          current
    DESCRIPTION     ""
    ::= { fmmC12ScgPtpEntry 8 }

fmmC12ScgPtpUsedFreqSlotList OBJECT-TYPE
    SYNTAX      DisplayString
    MAX-ACCESS  read-only
    STATUS      current
    DESCRIPTION ""
    ::= { fmmC12ScgPtpEntry 9 }

fmmC12ScgPtpAvailableFreqSlotList   OBJECT-TYPE
    SYNTAX      DisplayString
    MAX-ACCESS  read-only
    STATUS      current
    DESCRIPTION ""
    ::= { fmmC12ScgPtpEntry 10 }

fmmC12ScgPtpAllowedPassBandList OBJECT-TYPE
    SYNTAX      DisplayString
    MAX-ACCESS  read-only
    STATUS      current
    DESCRIPTION ""
    ::= { fmmC12ScgPtpEntry 11 }

fmmC12ScgPtpPassiveMirrorProvNeighborTP OBJECT-TYPE
    SYNTAX      DisplayString
    MAX-ACCESS  read-only
    STATUS      current
    DESCRIPTION ""
    ::= { fmmC12ScgPtpEntry 12 }

fmmC12ScgPtpRxPowerOffset OBJECT-TYPE
    SYNTAX      FloatTenths
    MAX-ACCESS  read-write
    STATUS      current
    DESCRIPTION ""
    ::= { fmmC12ScgPtpEntry 13 }


-- Conformance Statements
fmmCScgPtpConformance    OBJECT IDENTIFIER ::= { fmmCScgPtpMIB 3 }
fmmCScgPtpCompliances    OBJECT IDENTIFIER ::= { fmmCScgPtpConformance 1 }
fmmCScgPtpGroups         OBJECT IDENTIFIER ::= { fmmCScgPtpConformance 2 }

fmmCScgPtpCompliance MODULE-COMPLIANCE
    STATUS current
    DESCRIPTION
    "Describes the requirements for conformance to the FMMCSCGPTP-MIB"
    MODULE
        MANDATORY-GROUPS { fmmC5ScgPtpGroup }
    ::= { fmmCScgPtpCompliances 1 }

fmmC12ScgPtpCompliance MODULE-COMPLIANCE
    STATUS current
    DESCRIPTION
    "Describes the requirements for conformance to the FMMC12SCGPTP-MIB"
    MODULE
        MANDATORY-GROUPS { fmmC12ScgPtpGroup }
    ::= { fmmCScgPtpCompliances 2 }


fmmC5ScgPtpGroup OBJECT-GROUP
    OBJECTS {
        fmmC5ScgPtpScgNumber,
        fmmC5ScgPtpScgSupEqptType,
        fmmC5ScgPtpAutoDiscoveryState,
        fmmC5ScgPtpDiscoveredNeighborTP,
        fmmC5ScgPtpInterfaceType,
        fmmC5ScgPtpProvisionedNeighborTP,
        fmmC5ScgPtpProvisionedNeighborAdTpType,
        fmmC5ScgPtpPmHistStatsEnable,
        fmmC5ScgPtpUsedFreqSlotList,
		fmmC5ScgPtpAvailableFreqSlotList,
		fmmC5ScgPtpAutoDiscSoakTime,
	    fmmC5ScgPtpTxPowerOffset,
    	fmmC5ScgPtpAllowedPassBandList,
        fmmC5ScgPtpPassiveMirrorProvNeighborTP,
		fmmC5ScgPtpRxPowerOffset
    }
    STATUS current
    DESCRIPTION
        " A collection of objects for managing the fmmC5ScgPtp"
    ::= { fmmCScgPtpGroups 1 }

fmmC12ScgPtpGroup OBJECT-GROUP
    OBJECTS {
        fmmC12ScgPtpScgNumber,
        fmmC12ScgPtpScgSupEqptType,
        fmmC12ScgPtpAutoDiscoveryState,
        fmmC12ScgPtpDiscoveredNeighborTP,
        fmmC12ScgPtpInterfaceType,
        fmmC12ScgPtpProvisionedNeighborTP,
        fmmC12ScgPtpProvisionedNeighborAdTpType,
        fmmC12ScgPtpPmHistStatsEnable,
        fmmC12ScgPtpUsedFreqSlotList,
        fmmC12ScgPtpAvailableFreqSlotList,
        fmmC12ScgPtpPassiveMirrorProvNeighborTP,
        fmmC12ScgPtpRxPowerOffset
    }
    STATUS current
    DESCRIPTION
        " A collection of objects for managing the fmmC12ScgPtp"
    ::= { fmmCScgPtpGroups 2 }


END

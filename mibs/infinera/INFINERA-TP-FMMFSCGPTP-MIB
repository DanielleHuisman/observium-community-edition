-- *****************************************************************
-- INFINERA-TP-FMMFSCGPTP-MIB
-- Copyright (c) 2008-2015 by Infinera Inc
-- All rights reserved.
-- ****************************************************************

INFINERA-TP-FMMFSCGPTP-MIB DEFINITIONS ::= BEGIN

IMPORTS
    MODULE-IDENTITY, OBJECT-TYPE, Integer32     FROM SNMPv2-SMI
    MODULE-COMPLIANCE, OBJECT-GROUP             FROM SNMPv2-CONF
    DisplayString                               FROM SNMPv2-TC
    ifIndex                                     FROM IF-MIB
    FloatHundredths, InfnEnableDisable,
    InfnEqptType, InfnAutoDiscoveryState,
	InfnInterfaceType, InfnAdTpType,
	InfnPmHistStatsControl, InfnSpectrumType	FROM INFINERA-TC-MIB
    terminationPoint                            FROM INFINERA-REG-MIB;

fmmFScgPtpMIB MODULE-IDENTITY
    LAST-UPDATED  "201505200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201505200000Z"
    DESCRIPTION
        "First Version"
    ::= { terminationPoint 60 }

fmmFScgPtpTable OBJECT-TYPE
    SYNTAX      SEQUENCE OF FmmFScgPtpEntry
    MAX-ACCESS  not-accessible
    STATUS      current
    DESCRIPTION
        "A list of FmmFScgPtp entries. Each entry is uniquely identified by the value of ifIndex."
    ::= { fmmFScgPtpMIB 1 }

fmmFScgPtpEntry  OBJECT-TYPE
    SYNTAX      FmmFScgPtpEntry
    MAX-ACCESS  not-accessible
    STATUS      current
    DESCRIPTION
        "A FmmFScgPtp entry containing information pertaining to Infinera FmmFScgPtp Interfaces.
        This table is a subclass of IfCommon. Entries will exist in this table only for
        interfaces of type DLM OCG PTP."
    INDEX { ifIndex }
    ::= { fmmFScgPtpTable 1 }


FmmFScgPtpEntry  ::= SEQUENCE {
    fmmFScgPtpScgNumber                      Integer32,
    fmmFScgPtpScgSupEqptType                 InfnEqptType,
    fmmFScgPtpMPOAID                         DisplayString,
    fmmFScgPtpProvisionedFPMPO               DisplayString,
    fmmFScgPtpAutoDiscoveryState             InfnAutoDiscoveryState,
    fmmFScgPtpDiscoveredNeighborTP           DisplayString,
    fmmFScgPtpInterfaceType                  InfnInterfaceType,
    fmmFScgPtpProvisionedNeighborTP          DisplayString,
    fmmFScgPtpProvisionedNeighborAdTpType    InfnAdTpType,
    fmmFScgPtpPmHistStatsEnable              InfnPmHistStatsControl,
    fmmFScgPtpProvisionedOpenWaveRemotePtp   DisplayString,
    fmmFScgPtpPowerControlLoop               InfnEnableDisable,
    fmmFScgPtpUsedFreqSlotList               DisplayString,
	fmmFScgPtpProvisionedSpectrumType		 InfnSpectrumType,
	fmmFScgPtpProvisionedSuperChannelNumber  DisplayString,
	fmmFScgPtpAutoDiscSoakTime				 Integer32,
	fmmFScgPtpTargetRxPower					 FloatHundredths
}

fmmFScgPtpScgNumber OBJECT-TYPE
    SYNTAX      Integer32
    MAX-ACCESS  read-only
    STATUS      current
    DESCRIPTION ""
    ::= { fmmFScgPtpEntry 1 }

fmmFScgPtpScgSupEqptType OBJECT-TYPE
    SYNTAX      InfnEqptType
    MAX-ACCESS  read-write
    STATUS      current
    DESCRIPTION ""
    ::= { fmmFScgPtpEntry 2 }

fmmFScgPtpMPOAID OBJECT-TYPE
    SYNTAX      DisplayString
    MAX-ACCESS  read-write
    STATUS      current
    DESCRIPTION ""
    ::= { fmmFScgPtpEntry 3 }

fmmFScgPtpProvisionedFPMPO  OBJECT-TYPE
    SYNTAX      DisplayString
    MAX-ACCESS  read-write
    STATUS      current
    DESCRIPTION ""
    ::= { fmmFScgPtpEntry 4 }


fmmFScgPtpAutoDiscoveryState OBJECT-TYPE
    SYNTAX      InfnAutoDiscoveryState
    MAX-ACCESS  read-only
    STATUS      current
    DESCRIPTION ""
    ::= { fmmFScgPtpEntry 5 }

fmmFScgPtpDiscoveredNeighborTP OBJECT-TYPE
    SYNTAX      DisplayString
    MAX-ACCESS  read-only
    STATUS      current
    DESCRIPTION ""
    ::= { fmmFScgPtpEntry 6 }

fmmFScgPtpProvisionedNeighborTP OBJECT-TYPE
    SYNTAX      DisplayString
    MAX-ACCESS  read-only
    STATUS      current
    DESCRIPTION ""
    ::= { fmmFScgPtpEntry 7 }

fmmFScgPtpProvisionedNeighborAdTpType OBJECT-TYPE
    SYNTAX      InfnAdTpType
    MAX-ACCESS  read-only
    STATUS      current
    DESCRIPTION ""
    ::= { fmmFScgPtpEntry 8 }

fmmFScgPtpInterfaceType OBJECT-TYPE
    SYNTAX      InfnInterfaceType
    MAX-ACCESS  read-write
    STATUS      current
    DESCRIPTION ""
    ::= { fmmFScgPtpEntry 9 }

fmmFScgPtpProvisionedOpenWaveRemotePtp OBJECT-TYPE
    SYNTAX          DisplayString
    MAX-ACCESS      read-write
    STATUS          current
    DESCRIPTION     ""
    ::= { fmmFScgPtpEntry 10 }

fmmFScgPtpPmHistStatsEnable OBJECT-TYPE
    SYNTAX          InfnPmHistStatsControl
    MAX-ACCESS      read-only
    STATUS          current
    DESCRIPTION     ""
    ::= { fmmFScgPtpEntry 11 }


fmmFScgPtpPowerControlLoop  OBJECT-TYPE
    SYNTAX      InfnEnableDisable
    MAX-ACCESS  read-write
    STATUS      current
    DESCRIPTION ""
    ::= { fmmFScgPtpEntry  12 }

fmmFScgPtpUsedFreqSlotList OBJECT-TYPE
    SYNTAX      DisplayString
    MAX-ACCESS  read-only
    STATUS      current
    DESCRIPTION ""
    ::= { fmmFScgPtpEntry 13 }

fmmFScgPtpProvisionedSpectrumType OBJECT-TYPE
    SYNTAX		InfnSpectrumType
    MAX-ACCESS  read-write
    STATUS      current
    DESCRIPTION ""
    ::= { fmmFScgPtpEntry 14 }


fmmFScgPtpProvisionedSuperChannelNumber OBJECT-TYPE
    SYNTAX      DisplayString
    MAX-ACCESS  read-only
    STATUS      current
    DESCRIPTION " Super Channels are not applicable to line ports"
    ::= { fmmFScgPtpEntry 15 }

fmmFScgPtpAutoDiscSoakTime	OBJECT-TYPE
    SYNTAX      Integer32 
    MAX-ACCESS  read-write
    STATUS      current
    DESCRIPTION ""
    ::= { fmmFScgPtpEntry 16 }

fmmFScgPtpTargetRxPower	OBJECT-TYPE
    SYNTAX      FloatHundredths  
    MAX-ACCESS  read-only
    STATUS      current
    DESCRIPTION ""
    ::= { fmmFScgPtpEntry 17 }

-- Conformance Statements
fmmFScgPtpConformance    OBJECT IDENTIFIER ::= { fmmFScgPtpMIB 3 }
fmmFScgPtpCompliances    OBJECT IDENTIFIER ::= { fmmFScgPtpConformance 1 }
fmmFScgPtpGroups         OBJECT IDENTIFIER ::= { fmmFScgPtpConformance 2 }

fmmFScgPtpCompliance MODULE-COMPLIANCE
    STATUS current
    DESCRIPTION
    "Describes the requirements for conformance to the FMMFSCGPTP-MIB"
    MODULE
        MANDATORY-GROUPS { fmmFScgPtpGroup }
    ::= { fmmFScgPtpCompliances 1 }

fmmFScgPtpGroup OBJECT-GROUP
    OBJECTS {
        fmmFScgPtpScgNumber,
        fmmFScgPtpScgSupEqptType,
        fmmFScgPtpMPOAID,
        fmmFScgPtpProvisionedFPMPO,
        fmmFScgPtpAutoDiscoveryState,
        fmmFScgPtpDiscoveredNeighborTP,
        fmmFScgPtpInterfaceType,
        fmmFScgPtpProvisionedNeighborTP,
        fmmFScgPtpProvisionedNeighborAdTpType,
        fmmFScgPtpPmHistStatsEnable,
        fmmFScgPtpProvisionedOpenWaveRemotePtp,
        fmmFScgPtpPowerControlLoop,
        fmmFScgPtpUsedFreqSlotList,
		fmmFScgPtpProvisionedSpectrumType,
		fmmFScgPtpProvisionedSuperChannelNumber,
		fmmFScgPtpAutoDiscSoakTime,
		fmmFScgPtpTargetRxPower   
    }
    STATUS current
    DESCRIPTION
        " A collection of objects for managing the fmmFScgPtp"
    ::= { fmmFScgPtpGroups 1 }
END

-- *****************************************************************
-- INFINERA-TP-FMPO25-MIB
-- Copyright (c) 2008-2012 by Infinera Inc
-- All rights reserved.
-- ****************************************************************

INFINERA-TP-FMPO25-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths,InfnEnableDisable           FROM INFINERA-TC-MIB
    terminationPoint                            FROM INFINERA-REG-MIB;

fmpo25PtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 40 }

fmpo25PtpTable OBJECT-TYPE
    SYNTAX      SEQUENCE OF Fmpo25PtpEntry
    MAX-ACCESS  not-accessible
    STATUS      current
    DESCRIPTION
        "A list of Fmpo25Ptp entries. Each entry is uniquely identified by the value of ifIndex."
    ::= { fmpo25PtpMIB 1 } 

fmpo25PtpEntry  OBJECT-TYPE
    SYNTAX      Fmpo25PtpEntry
    MAX-ACCESS  not-accessible
    STATUS      current
    DESCRIPTION
        "A Fmpo25Ptp entry containing information pertaining to Infinera Fmpo25Ptp Interfaces.
        This table is a subclass of IfCommon. Entries will exist in this table only for
        interfaces of type DLM OCG PTP."
    INDEX { ifIndex }
    ::= { fmpo25PtpTable 1 }


Fmpo25PtpEntry  ::= SEQUENCE {
    fmpo25PtpProvNbrTP           DisplayString
}

fmpo25PtpProvNbrTP   OBJECT-TYPE
    SYNTAX      DisplayString
    MAX-ACCESS  read-write
    STATUS      current
    DESCRIPTION ""
    ::= { fmpo25PtpEntry 1 }

-- Conformance Statements
fmpo25PtpConformance    OBJECT IDENTIFIER ::= { fmpo25PtpMIB 3 }
fmpo25PtpCompliances    OBJECT IDENTIFIER ::= { fmpo25PtpConformance 1 }
fmpo25PtpGroups         OBJECT IDENTIFIER ::= { fmpo25PtpConformance 2 }

fmpo25PtpCompliance MODULE-COMPLIANCE
    STATUS current
    DESCRIPTION
    "Describes the requirements for conformance to the FMPO25-MIB"
    MODULE
        MANDATORY-GROUPS { fmpo25PtpGroup }
    ::= { fmpo25PtpCompliances 1 }

fmpo25PtpGroup OBJECT-GROUP
    OBJECTS {
        fmpo25PtpProvNbrTP
}
    STATUS current
    DESCRIPTION
        " A collection of objects for managing the fmpo25Ptp"
    ::= { fmpo25PtpGroups 1 }
END

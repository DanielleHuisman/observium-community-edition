-- *****************************************************************
-- INFINERA-TP-FMPO50-MIB
-- Copyright (c) 2008-2012 by Infinera Inc
-- All rights reserved.
-- ****************************************************************

INFINERA-TP-FMPO50-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths,InfnEnableDisable           FROM INFINERA-TC-MIB
    terminationPoint                            FROM INFINERA-REG-MIB;

fmpo50PtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 41 }

fmpo50PtpTable OBJECT-TYPE
    SYNTAX      SEQUENCE OF Fmpo50PtpEntry
    MAX-ACCESS  not-accessible
    STATUS      current
    DESCRIPTION
        "A list of Fmpo50Ptp entries. Each entry is uniquely identified by the value of ifIndex."
    ::= { fmpo50PtpMIB 1 } 

fmpo50PtpEntry  OBJECT-TYPE
    SYNTAX      Fmpo50PtpEntry
    MAX-ACCESS  not-accessible
    STATUS      current
    DESCRIPTION
        "A Fmpo50Ptp entry containing information pertaining to Infinera Fmpo50Ptp Interfaces.
        This table is a subclass of IfCommon. Entries will exist in this table only for
        interfaces of type DLM OCG PTP."
    INDEX { ifIndex }
    ::= { fmpo50PtpTable 1 }


Fmpo50PtpEntry  ::= SEQUENCE {
    fmpo50PtpProvNbrTP           DisplayString
}

fmpo50PtpProvNbrTP   OBJECT-TYPE
    SYNTAX      DisplayString
    MAX-ACCESS  read-write
    STATUS      current
    DESCRIPTION ""
    ::= { fmpo50PtpEntry 1 }

-- Conformance Statements
fmpo50PtpConformance    OBJECT IDENTIFIER ::= { fmpo50PtpMIB 3 }
fmpo50PtpCompliances    OBJECT IDENTIFIER ::= { fmpo50PtpConformance 1 }
fmpo50PtpGroups         OBJECT IDENTIFIER ::= { fmpo50PtpConformance 2 }

fmpo50PtpCompliance MODULE-COMPLIANCE
    STATUS current
    DESCRIPTION
    "Describes the requirements for conformance to the FMPO50-MIB"
    MODULE
        MANDATORY-GROUPS { fmpo50PtpGroup }
    ::= { fmpo50PtpCompliances 1 }

fmpo50PtpGroup OBJECT-GROUP
    OBJECTS {
        fmpo50PtpProvNbrTP
}
    STATUS current
    DESCRIPTION
        " A collection of objects for managing the fmpo50Ptp"
    ::= { fmpo50PtpGroups 1 }
END

-- *****************************************************************
-- INFINERA-TP-FMPSCGPTP-MIB
-- Copyright (c) 2008-2012 by Infinera Inc
-- All rights reserved.
-- ****************************************************************

INFINERA-TP-FMPSCGPTP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths,InfnEnableDisable           FROM INFINERA-TC-MIB
    terminationPoint                            FROM INFINERA-REG-MIB;

fmpScgPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 53 }

fmpScgPtpTable OBJECT-TYPE
    SYNTAX      SEQUENCE OF FmpScgPtpEntry
    MAX-ACCESS  not-accessible
    STATUS      current
    DESCRIPTION
        "A list of FmpScgPtp entries. Each entry is uniquely identified by the value of ifIndex."
    ::= { fmpScgPtpMIB 1 }

fmpScgPtpEntry  OBJECT-TYPE
    SYNTAX      FmpScgPtpEntry
    MAX-ACCESS  not-accessible
    STATUS      current
    DESCRIPTION
        "A FmpScgPtp entry containing information pertaining to Infinera FmpScgPtp Interfaces.
        This table is a subclass of IfCommon. Entries will exist in this table only for
        interfaces of type DLM OCG PTP."
    INDEX { ifIndex }
    ::= { fmpScgPtpTable 1 }


FmpScgPtpEntry  ::= SEQUENCE {
    fmpScgPtpProvisionedNeighborTP  DisplayString,
    fmpScgPtpMPOAID                 DisplayString,
    fmpScgPtpProvisionedOpenWaveRemoteTP  DisplayString,
    fmpScgPtpNeighborFPMPOID        DisplayString
}

fmpScgPtpProvisionedNeighborTP  OBJECT-TYPE
    SYNTAX      DisplayString
    MAX-ACCESS  read-write
    STATUS      current
    DESCRIPTION ""
    ::= { fmpScgPtpEntry 1 }

fmpScgPtpMPOAID     OBJECT-TYPE
    SYNTAX      DisplayString
    MAX-ACCESS  read-write
    STATUS      current
    DESCRIPTION ""
    ::= { fmpScgPtpEntry 2 }

fmpScgPtpProvisionedOpenWaveRemoteTP OBJECT-TYPE
    SYNTAX      DisplayString
    MAX-ACCESS  read-write
    STATUS      current
    DESCRIPTION ""
    ::= { fmpScgPtpEntry 3 }

fmpScgPtpNeighborFPMPOID OBJECT-TYPE
    SYNTAX      DisplayString
    MAX-ACCESS  read-write
    STATUS      current
    DESCRIPTION ""
    ::= { fmpScgPtpEntry 4 }

-- Conformance Statements
fmpScgPtpConformance    OBJECT IDENTIFIER ::= { fmpScgPtpMIB 3 }
fmpScgPtpCompliances    OBJECT IDENTIFIER ::= { fmpScgPtpConformance 1 }
fmpScgPtpGroups         OBJECT IDENTIFIER ::= { fmpScgPtpConformance 2 }

fmpScgPtpCompliance MODULE-COMPLIANCE
    STATUS current
    DESCRIPTION
    "Describes the requirements for conformance to the FMPSCGPTP-MIB"
    MODULE
        MANDATORY-GROUPS { fmpScgPtpGroup }
    ::= { fmpScgPtpCompliances 1 }

fmpScgPtpGroup OBJECT-GROUP
    OBJECTS {

        fmpScgPtpProvisionedNeighborTP,
        fmpScgPtpMPOAID,
        fmpScgPtpProvisionedOpenWaveRemoteTP,
        fmpScgPtpNeighborFPMPOID
}
    STATUS current
    DESCRIPTION
        " A collection of objects for managing the fmpScgPtp"
    ::= { fmpScgPtpGroups 1 }
END

-- *****************************************************************
-- INFINERA-TP-GAMOCGPTP-MIB
-- 
-- October 2008, Sharfuddin Syed / Narendra Gupta
-- 
-- 
-- Copyright (c) 2008-2012 by Infinera Inc.
-- All rights reserved.
-- ****************************************************************

INFINERA-TP-GAMOCGPTP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    InfnDcmType                                 FROM INFINERA-TC-MIB
    terminationPoint                            FROM INFINERA-REG-MIB;


gamOcgPtpMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 8 }



gamOcgPtpTable OBJECT-TYPE
    SYNTAX      SEQUENCE OF GamOcgPtpEntry
    MAX-ACCESS  not-accessible
    STATUS      current
    DESCRIPTION
        "A list of GamOcgPtp entries. Each entry is uniquely identified by the value of ifIndex."
    ::= { gamOcgPtpMIB 1 } 

gamOcgPtpEntry  OBJECT-TYPE
    SYNTAX      GamOcgPtpEntry
    MAX-ACCESS  not-accessible
    STATUS      current
    DESCRIPTION
        "A GamOcgPtp entry containing information pertaining to Infinera GamOcgPtp interfaces.
        This table is a subclass of IfCommon.
        Entries will exist in this table only for interfaces of type GamOcgPtp."
    INDEX { ifIndex }
    ::= { gamOcgPtpTable 1 }


GamOcgPtpEntry  ::= SEQUENCE {
    gamOcgPtpDiscoveredOcgTP         DisplayString,
    gamOcgPtpProvisionedOcgTP        DisplayString,
    gamOcgPtpDiscoveredRemoteTP      DisplayString,
    gamOcgPtpPmHistStatsEnable       INTEGER,
    gamOcgPtpInlineDcmType           InfnDcmType
}

gamOcgPtpDiscoveredOcgTP OBJECT-TYPE
    SYNTAX      DisplayString
    MAX-ACCESS  read-only
    STATUS      current
    DESCRIPTION "Discovered OCG on the BMM/DLM."
    ::= { gamOcgPtpEntry  1 }


gamOcgPtpProvisionedOcgTP OBJECT-TYPE
    SYNTAX      DisplayString
    MAX-ACCESS  read-write
    STATUS      current
    DESCRIPTION "The name of the DLM/XLM OCG PTP that this GAM is conneted to.
     If the configured OCG PTP does not match the discovered OCG PTP, 
     a mismatch alarm is raised. If it is empty, the attribute is automatically
     filled when a fiber is connected and a valid Discovered OCG PTP is obtained."
    ::= { gamOcgPtpEntry  2 }


gamOcgPtpDiscoveredRemoteTP OBJECT-TYPE
    SYNTAX      DisplayString
    MAX-ACCESS  read-only
    STATUS      current
    DESCRIPTION "The name of the DLM TPs to which this fiber is connected."
    ::= { gamOcgPtpEntry  3 }


gamOcgPtpPmHistStatsEnable OBJECT-TYPE
    SYNTAX  INTEGER {
        enabled(1),
        disabled(2)
    }
    MAX-ACCESS  read-write
    STATUS      current
    DESCRIPTION "Flag to enable or disable PM collection."
    DEFVAL      { enabled }
    ::= { gamOcgPtpEntry  4 }

gamOcgPtpInlineDcmType OBJECT-TYPE
    SYNTAX  InfnDcmType 
    MAX-ACCESS  read-write
    STATUS      obsolete
    DESCRIPTION "Inline DCM type configuration."
    DEFVAL      { unspecified } 
    ::= { gamOcgPtpEntry  5 }

-- Conformance Statements
gamOcgPtpConformance    OBJECT IDENTIFIER ::= { gamOcgPtpMIB 3 }
gamOcgPtpCompliances    OBJECT IDENTIFIER ::= { gamOcgPtpConformance 1 }
gamOcgPtpGroups         OBJECT IDENTIFIER ::= { gamOcgPtpConformance 2 }

gamOcgPtpCompliance MODULE-COMPLIANCE
    STATUS current
    DESCRIPTION
    "Describes the requirements for conformance to the GAMOCGPTP-MIB"
    MODULE
        MANDATORY-GROUPS { gamOcgPtpGroup }
    ::= { gamOcgPtpCompliances 1 }

gamOcgPtpGroup OBJECT-GROUP
    OBJECTS {
        gamOcgPtpDiscoveredOcgTP,
        gamOcgPtpProvisionedOcgTP,
        gamOcgPtpDiscoveredRemoteTP,
        gamOcgPtpPmHistStatsEnable,
        gamOcgPtpInlineDcmType          
    }
    STATUS current
    DESCRIPTION
        " A collection of objects for managing the gamOcgPtp"
    ::= { gamOcgPtpGroups 1 }


END

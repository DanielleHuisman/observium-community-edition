-- *****************************************************************
-- INFINERA-TP-GFPCLIENTCTP-MIB
-- Copyright (c) 2011-2012 by Infinera Inc.
-- All rights reserved.
-- ****************************************************************

INFINERA-TP-GFPCLIENTCTP-MIB DEFINITIONS ::= BEGIN

IMPORTS
    MODULE-IDENTITY, OBJECT-TYPE,
    Integer32, Counter64          			FROM SNMPv2-SMI
    MODULE-COMPLIANCE, OBJECT-GROUP            	 	FROM SNMPv2-CONF
    DisplayString, TruthValue                  		FROM SNMPv2-TC
    ifIndex                                     	FROM IF-MIB
    InfnServiceType,InfnServiceMode, InfnSMQ,
    InfnGFPState, InfnGFPPayloadFCS, 
    InfnGfpExtHdrTyp   					FROM INFINERA-TC-MIB

    terminationPoint                        		FROM INFINERA-REG-MIB;


gfpclientCtpMIB MODULE-IDENTITY
    LAST-UPDATED  "201104200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201104200000Z"
    DESCRIPTION
        "First Version"
    ::= { terminationPoint 32 }



gfpclientCtpTable OBJECT-TYPE
    SYNTAX      SEQUENCE OF GfpClientCtpEntry
    MAX-ACCESS  not-accessible
    STATUS      current
    DESCRIPTION
        "A list of OtuClientCtp entries. Each entry is uniquely identified by the value of ifIndex."
    ::= { gfpclientCtpMIB 1 } 

gfpclientCtpEntry  OBJECT-TYPE
    SYNTAX      GfpClientCtpEntry
    MAX-ACCESS  not-accessible
    STATUS      current
    DESCRIPTION
        "A GfpClientCtp entry containing information pertaining to Infinera GfpClientCtp interfaces.
        Entries will exist in this table for interfaces of type otuclientCtp."
    INDEX { ifIndex }
    ::= { gfpclientCtpTable 1 }


GfpClientCtpEntry  ::= SEQUENCE {
    
    gfpclientCtpServiceMode                     InfnServiceMode,
    gfpclientCtpServiceModeQualifier            InfnSMQ,
    gfpclientCtpConfigServiceType               InfnServiceType,
    gfpclientCtpPayloadFCS                      InfnGFPPayloadFCS,    
    gfpclientCtpGFPState		  	InfnGFPState,   
    gfpclientCtpExtHeaderType			InfnGfpExtHdrTyp,			  
    gfpclientCtpChannelId			Integer32
             
}



gfpclientCtpServiceMode OBJECT-TYPE
    SYNTAX  InfnServiceMode
    MAX-ACCESS  read-only
    STATUS      current
    DESCRIPTION ""
    DEFVAL      { none }
    ::= { gfpclientCtpEntry  1 }

gfpclientCtpServiceModeQualifier  OBJECT-TYPE
    SYNTAX      InfnSMQ
    MAX-ACCESS  read-only
    STATUS      current
    DESCRIPTION ""
    DEFVAL      { none }
    ::= { gfpclientCtpEntry  2 }

gfpclientCtpConfigServiceType  OBJECT-TYPE
    SYNTAX      InfnServiceType
    MAX-ACCESS  read-only
    STATUS      current
    DESCRIPTION ""
    DEFVAL      { bwGfp }
    ::= { gfpclientCtpEntry  3 }

gfpclientCtpPayloadFCS  OBJECT-TYPE
    SYNTAX      InfnGFPPayloadFCS
    MAX-ACCESS  read-write
    STATUS      current

    DESCRIPTION "	whether or not Payload FCS is
	included in the generated (sourced) GFP client
	frames."
    DEFVAL      { disable }
    ::= { gfpclientCtpEntry  4 }

gfpclientCtpGFPState  OBJECT-TYPE
    SYNTAX      InfnGFPState
    MAX-ACCESS  read-only
    STATUS      current
    DESCRIPTION ""
    ::= { gfpclientCtpEntry  5 }

gfpclientCtpExtHeaderType  OBJECT-TYPE
    SYNTAX      InfnGfpExtHdrTyp
    MAX-ACCESS  read-write
    STATUS      current
    DESCRIPTION ""
    DEFVAL      { null }
    ::= { gfpclientCtpEntry  6 }

gfpclientCtpChannelId  OBJECT-TYPE
    SYNTAX     	Integer32
    MAX-ACCESS  read-write
    STATUS      current
    DESCRIPTION ""
    DEFVAL      { 0 }
    ::= { gfpclientCtpEntry  7 }



-- Conformance Statements
gfpclientCtpConformance    OBJECT IDENTIFIER ::= { gfpclientCtpMIB 3 }
gfpclientCtpCompliances    OBJECT IDENTIFIER ::= { gfpclientCtpConformance 1 }
gfpclientCtpGroups         OBJECT IDENTIFIER ::= { gfpclientCtpConformance 2 }

gfpclientCtpCompliance MODULE-COMPLIANCE
    STATUS current
    DESCRIPTION
    "Describes the requirements for conformance to the OTUCLIENTCTP-MIB"
    MODULE
        MANDATORY-GROUPS { gfpclientCtpGroup }
    ::= { gfpclientCtpCompliances 1 }

gfpclientCtpGroup OBJECT-GROUP
    OBJECTS {
   	
    gfpclientCtpServiceMode ,
    gfpclientCtpServiceModeQualifier ,
    gfpclientCtpConfigServiceType ,
    gfpclientCtpPayloadFCS ,    
    gfpclientCtpGFPState,   
    gfpclientCtpExtHeaderType,			  
    gfpclientCtpChannelId			
   
    }
    STATUS current
    DESCRIPTION
        " A collection of objects for managing the gfpclientCtp"
    ::= { gfpclientCtpGroups 1 }


END

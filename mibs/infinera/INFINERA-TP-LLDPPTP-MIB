-- *****************************************************************
-- INFINERA-TP-LLDPPTP-MIB
--
-- June 2015, Kavitha Manjunatha / Narendra Gupta
--
-- Copyright (c) 2008-2012 by Infinera Inc.
-- All rights reserved.
-- ****************************************************************

INFINERA-TP-LLDPPTP-MIB DEFINITIONS ::= BEGIN

IMPORTS
    MODULE-IDENTITY, OBJECT-TYPE, Integer32     FROM SNMPv2-SMI
    MODULE-COMPLIANCE, OBJECT-GROUP             FROM SNMPv2-CONF
    DisplayString                               FROM SNMPv2-TC
    ifIndex                                     FROM IF-MIB
    InfnChassisIdSubtype, InfnPortIdSubtype,
    InfnManAddrSubtype, InfnManAddrIfSubtype    FROM INFINERA-TC-MIB
    terminationPoint                            FROM INFINERA-REG-MIB;

lldpPtpMIB MODULE-IDENTITY
    LAST-UPDATED  "201506240000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "201506240000Z"
    DESCRIPTION
        " "
::= { terminationPoint 56 }


lldpPtpConformance   OBJECT IDENTIFIER ::= { lldpPtpMIB 3 }
lldpPtpCompliances   OBJECT IDENTIFIER ::= { lldpPtpConformance 1 }
lldpPtpGroups        OBJECT IDENTIFIER ::= { lldpPtpConformance 2 }

lldpRemoteSysPtpTable  OBJECT-TYPE
    SYNTAX SEQUENCE OF LldpPtpEntry
    MAX-ACCESS not-accessible
    STATUS     current
    DESCRIPTION
        "A list of LldpPtp entries. Each entry is uniquely identified by
                the value of ifIndex."
    ::= { lldpPtpMIB 1 }

lldpPtpEntry  OBJECT-TYPE
    SYNTAX     LldpPtpEntry
    MAX-ACCESS not-accessible
    STATUS     current
    DESCRIPTION
        "A LldpPtp entry containing information pertaining to Infinera TribPtp
         interfaces. This table is a subclass of IfCommon. Entries will exist
         in this table only for interfaces of type LldpPtp."
    INDEX { ifIndex }
    ::= { lldpRemoteSysPtpTable 1 }

LldpPtpEntry  ::= SEQUENCE {
    lldpRemoteSysChassisIdSubtype         InfnChassisIdSubtype,
    lldpRemoteSysChassisId                DisplayString,
    lldpRemoteSysPortIdSubtype            InfnPortIdSubtype,
    lldpRemoteSysPortId                   DisplayString,
    lldpRemoteSysTtl			  Integer32,
    lldpRemoteSysPortDesc		  DisplayString,
    lldpRemoteSysSysName		  DisplayString,
    lldpRemoteSysSysDesc		  DisplayString,
    lldpRemoteSysLastReceivedTimeString   DisplayString
}

lldpRemoteSysChassisIdSubtype  OBJECT-TYPE
    SYNTAX     InfnChassisIdSubtype
    MAX-ACCESS read-only
    STATUS     current
    DESCRIPTION
        "An identifer for Remote System Chassis ID subtype"
    ::= { lldpPtpEntry 1 }

lldpRemoteSysChassisId  OBJECT-TYPE
    SYNTAX     DisplayString
    MAX-ACCESS read-only
    STATUS     current
    DESCRIPTION
        "LLDP Remote System Chassis ID"
    ::= { lldpPtpEntry 2 }

lldpRemoteSysPortIdSubtype  OBJECT-TYPE
    SYNTAX     InfnPortIdSubtype
    MAX-ACCESS read-only
    STATUS     current
    DESCRIPTION
        "An identifier for LLDP Remote System Port ID Subtype"
    ::= { lldpPtpEntry 3 }

lldpRemoteSysPortId  OBJECT-TYPE
    SYNTAX     DisplayString
    MAX-ACCESS read-only
    STATUS     current
    DESCRIPTION
        "LLDP Remote System Port ID"
    ::= { lldpPtpEntry 4 }

lldpRemoteSysTtl  OBJECT-TYPE
    SYNTAX     Integer32
    MAX-ACCESS read-only
    STATUS     current
    DESCRIPTION
        "LLDP Remote System TTL"
    ::= { lldpPtpEntry 5 }

lldpRemoteSysPortDesc  OBJECT-TYPE
    SYNTAX     DisplayString
    MAX-ACCESS read-only
    STATUS     current
    DESCRIPTION
        "LLDP Remote System Port description"
    ::= { lldpPtpEntry 6 }

lldpRemoteSysSysName  OBJECT-TYPE
    SYNTAX     DisplayString
    MAX-ACCESS read-only
    STATUS     current
    DESCRIPTION
        "LLDP Remote System Name"
    ::= { lldpPtpEntry 7 }

lldpRemoteSysSysDesc  OBJECT-TYPE
    SYNTAX     DisplayString
    MAX-ACCESS read-only
    STATUS     current
    DESCRIPTION
        "LLDP Remote System Description"
    ::= { lldpPtpEntry 8 }

lldpRemoteSysLastReceivedTimeString  OBJECT-TYPE
    SYNTAX     DisplayString
    MAX-ACCESS read-write
    STATUS     current
    DESCRIPTION
        ""
    ::= { lldpPtpEntry 9 }

lldpPtpCompliance  MODULE-COMPLIANCE
    STATUS     current
    DESCRIPTION
        "Describes the requirements for conformance to the LLDPPTP-MIB"
    MODULE
        MANDATORY-GROUPS { lldpPtpGroup }
    ::= { lldpPtpCompliances 1 }

lldpPtpGroup  OBJECT-GROUP
    OBJECTS {
	    lldpRemoteSysChassisIdSubtype,
	    lldpRemoteSysChassisId,
	    lldpRemoteSysPortIdSubtype,
	    lldpRemoteSysPortId,
	    lldpRemoteSysTtl,
	    lldpRemoteSysPortDesc,
	    lldpRemoteSysSysName,
	    lldpRemoteSysSysDesc,
	    lldpRemoteSysLastReceivedTimeString
        }
    STATUS     current
    DESCRIPTION
        " A collection of objects for managing lldpPtp interfaces."
    ::= { lldpPtpGroups 1 }
END

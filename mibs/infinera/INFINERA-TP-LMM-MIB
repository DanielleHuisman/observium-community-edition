-- *****************************************************************
-- INFINERA-TP-LMM-MIB
-- Copyright (c) 2008-2012 by Infinera Inc
-- All rights reserved.
-- ****************************************************************

INFINERA-TP-LMM-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths,InfnEnableDisable           FROM INFINERA-TC-MIB
    terminationPoint                            FROM INFINERA-REG-MIB;

lmmPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 55 }

lmmPtpTable OBJECT-TYPE
    SYNTAX      SEQUENCE OF LmmPtpEntry
    MAX-ACCESS  not-accessible
    STATUS      current
    DESCRIPTION
        "A list of LmmPtp entries. Each entry is uniquely identified by the value of ifIndex."
    ::= { lmmPtpMIB 1 } 

lmmPtpEntry  OBJECT-TYPE
    SYNTAX      LmmPtpEntry
    MAX-ACCESS  not-accessible
    STATUS      current
    DESCRIPTION
        "A LmmPtp entry containing information pertaining to Infinera LmmPtp Interfaces.
        This table is a subclass of IfCommon. Entries will exist in this table only for
        interfaces of type DLM OCG PTP."
    INDEX { ifIndex }
    ::= { lmmPtpTable 1 }


LmmPtpEntry  ::= SEQUENCE {
    lmmPtpRxProvNbrTP           DisplayString,
    lmmPtpTxProvNbrTP           DisplayString,
    lmmPtpProvisionedOpenWaveRemoteTP	 DisplayString
}

lmmPtpRxProvNbrTP   OBJECT-TYPE
    SYNTAX      DisplayString
    MAX-ACCESS  read-write
    STATUS      current
    DESCRIPTION ""
    ::= { lmmPtpEntry 1 }

lmmPtpTxProvNbrTP     OBJECT-TYPE
    SYNTAX      DisplayString
    MAX-ACCESS  read-write
    STATUS      current
    DESCRIPTION ""
    ::= { lmmPtpEntry 2 }

lmmPtpProvisionedOpenWaveRemoteTP     OBJECT-TYPE
    SYNTAX      DisplayString
    MAX-ACCESS  read-write
    STATUS      current
    DESCRIPTION ""
    ::= { lmmPtpEntry 3 }

-- Conformance Statements
lmmPtpConformance    OBJECT IDENTIFIER ::= { lmmPtpMIB 3 }
lmmPtpCompliances    OBJECT IDENTIFIER ::= { lmmPtpConformance 1 }
lmmPtpGroups         OBJECT IDENTIFIER ::= { lmmPtpConformance 2 }

lmmPtpCompliance MODULE-COMPLIANCE
    STATUS current
    DESCRIPTION
    "Describes the requirements for conformance to the LMM-MIB"
    MODULE
        MANDATORY-GROUPS { lmmPtpGroup }
    ::= { lmmPtpCompliances 1 }

lmmPtpGroup OBJECT-GROUP
    OBJECTS {

        lmmPtpRxProvNbrTP,
        lmmPtpTxProvNbrTP,
        lmmPtpProvisionedOpenWaveRemoteTP
}
    STATUS current
    DESCRIPTION
        " A collection of objects for managing the lmmPtp"
    ::= { lmmPtpGroups 1 }
END

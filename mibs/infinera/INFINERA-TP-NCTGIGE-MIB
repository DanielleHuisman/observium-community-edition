-- *****************************************************************
-- INFINERA-TP-NCTGIGE-MIB
-- 
-- October 2008, Sharfuddin Syed / Narendra Gupta
-- 
-- 
-- Copyright (c) 2008-2012 by Infinera Inc.
-- All rights reserved.
-- ****************************************************************

INFINERA-TP-NCTGIGE-MIB DEFINITIONS ::= BEGIN

IMPORTS
    MODULE-IDENTITY, OBJECT-TYPE,
    Integer32                                   FROM SNMPv2-SMI
    MODULE-COMPLIANCE, OBJECT-GROUP             FROM SNMPv2-CONF
    DisplayString                               FROM SNMPv2-TC
    ifIndex                                     FROM IF-MIB
    FloatTenths,InfnNctType,InfnChassisType     FROM INFINERA-TC-MIB
    terminationPoint                            FROM INFINERA-REG-MIB;


nctGigEMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 12 }



nctGigETable OBJECT-TYPE
    SYNTAX      SEQUENCE OF NctGigEEntry
    MAX-ACCESS  not-accessible
    STATUS      current
    DESCRIPTION
        "A list of NctGigE entries. Each entry is uniquely identified by the value of ifIndex."
    ::= { nctGigEMIB 1 } 

nctGigEEntry  OBJECT-TYPE
    SYNTAX      NctGigEEntry
    MAX-ACCESS  not-accessible
    STATUS      current
    DESCRIPTION
        "A NctGigE entry containing information pertaining to Infinera NctGigE interfaces
        This table is a subclass of IfCommon. Entries will exist in this table only for
        interfaces of type ChannelCtp."
    INDEX { ifIndex }
    ::= { nctGigETable 1 }


NctGigEEntry  ::= SEQUENCE {
    nctGigEPortType                INTEGER,
    nctGigEForwardingState         INTEGER,
    nctGigEPeerPortId              INTEGER,
    nctGigEPeerChassisSerNum       DisplayString,
    nctGigEPeerChassisId           DisplayString,
    nctGigEPeerMcmSlotNum          Integer32,
    nctGigEPeerChassisType         InfnChassisType,
    interfaceTypeNCT       		   InfnNctType
}

nctGigEPortType OBJECT-TYPE
    SYNTAX  INTEGER {
        none(1),
        nct(2),
        gige(3)
    }
    MAX-ACCESS  read-only
    STATUS      current
    DESCRIPTION "Identifies the NCT port."
    DEFVAL      { none }
    ::= { nctGigEEntry  1 }


nctGigEForwardingState OBJECT-TYPE
    SYNTAX  INTEGER {
        disabled(1),
        enabled(2),
        unknown(3)
    }
    MAX-ACCESS  read-only
    STATUS      current
    DESCRIPTION "Identifies the forwarding state of the port."
    DEFVAL      { unknown }
    ::= { nctGigEEntry  2 }


nctGigEPeerPortId OBJECT-TYPE
    SYNTAX  INTEGER {
        none(1),
        nct1(2),
        nct2(3),
        gige(4)
    }
    MAX-ACCESS  read-only
    STATUS      current
    DESCRIPTION "Identifies the peer NCT port ID."
    DEFVAL      { none }
    ::= { nctGigEEntry  3 }


nctGigEPeerChassisSerNum OBJECT-TYPE
    SYNTAX      DisplayString
    MAX-ACCESS  read-only
    STATUS      current
    DESCRIPTION "Serial number of the peer chassis to which the NCT cable is connected."
    ::= { nctGigEEntry  4 }


nctGigEPeerChassisId OBJECT-TYPE
    SYNTAX      DisplayString
    MAX-ACCESS  read-only
    STATUS      current
    DESCRIPTION "PeerChassisId"
    ::= { nctGigEEntry  5 }


nctGigEPeerMcmSlotNum OBJECT-TYPE
    SYNTAX      Integer32
    MAX-ACCESS  read-only
    STATUS      current
    DESCRIPTION "Slot number of the peer MCM."
    DEFVAL      { 0 }
    ::= { nctGigEEntry  6 }


nctGigEPeerChassisType OBJECT-TYPE
    SYNTAX  InfnChassisType 
    MAX-ACCESS  read-only
    STATUS      current
    DESCRIPTION "The peer chassis type."
    DEFVAL      { cBand }
    ::= { nctGigEEntry  7 }

interfaceTypeNCT  OBJECT-TYPE
    SYNTAX     InfnNctType
    MAX-ACCESS read-write
    STATUS     current
    DESCRIPTION 
		"Defines the default active physical interface for NCT port"
        
    ::= { nctGigEEntry 8 }

-- Conformance Statements
nctGigEConformance    OBJECT IDENTIFIER ::= { nctGigEMIB 3 }
nctGigECompliances    OBJECT IDENTIFIER ::= { nctGigEConformance 1 }
nctGigEGroups         OBJECT IDENTIFIER ::= { nctGigEConformance 2 }

nctGigECompliance MODULE-COMPLIANCE
    STATUS current
    DESCRIPTION
    "Describes the requirements for conformance to the NCTGIGE-MIB"
    MODULE
        MANDATORY-GROUPS { nctGigEGroup }
    ::= { nctGigECompliances 1 }

nctGigEGroup OBJECT-GROUP
    OBJECTS {
        nctGigEPortType,
        nctGigEForwardingState,
        nctGigEPeerPortId,
        nctGigEPeerChassisSerNum,
        nctGigEPeerChassisId,
        nctGigEPeerMcmSlotNum,
        nctGigEPeerChassisType,
        interfaceTypeNCT
    }
    STATUS current
    DESCRIPTION
        " A collection of objects for managing the nctGigE"
    ::= { nctGigEGroups 1 }


END

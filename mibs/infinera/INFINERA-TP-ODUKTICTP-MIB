-- *****************************************************************
-- INFINERA-TP-ODUKTICTP-MIB
-- 
-- Copyright (c) 2011-2012 by Infinera Inc.
-- All rights reserved.
-- ****************************************************************

INFINERA-TP-ODUKTICTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    InfnServiceType,InfnArc,InfnEnableDisable,
    InfnMonitoringMode                          FROM INFINERA-TC-MIB
    terminationPoint                            FROM INFINERA-REG-MIB;


oduiktClientCtpMIB MODULE-IDENTITY
    LAST-UPDATED  "201110200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201110200000Z"
    DESCRIPTION
        "First Version"
    ::= { terminationPoint 35 }



oduiktClientCtpTable OBJECT-TYPE
    SYNTAX      SEQUENCE OF OduiktClientCtpEntry

    MAX-ACCESS  not-accessible
    STATUS      current
    DESCRIPTION
        "A list of OduiktClientCtp entries. Each entry is uniquely identified by the value of ifIndex."
    ::= { oduiktClientCtpMIB 1 } 

oduiktClientCtpEntry  OBJECT-TYPE
    SYNTAX      OduiktClientCtpEntry
    MAX-ACCESS  not-accessible
    STATUS      current
    DESCRIPTION
        "A OduiktClientCtp entry containing information pertaining to Infinera OduiktClientCtp interfaces.
        Entries will exist in this table for interfaces of type oduiktclientCtp."
    INDEX { ifIndex , oduiktClientCtpTcmIdentifier}
    ::= { oduiktClientCtpTable 1 }


OduiktClientCtpEntry  ::= SEQUENCE {
    oduiktClientCtpTcmIdentifier		            Integer32,
    oduiktClientCtpSide		                    INTEGER,
    oduiktClientCtpConfiguredServiceType         InfnServiceType,
    oduiktClientCtpAlarmReportControl            InfnArc,
    oduiktClientCtpSupportingCircuitIdList       DisplayString,
    oduiktClientCtpMonitoringMode                InfnMonitoringMode,
    oduiktClientCtpDSThreshold                   Integer32,
    oduiktClientCtpTxTTI                         DisplayString,
    oduiktClientCtpExpectedSAPI                  DisplayString,
    oduiktClientCtpExpectedDAPI                  DisplayString,
    oduiktClientCtpTimDetMode                    INTEGER,
    oduiktClientCtpReceivedTTI                   DisplayString,
    oduiktClientCtpPmHistStatsEnable             INTEGER,
    
    oduiktClientCtpRxEb15MinutesTce              Integer32,
    oduiktClientCtpRxEbDayTce                    Integer32,
    oduiktClientCtpRxDs15MinutesTce              Integer32,
    oduiktClientCtpRxDsDayTce                    Integer32,
    oduiktClientCtpRxEbDayTceReporting           TruthValue,
    oduiktClientCtpRxEb15MinutesTceReporting     TruthValue,     
    oduiktClientCtpRxDsDayTceReporting           TruthValue,
    oduiktClientCtpRxDs15MinutesTceReporting     TruthValue,
    oduiktClientCtpSDThreshold                   Integer32,    
    oduiktClientCtpRxBei15MinutesTce		Counter64,
    oduiktClientCtpRxBeiDayTce			Counter64,
    oduiktClientCtpRxBei15MinutesTceReporting    TruthValue,
    oduiktClientCtpRxBeiDayTceReporting           TruthValue
}

oduiktClientCtpTcmIdentifier  OBJECT-TYPE
    SYNTAX      Integer32 (1..12)
    MAX-ACCESS  read-only
    STATUS      current
    DESCRIPTION "The TCM field identifier for this Tandem Connection Monitoring point. 
    This TCM identifier is used along with the Side identifier to explicitly formulate the AID of the 
    ODUikT Client CTP. 
    Note that out of the 6 values, a maximum of 3 can be active at any given time, each with one or both 
    sides (facility and/or terminal) active (e.g., there can be up to 12 ODUikT CTP object instances, but 
    only for 3 TCM IDs)."
    ::= { oduiktClientCtpEntry  1 }

oduiktClientCtpSide  OBJECT-TYPE
    SYNTAX  INTEGER {
    fac(1),
    term(2)
    }
    MAX-ACCESS  read-only
    STATUS      current
    DESCRIPTION "TThe TCM Side identifier for this Tandem Connection Monitoring point. 
    This TCM Side identifier is used along with the TCM identifier to explicitly formulate the AID of the 
    ODUikT Client CTP. For ODUk-based adaptation, TCMs can only be enabled on the Facility-side."
    ::= { oduiktClientCtpEntry  2 }

oduiktClientCtpConfiguredServiceType  OBJECT-TYPE
    SYNTAX  InfnServiceType
    MAX-ACCESS  read-only
    STATUS      current
    DESCRIPTION "The ODU Service type that is configured on this generic OduClientCtp managed object."
      ::= { oduiktClientCtpEntry 3 }

oduiktClientCtpAlarmReportControl  OBJECT-TYPE
    SYNTAX InfnArc
    MAX-ACCESS  read-write
    STATUS      current
    DESCRIPTION "  The Alarm Reporting Control Flag for the ODUikT Clients. "
    DEFVAL      { allowed }
    ::= { oduiktClientCtpEntry  4 }


oduiktClientCtpSupportingCircuitIdList   OBJECT-TYPE
    SYNTAX      DisplayString
    MAX-ACCESS  read-only
    STATUS      current
    DESCRIPTION "The Supporting Circuit ID List that is this client is using.  "
    ::= { oduiktClientCtpEntry   5 }

oduiktClientCtpMonitoringMode OBJECT-TYPE
    SYNTAX  InfnMonitoringMode
    MAX-ACCESS  read-write
    STATUS      current
    DESCRIPTION "Allowed Section Monitoring / Path  Monitoring / TCM Attribute Value(s)
        (For side corresponding to MonitoringMode) (Fac-Side/Term-Side)."      
    ::= { oduiktClientCtpEntry 6 }


oduiktClientCtpDSThreshold OBJECT-TYPE
    SYNTAX      Integer32 (1..100)
    MAX-ACCESS  read-write
    STATUS      current
    DESCRIPTION " This attribute indicates the threshold level for declaring a performance monitoring (PM) Second to be bad.
    A PM Second is declared bad if the percentage of detected error blocks in that second is greater than or equal to the specified threshold level. 
    This attribute maps to the DEGThr MIB of RFC-3591"
    DEFVAL      { 30 }
    ::= { oduiktClientCtpEntry  7 }


 
oduiktClientCtpTxTTI OBJECT-TYPE
    SYNTAX      DisplayString (SIZE(1..64))
    MAX-ACCESS  read-write
    STATUS      current
    DESCRIPTION
        " The TTI message that needs to be transmitted from Trib to Line direction. 
        This message is inserted only when the TribInsertTTI field is set to Enabled."
    ::= { oduiktClientCtpEntry  8 }

oduiktClientCtpExpectedSAPI OBJECT-TYPE
    SYNTAX      DisplayString  (SIZE(1..16))
    MAX-ACCESS  read-write
    STATUS      current
    DESCRIPTION
        " The Source Access Point Identifier that is expected in the Trib to Line direction. "
    ::= { oduiktClientCtpEntry   9 }

oduiktClientCtpExpectedDAPI OBJECT-TYPE
    SYNTAX      DisplayString  (SIZE(1..16))
    MAX-ACCESS  read-write
    STATUS      current
    DESCRIPTION
        " The Destination Access Point Identifier that is expected in the Trib to Line direction. "
    ::= { oduiktClientCtpEntry  10 }


oduiktClientCtpTimDetMode  OBJECT-TYPE
    SYNTAX  INTEGER {
    off(1),
    sapi(2),
    dapi(3),
    sapidapi(4)
    }
    MAX-ACCESS  read-write
    STATUS      current
    DESCRIPTION "This attribute is used to configure if the TIM-S alarm shall be reported on mismatch of Expected and Received TTI message.
    The following are the values and their meaning:
        OFF: TIM-S is not reported.
        DAPI: TIM-S is reported only if the DAPI message mismatch occurs. 
        SAPI: TIM-S is reported only if the SAPI message mismatch occurs.
        DAPISAPI: Either the DAPI or the SAPI messages are in a 
        mismatch state."
    DEFVAL      { off }
    ::= { oduiktClientCtpEntry 11 }

oduiktClientCtpReceivedTTI  OBJECT-TYPE
    SYNTAX      DisplayString (SIZE(1..64))
    MAX-ACCESS  read-only
    STATUS      current
    DESCRIPTION "The TTI message received from the side indicated by the AID of the ODUikT CTP. "
    ::= { oduiktClientCtpEntry  12 }

oduiktClientCtpPmHistStatsEnable OBJECT-TYPE
    SYNTAX  INTEGER {
        enabled(1),
        disabled(2)
        }
    MAX-ACCESS  read-write
    STATUS      current
    DESCRIPTION " Flag to enable or disable the collection of PMs on the side indicated by the AID of the ODUikT CTP."
    DEFVAL      { enabled }
    ::= { oduiktClientCtpEntry  13 }



oduiktClientCtpRxEb15MinutesTce  OBJECT-TYPE
    SYNTAX      Integer32
    MAX-ACCESS  read-write
    STATUS      current
    DESCRIPTION "Number of Error Block in received direction during 15 minutes interval."
    DEFVAL      { 1500 }
    ::= { oduiktClientCtpEntry  14 }


oduiktClientCtpRxEbDayTce OBJECT-TYPE
    SYNTAX      Integer32
    MAX-ACCESS  read-write
    STATUS      current
    DESCRIPTION "Number of Error Block in received direction during 24 hours interval."
    DEFVAL      { 15000 }
    ::= { oduiktClientCtpEntry  15 }


oduiktClientCtpRxDs15MinutesTce  OBJECT-TYPE
    SYNTAX      Integer32
    MAX-ACCESS  read-write
    STATUS      current
    DESCRIPTION "Number of Defect Seconds in received direction during 15 minutes interval."
    DEFVAL      { 120 }
    ::= { oduiktClientCtpEntry  16 }


oduiktClientCtpRxDsDayTce OBJECT-TYPE
    SYNTAX      Integer32
    MAX-ACCESS  read-write
    STATUS      current
    DESCRIPTION "Number of Defect Seconds in receive direction during 24 hours interval."
    DEFVAL      { 1200 }
    ::= { oduiktClientCtpEntry  17 }


oduiktClientCtpRxEbDayTceReporting OBJECT-TYPE
    SYNTAX      TruthValue
    MAX-ACCESS  read-write
    STATUS      current
    DESCRIPTION " Flag that enables/disables the reporting of RxEbDayTce threshold crossing."
    DEFVAL      { false }
    ::= { oduiktClientCtpEntry  18 }

oduiktClientCtpRxEb15MinutesTceReporting OBJECT-TYPE
    SYNTAX      TruthValue
    MAX-ACCESS  read-write
    STATUS      current
    DESCRIPTION "  Flag that enables/disables the reporting of RxEb15MinutesTce threshold crossing."
    DEFVAL      { false }
    ::= { oduiktClientCtpEntry  19 }

oduiktClientCtpRxDsDayTceReporting OBJECT-TYPE
    SYNTAX      TruthValue
    MAX-ACCESS  read-write
    STATUS      current
    DESCRIPTION " Flag that enables/disables the reporting of RxDsDayTce threshold crossing."
    DEFVAL      { false }
    ::= { oduiktClientCtpEntry  20 }

oduiktClientCtpRxDs15MinutesTceReporting OBJECT-TYPE
    SYNTAX      TruthValue
    MAX-ACCESS  read-write
    STATUS      current
    DESCRIPTION " Flag that enables/disables the reporting of RxDs15MinutesTce threshold crossing."
    DEFVAL      { false }
    ::= { oduiktClientCtpEntry  21 }

oduiktClientCtpSDThreshold  OBJECT-TYPE
    SYNTAX      Integer32 (2..10)
    MAX-ACCESS  read-write
    STATUS      current
    DESCRIPTION "This attribute indicates the threshold level for declaring a Degraded  Signal defect. 
    A Degraded Signal defect shall be declared if SDThreshold consecutive bad PM Seconds are detected.
    This attributes maps to the DEGM MIB of RFC-3591."
    DEFVAL      { 7 }
    ::= { oduiktClientCtpEntry  22 }

oduiktClientCtpRxBei15MinutesTce  OBJECT-TYPE
    SYNTAX     	Counter64
    MAX-ACCESS  read-write
    STATUS      current
    DESCRIPTION "This attribute indicates the threshold level for Received BEI counts for 15Min-interval"
    ::= { oduiktClientCtpEntry  23 }

oduiktClientCtpRxBeiDayTce  OBJECT-TYPE
    SYNTAX      Counter64
    MAX-ACCESS  read-write
    STATUS      current
    DESCRIPTION "This attribute indicates the threshold level for Received BEI counts for day-interval"
    ::= { oduiktClientCtpEntry  24 }

oduiktClientCtpRxBei15MinutesTceReporting OBJECT-TYPE
    SYNTAX      TruthValue
    MAX-ACCESS  read-write
    STATUS      current
    DESCRIPTION " Flag that enables/disables the reporting of RxBei15MinutesTce threshold crossing."
    DEFVAL      { false }
    ::= { oduiktClientCtpEntry  25 }

oduiktClientCtpRxBeiDayTceReporting OBJECT-TYPE
    SYNTAX      TruthValue
    MAX-ACCESS  read-write
    STATUS      current
    DESCRIPTION " Flag that enables/disables the reporting of RxBeiDay Tce threshold crossing."
    DEFVAL      { false }
    ::= { oduiktClientCtpEntry  26 }

-- Conformance Statements
oduiktClientCtpConformance    OBJECT IDENTIFIER ::= { oduiktClientCtpMIB 3 }
oduiktClientCtpCompliances    OBJECT IDENTIFIER ::= { oduiktClientCtpConformance 1 }
oduiktClientCtpGroups         OBJECT IDENTIFIER ::= { oduiktClientCtpConformance 2 }

oduiktClientCtpCompliance MODULE-COMPLIANCE
    STATUS current
    DESCRIPTION
    "Describes the requirements for conformance to the ODUIKTCLIENTCTP-MIB"
    MODULE
        MANDATORY-GROUPS { oduiktClientCtpGroup }
    ::= { oduiktClientCtpCompliances 1 }

oduiktClientCtpGroup OBJECT-GROUP
    OBJECTS {
    oduiktClientCtpTcmIdentifier,
    oduiktClientCtpSide,
    oduiktClientCtpConfiguredServiceType,
    oduiktClientCtpAlarmReportControl,
    oduiktClientCtpSupportingCircuitIdList,
    oduiktClientCtpMonitoringMode,
    oduiktClientCtpDSThreshold,

    oduiktClientCtpTxTTI      ,
    oduiktClientCtpExpectedSAPI,
    oduiktClientCtpExpectedDAPI,
    oduiktClientCtpTimDetMode  ,
    oduiktClientCtpReceivedTTI ,
    oduiktClientCtpPmHistStatsEnable,
    
    oduiktClientCtpRxEb15MinutesTce ,
    oduiktClientCtpRxEbDayTce,

    oduiktClientCtpRxDs15MinutesTce,
    oduiktClientCtpRxDsDayTce,

    oduiktClientCtpRxEbDayTceReporting,
    oduiktClientCtpRxEb15MinutesTceReporting ,     

    oduiktClientCtpRxDsDayTceReporting,
    oduiktClientCtpRxDs15MinutesTceReporting,
    oduiktClientCtpSDThreshold ,
    oduiktClientCtpRxBei15MinutesTce,				
    oduiktClientCtpRxBeiDayTce,					
    oduiktClientCtpRxBei15MinutesTceReporting,    
    oduiktClientCtpRxBeiDayTceReporting     
    }
    STATUS current
    DESCRIPTION
        " A collection of objects for managing the oduiktClientCtp"
    ::= { oduiktClientCtpGroups 1 }


END

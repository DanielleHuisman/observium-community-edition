-- *****************************************************************
-- INFINERA-TP-OFXSCGPTP-MIB
-- Copyright (c) 2008-2012 by Infinera Inc.
-- All rights reserved.
-- ****************************************************************

INFINERA-TP-OFXSCGPTP-MIB DEFINITIONS ::= BEGIN

IMPORTS
    MODULE-IDENTITY, OBJECT-TYPE                FROM SNMPv2-SMI
    MODULE-COMPLIANCE, OBJECT-GROUP             FROM SNMPv2-CONF
    DisplayString, TruthValue                   FROM SNMPv2-TC
    ifIndex                                     FROM IF-MIB
    InfnEnableDisable, InfnEncoding,
    FloatTenths,InfnEqptType,InfnOperatingMode,
    FloatHundredths                             FROM INFINERA-TC-MIB
    terminationPoint                            FROM INFINERA-REG-MIB;

ofxScgPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 42 }

ofxScgPtpTable OBJECT-TYPE
    SYNTAX      SEQUENCE OF OfxScgPtpEntry
    MAX-ACCESS  not-accessible
    STATUS      current
    DESCRIPTION
        "A list of OfxScgPtp entries. Each entry is uniquely identified by the value of ifIndex."
    ::= { ofxScgPtpMIB 1 } 

ofxScgPtpEntry  OBJECT-TYPE
    SYNTAX      OfxScgPtpEntry
    MAX-ACCESS  not-accessible
    STATUS      current
    DESCRIPTION
        "A OfxScgPtp entry containing information pertaining to Infinera OfxScgPtp Interfaces.
        This table is a subclass of IfCommon. Entries will exist in this table only for
        interfaces of type DLM OCG PTP."
    INDEX { ifIndex }
    ::= { ofxScgPtpTable 1 }


OfxScgPtpEntry  ::= SEQUENCE {
    ofxScgPtpPowerControlLoop       InfnEnableDisable,
    ofxScgPtpProvEncodingMode       InfnEncoding,
    ofxScgPtpLineSystemMode         INTEGER,
    ofxScgPtpInstalledEncodingMode  InfnEncoding,
    ofxScgPtpRxPowerOffset          FloatHundredths,
    ofxScgPtpProvisionedPeerTp      DisplayString,
    ofxScgPtpOpenwaveTargetTxScgPower FloatTenths,
    ofxScgPtpCarrierCount           FloatHundredths,
    ofxScgPtpOperatingMode          InfnOperatingMode,
    ofxScgPtpUnAssignedCarrierList  DisplayString
}

ofxScgPtpPowerControlLoop OBJECT-TYPE
    SYNTAX      InfnEnableDisable
    MAX-ACCESS  read-write
    STATUS      current
    DESCRIPTION ""
    ::= { ofxScgPtpEntry  1 }

ofxScgPtpProvEncodingMode   OBJECT-TYPE
    SYNTAX      InfnEncoding
    MAX-ACCESS  read-write
    STATUS      current
    DESCRIPTION ""
    ::= { ofxScgPtpEntry  2 }

ofxScgPtpLineSystemMode OBJECT-TYPE
    SYNTAX      INTEGER {
        modeOcg(1),
        modeOpenWave(2),
        modeScg(3),
        modeScgPassiveMux1 (4)
    }
    MAX-ACCESS  read-write
    STATUS      current
    DESCRIPTION ""
    ::= { ofxScgPtpEntry  3 }


ofxScgPtpInstalledEncodingMode  OBJECT-TYPE
    SYNTAX      InfnEncoding
    MAX-ACCESS  read-write
    STATUS      current
    DESCRIPTION ""
    ::= { ofxScgPtpEntry  4 }

ofxScgPtpRxPowerOffset  OBJECT-TYPE
    SYNTAX  FloatHundredths
    MAX-ACCESS  read-write
    STATUS      current
    DESCRIPTION ""
    ::= { ofxScgPtpEntry 5 }

ofxScgPtpProvisionedPeerTp OBJECT-TYPE
    SYNTAX   DisplayString
    MAX-ACCESS  read-write
    STATUS      current
    DESCRIPTION ""
    ::= { ofxScgPtpEntry 6 }

ofxScgPtpOpenwaveTargetTxScgPower OBJECT-TYPE
    SYNTAX  FloatTenths
    MAX-ACCESS  read-write
    STATUS      current
    DESCRIPTION ""
    ::= { ofxScgPtpEntry 7 }
    
ofxScgPtpCarrierCount  OBJECT-TYPE
    SYNTAX  FloatHundredths 
    MAX-ACCESS  read-write
    STATUS      current
    DESCRIPTION ""
    ::= { ofxScgPtpEntry 8 }

ofxScgPtpOperatingMode  OBJECT-TYPE
    SYNTAX      InfnOperatingMode
    MAX-ACCESS  read-write
    STATUS      current
    DESCRIPTION ""
    ::= { ofxScgPtpEntry  9 }

ofxScgPtpUnAssignedCarrierList OBJECT-TYPE
    SYNTAX   DisplayString
    MAX-ACCESS  read-only
    STATUS      current
    DESCRIPTION ""
    ::= { ofxScgPtpEntry 10 }

-- Conformance Statements
ofxScgPtpConformance    OBJECT IDENTIFIER ::= { ofxScgPtpMIB 3 }
ofxScgPtpCompliances    OBJECT IDENTIFIER ::= { ofxScgPtpConformance 1 }
ofxScgPtpGroups         OBJECT IDENTIFIER ::= { ofxScgPtpConformance 2 }

ofxScgPtpCompliance MODULE-COMPLIANCE
    STATUS current
    DESCRIPTION
    "Describes the requirements for conformance to the OFXSCGPTP-MIB"
    MODULE
        MANDATORY-GROUPS { ofxScgPtpGroup }
    ::= { ofxScgPtpCompliances 1 }

ofxScgPtpGroup OBJECT-GROUP
    OBJECTS {
        ofxScgPtpPowerControlLoop, 
        ofxScgPtpProvEncodingMode,     
        ofxScgPtpLineSystemMode,     
        ofxScgPtpInstalledEncodingMode,
        ofxScgPtpRxPowerOffset,
        ofxScgPtpProvisionedPeerTp,
        ofxScgPtpOpenwaveTargetTxScgPower,
        ofxScgPtpCarrierCount,
        ofxScgPtpOperatingMode,
        ofxScgPtpUnAssignedCarrierList 
    }
    STATUS current
    DESCRIPTION
        " A collection of objects for managing the ofxScgPtp"
    ::= { ofxScgPtpGroups 1 }
END

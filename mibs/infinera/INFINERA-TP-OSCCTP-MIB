-- *****************************************************************
-- INFINERA-TP-OSCCTP-MIB
-- 
-- October 2008, Sharfuddin Syed / Narendra Gupta
-- 
-- 
-- Copyright (c) 2008-2012 by Infinera Inc.
-- All rights reserved.
-- ****************************************************************

INFINERA-TP-OSCCTP-MIB DEFINITIONS ::= BEGIN

IMPORTS
    OBJECT-TYPE, MODULE-IDENTITY, Integer32        FROM SNMPv2-SMI
    OBJECT-GROUP, MODULE-COMPLIANCE                FROM SNMPv2-CONF
    TruthValue                                     FROM SNMPv2-TC
    ifIndex                                        FROM IF-MIB
    terminationPoint                               FROM INFINERA-REG-MIB
    InfnAdminState                                 FROM INFINERA-TC-MIB
    InetAddress, InetAddressType                   FROM INET-ADDRESS-MIB;

oscCtpMIB MODULE-IDENTITY
    LAST-UPDATED  "200810200000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "

    REVISION  "200810200000Z"
    DESCRIPTION 
        "First Version"
::= { terminationPoint 13 }


-- Conformance Statements

oscCtpConformance    OBJECT IDENTIFIER ::= { oscCtpMIB 3 }
oscCtpCompliances    OBJECT IDENTIFIER ::= { oscCtpConformance 1 }
oscCtpGroups         OBJECT IDENTIFIER ::= { oscCtpConformance 2 }

oscCtpTable  OBJECT-TYPE
    SYNTAX SEQUENCE OF OscCtpEntry
    MAX-ACCESS not-accessible
    STATUS     current
    DESCRIPTION 
        "A list of OscCtp entries. Each entry is uniquely identified by the value of ifIndex."
    ::= { oscCtpMIB 1 }

oscCtpEntry  OBJECT-TYPE
    SYNTAX     OscCtpEntry
    MAX-ACCESS not-accessible
    STATUS     current
    DESCRIPTION 
        "A OscCtp entry containing information pertaining to Infinera OscCtp interfaces.
                This table is a subclass of IfCommon. Entries will exist in this table only for interfaces
                of type OSC CTP."
    INDEX { ifIndex }
    ::= { oscCtpTable 1 }

OscCtpEntry ::= SEQUENCE {
    oscCtpOscIpAddressType                     InetAddressType,
    oscCtpOscIpAddress                         InetAddress,
    oscCtpOscNetmask                           InetAddress,
    oscCtpOscIpIfAdminState                    InfnAdminState,
    oscCtpOspfCost                             Integer32,
    oscCtpTECost                               Integer32,
    oscCtpOspfHelloInterval                    Integer32,
    oscCtpOspfArea                             InetAddress,
    oscCtpOspfDeadInterval                     Integer32,
    oscCtpOspfInstanceId                       Integer32,
    oscCtpOspfRoutingEnabled                   TruthValue,
    oscCtpPmHistStatsEnable                    INTEGER
}

oscCtpOscIpAddressType  OBJECT-TYPE
    SYNTAX     InetAddressType
    MAX-ACCESS read-write
    STATUS     current
    DESCRIPTION 
        "The type of the oscCtpOscIpAddress, oscCtpOscNetmask and oscCtpOspfArea addresses as defined in the
                InetAddress MIB."
    ::= { oscCtpEntry 1 }

oscCtpOscIpAddress  OBJECT-TYPE
    SYNTAX     InetAddress
    MAX-ACCESS read-write
    STATUS     current
    DESCRIPTION 
        "IP address of interface. IP address of this OSM for OSC communication. This IP is assigned by the
                user and is unique within a signaling domain. "
    ::= { oscCtpEntry 2 }

oscCtpOscNetmask  OBJECT-TYPE
    SYNTAX     InetAddress
    MAX-ACCESS read-write
    STATUS     current
    DESCRIPTION 
        "The net mask for the Osc IpAddress."
    ::= { oscCtpEntry 3 }

oscCtpOscIpIfAdminState  OBJECT-TYPE
    SYNTAX     InfnAdminState
    MAX-ACCESS read-write
    STATUS     current
    DESCRIPTION 
        ""
    ::= { oscCtpEntry 4 }

oscCtpOspfCost  OBJECT-TYPE
    SYNTAX     Integer32 (1..255)
    MAX-ACCESS read-write
    STATUS     obsolete
    DESCRIPTION 
        "This attribute identifies the cost associated with using this link. This is the control plane
                OSPF cost. he higher the number, less desirable the link. This is an attribute that can be set
                by the user using the OSC TP."
    DEFVAL  { 100 }
    ::= { oscCtpEntry 5 }

oscCtpTECost  OBJECT-TYPE
    SYNTAX     Integer32
    MAX-ACCESS read-write
    STATUS     obsolete
    DESCRIPTION 
        "This attribute identifies the cost associated with using the TE links associated with the
                corresponding control link/OSC."
    DEFVAL  { 100 }
    ::= { oscCtpEntry 6 }

oscCtpOspfHelloInterval  OBJECT-TYPE
    SYNTAX     Integer32 (10..1200)
    UNITS     "seconds"
    MAX-ACCESS read-write
    STATUS     obsolete
    DESCRIPTION 
        "OspfHelloInterval.  This value cannot be changed when GMPLS is enabled. GMPLS must be disabled
                to change the value and then re-enabled."
    DEFVAL  { 30 }
    ::= { oscCtpEntry 7 }

oscCtpOspfArea  OBJECT-TYPE
    SYNTAX     InetAddress
    MAX-ACCESS read-only
    STATUS     obsolete
    DESCRIPTION 
        "The OSPF area and is currently set to 1. This attribute is for future use."
    ::= { oscCtpEntry 8 }

oscCtpOspfDeadInterval  OBJECT-TYPE
    SYNTAX     Integer32 (30..3600)
    UNITS     "seconds"
    MAX-ACCESS read-write
    STATUS     obsolete
    DESCRIPTION 
        "OspfDeadInterval. Should be at least 3 times the oscCtpOspfHelloInterval. This value cannot be changed when GMPLS is
                enabled. GMPLS must be disabled to change the value and then re-enabled."
    DEFVAL  { 300 }
    ::= { oscCtpEntry 9 }

oscCtpOspfInstanceId  OBJECT-TYPE
    SYNTAX     Integer32
    MAX-ACCESS read-only
    STATUS     obsolete
    DESCRIPTION 
        "This is the OSPF Instance ID and is currently set to 1. This attribute is for future use."
    ::= { oscCtpEntry 10 }

oscCtpOspfRoutingEnabled  OBJECT-TYPE
    SYNTAX     TruthValue
    MAX-ACCESS read-write
    STATUS     obsolete
    DESCRIPTION 
        "Flag to enable/disable GMPLS."
    DEFVAL  { false }
    ::= { oscCtpEntry 11 }

oscCtpPmHistStatsEnable  OBJECT-TYPE
    SYNTAX     INTEGER {
        enabled (1),
        disabled (2)
    }
    MAX-ACCESS read-write
    STATUS     current
    DESCRIPTION 
        "Flag to enable or disable PM collection."
    DEFVAL  { enabled }
    ::= { oscCtpEntry 12 }

oscCtpCompliance  MODULE-COMPLIANCE
    STATUS     current
    DESCRIPTION 
        "Describes the requirements for conformance to the OSCCTP-MIB"
    MODULE
        MANDATORY-GROUPS { oscCtpGroup } 
    ::= { oscCtpCompliances 1 }

oscCtpGroup  OBJECT-GROUP
    OBJECTS { oscCtpOscIpAddressType, 
        oscCtpOscIpAddress, 
        oscCtpOscNetmask, 
        oscCtpOspfCost, 
        oscCtpTECost, 
        oscCtpOspfHelloInterval, 
        oscCtpOspfArea, 
        oscCtpOspfDeadInterval, 
        oscCtpOspfInstanceId, 
        oscCtpOspfRoutingEnabled, 
        oscCtpPmHistStatsEnable }
    STATUS     current
    DESCRIPTION 
        " A collection of objects for managing the oscCtp"
    ::= { oscCtpGroups 1 }
END

-- This MIB was created using NuDesign Team's Visual MIBuilder (Ver 4.7).

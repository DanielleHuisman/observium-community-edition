-- *****************************************************************
-- INFINERA-TP-OSCTCTP-MIB
-- 
-- October 2008, Sharfuddin Syed / Narendra Gupta
-- 
-- 
-- Copyright (c) 2008-2012 by Infinera Inc.
-- All rights reserved.
-- ****************************************************************

INFINERA-TP-OSCTCTP-MIB DEFINITIONS ::= BEGIN

IMPORTS
    OBJECT-TYPE, MODULE-IDENTITY, Integer32        FROM SNMPv2-SMI
    OBJECT-GROUP, MODULE-COMPLIANCE                FROM SNMPv2-CONF
    ifIndex                                        FROM IF-MIB
    terminationPoint                               FROM INFINERA-REG-MIB;
    
osctCtpMIB MODULE-IDENTITY
    LAST-UPDATED  "200903250000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "

    REVISION  "200903250000Z"
    DESCRIPTION 
        "First Version"
::= { terminationPoint 11 }


-- Conformance Statements

osctCtpConformance    OBJECT IDENTIFIER ::= { osctCtpMIB 3 }
osctCtpCompliances    OBJECT IDENTIFIER ::= { osctCtpConformance 1 }
osctCtpGroups         OBJECT IDENTIFIER ::= { osctCtpConformance 2 }

osctCtpTable  OBJECT-TYPE
    SYNTAX SEQUENCE OF OsctCtpEntry
    MAX-ACCESS not-accessible
    STATUS     current
    DESCRIPTION 
        "A list of OsctCtp entries. Each entry is uniquely identified by the value of ifIndex."
    ::= { osctCtpMIB 1 }

osctCtpEntry  OBJECT-TYPE
    SYNTAX     OsctCtpEntry
    MAX-ACCESS not-accessible
    STATUS     current
    DESCRIPTION 
        "A OsctCtp entry containing information pertaining to Infinera OsctCtp interfaces.
                This table is a subclass of IfCommon. Entries will exist in this table only for interfaces
                of type OSCT CTP."
    INDEX { ifIndex }
    ::= { osctCtpTable 1 }

OsctCtpEntry ::= SEQUENCE {
   
    osctCtpPmHistStatsEnable                    INTEGER
}

osctCtpPmHistStatsEnable  OBJECT-TYPE
    SYNTAX     INTEGER {
        enabled (1),
        disabled (2)
    }
    MAX-ACCESS read-write
    STATUS     current
    DESCRIPTION 
        "Flag to enable or disable PM collection."
    DEFVAL  { enabled }
    ::= { osctCtpEntry 1 }
    
    osctCtpGroup  OBJECT-GROUP
    OBJECTS { osctCtpPmHistStatsEnable }
    STATUS     current
    DESCRIPTION 
        " A collection of objects for managing the osctCtp"
    ::= { osctCtpGroups 1 }
END

-- *****************************************************************
-- INFINERA-TP-OTUCLIENTCTP-MIB
-- Copyright (c) 2008-2012 by Infinera Inc.
-- All rights reserved.
-- ****************************************************************

INFINERA-TP-OTUCLIENTCTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    InfnServiceType,InfnEqptType,InfnArc,
    InfnEnableDisable,InfnLoopbackType,
    InfnMonitoringMode,InfnSMQ,InfnServiceMode
                                                FROM INFINERA-TC-MIB
    terminationPoint                            FROM INFINERA-REG-MIB;


otuClientCtpMIB MODULE-IDENTITY
    LAST-UPDATED  "200904200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200904200000Z"
    DESCRIPTION
        "First Version"
    ::= { terminationPoint 25 }



otuClientCtpTable OBJECT-TYPE
    SYNTAX      SEQUENCE OF OtuClientCtpEntry
    MAX-ACCESS  not-accessible
    STATUS      current
    DESCRIPTION
        "A list of OtuClientCtp entries. Each entry is uniquely identified by the value of ifIndex."
    ::= { otuClientCtpMIB 1 } 

otuClientCtpEntry  OBJECT-TYPE
    SYNTAX      OtuClientCtpEntry
    MAX-ACCESS  not-accessible
    STATUS      current
    DESCRIPTION
        "A OtuClientCtp entry containing information pertaining to Infinera OtuClientCtp interfaces.
        Entries will exist in this table for interfaces of type otuclientCtp."
    INDEX { ifIndex }
    ::= { otuClientCtpTable 1 }


OtuClientCtpEntry  ::= SEQUENCE {
    otuClientCtpFacPrbsGenMode                  InfnEnableDisable,
    otuClientCtpFacPrbsMonMode                  InfnEnableDisable,
    otuClientCtpServiceMode                     InfnServiceMode,
    otuClientCtpServiceModeQualifier            InfnSMQ,
    otuClientCtpFecCorrection                   InfnEnableDisable,
    otuClientCtpFecEnabled                      InfnEnableDisable,

    otuClientCtpTermTxTTI                       DisplayString,
    otuClientCtpTermExpectedSAPI                DisplayString,
    otuClientCtpTermExpectedDAPI                DisplayString,

    otuClientCtpFacTxTTI                        DisplayString,
    otuClientCtpFacExpectedSAPI                 DisplayString,
    otuClientCtpFacExpectedDAPI                 DisplayString,

    otuClientCtpTermReceivedTTI                 DisplayString,
    otuClientCtpFacReceivedTTI                  DisplayString,

    otuClientCtpTermTimDetMode                  INTEGER,
    otuClientCtpFacTimDetMode                   INTEGER,

    otuClientCtpRxEb15MinutesTce                Integer32,
    otuClientCtpTxEb15MinutesTce                Integer32,
    otuClientCtpRxEbDayTce                      Integer32,
    otuClientCtpTxEbDayTce                      Integer32,

    otuClientCtpRxDs15MinutesTce                Integer32,
    otuClientCtpTxDs15MinutesTce                Integer32,
    otuClientCtpRxDsDayTce                      Integer32,
    otuClientCtpTxDsDayTce                      Integer32,

    otuClientCtpRxEbDayTceReporting             TruthValue,
    otuClientCtpRxEb15MinutesTceReporting       TruthValue,     
    otuClientCtpTxEbDayTceReporting             TruthValue,
    otuClientCtpTxEb15MinutesTceReporting       TruthValue,     

    otuClientCtpRxDsDayTceReporting             TruthValue,
    otuClientCtpRxDs15MinutesTceReporting       TruthValue,     
    otuClientCtpTxDsDayTceReporting             TruthValue,
    otuClientCtpTxDs15MinutesTceReporting       TruthValue,

    otuClientCtpConfiguredServiceType           InfnServiceType,
    otuClientCtpTamType                         InfnEqptType,
    otuClientCtpLoopback                        InfnLoopbackType,
    
    otuClientCtpFacPmHistStatsEnable            InfnEnableDisable,
    otuClientCtpTermPmHistStatsEnable           InfnEnableDisable,
    
    otuClientCtpAlarmReportControl              InfnArc,
    otuClientCtpSupportingCircuitIdList         DisplayString,
    
    otuClientCtpFacDSThreshold                  Integer32,
   -- otuClientCtpFacSDThreshold                  Integer32,
    otuClientCtpTermDSThreshold                 Integer32,
   -- otuClientCtpTermSDThreshold                 Integer32,
    
    otuClientCtpTermPrbsGenMode                 InfnEnableDisable,
    otuClientCtpTermPrbsMonMode                 InfnEnableDisable,
    
    otuClientCtpFacMonitoringMode               InfnMonitoringMode,
    otuClientCtpTermMonitoringMode              InfnMonitoringMode,

    otuClientCtpRxBei15MinutesTce                Integer32,
    otuClientCtpTxBei15MinutesTce                Integer32,
    otuClientCtpRxBeiDayTce                      Integer32,
    otuClientCtpTxBeiDayTce                      Integer32,

    otuClientCtpRxBeiDayTceReporting             TruthValue,
    otuClientCtpRxBei15MinutesTceReporting       TruthValue,     
    otuClientCtpTxBeiDayTceReporting             TruthValue,
    otuClientCtpTxBei15MinutesTceReporting       TruthValue
    
}

otuClientCtpFacPrbsGenMode OBJECT-TYPE
    SYNTAX  InfnEnableDisable
    MAX-ACCESS  read-write
    STATUS      current
    DESCRIPTION "  This atTermute is used to enable or disable the generation of a PRBS test pattern toward the Facility 
                side (e.g., toward the client interface). "
    DEFVAL      { disabled }
    ::= { otuClientCtpEntry  1 }


otuClientCtpFacPrbsMonMode OBJECT-TYPE
    SYNTAX  InfnEnableDisable
    MAX-ACCESS  read-write
    STATUS      current
    DESCRIPTION " This atTermute is used to enable or disable the monitoring of a PRBS test pattern coming from 
                the Facility side (e.g., from the client interface)."
    DEFVAL      { disabled }
    ::= { otuClientCtpEntry  2 }

otuClientCtpServiceMode OBJECT-TYPE
    SYNTAX  InfnServiceMode
    MAX-ACCESS  read-only
    STATUS      current
    DESCRIPTION "'None’ is the default value indicated for the OTU client CTP when it is initially created. 
     OTUk alarms, loopbacks/diagnostics, PMs, etc. are intended to be supported in alignment with pre-R6 support for 
     similar SONET/SDH CTPs. See also Fac/TermMonitoringMode"
    DEFVAL      { none }
    ::= { otuClientCtpEntry  3 }

otuClientCtpServiceModeQualifier  OBJECT-TYPE
    SYNTAX      InfnSMQ
    MAX-ACCESS  read-only
    STATUS      current
    DESCRIPTION "The Service Mode Qualifier (SMQ) of the ODU client CTP (i.e., the mode/type of service in which 
        this ODU client CTP is being used,). None’ is the default value indicated for the OTU client CTP when it is initially created.
        Value is set as a result of service provisioning (see Xcon and SNC provisioning). Allowed value is dependent on the Configured Service Type and 
        the Service Mode (which are also the result of service provisioning)"
    DEFVAL      { none }
    ::= { otuClientCtpEntry  4 }


otuClientCtpFecCorrection OBJECT-TYPE
    SYNTAX  InfnEnableDisable
    MAX-ACCESS  read-write
    STATUS      current
    DESCRIPTION "This atTermute is used to enable or disable the FEC correction at the ingress of the OTU client facility.
    When Disabled, the FEC statistics are still provided. Applicable to:All OtuClientCtp."
    DEFVAL      { enabled }
    ::= { otuClientCtpEntry  5 }

otuClientCtpFecEnabled OBJECT-TYPE
    SYNTAX  InfnEnableDisable
    MAX-ACCESS  read-write
    STATUS      current
    DESCRIPTION "This atTermute is used to enable or disable the G.709 Fec Generation 
        and handling on the OTU Term interface. If the FECEnabled is FALSE, all zeroes are inserted on the FEC overhead signal. 
        Similarly, a OTU Term interfaces receiving the Zero FEC signal, will not be able to detect or correct errors"
    DEFVAL      { enabled }
    ::= { otuClientCtpEntry  6 }



otuClientCtpTermTxTTI OBJECT-TYPE
    SYNTAX      DisplayString (SIZE(1..64))
    MAX-ACCESS  read-write
    STATUS      current
    DESCRIPTION "The TTI message that needs to be transmitted in the Terminal direction (e.g., from Trib to Line 
    direction). "
    ::= { otuClientCtpEntry  7 }

otuClientCtpTermExpectedSAPI OBJECT-TYPE
    SYNTAX      DisplayString (SIZE(1..16))
    MAX-ACCESS  read-write
    STATUS      current
    DESCRIPTION "The Source Access Point Identifier that is expected from the Terminal side 
    (e.g., in the Line  to Trib direction). "
    ::= { otuClientCtpEntry  8 }

otuClientCtpTermExpectedDAPI OBJECT-TYPE
    SYNTAX      DisplayString (SIZE(1..16))
    MAX-ACCESS  read-write
    STATUS      current
    DESCRIPTION " The Destination Access Point Identifier that is expected from the Terminal side 
    (e.g., in the Line to Trib direction). "
    ::= { otuClientCtpEntry  9 }


otuClientCtpFacTxTTI OBJECT-TYPE
    SYNTAX      DisplayString (SIZE(1..64))
    MAX-ACCESS  read-write
    STATUS      current
    DESCRIPTION "The TTI message that needs to be transmitted in the Facility direction (e.g., from Line to Trib direction)."
    ::= { otuClientCtpEntry  10 }

otuClientCtpFacExpectedSAPI OBJECT-TYPE
    SYNTAX      DisplayString (SIZE(1..16))
    MAX-ACCESS  read-write 
    STATUS      current
    DESCRIPTION "The Source Access Point Identifier that is expected from the Facility side (e.g., Trib to Line direction). "
    ::= { otuClientCtpEntry  11 }

otuClientCtpFacExpectedDAPI OBJECT-TYPE
    SYNTAX      DisplayString (SIZE(1..16))
    MAX-ACCESS  read-write
    STATUS      current
    DESCRIPTION "The Destination Access Point Identifier that is expected from the Facility side (e.g., Trib to Line direction) "
    ::= { otuClientCtpEntry  12 }

otuClientCtpTermReceivedTTI  OBJECT-TYPE
    SYNTAX      DisplayString (SIZE(1..64))
    MAX-ACCESS  read-only
    STATUS      current
    DESCRIPTION "The TTI message received from the Terminal side (e.g., in the Line to Trib direction) of an OTU 
                 Trib Interface. "
    ::= { otuClientCtpEntry  13 }

otuClientCtpFacReceivedTTI  OBJECT-TYPE
    SYNTAX      DisplayString (SIZE(1..64))
    MAX-ACCESS  read-only
    STATUS      current
    DESCRIPTION "The TTI message received from the Facility side (e.g., in the Trib to Line direction) of an OTU 
                 Trib Interface.  "
    ::= { otuClientCtpEntry  14 }


otuClientCtpRxEb15MinutesTce  OBJECT-TYPE
    SYNTAX      Integer32
    MAX-ACCESS  read-write
    STATUS      current
    DESCRIPTION "Number of ErrorBlock in receive direction during 15 minutes interval."
    DEFVAL      { 1500 }
    ::= { otuClientCtpEntry  15 }

otuClientCtpTxEb15MinutesTce  OBJECT-TYPE
    SYNTAX      Integer32
    MAX-ACCESS  read-write
    STATUS      current
    DESCRIPTION "Number of ErrorBlock in transmit direction during 15 minutes interval."
    DEFVAL      { 1500 }
    ::= { otuClientCtpEntry  16 }

otuClientCtpRxEbDayTce OBJECT-TYPE
    SYNTAX      Integer32
    MAX-ACCESS  read-write
    STATUS      current
    DESCRIPTION "Number of ErrorBlock in receive direction during 24 hours interval."
    DEFVAL      { 15000 }
    ::= { otuClientCtpEntry  17 }

otuClientCtpTxEbDayTce OBJECT-TYPE
    SYNTAX      Integer32
    MAX-ACCESS  read-write
    STATUS      current
    DESCRIPTION "Number of ErrorBlock in transmit direction during 24 hours interval."
    DEFVAL      { 15000 }
    ::= { otuClientCtpEntry  18 }

otuClientCtpRxDs15MinutesTce  OBJECT-TYPE
    SYNTAX      Integer32
    MAX-ACCESS  read-write
    STATUS      current
    DESCRIPTION "Number of Defect Seconds in receive direction during 15 minutes interval."
    DEFVAL      { 120 }
    ::= { otuClientCtpEntry  19 }

otuClientCtpTxDs15MinutesTce  OBJECT-TYPE
    SYNTAX      Integer32
    MAX-ACCESS  read-write
    STATUS      current
    DESCRIPTION "Number of Defect Seconds in transmit direction during 15 minutes interval."
    DEFVAL      { 120 }
    ::= { otuClientCtpEntry  20 }

otuClientCtpRxDsDayTce OBJECT-TYPE
    SYNTAX      Integer32
    MAX-ACCESS  read-write
    STATUS      current
    DESCRIPTION "Number of Defect Seconds in receive direction during 24 hours interval."
    DEFVAL      { 1200 }
    ::= { otuClientCtpEntry  21 }

otuClientCtpTxDsDayTce OBJECT-TYPE
    SYNTAX      Integer32
    MAX-ACCESS  read-write
    STATUS      current
    DESCRIPTION "Number of Defect Seconds in transmit direction during 24 hours interval."
    DEFVAL      { 1200 }
    ::= { otuClientCtpEntry  22 }


otuClientCtpRxEbDayTceReporting OBJECT-TYPE
    SYNTAX      TruthValue
    MAX-ACCESS  read-write
    STATUS      current
    DESCRIPTION " Flag that enables/disables the reporting of RxEbDayTce threshold crossing."
    DEFVAL      { false }
    ::= { otuClientCtpEntry  23 }

otuClientCtpRxEb15MinutesTceReporting OBJECT-TYPE
    SYNTAX      TruthValue
    MAX-ACCESS  read-write
    STATUS      current
    DESCRIPTION "  Flag that enables/disables the reporting of RxEb15MinutesTce threshold crossing."
    DEFVAL      { false }
    ::= { otuClientCtpEntry  24 }

otuClientCtpTxEbDayTceReporting OBJECT-TYPE
    SYNTAX      TruthValue
    MAX-ACCESS  read-write
    STATUS      current
    DESCRIPTION " Flag that enables/disables the reporting of TxEbDayTce threshold crossing."
    DEFVAL      { false }
    ::= { otuClientCtpEntry  25 }

otuClientCtpTxEb15MinutesTceReporting OBJECT-TYPE
    SYNTAX      TruthValue
    MAX-ACCESS  read-write
    STATUS      current
    DESCRIPTION " Flag that enables/disables the reporting of TxEb15MinutesTce threshold crossing."
    DEFVAL      { false }
    ::= { otuClientCtpEntry  26 }

otuClientCtpRxDsDayTceReporting OBJECT-TYPE
    SYNTAX      TruthValue
    MAX-ACCESS  read-write
    STATUS      current
    DESCRIPTION " Flag that enables/disables the reporting of RxDsDayTce threshold crossing."
    DEFVAL      { false }
    ::= { otuClientCtpEntry  27 }

otuClientCtpRxDs15MinutesTceReporting OBJECT-TYPE
    SYNTAX      TruthValue
    MAX-ACCESS  read-write
    STATUS      current
    DESCRIPTION " Flag that enables/disables the reporting of RxDs15MinutesTce threshold crossing."
    DEFVAL      { false }
    ::= { otuClientCtpEntry  28 }

otuClientCtpTxDsDayTceReporting OBJECT-TYPE
    SYNTAX      TruthValue
    MAX-ACCESS  read-write
    STATUS      current
    DESCRIPTION " Flag that enables/disables the reporting of RxDsDayTce threshold crossing."
    DEFVAL      { false }
    ::= { otuClientCtpEntry  29 }

otuClientCtpTxDs15MinutesTceReporting OBJECT-TYPE
    SYNTAX      TruthValue
    MAX-ACCESS  read-write
    STATUS      current
    DESCRIPTION " Flag that enables/disables the reporting of RxDs15MinutesTce threshold crossing."
    DEFVAL      { false }
    ::= { otuClientCtpEntry  30 }


otuClientCtpTermTimDetMode  OBJECT-TYPE
    SYNTAX  INTEGER {
    off(1),
    sapi(2),
    dapi(3),
    sapidapi(4)
    }
    MAX-ACCESS  read-write
    STATUS      current
    DESCRIPTION "This atTermute is used to configure if the TIM-S alarm shall be reported on mismatch of Expected 
        and Received TTI message. The following are the values and their meaning:
        OFF: TIM-S is not reported.
        DAPI: TIM-S is reported only if the DAPI message mismatch occurs. 
        SAPI: TIM-S is reported only if the SAPI message mismatch occurs.
        DAPI_SAPI: Either the DAPI or   the SAPI messages are in a mis- match state."
    DEFVAL      { off }
    ::= { otuClientCtpEntry 31 }
 
otuClientCtpFacTimDetMode  OBJECT-TYPE
    SYNTAX  INTEGER {
    off(1),
    sapi(2),
    dapi(3),
    sapidapi(4)
    }
    MAX-ACCESS  read-write
    STATUS      current
    DESCRIPTION "This atTermute is used to configure if the TIM-S alarm shall be reported on mismatch of Expected 
        and Received TTI message. The following are the values and their meaning:
        OFF: TIM-S is not reported.
        DAPI: TIM-S is reported only if the DAPI message mismatch occurs. 
        SAPI: TIM-S is reported only if the SAPI message mismatch occurs.
        DAPI_SAPI: Either the DAPI or the SAPI messages are in a mismatch       state. "
    DEFVAL      { off }
    ::= { otuClientCtpEntry 32 }
 

otuClientCtpConfiguredServiceType   OBJECT-TYPE
    SYNTAX   InfnServiceType
    MAX-ACCESS  read-only
    STATUS      current
    DESCRIPTION "The OTU Service type that is configured on this generic OtuClientCtp managed object. 
        Note TL1 commands (ED-OTUk and RTRV-OTUk) shall support individual secondary modifiers for each OTU client rates.  "
      ::= { otuClientCtpEntry 33 }

otuClientCtpTamType OBJECT-TYPE
    SYNTAX     InfnEqptType
    MAX-ACCESS read-only
    STATUS     obsolete
    DESCRIPTION "The equipment type where this OTU client is residing."
    ::= { otuClientCtpEntry  34 }


otuClientCtpLoopback OBJECT-TYPE
    SYNTAX  InfnLoopbackType
    MAX-ACCESS  read-write
    STATUS      current
    DESCRIPTION "The Type of Loopback that is provisioned on this ODU Client interface."
    DEFVAL      { none }
    ::= { otuClientCtpEntry  35 }

otuClientCtpFacPmHistStatsEnable OBJECT-TYPE
    SYNTAX  InfnEnableDisable
    MAX-ACCESS  read-write
    STATUS      current
    DESCRIPTION "  Flag to enable or disable the collection of PMs on the Facility side of OTU Clients."
    DEFVAL      { enabled }
    ::= { otuClientCtpEntry  36 }

otuClientCtpTermPmHistStatsEnable OBJECT-TYPE
    SYNTAX  InfnEnableDisable
    MAX-ACCESS  read-write
    STATUS      current
    DESCRIPTION "  Flag to enable or disable the collection of PMs on the Terminal side of OTU Clients."
    DEFVAL      { enabled }
    ::= { otuClientCtpEntry  37 }

otuClientCtpAlarmReportControl OBJECT-TYPE
    SYNTAX InfnArc
    MAX-ACCESS  read-write
    STATUS      current
    DESCRIPTION " The Alarm Reporting Control Flag for the OTU Clients. ."
    DEFVAL      { allowed }
    ::= { otuClientCtpEntry  38 }

otuClientCtpSupportingCircuitIdList  OBJECT-TYPE
    SYNTAX      DisplayString
    MAX-ACCESS  read-only
    STATUS      current
    DESCRIPTION "The Supporting Circuit ID List that is this client is using. "
    ::= { otuClientCtpEntry   39 }


otuClientCtpFacDSThreshold OBJECT-TYPE
    SYNTAX      Integer32 (1..100)
    MAX-ACCESS  read-write
    STATUS      current
    DESCRIPTION "This attribute indicates the Facility-side (e.g., Trib-side) threshold level for declaring a 
    performance monitoring (PM) Second to be bad. A PM Second is declared bad if the percentage of detected errored blocks
    in that second is greater than or equal to the specified threshold level. 
    This attribute maps to the DEGThr MIB of RFC-3591"
    DEFVAL      { 30 }
    ::= { otuClientCtpEntry  40 }

-- otuClientCtpFacSDThreshold  OBJECT-TYPE
--    SYNTAX      Integer32 (2..10)
--    MAX-ACCESS  read-write
--    STATUS      current
--    DESCRIPTION "This attribute indicates the Facility-side (e.g.,Trib-side) threshold level for declaring a 
--    Degraded Signal defect. A Degraded Signal defect shall be declared if SDThreshold consecutive bad PM Seconds are 
--    detected. This attribute maps to the DEGM MIB of RFC-3591"
--    DEFVAL      { 7 }
--    ::= { otuClientCtpEntry  41 }
    
otuClientCtpTermDSThreshold  OBJECT-TYPE
    SYNTAX      Integer32 (1..100)
    MAX-ACCESS  read-write
    STATUS      current
    DESCRIPTION "This attribute indicates the Terminal-side (e.g., Line-side) threshold level for declaring a 
    performance monitoring (PM) Second to be bad. A PM Second is declared bad if the percentage of detected errored blocks
    in that second is greater than or equal to the specified threshold level. 
    This attribute maps to the DEGThr MIB of RFC-3591"
    DEFVAL      { 30 }
    ::= { otuClientCtpEntry  41 }

-- otuClientCtpTermSDThreshold  OBJECT-TYPE
--    SYNTAX      Integer32 (2..10)
--    MAX-ACCESS  read-write
--    STATUS      current
--    DESCRIPTION "This attribute indicates the Terminal-side (e.g.,Line-side) threshold level for declaring a 
--    Degraded Signal defect. A Degraded Signal defect shall be declared if SDThreshold consecutive bad PM Seconds are 
--    detected. This attribute maps to the DEGM MIB of RFC-3591"
--    DEFVAL      { 7 }
--    ::= { otuClientCtpEntry  43 }


otuClientCtpTermPrbsGenMode OBJECT-TYPE
    SYNTAX  InfnEnableDisable
    MAX-ACCESS  read-write
    STATUS      current
    DESCRIPTION "This attribute is used to enable or disable the generation of a PRBS test pattern toward the Terminal side 
    (e.g., toward the line interface).System should disallow enabling for cases in which OTU-encapsulated PRBS to terminal-side 
    does not apply - e.g., when ServiceMode = Adaptation.. "
    DEFVAL      { disabled }
    ::= { otuClientCtpEntry  42 }


otuClientCtpTermPrbsMonMode OBJECT-TYPE
    SYNTAX  InfnEnableDisable
    MAX-ACCESS  read-write
    STATUS      current
    DESCRIPTION "  This attribute is used to enable or disable the monitoring of a PRBS test pattern coming from 
    the Terminal side (e.g., from the Line interface). Applicable to: All OTU Clients System should disallow enabling for cases in 
    which OTU-encapsulated PRBS from terminal side does not apply - e.g., when ServiceMode = Adaptation."
    DEFVAL      { disabled }
    ::= { otuClientCtpEntry  43 }

otuClientCtpFacMonitoringMode OBJECT-TYPE
    SYNTAX  InfnMonitoringMode
    MAX-ACCESS  read-write
    STATUS      current
    DESCRIPTION "Allowed Section Monitoring / Path  Monitoring / TCM Attribute Value(s)
        (For side corresponding to MonitoringMode) (Fac-Side/Term-Side)."      
    ::= { otuClientCtpEntry 44 }
 
otuClientCtpTermMonitoringMode OBJECT-TYPE
    SYNTAX  InfnMonitoringMode
    MAX-ACCESS  read-write
    STATUS      current
    DESCRIPTION "Allowed Section Monitoring / Path  Monitoring / TCM Attribute Value(s)
        (For side corresponding to MonitoringMode) (Fac-Side/Term-Side)."      
    ::= { otuClientCtpEntry 45 }
 

otuClientCtpRxBei15MinutesTce  OBJECT-TYPE
    SYNTAX      Integer32
    MAX-ACCESS  read-write
    STATUS      current
    DESCRIPTION "Number of Error Block in received direction during 15 minutes interval."
    DEFVAL      { 1500 }
    ::= { otuClientCtpEntry  46 }

otuClientCtpTxBei15MinutesTce  OBJECT-TYPE
    SYNTAX      Integer32
    MAX-ACCESS  read-write
    STATUS      current
    DESCRIPTION "Number of Error Block in transmitted direction during 15 minutes interval."
    DEFVAL      { 1500 }
    ::= { otuClientCtpEntry  47 }

otuClientCtpRxBeiDayTce OBJECT-TYPE
    SYNTAX      Integer32
    MAX-ACCESS  read-write
    STATUS      current
    DESCRIPTION "Number of Error Block in received direction during 24 hours interval."
    DEFVAL      { 15000 }
    ::= { otuClientCtpEntry  48 }

otuClientCtpTxBeiDayTce OBJECT-TYPE
    SYNTAX      Integer32
    MAX-ACCESS  read-write
    STATUS      current
    DESCRIPTION "Number of Error Block in transmitted direction during 24 hours interval."
    DEFVAL      { 15000 }
    ::= { otuClientCtpEntry  49 }

otuClientCtpRxBeiDayTceReporting OBJECT-TYPE
    SYNTAX      TruthValue
    MAX-ACCESS  read-write
    STATUS      current
    DESCRIPTION " Flag that enables/disables the reporting of RxEbDayTce threshold crossing."
    DEFVAL      { false }
    ::= { otuClientCtpEntry  50 }

otuClientCtpRxBei15MinutesTceReporting OBJECT-TYPE
    SYNTAX      TruthValue
    MAX-ACCESS  read-write
    STATUS      current
    DESCRIPTION "  Flag that enables/disables the reporting of RxEb15MinutesTce threshold crossing."
    DEFVAL      { false }
    ::= { otuClientCtpEntry  51 }

otuClientCtpTxBeiDayTceReporting OBJECT-TYPE
    SYNTAX      TruthValue
    MAX-ACCESS  read-write
    STATUS      current
    DESCRIPTION " Flag that enables/disables the reporting of TxEbDayTce threshold crossing."
    DEFVAL      { false }
    ::= { otuClientCtpEntry  52 }

otuClientCtpTxBei15MinutesTceReporting OBJECT-TYPE
    SYNTAX      TruthValue
    MAX-ACCESS  read-write
    STATUS      current
    DESCRIPTION " Flag that enables/disables the reporting of TxEb15MinutesTce threshold crossing."
    DEFVAL      { false }
    ::= { otuClientCtpEntry  53 }



-- Conformance Statements
otuClientCtpConformance    OBJECT IDENTIFIER ::= { otuClientCtpMIB 3 }
otuClientCtpCompliances    OBJECT IDENTIFIER ::= { otuClientCtpConformance 1 }
otuClientCtpGroups         OBJECT IDENTIFIER ::= { otuClientCtpConformance 2 }

otuClientCtpCompliance MODULE-COMPLIANCE
    STATUS current
    DESCRIPTION
    "Describes the requirements for conformance to the OTUCLIENTCTP-MIB"
    MODULE
        MANDATORY-GROUPS { otuClientCtpGroup }
    ::= { otuClientCtpCompliances 1 }

otuClientCtpGroup OBJECT-GROUP
    OBJECTS {
    otuClientCtpFacPrbsGenMode,
    otuClientCtpFacPrbsMonMode,
    otuClientCtpServiceMode,
    otuClientCtpServiceModeQualifier,
    otuClientCtpFecCorrection,
    otuClientCtpFecEnabled,

    otuClientCtpTermTxTTI,
    otuClientCtpTermExpectedSAPI,
    otuClientCtpTermExpectedDAPI,

    otuClientCtpFacTxTTI,
    otuClientCtpFacExpectedSAPI,
    otuClientCtpFacExpectedDAPI,

    otuClientCtpTermReceivedTTI,
    otuClientCtpFacReceivedTTI,

    otuClientCtpTermTimDetMode,
    otuClientCtpFacTimDetMode,

    otuClientCtpRxEb15MinutesTce,
    otuClientCtpTxEb15MinutesTce,
    otuClientCtpRxEbDayTce,
    otuClientCtpTxEbDayTce,

    otuClientCtpRxDs15MinutesTce,
    otuClientCtpTxDs15MinutesTce,
    otuClientCtpRxDsDayTce,
    otuClientCtpTxDsDayTce,

    otuClientCtpRxEbDayTceReporting,
    otuClientCtpRxEb15MinutesTceReporting,      
    otuClientCtpTxEbDayTceReporting,
    otuClientCtpTxEb15MinutesTceReporting,      

    otuClientCtpRxDsDayTceReporting,
    otuClientCtpRxDs15MinutesTceReporting,      
    otuClientCtpTxDsDayTceReporting,
    otuClientCtpTxDs15MinutesTceReporting,        
    otuClientCtpConfiguredServiceType,
    otuClientCtpTamType,
    otuClientCtpLoopback,
    otuClientCtpFacPmHistStatsEnable,
    otuClientCtpTermPmHistStatsEnable,
    otuClientCtpAlarmReportControl,
    otuClientCtpSupportingCircuitIdList,
    otuClientCtpFacDSThreshold,
--    otuClientCtpFacSDThreshold,
    otuClientCtpFacMonitoringMode ,
    otuClientCtpTermMonitoringMode,

    otuClientCtpRxBei15MinutesTce,
    otuClientCtpTxBei15MinutesTce,
    otuClientCtpRxBeiDayTce,
    otuClientCtpTxBeiDayTce,

    otuClientCtpRxBeiDayTceReporting,
    otuClientCtpRxBei15MinutesTceReporting,     
    otuClientCtpTxBeiDayTceReporting,
    otuClientCtpTxBei15MinutesTceReporting
    
    }
    STATUS current
    DESCRIPTION
        " A collection of objects for managing the otuClientCtp"
    ::= { otuClientCtpGroups 1 }


END

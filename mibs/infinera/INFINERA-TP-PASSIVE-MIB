-- *****************************************************************
-- INFINERA-TP-PASSIVE-MIB
-- Copyright (c) 2008-2012 by Infinera Inc
-- All rights reserved.
-- ****************************************************************

INFINERA-TP-PASSIVE-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths,InfnEnableDisable           FROM INFINERA-TC-MIB
    commonTerminationPoint                      FROM INFINERA-REG-MIB;

passivePtpMIB MODULE-IDENTITY
    LAST-UPDATED  "201708010000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201701080000Z"
    DESCRIPTION
        "First Version"
    ::= { commonTerminationPoint 2 }

passivePtpTable OBJECT-TYPE
    SYNTAX      SEQUENCE OF PassivePtpEntry
    MAX-ACCESS  not-accessible
    STATUS      current
    DESCRIPTION
        "A list of PassivePtp entries. Each entry is uniquely identified by the value of ifIndex."
    ::= { passivePtpMIB 1 }

passivePtpEntry  OBJECT-TYPE
    SYNTAX      PassivePtpEntry
    MAX-ACCESS  not-accessible
    STATUS      current
    DESCRIPTION
        "A PassivePtp entry containing information pertaining to Infinera PassivePtp Interfaces.
        This table is a subclass of IfCommon. Entries will exist in this table only for
        interfaces of type DLM OCG PTP."
    INDEX { ifIndex }
    ::= { passivePtpTable 1 }


PassivePtpEntry  ::= SEQUENCE {
    passiveMoId                   DisplayString,
    passivePtpType                DisplayString,
    passivePtpProvNbrTP           DisplayString
}

passiveMoId   OBJECT-TYPE
    SYNTAX      DisplayString
    MAX-ACCESS  read-write
    STATUS      current
    DESCRIPTION ""
    ::= { passivePtpEntry 1 }

passivePtpType   OBJECT-TYPE
    SYNTAX      DisplayString
    MAX-ACCESS  read-only
    STATUS      current
    DESCRIPTION ""
    ::= { passivePtpEntry 2 }

passivePtpProvNbrTP   OBJECT-TYPE
    SYNTAX      DisplayString
    MAX-ACCESS  read-write
    STATUS      current
    DESCRIPTION ""
    ::= { passivePtpEntry 3 }

-- Conformance Statements
passivePtpConformance    OBJECT IDENTIFIER ::= { passivePtpMIB 3 }
passivePtpCompliances    OBJECT IDENTIFIER ::= { passivePtpConformance 1 }
passivePtpGroups         OBJECT IDENTIFIER ::= { passivePtpConformance 2 }

passivePtpCompliance MODULE-COMPLIANCE
    STATUS current
    DESCRIPTION
    "Describes the requirements for conformance to the PASSIVE-MIB"
    MODULE
        MANDATORY-GROUPS { passivePtpGroup }
    ::= { passivePtpCompliances 1 }

passivePtpGroup OBJECT-GROUP
    OBJECTS {
        passiveMoId,
        passivePtpType,
        passivePtpProvNbrTP
    }
    STATUS current
    DESCRIPTION
        " A collection of objects for managing the passivePtp"
    ::= { passivePtpGroups 1 }
END

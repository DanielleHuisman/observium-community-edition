-- *****************************************************************
-- INFINERA-TP-PXMAC-MIB
--   
-- Mithun Murthy/ Divyank Rastogi
--   
--   
-- Copyright (c) 2008-2012 by Infinera Inc.
-- All rights reserved.
-- ****************************************************************

INFINERA-TP-PXMAC-MIB DEFINITIONS ::= BEGIN

IMPORTS
    MODULE-IDENTITY, OBJECT-TYPE, Integer32     FROM SNMPv2-SMI
    MODULE-COMPLIANCE, OBJECT-GROUP             FROM SNMPv2-CONF
    DisplayString                               FROM SNMPv2-TC
    ifIndex                                     FROM IF-MIB
	FloatTenths, InfnIngressMatchCriteria, 
	InfnActionOnVlan, InfnEgressActionPriority,
	InfnPmHistStatsControl,InfnLoopback,
	InfnLoopbackBehavior, InfnCreationType,
	InfnFlapActionClear							FROM INFINERA-TC-MIB
    terminationPoint                            FROM INFINERA-REG-MIB;

pxmAcMIB MODULE-IDENTITY
    LAST-UPDATED  "201605200000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "

    REVISION  "201605150000Z"
    DESCRIPTION 
        " "
::= { terminationPoint 72 }


pxmAcConformance   OBJECT IDENTIFIER ::= { pxmAcMIB 3 }
pxmAcCompliances   OBJECT IDENTIFIER ::= { pxmAcConformance 1 }
pxmAcGroups        OBJECT IDENTIFIER ::= { pxmAcConformance 2 }

pxmAcTable  OBJECT-TYPE
    SYNTAX SEQUENCE OF PxmAcEntry
    MAX-ACCESS not-accessible
    STATUS     current
    DESCRIPTION 
        "A list of PxmAc entries. Each entry is uniquely identified by
                the value of ifIndex."
    ::= { pxmAcMIB 1 }

pxmAcEntry  OBJECT-TYPE
    SYNTAX     PxmAcEntry
    MAX-ACCESS not-accessible
    STATUS     current
    DESCRIPTION 
        "A PxmAc entry containing information pertaining to
                Infinera PxmAc interfaces. This table is a subclass of IfCommon.
                Entries will exist in this table only for interfaces of type PxmAc."
    INDEX { ifIndex }
    ::= { pxmAcTable 1 }

PxmAcEntry  ::= SEQUENCE { 
	pxmAcIngressMatchCriteria		InfnIngressMatchCriteria,
	pxmAcIngressMatchOuterVlanId	DisplayString, 
	pxmAcIngressMatchInnerVlanId	DisplayString,	
	pxmAcIngressMatchOuterPriority	DisplayString,
	pxmAcIngressActionOuterVlan		InfnActionOnVlan,
	pxmAcIngressRewriteOuterVlanId	Integer32,
	pxmAcEgressActionOuterVlan		InfnActionOnVlan,
	pxmAcEgressRewriteOuterVlanId	Integer32,
	pxmAcEgressActionInnerVlan		InfnActionOnVlan,
	pxmAcEgressRewriteInnerVlanId	Integer32,
	pxmAcEgressActionOuterPriority	InfnEgressActionPriority,
	pxmAcEgressRewriteOuterPriority	Integer32,
	pxmAcEgressActionInnerPriority	InfnEgressActionPriority,
	pxmAcEgressRewriteInnerPriority	Integer32,
	pxmAcIngressTrafficClass		Integer32,
	pxmAcLoopback					InfnLoopback,
	pxmAcLoopbackBehavior			InfnLoopbackBehavior,
	pxmAcCreationType				InfnCreationType, 
	pxmAcPmHistStatsEnable			InfnPmHistStatsControl,
	pxmAcSplitHorizonGroupID 		Integer32,
	pxmAcFlapActionClear			InfnFlapActionClear	
}

pxmAcIngressMatchCriteria OBJECT-TYPE
    SYNTAX     	InfnIngressMatchCriteria	
    MAX-ACCESS	read-write
    STATUS     	current
    DESCRIPTION 
        ""
    ::= { pxmAcEntry 1 }

pxmAcIngressMatchOuterVlanId	OBJECT-TYPE
    SYNTAX    DisplayString 
    MAX-ACCESS read-write
    STATUS     current
    DESCRIPTION 
        ""
    ::= { pxmAcEntry 2 }

pxmAcIngressMatchInnerVlanId	OBJECT-TYPE
    SYNTAX     DisplayString 
    MAX-ACCESS read-write
    STATUS     current
    DESCRIPTION 
        ""
    ::= { pxmAcEntry 3 }

pxmAcIngressMatchOuterPriority	OBJECT-TYPE
    SYNTAX     DisplayString 
    MAX-ACCESS read-write
    STATUS     current
    DESCRIPTION 
        ""
    ::= { pxmAcEntry 4 }

pxmAcIngressActionOuterVlan OBJECT-TYPE
    SYNTAX     InfnActionOnVlan 
    MAX-ACCESS read-write
    STATUS     current
    DESCRIPTION 
        ""
    ::= { pxmAcEntry 5 }
	
pxmAcIngressRewriteOuterVlanId	OBJECT-TYPE
    SYNTAX   	Integer32
    MAX-ACCESS read-write
    STATUS     current
    DESCRIPTION 
        ""
    ::= { pxmAcEntry 6 }
	
pxmAcEgressActionOuterVlan		OBJECT-TYPE
    SYNTAX    InfnActionOnVlan
    MAX-ACCESS read-write
    STATUS     current
    DESCRIPTION 
        ""
    ::= { pxmAcEntry 7 }
	
pxmAcEgressRewriteOuterVlanId	OBJECT-TYPE
    SYNTAX   Integer32
    MAX-ACCESS read-write
    STATUS     current
    DESCRIPTION 
        ""
    ::= { pxmAcEntry 8 }
	
pxmAcEgressActionInnerVlan	OBJECT-TYPE
    SYNTAX    InfnActionOnVlan
	MAX-ACCESS read-write
    STATUS     current
    DESCRIPTION 
        ""
    ::= { pxmAcEntry 9 }
	
pxmAcEgressRewriteInnerVlanId	OBJECT-TYPE
    SYNTAX   Integer32
    MAX-ACCESS read-write
    STATUS     current
    DESCRIPTION 
        ""
    ::= { pxmAcEntry 10 }
	
pxmAcEgressActionOuterPriority	OBJECT-TYPE
    SYNTAX    InfnEgressActionPriority	
    MAX-ACCESS read-write
    STATUS     current
    DESCRIPTION 
        ""
    ::= { pxmAcEntry 11 }
	
pxmAcEgressRewriteOuterPriority	OBJECT-TYPE
    SYNTAX   	Integer32
    MAX-ACCESS read-write
    STATUS     current
    DESCRIPTION 
        ""
    ::= { pxmAcEntry 12 }
	
pxmAcEgressActionInnerPriority	OBJECT-TYPE
    SYNTAX    InfnEgressActionPriority
	MAX-ACCESS read-write
    STATUS     current
    DESCRIPTION 
        ""
    ::= { pxmAcEntry 13 }
	
pxmAcEgressRewriteInnerPriority	OBJECT-TYPE
    SYNTAX  	Integer32 
    MAX-ACCESS read-write
    STATUS     current
    DESCRIPTION 
        ""
    ::= { pxmAcEntry 14 }
	
pxmAcIngressTrafficClass		OBJECT-TYPE
    SYNTAX  	Integer32 
    MAX-ACCESS read-write
    STATUS     current
    DESCRIPTION 
        ""
    ::= { pxmAcEntry 15 }
	
pxmAcLoopback		OBJECT-TYPE
    SYNTAX		InfnLoopback	   
    MAX-ACCESS read-write
    STATUS     current
    DESCRIPTION 
        ""
    ::= { pxmAcEntry 16 }
	
pxmAcLoopbackBehavior		OBJECT-TYPE
    SYNTAX   InfnLoopbackBehavior
    MAX-ACCESS read-write
    STATUS     current
    DESCRIPTION 
        ""
    ::= { pxmAcEntry 17 }
	
pxmAcCreationType		OBJECT-TYPE
    SYNTAX     InfnCreationType
    MAX-ACCESS read-write
    STATUS     current
    DESCRIPTION 
        ""
    ::= { pxmAcEntry 18 }

pxmAcPmHistStatsEnable	OBJECT-TYPE
    SYNTAX     InfnPmHistStatsControl 
    MAX-ACCESS read-write
    STATUS     current
    DESCRIPTION 
        ""
    ::= { pxmAcEntry 19 }

pxmAcSplitHorizonGroupID	OBJECT-TYPE
    SYNTAX    Integer32 
    MAX-ACCESS read-write
    STATUS     current
    DESCRIPTION 
        ""
    ::= { pxmAcEntry  20 }

pxmAcFlapActionClear	OBJECT-TYPE
    SYNTAX     InfnFlapActionClear
    MAX-ACCESS read-write
    STATUS     current
    DESCRIPTION 
        ""
    ::= { pxmAcEntry  21 }

pxmAcCompliance  MODULE-COMPLIANCE
    STATUS     current
    DESCRIPTION 
        "Describes the requirements for conformance to the TRIBPTP-MIB"
    MODULE
        MANDATORY-GROUPS { pxmAcGroup } 
    ::= { pxmAcCompliances 1 }

pxmAcGroup  OBJECT-GROUP
    OBJECTS { 
		pxmAcIngressMatchCriteria,      
		pxmAcIngressMatchOuterVlanId,   
		pxmAcIngressMatchInnerVlanId,   
		pxmAcIngressMatchOuterPriority, 
		pxmAcIngressActionOuterVlan,    
		pxmAcIngressRewriteOuterVlanId, 
		pxmAcEgressActionOuterVlan,     
		pxmAcEgressRewriteOuterVlanId,  
		pxmAcEgressActionInnerVlan,     
		pxmAcEgressRewriteInnerVlanId,  
		pxmAcEgressActionOuterPriority, 
		pxmAcEgressRewriteOuterPriority,
		pxmAcEgressActionInnerPriority, 
		pxmAcEgressRewriteInnerPriority,
		pxmAcIngressTrafficClass,       
		pxmAcLoopback,                  
		pxmAcLoopbackBehavior,          
		pxmAcCreationType,      
		pxmAcPmHistStatsEnable,
		pxmAcSplitHorizonGroupID,
 		pxmAcFlapActionClear 
	}
    STATUS     current
    DESCRIPTION 
        " A collection of objects for managing pxmAc interfaces."
    ::= { pxmAcGroups 1 }
END

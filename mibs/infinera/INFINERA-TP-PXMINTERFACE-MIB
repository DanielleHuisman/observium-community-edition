-- *****************************************************************
-- INFINERA-TP-PXMINTERFACE-MIB
--   
-- Mithun Murthy/ Divyank Rastogi
--   
--   
-- Copyright (c) 2008-2012 by Infinera Inc.
-- All rights reserved.
-- ****************************************************************

INFINERA-TP-PXMINTERFACE-MIB DEFINITIONS ::= BEGIN

IMPORTS
    MODULE-IDENTITY, OBJECT-TYPE, Integer32     FROM SNMPv2-SMI
    MODULE-COMPLIANCE, OBJECT-GROUP             FROM SNMPv2-CONF
    DisplayString                               FROM SNMPv2-TC
    ifIndex                                     FROM IF-MIB
	InfnPxmIntfProtocolType 	                FROM INFINERA-TC-MIB
    terminationPoint                            FROM INFINERA-REG-MIB;

pxmInterfaceMIB MODULE-IDENTITY
    LAST-UPDATED  "201605200000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "

    REVISION  "201605200000Z"
    DESCRIPTION 
        " "
::= { terminationPoint 73 }


pxmInterfaceConformance   OBJECT IDENTIFIER ::= { pxmInterfaceMIB 3 }
pxmInterfaceCompliances   OBJECT IDENTIFIER ::= { pxmInterfaceConformance 1 }
pxmInterfaceGroups        OBJECT IDENTIFIER ::= { pxmInterfaceConformance 2 }

pxmInterfaceTable  OBJECT-TYPE
    SYNTAX SEQUENCE OF PxmInterfaceEntry
    MAX-ACCESS not-accessible
    STATUS     current
    DESCRIPTION 
        "A list of PxmInterface entries. Each entry is uniquely identified by
                the value of ifIndex."
    ::= { pxmInterfaceMIB 1 }

pxmInterfaceEntry  OBJECT-TYPE
    SYNTAX     PxmInterfaceEntry
    MAX-ACCESS not-accessible
    STATUS     current
    DESCRIPTION 
        "A PxmInterface entry containing information pertaining to
                Infinera PxmInterface interfaces. This table is a subclass of IfCommon.
                Entries will exist in this table only for interfaces of type PxmInterface."
    INDEX { ifIndex }
    ::= { pxmInterfaceTable 1 }

PxmInterfaceEntry  ::= SEQUENCE { 
    pxmInterfaceProtocolType        InfnPxmIntfProtocolType,
	pxmInterfaceMacAddress			DisplayString
}

pxmInterfaceProtocolType  OBJECT-TYPE
    SYNTAX     InfnPxmIntfProtocolType
    MAX-ACCESS read-only
    STATUS     current
    DESCRIPTION 
        "PXM Interface Protocol type"
    ::= { pxmInterfaceEntry 1 }

pxmInterfaceMacAddress        OBJECT-TYPE
    SYNTAX     DisplayString
    MAX-ACCESS read-only
    STATUS     current
    DESCRIPTION
        ""
    ::= { pxmInterfaceEntry 2 }


pxmInterfaceCompliance  MODULE-COMPLIANCE
    STATUS     current
    DESCRIPTION 
        "Describes the requirements for conformance to the TRIBPTP-MIB"
    MODULE
        MANDATORY-GROUPS { pxmInterfaceGroup } 
    ::= { pxmInterfaceCompliances 1 }

pxmInterfaceGroup  OBJECT-GROUP
    OBJECTS { 
        pxmInterfaceProtocolType,
		pxmInterfaceMacAddress
    }
    STATUS     current
    DESCRIPTION 
        " A collection of objects for managing pxmInterface interfaces."
    ::= { pxmInterfaceGroups 1 }
END

-- ***************************************************************
-- INFINERA-TP-PXMLSP-MIB
--   
-- May 2016, Meraj Hussain Syed / Kavitha Manjuntha
--   
--   
-- Copyright (c) 2008-2012 by Infinera Inc.
-- All rights reserved.
-- ****************************************************************
INFINERA-TP-PXMLSP-MIB DEFINITIONS ::= BEGIN

IMPORTS
    OBJECT-TYPE, MODULE-IDENTITY, Unsigned32    FROM SNMPv2-SMI
    OBJECT-GROUP, MODULE-COMPLIANCE             FROM SNMPv2-CONF
    DisplayString                               FROM SNMPv2-TC
    ifIndex                                     FROM IF-MIB
    terminationPoint                            FROM INFINERA-REG-MIB
    InfnEnableDisable, InfnMplsQosModel,
	InfnLSPLoopBackBehaviour, InfnLSPType       FROM INFINERA-TC-MIB;
                             

lspMIB MODULE-IDENTITY
    LAST-UPDATED  "201605200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for LSP equipment table."
::= { terminationPoint 71 }

lspConformance       OBJECT IDENTIFIER ::= { lspMIB 3 }
lspCompliances       OBJECT IDENTIFIER ::= { lspConformance 1 }
lspGroups            OBJECT IDENTIFIER ::= { lspConformance 2 }

lspTable  OBJECT-TYPE
    SYNTAX SEQUENCE OF LspEntry
    MAX-ACCESS not-accessible
    STATUS     current
    DESCRIPTION 
        "This table contains all LSP  modules that are currently present in a network element.
        "
    ::= { lspMIB 1 }

lspEntry  OBJECT-TYPE
    SYNTAX     LspEntry
    MAX-ACCESS not-accessible
    STATUS     current
    DESCRIPTION 
        "A row in the LSP table. Each row in the table is identified with a unique entPhysicalIndexID."
    INDEX { ifIndex }
    ::= { lspTable 1 }

LspEntry ::= SEQUENCE {
    lspType                             InfnLSPType,
    lspIncomingLabel                    Integer32,
    lspOutgoingLabel                    Integer32,
    lspQOSModel                         InfnMplsQosModel,
    lspConfiguredTTL                    Integer32,
    lspConfiguredTrafficClass           Integer32,
    lspMaxReservableBw                  Integer32,
    lspAvailableBW                      Integer32,
    lspLoopBack                         InfnEnableDisable,
    lspLoopBackbehaviour                InfnLSPLoopBackBehaviour,
    lspId                            	DisplayString,
	lspSupportingEqptAid                DisplayString,
    lspNum                              Integer32,
    lspNextHop                          DisplayString,
    lspAssociatedPeerLSP                DisplayString,
    lspAssociatedMplsTunnel             DisplayString
}

lspType  OBJECT-TYPE
    SYNTAX     InfnLSPType
    MAX-ACCESS read-write
    STATUS     current
    DESCRIPTION 
        ""
    ::= { lspEntry 1 }

lspIncomingLabel  OBJECT-TYPE
    SYNTAX     Integer32
    MAX-ACCESS read-create
    STATUS     current
    DESCRIPTION 
        ""
    ::= { lspEntry 2 }

lspOutgoingLabel  OBJECT-TYPE
    SYNTAX     Integer32
    MAX-ACCESS read-create
    STATUS     current
    DESCRIPTION 
        ""
    ::= { lspEntry 3 }

lspQOSModel  OBJECT-TYPE
    SYNTAX     InfnMplsQosModel
    MAX-ACCESS read-create
    STATUS     current
    DESCRIPTION 
        ""
    ::= { lspEntry 4 }

lspConfiguredTTL  OBJECT-TYPE
    SYNTAX     Integer32
    MAX-ACCESS read-write
    STATUS     current
    DESCRIPTION 
        ""
    ::= { lspEntry 5 }
	
lspConfiguredTrafficClass  OBJECT-TYPE
    SYNTAX     Integer32
    MAX-ACCESS read-write
    STATUS     current
    DESCRIPTION 
        ""
    ::= { lspEntry 6 }

lspMaxReservableBw OBJECT-TYPE
    SYNTAX     Integer32
    MAX-ACCESS read-only
    STATUS     current
    DESCRIPTION 
        ""
    ::= { lspEntry 7 }

lspAvailableBW OBJECT-TYPE
    SYNTAX     Integer32
    MAX-ACCESS read-only
    STATUS     current
    DESCRIPTION 
        ""
    ::= { lspEntry 8 }
	
lspLoopBack OBJECT-TYPE
    SYNTAX     InfnEnableDisable
    MAX-ACCESS read-write
    STATUS     current
    DESCRIPTION 
        ""
    ::= { lspEntry 9}
	
lspLoopBackbehaviour OBJECT-TYPE
    SYNTAX     InfnLSPLoopBackBehaviour
    MAX-ACCESS read-only
    STATUS     current
    DESCRIPTION 
        ""
    ::= { lspEntry 10}

lspId OBJECT-TYPE
    SYNTAX     DisplayString
    MAX-ACCESS read-write
    STATUS     current
    DESCRIPTION 
        ""
    ::= { lspEntry 11}
	
lspSupportingEqptAid OBJECT-TYPE
    SYNTAX     DisplayString
    MAX-ACCESS read-create
    STATUS     current
    DESCRIPTION 
        ""
    ::= { lspEntry 12}

lspNum OBJECT-TYPE
    SYNTAX     Integer32
    MAX-ACCESS read-only
    STATUS     current
    DESCRIPTION 
        ""
    ::= { lspEntry 13}

lspNextHop OBJECT-TYPE
    SYNTAX     DisplayString
    MAX-ACCESS read-write
    STATUS     current
    DESCRIPTION 
        ""
    ::= { lspEntry 14}

lspAssociatedPeerLSP OBJECT-TYPE
    SYNTAX     DisplayString
    MAX-ACCESS read-write
    STATUS     current
    DESCRIPTION 
        ""
    ::= { lspEntry 15}

lspAssociatedMplsTunnel OBJECT-TYPE
    SYNTAX     DisplayString
    MAX-ACCESS read-write
    STATUS     current
    DESCRIPTION 
        ""
    ::= { lspEntry 16}

lspCompliance  MODULE-COMPLIANCE
    STATUS     current
    DESCRIPTION ""
    MODULE
        MANDATORY-GROUPS { lspGroup } 
    ::= { lspCompliances 1 }

lspGroup  OBJECT-GROUP
    OBJECTS { 
        lspType,
        lspIncomingLabel,
        lspOutgoingLabel,
        lspQOSModel,
        lspConfiguredTTL,
        lspConfiguredTrafficClass,
        lspMaxReservableBw,
        lspAvailableBW,
        lspLoopBack,
        lspLoopBackbehaviour, 
        lspId, 
	    lspSupportingEqptAid,
        lspNum,
        lspNextHop,
        lspAssociatedPeerLSP,
        lspAssociatedMplsTunnel
    }
    STATUS     current
    DESCRIPTION ""
    ::= { lspGroups 1 }
END

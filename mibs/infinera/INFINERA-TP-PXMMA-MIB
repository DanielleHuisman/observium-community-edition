-- *****************************************************************
-- INFINERA-TP-PXMMA-MIB
--   
-- Mithun Murthy/ Divyank Rastogi
--   
--   
-- Copyright (c) 2008-2016 by Infinera Inc.
-- All rights reserved.
-- ****************************************************************

INFINERA-TP-PXMMA-MIB DEFINITIONS ::= BEGIN

IMPORTS
    MODULE-IDENTITY, OBJECT-TYPE, Integer32     FROM SNMPv2-SMI
    MODULE-COMPLIANCE, OBJECT-GROUP             FROM SNMPv2-CONF
    TruthValue, DisplayString                   FROM SNMPv2-TC
    ifIndex                                     FROM IF-MIB
	InfnCcmInterval,InfnMANameFormat,
	InfnSenderIDTLV 							FROM INFINERA-TC-MIB
    terminationPoint 							FROM INFINERA-REG-MIB;

pxmMaMIB MODULE-IDENTITY
    LAST-UPDATED  "201605300000Z"
    ORGANIZATION 
        "Infinera"
    CONTACT-INFO 
        "Infinera
                1322 Bordeaux Drive
                Sunnyvale, CA - 94089
        
                Contact : Technical Support
                Email   : support@infinera.com
                Phone   : 1-877-INF-5288"
    DESCRIPTION 
        " "

    REVISION  "201605300000Z"
    DESCRIPTION 
        " "
::= { terminationPoint 79 }


pxmMaConformance   OBJECT IDENTIFIER ::= { pxmMaMIB 3 }
pxmMaCompliances   OBJECT IDENTIFIER ::= { pxmMaConformance 1 }
pxmMaGroups        OBJECT IDENTIFIER ::= { pxmMaConformance 2 }

pxmMaTable  OBJECT-TYPE
    SYNTAX SEQUENCE OF PxmMaBaseEntry
    MAX-ACCESS not-accessible
    STATUS     current
    DESCRIPTION 
        "A list of PxmMaBase entries. Each entry is uniquely identified by
                the value of ifIndex."
    ::= { pxmMaMIB 1 }

pxmMaEntry  OBJECT-TYPE
    SYNTAX     PxmMaBaseEntry
    MAX-ACCESS not-accessible
    STATUS     current
    DESCRIPTION 
        "A PxmMaBase entry containing information pertaining to
         Infinera PxmMaBase interfaces. This table is a subclass of IfCommon.
         Entries will exist in this table only for interfaces of type PxmMaBase."
    INDEX { ifIndex }
    ::= { pxmMaTable 1 }

PxmMaBaseEntry  ::= SEQUENCE { 
	pxmMaMAName			DisplayString,
    pxmMaRMepAgeOutInterval Integer32,
    pxmMaMDAid			 DisplayString,
	pxmMaCcmInterval	InfnCcmInterval,
	pxmMaMANameFormat	InfnMANameFormat,
	pxmMaSenderIDTLV	InfnSenderIDTLV,	
	pxmMaMDName			DisplayString,
	pxmMaMDLevel		Integer32
}

pxmMaMAName	OBJECT-TYPE
    SYNTAX     DisplayString
    MAX-ACCESS read-write
    STATUS     current
    DESCRIPTION 
		""
    ::= { pxmMaEntry 1 }

pxmMaRMepAgeOutInterval OBJECT-TYPE
    SYNTAX     Integer32
    MAX-ACCESS read-write
    STATUS     current
    DESCRIPTION 
        "PXM from cos type"
    ::= { pxmMaEntry 2 }

pxmMaMDAid		OBJECT-TYPE
    SYNTAX     DisplayString 
    MAX-ACCESS read-only
    STATUS     current
    DESCRIPTION 
        ""
    ::= { pxmMaEntry 3 }

pxmMaCcmInterval OBJECT-TYPE
    SYNTAX     InfnCcmInterval
    MAX-ACCESS read-write
    STATUS     current
    DESCRIPTION 
        ""
    ::= { pxmMaEntry 4 }

pxmMaMANameFormat	OBJECT-TYPE
    SYNTAX     InfnMANameFormat 
    MAX-ACCESS read-write
    STATUS     current
    DESCRIPTION 
        ""
    ::= { pxmMaEntry 5 }

pxmMaSenderIDTLV	OBJECT-TYPE
    SYNTAX     InfnSenderIDTLV
    MAX-ACCESS read-only
    STATUS     current
    DESCRIPTION 
        ""
    ::= { pxmMaEntry 6 }

pxmMaMDName		OBJECT-TYPE
    SYNTAX    	DisplayString 
    MAX-ACCESS read-only
    STATUS     current
    DESCRIPTION 
        ""
    ::= { pxmMaEntry 7 }

pxmMaMDLevel	OBJECT-TYPE
    SYNTAX     Integer32 
    MAX-ACCESS read-only
    STATUS     current
    DESCRIPTION 
        ""
    ::= { pxmMaEntry 8 }

pxmMaCompliance  MODULE-COMPLIANCE
    STATUS     current
    DESCRIPTION 
        "Describes the requirements for conformance to the TRIBPTP-MIB"
    MODULE
        MANDATORY-GROUPS { pxmMaGroup } 
    ::= { pxmMaCompliances 1 }

pxmMaGroup  OBJECT-GROUP
    OBJECTS { 
    	pxmMaMAName,         
		pxmMaRMepAgeOutInterval,
		pxmMaMDAid,          
		pxmMaCcmInterval,    
		pxmMaMANameFormat,   
		pxmMaSenderIDTLV,    
		pxmMaMDName,         
		pxmMaMDLevel        
	}
    STATUS     current
    DESCRIPTION 
        " A collection of objects for managing pxmMa interfaces."
    ::= { pxmMaGroups 1 }
END

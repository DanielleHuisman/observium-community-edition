-- ***************************************************************
-- INFINERA-TP-PXMNEXTHOP-MIB
--   
-- May 2016, Kavitha Manjunatha / Divyank Rastogi
--   
--   
-- Copyright (c) 2008-2012 by Infinera Inc.
-- All rights reserved.
-- ****************************************************************
INFINERA-TP-PXMNEXTHOP-MIB DEFINITIONS ::= BEGIN

IMPORTS
    OBJECT-TYPE, MODULE-IDENTITY, Unsigned32    FROM SNMPv2-SMI
    OBJECT-GROUP, MODULE-COMPLIANCE             FROM SNMPv2-CONF
    DisplayString                               FROM SNMPv2-TC
    ifIndex                                     FROM IF-MIB
    terminationPoint                            FROM INFINERA-REG-MIB;

pxmNextHopMIB MODULE-IDENTITY
    LAST-UPDATED  "201605200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for NEXTHOP interface."
::= { terminationPoint 68 }

pxmNextHopConformance       OBJECT IDENTIFIER ::= { pxmNextHopMIB 3 }
pxmNextHopCompliances       OBJECT IDENTIFIER ::= { pxmNextHopConformance 1 }
pxmNextHopGroups            OBJECT IDENTIFIER ::= { pxmNextHopConformance 2 }

pxmNextHopTable  OBJECT-TYPE
    SYNTAX SEQUENCE OF PxmNextHopEntry
    MAX-ACCESS not-accessible
    STATUS     current
    DESCRIPTION 
        "This table contains all NEXTHOP  modules that are currently present
        in a network element."
    ::= { pxmNextHopMIB 1 }

pxmNextHopEntry  OBJECT-TYPE
    SYNTAX     PxmNextHopEntry
    MAX-ACCESS not-accessible
    STATUS     current
    DESCRIPTION 
        "A row in the MEP table. Each row in the table is identified with a unique entPhysicalIndexID."
    INDEX { ifIndex }
    ::= { pxmNextHopTable 1 }

PxmNextHopEntry ::= SEQUENCE {
    pxmNextHopMacAddress         DisplayString
}

pxmNextHopMacAddress  OBJECT-TYPE
    SYNTAX     DisplayString
    MAX-ACCESS read-write
    STATUS     current
    DESCRIPTION 
        ""
    ::= { pxmNextHopEntry 1 }

pxmNextHopCompliance  MODULE-COMPLIANCE
    STATUS     current
    DESCRIPTION ""
    MODULE
        MANDATORY-GROUPS { pxmNextHopGroup } 
    ::= { pxmNextHopCompliances 1 }

pxmNextHopGroup  OBJECT-GROUP
    OBJECTS { 
        pxmNextHopMacAddress
    }
    STATUS     current
    DESCRIPTION ""
    ::= { pxmNextHopGroups 1 }
END

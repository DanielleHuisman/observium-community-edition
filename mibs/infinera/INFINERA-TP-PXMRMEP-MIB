-- ***************************************************************
-- INFINERA-TP-PXMMEP-MIB
--   
-- May 2016, Meraj Hussain Syed / Kavitha Manjuntha
--   
--   
-- Copyright (c) 2008-2012 by Infinera Inc.
-- All rights reserved.
-- ****************************************************************
INFINERA-TP-PXMRMEP-MIB DEFINITIONS ::= BEGIN

IMPORTS
    OBJECT-TYPE, MODULE-IDENTITY, Unsigned32    FROM SNMPv2-SMI
    OBJECT-GROUP, MODULE-COMPLIANCE             FROM SNMPv2-CONF
    DisplayString                               FROM SNMPv2-TC
    ifIndex                                     FROM IF-MIB
    terminationPoint                            FROM INFINERA-REG-MIB
    InfnRMepType, InfnRmepState,
	InfnIsEnabled, InfnPortStatusTLV,
    InfnInterfaceStatusTLV, InfnSenderIDTLV     FROM INFINERA-TC-MIB;
                             

rmepMIB MODULE-IDENTITY
    LAST-UPDATED  "201605200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for RMEP equipment table."
::= { terminationPoint 77 }

rmepConformance       OBJECT IDENTIFIER ::= { rmepMIB 3 }
rmepCompliances       OBJECT IDENTIFIER ::= { rmepConformance 1 }
rmepGroups            OBJECT IDENTIFIER ::= { rmepConformance 2 }

rmepTable  OBJECT-TYPE
    SYNTAX SEQUENCE OF RmepEntry
    MAX-ACCESS not-accessible
    STATUS     current
    DESCRIPTION 
        "This table contains all RMEP  modules that are currently present in a network element.
        "
    ::= { rmepMIB 1 }

rmepEntry  OBJECT-TYPE
    SYNTAX     RmepEntry
    MAX-ACCESS not-accessible
    STATUS     current
    DESCRIPTION 
        "A row in the RMEP table. Each row in the table is identified with a unique entPhysicalIndexID."
    INDEX { ifIndex }
    ::= { rmepTable 1 }

RmepEntry ::= SEQUENCE {
    rmepLocalMepAid                     DisplayString,
    rmepLocalMepId                      Integer32,
    rmepRMepId                          Integer32,
    rmepRMepType                        InfnRMepType,
    rmepMDLevel                         Integer32,
    rmepRmepState                       InfnRmepState,
    rmepFailedOkTime                    Integer32,
    rmepMacAddress                      DisplayString,
    rmepRDI                             InfnIsEnabled,
    rmepPortStatusTLV                   InfnPortStatusTLV ,
    rmepInterfaceStatusTLV              InfnInterfaceStatusTLV,
    rmepSenderIDTLV                     InfnSenderIDTLV
}

rmepLocalMepAid  OBJECT-TYPE
    SYNTAX     DisplayString
    MAX-ACCESS read-only
    STATUS     current
    DESCRIPTION 
        ""
    ::= { rmepEntry 1 }

rmepLocalMepId  OBJECT-TYPE
    SYNTAX     Integer32
    MAX-ACCESS read-only
    STATUS     current
    DESCRIPTION 
        ""
    ::= { rmepEntry 2 }

rmepRMepId  OBJECT-TYPE
    SYNTAX     Integer32
    MAX-ACCESS read-only
    STATUS     current
    DESCRIPTION 
        ""
    ::= { rmepEntry 3 }

rmepRMepType  OBJECT-TYPE
    SYNTAX     InfnRMepType
    MAX-ACCESS read-write
    STATUS     current
    DESCRIPTION 
        ""
    ::= { rmepEntry 4 }

rmepMDLevel  OBJECT-TYPE
    SYNTAX     Integer32
    MAX-ACCESS read-only
    STATUS     current
    DESCRIPTION 
        ""
    ::= { rmepEntry 5 }

rmepRmepState  OBJECT-TYPE
    SYNTAX     InfnRmepState
    MAX-ACCESS read-only
    STATUS     current
    DESCRIPTION 
        ""
    ::= { rmepEntry 6 }

rmepFailedOkTime OBJECT-TYPE
    SYNTAX     Integer32
    MAX-ACCESS read-only
    STATUS     current
    DESCRIPTION 
        ""
    ::= { rmepEntry 7 }
	
rmepMacAddress OBJECT-TYPE
    SYNTAX     DisplayString
    MAX-ACCESS read-only
    STATUS     current
    DESCRIPTION 
        ""
    ::= { rmepEntry 8 }

rmepRDI OBJECT-TYPE
    SYNTAX     InfnIsEnabled
    MAX-ACCESS read-only
    STATUS     current
    DESCRIPTION 
        ""
    ::= { rmepEntry 9}
	
rmepPortStatusTLV OBJECT-TYPE
    SYNTAX     InfnPortStatusTLV
    MAX-ACCESS read-only
    STATUS     current
    DESCRIPTION 
        ""
    ::= { rmepEntry 10}

rmepInterfaceStatusTLV OBJECT-TYPE
    SYNTAX     InfnInterfaceStatusTLV
    MAX-ACCESS read-only
    STATUS     current
    DESCRIPTION 
        ""
    ::= { rmepEntry 11}
	
rmepSenderIDTLV  OBJECT-TYPE
    SYNTAX     InfnSenderIDTLV
    MAX-ACCESS read-write
    STATUS     current
    DESCRIPTION 
        ""
    ::= { rmepEntry 12}
	
rmepCompliance  MODULE-COMPLIANCE
    STATUS     current
    DESCRIPTION ""
    MODULE
        MANDATORY-GROUPS { rmepGroup } 
    ::= { rmepCompliances 1 }

rmepGroup  OBJECT-GROUP
    OBJECTS { 
        rmepLocalMepAid,
        rmepLocalMepId,
        rmepRMepId,
        rmepRMepType,
        rmepMDLevel,
        rmepRmepState,
        rmepFailedOkTime,
        rmepMacAddress,
        rmepRDI,
        rmepPortStatusTLV,
        rmepInterfaceStatusTLV,
        rmepSenderIDTLV
    }
    STATUS     current
    DESCRIPTION ""
    ::= { rmepGroups 1 }
END

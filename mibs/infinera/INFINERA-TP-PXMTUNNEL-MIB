-- ***************************************************************
-- INFINERA-TP-PXMTUNNEL-MIB
--   
-- May 2016, Kavitha Manjunatha / Divyank Rastogi
--   
--   
-- Copyright (c) 2008-2012 by Infinera Inc.
-- All rights reserved.
-- ****************************************************************
INFINERA-TP-PXMTUNNEL-MIB DEFINITIONS ::= BEGIN

IMPORTS
    OBJECT-TYPE, MODULE-IDENTITY, Unsigned32    FROM SNMPv2-SMI
    OBJECT-GROUP, MODULE-COMPLIANCE             FROM SNMPv2-CONF
    DisplayString                               FROM SNMPv2-TC
    ifIndex                                     FROM IF-MIB
    terminationPoint                            FROM INFINERA-REG-MIB;

pxmTunnelMIB MODULE-IDENTITY
    LAST-UPDATED  "201605200000Z"
    ORGANIZATION 
        "INFINERA"
    CONTACT-INFO 
        "Infinera
        169 Java Drive
        Sunnyvale, CA - 94089
        
        Contact : Technical Support
        Email   : support@infinera.com
        Phone   : 1-877-INF-5288"
    DESCRIPTION 
        "This MIB is modeling for PXMTUNNEL interface."
::= { terminationPoint 69 }

pxmTunnelConformance       OBJECT IDENTIFIER ::= { pxmTunnelMIB 3 }
pxmTunnelCompliances       OBJECT IDENTIFIER ::= { pxmTunnelConformance 1 }
pxmTunnelGroups            OBJECT IDENTIFIER ::= { pxmTunnelConformance 2 }

pxmTunnelTable  OBJECT-TYPE
    SYNTAX SEQUENCE OF PxmTunnelEntry
    MAX-ACCESS not-accessible
    STATUS     current
    DESCRIPTION 
        "This table contains all PXMTUNNEL  modules that are currently present in a network element.
        "
    ::= { pxmTunnelMIB 1 }

pxmTunnelEntry  OBJECT-TYPE
    SYNTAX     PxmTunnelEntry
    MAX-ACCESS not-accessible
    STATUS     current
    DESCRIPTION 
        "A row in the PXMTUNNEL table. Each row in the table is identified with a unique entPhysicalIndexID."
    INDEX { ifIndex }
    ::= { pxmTunnelTable 1 }

PxmTunnelEntry ::= SEQUENCE {
    pxmTunnelMTUSize               Integer32,
    pxmTunnelNum                   Integer32,
    pxmTunnelId                    DisplayString,
    pxmTunnelSupportingEqptAid     DisplayString,
    pxmTunnelAssociatedLSPList     DisplayString
}

pxmTunnelMTUSize  OBJECT-TYPE
    SYNTAX     Integer32
    MAX-ACCESS read-write
    STATUS     current
    DESCRIPTION 
        ""
    ::= { pxmTunnelEntry 1 }

pxmTunnelNum  OBJECT-TYPE
    SYNTAX     Integer32
    MAX-ACCESS read-write
    STATUS     current
    DESCRIPTION 
        ""
    ::= { pxmTunnelEntry 2 }

pxmTunnelId  OBJECT-TYPE
    SYNTAX     DisplayString
    MAX-ACCESS read-write
    STATUS     current
    DESCRIPTION 
        ""
    ::= { pxmTunnelEntry 3 }

pxmTunnelSupportingEqptAid  OBJECT-TYPE
    SYNTAX     DisplayString
    MAX-ACCESS read-create
    STATUS     current
    DESCRIPTION 
        ""
    ::= { pxmTunnelEntry 4 }

pxmTunnelAssociatedLSPList OBJECT-TYPE
    SYNTAX     DisplayString
    MAX-ACCESS read-only
    STATUS     current
    DESCRIPTION 
        ""
    ::= { pxmTunnelEntry 5 }

pxmTunnelCompliance  MODULE-COMPLIANCE
    STATUS     current
    DESCRIPTION ""
    MODULE
        MANDATORY-GROUPS { pxmTunnelGroup } 
    ::= { pxmTunnelCompliances 1 }

pxmTunnelGroup  OBJECT-GROUP
    OBJECTS { 
        pxmTunnelMTUSize,
        pxmTunnelNum,
        pxmTunnelId,
        pxmTunnelSupportingEqptAid,
        pxmTunnelAssociatedLSPList
    }
    STATUS     current
    DESCRIPTION ""
    ::= { pxmTunnelGroups 1 }
END

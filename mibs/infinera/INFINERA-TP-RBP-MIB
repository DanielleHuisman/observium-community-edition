-- *****************************************************************
-- INFINERA-TP-RBP-MIB
-- Copyright (c) 2008-2012 by Infinera Inc
-- All rights reserved.
-- ****************************************************************

INFINERA-TP-RBP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths,InfnEnableDisable           FROM INFINERA-TC-MIB
    terminationPoint                            FROM INFINERA-REG-MIB;

rbpPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 54 }

rbpPtpTable OBJECT-TYPE
    SYNTAX      SEQUENCE OF RbpPtpEntry
    MAX-ACCESS  not-accessible
    STATUS      current
    DESCRIPTION
        "A list of RbpPtp entries. Each entry is uniquely identified by the value of ifIndex."
    ::= { rbpPtpMIB 1 } 

rbpPtpEntry  OBJECT-TYPE
    SYNTAX      RbpPtpEntry
    MAX-ACCESS  not-accessible
    STATUS      current
    DESCRIPTION
        "A RbpPtp entry containing information pertaining to Infinera RbpPtp Interfaces.
        This table is a subclass of IfCommon. Entries will exist in this table only for
        interfaces of type DLM OCG PTP."
    INDEX { ifIndex }
    ::= { rbpPtpTable 1 }


RbpPtpEntry  ::= SEQUENCE {
    rbpPtpProvNbrTP           DisplayString
}

rbpPtpProvNbrTP   OBJECT-TYPE
    SYNTAX      DisplayString
    MAX-ACCESS  read-write
    STATUS      current
    DESCRIPTION ""
    ::= { rbpPtpEntry 1 }

-- Conformance Statements
rbpPtpConformance    OBJECT IDENTIFIER ::= { rbpPtpMIB 3 }
rbpPtpCompliances    OBJECT IDENTIFIER ::= { rbpPtpConformance 1 }
rbpPtpGroups         OBJECT IDENTIFIER ::= { rbpPtpConformance 2 }

rbpPtpCompliance MODULE-COMPLIANCE
    STATUS current
    DESCRIPTION
    "Describes the requirements for conformance to the RBP-MIB"
    MODULE
        MANDATORY-GROUPS { rbpPtpGroup }
    ::= { rbpPtpCompliances 1 }

rbpPtpGroup OBJECT-GROUP
    OBJECTS {

        rbpPtpProvNbrTP
}
    STATUS current
    DESCRIPTION
        " A collection of objects for managing the rbpPtp"
    ::= { rbpPtpGroups 1 }
END

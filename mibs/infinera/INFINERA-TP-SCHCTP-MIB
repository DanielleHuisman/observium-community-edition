-- *****************************************************************
-- INFINERA-TP-SCHCTP-MIB
-- Copyright (c) 2013-2014 by Infinera Inc.
-- All rights reserved.
-- ****************************************************************

INFINERA-TP-SCHCTP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    InfnCarrierType, InfnModulation,
    InfnEnableDisable,InfnSuperChannelNumber,
    InfnEncoding, FloatTenths,
    FloatArbitraryPrecision,
    InfnChannelPlanType, InfnFrequencySlotPlanType,
    InfnTimReptMode, InfnMonitoringMode,
    InfnShutterState, InfnReporting,
    InfnProvBaudRate, InfnOpticalSignal,
    InfnOpticalRate, FloatHundredths            FROM INFINERA-TC-MIB
    terminationPoint                            FROM INFINERA-REG-MIB;

schCtpMIB MODULE-IDENTITY
    LAST-UPDATED  "201309050000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201309050000Z"
    DESCRIPTION
        "First Version"
    ::= { terminationPoint 50 }

schCtpTable OBJECT-TYPE
    SYNTAX      SEQUENCE OF SchCtpEntry
    MAX-ACCESS  not-accessible
    STATUS      current
    DESCRIPTION
        "A list of SchCtp entries. Each entry is uniquely identified by the value of ifIndex."
    ::= { schCtpMIB 1 }

schCtpEntry  OBJECT-TYPE
    SYNTAX      SchCtpEntry
    MAX-ACCESS  not-accessible
    STATUS      current
    DESCRIPTION
        "A SchCtp entry containing information pertaining to Infinera SchCtp Interfaces.
        This table is a subclass of IfCommon. Entries will exist in this table only for
        interfaces of type SCH CTP."
    INDEX { ifIndex }
    ::= { schCtpTable 1 }


SchCtpEntry  ::= SEQUENCE {
    schCtpCarrierGroupMode              InfnCarrierType,
    schCtpPmHistStatsEnable             INTEGER,
    schCtpProvSuperChannelNum           InfnSuperChannelNumber,
    schCtpProvModulation                InfnModulation,
    schCtpProvEncoding                  InfnEncoding,
    schCtpSpectralBandWidth             Integer32,
    schCtpAggregrateRate                InfnOpticalRate,
    schCtpInstalledModulation           InfnModulation,
    schCtpInstalledEncoding             InfnEncoding,
    schCtpChannelPlanType               InfnChannelPlanType,
    schCtpFrequencySlotPlanType         InfnFrequencySlotPlanType,
    schCtpInstalledSuperChannelNum      InfnSuperChannelNumber,
    schCtpOffset                        FloatHundredths,
    schCtpOffsetOverride                InfnEnableDisable,
    schCtpSupportingCircuitIdList       DisplayString,
    schCtpAssociatedClientSCHCTP        DisplayString,
    schCtpPowerOffset                   FloatArbitraryPrecision,
	schCtpExpectedTTI                   DisplayString,
    schCtpTransmitTTI                   DisplayString,
    schCtpRecievedTTI                   DisplayString,
    schCtpMonitoringMode                InfnMonitoringMode,
    schCtpTargetOpr						FloatTenths,
	schCtpIntraSchCarrierRippleThreshold FloatTenths,
    schCtpShutterState                  InfnShutterState,
    schCtpIntraSchCarRipple             InfnReporting,
	schCtpFreqSlotList                  DisplayString,
	schCtpSupportingCarrierList         DisplayString,
    schCtpSupportingCarrGrpList         DisplayString,
    schCtpProvBaudRate                  InfnProvBaudRate,
    schCtpOpticalSignal                 InfnOpticalSignal,
    schCtpAssocTeIntfList               DisplayString,
    schCtpRxSchPowerOffset              FloatArbitraryPrecision,
    schCtpFlexOptChnlList               DisplayString,
    schCtpCarrierList                   DisplayString,
    schCtpPassBandList                  DisplayString,
    schCtpPassBandStatusList            DisplayString
    }



schCtpCarrierGroupMode  OBJECT-TYPE
    SYNTAX      InfnCarrierType
    MAX-ACCESS  read-only
    STATUS      current
    DESCRIPTION ""
    ::= { schCtpEntry 1 }

schCtpAssociatedClientSCHCTP OBJECT-TYPE
    SYNTAX      DisplayString
    MAX-ACCESS  read-write
    STATUS      current
    DESCRIPTION ""
    ::= { schCtpEntry 2 }

schCtpPmHistStatsEnable OBJECT-TYPE
    SYNTAX  INTEGER {
        enabled(1),
        disabled(2)
    }
    MAX-ACCESS  read-write
    STATUS      current
    DESCRIPTION "Flag to enable or disable Historic PM collection."
    DEFVAL      { enabled }
    ::= { schCtpEntry  3 }

schCtpProvSuperChannelNum OBJECT-TYPE
    SYNTAX      InfnSuperChannelNumber
    MAX-ACCESS  read-only
    STATUS      current
    DESCRIPTION "Super channel number."
    ::= { schCtpEntry  4 }

schCtpProvModulation OBJECT-TYPE
    SYNTAX  InfnModulation
    MAX-ACCESS  read-write
    STATUS      current
    DESCRIPTION "Provisional modulation"
    ::= { schCtpEntry  5 }

schCtpProvEncoding OBJECT-TYPE
    SYNTAX      InfnEncoding
    MAX-ACCESS  read-write
    STATUS      current
    DESCRIPTION "Provisonal encoding."
    ::= { schCtpEntry  6 }

schCtpSpectralBandWidth OBJECT-TYPE
    SYNTAX      Integer32
    MAX-ACCESS  read-only
    STATUS      current
    DESCRIPTION "Spectral bandwidth."
    ::= { schCtpEntry  7 }

schCtpAggregrateRate OBJECT-TYPE
    SYNTAX      InfnOpticalRate
    MAX-ACCESS  read-only
    STATUS      current
    DESCRIPTION "Aggregrate rate."
    ::= { schCtpEntry  8 }


schCtpChannelPlanType   OBJECT-TYPE
    SYNTAX      InfnChannelPlanType
    MAX-ACCESS  read-only
    STATUS      current
    DESCRIPTION ""
    ::= { schCtpEntry 9 }


schCtpFrequencySlotPlanType OBJECT-TYPE
    SYNTAX      InfnFrequencySlotPlanType
    MAX-ACCESS  read-create
    STATUS      current
    DESCRIPTION ""
    ::= { schCtpEntry 10 }

schCtpInstalledSuperChannelNum  OBJECT-TYPE
    SYNTAX      InfnSuperChannelNumber
    MAX-ACCESS  read-only
    STATUS      current
    DESCRIPTION ""
    ::= { schCtpEntry 11 }


schCtpInstalledModulation  OBJECT-TYPE
    SYNTAX      InfnModulation
    MAX-ACCESS  read-only
    STATUS      current
    DESCRIPTION "Installed modulation type."
    ::= { schCtpEntry  12 }


schCtpInstalledEncoding OBJECT-TYPE
    SYNTAX      InfnEncoding
    MAX-ACCESS  read-only
    STATUS      current
    DESCRIPTION "Installed encoding type."
    ::= { schCtpEntry  13 }

schCtpOffset    OBJECT-TYPE
    SYNTAX  FloatHundredths
    MAX-ACCESS  read-write
    STATUS      current
    DESCRIPTION ""
    ::= { schCtpEntry 14 }

schCtpOffsetOverride    OBJECT-TYPE
    SYNTAX      InfnEnableDisable
    MAX-ACCESS  read-write
    STATUS      current
    DESCRIPTION ""
    ::= { schCtpEntry 15 }

schCtpPowerOffset   OBJECT-TYPE
    SYNTAX      FloatArbitraryPrecision
    MAX-ACCESS  read-write
    STATUS      current
    DESCRIPTION ""
    ::= { schCtpEntry 16 }

schCtpSupportingCircuitIdList OBJECT-TYPE
    SYNTAX      DisplayString
    MAX-ACCESS  read-only
    STATUS      current
    DESCRIPTION ""
    ::= { schCtpEntry 17 }

schCtpExpectedTTI   OBJECT-TYPE
    SYNTAX      DisplayString
    MAX-ACCESS  read-write
    STATUS      current
    DESCRIPTION ""
    ::= { schCtpEntry 18 }

schCtpTransmitTTI   OBJECT-TYPE
    SYNTAX      DisplayString
    MAX-ACCESS  read-write
    STATUS      current
    DESCRIPTION ""
    ::= { schCtpEntry 19 }

schCtpRecievedTTI   OBJECT-TYPE
    SYNTAX      DisplayString
    MAX-ACCESS  read-only
    STATUS      current
    DESCRIPTION ""
    ::= { schCtpEntry 20 }

schCtpMonitoringMode    OBJECT-TYPE
    SYNTAX      InfnMonitoringMode
    MAX-ACCESS  read-write
    STATUS      current
    DESCRIPTION ""
    ::= { schCtpEntry 21 }

schCtpTargetOpr	OBJECT-TYPE
    SYNTAX      FloatTenths
    MAX-ACCESS  read-only
    STATUS      current
    DESCRIPTION ""
    ::= { schCtpEntry 22 }

schCtpIntraSchCarrierRippleThreshold OBJECT-TYPE
    SYNTAX      FloatTenths
    MAX-ACCESS  read-write
    STATUS      current
    DESCRIPTION ""
    ::= { schCtpEntry 23 }

schCtpShutterState OBJECT-TYPE
    SYNTAX      InfnShutterState
    MAX-ACCESS  read-write
    STATUS      current
    DESCRIPTION ""
    ::= { schCtpEntry 24 }

schCtpIntraSchCarRipple OBJECT-TYPE
    SYNTAX      InfnReporting
    MAX-ACCESS  read-write
    STATUS      current
    DESCRIPTION ""
    ::= { schCtpEntry 25 }

schCtpFreqSlotList   OBJECT-TYPE
    SYNTAX      DisplayString
    MAX-ACCESS  read-only
    STATUS      current
    DESCRIPTION ""
    ::= { schCtpEntry 26 }

schCtpSupportingCarrierList   OBJECT-TYPE
    SYNTAX      DisplayString
    MAX-ACCESS  read-only
    STATUS      current
    DESCRIPTION ""
    ::= { schCtpEntry 27 }

schCtpProvBaudRate   OBJECT-TYPE
    SYNTAX      InfnProvBaudRate
    MAX-ACCESS  read-create
    STATUS      current
    DESCRIPTION ""
    ::= { schCtpEntry 28 }

schCtpSupportingCarrGrpList   OBJECT-TYPE
    SYNTAX      DisplayString
    MAX-ACCESS  read-write
    STATUS      current
    DESCRIPTION ""
    ::= { schCtpEntry 29 }

schCtpOpticalSignal  OBJECT-TYPE
    SYNTAX      InfnOpticalSignal
    MAX-ACCESS  read-write
    STATUS      current
    DESCRIPTION ""
    ::= { schCtpEntry 30 }

schCtpAssocTeIntfList   OBJECT-TYPE
    SYNTAX      DisplayString
    MAX-ACCESS  read-only
    STATUS      current
    DESCRIPTION ""
    ::= { schCtpEntry 31 }

schCtpRxSchPowerOffset   OBJECT-TYPE
    SYNTAX      FloatArbitraryPrecision
    MAX-ACCESS  read-only
    STATUS      current
    DESCRIPTION ""
    ::= { schCtpEntry 32 }

schCtpFlexOptChnlList   OBJECT-TYPE
    SYNTAX      DisplayString
    MAX-ACCESS  read-only
    STATUS      current
    DESCRIPTION ""
    ::= { schCtpEntry 33 }

schCtpCarrierList   OBJECT-TYPE
    SYNTAX      DisplayString
    MAX-ACCESS  read-write
    STATUS      current
    DESCRIPTION ""
    ::= { schCtpEntry 34 }

schCtpPassBandList   OBJECT-TYPE
    SYNTAX      DisplayString
    MAX-ACCESS  read-write
    STATUS      current
    DESCRIPTION ""
    ::= { schCtpEntry 35 }

schCtpPassBandStatusList   OBJECT-TYPE
    SYNTAX      DisplayString
    MAX-ACCESS  read-write
    STATUS      current
    DESCRIPTION ""
    ::= { schCtpEntry 36 }

-- Conformance Statements
schCtpConformance    OBJECT IDENTIFIER ::= { schCtpMIB 3 }
schCtpCompliances    OBJECT IDENTIFIER ::= { schCtpConformance 1 }
schCtpGroups         OBJECT IDENTIFIER ::= { schCtpConformance 2 }

schCtpCompliance MODULE-COMPLIANCE
    STATUS current
    DESCRIPTION
    "Describes the requirements for conformance to the SCHCTP-MIB"
    MODULE
        MANDATORY-GROUPS { schCtpGroup }
    ::= { schCtpCompliances 1 }

schCtpGroup OBJECT-GROUP
    OBJECTS {
    schCtpPmHistStatsEnable       ,
    schCtpProvSuperChannelNum      ,
    schCtpProvModulation            ,
    schCtpProvEncoding               ,
    schCtpSpectralBandWidth           ,
    schCtpAggregrateRate               ,
    schCtpCarrierGroupMode               ,
    schCtpInstalledModulation             ,
    schCtpInstalledEncoding               ,
    schCtpChannelPlanType                 ,
    schCtpFrequencySlotPlanType           ,
    schCtpInstalledSuperChannelNum        ,
    schCtpOffset                          ,
    schCtpOffsetOverride                  ,
    schCtpSupportingCircuitIdList         ,
    schCtpAssociatedClientSCHCTP          ,
    schCtpPowerOffset                     ,
	schCtpExpectedTTI					  ,
    schCtpTransmitTTI                     ,
    schCtpRecievedTTI                     ,
    schCtpMonitoringMode                 ,
	schCtpTargetOpr,
	schCtpIntraSchCarrierRippleThreshold,
    schCtpShutterState,
    schCtpIntraSchCarRipple,
	schCtpFreqSlotList,
	schCtpSupportingCarrierList,
    schCtpProvBaudRate,
    schCtpSupportingCarrGrpList,
    schCtpProvBaudRate,
    schCtpOpticalSignal,
    schCtpAssocTeIntfList,
    schCtpRxSchPowerOffset,
    schCtpFlexOptChnlList,
    schCtpCarrierList,
    schCtpPassBandList,
    schCtpPassBandStatusList
    }
    STATUS current
    DESCRIPTION
        " A collection of objects for managing the SchCtp"
    ::= { schCtpGroups 1 }

END

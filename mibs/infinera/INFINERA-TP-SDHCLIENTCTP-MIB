-- *****************************************************************
-- INFINERA-TP-SDHCLIENTCTP-MIB
-- 
-- October 2008, Sharfuddin Syed / Narendra Gupta
-- 
-- 
-- Copyright (c) 2008-2012 by Infinera Inc.
-- All rights reserved.
-- ****************************************************************

INFINERA-TP-SDHCLIENTCTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    InfnServiceType,InfnEnableDisable,InfnServiceMode,
	InfnSMQ, InfnClientAction, InfnLoopbackType, InfnJ0TraceMode,
    InfnJ0MessageCompliance, InfnPmHistStatsControl FROM INFINERA-TC-MIB
    terminationPoint                            FROM INFINERA-REG-MIB;


sdhClientCtpMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 15 }



sdhClientCtpTable OBJECT-TYPE
    SYNTAX      SEQUENCE OF SdhClientCtpEntry
    MAX-ACCESS  not-accessible
    STATUS      current
    DESCRIPTION
        "A list of SdhClientCtp entries. Each entry is uniquely identified by the value of ifIndex."
    ::= { sdhClientCtpMIB 1 } 

sdhClientCtpEntry  OBJECT-TYPE
    SYNTAX      SdhClientCtpEntry
    MAX-ACCESS  not-accessible
    STATUS      current
    DESCRIPTION
        "A SdhClientCtp entry containing information pertaining to Infinera SdhClientCtp interfaces.
        Entries will exist in this table for interfaces of type sdhclientCtp."
    INDEX { ifIndex }
    ::= { sdhClientCtpTable 1 }


SdhClientCtpEntry  ::= SEQUENCE {
    sdhClientCtpTribPrbsGenMode                InfnEnableDisable,
    sdhClientCtpTribPrbsMonMode                InfnEnableDisable,
    sdhClientCtpSupportingCircuitIdList        DisplayString,
    sdhClientCtpLoopback                       InfnLoopbackType,
    sdhClientCtpPmHistStatsEnable              InfnPmHistStatsControl,
    sdhClientCtpConfiguredServiceType          InfnServiceType,
    sdhClientCtpRxJ0                           DisplayString,
    sdhClientCtpExpectedRxJ0                   DisplayString,
    sdhClientCtpTransmittedJ0                  DisplayString,
    sdhClientCtpRxJ0MessageLength              Integer32,
    sdhClientCtpRxJ0MismatchReporting          InfnEnableDisable,
    sdhClientCtpRxJ0TraceMode                  InfnJ0TraceMode,
    sdhClientCtpRxJ0MessageCompliance          InfnJ0MessageCompliance,
    sdhClientCtpRxBe15MinutesTce               Counter64,
    sdhClientCtpRxEs15MinutesTce               Integer32,
    sdhClientCtpRxSes15MinutesTce              Integer32,
    sdhClientCtpRxOfs15MinutesTce              Integer32,
    sdhClientCtpRxLoss15MinutesTce             Integer32,
    sdhClientCtpRxBeDayTce                     Counter64,
    sdhClientCtpRxEsDayTce                     Integer32,
    sdhClientCtpRxSesDayTce                    Integer32,
    sdhClientCtpRxOfsDayTce                    Integer32,
    sdhClientCtpRxLossDayTce                   Integer32,
    sdhClientCtpTxBe15MinutesTce               Counter64,
    sdhClientCtpTxEs15MinutesTce               Integer32,
    sdhClientCtpTxSes15MinutesTce              Integer32,
    sdhClientCtpTxOfs15MinutesTce              Integer32,
    sdhClientCtpTxBeDayTce                     Counter64,
    sdhClientCtpTxEsDayTce                     Integer32,
    sdhClientCtpTxSesDayTce                    Integer32,
    sdhClientCtpTxOfsDayTce                    Integer32,
    sdhClientCtpRxBe15MinutesTceReporting      TruthValue,
    sdhClientCtpRxEs15MinutesTceReporting      TruthValue,
    sdhClientCtpRxSes15MinutesTceReporting     TruthValue,
    sdhClientCtpRxBeDayTceReporting            TruthValue,
    sdhClientCtpRxEsDayTceReporting            TruthValue,
    sdhClientCtpRxSesDayTceReporting           TruthValue,
    sdhClientCtpRxOfs15MinutesTceReporting     TruthValue,
    sdhClientCtpRxOfsDayReporting              TruthValue,
    sdhClientCtpRxLoss15MinutesTceReporting    TruthValue,
    sdhClientCtpRxLossDayReporting             TruthValue,
    sdhClientCtpTxBe15MinutesTceReporting      TruthValue,
    sdhClientCtpTxEs15MinutesTceReporting      TruthValue,
    sdhClientCtpTxSes15MinutesTceReporting     TruthValue,
    sdhClientCtpTxBeDayTceReporting            TruthValue,
    sdhClientCtpTxEsDayTceReporting            TruthValue,
    sdhClientCtpTxSesDayTceReporting           TruthValue,
    sdhClientCtpTxOfs15MinutesTceReporting     TruthValue,
    sdhClientCtpTxOfsDayReporting              TruthValue,
    sdhClientCtpUasMonitoring                  InfnEnableDisable,
    sdhClientCtpRxUasDayTce                    Integer32,
    sdhClientCtpTxUasDayTce                    Integer32,
    sdhClientCtpTxUas15MinutesTce              Integer32,
    sdhClientCtpRxUas15MinutesTce              Integer32,
    sdhClientCtpRxUas15MinutesTceReporting     TruthValue,
    sdhClientCtpTxUas15MinutesTceReporting     TruthValue,
    sdhClientCtpRxUasDayTceReporting	       TruthValue,
    sdhClientCtpTxUasDayTceReporting 	       TruthValue,
    sdhClientCtpLinePrbsGenMode                InfnEnableDisable, 
    sdhClientCtpLinePrbsMonMode                InfnEnableDisable,
    sdhClientCtpServiceMode			           InfnServiceMode,
    sdhClientCtpServiceModeQualifier		   InfnSMQ,
    sdhClientCtpEncapClientDisableAction       InfnClientAction 
}

sdhClientCtpTribPrbsGenMode OBJECT-TYPE
    SYNTAX      InfnEnableDisable
    MAX-ACCESS  read-write
    STATUS      current
    DESCRIPTION "Flag which enables the generation of PRBS data on the transmit side."
    DEFVAL      { disabled }
    ::= { sdhClientCtpEntry  1 }


sdhClientCtpTribPrbsMonMode OBJECT-TYPE
    SYNTAX      InfnEnableDisable 
    MAX-ACCESS  read-write
    STATUS      current
    DESCRIPTION "Flag which enables the monitoring of bit errors."
    DEFVAL      { disabled }
    ::= { sdhClientCtpEntry  2 }


sdhClientCtpSupportingCircuitIdList OBJECT-TYPE
    SYNTAX      DisplayString
    MAX-ACCESS  read-only
    STATUS      current
    DESCRIPTION
        "An unordered list of the circuitIDs supporting this Managed Object.
        This string contains the string representation of each supporting
        circuitID, separated by a ',' (comma) if there is more than one
        supporting circuitID."
    ::= { sdhClientCtpEntry  3 }


sdhClientCtpLoopback OBJECT-TYPE
    SYNTAX   InfnLoopbackType
    MAX-ACCESS  read-write
    STATUS      current
    DESCRIPTION "Flag to enable the loopback."
    DEFVAL      { none }
    ::= { sdhClientCtpEntry  4 }


sdhClientCtpPmHistStatsEnable OBJECT-TYPE
    SYNTAX      InfnPmHistStatsControl  
    MAX-ACCESS  read-write
    STATUS      current
    DESCRIPTION "Flag to enable or disable PM collection."
    DEFVAL      { enabled }
    ::= { sdhClientCtpEntry  5 }


sdhClientCtpConfiguredServiceType OBJECT-TYPE
    SYNTAX      InfnServiceType 
    MAX-ACCESS  read-only
    STATUS      current
    DESCRIPTION "The configured payload type."
    ::= { sdhClientCtpEntry  6 }


sdhClientCtpRxJ0 OBJECT-TYPE
    SYNTAX      DisplayString
    MAX-ACCESS  read-only
    STATUS      current
    DESCRIPTION
        "The trace that we are receiving currently. (COs update the MOs only when
         there is a change in the filtered received trace). CRC at the first 
         byte is removed. Whatever is remaining is converted to
         ascii representation of hex string and reported to users. For example,
         Infinera followed by 0x1 character will result in string 'Infinera\01h'. 
         With this approach the length could be as large as
         256 characters."
    ::= { sdhClientCtpEntry  7 }


sdhClientCtpExpectedRxJ0 OBJECT-TYPE
    SYNTAX      DisplayString
    MAX-ACCESS  read-write
    STATUS      current
    DESCRIPTION
        "The J0 trace that is to be expected from the receive side from the 
        customer equipment. If not zero-length and different from 
        J0ReceivedTrace, a J0 mismatch alarm will be raised. Message is
        always ASCII characters."
    ::= { sdhClientCtpEntry  8 }


sdhClientCtpTransmittedJ0 OBJECT-TYPE
    SYNTAX      DisplayString
    MAX-ACCESS  read-write
    STATUS      current
    DESCRIPTION "Transmitted J0 message."
    ::= { sdhClientCtpEntry  9 }


sdhClientCtpRxJ0MessageLength OBJECT-TYPE
    SYNTAX      Integer32
    MAX-ACCESS  read-write
    STATUS      current
    DESCRIPTION "The length of J0 byte."
    DEFVAL      { 16 }
    ::= { sdhClientCtpEntry  10 }


sdhClientCtpRxJ0MismatchReporting OBJECT-TYPE
    SYNTAX      InfnEnableDisable 
    MAX-ACCESS  read-write
    STATUS      current
    DESCRIPTION "Flag that enables or disables the reporting of J0 trace 
    mismatch condition."
    DEFVAL      { disabled }
    ::= { sdhClientCtpEntry  11 }


sdhClientCtpRxJ0TraceMode OBJECT-TYPE
    SYNTAX   InfnJ0TraceMode 
    MAX-ACCESS  read-write
    STATUS      current
    DESCRIPTION "The trace mode."
    DEFVAL      { transparent }
    ::= { sdhClientCtpEntry  12 }


sdhClientCtpRxJ0MessageCompliance OBJECT-TYPE
    SYNTAX   InfnJ0MessageCompliance
    MAX-ACCESS  read-write
    STATUS      current
    DESCRIPTION "J0 Message trace compliance."
    DEFVAL      { ansiItu }
    ::= { sdhClientCtpEntry  13 }


sdhClientCtpRxBe15MinutesTce OBJECT-TYPE
    SYNTAX      Counter64
    MAX-ACCESS  read-write
    STATUS      current
    DESCRIPTION
        "Count of the number of errors within a block in the incoming clients
         SDH signal in 15 minutes."
    ::= { sdhClientCtpEntry  14 }


sdhClientCtpRxEs15MinutesTce OBJECT-TYPE
    SYNTAX      Integer32
    MAX-ACCESS  read-write
    STATUS      current
    DESCRIPTION "Count of BIP errors detected at the Section layer in 15 minute
    (in the incoming clients SONET signal). Up to eight Section BIP errors can 
    be detected per STS-N frame, with each error incrementing the Sonet-Rx-CV-S
    current second register."
    DEFVAL      { 120 }
    ::= { sdhClientCtpEntry  15 }


sdhClientCtpRxSes15MinutesTce OBJECT-TYPE
    SYNTAX      Integer32
    MAX-ACCESS  read-write
    STATUS      current
    DESCRIPTION "Count of the seconds during which30% or more RS block errors
    were detected or an LOS or SEF defect was present in 15 minutes."
    DEFVAL      { 3 }
    ::= { sdhClientCtpEntry  16 }


sdhClientCtpRxOfs15MinutesTce OBJECT-TYPE
    SYNTAX      Integer32
    MAX-ACCESS  read-write
    STATUS      current
    DESCRIPTION "Regenerator Section - Out of Frame Seconds. Count of the 
    number of seconds that Out of Frame is received in 15 minutes."
    DEFVAL      { 3 }
    ::= { sdhClientCtpEntry  17 }


sdhClientCtpRxLoss15MinutesTce OBJECT-TYPE
    SYNTAX      Integer32
    MAX-ACCESS  read-write
    STATUS      current
    DESCRIPTION "Regenerator Section - Loss of Signal Seconds. Count of the number
     of seconds that SDH client LOS is received in 15 minutes."
    DEFVAL      { 3 }
    ::= { sdhClientCtpEntry  18 }


sdhClientCtpRxBeDayTce OBJECT-TYPE
    SYNTAX      Counter64
    MAX-ACCESS  read-write
    STATUS      current
    DESCRIPTION
        "Count of the number of errors within a block in the incoming clients 
         SDH signal in 24 hours."
    ::= { sdhClientCtpEntry  19 }


sdhClientCtpRxEsDayTce OBJECT-TYPE
    SYNTAX      Integer32
    MAX-ACCESS  read-write
    STATUS      current
    DESCRIPTION "Count of BIP errors detected at the Section layer in 24 hours 
    (in the incoming clients SONET signal). Up to eight Section BIP errors can
    be detected per STS-N frame, with each error incrementing the Sonet-Rx-CV-S
    current second register."
    DEFVAL      { 1200 }
    ::= { sdhClientCtpEntry  20 }


sdhClientCtpRxSesDayTce OBJECT-TYPE
    SYNTAX      Integer32
    MAX-ACCESS  read-write
    STATUS      current
    DESCRIPTION "Count of the seconds during which30% or more RS block errors 
    were detected or an LOS or SEF defect was present in 24 hours."
    DEFVAL      { 7 }
    ::= { sdhClientCtpEntry  21 }


sdhClientCtpRxOfsDayTce OBJECT-TYPE
    SYNTAX      Integer32
    MAX-ACCESS  read-write
    STATUS      current
    DESCRIPTION "Regenerator Section - Out of Frame Seconds. Count of the number
    of seconds that Out of Frame is received in 24 hours."
    DEFVAL      { 7 }
    ::= { sdhClientCtpEntry  22 }


sdhClientCtpRxLossDayTce OBJECT-TYPE
    SYNTAX      Integer32
    MAX-ACCESS  read-write
    STATUS      current
    DESCRIPTION "Regenerator Section - Loss of Signal Seconds. Count of the 
    number of seconds that SDH client LOS is received in 24 hours."
    DEFVAL      { 3 }
    ::= { sdhClientCtpEntry  23 }


sdhClientCtpTxBe15MinutesTce OBJECT-TYPE
    SYNTAX      Counter64
    MAX-ACCESS  read-write
    STATUS      current
    DESCRIPTION
        "Count of the number of errors within a block in the SDH signal 
        received from the network and to be transmitted to the receiving client
         in 15 minutes."
    ::= { sdhClientCtpEntry  24 }


sdhClientCtpTxEs15MinutesTce OBJECT-TYPE
    SYNTAX      Integer32
    MAX-ACCESS  read-write
    STATUS      current
    DESCRIPTION "Count of the number of seconds during which (at any point 
    during the second) at least one Tx RS block error was detected or an LOS
     or SEF defect was present in 15 minutes."
    DEFVAL      { 120 }
    ::= { sdhClientCtpEntry  25 }


sdhClientCtpTxSes15MinutesTce OBJECT-TYPE
    SYNTAX      Integer32
    MAX-ACCESS  read-write
    STATUS      current
    DESCRIPTION "Count of the seconds during which K (=10000) or more 
    SONET TX BIP errors were detected or an LOS or SEF defect was present
    in 15 minutes."
    DEFVAL      { 3 }
    ::= { sdhClientCtpEntry  26 }


sdhClientCtpTxOfs15MinutesTce OBJECT-TYPE
    SYNTAX      Integer32
    MAX-ACCESS  read-write
    STATUS      current
    DESCRIPTION "Regenerator Section - Out of Frame Seconds. Count of the number
     of seconds that Out of  Frame is detected in 15 minutes."
    DEFVAL      { 3 }
    ::= { sdhClientCtpEntry  27 }


sdhClientCtpTxBeDayTce OBJECT-TYPE
    SYNTAX      Counter64
    MAX-ACCESS  read-write
    STATUS      current
    DESCRIPTION
        "Count of the number of errors within a block in the SDH signal 
        received from the network and to be transmitted to the receiving 
        client in 24 hours."
    ::= { sdhClientCtpEntry  28 }


sdhClientCtpTxEsDayTce OBJECT-TYPE
    SYNTAX      Integer32
    MAX-ACCESS  read-write
    STATUS      current
    DESCRIPTION "Count of the number of seconds during which (at any point 
    during the second) at least one Tx RS block error was detected or an LOS
    or SEF defect was present in 24 hours."
    DEFVAL      { 1200 }
    ::= { sdhClientCtpEntry  29 }


sdhClientCtpTxSesDayTce OBJECT-TYPE
    SYNTAX      Integer32
    MAX-ACCESS  read-write
    STATUS      current
    DESCRIPTION "Count of the seconds during which K (=10000) or more 
    SONET TX BIP errors were detected or an LOS or SEF defect was present 
    in 24 hours."
    DEFVAL      { 7 }
    ::= { sdhClientCtpEntry  30 }


sdhClientCtpTxOfsDayTce OBJECT-TYPE
    SYNTAX      Integer32
    MAX-ACCESS  read-write
    STATUS      current
    DESCRIPTION "Regenerator Section - Out of Frame Seconds. Count of the 
    number of seconds that Out of  Frame is detected in 24 hours."
    DEFVAL      { 7 }
    ::= { sdhClientCtpEntry  31 }


sdhClientCtpRxBe15MinutesTceReporting OBJECT-TYPE
    SYNTAX      TruthValue
    MAX-ACCESS  read-write
    STATUS      current
    DESCRIPTION "Flag that enables the reporting of RxBe15MinutesTce threshold crossing."
    DEFVAL      { false }
    ::= { sdhClientCtpEntry  32 }


sdhClientCtpRxEs15MinutesTceReporting OBJECT-TYPE
    SYNTAX      TruthValue
    MAX-ACCESS  read-write
    STATUS      current
    DESCRIPTION "Flag that enables the reporting of RxEs15Minutes threshold crossing."
    DEFVAL      { false }
    ::= { sdhClientCtpEntry  33 }


sdhClientCtpRxSes15MinutesTceReporting OBJECT-TYPE
    SYNTAX      TruthValue
    MAX-ACCESS  read-write
    STATUS      current
    DESCRIPTION "Flag that enables the reporting of RxSes15MinutesTce threshold crossing."
    DEFVAL      { false }
    ::= { sdhClientCtpEntry  34 }


sdhClientCtpRxBeDayTceReporting OBJECT-TYPE
    SYNTAX      TruthValue
    MAX-ACCESS  read-write
    STATUS      current
    DESCRIPTION "Flag that enables the reporting of RxBeDayTce threshold crossing."
    DEFVAL      { false }
    ::= { sdhClientCtpEntry  35 }


sdhClientCtpRxEsDayTceReporting OBJECT-TYPE
    SYNTAX      TruthValue
    MAX-ACCESS  read-write
    STATUS      current
    DESCRIPTION "Flag that enables the reporting of RxEsDayTce threshold crossing."
    DEFVAL      { false }
    ::= { sdhClientCtpEntry  36 }


sdhClientCtpRxSesDayTceReporting OBJECT-TYPE
    SYNTAX      TruthValue
    MAX-ACCESS  read-write
    STATUS      current
    DESCRIPTION "Flag that enables the reporting of RxSesDayTce threshold crossing."
    DEFVAL      { false }
    ::= { sdhClientCtpEntry  37 }


sdhClientCtpRxOfs15MinutesTceReporting OBJECT-TYPE
    SYNTAX      TruthValue
    MAX-ACCESS  read-write
    STATUS      current
    DESCRIPTION "Flag that enables the reporting of RxOfs15MinutesTce threshold crossing."
    DEFVAL      { false }
    ::= { sdhClientCtpEntry  38 }


sdhClientCtpRxOfsDayReporting OBJECT-TYPE
    SYNTAX      TruthValue
    MAX-ACCESS  read-write
    STATUS      current
    DESCRIPTION "Flag that enables the reporting of RxOfsDayTce threshold crossing."
    DEFVAL      { false }
    ::= { sdhClientCtpEntry  39 }


sdhClientCtpRxLoss15MinutesTceReporting OBJECT-TYPE
    SYNTAX      TruthValue
    MAX-ACCESS  read-write
    STATUS      current
    DESCRIPTION "Flag that enables the reporting of RxLoss15MinutesTce threshold crossing."
    DEFVAL      { false }
    ::= { sdhClientCtpEntry  40 }


sdhClientCtpRxLossDayReporting OBJECT-TYPE
    SYNTAX      TruthValue
    MAX-ACCESS  read-write
    STATUS      current
    DESCRIPTION "Flag that enables the reporting of RxLossDayTce threshold crossing."
    DEFVAL      { false }
    ::= { sdhClientCtpEntry  41 }


sdhClientCtpTxBe15MinutesTceReporting OBJECT-TYPE
    SYNTAX      TruthValue
    MAX-ACCESS  read-write
    STATUS      current
    DESCRIPTION "Flag that enables the reporting of TxBe15MinutesTce crossing."
    DEFVAL      { false }
    ::= { sdhClientCtpEntry  42 }


sdhClientCtpTxEs15MinutesTceReporting OBJECT-TYPE
    SYNTAX      TruthValue
    MAX-ACCESS  read-write
    STATUS      current
    DESCRIPTION "Flag that enables the reporting of TxEs15MinutesTce crossing."
    DEFVAL      { false }
    ::= { sdhClientCtpEntry  43 }


sdhClientCtpTxSes15MinutesTceReporting OBJECT-TYPE
    SYNTAX      TruthValue
    MAX-ACCESS  read-write
    STATUS      current
    DESCRIPTION "Flag that enables the reporting of TxSes15MinutesTce crossing."
    DEFVAL      { false }
    ::= { sdhClientCtpEntry  44 }


sdhClientCtpTxBeDayTceReporting OBJECT-TYPE
    SYNTAX      TruthValue
    MAX-ACCESS  read-write
    STATUS      current
    DESCRIPTION "Flag that enables the reporting of TxBeDayTce crossing."
    DEFVAL      { false }
    ::= { sdhClientCtpEntry  45 }


sdhClientCtpTxEsDayTceReporting OBJECT-TYPE
    SYNTAX      TruthValue
    MAX-ACCESS  read-write
    STATUS      current
    DESCRIPTION "Flag that enables the reporting of TxEsDayTce crossing."
    DEFVAL      { false }
    ::= { sdhClientCtpEntry  46 }


sdhClientCtpTxSesDayTceReporting OBJECT-TYPE
    SYNTAX      TruthValue
    MAX-ACCESS  read-write
    STATUS      current
    DESCRIPTION "Flag that enables the reporting of TxSefsDayTce crossing."
    DEFVAL      { false }
    ::= { sdhClientCtpEntry  47 }


sdhClientCtpTxOfs15MinutesTceReporting OBJECT-TYPE
    SYNTAX      TruthValue
    MAX-ACCESS  read-write
    STATUS      current
    DESCRIPTION "Flag that enables the reporting of TxOfs15MinutesTce crossing."
    DEFVAL      { false }
    ::= { sdhClientCtpEntry  48 }


sdhClientCtpTxOfsDayReporting OBJECT-TYPE
    SYNTAX      TruthValue
    MAX-ACCESS  read-write
    STATUS      current
    DESCRIPTION "Flag that enables the reporting of TxOfsDayTce crossing."
    DEFVAL      { false }
    ::= { sdhClientCtpEntry  49 }
    
sdhClientCtpUasMonitoring  OBJECT-TYPE
    SYNTAX      InfnEnableDisable
    MAX-ACCESS  read-write
    STATUS      current
    DESCRIPTION "Flag which enables/disables SDH Un-Available seconds PM Monitoring"
    DEFVAL      { disabled }
    ::= { sdhClientCtpEntry  50 }

sdhClientCtpRxUas15MinutesTce OBJECT-TYPE
    SYNTAX      Integer32
    MAX-ACCESS  read-write
    STATUS      current
    DESCRIPTION "15 minutest receive count for Unavailable seconds"
    DEFVAL      { 1 }
    ::= { sdhClientCtpEntry  51 }

sdhClientCtpRxUasDayTce OBJECT-TYPE
    SYNTAX      Integer32
    MAX-ACCESS  read-write
    STATUS      current
    DESCRIPTION "24 hour receive count for un available seconds."
    DEFVAL      { 1 }
    ::= { sdhClientCtpEntry  52 }

sdhClientCtpTxUas15MinutesTce OBJECT-TYPE
    SYNTAX      Integer32
    MAX-ACCESS  read-write
    STATUS      current
    DESCRIPTION "15 minutes transmit count for unavailable seconds."
    DEFVAL      { 1 }
    ::= { sdhClientCtpEntry  53 }

sdhClientCtpTxUasDayTce OBJECT-TYPE
    SYNTAX      Integer32
    MAX-ACCESS  read-write
    STATUS      current
    DESCRIPTION "24 hours transmit count for unavilable seconds."
    DEFVAL      { 1 }
    ::= { sdhClientCtpEntry  54 }

sdhClientCtpRxUas15MinutesTceReporting OBJECT-TYPE
    SYNTAX      TruthValue
    MAX-ACCESS  read-write
    STATUS      current
    DESCRIPTION "Flag that enables the reporting of SdhRxUas15MinutesTce crossing."
    DEFVAL      { false }
    ::= { sdhClientCtpEntry  55 }


sdhClientCtpRxUasDayTceReporting OBJECT-TYPE
    SYNTAX      TruthValue
    MAX-ACCESS  read-write
    STATUS      current
    DESCRIPTION "Flag that enables the reporting of SdhRxUasDayTce crossing."
    DEFVAL      { false }
    ::= { sdhClientCtpEntry  56 }

sdhClientCtpTxUas15MinutesTceReporting OBJECT-TYPE
    SYNTAX      TruthValue
    MAX-ACCESS  read-write
    STATUS      current
    DESCRIPTION "Flag that enables the reporting of sdhTxUas15MinutesTce crossing."
    DEFVAL      { false }
    ::= { sdhClientCtpEntry  57 }

sdhClientCtpTxUasDayTceReporting OBJECT-TYPE
    SYNTAX      TruthValue
    MAX-ACCESS  read-write
    STATUS      current
    DESCRIPTION "Flag that enables the reporting of SdhTxUasDayTce crossing."
    DEFVAL      { false }
    ::= { sdhClientCtpEntry  58 }

sdhClientCtpLinePrbsGenMode OBJECT-TYPE
    SYNTAX   InfnEnableDisable
    MAX-ACCESS  read-write
    STATUS      current
    DESCRIPTION "Flag which enables the generation of PRBS data on the Line side."
    DEFVAL      { disabled }
    ::= { sdhClientCtpEntry  59 }

sdhClientCtpLinePrbsMonMode OBJECT-TYPE
    SYNTAX  InfnEnableDisable
    MAX-ACCESS  read-write
    STATUS      current
    DESCRIPTION "Flag which enables the monitoring of bit errors."
    DEFVAL      { disabled }
    ::= { sdhClientCtpEntry  60 }

sdhClientCtpServiceMode 	OBJECT-TYPE
    SYNTAX     InfnServiceMode
    MAX-ACCESS read-only
    STATUS     current
    DESCRIPTION 
        "The Service Mode (SM) of the client CTP (i.e., the mode/type of service in which 
        this SDH client CTP is being used."
    ::= { sdhClientCtpEntry 61 }

sdhClientCtpServiceModeQualifier 	OBJECT-TYPE
    SYNTAX     InfnSMQ
    MAX-ACCESS read-only
    STATUS     current
    DESCRIPTION 
        "The Service Mode Qualifier (SMQ) of the SDH client CTP 
    (i.e., the mode/type of service in which this SDH client CTP is being used."
    ::= { sdhClientCtpEntry 62 }

sdhClientCtpEncapClientDisableAction OBJECT-TYPE
    SYNTAX      InfnClientAction
    MAX-ACCESS  read-write
    STATUS      current
    DESCRIPTION ""
    ::= { sdhClientCtpEntry 63 }


-- Conformance Statements
sdhClientCtpConformance    OBJECT IDENTIFIER ::= { sdhClientCtpMIB 3 }
sdhClientCtpCompliances    OBJECT IDENTIFIER ::= { sdhClientCtpConformance 1 }
sdhClientCtpGroups         OBJECT IDENTIFIER ::= { sdhClientCtpConformance 2 }

sdhClientCtpCompliance MODULE-COMPLIANCE
    STATUS current
    DESCRIPTION
    "Describes the requirements for conformance to the SDHCLIENTCTP-MIB"
    MODULE
        MANDATORY-GROUPS { sdhClientCtpGroup }
    ::= { sdhClientCtpCompliances 1 }

sdhClientCtpGroup OBJECT-GROUP
    OBJECTS {
        sdhClientCtpTribPrbsGenMode,
        sdhClientCtpTribPrbsMonMode,
        sdhClientCtpSupportingCircuitIdList,
        sdhClientCtpLoopback,
        sdhClientCtpPmHistStatsEnable,
        sdhClientCtpConfiguredServiceType,
        sdhClientCtpRxJ0,
        sdhClientCtpExpectedRxJ0,
        sdhClientCtpTransmittedJ0,
        sdhClientCtpRxJ0MessageLength,
        sdhClientCtpRxJ0MismatchReporting,
        sdhClientCtpRxJ0TraceMode,
        sdhClientCtpRxJ0MessageCompliance,
        sdhClientCtpRxBe15MinutesTce,
        sdhClientCtpRxEs15MinutesTce,
        sdhClientCtpRxSes15MinutesTce,
        sdhClientCtpRxOfs15MinutesTce,
        sdhClientCtpRxLoss15MinutesTce,
        sdhClientCtpRxBeDayTce,
        sdhClientCtpRxEsDayTce,
        sdhClientCtpRxSesDayTce,
        sdhClientCtpRxOfsDayTce,
        sdhClientCtpRxLossDayTce,
        sdhClientCtpTxBe15MinutesTce,
        sdhClientCtpTxEs15MinutesTce,
        sdhClientCtpTxSes15MinutesTce,
        sdhClientCtpTxOfs15MinutesTce,
        sdhClientCtpTxBeDayTce,
        sdhClientCtpTxEsDayTce,
        sdhClientCtpTxSesDayTce,
        sdhClientCtpTxOfsDayTce,
        sdhClientCtpRxBe15MinutesTceReporting,
        sdhClientCtpRxEs15MinutesTceReporting,
        sdhClientCtpRxSes15MinutesTceReporting,
        sdhClientCtpRxBeDayTceReporting,
        sdhClientCtpRxEsDayTceReporting,
        sdhClientCtpRxSesDayTceReporting,
        sdhClientCtpRxOfs15MinutesTceReporting,
        sdhClientCtpRxOfsDayReporting,
        sdhClientCtpRxLoss15MinutesTceReporting,
        sdhClientCtpRxLossDayReporting,
        sdhClientCtpTxBe15MinutesTceReporting,
        sdhClientCtpTxEs15MinutesTceReporting,
        sdhClientCtpTxSes15MinutesTceReporting,
        sdhClientCtpTxBeDayTceReporting,
        sdhClientCtpTxEsDayTceReporting,
        sdhClientCtpTxSesDayTceReporting,
        sdhClientCtpTxOfs15MinutesTceReporting,
        sdhClientCtpTxOfsDayReporting,
    	sdhClientCtpUasMonitoring,
	    sdhClientCtpRxUasDayTce,
    	sdhClientCtpTxUasDayTce,
	    sdhClientCtpTxUas15MinutesTce,
	    sdhClientCtpRxUas15MinutesTce,
	    sdhClientCtpRxUas15MinutesTceReporting,
	    sdhClientCtpTxUas15MinutesTceReporting,
	    sdhClientCtpRxUasDayTceReporting,
	    sdhClientCtpTxUasDayTceReporting,
	    sdhClientCtpServiceMode,
	    sdhClientCtpServiceModeQualifier   	,
        sdhClientCtpEncapClientDisableAction
    }
    STATUS current
    DESCRIPTION
        " A collection of objects for managing the sdhClientCtp"
    ::= { sdhClientCtpGroups 1 }


END

-- *****************************************************************
-- INFINERA-TP-XSCGPTP-MIB
--
-- September 2014, Anusree Bhattacharjee
--
--
-- Copyright (c) 2014 by Infinera Inc.
-- All rights reserved.
-- ****************************************************************

INFINERA-TP-XSCGPTP-MIB DEFINITIONS ::= BEGIN

IMPORTS
    MODULE-IDENTITY, OBJECT-TYPE, Integer32     FROM SNMPv2-SMI
    MODULE-COMPLIANCE, OBJECT-GROUP             FROM SNMPv2-CONF
    DisplayString, TruthValue                   FROM SNMPv2-TC
    ifIndex                                     FROM IF-MIB
    terminationPoint                            FROM INFINERA-REG-MIB
    InfnPCLOperatingMode, InfnOpticalSignal,
    InfnOpticalSignalStatus,
    FloatArbitraryPrecision,
    InfnPicStatus, InfnLicenseModulationType,
    InfnEqptType, InfnLineSystemMode,
	InfnAutoDiscoveryState, InfnAdTpType,
    InfnWaveInterfaceType, InfnPowerControlLoop,
    InfnEncoding, FloatHundredths, FloatTenths,
    InfnPmHistStatsControl, InfnEnableDisable,
    InfnFECOverHeadPercent                      FROM INFINERA-TC-MIB;


xScgPtpMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 57 }

xScgPtpTable OBJECT-TYPE
    SYNTAX      SEQUENCE OF XScgPtpEntry
    MAX-ACCESS  not-accessible
    STATUS      current
    DESCRIPTION
        "A list of XScgPtp entries. Each entry is uniquely identified by the value of ifIndex."
    ::= { xScgPtpMIB 1 }

xScgPtpEntry  OBJECT-TYPE
    SYNTAX      XScgPtpEntry
    MAX-ACCESS  not-accessible
    STATUS      current
    DESCRIPTION
        "A XScgPtp entry containing information pertaining to Infinera XScgPtp Interfaces.
        This table is a subclass of IfCommon. Entries will exist in this table only for
        interfaces of type OCG PTP."
    INDEX { ifIndex }
    ::= { xScgPtpTable 1 }


XScgPtpEntry  ::= SEQUENCE {
	xScgPtpOpenwaveTargetTxScgPower            FloatTenths,
    xScgPtpMPOAID                              DisplayString,
    xScgPtpProvisionedFPMPO                    DisplayString,
    xScgPtpAutoDiscoveryState                  InfnAutoDiscoveryState,
    xScgPtpDiscoveredNeighborTP                DisplayString,
    xScgPtpProvisionedNeighborTP               DisplayString,
    xScgPtpProvisionedNeighborAdTpType         InfnAdTpType,
    xScgPtpInterfaceType                       InfnWaveInterfaceType,
    xScgPtpProvisionedOpenWaveRemotePtp        DisplayString,
    xScgPtpPmHistStatsEnable                   InfnPmHistStatsControl,
    xScgPtpMaxFruGain                          FloatHundredths,
    xScgPtpRecommendedGain                     FloatTenths,
    xScgPtpRxEdfaOutputPowerTarget             FloatTenths,
    xScgPtpGain                                FloatTenths,
    xScgPtpAvailableTunableSchNumbers          DisplayString,
    xScgPtpPowerControlLoop                    InfnPowerControlLoop,
	xScgPtpProvisionedEncodingMode             InfnEncoding,
	xScgPtpInstalledEncodingMode               InfnEncoding,
	xScgPtpLineSystemMode                      InfnLineSystemMode,
    xScgPtpTargetTxPowerOffset                 FloatTenths,
    xScgPtpTargetTxPower                       FloatTenths,
    xScgPtpRxPowerOffset                       FloatTenths,
    xScgPtpProvisionedPeerTp                   DisplayString,
    xScgPtpBwQmax                              FloatTenths,
    xScgPtpBwQused                             FloatTenths,
    xScgPtpBwQlicensed                         FloatTenths,
    xScgPtpTxPicState                          InfnPicStatus,
    xScgPtpRxPicState                          InfnPicStatus,
    xScgPtpCarrierCount                        FloatTenths,
    xScgPtpLoopback                            TruthValue,
    xScgPtpDefFlexLicModFormat                 InfnLicenseModulationType,
    xScgPtpBwUsgWaterMarkGranularity           FloatTenths,
    xScgPtpFECOverheadRatio                    InfnFECOverHeadPercent,
    xScgPtpBw16Qmax                            FloatTenths,
    xScgPtpBw16Qused                           FloatTenths,
    xScgPtpBw16Qlicensed                       FloatTenths,
    xScgPtpBw8Qmax                             FloatTenths,
    xScgPtpBw8Qused                            FloatTenths,
    xScgPtpBw8Qlicensed                        FloatTenths,
    xScgPtpBw3Qmax                             FloatTenths,
    xScgPtpBw3Qused                            FloatTenths,
    xScgPtpBw3Qlicensed                        FloatTenths,
    xScgPtpBwBmax                              FloatTenths,
    xScgPtpBwBused                             FloatTenths,
    xScgPtpBwBlicensed                         FloatTenths,
    xScgPtpUnAssignedCarrierList               DisplayString,
    xScgPtpInstalledFECOHRatio                 InfnFECOverHeadPercent,
    xScgPtpRxPCLOprMode                        InfnPCLOperatingMode,
    xScgPtpInstalledRxPCLOprMode               InfnPCLOperatingMode,
    xScgPtpCarrierCount33Gbaud                 FloatArbitraryPrecision,
    xScgPtpCarrierCount22Gbaud                 FloatArbitraryPrecision,
    xScgPtpCarrierCount17Gbaud                 FloatArbitraryPrecision,
    xScgPtpOpticalSignal                       InfnOpticalSignal,
    xScgPtpOpticalSignalStatus                 InfnOpticalSignalStatus,
    xScgPtpPerCarrierTargetTxPower             FloatArbitraryPrecision,
    xScgPtpExpTotalTxPower                     FloatArbitraryPrecision
}

xScgPtpOpenwaveTargetTxScgPower   OBJECT-TYPE
    SYNTAX      FloatTenths
    MAX-ACCESS  read-write
    STATUS      current
    DESCRIPTION ""
    ::= { xScgPtpEntry 1 }

xScgPtpMPOAID OBJECT-TYPE
    SYNTAX      DisplayString
    MAX-ACCESS  read-write
    STATUS      current
    DESCRIPTION ""
    ::= { xScgPtpEntry 2 }

xScgPtpProvisionedFPMPO  OBJECT-TYPE
    SYNTAX      DisplayString
    MAX-ACCESS  read-write
    STATUS      current
    DESCRIPTION ""
    ::= { xScgPtpEntry 3 }

xScgPtpAutoDiscoveryState OBJECT-TYPE
    SYNTAX      InfnAutoDiscoveryState
    MAX-ACCESS  read-only
    STATUS      current
    DESCRIPTION ""
    ::= { xScgPtpEntry 4 }

xScgPtpDiscoveredNeighborTP OBJECT-TYPE
    SYNTAX      DisplayString
    MAX-ACCESS  read-only
    STATUS      current
    DESCRIPTION ""
    ::= { xScgPtpEntry 5 }

xScgPtpProvisionedNeighborTP OBJECT-TYPE
    SYNTAX      DisplayString
    MAX-ACCESS  read-write
    STATUS      current
    DESCRIPTION ""
    ::= { xScgPtpEntry 6 }

xScgPtpProvisionedNeighborAdTpType OBJECT-TYPE
    SYNTAX      InfnAdTpType
    MAX-ACCESS  read-only
    STATUS      current
    DESCRIPTION ""
    ::= { xScgPtpEntry 7 }

xScgPtpInterfaceType OBJECT-TYPE
    SYNTAX      InfnWaveInterfaceType
    MAX-ACCESS  read-write
    STATUS      current
    DESCRIPTION ""
    ::= { xScgPtpEntry 8 }

xScgPtpProvisionedOpenWaveRemotePtp OBJECT-TYPE
    SYNTAX      DisplayString
    MAX-ACCESS  read-write
    STATUS      current
    DESCRIPTION ""
    ::= { xScgPtpEntry 9 }

xScgPtpPmHistStatsEnable OBJECT-TYPE
    SYNTAX      InfnPmHistStatsControl
    MAX-ACCESS      read-write
    STATUS          current
    DESCRIPTION     ""
    ::= { xScgPtpEntry 10 }

xScgPtpMaxFruGain  OBJECT-TYPE
    SYNTAX      FloatHundredths
    MAX-ACCESS  read-only
    STATUS      current
    DESCRIPTION ""
    ::= { xScgPtpEntry 11 }

xScgPtpRecommendedGain OBJECT-TYPE
    SYNTAX          FloatTenths
    MAX-ACCESS      read-only
    STATUS          current
    DESCRIPTION     ""
    ::= { xScgPtpEntry 12 }

xScgPtpRxEdfaOutputPowerTarget  OBJECT-TYPE
    SYNTAX      FloatTenths
    MAX-ACCESS  read-only
    STATUS      current
    DESCRIPTION ""
    ::= { xScgPtpEntry 13 }

xScgPtpGain   OBJECT-TYPE
    SYNTAX      FloatTenths
    MAX-ACCESS  read-write
    STATUS      current
    DESCRIPTION ""
    ::= { xScgPtpEntry 14 }

xScgPtpAvailableTunableSchNumbers OBJECT-TYPE
    SYNTAX      DisplayString
    MAX-ACCESS  read-only
    STATUS      current
    DESCRIPTION ""
    ::= { xScgPtpEntry 15 }

xScgPtpPowerControlLoop OBJECT-TYPE
    SYNTAX      InfnPowerControlLoop
    MAX-ACCESS  read-write
    STATUS      current
    DESCRIPTION ""
    DEFVAL      { disabled }
    ::= { xScgPtpEntry 16 }

xScgPtpProvisionedEncodingMode OBJECT-TYPE
    SYNTAX      InfnEncoding
    MAX-ACCESS  read-write
    STATUS      current
    DESCRIPTION ""
    DEFVAL      { none }
    ::= { xScgPtpEntry 17 }

xScgPtpInstalledEncodingMode   OBJECT-TYPE
    SYNTAX      InfnEncoding
    MAX-ACCESS  read-write
    STATUS      current
    DESCRIPTION ""
    DEFVAL      { none }
    ::= { xScgPtpEntry 18 }

xScgPtpLineSystemMode OBJECT-TYPE
    SYNTAX      InfnLineSystemMode
    MAX-ACCESS  read-only
    STATUS      current
    DESCRIPTION ""
    DEFVAL      { modeOpenWave }
    ::= { xScgPtpEntry 19 }

xScgPtpTargetTxPowerOffset   OBJECT-TYPE
    SYNTAX      FloatTenths
    MAX-ACCESS  read-write
    STATUS      current
    DESCRIPTION ""
    ::= { xScgPtpEntry 20 }

xScgPtpTargetTxPower   OBJECT-TYPE
    SYNTAX      FloatTenths
    MAX-ACCESS  read-only
    STATUS      current
    DESCRIPTION ""
    ::= { xScgPtpEntry 21 }

xScgPtpRxPowerOffset   OBJECT-TYPE
    SYNTAX      FloatTenths
    MAX-ACCESS  read-write
    STATUS      current
    DESCRIPTION ""
    ::= { xScgPtpEntry 22 }

xScgPtpProvisionedPeerTp OBJECT-TYPE
    SYNTAX      DisplayString
    MAX-ACCESS  read-write
    STATUS      current
    DESCRIPTION ""
    ::= { xScgPtpEntry 23 }

xScgPtpBwQmax  OBJECT-TYPE
    SYNTAX      FloatTenths
    MAX-ACCESS  read-only
    STATUS      current
    DESCRIPTION ""
    ::= { xScgPtpEntry 24 }

xScgPtpBwQused  OBJECT-TYPE
    SYNTAX      FloatTenths
    MAX-ACCESS  read-only
    STATUS      current
    DESCRIPTION ""
    ::= { xScgPtpEntry 25 }

xScgPtpBwQlicensed  OBJECT-TYPE
    SYNTAX      FloatTenths
    MAX-ACCESS  read-only
    STATUS      current
    DESCRIPTION ""
    ::= { xScgPtpEntry 26 }

xScgPtpTxPicState  OBJECT-TYPE
    SYNTAX      InfnPicStatus
    MAX-ACCESS  read-only
    STATUS      current
    DESCRIPTION ""
    ::= { xScgPtpEntry 27 }

xScgPtpRxPicState  OBJECT-TYPE
    SYNTAX      InfnPicStatus
    MAX-ACCESS  read-only
    STATUS      current
    DESCRIPTION ""
    ::= { xScgPtpEntry 28 }

xScgPtpCarrierCount  OBJECT-TYPE
    SYNTAX      FloatTenths
    MAX-ACCESS  read-only
    STATUS      current
    DESCRIPTION ""
    ::= { xScgPtpEntry 29 }

xScgPtpLoopback  OBJECT-TYPE
    SYNTAX      TruthValue
    MAX-ACCESS  read-only
    STATUS      current
    DESCRIPTION ""
    ::= { xScgPtpEntry 30 }

xScgPtpDefFlexLicModFormat  OBJECT-TYPE
    SYNTAX      InfnLicenseModulationType
    MAX-ACCESS  read-only
    STATUS      current
    DESCRIPTION ""
    ::= { xScgPtpEntry 31 }

xScgPtpBwUsgWaterMarkGranularity  OBJECT-TYPE
    SYNTAX      FloatTenths
    MAX-ACCESS  read-only
    STATUS      current
    DESCRIPTION ""
    ::= { xScgPtpEntry 32 }

xScgPtpFECOverheadRatio OBJECT-TYPE
    SYNTAX      InfnFECOverHeadPercent
    MAX-ACCESS  read-write
    STATUS      current
    DESCRIPTION ""
    ::= { xScgPtpEntry 33 }

xScgPtpBw16Qmax OBJECT-TYPE
    SYNTAX          FloatTenths
    MAX-ACCESS      read-only
    STATUS          current
    DESCRIPTION     ""
    ::= { xScgPtpEntry 34 }

xScgPtpBw16Qused OBJECT-TYPE
    SYNTAX          FloatTenths
    MAX-ACCESS      read-only
    STATUS          current
    DESCRIPTION     ""
    ::= { xScgPtpEntry 35 }

xScgPtpBw16Qlicensed OBJECT-TYPE
    SYNTAX          FloatTenths
    MAX-ACCESS      read-only
    STATUS          current
    DESCRIPTION     ""
    ::= { xScgPtpEntry 36 }

xScgPtpBw8Qmax OBJECT-TYPE
    SYNTAX          FloatTenths
    MAX-ACCESS      read-only
    STATUS          current
    DESCRIPTION     ""
    ::= { xScgPtpEntry 37 }

xScgPtpBw8Qused OBJECT-TYPE
    SYNTAX          FloatTenths
    MAX-ACCESS      read-only
    STATUS          current
    DESCRIPTION     ""
    ::= { xScgPtpEntry 38 }

xScgPtpBw8Qlicensed OBJECT-TYPE
    SYNTAX          FloatTenths
    MAX-ACCESS      read-only
    STATUS          current
    DESCRIPTION     ""
    ::= { xScgPtpEntry 39 }

xScgPtpBw3Qmax OBJECT-TYPE
    SYNTAX          FloatTenths
    MAX-ACCESS      read-only
    STATUS          current
    DESCRIPTION     ""
    ::= { xScgPtpEntry 40 }

xScgPtpBw3Qused OBJECT-TYPE
    SYNTAX          FloatTenths
    MAX-ACCESS      read-only
    STATUS          current
    DESCRIPTION     ""
    ::= { xScgPtpEntry 41 }

xScgPtpBw3Qlicensed OBJECT-TYPE
    SYNTAX          FloatTenths
    MAX-ACCESS      read-only
    STATUS          current
    DESCRIPTION     ""
    ::= { xScgPtpEntry 42 }

xScgPtpBwBmax OBJECT-TYPE
    SYNTAX          FloatTenths
    MAX-ACCESS      read-only
    STATUS          current
    DESCRIPTION     ""
    ::= { xScgPtpEntry 43 }

xScgPtpBwBused OBJECT-TYPE
    SYNTAX          FloatTenths
    MAX-ACCESS      read-only
    STATUS          current
    DESCRIPTION     ""
    ::= { xScgPtpEntry 44 }

xScgPtpBwBlicensed OBJECT-TYPE
    SYNTAX          FloatTenths
    MAX-ACCESS      read-only
    STATUS          current
    DESCRIPTION     ""
    ::= { xScgPtpEntry 45 }

xScgPtpUnAssignedCarrierList OBJECT-TYPE
    SYNTAX      DisplayString
    MAX-ACCESS  read-only
    STATUS      current
    DESCRIPTION ""
    ::= { xScgPtpEntry 46 }

xScgPtpInstalledFECOHRatio OBJECT-TYPE
    SYNTAX      InfnFECOverHeadPercent
    MAX-ACCESS  read-only
    STATUS      current
    DESCRIPTION ""
    ::= { xScgPtpEntry 47 }

xScgPtpRxPCLOprMode OBJECT-TYPE
    SYNTAX      InfnPCLOperatingMode
    MAX-ACCESS  read-write
    STATUS      current
    DESCRIPTION ""
    ::= { xScgPtpEntry 48 }

xScgPtpInstalledRxPCLOprMode OBJECT-TYPE
    SYNTAX      InfnPCLOperatingMode
    MAX-ACCESS  read-write
    STATUS      current
    DESCRIPTION ""
    ::= { xScgPtpEntry 49 }

xScgPtpCarrierCount33Gbaud OBJECT-TYPE
    SYNTAX      FloatArbitraryPrecision
    MAX-ACCESS  read-write
    STATUS      current
    DESCRIPTION ""
    ::= { xScgPtpEntry 50 }

xScgPtpCarrierCount22Gbaud OBJECT-TYPE
    SYNTAX      FloatArbitraryPrecision
    MAX-ACCESS  read-write
    STATUS      current
    DESCRIPTION ""
    ::= { xScgPtpEntry 51 }

xScgPtpCarrierCount17Gbaud OBJECT-TYPE
    SYNTAX      FloatArbitraryPrecision
    MAX-ACCESS  read-write
    STATUS      current
    DESCRIPTION ""
    ::= { xScgPtpEntry 52 }

xScgPtpOpticalSignal OBJECT-TYPE
    SYNTAX      InfnOpticalSignal
    MAX-ACCESS  read-write
    STATUS      current
    DESCRIPTION ""
    ::= { xScgPtpEntry 53 }

xScgPtpOpticalSignalStatus OBJECT-TYPE
    SYNTAX      InfnOpticalSignalStatus
    MAX-ACCESS  read-only
    STATUS      current
    DESCRIPTION ""
    ::= { xScgPtpEntry 54 }

xScgPtpPerCarrierTargetTxPower OBJECT-TYPE
    SYNTAX      FloatArbitraryPrecision
    MAX-ACCESS  read-write
    STATUS      current
    DESCRIPTION ""
    ::= { xScgPtpEntry 55 }

xScgPtpExpTotalTxPower OBJECT-TYPE
    SYNTAX      FloatArbitraryPrecision
    MAX-ACCESS  read-only
    STATUS      current
    DESCRIPTION ""
    ::= { xScgPtpEntry 56 }

-- Conformance Statement
xScgPtpConformance    OBJECT IDENTIFIER ::= { xScgPtpMIB 3 }
xScgPtpCompliances    OBJECT IDENTIFIER ::= { xScgPtpConformance 1 }
xScgPtpGroups         OBJECT IDENTIFIER ::= { xScgPtpConformance 2 }

xScgPtpCompliance MODULE-COMPLIANCE
    STATUS current
    DESCRIPTION
    "Describes the requirements for conformance to the XSCGPTP-MIB"
    MODULE
        MANDATORY-GROUPS { xScgPtpGroup }
    ::= { xScgPtpCompliances 1 }

xScgPtpGroup OBJECT-GROUP
    OBJECTS {
        xScgPtpOpenwaveTargetTxScgPower,
        xScgPtpMPOAID,
        xScgPtpProvisionedFPMPO,
        xScgPtpAutoDiscoveryState,
        xScgPtpDiscoveredNeighborTP,
        xScgPtpProvisionedNeighborTP,
        xScgPtpProvisionedNeighborAdTpType,
        xScgPtpInterfaceType,
        xScgPtpProvisionedOpenWaveRemotePtp,
        xScgPtpPmHistStatsEnable,
        xScgPtpMaxFruGain,
        xScgPtpRecommendedGain,
        xScgPtpRxEdfaOutputPowerTarget,
        xScgPtpGain,
        xScgPtpAvailableTunableSchNumbers,
        xScgPtpPowerControlLoop,
        xScgPtpProvisionedEncodingMode,
        xScgPtpInstalledEncodingMode,
        xScgPtpLineSystemMode,
        xScgPtpTargetTxPowerOffset,
        xScgPtpTargetTxPower,
        xScgPtpRxPowerOffset,
        xScgPtpProvisionedPeerTp,
        xScgPtpBwQmax,
        xScgPtpBwQused,
        xScgPtpBwQlicensed,
        xScgPtpTxPicState,
        xScgPtpRxPicState,
        xScgPtpCarrierCount,
        xScgPtpLoopback,
        xScgPtpDefFlexLicModFormat,
        xScgPtpBwUsgWaterMarkGranularity,
        xScgPtpFECOverheadRatio,
        xScgPtpBw16Qmax,
        xScgPtpBw16Qused,
        xScgPtpBw16Qlicensed,
        xScgPtpBw8Qmax,
        xScgPtpBw8Qused,
        xScgPtpBw8Qlicensed,
        xScgPtpBw3Qmax,
        xScgPtpBw3Qused,
        xScgPtpBw3Qlicensed,
        xScgPtpBwBmax,
        xScgPtpBwBused,
        xScgPtpBwBlicensed,
        xScgPtpUnAssignedCarrierList,
        xScgPtpInstalledFECOHRatio,
        xScgPtpRxPCLOprMode,
        xScgPtpCarrierCount33Gbaud,
        xScgPtpCarrierCount22Gbaud,
        xScgPtpCarrierCount17Gbaud,
        xScgPtpOpticalSignal,
        xScgPtpOpticalSignalStatus,
        xScgPtpInstalledRxPCLOprMode,
        xScgPtpPerCarrierTargetTxPower,
        xScgPtpExpTotalTxPower
    }
    STATUS current
    DESCRIPTION
        " A collection of objects for managing the xScgPtp"
    ::= { xScgPtpGroups 1 }


END

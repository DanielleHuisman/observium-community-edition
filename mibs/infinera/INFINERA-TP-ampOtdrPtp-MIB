-- *****************************************************************
-- INFINERA-TP-AmpOTDRPtp-MIB
--   
-- Copyright (c) 2008-2012 by Infinera Inc.
-- All rights reserved.
-- ****************************************************************

INFINERA-TP-ampOtdrPtp-MIB DEFINITIONS ::= BEGIN

IMPORTS
    MODULE-IDENTITY, OBJECT-TYPE                FROM SNMPv2-SMI
    MODULE-COMPLIANCE, OBJECT-GROUP             FROM SNMPv2-CONF
    ifIndex                                     FROM IF-MIB
    terminationPoint                            FROM INFINERA-REG-MIB
    DisplayString                               FROM SNMPv2-TC;

ampOtdrPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION " "
    REVISION    "201310200000Z"
    DESCRIPTION "First Version"
    ::= { terminationPoint 49 }

ampOtdrPtpTable OBJECT-TYPE
    SYNTAX      SEQUENCE OF AmpOtdrPtpEntry
    MAX-ACCESS  not-accessible
    STATUS      current
    DESCRIPTION 
        "A list of ampOtdrPtp entries. Each entry is uniquely identified by the value of ifIndex."
    ::= { ampOtdrPtpMIB 1 } 

ampOtdrPtpEntry  OBJECT-TYPE  
    SYNTAX      AmpOtdrPtpEntry
    MAX-ACCESS  not-accessible
    STATUS      current
    DESCRIPTION "" 
    INDEX { ifIndex }
    ::= { ampOtdrPtpTable 1 }


AmpOtdrPtpEntry  ::= SEQUENCE { 
    ampOtdrPtpConnectivityState             INTEGER,
    ampOtdrPtpLstSuccConnValidationTime     Integer32,
    ampOtdrPtpExpectedNeighborPtp           DisplayString
}

ampOtdrPtpConnectivityState OBJECT-TYPE
    SYNTAX      INTEGER {
        notVerified(1),
        valid(2),
        inValid(3)
    }
    MAX-ACCESS  read-only
    STATUS      current
    DESCRIPTION ""
    ::= { ampOtdrPtpEntry  1 }


ampOtdrPtpLstSuccConnValidationTime OBJECT-TYPE
    SYNTAX      Integer32
    MAX-ACCESS  read-only
    STATUS      current
    DESCRIPTION ""
    ::= { ampOtdrPtpEntry  2 }

ampOtdrPtpExpectedNeighborPtp   OBJECT-TYPE
    SYNTAX      DisplayString
    MAX-ACCESS  read-write
    STATUS      current
    DESCRIPTION ""
    ::= { ampOtdrPtpEntry  3 }

-- Conformance Statements 
ampOtdrPtpConformance    OBJECT IDENTIFIER ::= { ampOtdrPtpMIB 3 } 
ampOtdrPtpCompliances    OBJECT IDENTIFIER ::= { ampOtdrPtpConformance 1 } 
ampOtdrPtpGroups         OBJECT IDENTIFIER ::= { ampOtdrPtpConformance 2 } 

ampOtdrPtpCompliance MODULE-COMPLIANCE
    STATUS current
    DESCRIPTION
    "Describes the requirements for conformance to the ampOtdrPtp-MIB"
    MODULE
        MANDATORY-GROUPS { ampOtdrPtpGroup }
    ::= { ampOtdrPtpCompliances 1 }

ampOtdrPtpGroup OBJECT-GROUP
    OBJECTS { 
        ampOtdrPtpConnectivityState,
        ampOtdrPtpLstSuccConnValidationTime,
        ampOtdrPtpExpectedNeighborPtp
    }
    STATUS current
    DESCRIPTION
        " A collection of objects for managing the ampOtdrPtp"
    ::= { ampOtdrPtpGroups 1 }
END

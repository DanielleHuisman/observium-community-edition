--------------------------------------------------------------------------
-- INFINERA-TRAP-MIB:  Infinera SNMP FIS Trap MIB file
--
-- May 2011, Varatharajan
--
-- (c) Copyright 2012 Infinera Corporation. All rights reserved.
--------------------------------------------------------------------------
 

INFINERA-TRAP-MIB	DEFINITIONS ::= BEGIN
	IMPORTS
		DisplayString
			FROM SNMPv2-TC

		ems
			FROM INFINERA-REG-MIB

		OBJECT-GROUP, NOTIFICATION-GROUP
			FROM SNMPv2-CONF
		OBJECT-TYPE, NOTIFICATION-TYPE, MODULE-IDENTITY, 
		Integer32, enterprises
			FROM SNMPv2-SMI;


emsEvent	MODULE-IDENTITY
		LAST-UPDATED	"200505251000Z"
		ORGANIZATION	"Infinera"
		CONTACT-INFO	"Infinera
                        	1322 Bordeaux Drive
                        	Sunnyvale, CA - 94089
	
                        	Contact : Technical Support
                        	Email   : support@infinera.com
                        	Phone   : 1-877-INF-5288"
		DESCRIPTION	"Module representing Events generated 
				by Infinera Network Elements"
		::=  {  ems  1  }

emsAlarmTable OBJECT-TYPE
	SYNTAX  SEQUENCE OF EmsAlarmEntry
	MAX-ACCESS   not-accessible
	STATUS  current
	DESCRIPTION
		"A list of Alarm entries.  The number of
		entries is given by the value of emsNotificationId."
	::= { ems 2 }

emsAlarmEntry OBJECT-TYPE
      SYNTAX  EmsAlarmEntry
      MAX-ACCESS  not-accessible
      STATUS  current
      DESCRIPTION
	      "An Alarm entry containing all the information
	      pertaining to Infinera Alarm as per TMF814 model."
      INDEX   { emsNotificationId }
      ::= { emsAlarmTable 1 }

emsAuditTable OBJECT-TYPE
	SYNTAX  SEQUENCE OF EmsAuditEntry
	MAX-ACCESS  not-accessible
	STATUS  current
	DESCRIPTION
		"A list of Audit entries.  The number of
		entries is given by the value of auditEmsNotificationId."
	::= { ems 3 }

emsAuditEntry OBJECT-TYPE
      SYNTAX  EmsAuditEntry
      MAX-ACCESS  not-accessible
      STATUS  current
      DESCRIPTION
	      "An Audit entry containing all the information
	      pertaining to Infinera Audit Event."
      INDEX   { auditEmsNotificationId }
      ::= { emsAuditTable 1 }

emsAdminTable OBJECT-TYPE
	SYNTAX  SEQUENCE OF EmsAdminEntry
	MAX-ACCESS  not-accessible
	STATUS  current
	DESCRIPTION
		"A list of Admin entries.  The number of
		entries is given by the value of adminEmsNotificationId."
	::= { ems 4 }

emsAdminEntry OBJECT-TYPE
      SYNTAX  EmsAdminEntry
      MAX-ACCESS  not-accessible
      STATUS  current
      DESCRIPTION
	      "An Admin entry containing all the information
	      pertaining to Infinera Admin Event."
      INDEX   { adminEmsNotificationId }
      ::= { emsAdminTable 1 }

emsSecurityTable OBJECT-TYPE
	SYNTAX  SEQUENCE OF EmsSecurityEntry
	MAX-ACCESS  not-accessible
	STATUS  current
	DESCRIPTION
		"A list of Security entries.  The number of
		entries is given by the value of securityEmsNotificationId."
	::= { ems 5 }

emsSecurityEntry OBJECT-TYPE
      SYNTAX  EmsSecurityEntry
      MAX-ACCESS  not-accessible
      STATUS  current
      DESCRIPTION
	      "An Security entry containing all the information
	      pertaining to Infinera Security Event."
      INDEX   { securityEmsNotificationId }
      ::= { emsSecurityTable 1 }

emsTCATable OBJECT-TYPE
	SYNTAX  SEQUENCE OF EmsTCAEntry
	MAX-ACCESS  not-accessible
	STATUS  current
	DESCRIPTION
		"A list of TCA entries.  The number of
		entries is given by the value of tcaEmsNotificationId."
	::= { ems 6 }

emsTCAEntry OBJECT-TYPE
      SYNTAX  EmsTCAEntry
      MAX-ACCESS  not-accessible
      STATUS  current
      DESCRIPTION
	      "An TCA entry containing all the information
	      pertaining to Infinera TCA Event."
      INDEX   { tcaEmsNotificationId }
      ::= { emsTCATable 1 }

-- 
-- Generic attributes - common to all events are defined below
-- 

emsNotificationId	OBJECT-TYPE	
			SYNTAX		Integer32  ( 0 .. 2147483647  ) 
			MAX-ACCESS	accessible-for-notify
			STATUS		current
			DESCRIPTION	"The Notification ID generated by EMS for
			each trap forwarded to NBI/OSS."
			::=  {  emsAlarmEntry  1  }

neNotificationId	OBJECT-TYPE	
			SYNTAX		Integer32  ( 0 .. 2147483647  ) 
			MAX-ACCESS	read-only
			STATUS		current
			DESCRIPTION	"Maps to the Notification ID generated
					by Infinera NE. Since this is specific 
					to each NE, the NE Name attribute should 
					be used in conjunction with this attribute."
			::=  {  emsAlarmEntry  2 }

emsTime		OBJECT-TYPE	
		SYNTAX		DisplayString
		MAX-ACCESS	read-only
		STATUS		current
		DESCRIPTION	"ems time in ISO 8601 format YYYY-MM-DD<space>hh:mm:ss.mmmm<Z>"
		::=  {  emsAlarmEntry  3  }

neTime		OBJECT-TYPE	
		SYNTAX		DisplayString
		MAX-ACCESS	read-only
		STATUS		current
		DESCRIPTION	"ne time in ISO 8601 format YYYY-MM-DD<space>hh:mm:ss.mmmm<Z>"
		::=  {  emsAlarmEntry  4  }

emsName		OBJECT-TYPE	
		SYNTAX		DisplayString  ( SIZE ( 255  ) ) 
		MAX-ACCESS	read-only
		STATUS		current
		DESCRIPTION	"EMS Name or IP Address of the EMS Server.
				This is useful if one NBI Client connects 
				to more than EMS and receives traps. Default is Infinera"
		::=  {  emsAlarmEntry  5  }

neName		OBJECT-TYPE	
		SYNTAX		DisplayString  ( SIZE ( 1 .. 20  ) ) 
		MAX-ACCESS	read-only
		STATUS		current
		DESCRIPTION	"The Name of the network element. This maps
				to the ME Name of the Info Model."
		::=  {  emsAlarmEntry  6  }

neNodeId		OBJECT-TYPE	
		SYNTAX		DisplayString  ( SIZE ( 1 .. 128  ) ) 
		MAX-ACCESS	read-only
		STATUS		current
		DESCRIPTION	"The Node ID of the network element. "
		::=  {  emsAlarmEntry  7  }

objectType	OBJECT-TYPE	
		SYNTAX		DisplayString
		MAX-ACCESS	read-only
		STATUS		current
		DESCRIPTION	"Represents MO Type on Infinera Info Mode/XML Interface"
		::=  {  emsAlarmEntry  8  }

objectName	OBJECT-TYPE	
		SYNTAX		DisplayString
		MAX-ACCESS	read-only
		STATUS		current
		DESCRIPTION	"Represents AID of an object"
		::=  {  emsAlarmEntry  9  }

sessionNotificationId	OBJECT-TYPE	
		SYNTAX		Integer32  ( 0 .. 2147483647  ) 
		MAX-ACCESS	read-only
		STATUS		current
		DESCRIPTION	"Represents the notification ID on a per session
					basis. This will allow individual OSS clients to
					retrieve missing traps in that session."
		::=  {  emsAlarmEntry  10  }

--
-- Attributes specific to Alarms are defined below
--

neProbableCause	OBJECT-TYPE	
		SYNTAX		DisplayString
		MAX-ACCESS	read-only
		STATUS		current
		DESCRIPTION	"NE probabale cause. Represents 
				nativeProbableCause in TMF 814"
		::=  {  emsAlarmEntry  11  }

emsProbableCause	OBJECT-TYPE	
			SYNTAX		DisplayString
			MAX-ACCESS	read-only
			STATUS		current
			DESCRIPTION	"EMS Probable Cause. Represents 
					probableCause in TMF 814"
			::=  {  emsAlarmEntry  12  }

perceivedSeverity	OBJECT-TYPE	
			SYNTAX		INTEGER  { 
						psIndeterminate ( 1 ) , 
						psCritical ( 2 ) , 
						psMajor ( 3 ) , 
						psMinor ( 4 ) , 
						psWarning ( 5 ) , 
						psCleared ( 6 ) 
						} 
			MAX-ACCESS	read-only
			STATUS		current
			DESCRIPTION	"Perceived Severity. 
					Maps to perceivedSeverity in TMF 814 and 
					Infinera XML interface."
			::=  {  emsAlarmEntry  13  }

assertedSeverity	OBJECT-TYPE
			SYNTAX		INTEGER  { 
						psIndeterminate ( 1 ) , 
						psCritical ( 2 ) , 
						psMajor ( 3 ) , 
						psMinor ( 4 ) , 
						psWarning ( 5 ) , 
						psCleared ( 6 ) 
						} 
			MAX-ACCESS	read-only
			STATUS		current
			DESCRIPTION	"The severity with which this alarm was asserted."
			::=  {  emsAlarmEntry  14  }

serviceAffecting	OBJECT-TYPE	
			SYNTAX		INTEGER  
					{ 
					saUnknown ( 1 ) , 
					saServiceAffecting ( 2 ) , 
					saNonServiceAffecting ( 3 ) 
					} 
			MAX-ACCESS	read-only
			STATUS		current
			DESCRIPTION	"The value specifies if the alarm is 
					for a service affecting condition or not."
			::=  {  emsAlarmEntry  15  }

probableCauseDescription	OBJECT-TYPE	
			SYNTAX		DisplayString  ( SIZE ( 0 .. 255  ) ) 
			MAX-ACCESS	read-only
			STATUS		current
			DESCRIPTION	"Descriptive text for the probableCause 
					attribute. The term is mapped to the 
					probableCauseDescription field of alarms 
					raised by Infinera Network Elements"
			::=  {  emsAlarmEntry  16  }

category	OBJECT-TYPE	
			SYNTAX		INTEGER  { 	unknown ( 1 ) ,
								equipment ( 2 ) , 
								facility ( 3 ) ,
								communications ( 4 ),
								softwareProcessing ( 5 ),
								environmental ( 6 ),
								qualityOfService ( 7 ),
								ems (8)
							} 
			MAX-ACCESS	read-only
			STATUS		current
			DESCRIPTION	"Represents the category of the object that 
					caused the alarm."
			::=  {  emsAlarmEntry  17  }

--
-- Attributes derived from AT&T EMS-NMS Interface Spec
--

proposedRepairActions 	OBJECT-TYPE	
		SYNTAX		DisplayString
		MAX-ACCESS	read-only
		STATUS		current
		DESCRIPTION	"If the cause of the alarm is known, 
					the EMS can suggest one or more solutions 
					to the problem. Not Mandatory"
		::=  {  emsAlarmEntry  18  }	
		
--
-- Additional Text field.
--

additionalText	OBJECT-TYPE	
		SYNTAX		DisplayString
		MAX-ACCESS	read-only
		STATUS		current
		DESCRIPTION	"Additional text describing the alarm"
		::=  {  emsAlarmEntry  19  }

--
-- Attributes for Correlation ID
--

emsCorrelationId	OBJECT-TYPE	
		SYNTAX		Integer32  ( 0 .. 2147483647  ) 
		MAX-ACCESS	read-only
		STATUS		current
		DESCRIPTION	"Represents the correlation ID generated by
					the EMS."
		::=  {  emsAlarmEntry  20  }
		
neCorrelationId	OBJECT-TYPE	
		SYNTAX		Integer32  ( 0 .. 2147483647  ) 
		MAX-ACCESS	read-only
		STATUS		current
		DESCRIPTION	"Represents the correlation ID generated by
					the Network Element."
		::=  {  emsAlarmEntry  21  }	
		
--
-- Attribute for representing the circuit id of the service in trib PTP and client CTP alarms. Added in FIS release 7.0
--
		
circuitId	OBJECT-TYPE	
		SYNTAX		DisplayString
		MAX-ACCESS	read-only
		STATUS		current
		DESCRIPTION	"Represents the circuit id of the service carried by the source of this alarm"
		::=  {  emsAlarmEntry  22  }

--
-- Attributes specific to Audit Events are defined below
--

auditEmsNotificationId	OBJECT-TYPE	
			SYNTAX		Integer32  ( 0 .. 2147483647  ) 
			MAX-ACCESS	accessible-for-notify
			STATUS		current
			DESCRIPTION	"The Notification ID generated by EMS for
			each trap forwarded to NBI/OSS."
			::=  {  emsAuditEntry  1  }

auditNeNotificationId	OBJECT-TYPE	
			SYNTAX		Integer32  ( 0 .. 2147483647  ) 
			MAX-ACCESS	read-only
			STATUS		current
			DESCRIPTION	"Maps to the Notification ID generated
					by Infinera NE. Since this is specific 
					to each NE, the NE Name attribute should 
					be used in conjunction with this attribute."
			::=  {  emsAuditEntry  2 }

auditEmsTime		OBJECT-TYPE	
		SYNTAX		DisplayString
		MAX-ACCESS	read-only
		STATUS		current
		DESCRIPTION	"ems time in ISO 8601 format YYYY-MM-DD<space>hh:mm:ss.mmmm<Z>"
		::=  {  emsAuditEntry  3  }

auditNeTime		OBJECT-TYPE	
		SYNTAX		DisplayString
		MAX-ACCESS	read-only
		STATUS		current
		DESCRIPTION	"ne time in ISO 8601 format YYYY-MM-DD<space>hh:mm:ss.mmmm<Z>"
		::=  {  emsAuditEntry  4  }

auditEmsName		OBJECT-TYPE	
		SYNTAX		DisplayString  ( SIZE ( 255  ) ) 
		MAX-ACCESS	read-only
		STATUS		current
		DESCRIPTION	"EMS Name or IP Address of the EMS Server.
				This is useful if one NBI Client connects 
				to more than EMS and receives traps. Default is Infinera"
		::=  {  emsAuditEntry  5  }

auditNeName		OBJECT-TYPE	
		SYNTAX		DisplayString  ( SIZE ( 1 .. 20  ) ) 
		MAX-ACCESS	read-only
		STATUS		current
		DESCRIPTION	"The Name of the network element. This maps
				to the ME Name of the Info Model."
		::=  {  emsAuditEntry  6  }

auditNeNodeId		OBJECT-TYPE	
		SYNTAX		DisplayString  ( SIZE ( 1 .. 128  ) ) 
		MAX-ACCESS	read-only
		STATUS		current
		DESCRIPTION	"The Node ID of the network element. "
		::=  {  emsAuditEntry  7  }

auditObjectType	OBJECT-TYPE	
		SYNTAX		DisplayString
		MAX-ACCESS	read-only
		STATUS		current
		DESCRIPTION	"Represents MO Type on Infinera Info Mode/XML Interface"
		::=  {  emsAuditEntry  8  }

auditObjectName	OBJECT-TYPE	
		SYNTAX		DisplayString
		MAX-ACCESS	read-only
		STATUS		current
		DESCRIPTION	"Represents AID of an object"
		::=  {  emsAuditEntry  9  }

auditAccountName	OBJECT-TYPE	
		SYNTAX		DisplayString  ( SIZE ( 0 .. 255  ) ) 
		MAX-ACCESS	read-only
		STATUS		current
		DESCRIPTION	"ID of the user who performed this operation."
		::=  {  emsAuditEntry  10  }
		

auditClientHostName	OBJECT-TYPE	
		SYNTAX		DisplayString  ( SIZE ( 0 .. 255  ) ) 
		MAX-ACCESS	read-only
		STATUS		current
		DESCRIPTION	"IP address or host name from which the 
				operation was performed."
		::=  {  emsAuditEntry  11  }

auditOperationName	OBJECT-TYPE	
		SYNTAX		DisplayString  ( SIZE ( 0 .. 255  ) ) 
		MAX-ACCESS	read-only
		STATUS		current
		DESCRIPTION	"The operation type which resulted in this 
				Audit event."
		::=  {  emsAuditEntry  12  }

auditOperationStatus	OBJECT-TYPE	
		SYNTAX		DisplayString  ( SIZE ( 0 .. 255  ) ) 
		MAX-ACCESS	read-only
		STATUS		current
		DESCRIPTION	"The status of the operation for this Audit 
				Event. Could be success or failure etc."
		::=  {  emsAuditEntry  13  }

auditParamList	OBJECT-TYPE	
		SYNTAX		DisplayString
		MAX-ACCESS	read-only
		STATUS		current
		DESCRIPTION	"This attribute contains DisplayString data in 
				comma separated format. The data represents the 
				attributes and their values that got 
				affected by the operation which resulted 
				in this Audit event."
		::=  {  emsAuditEntry  14  }
		
--
-- Attributes specific to Security Events are defined below
--

securityEmsNotificationId	OBJECT-TYPE	
			SYNTAX		Integer32  ( 0 .. 2147483647  ) 
			MAX-ACCESS	accessible-for-notify
			STATUS		current
			DESCRIPTION	"The Notification ID generated by EMS for
			each trap forwarded to NBI/OSS."
			::=  {  emsSecurityEntry  1  }

securityNeNotificationId	OBJECT-TYPE	
			SYNTAX		Integer32  ( 0 .. 2147483647  ) 
			MAX-ACCESS	read-only
			STATUS		current
			DESCRIPTION	"Maps to the Notification ID generated
					by Infinera NE. Since this is specific 
					to each NE, the NE Name attribute should 
					be used in conjunction with this attribute."
			::=  {  emsSecurityEntry  2 }

securityEmsTime		OBJECT-TYPE	
		SYNTAX		DisplayString
		MAX-ACCESS	read-only
		STATUS		current
		DESCRIPTION	"ems time in ISO 8601 format YYYY-MM-DD<space>hh:mm:ss.mmmm<Z>"
		::=  {  emsSecurityEntry  3  }

securityNeTime		OBJECT-TYPE	
		SYNTAX		DisplayString
		MAX-ACCESS	read-only
		STATUS		current
		DESCRIPTION	"ne time in ISO 8601 format YYYY-MM-DD<space>hh:mm:ss.mmmm<Z>"
		::=  {  emsSecurityEntry  4  }

securityEmsName		OBJECT-TYPE	
		SYNTAX		DisplayString  ( SIZE ( 255  ) ) 
		MAX-ACCESS	read-only
		STATUS		current
		DESCRIPTION	"EMS Name or IP Address of the EMS Server.
				This is useful if one NBI Client connects 
				to more than EMS and receives traps. Default is Infinera"
		::=  {  emsSecurityEntry  5  }

securityNeName		OBJECT-TYPE	
		SYNTAX		DisplayString  ( SIZE ( 1 .. 20  ) ) 
		MAX-ACCESS	read-only
		STATUS		current
		DESCRIPTION	"The Name of the network element. This maps
				to the ME Name of the Info Model."
		::=  {  emsSecurityEntry  6  }

securityNeNodeId		OBJECT-TYPE	
		SYNTAX		DisplayString  ( SIZE ( 1 .. 128  ) ) 
		MAX-ACCESS	read-only
		STATUS		current
		DESCRIPTION	"The Node ID of the network element. "
		::=  {  emsSecurityEntry  7  }

securityObjectType	OBJECT-TYPE	
		SYNTAX		DisplayString
		MAX-ACCESS	read-only
		STATUS		current
		DESCRIPTION	"Represents MO Type on Infinera Info Mode/XML Interface"
		::=  {  emsSecurityEntry  8  }

securityObjectName	OBJECT-TYPE	
		SYNTAX		DisplayString
		MAX-ACCESS	read-only
		STATUS		current
		DESCRIPTION	"Represents AID of an object"
		::=  {  emsSecurityEntry  9  }

securityAccountName	OBJECT-TYPE	
		SYNTAX		DisplayString  ( SIZE ( 0 .. 255  ) ) 
		MAX-ACCESS	read-only
		STATUS		current
		DESCRIPTION	"ID of the user who performed this operation."
		::=  {  emsSecurityEntry  10  }
		

securityClientHostName	OBJECT-TYPE	
		SYNTAX		DisplayString  ( SIZE ( 0 .. 255  ) ) 
		MAX-ACCESS	read-only
		STATUS		current
		DESCRIPTION	"IP address or host name from which the 
				operation was performed."
		::=  {  emsSecurityEntry  11  }

securityCause	OBJECT-TYPE	
		SYNTAX		DisplayString  ( SIZE ( 0 .. 255  ) ) 
		MAX-ACCESS	read-only
		STATUS		current
		DESCRIPTION	"Descriptive text for the cause 
				attribute. The term is mapped to the 
				cause field of security events
				raised by Infinera Network Elements"
		::=  {  emsSecurityEntry  12  }

--
-- Attributes specific to Admin Events are defined below
--

adminEmsNotificationId	OBJECT-TYPE	
			SYNTAX		Integer32  ( 0 .. 2147483647  ) 
			MAX-ACCESS	accessible-for-notify
			STATUS		current
			DESCRIPTION	"The Notification ID generated by EMS for
			each trap forwarded to NBI/OSS."
			::=  {  emsAdminEntry  1  }

adminNeNotificationId	OBJECT-TYPE	
			SYNTAX		Integer32  ( 0 .. 2147483647  ) 
			MAX-ACCESS	read-only
			STATUS		current
			DESCRIPTION	"Maps to the Notification ID generated
					by Infinera NE. Since this is specific 
					to each NE, the NE Name attribute should 
					be used in conjunction with this attribute."
			::=  {  emsAdminEntry  2 }

adminEmsTime		OBJECT-TYPE	
		SYNTAX		DisplayString
		MAX-ACCESS	read-only
		STATUS		current
		DESCRIPTION	"ems time in ISO 8601 format YYYY-MM-DD<space>hh:mm:ss.mmmm<Z>"
		::=  {  emsAdminEntry  3  }

adminNeTime		OBJECT-TYPE	
		SYNTAX		DisplayString
		MAX-ACCESS	read-only
		STATUS		current
		DESCRIPTION	"ne time in ISO 8601 format YYYY-MM-DD<space>hh:mm:ss.mmmm<Z>"
		::=  {  emsAdminEntry  4  }

adminEmsName		OBJECT-TYPE	
		SYNTAX		DisplayString  ( SIZE ( 255  ) ) 
		MAX-ACCESS	read-only
		STATUS		current
		DESCRIPTION	"EMS Name or IP Address of the EMS Server.
				This is useful if one NBI Client connects 
				to more than EMS and receives traps. Default is Infinera"
		::=  {  emsAdminEntry  5  }

adminNeName		OBJECT-TYPE	
		SYNTAX		DisplayString  ( SIZE ( 1 .. 20  ) ) 
		MAX-ACCESS	read-only
		STATUS		current
		DESCRIPTION	"The Name of the network element. This maps
				to the ME Name of the Info Model."
		::=  {  emsAdminEntry  6  }

adminNeNodeId		OBJECT-TYPE	
		SYNTAX		DisplayString  ( SIZE ( 1 .. 128  ) ) 
		MAX-ACCESS	read-only
		STATUS		current
		DESCRIPTION	"The Node ID of the network element. "
		::=  {  emsAdminEntry  7  }

adminObjectType	OBJECT-TYPE	
		SYNTAX		DisplayString
		MAX-ACCESS	read-only
		STATUS		current
		DESCRIPTION	"Represents MO Type on Infinera Info Mode/XML Interface"
		::=  {  emsAdminEntry  8  }

adminObjectName	OBJECT-TYPE	
		SYNTAX		DisplayString
		MAX-ACCESS	read-only
		STATUS		current
		DESCRIPTION	"Represents AID of an object"
		::=  {  emsAdminEntry  9  }

adminCause	OBJECT-TYPE	
		SYNTAX		DisplayString  ( SIZE ( 0 .. 255  ) ) 
		MAX-ACCESS	read-only
		STATUS		current
		DESCRIPTION	"Descriptive text for the cause 
				attribute. The term is mapped to the 
				cause field of admin events
				raised by Infinera Network Elements"
		::=  {  emsAdminEntry  10  }

--
-- Attributes specific to TCA Events are defined below
--

tcaEmsNotificationId	OBJECT-TYPE	
			SYNTAX		Integer32  ( 0 .. 2147483647  ) 
			MAX-ACCESS	accessible-for-notify
			STATUS		current
			DESCRIPTION	"The Notification ID generated by EMS for
			each trap forwarded to NBI/OSS."
			::=  {  emsTCAEntry  1  }

tcaNeNotificationId	OBJECT-TYPE	
			SYNTAX		Integer32  ( 0 .. 2147483647  ) 
			MAX-ACCESS	read-only
			STATUS		current
			DESCRIPTION	"Maps to the Notification ID generated
					by Infinera NE. Since this is specific 
					to each NE, the NE Name attribute should 
					be used in conjunction with this attribute."
			::=  {  emsTCAEntry  2 }

tcaEmsTime		OBJECT-TYPE	
		SYNTAX		DisplayString
		MAX-ACCESS	read-only
		STATUS		current
		DESCRIPTION	"ems time in ISO 8601 format YYYY-MM-DD<space>hh:mm:ss.mmmm<Z>"
		::=  {  emsTCAEntry  3  }

tcaNeTime		OBJECT-TYPE	
		SYNTAX		DisplayString
		MAX-ACCESS	read-only
		STATUS		current
		DESCRIPTION	"ne time in ISO 8601 format YYYY-MM-DD<space>hh:mm:ss.mmmm<Z>"
		::=  {  emsTCAEntry  4  }

tcaEmsName		OBJECT-TYPE	
		SYNTAX		DisplayString  ( SIZE ( 255  ) ) 
		MAX-ACCESS	read-only
		STATUS		current
		DESCRIPTION	"EMS Name or IP Address of the EMS Server.
				This is useful if one NBI Client connects 
				to more than EMS and receives traps. Default is Infinera"
		::=  {  emsTCAEntry  5  }

tcaNeName		OBJECT-TYPE	
		SYNTAX		DisplayString  ( SIZE ( 1 .. 20  ) ) 
		MAX-ACCESS	read-only
		STATUS		current
		DESCRIPTION	"The Name of the network element. This maps
				to the ME Name of the Info Model."
		::=  {  emsTCAEntry  6  }

tcaNeNodeId		OBJECT-TYPE	
		SYNTAX		DisplayString  ( SIZE ( 1 .. 128  ) ) 
		MAX-ACCESS	read-only
		STATUS		current
		DESCRIPTION	"The Node ID of the network element. "
		::=  {  emsTCAEntry  7  }

tcaObjectType	OBJECT-TYPE	
		SYNTAX		DisplayString
		MAX-ACCESS	read-only
		STATUS		current
		DESCRIPTION	"Represents MO Type on Infinera Info Mode/XML Interface"
		::=  {  emsTCAEntry  8  }

tcaObjectName	OBJECT-TYPE	
		SYNTAX		DisplayString
		MAX-ACCESS	read-only
		STATUS		current
		DESCRIPTION	"Represents AID of an object"
		::=  {  emsTCAEntry  9  }

tcaClearableState	OBJECT-TYPE
			SYNTAX	INTEGER { 
					clearable ( 1 ) , 
					nonclearable ( 2 ) 
					} 
			MAX-ACCESS	read-only
			STATUS		current
			DESCRIPTION	"Represents whether this TCA is clearable or not."
			::=  {  emsTCAEntry  10  }
			
tcaParameterName	OBJECT-TYPE	
		SYNTAX		DisplayString  ( SIZE ( 0 .. 255  ) ) 
		MAX-ACCESS	read-only
		STATUS		current
		DESCRIPTION	"Represents the register/parameter name information
				where the threshold changes are happening (e.g. Errored Seconds)."
		::=  {  emsTCAEntry  11  }

tcaLocation	OBJECT-TYPE	
		SYNTAX		DisplayString  ( SIZE ( 0 .. 255  ) ) 
		MAX-ACCESS	read-only
		STATUS		current
		DESCRIPTION	"Represents the location of the source for
				this threshold (near end/far end etc.)."
		::=  {  emsTCAEntry  12  }

tcaThresholdType	OBJECT-TYPE	
		SYNTAX		DisplayString  ( SIZE ( 0 .. 255  ) ) 
		MAX-ACCESS	read-only
		STATUS		current
		DESCRIPTION	"Represents the type of the threshold
				(e.g. high threshold or low threshold crossed/cleared etc.)."
		::=  {  emsTCAEntry  13  }

tcaThresholdValue	OBJECT-TYPE	
		SYNTAX		DisplayString  ( SIZE ( 0 .. 255  ) ) 
		MAX-ACCESS	read-only
		STATUS		current
		DESCRIPTION	"Value that represents the configured threshold value."
		::=  {  emsTCAEntry  14  }

tcaCurrentValue	OBJECT-TYPE	
		SYNTAX		DisplayString  ( SIZE ( 0 .. 255  ) ) 
		MAX-ACCESS	read-only
		STATUS		current
		DESCRIPTION	"Value that represents the current threshold value."
		::=  {  emsTCAEntry  15  }

tcaGranularity	OBJECT-TYPE	
		SYNTAX		DisplayString  ( SIZE ( 0 .. 255  ) ) 
		MAX-ACCESS	read-only
		STATUS		current
		DESCRIPTION	"Value that represents the granularity of the event
				(e.g. 15-min/24-hour/unknown etc.)."
		::=  {  emsTCAEntry  16  }

tcaPerceivedSeverity	OBJECT-TYPE	
			SYNTAX		INTEGER  { 
						psIndeterminate ( 1 ) , 
						psCritical ( 2 ) , 
						psMajor ( 3 ) , 
						psMinor ( 4 ) , 
						psWarning ( 5 ) , 
						psCleared ( 6 ) 
						} 
			MAX-ACCESS	read-only
			STATUS		current
			DESCRIPTION	"Perceived Severity. 
					Maps to perceivedSeverity in TMF 814 and 
					Infinera XML interface."
			::=  {  emsTCAEntry  17  }

tcaAssertedSeverity	OBJECT-TYPE
			SYNTAX		INTEGER  { 
						psIndeterminate ( 1 ) , 
						psCritical ( 2 ) , 
						psMajor ( 3 ) , 
						psMinor ( 4 ) , 
						psWarning ( 5 ) , 
						psCleared ( 6 ) 
						} 
			MAX-ACCESS	read-only
			STATUS		current
			DESCRIPTION	"The severity with which this TCA was asserted."
			::=  {  emsTCAEntry  18  }
			
tcaNeCorrelationId	OBJECT-TYPE	
			SYNTAX		Integer32  ( 0 .. 2147483647  ) 
			MAX-ACCESS	read-only
			STATUS		current
			DESCRIPTION	"Represents the TCA correlation ID generated by
					the Network Element."
			::=  {  emsTCAEntry  19  }

tcaProbableCauseDescription	OBJECT-TYPE	
		SYNTAX		DisplayString  ( SIZE ( 0 .. 255  ) ) 
		MAX-ACCESS	read-only
		STATUS		current
		DESCRIPTION	"Value that represents the description of probable cause."
		::=  {  emsTCAEntry  20  }			
			
EmsAlarmEntry ::=
      SEQUENCE {
	emsNotificationId Integer32,
	neNotificationId  Integer32,
	emsTime DisplayString,
	neTime DisplayString,
	emsName DisplayString,
	neName DisplayString,
	neNodeId DisplayString,
	objectType DisplayString,
	objectName DisplayString,
	sessionNotificationId Integer32,
	neProbableCause DisplayString,
	emsProbableCause DisplayString,
	perceivedSeverity INTEGER,
	assertedSeverity INTEGER,
	serviceAffecting INTEGER, 
	probableCauseDescription DisplayString,
	category INTEGER, 
	proposedRepairActions DisplayString,
	additionalText DisplayString,
	emsCorrelationId Integer32,
	neCorrelationId Integer32,
	circuitId DisplayString
      }

EmsAuditEntry ::=
      SEQUENCE {
	auditEmsNotificationId Integer32,
	auditNeNotificationId Integer32,
	auditEmsTime DisplayString,
	auditNeTime DisplayString,
	auditEmsName DisplayString,
	auditNeName DisplayString,
	auditNeNodeId DisplayString,
	auditObjectType DisplayString,
	auditObjectName DisplayString,
	auditAccountName DisplayString,
	auditClientHostName DisplayString,
	auditOperationName DisplayString,
	auditOperationStatus DisplayString,
	auditParamList DisplayString
      }

EmsAdminEntry ::=
      SEQUENCE {
	adminEmsNotificationId Integer32,
	adminNeNotificationId Integer32,
	adminEmsTime DisplayString,
	adminNeTime DisplayString,
	adminEmsName DisplayString,
	adminNeName DisplayString,
	adminNeNodeId DisplayString,
	adminObjectType DisplayString,
	adminObjectName DisplayString,
	adminCause DisplayString
      }

EmsSecurityEntry ::=
      SEQUENCE {
	securityEmsNotificationId Integer32,
	securityNeNotificationId Integer32,
	securityEmsTime DisplayString,
	securityNeTime DisplayString,
	securityEmsName DisplayString,
	securityNeName DisplayString,
	securityNeNodeId DisplayString,
	securityObjectType DisplayString,
	securityObjectName DisplayString,
	securityAccountName DisplayString,
	securityClientHostName DisplayString,
	securityCause DisplayString
      }

EmsTCAEntry ::=
      SEQUENCE {
	tcaEmsNotificationId Integer32,
	tcaNeNotificationId Integer32,
	tcaEmsTime DisplayString,
	tcaNeTime DisplayString,
	tcaEmsName DisplayString,
	tcaNeName DisplayString,
	tcaNeNodeId DisplayString,
	tcaObjectType DisplayString,
	tcaObjectName DisplayString,
	tcaClearableState INTEGER,
	tcaParameterName DisplayString,
	tcaLocation DisplayString,
	tcaThresholdType DisplayString,
	tcaThresholdValue DisplayString,
	tcaCurrentValue DisplayString,
	tcaGranularity DisplayString,
	tcaPerceivedSeverity INTEGER,
	tcaAssertedSeverity INTEGER,
	tcaNeCorrelationId Integer32,
	tcaProbableCauseDescription DisplayString
      }

-- 
-- Infinera NM SNMP Notification Types are defined below
--
emsAlarm	NOTIFICATION-TYPE
		OBJECTS		{ 
  				emsNotificationId,
  				neNotificationId, 
  				emsTime, 
  				neTime, 
  				emsName, 
  				neName, 
  				neNodeId,
  				objectType, 
  				objectName, 
				sessionNotificationId,
  				emsProbableCause, 
  				neProbableCause, 
  				perceivedSeverity, 
  				assertedSeverity, 
  				serviceAffecting, 
  				category, 
  				probableCauseDescription,
  				proposedRepairActions,
  				additionalText,
  				emsCorrelationId,
  				neCorrelationId,
  				circuitId
				}
		STATUS		current
		DESCRIPTION	"SNMP Notification representing Conditions/Alarms 
				raised by Infinera Network Elements"
		::=  {  emsEvent  1  }


emsAudit	NOTIFICATION-TYPE
		OBJECTS		{ 
				auditEmsNotificationId,
				auditNeNotificationId,
				auditEmsTime,
				auditNeTime,
				auditEmsName,
				auditNeName,
				auditNeNodeId,
				auditObjectType,
				auditObjectName,
				auditAccountName,
				auditClientHostName,
				auditOperationName,
				auditOperationStatus,
				auditParamList,
				sessionNotificationId
				}
		STATUS		current
		DESCRIPTION	"SNMP Notification representing Audit events 
				generated by Infinera Network elements"
		::=  {  emsEvent  2  }

emsAdmin	NOTIFICATION-TYPE
		OBJECTS		{ 
				adminEmsNotificationId,
				adminNeNotificationId,
				adminEmsTime,
				adminNeTime,
				adminEmsName,
				adminNeName,
				adminNeNodeId,
				adminObjectType,
				adminObjectName,
				adminCause,
				sessionNotificationId
				}
		STATUS		current
		DESCRIPTION	"SNMP Notification representing Admin events 
				generated by Infinera Network elements"
		::=  {  emsEvent  3  }

emsSecurity	NOTIFICATION-TYPE
		OBJECTS		{ 
				securityEmsNotificationId,
				securityNeNotificationId,
				securityEmsTime,
				securityNeTime,
				securityEmsName,
				securityNeName,
				securityNeNodeId,
				securityObjectType,
				securityObjectName,
				securityAccountName,
				securityClientHostName,
				securityCause,
				sessionNotificationId
				}
		STATUS		current
		DESCRIPTION	"SNMP Notification representing Security events 
				generated by Infinera Network elements"
		::=  {  emsEvent  4  }
		
emsTCA	NOTIFICATION-TYPE
		OBJECTS		{ 
				tcaEmsNotificationId,
				tcaNeNotificationId,
				tcaEmsTime,
				tcaNeTime,
				tcaEmsName,
				tcaNeName,
				tcaNeNodeId,
				tcaObjectType,
				tcaObjectName,
				tcaClearableState,
				tcaParameterName,
				tcaLocation,
				tcaThresholdType,
				tcaThresholdValue,
				tcaCurrentValue,
				tcaGranularity,
				tcaPerceivedSeverity,
				tcaAssertedSeverity,
				tcaNeCorrelationId,
				tcaProbableCauseDescription,
				sessionNotificationId
				}
		STATUS		current
		DESCRIPTION	"SNMP Notification representing TCA events 
				generated by Infinera Network elements"
		::=  {  emsEvent  5  }

--
-- Conformance information...Just to Confirming to Standards
--

        emsEventConformance OBJECT IDENTIFIER ::= { emsEvent 6 }
        emsEventObjGroups    OBJECT IDENTIFIER ::= { emsEventConformance 1 }
        emsEventNotifGroups  OBJECT IDENTIFIER ::= { emsEventConformance 2 }

--
-- Units of conformance
--

        emsAlarmGroup    OBJECT-GROUP
            OBJECTS {
              circuitId, neCorrelationId, emsCorrelationId, additionalText, proposedRepairActions,
              category, probableCauseDescription, serviceAffecting, assertedSeverity,
              perceivedSeverity, emsProbableCause, neProbableCause, sessionNotificationId,
              objectName, objectType, neNodeId, neName, neNotificationId, emsName, neTime,
              emsTime, emsNotificationId
              }
            STATUS  current
            DESCRIPTION
                    " A collection of objects for monitoring the Alarms."
            ::= { emsEventObjGroups 1 }

        emsAuditGroup    OBJECT-GROUP
            OBJECTS {
              auditEmsNotificationId, auditNeNotificationId, auditEmsTime,
	      auditNeTime, auditEmsName, auditNeName, auditNeNodeId,
	      auditObjectType, auditObjectName,
	      auditAccountName, auditClientHostName, auditOperationName,
	      auditOperationStatus, auditParamList
              }
            STATUS  current
            DESCRIPTION
                    " A collection of objects for monitoring the Audit Events."
            ::= { emsEventObjGroups 2 }

        emsAdminGroup    OBJECT-GROUP
            OBJECTS {
              adminEmsNotificationId, adminNeNotificationId, adminEmsTime,
              adminNeTime, adminEmsName, adminNeName, adminNeNodeId,
              adminObjectType, adminObjectName, adminCause
              }
            STATUS  current
            DESCRIPTION
                    " A collection of objects for monitoring the Admin Events."
            ::= { emsEventObjGroups 3 }

	emsSecurityGroup    OBJECT-GROUP
            OBJECTS { 
	      securityEmsNotificationId, securityNeNotificationId, securityEmsTime,
	      securityNeTime, securityEmsName, securityNeName, securityNeNodeId,
	      securityObjectType, securityObjectName,
	      securityAccountName, securityClientHostName, securityCause
	      }
            STATUS  current
            DESCRIPTION
                    " A collection of objects for monitoring the Security Events."
            ::= { emsEventObjGroups 4 }

	emsTCAGroup    OBJECT-GROUP
            OBJECTS { 
	        tcaEmsNotificationId, tcaNeNotificationId, tcaEmsTime, tcaNeTime,
	        tcaEmsName, tcaNeName, tcaNeNodeId, tcaObjectType, tcaObjectName,
	        tcaClearableState, tcaParameterName,
	        tcaLocation, tcaThresholdType, tcaThresholdValue, tcaCurrentValue,
	        tcaGranularity, tcaPerceivedSeverity, tcaAssertedSeverity,
	        tcaNeCorrelationId, tcaProbableCauseDescription
	      }
            STATUS  current
            DESCRIPTION
                    " A collection of objects for monitoring the TCA Events."
            ::= { emsEventObjGroups 5 }

        emsNotifGroup    NOTIFICATION-GROUP
            NOTIFICATIONS {emsTCA, emsSecurity, emsAdmin, emsAudit, emsAlarm}
            STATUS  current
            DESCRIPTION
                    " A collection of objects for monitoring the DSA
                      entry statistics and cache performance."
            ::= { emsEventNotifGroups 1 }

END

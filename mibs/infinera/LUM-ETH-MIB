LUM-ETH-MIB DEFINITIONS ::= BEGIN

IMPORTS
    MODULE-IDENTITY, OBJECT-TYPE, Unsigned32, Integer32, NOTIFICATION-TYPE,
    Gauge32
        FROM SNMPv2-SMI
    OBJECT-GROUP, MODULE-COMPLIANCE, NOTIFICATION-GROUP
        FROM SNMPv2-CONF
    TEXTUAL-CONVENTION, DisplayString, DateAndTime
        FROM SNMPv2-TC
    lumModules, lumEthMIB
        FROM LUM-REG
    FaultStatus, MgmtNameString, SubrackNumber, SlotNumber, PortNumber,
    BoardOrInterfaceOperStatus, BoardOrInterfaceAdminStatus, ObjectProperty
        FROM LUM-TC;

lumEthMIBModule MODULE-IDENTITY
    LAST-UPDATED
        "201706150000Z" -- June 15th 2017
    ORGANIZATION
        "Infinera Corporation"
    CONTACT-INFO
        "techsupport@infinera.com"
    DESCRIPTION
        "The ethernet client interface MIB.

        - General

        - Ethernet client interfaces

"
    REVISION
        "201706150000Z" -- June 15th 2017
    DESCRIPTION
        "Changes made for release r29.0:
         - Changed ORGANIZATION and CONTACT-INFO"
    REVISION
        "201601110000Z" -- Jan 11th 2016
    DESCRIPTION
        "Added default value notPresent for operStatus."
    REVISION
        "200212060000Z" -- Dec 6th 2002
    DESCRIPTION
        "powerLevel attributes removed; not supported in hardware."
    REVISION
        "200211190000Z" -- Nov 19th 2002
    DESCRIPTION
        "InterpacketGap: removed 64."
    REVISION
        "200211130000Z" -- Nov 13th 2002
    DESCRIPTION
        "Removed auto from autoNeg."
    REVISION
        "200206250000Z" -- June 25th 2002
    DESCRIPTION
        "The initial revision of this module."
    ::= { lumModules 19 }


-- ----------------------------------------------------
-- Conformance area, containing groups and complicance
-- specifications.
-- ----------------------------------------------------

lumEthConfs OBJECT IDENTIFIER ::= { lumEthMIB 1 }
lumEthGroups OBJECT IDENTIFIER ::= { lumEthConfs 1 }
lumEthCompl OBJECT IDENTIFIER ::= { lumEthConfs 2 }


-- ----------------------------------------------------
-- Root for objects in the eth MIB
-- ----------------------------------------------------

lumEthMIBObjects OBJECT IDENTIFIER ::= { lumEthMIB 2 }


-- ----------------------------------------------------
-- This MIB contains the following groups:
-- ----------------------------------------------------

ethGeneral OBJECT IDENTIFIER ::= { lumEthMIBObjects 1 }
ethIfList OBJECT IDENTIFIER ::= { lumEthMIBObjects 2 }
lumentisEthNotifications  OBJECT IDENTIFIER ::= { lumEthMIBObjects 3 }


-- ----------------------------------------------------
-- Textual Conventions
-- ----------------------------------------------------

EthSignalFormat ::= TEXTUAL-CONVENTION
    STATUS current
    DESCRIPTION
        "Signal format for ethernet interfaces.

        gbE - Gigabit Ethernet signal

        lan10GbE - 10 Gigabit Ethernet LAN signal"
    SYNTAX INTEGER {
        undefined (0),
        gbE (1),
        lan10GbE (2) }


-- ----------------------------------------------------
-- General group
-- ----------------------------------------------------

ethGeneralLastChangeTime OBJECT-TYPE
    SYNTAX      DateAndTime
    MAX-ACCESS  read-only
    STATUS      current
    DESCRIPTION
        "The time when the configuration of the MIB was
        last changed.

"
    ::= { ethGeneral 1 }

ethGeneralStateLastChangeTime OBJECT-TYPE
    SYNTAX      DateAndTime
    MAX-ACCESS  read-only
    STATUS      current
    DESCRIPTION
        "The time when the state of the MIB was last
        changed.

"
    ::= { ethGeneral 2 }

ethGeneralEthIfTableSize OBJECT-TYPE
    SYNTAX      Unsigned32
    MAX-ACCESS  read-only
    STATUS      current
    DESCRIPTION
        "Size of table

"
    ::= { ethGeneral 3 }

-- ----------------------------------------------------
-- Multi-bit rate client interfaces
-- ----------------------------------------------------

ethIfTable  OBJECT-TYPE
    SYNTAX      SEQUENCE OF EthIfEntry
    MAX-ACCESS  not-accessible
    STATUS      current
    DESCRIPTION
        "The interface list."
    ::= { ethIfList 1 }

ethIfEntry OBJECT-TYPE
    SYNTAX      EthIfEntry
    MAX-ACCESS  not-accessible
    STATUS      current
    DESCRIPTION
        "An entry in the interface list.

"
    INDEX { ethIfIndex }
    ::= { ethIfTable 1 }

EthIfEntry ::=
    SEQUENCE {
        ethIfIndex                      Unsigned32,
        ethIfName                       MgmtNameString,
        ethIfDescr                      DisplayString,
        ethIfSubrack                    SubrackNumber,
        ethIfSlot                       SlotNumber,
        ethIfTxPort                     PortNumber,
        ethIfRxPort                     PortNumber,
        ethIfInvPhysIndexOrZero         Unsigned32,
        ethIfFormat                     EthSignalFormat,
        ethIfHighSpeed                  Gauge32,
        ethIfAdminStatus                BoardOrInterfaceAdminStatus,
        ethIfOperStatus                 BoardOrInterfaceOperStatus,
        ethIfLaserStatus                INTEGER,
        ethIfTxSignalStatus             INTEGER,
        ethIfAutoNegotiationMode        INTEGER,
        ethIfAutoNegotiationStatus      INTEGER,
        ethIfDuplexCapability           INTEGER,
        ethIfFlowControlMode            INTEGER,
        ethIfInterPacketGap             Gauge32,
        ethIfFrameSize                  Gauge32,
        ethIfPowerLevel                 Integer32,
        ethIfPowerLevelHighThreshold    Integer32,
        ethIfPowerLevelLowThreshold     Integer32,
        ethIfLaserBias                  Unsigned32,
        ethIfLaserBiasThreshold         Unsigned32,
        ethIfLossOfSignal               FaultStatus,
        ethIfReceivedPowerHigh          FaultStatus,
        ethIfReceivedPowerLow           FaultStatus,
        ethIfLaserBiasHigh              FaultStatus,
        ethIfLossOfSync                 FaultStatus,
        ethIfBitrateMismatch            FaultStatus,
        ethIfLinkDown                   FaultStatus,
        ethIfAuAlarmIndicationSignalW2C FaultStatus,
        ethIfForwardAls                 INTEGER,
        ethIfSuppressRemoteAlarms       INTEGER,
        ethIfFarEndLoopback             INTEGER,
        ethIfEntityId                   Unsigned32,
        ethIfGbeUtilization             Unsigned32,
        ethIfObjectProperty             ObjectProperty,
        ethIfPowerLevelLowRelativeThreshold Integer32 }

ethIfIndex OBJECT-TYPE
    SYNTAX      Unsigned32 (1..2147483647)
    MAX-ACCESS  read-only
    STATUS      current
    DESCRIPTION
        "An arbitrary index assigned to each entry.

"
    ::= { ethIfEntry 1 }

ethIfName OBJECT-TYPE
    SYNTAX      MgmtNameString
    MAX-ACCESS  read-only
    STATUS      current
    DESCRIPTION
        "The management name of the interface, for
        example 'eth1:2:1', where the first number
        indicates sub-rack, the second slot number and
        the third is the port number.
        Examples:

        eth:s:s:p - Eth client interface

"
    ::= { ethIfEntry 2 }

ethIfDescr OBJECT-TYPE
    SYNTAX      DisplayString
    MAX-ACCESS  read-write
    STATUS      current
    DESCRIPTION
        "User configurable label.

"
    DEFVAL { "" }
    ::= { ethIfEntry 3 }

ethIfSubrack OBJECT-TYPE
    SYNTAX      SubrackNumber
    MAX-ACCESS  read-only
    STATUS      current
    DESCRIPTION
        "The number of the subrack where the interface
        is located.

"
    ::= { ethIfEntry 4 }

ethIfSlot OBJECT-TYPE
    SYNTAX      SlotNumber
    MAX-ACCESS  read-only
    STATUS      current
    DESCRIPTION
        "The number of the slot where the interface is
        located.

"
    ::= { ethIfEntry 5 }

ethIfTxPort OBJECT-TYPE
    SYNTAX      PortNumber
    MAX-ACCESS  read-only
    STATUS      current
    DESCRIPTION
        "The number of the port where the TX-side of
        the interface is located.

"
    ::= { ethIfEntry 6 }

ethIfRxPort OBJECT-TYPE
    SYNTAX      PortNumber
    MAX-ACCESS  read-only
    STATUS      current
    DESCRIPTION
        "The number of the port where the RX-side of
        the interface is located.

"
    ::= { ethIfEntry 7 }

ethIfInvPhysIndexOrZero OBJECT-TYPE
    SYNTAX      Unsigned32 (0..2147483647)
    MAX-ACCESS  read-only
    STATUS      current
    DESCRIPTION
        "The row in the invPhysTable for this interface.
        Set to 0 if not known.

"
    ::= { ethIfEntry 8 }

ethIfFormat OBJECT-TYPE
    SYNTAX      EthSignalFormat
    MAX-ACCESS  read-only
    STATUS      current
    DESCRIPTION
        "The expected signal format.

        The default value is board dependent. For information
        about the default value for this particular board,
        please refer to the user manual.

"
    DEFVAL { gbE }
    ::= { ethIfEntry 9 }

ethIfHighSpeed OBJECT-TYPE
    SYNTAX      Gauge32 (1000..10000)
    MAX-ACCESS  read-only
    STATUS      current
    DESCRIPTION
        "The expected signal bit rate in units of
        1,000,000 bits (Mb) per second.

"
    ::= { ethIfEntry 10 }

ethIfAdminStatus OBJECT-TYPE
    SYNTAX      BoardOrInterfaceAdminStatus
    MAX-ACCESS  read-write
    STATUS      current
    DESCRIPTION
        "The administrative state for the interface.

        down - The interface should be inactive.

        service - The interface is activated but alarms
        are suppressed. Intended for use during service
        or re-configuration. When service is concluded
        adminStatus should be set to 'up' again.

        up - The interface should be activated when
        it becomes available. Alarms are not suppressed.

"
    DEFVAL { up }
    ::= { ethIfEntry 11 }

ethIfOperStatus OBJECT-TYPE
    SYNTAX      BoardOrInterfaceOperStatus
    MAX-ACCESS  read-only
    STATUS      current
    DESCRIPTION
        "The operational state for the interface.

        notPresent - The physical resources are not
        available.

        down - The interface is de-activated or the are
        faults preventing it from going to the
        'up'-state.

        up - The interface is operational.

"
    DEFVAL { notPresent }
    ::= { ethIfEntry 12 }

ethIfLaserStatus OBJECT-TYPE
    SYNTAX      INTEGER {
                    off (1),
                    on (2) }
    MAX-ACCESS  read-only
    STATUS      current
    DESCRIPTION
        "The operational state of the laser.

        off - The laser is turned off.

        on - The laser is turned on.

"
    ::= { ethIfEntry 13 }

ethIfTxSignalStatus OBJECT-TYPE
    SYNTAX      INTEGER {
                        down (1),
                        degraded (2),
                        up (3) }
    MAX-ACCESS  read-only
    STATUS      current
    DESCRIPTION
        "The operational state for outgoing (TX) signal
        of the interface.

        down - A fault that would lead to a protection
        switch has occurred.

        degraded - The signal quality is impaired.

        up - The signal is OK.

"
    ::= { ethIfEntry 14 }

ethIfAutoNegotiationMode OBJECT-TYPE
    SYNTAX      INTEGER {
                         off (1),
                         on (2) }
    MAX-ACCESS  read-write
    STATUS      current
    DESCRIPTION
        "The wanted auto negotiation mode.

        off - auto negotiation process is disabled

        on - auto negotiation process is enabled

"
    DEFVAL { on }
    ::= { ethIfEntry 15 }

ethIfAutoNegotiationStatus OBJECT-TYPE
    SYNTAX      INTEGER {
                         incomplete (1),
                         half (2),
                         full (3) }
    MAX-ACCESS  read-only
    STATUS      current
    DESCRIPTION
        "The result of the auto negotiation procedure

         incomplete - the result is still pending

         half - half duplex

         full - full duplex

"
    ::= { ethIfEntry 16 }

ethIfDuplexCapability OBJECT-TYPE
    SYNTAX      INTEGER {
                        half (2),
                        full (3) }
    MAX-ACCESS  read-only
    STATUS      current
    DESCRIPTION
        "The duplex capability of the HW.

         half - supports half duplex

         full - supports full duplex

"
    ::= { ethIfEntry 17 }

ethIfFlowControlMode OBJECT-TYPE
    SYNTAX      INTEGER {
                        noPause (1),
                        rxPause (2),
                        txPause (3),
                        bothPause (4) }
    MAX-ACCESS  read-write
    STATUS      current
    DESCRIPTION
        "The mode for handling of pause messages between
        the peers.

         noPause - PAUSE frame reception and
         transmission is disabled

         rxPause - PAUSE frame reception is enabled
         (asymmetric)

         txPause - PAUSE frame transmission is enabled
         (asymetric)

         bothPause - send and accept pause messages
         (symmetric).

"
    DEFVAL { rxPause }
    ::= { ethIfEntry 18 }

ethIfInterPacketGap OBJECT-TYPE
    SYNTAX      Gauge32 (72..456)
    MAX-ACCESS  read-write
    STATUS      current
    DESCRIPTION
        "Time between the frames in nano seconds.

        Legal values are 72, 80, ... 200, 320, 328,
        336, ... 456

"
    DEFVAL { 96 }
    ::= { ethIfEntry 19 }

ethIfFrameSize OBJECT-TYPE
    SYNTAX      Gauge32 (1518..9600)
    MAX-ACCESS  read-write
    STATUS      current
    DESCRIPTION
        "The maximum size of the transmitted and
        received frames (in bytes).

"
    DEFVAL { 9600 }
    ::= { ethIfEntry 20 }

ethIfPowerLevel OBJECT-TYPE
    SYNTAX      Integer32
    MAX-ACCESS  read-only
    STATUS      current
    DESCRIPTION
        "The received power level in units of 0.1 dBm.

"
    ::= { ethIfEntry 21 }

ethIfPowerLevelHighThreshold OBJECT-TYPE
    SYNTAX      Integer32 (-200..-10)
    MAX-ACCESS  read-write
    STATUS      deprecated
    DESCRIPTION
        "The upper threshold for received power level
        in units of 0.1 dBm.

"
    DEFVAL { -50 }
    ::= { ethIfEntry 22 }

ethIfPowerLevelLowThreshold OBJECT-TYPE
    SYNTAX      Integer32 (-200..-10)
    MAX-ACCESS  read-write
    STATUS      deprecated
    DESCRIPTION
        "The lower threshold for received power level
        in units of 0.1 dBm.

"
    DEFVAL { -160 }
    ::= { ethIfEntry 23 }

ethIfLaserBias OBJECT-TYPE
    SYNTAX      Unsigned32
    MAX-ACCESS  read-only
    STATUS      current
    DESCRIPTION
        "Measures laser bias current value in tenths
        of mA (0.1 mA).

"
    ::= { ethIfEntry 24 }

ethIfLaserBiasThreshold OBJECT-TYPE
    SYNTAX      Unsigned32 (0..300)
    MAX-ACCESS  read-write
    STATUS      current
    DESCRIPTION
        "Sets the threshold for the laser bias alarm.
        in percentage relative to the value set during
        production. The preset value is 100%.

"
    DEFVAL { 200 }
    ::= { ethIfEntry 25 }

ethIfLossOfSignal OBJECT-TYPE
    SYNTAX      FaultStatus
    MAX-ACCESS  read-only
    STATUS      current
    DESCRIPTION
        "Loss of signal.
        Applicable for all signal formats.

        A(ctivation): Active loss of signal HW
        indication.

        D(e-activation): Inactive loss of signal HW
        indication.

"
    ::= { ethIfEntry 26 }

ethIfReceivedPowerHigh OBJECT-TYPE
    SYNTAX      FaultStatus
    MAX-ACCESS  read-only
    STATUS      current
    DESCRIPTION
        "Received power level high threshold exceeded.

        A: The received power level exceeds the
        associated threshold.

        D: The received power level is 0.5 dB below
        the threshold.

"
    ::= { ethIfEntry 27 }

ethIfReceivedPowerLow OBJECT-TYPE
    SYNTAX      FaultStatus
    MAX-ACCESS  read-only
    STATUS      current
    DESCRIPTION
        "Received power level low threshold exceeded.

        A: The received power level is below the
        associated threshold.

        D: The received power level is 0.5 dB above
        the threshold.

"
    ::= { ethIfEntry 28 }

ethIfLaserBiasHigh OBJECT-TYPE
    SYNTAX      FaultStatus
    MAX-ACCESS  read-only
    STATUS      current
    DESCRIPTION
        "Laser bias high threshold exceeded.

        A: The laser bias current exceeds the associated
        threshold.

        D: The laser bias current is 0.5 mA below the
        associated threshold.

"
    ::= { ethIfEntry 29 }

ethIfLossOfSync OBJECT-TYPE
    SYNTAX      FaultStatus
    MAX-ACCESS  read-only
    STATUS      current
    DESCRIPTION
        "Loss of sync.

        A: GbE 'frame' can not be located.

        D: GbE 'frame' is located.

"
    ::= { ethIfEntry 30 }

ethIfBitrateMismatch OBJECT-TYPE
    SYNTAX      FaultStatus
    MAX-ACCESS  read-only
    STATUS      current
    DESCRIPTION
        "Bitrate mismatch.

        A: The interface is unable to lock to the
        inserted signal.

        D: The interface is able to lock to the
        inserted signal.

"
    ::= { ethIfEntry 31 }

ethIfLinkDown OBJECT-TYPE
    SYNTAX      FaultStatus
    MAX-ACCESS  read-only
    STATUS      current
    DESCRIPTION
        "A: Failure to negotiate a connection with the
        other party.

         D: A connection is negotiated.

"
    ::= { ethIfEntry 32 }

ethIfAuAlarmIndicationSignalW2C OBJECT-TYPE
    SYNTAX      FaultStatus
    MAX-ACCESS  read-only
    STATUS      current
    DESCRIPTION
        "Payload Alarm indication signal (AIS) on the
        trunk-side.

        A: An 'all ones' SDH signal is detected.

        D: SDH signal recovered.

"
    ::= { ethIfEntry 33 }

ethIfForwardAls OBJECT-TYPE
    SYNTAX      INTEGER {
                    disabled (1),
                    enabled (2) }
    MAX-ACCESS  read-write
    STATUS      current
    DESCRIPTION
        "Forward Automatic Laser Shut-down. Decides
        the behaviour of the client laser (W2C) when
        the trunc signal is defected.

        disabled - The laser is NOT turned off at
        failure.

        enabled - The laser is turned off at failure.

"
    DEFVAL { disabled }
    ::= { ethIfEntry 34 }

ethIfSuppressRemoteAlarms OBJECT-TYPE
    SYNTAX      INTEGER {
                    disabled (1),
                    enabled (2) }
    MAX-ACCESS  read-write
    STATUS      current
    DESCRIPTION
        "Suppress AIS in the alarm list. The fault
        status on the port object can, however, be seen.

        disabled - alarms are not suppressed.

        enabled - alarms are suppressed.

"
    DEFVAL { disabled }
    ::= { ethIfEntry 35 }

ethIfFarEndLoopback OBJECT-TYPE
    SYNTAX      INTEGER {
                    disabled (1),
                    enabled (2) }
    MAX-ACCESS  read-write
    STATUS      current
    DESCRIPTION
        "Loop the client TX signal back to the client RX.

        disabled - the signal is not looped

        enabled - the signal is looped.

"
    DEFVAL { disabled }
    ::= { ethIfEntry 36 }


ethIfEntityId OBJECT-TYPE
    SYNTAX      Unsigned32 (1..2147483647)
    MAX-ACCESS  read-only
    STATUS      current
    DESCRIPTION
        "Index in entity table.

        -- Only used for notifications

"
    ::= { ethIfEntry 37 }

ethIfGbeUtilization OBJECT-TYPE
    SYNTAX      Unsigned32 (0..1000)
    MAX-ACCESS  read-only
    STATUS      current
    DESCRIPTION
        "Shows a snapshot of the current bandwidth
         utilization of the GbE signal during the
         last second.

        It is expressed in per cent of 1 Gbps

"
    ::= { ethIfEntry 38 }

ethIfObjectProperty OBJECT-TYPE
    SYNTAX      ObjectProperty
    MAX-ACCESS  read-only
    STATUS      current
    DESCRIPTION
        "Property mask.

"
    ::= { ethIfEntry 39 }


ethIfPowerLevelLowRelativeThreshold OBJECT-TYPE
    SYNTAX      Integer32 (-50..100)
    MAX-ACCESS  read-write
    STATUS      current
    DESCRIPTION
        "The lower threshold for received power level in
        units of 0.1 dB, relative to the receiver
        sensitivity.

"
    DEFVAL { 30 }
    ::= { ethIfEntry 40 }

-- ----------------------------------------------------
-- Notifications
-- ----------------------------------------------------

ethNotifyPrefix OBJECT IDENTIFIER ::= { lumentisEthNotifications 0 }

ethIfTxSignalStatusDown NOTIFICATION-TYPE
    OBJECTS {
        ethIfIndex,
        ethIfName,
        ethIfSubrack,
        ethIfSlot,
        ethIfTxPort,
        ethIfRxPort,
        ethIfEntityId,
        ethIfTxSignalStatus }
    STATUS      current
    DESCRIPTION
        "Sent when the signal status attribute of an
        interface changes.

"
    ::= { ethNotifyPrefix 1 }

ethIfTxSignalStatusUp NOTIFICATION-TYPE
    OBJECTS {
        ethIfIndex,
        ethIfName,
        ethIfSubrack,
        ethIfSlot,
        ethIfTxPort,
        ethIfRxPort,
        ethIfEntityId,
        ethIfTxSignalStatus }
    STATUS      current
    DESCRIPTION
        "Sent when the signal status attribute of an
        interface changes.

"
    ::= { ethNotifyPrefix 2 }

ethIfTxSignalStatusDegraded NOTIFICATION-TYPE
    OBJECTS {
        ethIfIndex,
        ethIfName,
        ethIfSubrack,
        ethIfSlot,
        ethIfTxPort,
        ethIfRxPort,
        ethIfEntityId,
        ethIfTxSignalStatus }
    STATUS      current
    DESCRIPTION
        "Sent when the signal status attribute of an
        interface changes.

"
    ::= { ethNotifyPrefix 3 }


-- ----------------------------------------------------
-- Object and event groups
-- ----------------------------------------------------

ethGeneralGroup OBJECT-GROUP
    OBJECTS {
        ethGeneralLastChangeTime,
        ethGeneralStateLastChangeTime}
    STATUS      deprecated
    DESCRIPTION
        "The general objects."
    ::= { lumEthGroups 1 }

ethIfGroup OBJECT-GROUP
    OBJECTS {
        ethIfIndex,
        ethIfName,
        ethIfDescr,
        ethIfSubrack,
        ethIfSlot,
        ethIfTxPort,
        ethIfRxPort,
        ethIfInvPhysIndexOrZero,
        ethIfFormat,
        ethIfHighSpeed,
        ethIfPowerLevel,
        ethIfPowerLevelHighThreshold,
        ethIfPowerLevelLowThreshold,
        ethIfLaserStatus,
        ethIfAdminStatus,
        ethIfOperStatus,
        ethIfTxSignalStatus,
        ethIfAutoNegotiationMode,
        ethIfAutoNegotiationStatus,
        ethIfLaserBias,
        ethIfLaserBiasThreshold,
        ethIfDuplexCapability,
        ethIfFlowControlMode,
        ethIfInterPacketGap,
        ethIfFrameSize,
        ethIfLossOfSignal,
        ethIfReceivedPowerHigh,
        ethIfReceivedPowerLow,
        ethIfLaserBiasHigh,
        ethIfLossOfSync,
        ethIfBitrateMismatch,
        ethIfLinkDown }
    STATUS      deprecated
    DESCRIPTION
        "The eth interface objects."
    ::= { lumEthGroups 2 }

ethNotificationGroup NOTIFICATION-GROUP
    NOTIFICATIONS {
        ethIfTxSignalStatusDown,
        ethIfTxSignalStatusUp }
    STATUS      deprecated
    DESCRIPTION
        "The eth notifications."
    ::= { lumEthGroups 3 }

ethIfGroupV2 OBJECT-GROUP
    OBJECTS {
        ethIfIndex,
        ethIfName,
        ethIfDescr,
        ethIfSubrack,
        ethIfSlot,
        ethIfTxPort,
        ethIfRxPort,
        ethIfInvPhysIndexOrZero,
        ethIfFormat,
        ethIfHighSpeed,
        ethIfLaserStatus,
        ethIfAdminStatus,
        ethIfOperStatus,
        ethIfTxSignalStatus,
        ethIfAutoNegotiationMode,
        ethIfAutoNegotiationStatus,
        ethIfLaserBias,
        ethIfLaserBiasThreshold,
        ethIfDuplexCapability,
        ethIfFlowControlMode,
        ethIfInterPacketGap,
        ethIfFrameSize,
        ethIfLossOfSignal,
        ethIfReceivedPowerHigh,
        ethIfReceivedPowerLow,
        ethIfLaserBiasHigh,
        ethIfLossOfSync,
        ethIfBitrateMismatch,
        ethIfLinkDown }
    STATUS      deprecated
    DESCRIPTION
        "The eth interface objects v2."
    ::= { lumEthGroups 4 }

ethIfGroupV3 OBJECT-GROUP
    OBJECTS {
        ethIfIndex,
        ethIfName,
        ethIfDescr,
        ethIfSubrack,
        ethIfSlot,
        ethIfTxPort,
        ethIfRxPort,
        ethIfInvPhysIndexOrZero,
        ethIfFormat,
        ethIfHighSpeed,
        ethIfLaserStatus,
        ethIfAdminStatus,
        ethIfOperStatus,
        ethIfTxSignalStatus,
        ethIfAutoNegotiationMode,
        ethIfAutoNegotiationStatus,
        ethIfLaserBias,
        ethIfLaserBiasThreshold,
        ethIfDuplexCapability,
        ethIfFlowControlMode,
        ethIfInterPacketGap,
        ethIfFrameSize,
        ethIfLossOfSignal,
        ethIfReceivedPowerHigh,
        ethIfReceivedPowerLow,
        ethIfLaserBiasHigh,
        ethIfLossOfSync,
        ethIfBitrateMismatch,
        ethIfLinkDown,
        ethIfAuAlarmIndicationSignalW2C,
        ethIfForwardAls,
        ethIfSuppressRemoteAlarms,
        ethIfFarEndLoopback }
    STATUS      deprecated
    DESCRIPTION
        "The eth interface objects v3."
    ::= { lumEthGroups 5 }


ethNotificationGroupV2 NOTIFICATION-GROUP
    NOTIFICATIONS {
        ethIfTxSignalStatusDown,
        ethIfTxSignalStatusUp,
        ethIfTxSignalStatusDegraded }
    STATUS      current
    DESCRIPTION
        "The eth notifications."
    ::= { lumEthGroups 6 }

ethIfGroupV4 OBJECT-GROUP
    OBJECTS {
        ethIfIndex,
        ethIfName,
        ethIfDescr,
        ethIfSubrack,
        ethIfSlot,
        ethIfTxPort,
        ethIfRxPort,
        ethIfInvPhysIndexOrZero,
        ethIfFormat,
        ethIfHighSpeed,
        ethIfLaserStatus,
        ethIfAdminStatus,
        ethIfOperStatus,
        ethIfTxSignalStatus,
        ethIfAutoNegotiationMode,
        ethIfAutoNegotiationStatus,
        ethIfLaserBias,
        ethIfLaserBiasThreshold,
        ethIfDuplexCapability,
        ethIfFlowControlMode,
        ethIfInterPacketGap,
        ethIfFrameSize,
        ethIfLossOfSignal,
        ethIfReceivedPowerHigh,
        ethIfReceivedPowerLow,
        ethIfLaserBiasHigh,
        ethIfLossOfSync,
        ethIfBitrateMismatch,
        ethIfLinkDown,
        ethIfAuAlarmIndicationSignalW2C,
        ethIfForwardAls,
        ethIfSuppressRemoteAlarms,
        ethIfFarEndLoopback,
        ethIfGbeUtilization }
    STATUS      deprecated
    DESCRIPTION
        "The eth interface objects v4 (3.0)."
    ::= { lumEthGroups 7 }

ethGeneralGroupV2 OBJECT-GROUP
    OBJECTS {
        ethGeneralLastChangeTime,
        ethGeneralStateLastChangeTime,
        ethGeneralEthIfTableSize }
    STATUS      current
    DESCRIPTION
        "The general objects. (3.1)"
    ::= { lumEthGroups 8 }

ethIfGroupV5 OBJECT-GROUP
    OBJECTS {
        ethIfIndex,
        ethIfName,
        ethIfDescr,
        ethIfSubrack,
        ethIfSlot,
        ethIfTxPort,
        ethIfRxPort,
        ethIfInvPhysIndexOrZero,
        ethIfFormat,
        ethIfHighSpeed,
        ethIfLaserStatus,
        ethIfAdminStatus,
        ethIfOperStatus,
        ethIfTxSignalStatus,
        ethIfAutoNegotiationMode,
        ethIfAutoNegotiationStatus,
        ethIfLaserBias,
        ethIfLaserBiasThreshold,
        ethIfDuplexCapability,
        ethIfFlowControlMode,
        ethIfInterPacketGap,
        ethIfFrameSize,
        ethIfLossOfSignal,
        ethIfReceivedPowerHigh,
        ethIfReceivedPowerLow,
        ethIfLaserBiasHigh,
        ethIfLossOfSync,
        ethIfBitrateMismatch,
        ethIfLinkDown,
        ethIfAuAlarmIndicationSignalW2C,
        ethIfForwardAls,
        ethIfSuppressRemoteAlarms,
        ethIfFarEndLoopback,
        ethIfGbeUtilization,
        ethIfPowerLevel }
    STATUS      deprecated
    DESCRIPTION
        "The eth interface objects v5 (3.1)."
    ::= { lumEthGroups 9 }

ethIfGroupV6 OBJECT-GROUP
    OBJECTS {
        ethIfIndex,
        ethIfName,
        ethIfDescr,
        ethIfSubrack,
        ethIfSlot,
        ethIfTxPort,
        ethIfRxPort,
        ethIfInvPhysIndexOrZero,
        ethIfFormat,
        ethIfHighSpeed,
        ethIfLaserStatus,
        ethIfAdminStatus,
        ethIfOperStatus,
        ethIfTxSignalStatus,
        ethIfAutoNegotiationMode,
        ethIfAutoNegotiationStatus,
        ethIfLaserBias,
        ethIfLaserBiasThreshold,
        ethIfDuplexCapability,
        ethIfFlowControlMode,
        ethIfInterPacketGap,
        ethIfFrameSize,
        ethIfLossOfSignal,
        ethIfReceivedPowerHigh,
        ethIfReceivedPowerLow,
        ethIfLaserBiasHigh,
        ethIfLossOfSync,
        ethIfBitrateMismatch,
        ethIfLinkDown,
        ethIfAuAlarmIndicationSignalW2C,
        ethIfForwardAls,
        ethIfSuppressRemoteAlarms,
        ethIfFarEndLoopback,
        ethIfEntityId,
        ethIfGbeUtilization,
        ethIfPowerLevel,
        ethIfObjectProperty,
        ethIfPowerLevelLowRelativeThreshold }
    STATUS      current
    DESCRIPTION
        "The eth interface objects v6 (4.0)."
    ::= { lumEthGroups 10 }


-- ----------------------------------------------------
-- Compliance
-- ----------------------------------------------------

lumEthBasicComplV1 MODULE-COMPLIANCE
    STATUS      deprecated
    DESCRIPTION
        "Basic implementation requirements for the eth MIB V1."
    MODULE
        MANDATORY-GROUPS {
            ethGeneralGroup,
            ethIfGroup,
            ethNotificationGroup }
    ::= { lumEthCompl 1 }

lumEthBasicComplV2 MODULE-COMPLIANCE
    STATUS      deprecated
    DESCRIPTION
        "Basic implementation requirements for the eth MIB V2."
    MODULE
        MANDATORY-GROUPS {
            ethGeneralGroup,
            ethIfGroupV2,
            ethNotificationGroup }
    ::= { lumEthCompl 2 }

lumEthBasicComplV3 MODULE-COMPLIANCE
    STATUS      deprecated
    DESCRIPTION
        "Basic implementation requirements for the eth MIB V3."
    MODULE
        MANDATORY-GROUPS {
            ethGeneralGroup,
            ethIfGroupV3,
            ethNotificationGroupV2 }
    ::= { lumEthCompl 3 }

lumEthBasicComplV4 MODULE-COMPLIANCE
    STATUS      deprecated
    DESCRIPTION
        "Basic implementation requirements for the eth MIB V4 (3.0)."
    MODULE
        MANDATORY-GROUPS {
            ethGeneralGroup,
            ethIfGroupV4,
            ethNotificationGroupV2 }
    ::= { lumEthCompl 4 }

lumEthBasicComplV5 MODULE-COMPLIANCE
    STATUS      deprecated
    DESCRIPTION
        "Basic implementation requirements for the eth MIB V5 (3.1)."
    MODULE
        MANDATORY-GROUPS {
            ethGeneralGroupV2,
            ethIfGroupV5,
            ethNotificationGroupV2 }
    ::= { lumEthCompl 5 }

lumEthBasicComplV6 MODULE-COMPLIANCE
    STATUS      current
    DESCRIPTION
        "Basic implementation requirements for the eth MIB V6 (4.0)."
    MODULE
        MANDATORY-GROUPS {
            ethGeneralGroupV2,
            ethIfGroupV6,
            ethNotificationGroupV2 }
    ::= { lumEthCompl 6 }

END

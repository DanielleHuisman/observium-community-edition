LUM-IFAMPLIFIER-MIB DEFINITIONS ::= BEGIN

IMPORTS
    MODULE-IDENTITY, OBJECT-TYPE, Unsigned32
        FROM SNMPv2-SMI
    OBJECT-GROUP, MODULE-COMPLIANCE
        FROM SNMPv2-CONF
    DateAndTime, DisplayString
        FROM SNMPv2-TC
    lumModules, lumIfAmplifierMIB
        FROM LUM-REG
    MgmtNameString, Integer32WithNA, Signed32WithNA, AdminStatusWithNA, OperStatusWithNA, FaultStatusWithNA
        FROM LUM-TC;

lumIfAmplifierMIBModule MODULE-IDENTITY
    LAST-UPDATED
        "201809280000Z" -- September 28th 2018
    ORGANIZATION
        "Infinera Corporation"
    CONTACT-INFO
        "techsupport@infinera.com"
    DESCRIPTION
        "The MIB module for management of amplifier objects.

        The tables contained in this MIB are:

        (1) The General group contains some general attributes as time stamps
            and tables sizes.

        (2) The amplifier group contains information and
            configuration for high order amplifier object.
            The group is used for objects common for any amplifier type.

        (3) The module group contains information and
            configuration for all module objects.
            The group is used for representation of hardware modules on the board.

        (4) The raman group contains information and
            configuration for all Raman objects.
            The group is used for representation of amplifiers of Raman type.

        (5) The edfa group contains information and
            configuration for all EDFA objects.
            The group is used for representation of amplifiers of EDFA type.

"
    REVISION
        "201809280000Z" -- September 28th 2018
    DESCRIPTION
        "Changes made for release r31.1:
         - Added description field to amplifier."
    REVISION
        "201712150000Z" -- December 15th 2017
    DESCRIPTION
        "Changes made for release r30.0:
         - Added functionalType to amplifier.
         - Added actual-gain to Raman and EDFA."
    REVISION
        "201706150000Z" -- June 15th 2017
    DESCRIPTION
        "Changes made for release r29.0:
         - Changed ORGANIZATION and CONTACT-INFO"
    REVISION
        "201605300000Z" -- May 30th 2016
    DESCRIPTION
        "-Output power failed alarm added.
	 -Added default operStatus to not present."
    REVISION
        "201511300000Z" -- November 30th 2015
    DESCRIPTION
        "The initial revision of this module."
    ::= { lumModules 65 }

-- ----------------------------------------------------
-- Compliance area, containing groups and compliance
-- specifications.
-- ----------------------------------------------------

lumIfAmplifierConfs OBJECT IDENTIFIER ::= { lumIfAmplifierMIB 1 }
lumIfAmplifierGroups OBJECT IDENTIFIER ::= { lumIfAmplifierConfs 1 }
lumIfAmplifierCompl OBJECT IDENTIFIER ::= { lumIfAmplifierConfs 2 }

-- ----------------------------------------------------
-- Root for objects in the IFAMPLIFIER MIB
-- ----------------------------------------------------

lumIfAmplifierMIBObjects OBJECT IDENTIFIER ::= { lumIfAmplifierMIB 2 }

-- ----------------------------------------------------
-- This MIB contains the following groups:
-- ----------------------------------------------------

ifAmplifierGeneral OBJECT IDENTIFIER ::= { lumIfAmplifierMIBObjects 1 }
ifAmplifierAmplifierList OBJECT IDENTIFIER ::= { lumIfAmplifierMIBObjects 2 }
ifAmplifierModuleList OBJECT IDENTIFIER ::= { lumIfAmplifierMIBObjects 3 }
ifAmplifierRamanList OBJECT IDENTIFIER ::= { lumIfAmplifierMIBObjects 4 }
ifAmplifierEdfaList OBJECT IDENTIFIER ::= { lumIfAmplifierMIBObjects 5 }

-- ----------------------------------------------------
-- General group
-- ----------------------------------------------------

ifAmplifierGeneralConfigLastChangeTime OBJECT-TYPE
    SYNTAX      DateAndTime
    MAX-ACCESS  read-only
    STATUS      current
    DESCRIPTION
        "The time when the configuration of the MIB was
        last changed.

"
    ::= { ifAmplifierGeneral 1 }

ifAmplifierGeneralStateLastChangeTime OBJECT-TYPE
    SYNTAX      DateAndTime
    MAX-ACCESS  read-only
    STATUS      current
    DESCRIPTION
        "The time when the state and/or configuration of
        the MIB was last changed.

"
    ::= { ifAmplifierGeneral 2 }

ifAmplifierGeneralIfAmplifierAmplifierTableSize OBJECT-TYPE
    SYNTAX      Unsigned32
    MAX-ACCESS  read-only
    STATUS      current
    DESCRIPTION
        "Size of amplifier amplifier table.

"
    ::= { ifAmplifierGeneral 3 }

ifAmplifierGeneralIfAmplifierAmplifierConfigLastChangeTime OBJECT-TYPE
    SYNTAX      DateAndTime
    MAX-ACCESS  read-only
    STATUS      current
    DESCRIPTION
        "The time when the configuration of the table was
        last changed.

"
    ::= { ifAmplifierGeneral 4 }

ifAmplifierGeneralIfAmplifierAmplifierStateLastChangeTime OBJECT-TYPE
    SYNTAX      DateAndTime
    MAX-ACCESS  read-only
    STATUS      current
    DESCRIPTION
        "The time when the state and/or configuration of
        the table was last changed.

"
    ::= { ifAmplifierGeneral 5 }

ifAmplifierGeneralIfAmplifierModuleTableSize OBJECT-TYPE
    SYNTAX      Unsigned32
    MAX-ACCESS  read-only
    STATUS      current
    DESCRIPTION
        "Size of module amplifier table.

"
    ::= { ifAmplifierGeneral 6 }

ifAmplifierGeneralIfAmplifierModuleConfigLastChangeTime OBJECT-TYPE
    SYNTAX      DateAndTime
    MAX-ACCESS  read-only
    STATUS      current
    DESCRIPTION
        "The time when the configuration of the table was
        last changed.

"
    ::= { ifAmplifierGeneral 7 }

ifAmplifierGeneralIfAmplifierModuleStateLastChangeTime OBJECT-TYPE
    SYNTAX      DateAndTime
    MAX-ACCESS  read-only
    STATUS      current
    DESCRIPTION
        "The time when the state and/or configuration of
        the table was last changed.

"
    ::= { ifAmplifierGeneral 8 }

ifAmplifierGeneralIfAmplifierRamanTableSize OBJECT-TYPE
    SYNTAX      Unsigned32
    MAX-ACCESS  read-only
    STATUS      current
    DESCRIPTION
        "Size of Raman amplifier table.

"
    ::= { ifAmplifierGeneral 9 }

ifAmplifierGeneralIfAmplifierRamanConfigLastChangeTime OBJECT-TYPE
    SYNTAX      DateAndTime
    MAX-ACCESS  read-only
    STATUS      current
    DESCRIPTION
        "The time when the configuration of the table was
        last changed.

"
    ::= { ifAmplifierGeneral 10 }

ifAmplifierGeneralIfAmplifierRamanStateLastChangeTime OBJECT-TYPE
    SYNTAX      DateAndTime
    MAX-ACCESS  read-only
    STATUS      current
    DESCRIPTION
        "The time when the state and/or configuration of
        the table was last changed.

"
    ::= { ifAmplifierGeneral 11 }

ifAmplifierGeneralIfAmplifierEdfaTableSize OBJECT-TYPE
    SYNTAX      Unsigned32
    MAX-ACCESS  read-only
    STATUS      current
    DESCRIPTION
        "Size of EDFA amplifier table.

"
    ::= { ifAmplifierGeneral 12 }

ifAmplifierGeneralIfAmplifierEdfaConfigLastChangeTime OBJECT-TYPE
    SYNTAX      DateAndTime
    MAX-ACCESS  read-only
    STATUS      current
    DESCRIPTION
        "The time when the configuration of the table was
        last changed.

"
    ::= { ifAmplifierGeneral 13 }

ifAmplifierGeneralIfAmplifierEdfaStateLastChangeTime OBJECT-TYPE
    SYNTAX      DateAndTime
    MAX-ACCESS  read-only
    STATUS      current
    DESCRIPTION
        "The time when the state and/or configuration of
        the table was last changed.

"
    ::= { ifAmplifierGeneral 14 }

-- ----------------------------------------------------
-- Amplifier group
-- ----------------------------------------------------

ifAmplifierAmplifierTable  OBJECT-TYPE
    SYNTAX      SEQUENCE OF IfAmplifierAmplifierEntry
    MAX-ACCESS  not-accessible
    STATUS      current
    DESCRIPTION
        "The amplifier group contains information and
        configuration for all amplifier objects.
        The group is used for objects common for any amplifier type."

    ::= { ifAmplifierAmplifierList 1 }

ifAmplifierAmplifierEntry OBJECT-TYPE
    SYNTAX      IfAmplifierAmplifierEntry
    MAX-ACCESS  not-accessible
    STATUS      current
    DESCRIPTION
        "An entry in the ifAmplifier amplifier list.

"
    INDEX { ifAmplifierAmplifierIndex }
    ::= { ifAmplifierAmplifierTable 1 }

IfAmplifierAmplifierEntry ::=
    SEQUENCE {
        ifAmplifierAmplifierIndex           Unsigned32,
        ifAmplifierAmplifierName            MgmtNameString,
        ifAmplifierAmplifierUId             Unsigned32,
        ifAmplifierAmplifierRxPower         Signed32WithNA,
        ifAmplifierAmplifierTxPower         Signed32WithNA,
        ifAmplifierAmplifierWantedGain      Signed32WithNA,
        ifAmplifierAmplifierActualGain      Signed32WithNA,
        ifAmplifierAmplifierAdminStatus     AdminStatusWithNA,
        ifAmplifierAmplifierOperStatus      OperStatusWithNA,
        ifAmplifierAmplifierMidStageLoss    Signed32WithNA,
        ifAmplifierAmplifierTxIfIndex       Unsigned32,
        ifAmplifierAmplifierRxIfIndex       Unsigned32,
        ifAmplifierAmplifierSubrack         Unsigned32,
        ifAmplifierAmplifierSlot            Unsigned32,
        ifAmplifierAmplifierOutputPowerFail FaultStatusWithNA,
        ifAmplifierAmplifierSaturation      FaultStatusWithNA,
        ifAmplifierAmplifierFunctionalType  INTEGER,
        ifAmplifierAmplifierDescr           DisplayString}

ifAmplifierAmplifierIndex OBJECT-TYPE
    SYNTAX      Unsigned32
    MAX-ACCESS  read-only
    STATUS      current
    DESCRIPTION
        "An index assigned to each entry.

"
    ::= { ifAmplifierAmplifierEntry 1 }

ifAmplifierAmplifierName OBJECT-TYPE
    SYNTAX      MgmtNameString
    MAX-ACCESS  read-only
    STATUS      current
    DESCRIPTION
        "The management name of the amplifier object.

"
    ::= { ifAmplifierAmplifierEntry 2 }

ifAmplifierAmplifierUId OBJECT-TYPE
    SYNTAX      Unsigned32
    MAX-ACCESS  read-only
    STATUS      current
    DESCRIPTION
        "A unique identifier assigned to each entry.

"
    ::= { ifAmplifierAmplifierEntry 3 }

ifAmplifierAmplifierRxPower OBJECT-TYPE
    SYNTAX      Signed32WithNA
    MAX-ACCESS  read-only
    STATUS      current
    DESCRIPTION
        "The received signal power level in units of 0.1 dBm.

"
    ::= { ifAmplifierAmplifierEntry 4 }

ifAmplifierAmplifierTxPower OBJECT-TYPE
    SYNTAX      Signed32WithNA
    MAX-ACCESS  read-only
    STATUS      current
    DESCRIPTION
        "The transmitted power level in units of 0.1 dBm.

"
    ::= { ifAmplifierAmplifierEntry 5 }

ifAmplifierAmplifierWantedGain OBJECT-TYPE
    SYNTAX      Signed32WithNA
    MAX-ACCESS  read-write
    STATUS      current
    DESCRIPTION
        "The wanted signal gain setting in units of 0.1 dB.

        Range and default value depends on type of amplifier, see table below.

        Name                                  Min    Max   Default
        OARAED21/HG Hybrid Mode EDFA+Raman    27.0   39.0  27.0
        OARAED21/HG Individual Mode EDFA      15.0   27.0  15.0
        OARAED21/HG Individual Mode Raman      6.0   14.0  12.0
        OARAED20/LG Hybrid Mode EDFA+Raman    17.0   34.0  17.0
        OA20C/VG/II, OA2-20C/VG/II            20.0   30.0  20.0

"
    ::= { ifAmplifierAmplifierEntry 6 }

ifAmplifierAmplifierActualGain OBJECT-TYPE
    SYNTAX      Signed32WithNA
    MAX-ACCESS  read-only
    STATUS      current
    DESCRIPTION
        "Actual measured gain in units of 0.1 dB.

"
    ::= { ifAmplifierAmplifierEntry 7 }

ifAmplifierAmplifierAdminStatus OBJECT-TYPE
    SYNTAX      AdminStatusWithNA
    MAX-ACCESS  read-write
    STATUS      current
    DESCRIPTION
        "The administrative state of the interface.

        up - The interface is active.
             Pump(s) are activated if all activation criteria are fulfilled.

        down - The interface is de-activated. All pumps are shut off.

        service - The interface is activated but alarms are suppressed.
        Intended for use during service or re-configuration.
        When service is concluded adminStatus should be set to 'up' again.
        Note that there is no difference between 'up' and 'service',
        if no alarms can be raised from this object.

"
    DEFVAL { down }
    ::= { ifAmplifierAmplifierEntry 8 }

ifAmplifierAmplifierOperStatus OBJECT-TYPE
    SYNTAX      OperStatusWithNA
    MAX-ACCESS  read-only
    STATUS      current
    DESCRIPTION
        "The operational state of the interface.

        notPresent - The interface is not available.

        down - The interface is de-activated or there are
        faults preventing its transition to the 'up' state.

        up - The interface is active.

"
    DEFVAL { notPresent }
    ::= { ifAmplifierAmplifierEntry 9 }

ifAmplifierAmplifierMidStageLoss OBJECT-TYPE
    SYNTAX      Signed32WithNA
    MAX-ACCESS  read-only
    STATUS      current
    DESCRIPTION
        "The calculated loss between the two amplifier stages in units of 0.1 dB.

"
    ::= { ifAmplifierAmplifierEntry 10 }

ifAmplifierAmplifierTxIfIndex OBJECT-TYPE
    SYNTAX      Unsigned32
    MAX-ACCESS  read-only
    STATUS      current
    DESCRIPTION
        "The index number of the associated Tx port.

"
    ::= { ifAmplifierAmplifierEntry 11 }

ifAmplifierAmplifierRxIfIndex OBJECT-TYPE
    SYNTAX      Unsigned32
    MAX-ACCESS  read-only
    STATUS      current
    DESCRIPTION
        "The index number of the associated Rx port.

"
    ::= { ifAmplifierAmplifierEntry 12 }

ifAmplifierAmplifierSubrack OBJECT-TYPE
    SYNTAX      Unsigned32
    MAX-ACCESS  read-only
    STATUS      current
    DESCRIPTION
        "The subrack of the entry.

"
    ::= { ifAmplifierAmplifierEntry 13 }

ifAmplifierAmplifierSlot OBJECT-TYPE
    SYNTAX      Unsigned32
    MAX-ACCESS  read-only
    STATUS      current
    DESCRIPTION
        "The slot of the entry.

"
    ::= { ifAmplifierAmplifierEntry 14 }

ifAmplifierAmplifierOutputPowerFail OBJECT-TYPE
    SYNTAX      FaultStatusWithNA
    MAX-ACCESS  read-only
    STATUS      current
    DESCRIPTION
        "Output power failed alarm. If the difference of wanted gain
        and actual gain is larger than the safety margin and if the difference of
        output power and transmit power limit is larger than 0.7 dB
        the amplifier is not working properly.

"
    ::= { ifAmplifierAmplifierEntry 15 }

ifAmplifierAmplifierSaturation OBJECT-TYPE
    SYNTAX      FaultStatusWithNA
    MAX-ACCESS  read-only
    STATUS      current
    DESCRIPTION
        "Saturation alarm. If the difference of wanted gain and actual gain
        is larger than 1.0 dB (safety margin) the amplifier is considered saturated.

"
    ::= { ifAmplifierAmplifierEntry 16 }

ifAmplifierAmplifierFunctionalType OBJECT-TYPE
    SYNTAX      INTEGER {
                  undefined (1),
                  preAmp (2),
                  offLinePreAmp (3),
                  lineAmp (4),
                  booster (5) }
    MAX-ACCESS  read-write
    STATUS      current
    DESCRIPTION
        "The functional type of amplifier. This attribute is ONLY used
        to describe how the amplifier is used and traffic is not affected if changed.

        undefined     - default

        preAmp        - pre-amplifier. The receiving amplifier on a
                        terminal node.
                        The received signal is too weak to use without
                        amplification.

        offLinePreAmp - offline pre-amplifier. Receiving amplifier
                        in a non-terminal node. Offline pre-amplifier
                        amplifies dropped traffic, NOT line traffic.
                        Amplification is done before the received signal
                        is dropped.

        lineAmp       - line amplifier. Amplifier situated between
                        the terminal nodes, which amplifies passing
                        line traffic and (if applicable) added
                        traffic.
                        Amplification is done before sending the signal
                        on the line.

        booster       - booster. The transmitting amplifier from a
                        terminal node.
                        Used when receiving clients need a amplified signal.

"
    DEFVAL { undefined }
    ::= { ifAmplifierAmplifierEntry 17 }

ifAmplifierAmplifierDescr OBJECT-TYPE
    SYNTAX      DisplayString
    MAX-ACCESS  read-write
    STATUS      current
    DESCRIPTION
        "User configurable label.

"
    DEFVAL { "" }
    ::= { ifAmplifierAmplifierEntry 18 }


-- ----------------------------------------------------
-- Module group
-- ----------------------------------------------------

ifAmplifierModuleTable  OBJECT-TYPE
    SYNTAX      SEQUENCE OF IfAmplifierModuleEntry
    MAX-ACCESS  not-accessible
    STATUS      current
    DESCRIPTION
        "The module group contains information and
        configuration for all module objects.
        The group is used for representation of hardware modules on the board.
        "

    ::= { ifAmplifierModuleList 1 }

ifAmplifierModuleEntry OBJECT-TYPE
    SYNTAX      IfAmplifierModuleEntry
    MAX-ACCESS  not-accessible
    STATUS      current
    DESCRIPTION
        "An entry in the ifAmplifier module list.

"
    INDEX { ifAmplifierModuleIndex }
    ::= { ifAmplifierModuleTable 1 }

IfAmplifierModuleEntry ::=
    SEQUENCE {
        ifAmplifierModuleIndex                        Unsigned32,
        ifAmplifierModuleName                         MgmtNameString,
        ifAmplifierModuleUId                          Unsigned32,
        ifAmplifierModuleTemperature                  Integer32WithNA,
        ifAmplifierModuleInfo                         DisplayString,
        ifAmplifierModuleHighModuleTemperature        FaultStatusWithNA,
        ifAmplifierModuleHighPumpCurrent              FaultStatusWithNA,
        ifAmplifierModuleHighPumpTemperature          FaultStatusWithNA,
        ifAmplifierModuleCommunicationFailure         FaultStatusWithNA,
        ifAmplifierModuleColdRestart                  INTEGER,
        ifAmplifierModuleSubrack                      Unsigned32,
        ifAmplifierModuleSlot                         Unsigned32 }

ifAmplifierModuleIndex OBJECT-TYPE
    SYNTAX      Unsigned32
    MAX-ACCESS  read-only
    STATUS      current
    DESCRIPTION
        "An index assigned to each entry.

"
    ::= { ifAmplifierModuleEntry 1 }

ifAmplifierModuleName OBJECT-TYPE
    SYNTAX      MgmtNameString
    MAX-ACCESS  read-only
    STATUS      current
    DESCRIPTION
        "The management name of the module object.

"
    ::= { ifAmplifierModuleEntry 2 }

ifAmplifierModuleUId OBJECT-TYPE
    SYNTAX      Unsigned32
    MAX-ACCESS  read-only
    STATUS      current
    DESCRIPTION
        "A unique identifier assigned to each entry.

"
    ::= { ifAmplifierModuleEntry 3 }

ifAmplifierModuleTemperature OBJECT-TYPE
    SYNTAX      Integer32WithNA
    MAX-ACCESS  read-only
    STATUS      current
    DESCRIPTION
        "The actual module temperature in units of
        0.1 degrees Celsius.

"
    ::= { ifAmplifierModuleEntry 4 }

ifAmplifierModuleInfo OBJECT-TYPE
    SYNTAX      DisplayString
    MAX-ACCESS  read-only
    STATUS      current
    DESCRIPTION
        "Module information about firmware and serial number of the module on the board.

"
    ::= { ifAmplifierModuleEntry 5 }

ifAmplifierModuleHighModuleTemperature OBJECT-TYPE
    SYNTAX      FaultStatusWithNA
    MAX-ACCESS  read-only
    STATUS      current
    DESCRIPTION
        "The actual temperature is over the module internal temperature alarm threshold.

"
    ::= { ifAmplifierModuleEntry 6 }

ifAmplifierModuleHighPumpCurrent OBJECT-TYPE
    SYNTAX      FaultStatusWithNA
    MAX-ACCESS  read-only
    STATUS      current
    DESCRIPTION
        "The actual pump current of any pump in the module
        is over the module internal pump current alarm threshold.

"
    ::= { ifAmplifierModuleEntry 7 }

ifAmplifierModuleHighPumpTemperature OBJECT-TYPE
    SYNTAX      FaultStatusWithNA
    MAX-ACCESS  read-only
    STATUS      current
    DESCRIPTION
        "The actual pump temperature of any pump in the module
        is over the module internal pump temperature alarm threshold.

"
    ::= { ifAmplifierModuleEntry 8 }

ifAmplifierModuleCommunicationFailure OBJECT-TYPE
    SYNTAX      FaultStatusWithNA
    MAX-ACCESS  read-only
    STATUS      current
    DESCRIPTION
        "Communication between the module and the traffic unit has
        failed.

        A: The module does not respond.

        D: Communication works.

"
    ::= {ifAmplifierModuleEntry 9 }

ifAmplifierModuleColdRestart OBJECT-TYPE
    SYNTAX      INTEGER { doSoftwareColdRestart(1),
                          doNotSoftwareColdRestart(2)}
    MAX-ACCESS  read-write
    STATUS      current
    DESCRIPTION
        "Software initiated cold restart of the Amplifier Module.
        Cold restart process may take a few seconds, during this period traffic will be disturbed.

"
    DEFVAL { doNotSoftwareColdRestart }
    ::= { ifAmplifierModuleEntry 10 }

ifAmplifierModuleSubrack OBJECT-TYPE
    SYNTAX      Unsigned32
    MAX-ACCESS  read-only
    STATUS      current
    DESCRIPTION
        "The subrack of the entry.

"
    ::= { ifAmplifierModuleEntry 11 }

ifAmplifierModuleSlot OBJECT-TYPE
    SYNTAX      Unsigned32
    MAX-ACCESS  read-only
    STATUS      current
    DESCRIPTION
        "The slot of the entry.

"
    ::= { ifAmplifierModuleEntry 12 }

-- ----------------------------------------------------
-- Raman group
-- ----------------------------------------------------

ifAmplifierRamanTable  OBJECT-TYPE
    SYNTAX      SEQUENCE OF IfAmplifierRamanEntry
    MAX-ACCESS  not-accessible
    STATUS      current
    DESCRIPTION
        "The Raman group contains information and
         configuration for all Raman objects.
         The group is used for representation of amplifiers of Raman type.
         "

    ::= { ifAmplifierRamanList 1 }

ifAmplifierRamanEntry OBJECT-TYPE
    SYNTAX      IfAmplifierRamanEntry
    MAX-ACCESS  not-accessible
    STATUS      current
    DESCRIPTION
        "An entry in the ifAmplifier Raman list.

"
    INDEX { ifAmplifierRamanIndex }
    ::= { ifAmplifierRamanTable 1 }

IfAmplifierRamanEntry ::=
    SEQUENCE {
        ifAmplifierRamanIndex                       Unsigned32,
        ifAmplifierRamanName                        MgmtNameString,
        ifAmplifierRamanUId                         Unsigned32,
        ifAmplifierRamanLineFiberType               INTEGER,
        ifAmplifierRamanWantedGainTilt              Signed32WithNA,
        ifAmplifierRamanReceivedPowerLevel          Signed32WithNA,
        ifAmplifierRamanPump1Power                  Signed32WithNA,
        ifAmplifierRamanPump1Status                 INTEGER,
        ifAmplifierRamanPump2Power                  Signed32WithNA,
        ifAmplifierRamanPump2Status                 INTEGER,
        ifAmplifierRamanTotalPumpPower              Signed32WithNA,
        ifAmplifierRamanBackReflectionPower         Signed32WithNA,
        ifAmplifierRamanBackReflectionPowerRatio    Signed32WithNA,
        ifAmplifierRamanHighBackReflection          FaultStatusWithNA,
        ifAmplifierRamanHighBackReflectionThld      Signed32WithNA,
        ifAmplifierRamanPointInsertionLoss          Signed32WithNA,
        ifAmplifierRamanPointInsertionLossThld      Signed32WithNA,
        ifAmplifierRamanHighPointInsertionLoss      FaultStatusWithNA,
        ifAmplifierRamanRelatedAmplifierIndex       Unsigned32,
        ifAmplifierRamanSubrack                     Unsigned32,
        ifAmplifierRamanSlot                        Unsigned32,
	ifAmplifierRamanActualGain                  Signed32WithNA}

ifAmplifierRamanIndex OBJECT-TYPE
    SYNTAX      Unsigned32
    MAX-ACCESS  read-only
    STATUS      current
    DESCRIPTION
        "An index assigned to each entry.

"
    ::= { ifAmplifierRamanEntry 1 }

ifAmplifierRamanName OBJECT-TYPE
    SYNTAX      MgmtNameString
    MAX-ACCESS  read-only
    STATUS      current
    DESCRIPTION
        "The management name of the Raman object.

"
    ::= { ifAmplifierRamanEntry 2 }

ifAmplifierRamanUId OBJECT-TYPE
    SYNTAX      Unsigned32
    MAX-ACCESS  read-only
    STATUS      current
    DESCRIPTION
        "A unique identifier assigned to each entry.

"
    ::= { ifAmplifierRamanEntry 3 }

ifAmplifierRamanLineFiberType OBJECT-TYPE
    SYNTAX      INTEGER {
                        ftG652(1),
                        ftG655(2),
                        notApplicable(2147483647)}
    MAX-ACCESS  read-create
    STATUS      current
    DESCRIPTION
        "Line fiber type setting for the Raman amplifier.

"
    DEFVAL { ftG652 }
    ::= { ifAmplifierRamanEntry 4 }

ifAmplifierRamanWantedGainTilt OBJECT-TYPE
    SYNTAX      Signed32WithNA ( -15..5 | 2147483647 )
    MAX-ACCESS  read-write
    STATUS      current
    DESCRIPTION
        "The wanted Raman gain tilt. A negative value will amplify
        shorter wavelengths more than longer wavelengths.

"
    DEFVAL { 0 }
    ::= { ifAmplifierRamanEntry 5 }

ifAmplifierRamanReceivedPowerLevel OBJECT-TYPE
    SYNTAX      Signed32WithNA
    MAX-ACCESS  read-only
    STATUS      current
    DESCRIPTION
        "The received power level on the Raman input interface.
        The presented power level includes both signal and optical noise.
        In contrast Raman Rx power level only presents signal input.

"
    ::= { ifAmplifierRamanEntry 6 }

ifAmplifierRamanPump1Power OBJECT-TYPE
    SYNTAX      Signed32WithNA
    MAX-ACCESS  read-only
    STATUS      current
    DESCRIPTION
        "Pump power of the first Raman pump in units of 0.1 dBm.

"
    ::= { ifAmplifierRamanEntry 7 }

ifAmplifierRamanPump1Status OBJECT-TYPE
    SYNTAX  INTEGER {
                    off (0),
                    on (1),
                    notAvailable (2147483646),
                    notApplicable (2147483647) }
    MAX-ACCESS  read-only
    STATUS      current
    DESCRIPTION
        "Status of the first Raman pump. Can take values on or off.

"
    ::= { ifAmplifierRamanEntry 8 }

ifAmplifierRamanPump2Power OBJECT-TYPE
    SYNTAX      Signed32WithNA
    MAX-ACCESS  read-only
    STATUS      current
    DESCRIPTION
       "Pump power of the second Raman pump in units of 0.1 dBm.

"
    ::= { ifAmplifierRamanEntry 9 }

ifAmplifierRamanPump2Status OBJECT-TYPE
    SYNTAX  INTEGER {
                    off (0),
                    on (1),
                    notAvailable (2147483646),
                    notApplicable (2147483647) }
    MAX-ACCESS  read-only
    STATUS      current
    DESCRIPTION
        "Status of the second Raman pump. Can take values on or off.

"
    ::= { ifAmplifierRamanEntry 10 }

ifAmplifierRamanTotalPumpPower OBJECT-TYPE
    SYNTAX      Signed32WithNA
    MAX-ACCESS  read-only
    STATUS      current
    DESCRIPTION
        "Combined Raman Pumps power in units of 0.1 dBm.
        This is the total optical power that will enter through Raman Rx port into the line fiber.

"
    ::= { ifAmplifierRamanEntry 11 }

ifAmplifierRamanBackReflectionPower OBJECT-TYPE
    SYNTAX      Signed32WithNA
    MAX-ACCESS  read-only
    STATUS      current
    DESCRIPTION
        "The Back reflected power of the Raman pump in units of 0.1 dBm.

"
    ::= { ifAmplifierRamanEntry 12 }

ifAmplifierRamanBackReflectionPowerRatio OBJECT-TYPE
    SYNTAX      Signed32WithNA
    MAX-ACCESS  read-only
    STATUS      current
    DESCRIPTION
        "The Back reflected power ratio of the Raman pump.
        This parameter is calculated by dividing the Total pump power by
        the back reflected power of the Raman.
        Presented in units of 0.1 dB.

"
    ::= { ifAmplifierRamanEntry 13 }

ifAmplifierRamanHighBackReflection OBJECT-TYPE
    SYNTAX      FaultStatusWithNA
    MAX-ACCESS  read-only
    STATUS      current
    DESCRIPTION
        "High Back Reflection. When back reflection power ratio
        is below the High back reflection threshold the alarm is activated.

"
    ::= { ifAmplifierRamanEntry 14 }

ifAmplifierRamanHighBackReflectionThld OBJECT-TYPE
    SYNTAX      Signed32WithNA ( 200..280 | 2147483647)
    MAX-ACCESS  read-write
    STATUS      current
    DESCRIPTION
        "High Back Reflection Threshold. The threshold to trigger
        the High back reflection alarm.

"
    DEFVAL { 260 }
    ::= { ifAmplifierRamanEntry 15 }

ifAmplifierRamanPointInsertionLoss OBJECT-TYPE
    SYNTAX      Signed32WithNA
    MAX-ACCESS  read-only
    STATUS      current
    DESCRIPTION
        "Point Insertion Loss. The calculated insertion loss between
        the Raman pump and line fiber. Value is given in units of 0.1 dB
        and cannot be positive. Recommended value is between 0.0 and -0.5 dB.

"
    ::= { ifAmplifierRamanEntry 16 }

ifAmplifierRamanPointInsertionLossThld OBJECT-TYPE
    SYNTAX      Signed32WithNA
    MAX-ACCESS  read-write
    STATUS      current
    DESCRIPTION
        "Point Insertion Loss Threshold. Settable threshold for High point
        insertion loss alarm. If Point insertion loss is more negative than
        threshold High point insertion loss alarm will be activated.
        The recommended value for PIL is between 0 and -0.5 dB. A value lower
        than the default threshold value of -1 dB may severely reduce the
        Raman gain and cause a deterioration of the amplifier noise figure.

        Range depends on type of amplifier, see table below.

        Name                         Min       Max
        OARAED21/HG                  -1.0 dB   -0.5 dB
        OARAED20/LG                  -3.0 dB   -0.5 dB

"
    DEFVAL { -10 }
    ::= { ifAmplifierRamanEntry 17 }

ifAmplifierRamanHighPointInsertionLoss OBJECT-TYPE
    SYNTAX      FaultStatusWithNA
    MAX-ACCESS  read-only
    STATUS      current
    DESCRIPTION
        "High Point Insertion Loss. If Point insertion loss is below Point insertion loss threshold
        High point insertion loss alarm will be activated.

"
    ::= { ifAmplifierRamanEntry 18 }

ifAmplifierRamanRelatedAmplifierIndex OBJECT-TYPE
    SYNTAX      Unsigned32
    MAX-ACCESS  read-only
    STATUS      current
    DESCRIPTION
        "The index number of the associated Amplifier object.

"
    ::= { ifAmplifierRamanEntry 19 }

ifAmplifierRamanSubrack OBJECT-TYPE
    SYNTAX      Unsigned32
    MAX-ACCESS  read-only
    STATUS      current
    DESCRIPTION
        "The subrack of the entry.

"
    ::= { ifAmplifierRamanEntry 20 }

ifAmplifierRamanSlot OBJECT-TYPE
    SYNTAX      Unsigned32
    MAX-ACCESS  read-only
    STATUS      current
    DESCRIPTION
        "The slot of the entry.

"
    ::= { ifAmplifierRamanEntry 21 }

ifAmplifierRamanActualGain OBJECT-TYPE
    SYNTAX      Signed32WithNA
    MAX-ACCESS  read-only
    STATUS      current
    DESCRIPTION
        "The actual gain contribution of the Raman amplifier stage.

"
    ::= { ifAmplifierRamanEntry 22 }

-- ----------------------------------------------------
-- EDFA group
-- ----------------------------------------------------

ifAmplifierEdfaTable  OBJECT-TYPE
    SYNTAX      SEQUENCE OF IfAmplifierEdfaEntry
    MAX-ACCESS  not-accessible
    STATUS      current
    DESCRIPTION
        "The edfa group contains information and
        configuration for all EDFA objects.
        The group is used for representation of amplifiers of EDFA type.
        "

    ::= { ifAmplifierEdfaList 1 }

ifAmplifierEdfaEntry OBJECT-TYPE
    SYNTAX      IfAmplifierEdfaEntry
    MAX-ACCESS  not-accessible
    STATUS      current
    DESCRIPTION
        "An entry in the ifAmplifier EDFA list.

"
    INDEX { ifAmplifierEdfaIndex }
    ::= { ifAmplifierEdfaTable 1 }

IfAmplifierEdfaEntry ::=
    SEQUENCE {
        ifAmplifierEdfaIndex                        Unsigned32,
        ifAmplifierEdfaName                         MgmtNameString,
        ifAmplifierEdfaUId                          Unsigned32,
        ifAmplifierEdfaWantedGainTilt               Signed32WithNA,
        ifAmplifierEdfaTxPowerLimit                 Signed32WithNA,
        ifAmplifierEdfaPumpStatus                   INTEGER,
        ifAmplifierEdfaBackReflectionPower          Signed32WithNA,
        ifAmplifierEdfaBackReflectionPowerRatio     Signed32WithNA,
        ifAmplifierEdfaHighBackReflection           FaultStatusWithNA,
        ifAmplifierEdfaHighBackReflectionThld       Signed32WithNA,
        ifAmplifierEdfaSaturation                   FaultStatusWithNA,
        ifAmplifierEdfaMonitorPortLoss              Signed32WithNA,
        ifAmplifierEdfaRelatedAmplifierIndex        Unsigned32,
        ifAmplifierEdfaSubrack                      Unsigned32,
        ifAmplifierEdfaSlot                         Unsigned32,
        ifAmplifierEdfaPumpPower                    Signed32WithNA,
        ifAmplifierEdfaPumpCurrent                  Signed32WithNA,
	ifAmplifierEdfaActualGain                   Signed32WithNA}

ifAmplifierEdfaIndex OBJECT-TYPE
    SYNTAX      Unsigned32
    MAX-ACCESS  read-only
    STATUS      current
    DESCRIPTION
        "An index assigned to each entry.

"
    ::= { ifAmplifierEdfaEntry 1 }

ifAmplifierEdfaName OBJECT-TYPE
    SYNTAX      MgmtNameString
    MAX-ACCESS  read-only
    STATUS      current
    DESCRIPTION
        "The management name of the EDFA object.

"
    ::= { ifAmplifierEdfaEntry 2 }

ifAmplifierEdfaUId OBJECT-TYPE
    SYNTAX      Unsigned32
    MAX-ACCESS  read-only
    STATUS      current
    DESCRIPTION
        "A unique identifier assigned to each entry.

"
    ::= { ifAmplifierEdfaEntry 3 }

ifAmplifierEdfaWantedGainTilt OBJECT-TYPE
    SYNTAX      Signed32WithNA ( -20..0 | 2147483647 )
    MAX-ACCESS  read-write
    STATUS      current
    DESCRIPTION
        "The wanted EDFA gain tilt. A negative value will amplify
        shorter wavelengths more than longer wavelengths.

        Range and default value depends on type of amplifier.
        OARAED21/HG
        Min: -2
        Max: 0
        Default: -1

        OA20C/VG/II, OA2-20C/VG/II
        Min: -1
        Max: 0
        Default: 0

"
    DEFVAL { -10 }
    ::= { ifAmplifierEdfaEntry 4 }

ifAmplifierEdfaTxPowerLimit OBJECT-TYPE
    SYNTAX      Signed32WithNA
    MAX-ACCESS  read-write
    STATUS      current
    DESCRIPTION
        "Settable limit for maximum allowed output power.

        Range and default value depends on type of amplifier.

        Name                         Min   Max   Default
        OARAED21/HG                  15.0  21.5  21.5
        OARAED21/LG                  15.0  19.5  19.5
        OA20C/VG/II, OA2-20C/VG/II    0.0  19.5  19.5

"
    ::= { ifAmplifierEdfaEntry 5 }

ifAmplifierEdfaPumpStatus OBJECT-TYPE
    SYNTAX  INTEGER {
                    off (0),
                    on (1),
                    notAvailable (2147483646) }
    MAX-ACCESS  read-only
    STATUS      current
    DESCRIPTION
         "Status of the EDFA pump. Can take values on or off.

"
    ::= { ifAmplifierEdfaEntry 6 }

ifAmplifierEdfaBackReflectionPower OBJECT-TYPE
    SYNTAX      Signed32WithNA
    MAX-ACCESS  read-only
    STATUS      current
    DESCRIPTION
        "The Back reflected power of the EDFA output in units of 0.1 dBm.

"
    ::= { ifAmplifierEdfaEntry 7 }

ifAmplifierEdfaBackReflectionPowerRatio OBJECT-TYPE
    SYNTAX      Signed32WithNA
    MAX-ACCESS  read-only
    STATUS      current
    DESCRIPTION
        "The Back reflected power ratio of the EDFA output.
        This parameter is calculated by dividing the EDFA
        output power by the back reflected power of the EDFA.
        Presented in units of 0.1 dB.

"
    ::= { ifAmplifierEdfaEntry 8 }

ifAmplifierEdfaHighBackReflection OBJECT-TYPE
    SYNTAX      FaultStatusWithNA
    MAX-ACCESS  read-only
    STATUS      current
    DESCRIPTION
        "High Back Reflection. When back reflection power ratio
        is below the High back reflection threshold the alarm is activated.

"
    ::= { ifAmplifierEdfaEntry 9 }

ifAmplifierEdfaHighBackReflectionThld OBJECT-TYPE
    SYNTAX      Signed32WithNA ( 200..280 | 2147483647 )
    MAX-ACCESS  read-write
    STATUS      current
    DESCRIPTION
       "High Back Reflection Threshold.
       The threshold to trigger the High back reflection alarm.

"
    DEFVAL { 260 }
    ::= { ifAmplifierEdfaEntry 10 }

ifAmplifierEdfaSaturation OBJECT-TYPE
    SYNTAX      FaultStatusWithNA
    MAX-ACCESS  read-only
    STATUS      deprecated
    DESCRIPTION
        "Saturation alarm. If the difference of wanted gain and actual gain
        is larger than 1.0 dB the amplifier is considered saturated.

"
    ::= { ifAmplifierEdfaEntry 11 }

ifAmplifierEdfaMonitorPortLoss OBJECT-TYPE
    SYNTAX      Signed32WithNA
    MAX-ACCESS  read-only
    STATUS      current
    DESCRIPTION
        "Monitor port loss. The difference in attenuation between EDFA output and EDFA monitor port.
        This is a value that is module specific and is presented in units of 0.1 dB.

"
    ::= { ifAmplifierEdfaEntry 12 }

ifAmplifierEdfaRelatedAmplifierIndex OBJECT-TYPE
    SYNTAX      Unsigned32
    MAX-ACCESS  read-only
    STATUS      current
    DESCRIPTION
        "The index number of the associated Amplifier object.

"
    ::= { ifAmplifierEdfaEntry 13 }

ifAmplifierEdfaSubrack OBJECT-TYPE
    SYNTAX      Unsigned32
    MAX-ACCESS  read-only
    STATUS      current
    DESCRIPTION
        "The subrack of the entry.

"
    ::= { ifAmplifierEdfaEntry 14 }

ifAmplifierEdfaSlot OBJECT-TYPE
    SYNTAX      Unsigned32
    MAX-ACCESS  read-only
    STATUS      current
    DESCRIPTION
        "The slot of the entry.

"
    ::= { ifAmplifierEdfaEntry 15 }

ifAmplifierEdfaPumpPower OBJECT-TYPE
    SYNTAX      Signed32WithNA
    MAX-ACCESS  read-only
    STATUS      current
    DESCRIPTION
        "Pump power of the EDFA pump in units of 0.1 dBm.

"
    ::= { ifAmplifierEdfaEntry 16 }

ifAmplifierEdfaPumpCurrent OBJECT-TYPE
    SYNTAX      Signed32WithNA
    MAX-ACCESS  read-only
    STATUS      current
    DESCRIPTION
        "Pump current of the EDFA pump in units of 0.1 mA.

"
    ::= { ifAmplifierEdfaEntry 17 }

ifAmplifierEdfaActualGain OBJECT-TYPE
    SYNTAX      Signed32WithNA
    MAX-ACCESS  read-only
    STATUS      current
    DESCRIPTION
        "The actual gain contribution of the EDFA amplifier stage.

"
    ::= { ifAmplifierEdfaEntry 18 }

-- ----------------------------------------------------
-- Notifications
-- ----------------------------------------------------

-- ----------------------------------------------------
-- Object and event groups
-- ----------------------------------------------------

ifAmplifierGeneralGroupV1 OBJECT-GROUP
    OBJECTS {
        ifAmplifierGeneralConfigLastChangeTime,
        ifAmplifierGeneralStateLastChangeTime,
        ifAmplifierGeneralIfAmplifierAmplifierTableSize,
        ifAmplifierGeneralIfAmplifierAmplifierConfigLastChangeTime,
        ifAmplifierGeneralIfAmplifierAmplifierStateLastChangeTime,
        ifAmplifierGeneralIfAmplifierModuleTableSize,
        ifAmplifierGeneralIfAmplifierModuleConfigLastChangeTime,
        ifAmplifierGeneralIfAmplifierModuleStateLastChangeTime,
        ifAmplifierGeneralIfAmplifierRamanTableSize,
        ifAmplifierGeneralIfAmplifierRamanConfigLastChangeTime,
        ifAmplifierGeneralIfAmplifierRamanStateLastChangeTime,
        ifAmplifierGeneralIfAmplifierEdfaTableSize,
        ifAmplifierGeneralIfAmplifierEdfaConfigLastChangeTime,
        ifAmplifierGeneralIfAmplifierEdfaStateLastChangeTime }
    STATUS      current
    DESCRIPTION
        "The general objects."
    ::= { lumIfAmplifierGroups 1 }

ifAmplifierAmplifierGroupV1 OBJECT-GROUP
    OBJECTS {
        ifAmplifierAmplifierIndex,
        ifAmplifierAmplifierName,
        ifAmplifierAmplifierUId,
        ifAmplifierAmplifierRxPower,
        ifAmplifierAmplifierTxPower,
        ifAmplifierAmplifierWantedGain,
        ifAmplifierAmplifierActualGain,
        ifAmplifierAmplifierAdminStatus,
        ifAmplifierAmplifierOperStatus,
        ifAmplifierAmplifierMidStageLoss,
        ifAmplifierAmplifierTxIfIndex,
        ifAmplifierAmplifierRxIfIndex,
        ifAmplifierAmplifierSubrack,
        ifAmplifierAmplifierSlot }
    STATUS      deprecated
    DESCRIPTION
        "The ifAmplifierAmplifier objects."
    ::= { lumIfAmplifierGroups 2 }

ifAmplifierAmplifierGroupV2 OBJECT-GROUP
    OBJECTS {
        ifAmplifierAmplifierIndex,
        ifAmplifierAmplifierName,
        ifAmplifierAmplifierUId,
        ifAmplifierAmplifierRxPower,
        ifAmplifierAmplifierTxPower,
        ifAmplifierAmplifierWantedGain,
        ifAmplifierAmplifierActualGain,
        ifAmplifierAmplifierAdminStatus,
        ifAmplifierAmplifierOperStatus,
        ifAmplifierAmplifierMidStageLoss,
        ifAmplifierAmplifierTxIfIndex,
        ifAmplifierAmplifierRxIfIndex,
        ifAmplifierAmplifierSubrack,
        ifAmplifierAmplifierSlot,
        ifAmplifierAmplifierOutputPowerFail,
        ifAmplifierAmplifierSaturation }
    STATUS      deprecated
    DESCRIPTION
        "The ifAmplifierAmplifier objects (27.0)."
    ::= { lumIfAmplifierGroups 6 }

ifAmplifierModuleGroupV1 OBJECT-GROUP
    OBJECTS {
        ifAmplifierModuleIndex,
        ifAmplifierModuleName,
        ifAmplifierModuleUId,
        ifAmplifierModuleTemperature,
        ifAmplifierModuleInfo,
        ifAmplifierModuleHighModuleTemperature,
        ifAmplifierModuleHighPumpCurrent,
        ifAmplifierModuleHighPumpTemperature,
        ifAmplifierModuleCommunicationFailure,
        ifAmplifierModuleColdRestart,
        ifAmplifierModuleSubrack,
        ifAmplifierModuleSlot }
    STATUS      current
    DESCRIPTION
        "The ifAmplifierModule objects."
    ::= { lumIfAmplifierGroups 3 }

ifAmplifierRamanGroupV1 OBJECT-GROUP
    OBJECTS {
        ifAmplifierRamanIndex,
        ifAmplifierRamanName,
        ifAmplifierRamanUId,
        ifAmplifierRamanLineFiberType,
        ifAmplifierRamanWantedGainTilt,
        ifAmplifierRamanReceivedPowerLevel,
        ifAmplifierRamanPump1Power,
        ifAmplifierRamanPump1Status,
        ifAmplifierRamanPump2Power,
        ifAmplifierRamanPump2Status,
        ifAmplifierRamanTotalPumpPower,
        ifAmplifierRamanBackReflectionPower,
        ifAmplifierRamanBackReflectionPowerRatio,
        ifAmplifierRamanHighBackReflection,
        ifAmplifierRamanHighBackReflectionThld,
        ifAmplifierRamanPointInsertionLoss,
        ifAmplifierRamanPointInsertionLossThld,
        ifAmplifierRamanHighPointInsertionLoss,
        ifAmplifierRamanRelatedAmplifierIndex,
        ifAmplifierRamanSubrack,
        ifAmplifierRamanSlot }
    STATUS      deprecated
    DESCRIPTION
        "The ifAmplifierRaman objects."
    ::= { lumIfAmplifierGroups 4 }

ifAmplifierEdfaGroupV1 OBJECT-GROUP
    OBJECTS {
        ifAmplifierEdfaIndex,
        ifAmplifierEdfaName,
        ifAmplifierEdfaUId,
        ifAmplifierEdfaWantedGainTilt,
        ifAmplifierEdfaTxPowerLimit,
        ifAmplifierEdfaPumpStatus,
        ifAmplifierEdfaBackReflectionPower,
        ifAmplifierEdfaBackReflectionPowerRatio,
        ifAmplifierEdfaHighBackReflection,
        ifAmplifierEdfaHighBackReflectionThld,
        ifAmplifierEdfaSaturation,
        ifAmplifierEdfaMonitorPortLoss,
        ifAmplifierEdfaRelatedAmplifierIndex,
        ifAmplifierEdfaSubrack,
        ifAmplifierEdfaSlot }
    STATUS      deprecated
    DESCRIPTION
        "The ifAmplifierEdfa objects."
    ::= { lumIfAmplifierGroups 5 }

ifAmplifierEdfaGroupV2 OBJECT-GROUP
    OBJECTS {
        ifAmplifierEdfaIndex,
        ifAmplifierEdfaName,
        ifAmplifierEdfaUId,
        ifAmplifierEdfaWantedGainTilt,
        ifAmplifierEdfaTxPowerLimit,
        ifAmplifierEdfaPumpStatus,
        ifAmplifierEdfaBackReflectionPower,
        ifAmplifierEdfaBackReflectionPowerRatio,
        ifAmplifierEdfaHighBackReflection,
        ifAmplifierEdfaHighBackReflectionThld,
        ifAmplifierEdfaMonitorPortLoss,
        ifAmplifierEdfaRelatedAmplifierIndex,
        ifAmplifierEdfaSubrack,
        ifAmplifierEdfaSlot,
        ifAmplifierEdfaPumpPower,
        ifAmplifierEdfaPumpCurrent }
    STATUS      deprecated
    DESCRIPTION
        "The ifAmplifierEdfa objects (27.0)."
    ::= { lumIfAmplifierGroups 7 }

ifAmplifierRamanGroupV2 OBJECT-GROUP
    OBJECTS {
        ifAmplifierRamanIndex,
        ifAmplifierRamanName,
        ifAmplifierRamanUId,
        ifAmplifierRamanLineFiberType,
        ifAmplifierRamanWantedGainTilt,
        ifAmplifierRamanReceivedPowerLevel,
        ifAmplifierRamanPump1Power,
        ifAmplifierRamanPump1Status,
        ifAmplifierRamanPump2Power,
        ifAmplifierRamanPump2Status,
        ifAmplifierRamanTotalPumpPower,
        ifAmplifierRamanBackReflectionPower,
        ifAmplifierRamanBackReflectionPowerRatio,
        ifAmplifierRamanHighBackReflection,
        ifAmplifierRamanHighBackReflectionThld,
        ifAmplifierRamanPointInsertionLoss,
        ifAmplifierRamanPointInsertionLossThld,
        ifAmplifierRamanHighPointInsertionLoss,
        ifAmplifierRamanRelatedAmplifierIndex,
        ifAmplifierRamanSubrack,
        ifAmplifierRamanSlot,
        ifAmplifierRamanActualGain}
    STATUS      current
    DESCRIPTION
        "The ifAmplifierRaman objects (30.0)."
    ::= { lumIfAmplifierGroups 8 }

ifAmplifierEdfaGroupV3 OBJECT-GROUP
    OBJECTS {
        ifAmplifierEdfaIndex,
        ifAmplifierEdfaName,
        ifAmplifierEdfaUId,
        ifAmplifierEdfaWantedGainTilt,
        ifAmplifierEdfaTxPowerLimit,
        ifAmplifierEdfaPumpStatus,
        ifAmplifierEdfaBackReflectionPower,
        ifAmplifierEdfaBackReflectionPowerRatio,
        ifAmplifierEdfaHighBackReflection,
        ifAmplifierEdfaHighBackReflectionThld,
        ifAmplifierEdfaMonitorPortLoss,
        ifAmplifierEdfaRelatedAmplifierIndex,
        ifAmplifierEdfaSubrack,
        ifAmplifierEdfaSlot,
        ifAmplifierEdfaPumpPower,
        ifAmplifierEdfaPumpCurrent,
        ifAmplifierEdfaActualGain}
    STATUS      current
    DESCRIPTION
        "The ifAmplifierEdfa objects (30.0)."
    ::= { lumIfAmplifierGroups 9 }

ifAmplifierAmplifierGroupV3 OBJECT-GROUP
    OBJECTS {
        ifAmplifierAmplifierIndex,
        ifAmplifierAmplifierName,
        ifAmplifierAmplifierUId,
        ifAmplifierAmplifierRxPower,
        ifAmplifierAmplifierTxPower,
        ifAmplifierAmplifierWantedGain,
        ifAmplifierAmplifierActualGain,
        ifAmplifierAmplifierAdminStatus,
        ifAmplifierAmplifierOperStatus,
        ifAmplifierAmplifierMidStageLoss,
        ifAmplifierAmplifierTxIfIndex,
        ifAmplifierAmplifierRxIfIndex,
        ifAmplifierAmplifierSubrack,
        ifAmplifierAmplifierSlot,
        ifAmplifierAmplifierOutputPowerFail,
        ifAmplifierAmplifierSaturation,
        ifAmplifierAmplifierFunctionalType}
    STATUS      deprecated
    DESCRIPTION
        "The ifAmplifierAmplifier objects (30.0)."
    ::= { lumIfAmplifierGroups 10 }


ifAmplifierAmplifierGroupV4 OBJECT-GROUP
    OBJECTS {
        ifAmplifierAmplifierIndex,
        ifAmplifierAmplifierName,
        ifAmplifierAmplifierUId,
        ifAmplifierAmplifierRxPower,
        ifAmplifierAmplifierTxPower,
        ifAmplifierAmplifierWantedGain,
        ifAmplifierAmplifierActualGain,
        ifAmplifierAmplifierAdminStatus,
        ifAmplifierAmplifierOperStatus,
        ifAmplifierAmplifierMidStageLoss,
        ifAmplifierAmplifierTxIfIndex,
        ifAmplifierAmplifierRxIfIndex,
        ifAmplifierAmplifierSubrack,
        ifAmplifierAmplifierSlot,
        ifAmplifierAmplifierOutputPowerFail,
        ifAmplifierAmplifierSaturation,
        ifAmplifierAmplifierFunctionalType,
	ifAmplifierAmplifierDescr}
    STATUS      current
    DESCRIPTION
        "The ifAmplifierAmplifier objects (31.1)."
    ::= { lumIfAmplifierGroups 11 }


-- ----------------------------------------------------
-- Compliance
-- ----------------------------------------------------

lumIfAmplifierComplV1 MODULE-COMPLIANCE
    STATUS      deprecated
    DESCRIPTION
        "Basic implementation requirements for the ifAmplifier MIB."
    MODULE
        MANDATORY-GROUPS {
            ifAmplifierGeneralGroupV1,
            ifAmplifierAmplifierGroupV1,
            ifAmplifierModuleGroupV1,
            ifAmplifierRamanGroupV1,
            ifAmplifierEdfaGroupV1 }
    ::= { lumIfAmplifierCompl 1 }

lumIfAmplifierComplV2 MODULE-COMPLIANCE
    STATUS      deprecated
    DESCRIPTION
        "Basic implementation requirements for the ifAmplifier MIB (27.0)."
    MODULE
        MANDATORY-GROUPS {
            ifAmplifierGeneralGroupV1,
            ifAmplifierAmplifierGroupV2,
            ifAmplifierModuleGroupV1,
            ifAmplifierRamanGroupV1,
            ifAmplifierEdfaGroupV2 }
    ::= { lumIfAmplifierCompl 2 }

lumIfAmplifierComplV3 MODULE-COMPLIANCE
    STATUS      deprecated
    DESCRIPTION
        "Basic implementation requirements for the ifAmplifier MIB (30.0)."
    MODULE
        MANDATORY-GROUPS {
            ifAmplifierGeneralGroupV1,
            ifAmplifierAmplifierGroupV3,
            ifAmplifierModuleGroupV1,
            ifAmplifierRamanGroupV2,
            ifAmplifierEdfaGroupV3 }
    ::= { lumIfAmplifierCompl 3 }


lumIfAmplifierComplV4 MODULE-COMPLIANCE
    STATUS      current
    DESCRIPTION
        "Basic implementation requirements for the ifAmplifier MIB (31.1)."
    MODULE
        MANDATORY-GROUPS {
            ifAmplifierGeneralGroupV1,
            ifAmplifierAmplifierGroupV4,
            ifAmplifierModuleGroupV1,
            ifAmplifierRamanGroupV2,
            ifAmplifierEdfaGroupV3 }
    ::= { lumIfAmplifierCompl 4 }
END

LUM-IFIWDM-MIB DEFINITIONS ::= BEGIN

IMPORTS
    MODULE-IDENTITY, OBJECT-TYPE, Unsigned32
        FROM SNMPv2-SMI
    OBJECT-GROUP, MODULE-COMPLIANCE
        FROM SNMPv2-CONF
    DateAndTime
        FROM SNMPv2-TC
    lumModules, lumIfIwdmMIB
        FROM LUM-REG
    MgmtNameString, FaultStatusWithNA, EnabledDisabledWithNA, Unsigned32WithNA, SignalStatusWithNA, DisplayStringWithNA, SignalFormat
        FROM LUM-TC;

lumIfIwdmMIBModule MODULE-IDENTITY
    LAST-UPDATED
        "201706150000Z" -- June 15th 2017
    ORGANIZATION
        "Infinera Corporation"
    CONTACT-INFO
        "techsupport@infinera.com"
    DESCRIPTION
        "The MIB module the new iWDM mib. iWDM is a proprietary line
        format of Infinera. Similar to SDH it has two layers of overhead:
        iWDM regenerator section OH (iWDM-rs) and iWDM multiplex section
        OH (iWDM-ms). The management plane aspects of those two layers are
        specified in this MIB.

        The tables contained in this MIB are:

        (1) The General group contains some general attributes as time stamps
            and tables sizes.

        (2) The iWDM regenerator (iWDM-rs) group contains information and
            configuration for the regenerator section overhead.

        (3) The iWDM multiplexing (iWDM-ms) group contains information and
	    configuration for the multiplexing overhead.

"
    REVISION
        "201706150000Z" -- June 15th 2017
    DESCRIPTION
        "Changes made for release r29.0:
         - Changed ORGANIZATION and CONTACT-INFO"
    REVISION
        "201609300000Z" -- September 30th 2016
    DESCRIPTION
        "Changes made for release r27.1:
        - Added rfuac1 board."
    REVISION
        "201606140000Z" -- June 14th 2016
    DESCRIPTION
        "Added rxSignalStatus and txSignalStatus
         Added notAvialable and notApplicable to transmitted, received and
               expected trace identifier in IfIwdmRsEntry"
    REVISION
        "201512220000Z" -- December 22nd 2015
    DESCRIPTION
        "Changes made for release r27:
        - Added fhau1 board
        - Added fha1u1 board"
    REVISION
        "201501230000Z" -- January 23rd 2015
    DESCRIPTION
        "The initial revision of this module."
    ::= { lumModules 63 }


-- ----------------------------------------------------
-- Compliance area, containing groups and compliance
-- specifications.
-- ----------------------------------------------------

lumIfIwdmConfs OBJECT IDENTIFIER ::= { lumIfIwdmMIB 1 }
lumIfIwdmGroups OBJECT IDENTIFIER ::= { lumIfIwdmConfs 1 }
lumIfIwdmCompl OBJECT IDENTIFIER ::= { lumIfIwdmConfs 2 }


-- ----------------------------------------------------
-- Root for objects in the IFIWDM MIB
-- ----------------------------------------------------

lumIfIwdmMIBObjects OBJECT IDENTIFIER ::= { lumIfIwdmMIB 2 }


-- ----------------------------------------------------
-- This MIB contains the following groups:
-- ----------------------------------------------------

ifIwdmGeneral OBJECT IDENTIFIER ::= { lumIfIwdmMIBObjects 1 }
ifIwdmRsList OBJECT IDENTIFIER ::= { lumIfIwdmMIBObjects 2 }
ifIwdmMsList OBJECT IDENTIFIER ::= { lumIfIwdmMIBObjects 3 }
ifIwdmPathList OBJECT IDENTIFIER ::= { lumIfIwdmMIBObjects 4 }

-- ----------------------------------------------------
-- General group
-- ----------------------------------------------------

ifIwdmGeneralConfigLastChangeTime OBJECT-TYPE
    SYNTAX      DateAndTime
    MAX-ACCESS  read-only
    STATUS      current
    DESCRIPTION
        "The time when the configuration of the MIB was
        last changed.

"
    ::= { ifIwdmGeneral 1 }

ifIwdmGeneralStateLastChangeTime OBJECT-TYPE
    SYNTAX      DateAndTime
    MAX-ACCESS  read-only
    STATUS      current
    DESCRIPTION
        "The time when the state and/or configuration of the
	MIB was last changed.

"
    ::= { ifIwdmGeneral 2 }

ifIwdmGeneralIfIwdmRsTableSize OBJECT-TYPE
    SYNTAX      Unsigned32
    MAX-ACCESS  read-only
    STATUS      current
    DESCRIPTION
        "Size of rs table.

"
    ::= { ifIwdmGeneral 3 }

ifIwdmGeneralIfIwdmRsConfigLastChangeTime OBJECT-TYPE
    SYNTAX      DateAndTime
    MAX-ACCESS  read-only
    STATUS      current
    DESCRIPTION
        "The time when the configuration of the table was
        last changed.

"
    ::= { ifIwdmGeneral 4 }

ifIwdmGeneralIfIwdmRsStateLastChangeTime OBJECT-TYPE
   SYNTAX      DateAndTime
   MAX-ACCESS  read-only
   STATUS      current
   DESCRIPTION
       "The time when the state and/or configuration of the table was last
        changed.

"
   ::= { ifIwdmGeneral 5 }

ifIwdmGeneralIfIwdmMsTableSize OBJECT-TYPE
    SYNTAX      Unsigned32
    MAX-ACCESS  read-only
    STATUS      current
    DESCRIPTION
        "Size of ms table

"
    ::= { ifIwdmGeneral 6 }

ifIwdmGeneralIfIwdmMsConfigLastChangeTime OBJECT-TYPE
    SYNTAX      DateAndTime
    MAX-ACCESS  read-only
    STATUS      current
    DESCRIPTION
        "The time when the configuration of the table was
        last changed.

"
    ::= { ifIwdmGeneral 7 }

ifIwdmGeneralIfIwdmMsStateLastChangeTime OBJECT-TYPE
   SYNTAX      DateAndTime
   MAX-ACCESS  read-only
   STATUS      current
   DESCRIPTION
       "The time when the state and/or configuration of the
       table was last changed.

"
   ::= { ifIwdmGeneral 8 }

ifIwdmGeneralIfIwdmPathTableSize OBJECT-TYPE
    SYNTAX      Unsigned32
    MAX-ACCESS  read-only
    STATUS      current
    DESCRIPTION
        "Size of path table.

"
    ::= { ifIwdmGeneral 9 }

ifIwdmGeneralIfIwdmPathConfigLastChangeTime OBJECT-TYPE
    SYNTAX      DateAndTime
    MAX-ACCESS  read-only
    STATUS      current
    DESCRIPTION
        "The time when the configuration of the table was
        last changed.

"
    ::= { ifIwdmGeneral 10 }

ifIwdmGeneralIfIwdmPathStateLastChangeTime OBJECT-TYPE
   SYNTAX      DateAndTime
   MAX-ACCESS  read-only
   STATUS      current
   DESCRIPTION
       "The time when the state and/or configuration of the table was last
        changed.

"
   ::= { ifIwdmGeneral 11 }

-- ----------------------------------------------------
-- IWDM RS group
-- ----------------------------------------------------

ifIwdmRsTable  OBJECT-TYPE
    SYNTAX      SEQUENCE OF IfIwdmRsEntry
    MAX-ACCESS  not-accessible
    STATUS      current
    DESCRIPTION
        "The regenerator (iWDM-rs) group contains information and
         configuration for the iWDM regenerator section (iWDM-rs)."

    ::= { ifIwdmRsList 1 }

ifIwdmRsEntry OBJECT-TYPE
    SYNTAX      IfIwdmRsEntry
    MAX-ACCESS  not-accessible
    STATUS      current
    DESCRIPTION
        "An entry in the ifIwdm rs list.

"
    INDEX { ifIwdmRsIndex }
    ::= { ifIwdmRsTable 1 }

IfIwdmRsEntry ::=
    SEQUENCE {
        ifIwdmRsIndex                       Unsigned32,
        ifIwdmRsName                        MgmtNameString,
        ifIwdmRsTraceTransmitted            DisplayStringWithNA,
        ifIwdmRsTraceReceived               DisplayStringWithNA,
        ifIwdmRsTraceExpected               DisplayStringWithNA,
        ifIwdmRsTraceAlarmMode              EnabledDisabledWithNA,
        ifIwdmRsTraceTraceMismatch          FaultStatusWithNA,
        ifIwdmRsUpId                        Unsigned32,
        ifIwdmRsLossOfFrame                 FaultStatusWithNA,
        ifIwdmRsConnIfBasicIfIndex          Unsigned32WithNA,
        ifIwdmRsTxSignalStatus              SignalStatusWithNA,
        ifIwdmRsRxSignalStatus              SignalStatusWithNA,
        ifIwdmRsRate                        SignalFormat}

ifIwdmRsIndex OBJECT-TYPE
    SYNTAX      Unsigned32
    MAX-ACCESS  read-only
    STATUS      current
    DESCRIPTION
        "An index assigned to each entry.

"
    ::= { ifIwdmRsEntry 1 }

ifIwdmRsName OBJECT-TYPE
    SYNTAX      MgmtNameString
    MAX-ACCESS  read-only
    STATUS      current
    DESCRIPTION
        "The management name of the iWDM Rs,
        for example 'rs:1:2:1-2', where the first number indicates
        subrack, the second slot number and the third/fourth
        are the physical port numbers.

"
    ::= { ifIwdmRsEntry 2 }

ifIwdmRsTraceTransmitted   OBJECT-TYPE
    SYNTAX      DisplayStringWithNA (SIZE(0..63))
    MAX-ACCESS  read-write
    STATUS      current
    DESCRIPTION
        "The operator specific trace identifier to be transmitted
        from this interface.

        The trace identifier length is by default 0 to 63.
        For tpmrHL16G board only the length is 0 to 15.

        Set to empty string for default value.
        <IP address>:<subrack>:<slot>:<port>
        Note that only the last part of the IP address is used.

        The trace n/a is used to tell SNMP clients that
        this attribute is not used in current configuration.

"
    ::= { ifIwdmRsEntry 3 }

ifIwdmRsTraceReceived OBJECT-TYPE
    SYNTAX      DisplayStringWithNA (SIZE(0..63))
    MAX-ACCESS  read-only
    STATUS      current
    DESCRIPTION
        "The received operator specific trace identifier for this
         interface.

         The trace _notApplicable_ is used to tell SNMP clients that
         this attribute is not used in current configuration.

         The trace _notAvailable_ is used to tell SNMP clients that
         this attribute is not possible to read at the moment.

"
    ::= { ifIwdmRsEntry 4 }

ifIwdmRsTraceExpected OBJECT-TYPE
    SYNTAX          DisplayStringWithNA (SIZE(0..63))
    MAX-ACCESS      read-write
    STATUS          current
    DESCRIPTION
        "Trace identifier used for matching against
        the received trace identifier.

        The trace identifier length is by default 0 to 63.
        For tpmrHL16G board only the length is 0 to 15.

        The trace n/a is used to tell SNMP clients that
        this attribute is not used in current configuration.

"
    DEFVAL { "" }
    ::= { ifIwdmRsEntry 5 }

ifIwdmRsTraceAlarmMode OBJECT-TYPE
    SYNTAX      EnabledDisabledWithNA
    MAX-ACCESS  read-only
    STATUS      current
    DESCRIPTION
        "Controls if the trace identifier mismatch alarm
        should be raised.

        disabled - The alarm is disabled.

        enabled - The alarm is raised if expected trace identifier
        differs from the received trace identifier.

"
    DEFVAL { disabled }
    ::= { ifIwdmRsEntry 6 }

ifIwdmRsTraceTraceMismatch OBJECT-TYPE
    SYNTAX      FaultStatusWithNA
    MAX-ACCESS  read-only
    STATUS      current
    DESCRIPTION
        "Trace identifier mismatch.

        Indicates if the expected trace identifier
        differs from the received trace identifier.

        Alarm: The received trace identifier differs from
        the expected trace identifier.

        OK: The identifiers match.

"
    ::= { ifIwdmRsEntry 7 }

ifIwdmRsUpId OBJECT-TYPE
    SYNTAX      Unsigned32   (0..2147483647)
    MAX-ACCESS  read-only
    STATUS      current
    DESCRIPTION
        "Identity in the UP for the iwdmRs entry in the traffic unit
"
    DEFVAL { 0  }
    ::= { ifIwdmRsEntry 8 }



ifIwdmRsLossOfFrame OBJECT-TYPE
    SYNTAX      FaultStatusWithNA
    MAX-ACCESS  read-only
    STATUS      current
    DESCRIPTION
        "Loss of frame (LOF).


        Alarm: An iWDM frame cannot be located.

        OK: An iWDM frame can be located.

"
    ::= { ifIwdmRsEntry 9 }

ifIwdmRsConnIfBasicIfIndex OBJECT-TYPE
    SYNTAX      Unsigned32WithNA
    MAX-ACCESS  read-only
    STATUS      current
    DESCRIPTION
        "An index describing to which index in ifBasicIf table
        this object is related to.

"
    ::= { ifIwdmRsEntry 10 }

ifIwdmRsTxSignalStatus OBJECT-TYPE
        SYNTAX      SignalStatusWithNA
        MAX-ACCESS  read-only
        STATUS      current
        DESCRIPTION
            "The state for outgoing (Tx) signal
            of the interface.

            down - A major fault has occurred.

            degraded - The signal quality is impaired.

            up - The signal is OK.

"
        ::= { ifIwdmRsEntry 11 }

ifIwdmRsRxSignalStatus OBJECT-TYPE
        SYNTAX      SignalStatusWithNA
        MAX-ACCESS  read-only
        STATUS      current
        DESCRIPTION
            "The state for incoming (Rx) signal
            of the interface.

            down - A major fault has occurred.

            degraded - The signal quality is impaired.

            up - The signal is OK.

"
        ::= { ifIwdmRsEntry 12 }

ifIwdmRsRate OBJECT-TYPE
        SYNTAX      SignalFormat
        MAX-ACCESS  read-only
        STATUS      current
        DESCRIPTION
            "Rate

"
        DEFVAL { iwdm11G }
        ::= { ifIwdmRsEntry 13 }

-- ----------------------------------------------------
-- IWDM MS group
-- ----------------------------------------------------

ifIwdmMsTable  OBJECT-TYPE
    SYNTAX      SEQUENCE OF IfIwdmMsEntry
    MAX-ACCESS  not-accessible
    STATUS      current
    DESCRIPTION
        "The multiplexing (iWDM-ms) group contains information and
	 configuration for the iWDM multiplexing section (iWDM-ms)."

    ::= { ifIwdmMsList 1 }

ifIwdmMsEntry OBJECT-TYPE
    SYNTAX      IfIwdmMsEntry
    MAX-ACCESS  not-accessible
    STATUS      current
    DESCRIPTION
        "An entry in the ifIwdm ms list.

"
    INDEX { ifIwdmMsIndex }
    ::= { ifIwdmMsTable 1 }

IfIwdmMsEntry ::=
    SEQUENCE {
        ifIwdmMsIndex                       Unsigned32,
        ifIwdmMsName                        MgmtNameString,
        ifIwdmMsAlarmIndicationSignal       FaultStatusWithNA,
        ifIwdmMsBackwardDefectIndication    FaultStatusWithNA,
        ifIwdmMsUpId                        Unsigned32,
        ifIwdmMsConnIfBasicIfIndex          Unsigned32WithNA,
        ifIwdmMsTxSignalStatus              SignalStatusWithNA,
        ifIwdmMsRxSignalStatus              SignalStatusWithNA,
        ifIwdmMsRate                        SignalFormat}

ifIwdmMsIndex OBJECT-TYPE
    SYNTAX      Unsigned32
    MAX-ACCESS  read-only
    STATUS      current
    DESCRIPTION
        "An index assigned to each entry.

"
    ::= { ifIwdmMsEntry 1 }

ifIwdmMsName OBJECT-TYPE
    SYNTAX      MgmtNameString
    MAX-ACCESS  read-only
    STATUS      current
    DESCRIPTION
        "The management name of the iWDM Ms,
        for example 'ms:1:2:1-2', where the first number indicates
        subrack, the second slot number and the third/fourth
        are the physical port numbers.

"
    ::= { ifIwdmMsEntry 2 }

ifIwdmMsAlarmIndicationSignal OBJECT-TYPE
    SYNTAX      FaultStatusWithNA
    MAX-ACCESS  read-only
    STATUS      current
    DESCRIPTION
        "Alarm indication signal (AIS).

        Alarm: An 'all ones' pattern is detected.

        OK: The signal recovered.

"
    ::= { ifIwdmMsEntry 3 }

ifIwdmMsBackwardDefectIndication OBJECT-TYPE
    SYNTAX      FaultStatusWithNA
    MAX-ACCESS  read-only
    STATUS      current
    DESCRIPTION
        "Backward defect indication (BDI).

        Indicates if backward defect indication (BDI) alarm
        exists or not.

        Alarm: Backward defect indication (in wrapper) active.

        OK: Backward defect indication (in wrapper) inactive.

"
    ::= { ifIwdmMsEntry 4 }

ifIwdmMsUpId OBJECT-TYPE
    SYNTAX      Unsigned32   (0..2147483647)
    MAX-ACCESS  read-only
    STATUS      current
    DESCRIPTION
        "Identity in the UP for the iwdmMs entry in the traffic unit
"
    DEFVAL { 0  }
    ::= { ifIwdmMsEntry 5 }

ifIwdmMsConnIfBasicIfIndex OBJECT-TYPE
    SYNTAX      Unsigned32WithNA
    MAX-ACCESS  read-only
    STATUS      current
    DESCRIPTION
        "An index describing to which index in ifBasicIf table
        this object is related to.

"
    ::= { ifIwdmMsEntry 6 }

ifIwdmMsTxSignalStatus OBJECT-TYPE
        SYNTAX      SignalStatusWithNA
        MAX-ACCESS  read-only
        STATUS      current
        DESCRIPTION
            "The state for outgoing (Tx) signal
            of the interface.

            down - A major fault has occurred.

            degraded - The signal quality is impaired.

            up - The signal is OK.

"
        ::= { ifIwdmMsEntry 7 }

ifIwdmMsRxSignalStatus OBJECT-TYPE
        SYNTAX      SignalStatusWithNA
        MAX-ACCESS  read-only
        STATUS      current
        DESCRIPTION
            "The state for incoming (Rx) signal
            of the interface.

            down - A major fault has occurred.

            degraded - The signal quality is impaired.

            up - The signal is OK.

"
        ::= { ifIwdmMsEntry 8 }

ifIwdmMsRate OBJECT-TYPE
        SYNTAX      SignalFormat
        MAX-ACCESS  read-only
        STATUS      current
        DESCRIPTION
            "Rate

"
        DEFVAL { iwdm11G }
        ::= { ifIwdmMsEntry 9 }

-- ----------------------------------------------------
-- IWDM Path group
-- ----------------------------------------------------

ifIwdmPathTable  OBJECT-TYPE
    SYNTAX      SEQUENCE OF IfIwdmPathEntry
    MAX-ACCESS  not-accessible
    STATUS      current
    DESCRIPTION
        "The path (iWDM-path) group contains information and
         configuration for the iWDM path section (iWDM-path)."

    ::= { ifIwdmPathList 1 }

ifIwdmPathEntry OBJECT-TYPE
    SYNTAX      IfIwdmPathEntry
    MAX-ACCESS  not-accessible
    STATUS      current
    DESCRIPTION
        "An entry in the ifIwdm path list.

"
    INDEX { ifIwdmPathIndex }
    ::= { ifIwdmPathTable 1 }

IfIwdmPathEntry ::=
    SEQUENCE {
        ifIwdmPathIndex                       Unsigned32,
        ifIwdmPathName                        MgmtNameString,
        ifIwdmPathBackwardDefectIndication    FaultStatusWithNA,
        ifIwdmPathClientSignalFailure         FaultStatusWithNA,
        ifIwdmPathUId                         Unsigned32,
        ifIwdmPathConnIfBasicIfIndex          Unsigned32WithNA,
        ifIwdmPathTxSignalStatus              SignalStatusWithNA,
        ifIwdmPathRxSignalStatus              SignalStatusWithNA,
        ifIwdmPathRate                        SignalFormat}

ifIwdmPathIndex OBJECT-TYPE
    SYNTAX      Unsigned32
    MAX-ACCESS  read-only
    STATUS      current
    DESCRIPTION
        "An index assigned to each entry.

"
    ::= { ifIwdmPathEntry 1 }

ifIwdmPathName OBJECT-TYPE
    SYNTAX      MgmtNameString
    MAX-ACCESS  read-only
    STATUS      current
    DESCRIPTION
        "The management name of the iWDM path,
        for example 'path:1:2:1-2', where the first number indicates
        subrack, the second slot number and the third/fourth
        are the physical port numbers.

"
    ::= { ifIwdmPathEntry 2 }

ifIwdmPathBackwardDefectIndication OBJECT-TYPE
    SYNTAX      FaultStatusWithNA
    MAX-ACCESS  read-only
    STATUS      current
    DESCRIPTION
        "Backward defect indication (BDI).

        Indicates if backward defect indication (BDI) alarm
        exists or not.

        Alarm: Backward defect indication (in wrapper) active.

        OK: Backward defect indication (in wrapper) inactive.

"
    ::= { ifIwdmPathEntry 3 }

ifIwdmPathClientSignalFailure OBJECT-TYPE
    SYNTAX      FaultStatusWithNA
    MAX-ACCESS  read-only
    STATUS      current
    DESCRIPTION
        "Client signal failure.

"
    ::= { ifIwdmPathEntry 4 }

ifIwdmPathUId OBJECT-TYPE
    SYNTAX      Unsigned32   (0..2147483647)
    MAX-ACCESS  read-only
    STATUS      current
    DESCRIPTION
        "Unique identity for the iwdmPath entry in the traffic unit
"
    DEFVAL { 0  }
    ::= { ifIwdmPathEntry 5 }

ifIwdmPathConnIfBasicIfIndex OBJECT-TYPE
    SYNTAX      Unsigned32WithNA
    MAX-ACCESS  read-only
    STATUS      current
    DESCRIPTION
        "An index describing to which index in ifBasicIf table
        this object is related to.

"
    ::= { ifIwdmPathEntry 6 }

ifIwdmPathTxSignalStatus OBJECT-TYPE
    SYNTAX      SignalStatusWithNA
    MAX-ACCESS  read-only
    STATUS      current
    DESCRIPTION
        "The state for outgoing (Tx) signal
        of the interface.

        down - A major fault has occurred.

        degraded - The signal quality is impaired.

        up - The signal is OK.

"
    ::= { ifIwdmPathEntry 7 }

ifIwdmPathRxSignalStatus OBJECT-TYPE
        SYNTAX      SignalStatusWithNA
        MAX-ACCESS  read-only
        STATUS      current
        DESCRIPTION
            "The state for incoming (Rx) signal
            of the interface.

            down - A major fault has occurred.

            degraded - The signal quality is impaired.

            up - The signal is OK.

"
        ::= { ifIwdmPathEntry 8 }

ifIwdmPathRate OBJECT-TYPE
        SYNTAX      SignalFormat
        MAX-ACCESS  read-only
        STATUS      current
        DESCRIPTION
            "Rate

"
        DEFVAL { notApplicable }
        ::= { ifIwdmPathEntry 9 }

-- ----------------------------------------------------
-- Notifications
-- ----------------------------------------------------


-- ----------------------------------------------------
-- Object and event groups
-- ----------------------------------------------------

ifIwdmGeneralGroupV1 OBJECT-GROUP
    OBJECTS {
        ifIwdmGeneralConfigLastChangeTime,
        ifIwdmGeneralStateLastChangeTime,
        ifIwdmGeneralIfIwdmRsTableSize,
        ifIwdmGeneralIfIwdmRsConfigLastChangeTime,
        ifIwdmGeneralIfIwdmRsStateLastChangeTime,
        ifIwdmGeneralIfIwdmMsTableSize,
        ifIwdmGeneralIfIwdmMsConfigLastChangeTime,
        ifIwdmGeneralIfIwdmMsStateLastChangeTime }

    STATUS      deprecated
    DESCRIPTION
        "The general objects."
    ::= { lumIfIwdmGroups 1 }

ifIwdmGeneralGroupV2 OBJECT-GROUP
    OBJECTS {
        ifIwdmGeneralConfigLastChangeTime,
        ifIwdmGeneralStateLastChangeTime,
        ifIwdmGeneralIfIwdmRsTableSize,
        ifIwdmGeneralIfIwdmRsConfigLastChangeTime,
        ifIwdmGeneralIfIwdmRsStateLastChangeTime,
        ifIwdmGeneralIfIwdmMsTableSize,
        ifIwdmGeneralIfIwdmMsConfigLastChangeTime,
        ifIwdmGeneralIfIwdmMsStateLastChangeTime,
        ifIwdmGeneralIfIwdmPathTableSize,
        ifIwdmGeneralIfIwdmPathConfigLastChangeTime,
        ifIwdmGeneralIfIwdmPathStateLastChangeTime }

    STATUS      current
    DESCRIPTION
        "The general objects."
    ::= { lumIfIwdmGroups 2 }

ifIwdmRsGroupV1 OBJECT-GROUP
    OBJECTS {
        ifIwdmRsIndex,
        ifIwdmRsName,
        ifIwdmRsTraceTransmitted,
        ifIwdmRsTraceReceived,
        ifIwdmRsTraceExpected,
        ifIwdmRsTraceAlarmMode,
        ifIwdmRsTraceTraceMismatch,
        ifIwdmRsUpId,
        ifIwdmRsLossOfFrame,
	ifIwdmRsConnIfBasicIfIndex }

    STATUS      deprecated
    DESCRIPTION
        "The ifIwdm RS objects (R26.0)."
    ::= { lumIfIwdmGroups 3 }


ifIwdmMsGroupV1 OBJECT-GROUP
    OBJECTS {
        ifIwdmMsIndex,
        ifIwdmMsName,
        ifIwdmMsAlarmIndicationSignal,
        ifIwdmMsBackwardDefectIndication,
        ifIwdmMsUpId,
        ifIwdmMsConnIfBasicIfIndex }

    STATUS      deprecated
    DESCRIPTION
        "The ifIwdm MS objects (R26.0)."
    ::= { lumIfIwdmGroups 4 }


ifIwdmRsGroupV2 OBJECT-GROUP
    OBJECTS {
        ifIwdmRsIndex,
        ifIwdmRsName,
        ifIwdmRsTraceTransmitted,
        ifIwdmRsTraceReceived,
        ifIwdmRsTraceExpected,
        ifIwdmRsTraceAlarmMode,
        ifIwdmRsTraceTraceMismatch,
        ifIwdmRsUpId,
        ifIwdmRsLossOfFrame,
        ifIwdmRsConnIfBasicIfIndex,
        ifIwdmRsTxSignalStatus,
        ifIwdmRsRxSignalStatus }

    STATUS      deprecated
    DESCRIPTION
        "The ifIwdm RS objects (R27.0)."
    ::= { lumIfIwdmGroups 5 }


ifIwdmMsGroupV2 OBJECT-GROUP
    OBJECTS {
        ifIwdmMsIndex,
        ifIwdmMsName,
        ifIwdmMsAlarmIndicationSignal,
        ifIwdmMsBackwardDefectIndication,
        ifIwdmMsUpId,
        ifIwdmMsConnIfBasicIfIndex,
        ifIwdmMsTxSignalStatus,
        ifIwdmMsRxSignalStatus }

    STATUS      deprecated
    DESCRIPTION
        "The ifIwdm MS objects (R27.0)."
    ::= { lumIfIwdmGroups 6 }

ifIwdmRsGroupV3 OBJECT-GROUP
    OBJECTS {
        ifIwdmRsIndex,
        ifIwdmRsName,
        ifIwdmRsTraceTransmitted,
        ifIwdmRsTraceReceived,
        ifIwdmRsTraceExpected,
        ifIwdmRsTraceAlarmMode,
        ifIwdmRsTraceTraceMismatch,
        ifIwdmRsUpId,
        ifIwdmRsLossOfFrame,
        ifIwdmRsConnIfBasicIfIndex,
        ifIwdmRsTxSignalStatus,
        ifIwdmRsRxSignalStatus,
        ifIwdmRsRate }

    STATUS      current
    DESCRIPTION
        "The ifIwdm RS objects (R27.1)."
    ::= { lumIfIwdmGroups 7 }


ifIwdmMsGroupV3 OBJECT-GROUP
    OBJECTS {
        ifIwdmMsIndex,
        ifIwdmMsName,
        ifIwdmMsAlarmIndicationSignal,
        ifIwdmMsBackwardDefectIndication,
        ifIwdmMsUpId,
        ifIwdmMsConnIfBasicIfIndex,
        ifIwdmMsTxSignalStatus,
        ifIwdmMsRxSignalStatus,
        ifIwdmMsRate }

    STATUS      current
    DESCRIPTION
        "The ifIwdm MS objects (R27.1)."
    ::= { lumIfIwdmGroups 8 }

ifIwdmPathGroupV1 OBJECT-GROUP
    OBJECTS {
        ifIwdmPathIndex,
        ifIwdmPathName,
        ifIwdmPathUId,
        ifIwdmPathBackwardDefectIndication,
        ifIwdmPathClientSignalFailure,
        ifIwdmPathConnIfBasicIfIndex,
        ifIwdmPathTxSignalStatus,
        ifIwdmPathRxSignalStatus,
        ifIwdmPathRate }

    STATUS      current
    DESCRIPTION
        "The path objects."
    ::= { lumIfIwdmGroups 9 }

-- ----------------------------------------------------
-- Compliance
-- ----------------------------------------------------

lumIfIwdmComplV1 MODULE-COMPLIANCE
    STATUS      deprecated
    DESCRIPTION
        "Basic implementation requirements for the ifIwdm MIB. (R26.0)"
    MODULE
        MANDATORY-GROUPS {
            ifIwdmGeneralGroupV1,
            ifIwdmRsGroupV1,
            ifIwdmMsGroupV1 }
    ::= { lumIfIwdmCompl 1 }

    lumIfIwdmComplV2 MODULE-COMPLIANCE
        STATUS      deprecated
        DESCRIPTION
            "Basic implementation requirements for the ifIwdm MIB. (R27.0)"
        MODULE
            MANDATORY-GROUPS {
                ifIwdmGeneralGroupV1,
                ifIwdmRsGroupV2,
                ifIwdmMsGroupV2 }
        ::= { lumIfIwdmCompl 2 }

    lumIfIwdmComplV3 MODULE-COMPLIANCE
        STATUS      current
        DESCRIPTION
            "Basic implementation requirements for the ifIwdm MIB. (R27.1)"
        MODULE
            MANDATORY-GROUPS {
                ifIwdmGeneralGroupV2,
                ifIwdmRsGroupV3,
                ifIwdmMsGroupV3,
                ifIwdmPathGroupV1 }
        ::= { lumIfIwdmCompl 3 }

END

LUM-LLDP-V2-MIB DEFINITIONS ::= BEGIN

IMPORTS

    MODULE-IDENTITY, OBJECT-TYPE, Unsigned32, Counter32,Integer32
        FROM SNMPv2-SMI
    OBJECT-GROUP, MODULE-COMPLIANCE
        FROM SNMPv2-CONF
    DisplayString,TruthValue,DateAndTime,TEXTUAL-CONVENTION
        FROM SNMPv2-TC
    IpAddress
        FROM SNMPv2-SMI
    MgmtNameString, SubrackNumber, SlotNumber,PortNumber,TruthValueWithNA
        FROM LUM-TC
    SnmpAdminString
        FROM SNMP-FRAMEWORK-MIB
    lumModules, lumLldpV2MIB
        FROM LUM-REG;

lumLldpV2MIBModule MODULE-IDENTITY
    LAST-UPDATED
        "201712150000Z" -- Dec 15th 2017
    ORGANIZATION
        "Infinera Metro, formerly Transmode Systems AB"
    CONTACT-INFO
        "techsupport@infinera.com"
    DESCRIPTION
        "The MIB module for LLDP-V2.
        it is a customized version of the standard LLDP-V2-MIB.

        The tables contained in this MIB are:

        (1) The General group contains some general attributes as time stamps
            and tables sizes.

        (2) The lldpV2 Remote Systems table
        (3) The lldpV2 Local Agent Config table
        (4) The lldpV2 System Info table
        (5) The lldpV2 Statistics table

"

    REVISION
    "201712150000Z" -- Dec 15th 2017
    DESCRIPTION
    "Changes for r30.0:
    - Changed agentId in lldpStats table to read-only.
    - Changed display order of attributes in lldpAgentConfig, lldpV2RemoteSystemData and lldpStats tables."

    REVISION
        "201706150000Z" -- June 15th 2017
    DESCRIPTION
        "Changes made for release r29.0:
         - Changed ORGANIZATION and CONTACT-INFO"
    REVISION
        "201604300000Z" -- April 30th 2016
    DESCRIPTION
        "The initial revision of this module."
    ::= { lumModules 67 }

-- ----------------------------------------------------
-- Compliance area, containing groups and compliance
-- specifications.
-- ----------------------------------------------------

lumLldpV2Confs OBJECT IDENTIFIER ::= { lumLldpV2MIB 1 }

--------------------------------------------------------
--LLDP V2 MIB Module - Conformance Information
--------------------------------------------------------
lumLldpV2Groups       OBJECT IDENTIFIER ::= { lumLldpV2Confs 1 }
lumLldpV2Compliances  OBJECT IDENTIFIER ::= { lumLldpV2Confs 2 }


-- ----------------------------------------------------
-- Root for objects in the LLDPV2 MIB
-- ----------------------------------------------------

lumLldpV2MIBObjects OBJECT IDENTIFIER ::= { lumLldpV2MIB 2 }


-- ----------------------------------------------------
-- This MIB contains the following groups:
-- ----------------------------------------------------

lldpGeneral                      OBJECT IDENTIFIER ::= { lumLldpV2MIBObjects 1 }
lldpV2SystemInfo                   OBJECT IDENTIFIER ::= { lumLldpV2MIBObjects 2 }
lldpV2AgentConfig                  OBJECT IDENTIFIER ::= { lumLldpV2MIBObjects 3 }
lldpV2RemoteSystemData             OBJECT IDENTIFIER ::= { lumLldpV2MIBObjects 4 }
lldpV2Statistics                   OBJECT IDENTIFIER ::= { lumLldpV2MIBObjects 5 }


--
-- ***********************************************************
--
-- Textual Conventions
--
-- ***********************************************************

  LumAddressFamilyNumbers ::= TEXTUAL-CONVENTION
      STATUS       current
      DESCRIPTION
          "The definition of this textual convention with the
          addition of newly assigned values is published
          periodically by the IANA, in either the Assigned
          Numbers RFC, or some derivative of it specific to
          Internet Network Management number assignments.
          (The latest arrangements can be obtained by
          contacting the IANA.)

          The enumerations are described as:

          other(0),    -- none of the following
          ipV4(1),     -- IP Version 4
          ipV6(2),     -- IP Version 6
          nsap(3),     -- NSAP
          hdlc(4),     -- (8-bit multidrop)
          bbn1822(5),
          all802(6),   -- (includes all 802 media
                       --   plus Ethernet 'canonical format')
          e163(7),
          e164(8),     -- (SMDS, Frame Relay, ATM)
          f69(9),      -- (Telex)
          x121(10),    -- (X.25, Frame Relay)
          ipx(11),     -- IPX (Internet Protocol Exchange)
          appleTalk(12),  -- Apple Talk
          decnetIV(13),   -- DEC Net Phase IV
          banyanVines(14),  -- Banyan Vines
          e164withNsap(15),
                       -- (E.164 with NSAP format subaddress)
          dns(16),     -- (Domain Name System)
          distinguishedName(17), -- (Distinguished Name, per X.500)
          asNumber(18), -- (16-bit quantity, per the AS number space)
          xtpOverIpv4(19),  -- XTP over IP version 4
          xtpOverIpv6(20),  -- XTP over IP version 6
          xtpNativeModeXTP(21),  -- XTP native mode XTP
          fibreChannelWWPN(22),  -- Fibre Channel World-Wide Port Name
          fibreChannelWWNN(23),  -- Fibre Channel World-Wide Node Name
          gwid(24),    -- Gateway Identifier
          reserved(65535)

          Requests for new values should be made to IANA via
          email (iana@iana.org)."
      SYNTAX  INTEGER {
                  other(0),
                  ipV4(1),
                  ipV6(2),
                  nsap(3),
                  hdlc(4),
                  bbn1822(5),
                  all802(6),
                  e163(7),
                  e164(8),
                  f69(9),
                  x121(10),
                  ipx(11),
                  appleTalk(12),
                  decnetIV(13),
                  banyanVines(14),
                  e164withNsap(15),
                  dns(16),
                  distinguishedName(17), -- (Distinguished Name, per X.500)
                  asNumber(18), -- (16-bit quantity, per the AS number space)
                  xtpOverIpv4(19),
                  xtpOverIpv6(20),
                  xtpNativeModeXTP(21),
                  fibreChannelWWPN(22),
                  fibreChannelWWNN(23),
                  gwid(24),
                  reserved(65535),
                  notAvailable(2147483646),
                  notApplicable(2147483647)
              }

LldpV2ChassisIdSubtype ::= TEXTUAL-CONVENTION
    STATUS      current
    DESCRIPTION
            "This TC describes the source of a chassis identifier.

            The enumeration 'chassisComponent(1)' represents a chassis
            identifier based on the value of entPhysicalAlias object
            (defined in IETF RFC 4133) for a chassis component (i.e.,
            an entPhysicalClass value of 'chassis(3)').

            The enumeration 'interfaceAlias(2)' represents a chassis
            identifier based on the value of ifAlias object (defined in
            IETF RFC 2863) for an interface on the containing chassis.

            The enumeration 'portComponent(3)' represents a chassis
            identifier based on the value of entPhysicalAlias object
            (defined in IETF RFC 4133) for a port or backplane
            component (i.e., entPhysicalClass value of 'port(10)' or
            'backplane(4)'), within the containing chassis.

            The enumeration 'macAddress(4)' represents a chassis
            identifier based on the value of a unicast source address
            (encoded in network byte order and IEEE 802.3 canonical bit
            order), of a port on the containing chassis as defined in
            IEEE Std 802.

            The enumeration 'networkAddress(5)' represents a chassis
            identifier based on a network address, associated with
            a particular chassis. The encoded address is actually
            composed of two fields. The first field is a single octet,
            representing the IANA AddressFamilyNumbers value for the
            specific address type, and the second field is the network
            address value.

            The enumeration 'interfaceName(6)' represents a chassis
            identifier based on the value of ifName object (defined in
            IETF RFC 2863) for an interface on the containing chassis.

            The enumeration 'local(7)' represents a chassis identifier
            based on a locally defined value."
    SYNTAX  INTEGER {
            chassisComponent(1),
            interfaceAlias(2),
            portComponent(3),
            macAddress(4),
            networkAddress(5),
            interfaceName(6),
            local(7),
            notAvailable (2147483646)
    }

LldpV2ChassisId ::= TEXTUAL-CONVENTION
    DISPLAY-HINT "1x:"
    STATUS      current
    DESCRIPTION
            "This TC describes the format of a chassis identifier string.
            Objects of this type are always used with an associated
            LldpChassisIdSubtype object, which identifies the format of
            the particular LldpChassisId object instance.

            If the associated LldpChassisIdSubtype object has a value of
            'chassisComponent(1)', then the octet string identifies
            a particular instance of the entPhysicalAlias object
            (defined in IETF RFC 4133) for a chassis component (i.e.,
            an entPhysicalClass value of 'chassis(3)').

            If the associated LldpChassisIdSubtype object has a value
            of 'interfaceAlias(2)', then the octet string identifies
            a particular instance of the ifAlias object (defined in
            IETF RFC 2863) for an interface on the containing chassis.
            If the particular ifAlias object does not contain any values,
            another chassis identifier type should be used.

            If the associated LldpChassisIdSubtype object has a value
            of 'portComponent(3)', then the octet string identifies a
            particular instance of the entPhysicalAlias object (defined
            in IETF RFC 4133) for a port or backplane component within
            the containing chassis.

            If the associated LldpChassisIdSubtype object has a value of
            'macAddress(4)', then this string identifies a particular
            unicast source address (encoded in network byte order and
            IEEE 802.3 canonical bit order), of a port on the containing
            chassis as defined in IEEE Std 802.

            If the associated LldpChassisIdSubtype object has a value of
            'networkAddress(5)', then this string identifies a particular
            network address, encoded in network byte order, associated
            with one or more ports on the containing chassis. The first
            octet contains the IANA Address Family Numbers enumeration
            value for the specific address type, and octets 2 through
            N contain the network address value in network byte order.

            If the associated LldpChassisIdSubtype object has a value
            of 'interfaceName(6)', then the octet string identifies
            a particular instance of the ifName object (defined in
            IETF RFC 2863) for an interface on the containing chassis.
            If the particular ifName object does not contain any values,
            another chassis identifier type should be used.

            If the associated LldpChassisIdSubtype object has a value of
            'local(7)', then this string identifies a locally assigned
            Chassis ID."
    SYNTAX      OCTET STRING (SIZE (1..255))

LldpV2PortIdSubtype ::= TEXTUAL-CONVENTION
    STATUS      current
    DESCRIPTION
            "This TC describes the source of a particular type of port
            identifier used in the LLDP MIB.

            The enumeration 'interfaceAlias(1)' represents a port
            identifier based on the ifAlias MIB object, defined in IETF
            RFC 2863.

            The enumeration 'portComponent(2)' represents a port
            identifier based on the value of entPhysicalAlias (defined in
            IETF RFC 4133) for a port component (i.e., entPhysicalClass
            value of 'port(10)'), within the containing chassis.

            The enumeration 'macAddress(3)' represents a port identifier
            based on a unicast source address (encoded in network
            byte order and IEEE 802.3 canonical bit order), which has
            been detected by the agent and associated with a particular
            port (IEEE Std 802).

            The enumeration 'networkAddress(4)' represents a port
            identifier based on a network address, detected by the agent
            and associated with a particular port.

            The enumeration 'interfaceName(5)' represents a port
            identifier based on the ifName MIB object, defined in IETF
            RFC 2863.

            The enumeration 'agentCircuitId(6)' represents a port
            identifier based on the agent-local identifier of the circuit
            (defined in RFC 3046), detected by the agent and associated
            with a particular port.

            The enumeration 'local(7)' represents a port identifier
            based on a value locally assigned."

    SYNTAX  INTEGER {
            interfaceAlias(1),
            portComponent(2),
            macAddress(3),
            networkAddress(4),
            interfaceName(5),
            agentCircuitId(6),
            local(7),
            notAvailable (2147483646)
    }

LldpV2PortId ::= TEXTUAL-CONVENTION
    DISPLAY-HINT "1x:"
    STATUS      current
    DESCRIPTION
            "This TC describes the format of a port identifier string.
            Objects of this type are always used with an associated
            LldpPortIdSubtype object, which identifies the format of the
            particular LldpPortId object instance.

            If the associated LldpPortIdSubtype object has a value of
            'interfaceAlias(1)', then the octet string identifies a
            particular instance of the ifAlias object (defined in IETF
            RFC 2863). If the particular ifAlias object does not contain
            any values, another port identifier type should be used.

            If the associated LldpPortIdSubtype object has a value of
            'portComponent(2)', then the octet string identifies a
            particular instance of the entPhysicalAlias object (defined
            in IETF RFC 4133) for a port or backplane component.

            If the associated LldpPortIdSubtype object has a value of
            'macAddress(3)', then this string identifies a particular
            unicast source address (encoded in network byte order
            and IEEE 802.3 canonical bit order) associated with the port
            (IEEE Std 802).

            If the associated LldpPortIdSubtype object has a value of
            'networkAddress(4)', then this string identifies a network
            address associated with the port. The first octet contains
            the IANA AddressFamilyNumbers enumeration value for the
            specific address type, and octets 2 through N contain the
            networkAddress address value in network byte order.

            If the associated LldpPortIdSubtype object has a value of
            'interfaceName(5)', then the octet string identifies a
            particular instance of the ifName object (defined in IETF
            RFC 2863). If the particular ifName object does not contain
            any values, another port identifier type should be used.

            If the associated LldpPortIdSubtype object has a value of
            'agentCircuitId(6)', then this string identifies a agent-local
            identifier of the circuit (defined in RFC 3046).

            If the associated LldpPortIdSubtype object has a value of
            'local(7)', then this string identifies a locally
            assigned port ID."
    SYNTAX      OCTET STRING (SIZE (0..255))


LldpV2ManAddrIfSubtype ::= TEXTUAL-CONVENTION
    STATUS      current
    DESCRIPTION
            "This TC defines an enumeration value that identifies
            the interface numbering method used for defining the
            interface number associated with a management address.
            An object with this syntax defines the format of an
            interface number object.

            The enumeration 'unknown(1)' represents the case where the
            interface is not known. In this case, the corresponding
            interface number is of zero length.

            The enumeration 'ifIndex(2)' represents interface identifier
            based on the ifIndex MIB object.

            The enumeration 'systemPortNumber(3)' represents interface
            identifier based on the system port numbering convention."
    REFERENCE
            "8.5.9.5"

    SYNTAX  INTEGER {
            unknown(1),
            ifIndex(2),
            systemPortNumber(3),
            notAvailable (2147483646),
            notApplicable (2147483647)
    }

LldpV2ManAddress ::= TEXTUAL-CONVENTION
    DISPLAY-HINT "1x:"
    STATUS      current
    DESCRIPTION
            "The value of a management address associated with the LLDP
            agent that may be used to reach higher layer entities to
            assist discovery by network management.

            It should be noted that appropriate security credentials,
            such as SNMP engineId, may be required to access the LLDP
            agent using a management address. These necessary credentials
            should be known by the network management and the objects
            associated with the credentials are not included in the
            LLDP agent."
    SYNTAX      OCTET STRING (SIZE (1..127))


-- ----------------------------------------------------
-- General Group
-- ----------------------------------------------------

lldpV2GeneralConfigLastChangeTime OBJECT-TYPE
    SYNTAX      DateAndTime
    MAX-ACCESS  read-only
    STATUS      current
    DESCRIPTION
        "The time when the configuration of the MIB was
        last changed.
"
    ::= { lldpGeneral 1 }

lldpV2GeneralStateLastChangeTime OBJECT-TYPE
    SYNTAX      DateAndTime
    MAX-ACCESS  read-only
    STATUS      current
    DESCRIPTION
        "The time when the state and/or configuration of
    the MIB was last changed.
"
    ::= { lldpGeneral 2 }

lldpV2SystemInfoTableSize OBJECT-TYPE
    SYNTAX      Unsigned32
    MAX-ACCESS  read-only
    STATUS      current
    DESCRIPTION
        "Size of lldpV2SystemInfo table.
"
    ::= { lldpGeneral 3 }

lldpV2AgentConfigTableSize OBJECT-TYPE
    SYNTAX      Unsigned32
    MAX-ACCESS  read-only
    STATUS      current
    DESCRIPTION
        "Size of lldpV2AgentConfig table.
"
    ::= { lldpGeneral 4 }

lldpV2RemSystemDataTableSize OBJECT-TYPE
    SYNTAX      Unsigned32
    MAX-ACCESS  read-only
    STATUS      current
    DESCRIPTION
        "Size of lldpV2RemoteSystemData table.
"
    ::= { lldpGeneral 5 }

lldpV2StaticsTableSize OBJECT-TYPE
    SYNTAX      Unsigned32
    MAX-ACCESS  read-only
    STATUS      current
    DESCRIPTION
        "Size of lldpV2Statistics table.
"
    ::= { lldpGeneral 6 }



-- ----------------------------------------------------
-- LldpV2 Node System Information
-- ----------------------------------------------------


lldpV2SystemInfoTable   OBJECT-TYPE
    SYNTAX      SEQUENCE OF LldpV2SystemInfoEntry
    MAX-ACCESS  not-accessible
    STATUS      current
    DESCRIPTION
            "The table contians system related infromation used to send to the neighbors.
            It contains aggregated information also available in other tables but is presentied
            in this mib for informational purposes"
    ::= { lldpV2SystemInfo 1 }

lldpV2SystemInfoEntry   OBJECT-TYPE
    SYNTAX      LldpV2SystemInfoEntry
    MAX-ACCESS  not-accessible
    STATUS      current
    DESCRIPTION
            "System Information used when configuring a particular agent.
            The contents of this table is NOT persistent across
            re-initializations or re-boots.
"
     INDEX  { lldpV2SystemInfoIndex}
    ::= { lldpV2SystemInfoTable 1 }

LldpV2SystemInfoEntry ::= SEQUENCE {
      lldpV2SystemInfoIndex               Unsigned32,
      lldpV2SystemInfoName                MgmtNameString,
      lldpV2SystemInfoSystemMacAddress    OCTET STRING,
      lldpV2SystemInfoSystemName          MgmtNameString,
      lldpV2SystemInfoSystemDescription   DisplayString,
      lldpV2SystemInfoManagementIp        IpAddress,
      lldpV2SystemInfoManagementOID       OCTET STRING,
      lldpV2SystemInfoMaxNeighbors        Unsigned32
      }

lldpV2SystemInfoIndex OBJECT-TYPE
    SYNTAX      Unsigned32 (1..2147483647)
    MAX-ACCESS  read-only
    STATUS      current
    DESCRIPTION
        "An arbitrary index assigned to each entry.
"
    ::= { lldpV2SystemInfoEntry 1 }

lldpV2SystemInfoName OBJECT-TYPE
    SYNTAX      MgmtNameString
    MAX-ACCESS  read-create
    STATUS      current
    DESCRIPTION
            "The management name of this entry
"
    ::= { lldpV2SystemInfoEntry 2 }

lldpV2SystemInfoSystemName OBJECT-TYPE
    SYNTAX      MgmtNameString
    MAX-ACCESS  read-create
    STATUS      current
    DESCRIPTION
        "The system name of the Node
"
    ::= { lldpV2SystemInfoEntry 3 }

lldpV2SystemInfoSystemDescription OBJECT-TYPE
    SYNTAX      DisplayString
    MAX-ACCESS  read-create
    STATUS      current
    DESCRIPTION
        "The system description for the node
"
    ::= { lldpV2SystemInfoEntry 4 }


lldpV2SystemInfoSystemMacAddress   OBJECT-TYPE
    SYNTAX      OCTET STRING (SIZE (1..31))
    MAX-ACCESS  read-create
    STATUS      current
    DESCRIPTION
            " The System Interface MAC Address.
"
    ::= { lldpV2SystemInfoEntry 5 }

lldpV2SystemInfoManagementIp   OBJECT-TYPE
    SYNTAX      IpAddress
    MAX-ACCESS  read-create
    STATUS      current
    DESCRIPTION
        "The local Ip address address associated with this node.
"
    ::= { lldpV2SystemInfoEntry 6 }

lldpV2SystemInfoManagementOID   OBJECT-TYPE
    SYNTAX      OCTET STRING (SIZE (1..127))
    MAX-ACCESS  read-create
    STATUS      current
    DESCRIPTION
        "The Sysem Information OID.
"
    ::= { lldpV2SystemInfoEntry 7 }

lldpV2SystemInfoMaxNeighbors  OBJECT-TYPE
    SYNTAX Unsigned32(1..3600)
    MAX-ACCESS read-create
    STATUS     current
    DESCRIPTION
        "The Maximum number of neighbors allowed per agent.
"
    DEFVAL  { 1 }
   ::= { lldpV2SystemInfoEntry 8 }



-- ----------------------------------------------------
-- LldpV2 Local Agent System Data
-- ----------------------------------------------------


lldpV2AgentConfigTable   OBJECT-TYPE
    SYNTAX      SEQUENCE OF LldpV2AgentConfigEntry
    MAX-ACCESS  not-accessible
    STATUS      current
    DESCRIPTION
            "The table that controls LLDP frame transmission on individual
            agents and using particular destination MAC addresses."
    ::= { lldpV2AgentConfig 1 }

lldpV2AgentConfigEntry   OBJECT-TYPE
    SYNTAX      LldpV2AgentConfigEntry
    MAX-ACCESS  not-accessible
    STATUS      current
    DESCRIPTION
            "LLDP configuration information for a particular agent and
            destination MAC address.

            This configuration parameter controls the transmission and
            the reception of LLDP frames on those interface/address
            combinations whose rows are created in this table.

            Rows in this table can only be created for MAC addresses
            that can validly be used in association with the type of
            interface concerned, as defined by table 8-2.

            The contents of this table is NOT persistent across
            re-initializations or re-boots.
"
     INDEX  { lldpV2AgentConfigIndex}
    ::= { lldpV2AgentConfigTable 1 }

LldpV2AgentConfigEntry ::= SEQUENCE {
      lldpV2AgentConfigIndex               Unsigned32,
      lldpV2AgentConfigName                MgmtNameString,
      lldpV2AgentConfigAdminStatus         INTEGER,
      lldpV2AgentConfigLocalMacAddress     OCTET STRING,
      lldpV2AgentConfigDestMacAddress      OCTET STRING,
      lldpV2AgentConfigNotificationEnable  TruthValue,
      lldpV2AgentConfigMessageTxInterval   Unsigned32,
      lldpV2AgentConfigRxPort              PortNumber,
      lldpV2AgentConfigTxPort              PortNumber,
      lldpV2AgentConfigUpPort              Integer32,
      lldpV2AgentConfigAgentId             Integer32,
      lldpV2AgentConfigIfNo                PortNumber,
      lldpV2AgentConfigPortDesc            SnmpAdminString
      }
lldpV2AgentConfigIndex OBJECT-TYPE
    SYNTAX      Unsigned32 (1..2147483647)
    MAX-ACCESS  read-only
    STATUS      current
    DESCRIPTION
        "An arbitrary index assigned to each entry.
"
    ::= { lldpV2AgentConfigEntry 1 }

lldpV2AgentConfigName OBJECT-TYPE
    SYNTAX      MgmtNameString
    MAX-ACCESS  read-only
    STATUS      current
    DESCRIPTION
            "The management name of the LLDP agent
"
    ::= { lldpV2AgentConfigEntry 2 }

lldpV2AgentConfigLocalMacAddress   OBJECT-TYPE
    SYNTAX      OCTET STRING (SIZE (1..31))
    MAX-ACCESS  read-only
    STATUS      current
    DESCRIPTION
            " The local MAC address associated with this entry.
"
    ::= { lldpV2AgentConfigEntry 3 }

lldpV2AgentConfigDestMacAddress   OBJECT-TYPE
    SYNTAX      OCTET STRING (SIZE (1..31))
    MAX-ACCESS  read-only
    STATUS      current
    DESCRIPTION
            " The configured destination MAC address associated with this entry.
"
    ::= { lldpV2AgentConfigEntry 4 }

lldpV2AgentConfigAdminStatus  OBJECT-TYPE
    SYNTAX  INTEGER {
               disabled(1),
               txAndRx(2)
            }
    MAX-ACCESS read-write
    STATUS     current
    DESCRIPTION
        "The administrative state for the object.

        disable - The object is de-activated.

        txAndRx - The object is activated both for sending receiving
        remote information.

"
    DEFVAL  { disabled }
   ::= { lldpV2AgentConfigEntry 5 }

lldpV2AgentConfigNotificationEnable OBJECT-TYPE
    SYNTAX     TruthValue
    MAX-ACCESS read-write
    STATUS     current
    DESCRIPTION
            "The lldpV2AgentConfigNotificationEnable controls, on a per
            agent basis, whether or not notifications from the agent
            are enabled. The value true(1) means that notifications are
            enabled; the value false(2) means that they are not.
"
    DEFVAL  { false }
   ::= { lldpV2AgentConfigEntry 6 }


lldpV2AgentConfigMessageTxInterval OBJECT-TYPE
    SYNTAX      Unsigned32(1..3600)
    MAX-ACCESS  read-write
    STATUS      current
    DESCRIPTION
            "The interval at which LLDP frames are transmitted on
            behalf of LLDP agent.

            The default value for lldpV2AgentConfigMessageTxInterval object is
            30 seconds.

            The value of this object is restored from non-volatile
            storage after a re-initialization of the management system.
"
    DEFVAL     { 30 }
    ::= { lldpV2AgentConfigEntry 7 }

lldpV2AgentConfigRxPort OBJECT-TYPE
        SYNTAX      PortNumber
        MAX-ACCESS  read-create
        STATUS      current
        DESCRIPTION
            "The RX-port of the local interface.

"
        ::= { lldpV2AgentConfigEntry 8 }

lldpV2AgentConfigTxPort OBJECT-TYPE
    SYNTAX      PortNumber
    MAX-ACCESS  read-create
    STATUS      current
    DESCRIPTION
        "The TX-port of the interface.
"
    ::= { lldpV2AgentConfigEntry 9 }

lldpV2AgentConfigUpPort OBJECT-TYPE
    SYNTAX      Integer32   (-1..2147483647)
    MAX-ACCESS  read-create
    STATUS      current
    DESCRIPTION
        "Internal port reference for traffic unit.
"
    DEFVAL { -1 }
    ::= { lldpV2AgentConfigEntry 10 }

lldpV2AgentConfigAgentId OBJECT-TYPE
    SYNTAX      Integer32   (-1..2147483647)
    MAX-ACCESS  read-create
    STATUS      current
    DESCRIPTION
        "Internal reference id for the Agent.

"
    DEFVAL { -1 }
    ::= { lldpV2AgentConfigEntry 11 }

lldpV2AgentConfigIfNo   OBJECT-TYPE
    SYNTAX      PortNumber
    MAX-ACCESS  read-only
    STATUS      current
    DESCRIPTION
        "The physical interface number of the actual multi-connector port.
"
    ::= { lldpV2AgentConfigEntry 12 }

lldpV2AgentConfigPortDesc   OBJECT-TYPE
    SYNTAX          SnmpAdminString (SIZE(0..127))
    MAX-ACCESS      read-only
    STATUS          current
    DESCRIPTION
        "The string value used to identify the description of
        the given port.
"
    ::= { lldpV2AgentConfigEntry 13 }



-- Remote Entry table

lldpV2RemTable   OBJECT-TYPE
    SYNTAX      SEQUENCE OF LldpV2RemEntry
    MAX-ACCESS  not-accessible
    STATUS      current
    DESCRIPTION
            "This table contains one or more rows per physical network
            connection known to this agent. The agent may wish to ensure
            that only one lldpV2RemEntry is present for each local port
            and destination MAC address,or it may choose to maintain multiple
            lldpV2RemEntries for the same local port and destination MAC address."
    ::= { lldpV2RemoteSystemData 1 }

lldpV2RemEntry  OBJECT-TYPE
    SYNTAX      LldpV2RemEntry
    MAX-ACCESS  not-accessible
    STATUS      current
    DESCRIPTION
            "Information about a particular physical network connection.
            Entries may be created and deleted in this table by the agent,
            if a physical topology discovery process is active.
"
     INDEX  { lldpV2RemIndex}
    ::= { lldpV2RemTable 1 }


LldpV2RemEntry ::= SEQUENCE {
-- the following attributes should conform to standard attributes according to LLDP-V2-MIB
      lldpV2RemIndex                    Unsigned32,
      lldpV2RemName                     MgmtNameString,
      lldpV2RemLocalIfIndex             Unsigned32,
      lldpV2RemSourceMACAddress         OCTET STRING,
      lldpV2RemChassisIdSubtype         LldpV2ChassisIdSubtype,
      lldpV2RemChassisId                LldpV2ChassisId,
      lldpV2RemPortIdSubtype            LldpV2PortIdSubtype,
      lldpV2RemPortId                   LldpV2PortId,
      lldpV2RemPortDesc                 SnmpAdminString,
      lldpV2RemSysName                  SnmpAdminString,
      lldpV2RemSysDesc                  SnmpAdminString,
      lldpV2RemSysCapSupported          OCTET STRING,
      lldpV2RemSysCapEnabled            OCTET STRING,
      lldpV2RemManAddrSubtype           LumAddressFamilyNumbers,
      lldpV2RemManAddr                  LldpV2ManAddress,
      lldpV2RemManAddrIfSubtype         LldpV2ManAddrIfSubtype,
      lldpV2RemManAddrIfId              Unsigned32,
      lldpV2RemManAddrOID               OCTET STRING,
      lldpV2RemTooManyNeighbors         TruthValue,

-- the following attributes are non standard extension attributes
      lldpV2RemMtuSize                  Unsigned32,
      lldpV2RemLagId                    Unsigned32,
      lldpV2RemLagisAggCapable          TruthValueWithNA,
      lldpV2RemLagisAggregated          TruthValueWithNA,
      lldpV2RemUpTime                   Unsigned32,
      lldpV2RemTimeout                  Unsigned32,
      lldpV2RemTTL                      Unsigned32,

-- the following attributes are non standard attributes added for ENM housekeeping

      lldpV2RemSubrack                    SubrackNumber,
      lldpV2RemSlot                       SlotNumber,
      lldpV2RemTxPort                     PortNumber,
      lldpV2RemRxPort                     PortNumber,
      lldpV2RemIdx                        Integer32,
      lldpV2RemIfNo                       PortNumber,
      lldpV2RemUpPortId                   Integer32,
      lldpV2RemAgentId                    Integer32
      }

lldpV2RemIndex OBJECT-TYPE
    SYNTAX      Unsigned32 (1..2147483647)
    MAX-ACCESS  read-only
    STATUS      current
    DESCRIPTION
        "An arbitrary index assigned to each entry.
    An agent is encouraged to assign monotonically increasing
        index values to new entries, starting with one, after each
        reboot. It is considered unlikely that the lldpRemIndex
        can wrap between reboots.
"
    ::= { lldpV2RemEntry 1 }

lldpV2RemName OBJECT-TYPE
    SYNTAX      MgmtNameString
    MAX-ACCESS  read-create
    STATUS      current
    DESCRIPTION
            "The management name of the LLDP Remote entry.
            for example 'neighbor:1:2:1-2' (neighbor:[subrack]:[slot][if]:[tx-rx])
"

    ::= { lldpV2RemEntry 2 }

lldpV2RemLocalIfIndex OBJECT-TYPE
    SYNTAX      Unsigned32 (1..2147483647)
    MAX-ACCESS  read-create
    STATUS      current
    DESCRIPTION
        "The interface index value used to identify the port associated with this entry.
"
    ::= { lldpV2RemEntry 3 }

lldpV2RemSourceMACAddress   OBJECT-TYPE
    SYNTAX      OCTET STRING (SIZE (1..31))
    MAX-ACCESS  read-create
    STATUS      current
    DESCRIPTION
            "The source mac address of received LLDP frame.

"
    ::= { lldpV2RemEntry 4 }

lldpV2RemChassisIdSubtype   OBJECT-TYPE
    SYNTAX      LldpV2ChassisIdSubtype
    MAX-ACCESS  read-create
    STATUS      current
    DESCRIPTION
            "The type of encoding used to identify the chassis associated
            with the remote system.
"
    REFERENCE
            "8.5.2.2"
    ::= { lldpV2RemEntry 5 }

lldpV2RemChassisId   OBJECT-TYPE
    SYNTAX      LldpV2ChassisId
    MAX-ACCESS  read-create
    STATUS      current
    DESCRIPTION
            "The string value used to identify the chassis component
            associated with the remote system.
"
    REFERENCE
            "8.5.2.3"
    ::= { lldpV2RemEntry 6 }


lldpV2RemPortIdSubtype   OBJECT-TYPE
    SYNTAX      LldpV2PortIdSubtype
    MAX-ACCESS  read-create
    STATUS      current
    DESCRIPTION
            "The type of port identifier encoding used in the associated
            'lldpRemPortId' object.
"
    REFERENCE
            "8.5.3.2"
    ::= { lldpV2RemEntry 7 }

lldpV2RemPortId   OBJECT-TYPE
    SYNTAX      LldpV2PortId
    MAX-ACCESS  read-create
    STATUS      current
    DESCRIPTION
            "The string value used to identify the port component
            associated with the remote system.
"
    REFERENCE
            "8.5.3.3"
    ::= { lldpV2RemEntry 8 }


lldpV2RemPortDesc   OBJECT-TYPE
    SYNTAX          SnmpAdminString (SIZE(0..128))
    MAX-ACCESS      read-create
    STATUS          current
    DESCRIPTION
        "The string value used to identify the description of
        the given port associated with the remote system.
"
    ::= { lldpV2RemEntry 9 }


lldpV2RemSysName   OBJECT-TYPE
    SYNTAX      SnmpAdminString (SIZE(0..255))
    MAX-ACCESS  read-create
    STATUS      current
    DESCRIPTION
            "The string value used to identify the system name of the
            remote system.
"
    ::= { lldpV2RemEntry 10 }

lldpV2RemSysDesc   OBJECT-TYPE
    SYNTAX      SnmpAdminString (SIZE(0..255))
    MAX-ACCESS  read-create
    STATUS      current
    DESCRIPTION
            "The string value used to identify the system description
            of the remote system.

"
    ::= { lldpV2RemEntry 11 }

lldpV2RemSysCapEnabled   OBJECT-TYPE
    SYNTAX  OCTET STRING (SIZE (0..127))
    MAX-ACCESS  read-create
    STATUS      current
    DESCRIPTION
            "The capabilities that are enabled on the remote system.
            The original TLV is a bit mask and is decoded as follows.
            (O) Other (bit 0),
            (RE) Repeater (bit 1),
            (B) Bridge (bit 2),
            (W) WLAN AP (bit 3),
            (RO) Router (bit 4),
            (T) Telephone (bit 5),
            (D) DOCSIS cable device (bit 6)
            (S) Station(bit 7)
            (CV) cVLANComponent(bit 8),
            (SV) sVLANComponent(bit 9),
            (TP) twoPortMACRelay(bit 10)
"
    ::= { lldpV2RemEntry 12 }


lldpV2RemSysCapSupported   OBJECT-TYPE
    SYNTAX    OCTET STRING (SIZE (0..127))
    MAX-ACCESS  read-create
    STATUS      current
    DESCRIPTION
            "The capabilities that are supported on the remote system.
            The original TLV is a bit mask and is decoded as follows.
            (O) Other (bit 0),
            (RE) Repeater (bit 1),
            (B) Bridge (bit 2),
            (W) WLAN AP (bit 3),
            (RO) Router (bit 4),
            (T) Telephone (bit 5),
            (D) DOCSIS cable device (bit 6)
            (S) Station(bit 7)
            (CV) cVLANComponent(bit 8),
            (SV) sVLANComponent(bit 9),
            (TP) twoPortMACRelay(bit 10)
"
    ::= { lldpV2RemEntry 13 }


lldpV2RemManAddrSubtype  OBJECT-TYPE
    SYNTAX      LumAddressFamilyNumbers
    MAX-ACCESS  read-create
    STATUS      current
    DESCRIPTION
            "The type of management address identifier encoding used in
            the associated 'lldpRemManagmentAddr' object.

            It should be noted that only a subset of the possible
            address encodings enumerated in AddressFamilyNumbers
            are appropriate for use as a LLDP management
            address, either because some are just not apliccable or
            because the maximum size of a LldpV2ManAddress octet string
            would prevent the use of some address identifier encodings.

"
    REFERENCE
            "8.5.9.3"
    ::= { lldpV2RemEntry 14 }

lldpV2RemManAddr  OBJECT-TYPE
    SYNTAX      LldpV2ManAddress
    MAX-ACCESS  read-create
    STATUS      current
    DESCRIPTION
            "The string value used to identify the management address
            component associated with the remote system. The purpose
            of this address is to contact the management entity.

"
    ::= { lldpV2RemEntry 15 }

lldpV2RemManAddrIfSubtype  OBJECT-TYPE
    SYNTAX      LldpV2ManAddrIfSubtype
    MAX-ACCESS  read-create
    STATUS      current
    DESCRIPTION
            "The string value used to identify the management address
            component associated with the remote system. The purpose
            of this address is to contact the management entity.

"
    ::= { lldpV2RemEntry 16 }

lldpV2RemManAddrIfId  OBJECT-TYPE
    SYNTAX      Unsigned32 (0..2147483644 | 2147483646 | 2147483647)
    MAX-ACCESS  read-create
    STATUS      current
    DESCRIPTION
            "The integer value used to identify the interface number
            regarding the management address component associated with
            the remote system. The value depends upon the value of the
            lldpV2RemManAddrIfSubtype for the table row.

"

        REFERENCE
            "8.5.9.6"
    ::= { lldpV2RemEntry 17 }

lldpV2RemManAddrOID  OBJECT-TYPE
    SYNTAX      OCTET STRING (SIZE (0..31))
    MAX-ACCESS  read-create
    STATUS      current
    DESCRIPTION
            "The decoded OID value used to identify the type of hardware component
            or protocol entity associated with the management address
            advertised by the remote system agent.

"
    REFERENCE
            "8.5.9.8"
    ::= { lldpV2RemEntry 18 }


lldpV2RemTooManyNeighbors   OBJECT-TYPE
    SYNTAX      TruthValue
    MAX-ACCESS  read-create
    STATUS      current
    DESCRIPTION
            "Indicates that there are too many neighbors
             as determined by the variable tooManyNeighbors.

"
    ::= { lldpV2RemEntry 19 }


-- the following attributes are non standard extension attributes

lldpV2RemMtuSize   OBJECT-TYPE
    SYNTAX      Unsigned32 (0..2147483647)
    MAX-ACCESS  read-create
    STATUS      current
    DESCRIPTION
        "Indicates the remote side MTU size.

"
    ::= { lldpV2RemEntry 20 }


lldpV2RemLagId   OBJECT-TYPE
    SYNTAX      Unsigned32 (0..2147483647)
    MAX-ACCESS  read-create
    STATUS      current
    DESCRIPTION
        "Indicates the remote side lag Id.

"
    ::= { lldpV2RemEntry 21 }

lldpV2RemLagisAggCapable   OBJECT-TYPE
    SYNTAX      TruthValueWithNA
    MAX-ACCESS  read-create
    STATUS      current
    DESCRIPTION
        "Indicates if the remote side is capable of aggregation.

"
    ::= { lldpV2RemEntry 22 }

lldpV2RemLagisAggregated   OBJECT-TYPE
    SYNTAX      TruthValueWithNA
    MAX-ACCESS  read-create
    STATUS      current
    DESCRIPTION
            "Indicates if the remote side is aggregated.

"
    ::= { lldpV2RemEntry 23 }

lldpV2RemUpTime   OBJECT-TYPE
    SYNTAX      Unsigned32 (1..2147483647)
    MAX-ACCESS  read-create
    STATUS      current
    DESCRIPTION
            "Time since entry was first added (seconds).

"
    ::= { lldpV2RemEntry 24 }

lldpV2RemTimeout   OBJECT-TYPE
    SYNTAX      Unsigned32 (1..2147483647)
    MAX-ACCESS  read-create
    STATUS      current
    DESCRIPTION
        "Indicates the remote side timeout (seconds).

"
    ::= { lldpV2RemEntry 25 }

lldpV2RemTTL   OBJECT-TYPE
    SYNTAX      Unsigned32 (1..2147483647)
    MAX-ACCESS  read-create
    STATUS      current
    DESCRIPTION
        "Indicates the remote side TTL TLV (seconds).

"
    ::= { lldpV2RemEntry 26 }


-- The following attributes are added for housekeeping.

lldpV2RemSubrack OBJECT-TYPE
        SYNTAX      SubrackNumber
        MAX-ACCESS  read-create
        STATUS      current
        DESCRIPTION
            "The number of the subrack where the local interface
            is located.

"
        ::= { lldpV2RemEntry 27 }

lldpV2RemSlot OBJECT-TYPE
        SYNTAX      SlotNumber
        MAX-ACCESS  read-create
        STATUS      current
        DESCRIPTION
            "The number of the slot where the local interface is
            located.

"
        ::= { lldpV2RemEntry 28 }

lldpV2RemTxPort OBJECT-TYPE
        SYNTAX      PortNumber
        MAX-ACCESS  read-create
        STATUS      current
        DESCRIPTION
            "The TX-port of the local interface.

"
        ::= { lldpV2RemEntry 29 }

lldpV2RemRxPort OBJECT-TYPE
        SYNTAX      PortNumber
        MAX-ACCESS  read-create
        STATUS      current
        DESCRIPTION
            "The RX-port of the local interface.

"
        ::= { lldpV2RemEntry 30 }

lldpV2RemIdx OBJECT-TYPE
    SYNTAX      Integer32   (-1..2147483647)
    MAX-ACCESS  read-create
    STATUS      current
    DESCRIPTION
        "Internal object reference

"
    DEFVAL { -1  }
    ::= { lldpV2RemEntry 31 }

lldpV2RemIfNo OBJECT-TYPE
    SYNTAX      PortNumber
    MAX-ACCESS  read-create
    STATUS      current
    DESCRIPTION
        "The local physical interface number of the actual multi-connector port.

"
    DEFVAL { 1  }
    ::= { lldpV2RemEntry 32 }

lldpV2RemUpPortId OBJECT-TYPE
    SYNTAX      Integer32   (-1..2147483647)
    MAX-ACCESS  read-create
    STATUS      current
    DESCRIPTION
        "Internal port reference for traffic unit.
"
    DEFVAL { -1  }
    ::= { lldpV2RemEntry 33 }

lldpV2RemAgentId OBJECT-TYPE
    SYNTAX      Integer32   (-1..2147483647)
    MAX-ACCESS  read-create
    STATUS      current
    DESCRIPTION
        "Reference to AgentId.
"
    DEFVAL { -1  }
    ::= { lldpV2RemEntry 34 }



------------------------------------------------------------------------------------
-- LldpV2  Stats
-----------------------------------------------------------------------------------

lldpV2StatsTable  OBJECT-TYPE
    SYNTAX      SEQUENCE OF LldpV2StatsEntry
    MAX-ACCESS  not-accessible
    STATUS      current
    DESCRIPTION
            "A table containing LLDP transmission statistics."
    ::= { lldpV2Statistics 1 }

lldpV2StatsEntry   OBJECT-TYPE
     SYNTAX      LldpV2StatsEntry
     MAX-ACCESS  not-accessible
     STATUS      current
     DESCRIPTION
             "LLDP frame reception statistics for a particular port.
             The port is contained in the same chassis as the LLDP agent.
"
     INDEX  { lldpV2StatsIndex }
     ::= { lldpV2StatsTable 1 }

LldpV2StatsEntry ::= SEQUENCE {
      lldpV2StatsIndex                        Unsigned32,
      lldpV2StatsName                         MgmtNameString,
      lldpV2StatsAgentId                      Integer32,
      lldpV2StatsTxPortFramesTotal            Counter32,
      lldpV2StatsRxPortFramesDiscardedTotal   Counter32,
      lldpV2StatsRxPortFramesErrors           Counter32,
      lldpV2StatsRxPortFramesTotal            Counter32,
      lldpV2StatsAgeOutsTotal                 Counter32,
      lldpV2StatsTLVSDiscardedTotal           Counter32,
      lldpV2StatsTLVSUnrecognizedTotal        Counter32,
      lldpV2StatsSubrack                      SubrackNumber,
      lldpV2StatsSlot                         SlotNumber,
      lldpV2StatsTxPort                       PortNumber,
      lldpV2StatsRxPort                       PortNumber,
      lldpV2StatsIdx                          Integer32,
      lldpV2StatsIfNo                         PortNumber,
      lldpV2StatsClientIdx                    Integer32,
      lldpV2StatsUpPortId                     Integer32,
      lldpV2StatsReset                        INTEGER}

lldpV2StatsIndex OBJECT-TYPE
    SYNTAX      Unsigned32 (1..2147483647)
    MAX-ACCESS  read-only
    STATUS      current
    DESCRIPTION
        "An arbitrary index assigned to each entry.
"
    ::= { lldpV2StatsEntry 1 }

lldpV2StatsAgentId OBJECT-TYPE
    SYNTAX      Integer32   (-1..2147483647)
    MAX-ACCESS  read-only
    STATUS      current
    DESCRIPTION
        "Id of the Lldp agent.
"
    DEFVAL { -1 }
    ::= { lldpV2StatsEntry 2 }


lldpV2StatsName OBJECT-TYPE
    SYNTAX      MgmtNameString
    MAX-ACCESS  read-only
    STATUS      current
    DESCRIPTION
            "The management name is used to identify the agent.
"
    ::= { lldpV2StatsEntry 3 }

lldpV2StatsTxPortFramesTotal  OBJECT-TYPE
    SYNTAX        Counter32
    MAX-ACCESS    read-only
    STATUS        current
    DESCRIPTION
            "A count of all LLDP frames transmitted.
"
    ::= { lldpV2StatsEntry 4 }

lldpV2StatsRxPortFramesDiscardedTotal OBJECT-TYPE
    SYNTAX        Counter32
    MAX-ACCESS read-only
    STATUS     current
    DESCRIPTION
            "A count of all LLDPDUs received and then discarded.
"
   ::= { lldpV2StatsEntry 5 }

lldpV2StatsRxPortFramesErrors  OBJECT-TYPE
    SYNTAX        Counter32
    MAX-ACCESS    read-only
    STATUS        current
    DESCRIPTION
            "A count of all LLDPDUs received with one or more detectable errors.
"
    ::= { lldpV2StatsEntry 6 }

lldpV2StatsRxPortFramesTotal OBJECT-TYPE
    SYNTAX        Counter32
    MAX-ACCESS    read-only
    STATUS        current
    DESCRIPTION
            "A count of all LLDP frames received.
"
    ::= { lldpV2StatsEntry 7 }

lldpV2StatsAgeOutsTotal OBJECT-TYPE
    SYNTAX        Counter32
    MAX-ACCESS    read-only
    STATUS        current
    DESCRIPTION
            "A count of the times that a neighbours information is deleted from
            the LLDP remote systems MIB because of rxInfoTTL timer expiration.
"
    ::= { lldpV2StatsEntry 8 }

lldpV2StatsTLVSDiscardedTotal OBJECT-TYPE
    SYNTAX        Counter32
    MAX-ACCESS    read-only
    STATUS        current
    DESCRIPTION
       "A count of all TLVs received and discarded for any reason.
"
    ::= { lldpV2StatsEntry 9 }


lldpV2StatsTLVSUnrecognizedTotal OBJECT-TYPE
    SYNTAX        Counter32
    MAX-ACCESS    read-only
    STATUS        current
    DESCRIPTION
        "This counter provides a count of all TLVs not recognised by the receiving LLDP local agent.

"
    ::= { lldpV2StatsEntry 10 }


lldpV2StatsSubrack OBJECT-TYPE
    SYNTAX      SubrackNumber
    MAX-ACCESS  read-create
    STATUS      current
    DESCRIPTION
     "The number of the subrack where the local interface is located.

"
    ::= { lldpV2StatsEntry 11 }

lldpV2StatsSlot OBJECT-TYPE
   SYNTAX      SlotNumber
   MAX-ACCESS  read-create
   STATUS      current
   DESCRIPTION
   "The number of the slot where the local interface is located.

"
   ::= { lldpV2StatsEntry 12 }

lldpV2StatsTxPort OBJECT-TYPE
    SYNTAX      PortNumber
    MAX-ACCESS  read-create
    STATUS      current
    DESCRIPTION
    "The TX-port of the local interface.

"
    ::= { lldpV2StatsEntry 13 }

lldpV2StatsRxPort OBJECT-TYPE
    SYNTAX      PortNumber
    MAX-ACCESS  read-create
    STATUS      current
    DESCRIPTION
    "The RX-port of the local interface.

"
    ::= { lldpV2StatsEntry 14 }

lldpV2StatsIdx OBJECT-TYPE
    SYNTAX      Integer32   (-1..2147483647)
    MAX-ACCESS  read-create
    STATUS      current
    DESCRIPTION
    "Internal object reference

"
    DEFVAL { -1  }
    ::= { lldpV2StatsEntry 15 }

lldpV2StatsIfNo OBJECT-TYPE
    SYNTAX      PortNumber
    MAX-ACCESS  read-create
    STATUS      current
    DESCRIPTION
        "The local physical interface number of the actual multi-connector port.

"
    DEFVAL { 1  }
    ::= { lldpV2StatsEntry 16 }

lldpV2StatsClientIdx OBJECT-TYPE
    SYNTAX      Integer32   (-1..2147483647)
    MAX-ACCESS  read-create
    STATUS      current
    DESCRIPTION
        "Internal object reference local client interface.

"
    DEFVAL { -1  }
    ::= { lldpV2StatsEntry 17 }

lldpV2StatsUpPortId OBJECT-TYPE
    SYNTAX      Integer32   (-1..2147483647)
    MAX-ACCESS  read-create
    STATUS      current
    DESCRIPTION
        "Internal port reference for traffic unit.
"
    DEFVAL { -1  }
    ::= { lldpV2StatsEntry 18 }

lldpV2StatsReset OBJECT-TYPE
   SYNTAX      INTEGER {
                    normal (1),
                    reset (2) }
    MAX-ACCESS  read-write
    STATUS      current
    DESCRIPTION
        "Reset lldp statistics counters.
"
    DEFVAL { normal }
    ::= { lldpV2StatsEntry 19 }

-- ----------------------------------------------------
-- Object and event groups
-- ----------------------------------------------------

lldpV2GeneralGroupV1 OBJECT-GROUP
    OBJECTS {
        lldpV2GeneralConfigLastChangeTime,
        lldpV2GeneralStateLastChangeTime,
        lldpV2AgentConfigTableSize,
        lldpV2RemSystemDataTableSize,
        lldpV2StaticsTableSize}
    STATUS  current
    DESCRIPTION
        "General objects for the LLDP V2 general group (R27.0).
"
    ::= { lumLldpV2Groups 1 }

lldpV2SystemInfoGroupV1 OBJECT-GROUP
    OBJECTS {
      lldpV2SystemInfoIndex,
      lldpV2SystemInfoName,
      lldpV2SystemInfoSystemName,
      lldpV2SystemInfoSystemMacAddress,
      lldpV2SystemInfoSystemDescription,
      lldpV2SystemInfoManagementIp,
      lldpV2SystemInfoManagementOID,
      lldpV2SystemInfoMaxNeighbors}
    STATUS  current
    DESCRIPTION
        "General objects for the LLDP V2 system info group (R27.0)."
    ::= { lumLldpV2Groups 2 }


lldpV2AgentConfigGroupV1 OBJECT-GROUP
    OBJECTS {
      lldpV2AgentConfigIndex,
      lldpV2AgentConfigName,
      lldpV2AgentConfigLocalMacAddress,
      lldpV2AgentConfigAdminStatus,
      lldpV2AgentConfigNotificationEnable,
      lldpV2AgentConfigMessageTxInterval,
      lldpV2AgentConfigRxPort,
      lldpV2AgentConfigTxPort,
      lldpV2AgentConfigUpPort,
      lldpV2AgentConfigAgentId,
      lldpV2AgentConfigIfNo}
    STATUS  current
    DESCRIPTION
        "General objects for the LLDP V2 agent config group (R27.0)."
    ::= { lumLldpV2Groups 3 }


lldpV2RemoteSystemsDataGroupV1 OBJECT-GROUP
    OBJECTS {
-- the following attributes should conform to standard attributes according to LLDP-V2-MIB
    lldpV2RemIndex,
    lldpV2RemName,
    lldpV2RemLocalIfIndex,
    lldpV2RemSourceMACAddress,
    lldpV2RemChassisIdSubtype,
    lldpV2RemChassisId,
    lldpV2RemPortIdSubtype,
    lldpV2RemPortId,
    lldpV2RemPortDesc,
    lldpV2RemSysName,
    lldpV2RemSysDesc,
    lldpV2RemSysCapEnabled,
    lldpV2RemSysCapSupported,
    lldpV2RemManAddrSubtype,
    lldpV2RemManAddr,
    lldpV2RemManAddrIfSubtype,
    lldpV2RemManAddrIfId,
    lldpV2RemManAddrOID,
    lldpV2RemTooManyNeighbors,

-- the following attributes are non standard extension attributes
    lldpV2RemMtuSize,
    lldpV2RemLagId,
    lldpV2RemLagisAggCapable,
    lldpV2RemLagisAggregated,
    lldpV2RemUpTime,
    lldpV2RemTimeout,
    lldpV2RemTTL,

-- the following attributes are non standard attributes added for ENM housekeeping
    lldpV2RemSubrack,
    lldpV2RemSlot,
    lldpV2RemTxPort,
    lldpV2RemRxPort,
    lldpV2RemIdx,
    lldpV2RemIfNo,
    lldpV2RemUpPortId,
    lldpV2RemAgentId }
    STATUS  current
    DESCRIPTION
        "General objects for the LLDP V2 remote system group (R27.0)."
    ::= { lumLldpV2Groups 4 }


lldpV2StatsGroupV1 OBJECT-GROUP
    OBJECTS {
      lldpV2StatsIndex,
      lldpV2StatsName,
      lldpV2StatsAgentId,
      lldpV2StatsTxPortFramesTotal,
      lldpV2StatsRxPortFramesDiscardedTotal,
      lldpV2StatsRxPortFramesErrors,
      lldpV2StatsRxPortFramesTotal,
      lldpV2StatsAgeOutsTotal,
      lldpV2StatsTLVSDiscardedTotal,
      lldpV2StatsTLVSUnrecognizedTotal,
      lldpV2StatsSubrack,
      lldpV2StatsSlot,
      lldpV2StatsTxPort,
      lldpV2StatsRxPort,
      lldpV2StatsIdx,
      lldpV2StatsIfNo,
      lldpV2StatsClientIdx,
      lldpV2StatsUpPortId,
      lldpV2StatsReset}
    STATUS  current
    DESCRIPTION
        "General objects for the LLDP V2 statistics group (R27.0)."
    ::= { lumLldpV2Groups 5 }


lldpV2BasicComplV1 MODULE-COMPLIANCE
    STATUS       deprecated
    DESCRIPTION
        "The compliance statement for the LLDPV2. (R27.0)"
    MODULE
        MANDATORY-GROUPS {
            lldpV2GeneralGroupV1,
            lldpV2SystemInfoGroupV1,
            lldpV2AgentConfigGroupV1,
            lldpV2RemoteSystemsDataGroupV1,
            lldpV2StatsGroupV1 }
    ::= { lumLldpV2Compliances 1 }

lldpV2BasicComplV2 MODULE-COMPLIANCE
    STATUS       current
    DESCRIPTION
        "The compliance statement for the LLDPV2. (30.1)"
    MODULE
        MANDATORY-GROUPS {
            lldpV2GeneralGroupV1,
            lldpV2SystemInfoGroupV1,
            lldpV2AgentConfigGroupV1,
            lldpV2RemoteSystemsDataGroupV1,
            lldpV2StatsGroupV1 }
    ::= { lumLldpV2Compliances 2 }

END

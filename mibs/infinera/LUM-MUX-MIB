LUM-MUX-MIB DEFINITIONS ::= BEGIN

IMPORTS
    MODULE-IDENTITY, OBJECT-TYPE, Unsigned32, Integer32, Gauge32
        FROM SNMPv2-SMI
    OBJECT-GROUP, MODULE-COMPLIANCE
        FROM SNMPv2-CONF
    DisplayString, TEXTUAL-CONVENTION, DateAndTime
        FROM SNMPv2-TC
    lumModules, lumMuxMIB
        FROM LUM-REG
    FaultStatus, MgmtNameString, SubrackNumber, SlotNumber, PortNumber,
    LambdaFrequency, BoardOrInterfaceAdminStatus, BoardOrInterfaceOperStatus,
    ObjectProperty
        FROM LUM-TC;

lumMuxMIBModule MODULE-IDENTITY
    LAST-UPDATED
        "201706150000Z" -- June 15th 2017
    ORGANIZATION
        "Infinera Corporation"
    CONTACT-INFO
        "techsupport@infinera.com"
    DESCRIPTION
        "The muxponder trunk interfaces.
        Muxponder client interfaces are
        found in the multi-rate client interface MIB.

        - General

        - MUX trunk interfaces

"
    REVISION
        "201706150000Z" -- June 15th 2017
    DESCRIPTION
        "Changes made for release r29.0:
         - Changed ORGANIZATION and CONTACT-INFO"
    REVISION
        "201601110000Z" -- Jan 11th 2016
    DESCRIPTION
        "Added default value notPresent for operStatus."
    REVISION
        "201104120000Z" -- April 12th 2011
    DESCRIPTION
	"Added new compliance group to mark adding write support for trail trace."
    REVISION
        "200711120000Z" -- November 12th 2007
    DESCRIPTION
	"Fixed indexing of muxVc4Entry and minor compliance error."
    REVISION
        "200301290000Z" -- January 29th 2003
    DESCRIPTION
        "Changed the handling of VC4s again: added connectionMode/Status"
    REVISION
        "200212040000Z" -- December 4th 2002
    DESCRIPTION
        "Added trace identifier attributes in the mux interface table."
    REVISION
        "200210290000Z" -- October 29th 2002
    DESCRIPTION
        "Added txLambda/expectedTxLambda."
    REVISION
        "200210010000Z" -- October 1st 2002
    DESCRIPTION
        "Updated the VC-4 table."
    REVISION
        "200204030000Z" -- April 3rd 2002
    DESCRIPTION
        "Added laser status."
    REVISION
        "200201170000Z" -- January 17th 2002
    DESCRIPTION
        "Added lossOfFrame and alarmIndicationSignal alarms."
    REVISION
        "200112030000Z" -- December 3rd 2001
    DESCRIPTION
        "Moved admin and operStatus definitions to LUM-TC"
    REVISION
        "200111090000Z" -- November 9th 2001
    DESCRIPTION
        "Added bitrate mismatch alarm.
        Added laserBias meter and threshold, not supported yet but still."
    REVISION
        "200110300000Z" -- October 30th 2001
    DESCRIPTION
        "The initial revision of this module."
    ::= { lumModules 14 }

-- ----------------------------------------------------
-- Conformance area, containing groups and complicance
-- specifications.
-- ----------------------------------------------------

lumMuxConfs OBJECT IDENTIFIER ::= { lumMuxMIB 1 }
lumMuxGroups OBJECT IDENTIFIER ::= { lumMuxConfs 1 }
lumMuxCompl OBJECT IDENTIFIER ::= { lumMuxConfs 2 }


-- ----------------------------------------------------
-- Root for objects in the mux MIB
-- ----------------------------------------------------

lumMuxMIBObjects OBJECT IDENTIFIER ::= { lumMuxMIB 2 }


-- ----------------------------------------------------
-- This MIB contains the following groups:
-- ----------------------------------------------------

muxGeneral OBJECT IDENTIFIER ::= { lumMuxMIBObjects 1 }
muxIfList OBJECT IDENTIFIER ::= { lumMuxMIBObjects 2 }
muxVc4List OBJECT IDENTIFIER ::= { lumMuxMIBObjects 3 }


-- ----------------------------------------------------
-- Textual Conventions
-- ----------------------------------------------------

MuxTxDirection ::= TEXTUAL-CONVENTION
    STATUS   current
    DESCRIPTION
        "The direction of the transmitted signal.

        undefined - Unknown/Dont care

        toWest - The transmitted signal is sent to west

        toEast - The transmitted signal is sent to east"
    SYNTAX INTEGER {
        undefined (0),
        toWest (1),
        toEast (2) }


-- ----------------------------------------------------
-- General group
-- ----------------------------------------------------

muxGeneralLastChangeTime OBJECT-TYPE
    SYNTAX      DateAndTime
    MAX-ACCESS  read-only
    STATUS      current
    DESCRIPTION
        "The time when the configuration of the MIB was
        last changed.

"
    ::= { muxGeneral 1 }

muxGeneralStateLastChangeTime OBJECT-TYPE
    SYNTAX      DateAndTime
    MAX-ACCESS  read-only
    STATUS      current
    DESCRIPTION
        "The time when the state of the MIB was last
        changed.

"
    ::= { muxGeneral 2 }

muxGeneralMuxIfTableSize OBJECT-TYPE
    SYNTAX      Unsigned32
    MAX-ACCESS  read-only
    STATUS      current
    DESCRIPTION
        "Size of table

"
    ::= { muxGeneral 3 }

muxGeneralMuxVc4TableSize OBJECT-TYPE
    SYNTAX      Unsigned32
    MAX-ACCESS  read-only
    STATUS      current
    DESCRIPTION
        "Size of table

"
    ::= { muxGeneral 4 }


-- ----------------------------------------------------
-- MUX trunk interfaces
-- ----------------------------------------------------

muxIfTable  OBJECT-TYPE
    SYNTAX      SEQUENCE OF MuxIfEntry
    MAX-ACCESS  not-accessible
    STATUS      current
    DESCRIPTION
        "The interface list."
    ::= { muxIfList 1 }

muxIfEntry OBJECT-TYPE
    SYNTAX      MuxIfEntry
    MAX-ACCESS  not-accessible
    STATUS      current
    DESCRIPTION
        "An entry in the interface list.

"
    INDEX { muxIfIndex }
    ::= { muxIfTable 1 }

MuxIfEntry ::=
    SEQUENCE {
        muxIfIndex                      Unsigned32,
        muxIfName                       MgmtNameString,
        muxIfDescr                      DisplayString,
        muxIfSubrack                    SubrackNumber,
        muxIfSlot                       SlotNumber,
        muxIfTxPort                     PortNumber,
        muxIfRxPort                     PortNumber,
        muxIfInvPhysIndexOrZero         Unsigned32,
        muxIfPowerLevel                 Integer32,
        muxIfPowerLevelHighThreshold    Integer32,
        muxIfPowerLevelLowThreshold     Integer32,
        muxIfAdminStatus                BoardOrInterfaceAdminStatus,
        muxIfOperStatus                 BoardOrInterfaceOperStatus,
        muxIfLossOfSignal               FaultStatus,
        muxIfReceivedPowerHigh          FaultStatus,
        muxIfReceivedPowerLow           FaultStatus,
        muxIfBitrateMismatch            FaultStatus,
        muxIfLaserBias                  Unsigned32,
        muxIfLaserBiasThreshold         Unsigned32,
        muxIfJ0PathTrace                OCTET STRING,
        muxIfAlarmIndicationSignal      FaultStatus,
        muxIfLossOfFrame                FaultStatus,
        muxIfLaserStatus                INTEGER,
        muxIfTxDirection                MuxTxDirection,
        muxIfExpectedTxLambda           LambdaFrequency,
        muxIfTxLambda                   LambdaFrequency,
        muxIfTraceIntrusionMode         INTEGER,
        muxIfTraceTransmitted           DisplayString,
        muxIfTraceReceived              DisplayString,
        muxIfTraceExpected              DisplayString,
        muxIfTraceAlarmMode             INTEGER,
        muxIfTraceMismatch              FaultStatus,
        muxIfOHTransparency             INTEGER,
        muxIfSuppressRemoteAlarms       INTEGER,
        muxIfHighSpeedMin               Gauge32,
        muxIfHighSpeedMax               Gauge32,
        muxIfTrxCodeMismatch            FaultStatus,
        muxIfTrxBitrateUnavailable      FaultStatus,
        muxIfTrxMissing                 FaultStatus,
        muxIfTrxClass                   DisplayString,
        muxIfTransmitterFailed          FaultStatus,
        muxIfUnexpectedFrequency        FaultStatus,
        muxIfIllegalFrequency           FaultStatus,
        muxIfReceiverSensitivity        Integer32,
        muxIfPowerLevelLowRelativeThreshold Integer32,
        muxIfObjectProperty             ObjectProperty,
        muxIfTxPowerLevel               Integer32,
        muxIfLaserTempActual            Integer32 }

muxIfIndex OBJECT-TYPE
    SYNTAX      Unsigned32 (1..2147483647)
    MAX-ACCESS  read-only
    STATUS      current
    DESCRIPTION
        "An arbitrary index assigned to each if entry.

"
    ::= { muxIfEntry 1 }

muxIfName OBJECT-TYPE
    SYNTAX      MgmtNameString
    MAX-ACCESS  read-only
    STATUS      current
    DESCRIPTION
        "The management name of the interface,
        for example 'muxi:1:2:1', where the first number
        indicates sub-rack, the second slot number and
        the third is the port number.

"
    ::= { muxIfEntry 2 }

muxIfDescr OBJECT-TYPE
    SYNTAX      DisplayString
    MAX-ACCESS  read-write
    STATUS      current
    DESCRIPTION
        "User configurable label.

"
    DEFVAL { "" }
    ::= { muxIfEntry 3 }

muxIfSubrack OBJECT-TYPE
    SYNTAX      SubrackNumber
    MAX-ACCESS  read-only
    STATUS      current
    DESCRIPTION
        "The number of the subrack where the interface
        is located.

"
    ::= { muxIfEntry 4 }

muxIfSlot OBJECT-TYPE
    SYNTAX      SlotNumber
    MAX-ACCESS  read-only
    STATUS      current
    DESCRIPTION
        "The number of the slot where the interface is
        located.

"
    ::= { muxIfEntry 5 }

muxIfTxPort OBJECT-TYPE
    SYNTAX      PortNumber
    MAX-ACCESS  read-only
    STATUS      current
    DESCRIPTION
        "The number of the port where the TX-side of the
        interface is located.

"
    ::= { muxIfEntry 6 }

muxIfRxPort OBJECT-TYPE
    SYNTAX      PortNumber
    MAX-ACCESS  read-only
    STATUS      current
    DESCRIPTION
        "The number of the port where the RX-side of
        the interface is located.

"
    ::= { muxIfEntry 7 }

muxIfInvPhysIndexOrZero OBJECT-TYPE
    SYNTAX      Unsigned32 (0..2147483647)
    MAX-ACCESS  read-only
    STATUS      current
    DESCRIPTION
        "The row in the invPhysTable for this interface.
        Set to 0 if not known.

"
    ::= { muxIfEntry 8 }

muxIfPowerLevel OBJECT-TYPE
    SYNTAX      Integer32
    MAX-ACCESS  read-only
    STATUS      current
    DESCRIPTION
        "The received power level in units of 0.1 dBm.

"
    ::= { muxIfEntry 9 }

muxIfPowerLevelHighThreshold OBJECT-TYPE
    SYNTAX      Integer32 (-200..-10)
    MAX-ACCESS  read-write
    STATUS      current
    DESCRIPTION
        "The upper threshold for received power level in
        units of 0.1 dBm.

"
    DEFVAL { -50 }
    ::= { muxIfEntry 10 }

muxIfPowerLevelLowThreshold OBJECT-TYPE
    SYNTAX      Integer32 (-200..-10)
    MAX-ACCESS  read-write
    STATUS      current
    DESCRIPTION
        "The lower threshold for received power level in
        units of 0.1 dBm.

"
    DEFVAL { -160 }
    ::= { muxIfEntry 11 }

muxIfAdminStatus OBJECT-TYPE
    SYNTAX      BoardOrInterfaceAdminStatus
    MAX-ACCESS  read-write
    STATUS      current
    DESCRIPTION
        "The administrative state for the interface.

        down - The interface should be inactive.

        service - The interface is activated but alarms
        are suppressed. Intended for use during service
        or re-configuration. When service is concluded
        adminStatus should be set to 'up' again.

        up - The interface should be activated when
        it becomes available. Alarms are not suppressed.

        This attribute can be written via SNMP.
"
    DEFVAL { up }
    ::= { muxIfEntry 12 }

muxIfOperStatus OBJECT-TYPE
    SYNTAX      BoardOrInterfaceOperStatus
    MAX-ACCESS  read-only
    STATUS      current
    DESCRIPTION
        "The operational state for the interface.

        notPresent - The physical resources are not
        available.

        down - The interface is de-activated or the are
        faults preventing it from going to the
        'up'-state.

        up - The interface is operational.

"
    DEFVAL { notPresent }
    ::= { muxIfEntry 13 }

muxIfLossOfSignal OBJECT-TYPE
    SYNTAX      FaultStatus
    MAX-ACCESS  read-only
    STATUS      current
    DESCRIPTION
        "Loss of signal.
        Applicable for all signal formats.

        A(ctivation): Active loss of signal HW indication.

        D(e-activation): Inactive loss of signal HW
        indication.

"
    ::= { muxIfEntry 14 }

muxIfReceivedPowerHigh OBJECT-TYPE
    SYNTAX      FaultStatus
    MAX-ACCESS  read-only
    STATUS      current
    DESCRIPTION
        "Received power level is too high.
        Applicable for all signal formats.

        A: The received power level exceeds the
        the built-in overload threshold.

        D: The received power level is 0.5 dB below the
        overload threshold.

"
    ::= { muxIfEntry 15 }

muxIfReceivedPowerLow OBJECT-TYPE
    SYNTAX      FaultStatus
    MAX-ACCESS  read-only
    STATUS      current
    DESCRIPTION
        "Received power level low threshold exceeded.
        Applicable for all signal formats.

        A: The received power level is below the
        associated threshold.

        D: The received power level is 0.5 dB above
        the threshold.

"
    ::= { muxIfEntry 16 }

muxIfBitrateMismatch OBJECT-TYPE
    SYNTAX      FaultStatus
    MAX-ACCESS  read-only
    STATUS      current
    DESCRIPTION
        "Bitrate mismatch (Other).
        Applicable for other signal formats.

        D: The interface is unable to lock to the
        inserted signal.

        D: The interface is able to lock to the
        inserted signal.

"
    ::= { muxIfEntry 17 }

muxIfLaserBias OBJECT-TYPE
    SYNTAX      Unsigned32
    MAX-ACCESS  read-only
    STATUS      current
    DESCRIPTION
        "Measures laser bias current value in tenths
        of mA (0.1 mA).

"
    ::= { muxIfEntry 18 }

muxIfLaserBiasThreshold OBJECT-TYPE
    SYNTAX      Unsigned32 (0..300)
    MAX-ACCESS  read-write
    STATUS      current
    DESCRIPTION
        "Sets the threshold for the laser bias alarm.
        in percentage relative to the value set during
        production. The preset value is 100%.

"
    DEFVAL { 200 }
    ::= { muxIfEntry 19 }

muxIfJ0PathTrace OBJECT-TYPE
    SYNTAX      OCTET STRING (SIZE (1 | 16))
    MAX-ACCESS  read-only
    STATUS      deprecated
    DESCRIPTION
        "Note: This attribute is deprecated!

        The recevied J0 path trace string.
        Applicable for SDH/Sonet signal formats.

"
    ::= { muxIfEntry 20 }

muxIfAlarmIndicationSignal OBJECT-TYPE
    SYNTAX      FaultStatus
    MAX-ACCESS  read-only
    STATUS      current
    DESCRIPTION
        "Alarm indication signal.
        Applicable for SDH/Sonet signal formats.

        A: An 'all ones' SDH signal is detected.

        D: SDH signal recovered.

"
    ::= { muxIfEntry 21 }

muxIfLossOfFrame OBJECT-TYPE
    SYNTAX      FaultStatus
    MAX-ACCESS  read-only
    STATUS      current
    DESCRIPTION
        "Loss of frame.
        Applicable for SDH/Sonet signal formats.

        A: SDH frame can not be located.

        D: SDH frame is located.

"
    ::= { muxIfEntry 22 }

muxIfLaserStatus OBJECT-TYPE
    SYNTAX      INTEGER {
                    off (1),
                    on (2) }
    MAX-ACCESS  read-only
    STATUS      current
    DESCRIPTION
        "The operational state of the TX-side laser.

        off - The laser is turned off.

        on - The laser is turned on.

"
    ::= { muxIfEntry 23 }

muxIfTxDirection OBJECT-TYPE
    SYNTAX      MuxTxDirection
    MAX-ACCESS  read-write
    STATUS      current
    DESCRIPTION
        "The direction of the transmitted signal.

        undefined - Unknown/Dont care

        toWest - The transmitted signal is sent to west.

        toEast - The transmitted signal is sent to east.

"
    ::= { muxIfEntry 24 }

muxIfExpectedTxLambda OBJECT-TYPE
    SYNTAX      LambdaFrequency
    MAX-ACCESS  read-write
    STATUS      current
    DESCRIPTION
        "The expected frequency given in hundreds of
        GHz (0.01 GHz).
        This attribute can be written via SNMP.

"
    DEFVAL { 0 }
    ::= { muxIfEntry 25 }

muxIfTxLambda OBJECT-TYPE
    SYNTAX      LambdaFrequency
    MAX-ACCESS  read-only
    STATUS      current
    DESCRIPTION
        "The transmitted frequency given in hundreds
        of GHz (0.01 GHz).

"
    ::= { muxIfEntry 26 }

muxIfTraceIntrusionMode OBJECT-TYPE
    SYNTAX      INTEGER {
                    disabled (1),
                    enabled (2) }
    MAX-ACCESS  read-only
    STATUS      current
    DESCRIPTION
        "Indicates wether the trace identifier should
        be inserted in the transmitted signal.

        disabled - The trace identifier is taken from
        the recevied signal if possible.

        enabled -  The trace identifier set is inserted in
        the transmitted signal.

"
    ::= { muxIfEntry 27 }

muxIfTraceTransmitted   OBJECT-TYPE
    SYNTAX      DisplayString (SIZE(0..15))
    MAX-ACCESS  read-write
    STATUS      current
    DESCRIPTION
        "The trace identifier to be transmitted from
        this interface.

	Set to empty string for default value:

	<IP address>:<subrack>:<slot>:<port>

	Note that only the last part of the address
	is used.
"
    DEFVAL { "" }
    ::= { muxIfEntry 28 }

muxIfTraceReceived OBJECT-TYPE
    SYNTAX      DisplayString (SIZE(0..15))
    MAX-ACCESS  read-only
    STATUS      current
    DESCRIPTION
        "The received trace identifier for this interface.

"
    ::= { muxIfEntry 29 }

muxIfTraceExpected OBJECT-TYPE
    SYNTAX      DisplayString (SIZE(0..15))
    MAX-ACCESS  read-write
    STATUS      current
    DESCRIPTION
        "Trace identifier used for matching against
        the received trace identifier.

"
    DEFVAL { "" }
    ::= { muxIfEntry 30 }

muxIfTraceAlarmMode OBJECT-TYPE
    SYNTAX      INTEGER {
                    disabled (1),
                    enabled (2) }
    MAX-ACCESS  read-write
    STATUS      current
    DESCRIPTION
        "Controls if the trace identifier mismatch alarm
        should be raised.

        disabled - The alarm is disabled.

        enabled - The alarm is raised if expected trace
        identifier differs from the received trace
        identifier.

"
    DEFVAL { disabled }
    ::= { muxIfEntry 31 }

muxIfTraceMismatch OBJECT-TYPE
    SYNTAX      FaultStatus
    MAX-ACCESS  read-only
    STATUS      current
    DESCRIPTION
        "Indicates if the expected trace identifier
        differs from the received trace identifier.

        A: The received trace identifier differs from
        the expected trace identifier.

        D: The identifiers match.

"
    ::= { muxIfEntry 32 }

muxIfOHTransparency OBJECT-TYPE
    SYNTAX      INTEGER {
                    off (1),
                    on (2) }
    MAX-ACCESS  read-write
    STATUS      current
    DESCRIPTION
        "The 'OH Transparency' setting shall be set to 'off' for
        standard SDH/SONET mode.

        When set to 'on', the following tributary OH-bytes are
        transparently transported:
        E1, E2, F1, D1-D3, D4-D12, K1, K2

        The following are always terminated:
        J0, B1, B2, M1 and S1.

"
   DEFVAL { off }
   ::= { muxIfEntry 33 }

muxIfSuppressRemoteAlarms OBJECT-TYPE
    SYNTAX      INTEGER {
                    disabled (1),
                    enabled (2) }
    MAX-ACCESS  read-write
    STATUS      current
    DESCRIPTION
        "Suppress AIS and RDI in the alarm list. The fault status on
        the port object can, however, be seen.

        disabled - alarms are not suppressed.

        enabled - alarms are suppressed.

"
    DEFVAL { disabled }
    ::= { muxIfEntry 34 }

muxIfHighSpeedMin OBJECT-TYPE
    SYNTAX      Gauge32
    MAX-ACCESS  read-only
    STATUS      current
    DESCRIPTION
        "The minmum speed in units of 1,000,000 bits (Mb)
        per second. If this object reports a value of 'n'
        then the speed of the interface is somewhere in
        the range of 'n-500,000' to 'n+499,999'.

"
    ::= { muxIfEntry 35 }

muxIfHighSpeedMax OBJECT-TYPE
    SYNTAX      Gauge32
    MAX-ACCESS  read-only
    STATUS      current
    DESCRIPTION
        "The maximum speed in units of 1,000,000 bits per
        second. If this object reports a value of 'n'
        then the speed of the interface is somewhere in
        the range of 'n-500,000' to 'n+499,999'.

"
    ::= { muxIfEntry 36 }

muxIfTrxCodeMismatch OBJECT-TYPE
    SYNTAX      FaultStatus
    MAX-ACCESS  read-only
    STATUS      current
    DESCRIPTION
        "The inserted transceiver does not have a legal
        manufacturer code.

        A: A transceiver with illegal code is inserted.

        D: The transceiver with illegal code is removed.

"
    ::= { muxIfEntry 37 }

muxIfTrxBitrateUnavailable OBJECT-TYPE
    SYNTAX      FaultStatus
    MAX-ACCESS  read-only
    STATUS      current
    DESCRIPTION
        "The inserted transceiver does not support the requested
        bit rate.

        A: A transceiver with other supported bit rate than
           the requested bit rate is inserted.

        D: The transceiver with the non-requested bit rate is
           removed, or the object is reconfigured.

"
    ::= { muxIfEntry 38 }

muxIfTrxMissing OBJECT-TYPE
    SYNTAX      FaultStatus
    MAX-ACCESS  read-only
    STATUS      current
    DESCRIPTION
        "An expected transceiver is missing.

        A: An expected transceiver is missing.

        D: The missing transceiver is inserted.

"
    ::= { muxIfEntry 39 }

muxIfTrxClass OBJECT-TYPE
    SYNTAX      DisplayString
    MAX-ACCESS  read-only
    STATUS      current
    DESCRIPTION
        "String that describes the transceiver class.

"
    DEFVAL { "" }
    ::= { muxIfEntry 40 }

muxIfTransmitterFailed OBJECT-TYPE
    SYNTAX      FaultStatus
    MAX-ACCESS  read-only
    STATUS      current
    DESCRIPTION
        "The transceiver HW has detected a failure
         in the transmitter part.

        A: The transmitter has failed

        D: The transmitter is OK again

"
    ::= { muxIfEntry 41 }

muxIfUnexpectedFrequency OBJECT-TYPE
    SYNTAX      FaultStatus
    MAX-ACCESS  read-only
    STATUS      current
    DESCRIPTION
        "The actual frequency does not match the
        pre-configured frequency.

        A pre-configured frequency of '0' matches
        all actual frequencies.

        A: The configured frequency does not match the
        actual frequency.

        D: The configured frequency matches the actual
        frequency.

"
    ::= { muxIfEntry 42 }

muxIfIllegalFrequency OBJECT-TYPE
    SYNTAX      FaultStatus
    MAX-ACCESS  read-only
    STATUS      current
    DESCRIPTION
        "The frequency supported by the transceiver is not
        recognized by the system.

        A: Invalid or unknown frequency information is
           detected in the (pluggable) transceiver or
           board production data.

        D: The (pluggable) transceiver or board is
           replaced.

"
    ::= { muxIfEntry 43 }

muxIfReceiverSensitivity OBJECT-TYPE
    SYNTAX      Integer32
    MAX-ACCESS  read-only
    STATUS      current
    DESCRIPTION
        "The lowest power that the receiver is guaranteed
        to handle, in units of 0.1 dBm.

"
    ::= { muxIfEntry 44 }

muxIfPowerLevelLowRelativeThreshold OBJECT-TYPE
    SYNTAX      Integer32 (-50..100)
    MAX-ACCESS  read-write
    STATUS      current
    DESCRIPTION
        "The lower threshold for received power level in
        units of 0.1 dB, relative to the receiver
        sensitivity.

"
    DEFVAL { 30 }
    ::= { muxIfEntry 45 }

muxIfObjectProperty OBJECT-TYPE
    SYNTAX      ObjectProperty
    MAX-ACCESS  read-only
    STATUS      current
    DESCRIPTION
        "Property mask.

"
    ::= { muxIfEntry 46 }

muxIfTxPowerLevel OBJECT-TYPE
    SYNTAX      Integer32
    MAX-ACCESS  read-only
    STATUS      current
    DESCRIPTION
        "The transmitted power level in units of 0.1 dBm.

"
    ::= { muxIfEntry 47 }

muxIfLaserTempActual OBJECT-TYPE
    SYNTAX      Integer32
    MAX-ACCESS  read-only
    STATUS      current
    DESCRIPTION
        "The actual laser temperature in units of
        0.1 degrees centigrade.

"
    ::= { muxIfEntry 48 }


-- ----------------------------------------------------
-- MUX VC-4 objects
-- ----------------------------------------------------

muxVc4Table  OBJECT-TYPE
    SYNTAX      SEQUENCE OF MuxVc4Entry
    MAX-ACCESS  not-accessible
    STATUS      current
    DESCRIPTION
        "The interface list."
    ::= { muxVc4List 1 }

muxVc4Entry OBJECT-TYPE
    SYNTAX      MuxVc4Entry
    MAX-ACCESS  not-accessible
    STATUS      current
    DESCRIPTION
        "An entry in the interface list.

"
    INDEX { muxVc4Index }
    ::= { muxVc4Table 1 }

MuxVc4Entry ::=
    SEQUENCE {
        muxVc4Index                     Unsigned32,
        muxVc4Name                      MgmtNameString,
        muxVc4Descr                     DisplayString,
        muxVc4Subrack                   SubrackNumber,
        muxVc4Slot                      SlotNumber,
        muxVc4TxPort                    PortNumber,
        muxVc4RxPort                    PortNumber,
        muxVc4Vc4                       Unsigned32,
        muxVc4Mode                      INTEGER,
        muxVc4ClientDropPort            Unsigned32,
        muxVc4TxDirection               MuxTxDirection,
        muxVc4ClientAddPort             Unsigned32,
        muxVc4ConnectionMode            INTEGER,
        muxVc4ConnectionStatus          INTEGER,
        muxVc4ConnectionOverview        DisplayString,
        muxVc4ObjectProperty            ObjectProperty,
        muxVc4AuAlarmIndicationSignalW2C INTEGER,
        muxVc4AuLossOfPointerW2C        INTEGER,
        muxVc4RxSignalStatus            INTEGER,
        muxVc4ConcatenationStatus       INTEGER,
        muxVc4PayloadStatus             INTEGER,
        muxVc4AdminStatus               INTEGER }

muxVc4Index OBJECT-TYPE
    SYNTAX      Unsigned32 (1..2147483647)
    MAX-ACCESS  read-only
    STATUS      current
    DESCRIPTION
        "An arbitrary index assigned to each if entry.
"
    ::= { muxVc4Entry 1 }

muxVc4Name OBJECT-TYPE
    SYNTAX      MgmtNameString
    MAX-ACCESS  read-only
    STATUS      current
    DESCRIPTION
        "The management name of the vc4,
        e.g. vc4:1:2:21-22:8 where the first number
        indicates sub-rack, the second slot number and
        the third/forth are the port numbers. The last
        number is the vc4 id within the STM16 frame.

"
    ::= { muxVc4Entry 2 }

muxVc4Descr OBJECT-TYPE
    SYNTAX      DisplayString
    MAX-ACCESS  read-write
    STATUS      current
    DESCRIPTION
        "User configurable label.

"
    DEFVAL { "" }
    ::= { muxVc4Entry 3 }

muxVc4Subrack OBJECT-TYPE
    SYNTAX      SubrackNumber
    MAX-ACCESS  read-only
    STATUS      current
    DESCRIPTION
        "The number of the subrack where the vc4 is
        located.

"
    ::= { muxVc4Entry 4 }

muxVc4Slot OBJECT-TYPE
    SYNTAX      SlotNumber
    MAX-ACCESS  read-only
    STATUS      current
    DESCRIPTION
        "The number of the slot where the vc4 is
        located.

"
    ::= { muxVc4Entry 5 }

muxVc4TxPort OBJECT-TYPE
    SYNTAX      PortNumber
    MAX-ACCESS  read-only
    STATUS      current
    DESCRIPTION
        "The number of the port where the TX-side of the
        vc4 is located.

"
    ::= { muxVc4Entry 6 }

muxVc4RxPort OBJECT-TYPE
    SYNTAX      PortNumber
    MAX-ACCESS  read-only
    STATUS      current
    DESCRIPTION
        "The number of the port where the RX-side of the
        vc4 is located.

"
    ::= { muxVc4Entry 7 }

muxVc4Vc4 OBJECT-TYPE
    SYNTAX      Unsigned32 (1..16)
    MAX-ACCESS  read-only
    STATUS      current
    DESCRIPTION
        "The id of the vc4 within the STM16 frame.

"
    ::= { muxVc4Entry 8 }

muxVc4Mode OBJECT-TYPE
    SYNTAX      INTEGER {
                    addDrop (1),
                    passThrough (2) }
    MAX-ACCESS  read-only
    STATUS      current
    DESCRIPTION
        "What to do with the vc4.

        addDrop - Add/drop it from/to the ports specified
        by muxVc4ClientDropPort and muxVc4ClientAddPort.

        passThrough - Pass-through.

"
    ::= { muxVc4Entry 9 }

muxVc4ClientDropPort OBJECT-TYPE
    SYNTAX      Unsigned32 (0..20)
    MAX-ACCESS  read-only
    STATUS      current
    DESCRIPTION
        "The connected drop port, if muxVc4Mode is
        set to 'addDrop'.

        0 is undefined (used at pass-through).

        For mxp028:

        1 - first SMT4 i/f
        3 - second STM4 i/f
        5 - first STM1 i/f
        ...
        19 - 8th STM1 i/f

        For mxp004:

        1 - first STM1 i/f
        ...
        7 - 4th STM1 i/f

"
    DEFVAL { 0 }
    ::= { muxVc4Entry 10 }

muxVc4TxDirection OBJECT-TYPE
    SYNTAX      MuxTxDirection
    MAX-ACCESS  read-only
    STATUS      current
    DESCRIPTION
        "The direction of the transmitted signal.

        undefined - Unknown/Dont care

        toWest - The transmitted signal is sent to west.

        toEast - The transmitted signal is sent to east.

"
    ::= { muxVc4Entry 11 }

muxVc4ClientAddPort OBJECT-TYPE
    SYNTAX      Unsigned32 (0..20)
    MAX-ACCESS  read-only
    STATUS      current
    DESCRIPTION
        "The connected add port, if muxVc4Mode is set
        to 'addDrop'.

        0 is undefined (used at pass-through)

        For mxp028:

        2 - first SMT4 i/f
        4 - second STM4 i/f
        6 - first STM1 i/f
        ...
        20 - 8th STM1 i/f

        For mxp004:

        2 - first STM1 i/f
        ...
        8 - 4th STM1 i/f

"
    ::= { muxVc4Entry 12 }

muxVc4ConnectionMode OBJECT-TYPE
    SYNTAX      INTEGER {
                    unused (1),
                    ringUsed (2),
                    nodeUsed (3) }
    MAX-ACCESS  read-write
    STATUS      deprecated
    DESCRIPTION
        "Describes how the VC is used in the ring and
        the node.

         unused - The VC4 is not used in the ring.

         ringUsed - the VC4 is used in the ring,
         but is not allowed to add/drop in this node.

         nodeUsed - the VC4 is allowed to drop in this
         node.

"
    DEFVAL { unused }
    ::= { muxVc4Entry 13 }

muxVc4ConnectionStatus OBJECT-TYPE
    SYNTAX      INTEGER {
                    addDrop (1),
                    passThrough (2),
                    unconnected (3) }
    MAX-ACCESS  read-only
    STATUS      deprecated
    DESCRIPTION
        "How the VC4 is handled.

        addDrop - Add/drop it from/to the ports specified
        by muxVc4ClientDropPort and muxVc4ClientAddPort.

        passThrough - Pass-through the node.

        unconnected - The vc4 is not connected in the
        ring.

"
    ::= { muxVc4Entry 14 }

muxVc4ConnectionOverview OBJECT-TYPE
    SYNTAX      DisplayString
    MAX-ACCESS  read-only
    STATUS      current
    DESCRIPTION
        "What to do with the vc4.

        addDrop - Add/drop it from/to the ports specified
        by muxVc4ClientDropPort and muxVc4ClientAddPort.

        passThrough - Pass-through the node.

"
    ::= { muxVc4Entry 15 }

muxVc4ObjectProperty OBJECT-TYPE
    SYNTAX      ObjectProperty
    MAX-ACCESS  read-only
    STATUS      current
    DESCRIPTION
        "Property mask.

"
    ::= { muxVc4Entry 16 }

muxVc4AuAlarmIndicationSignalW2C OBJECT-TYPE
    SYNTAX      INTEGER {
                    ok (1),
                    alarm (2) }
    MAX-ACCESS  read-only
    STATUS      current
    DESCRIPTION
        "Alarm indication signal (AIS) on the trunk-side.
        Applicable for SDH/Sonet signal formats.

        A: An 'all ones' SDH signal is detected.

        D: SDH signal recovered.
"
    ::= { muxVc4Entry 17 }

muxVc4AuLossOfPointerW2C OBJECT-TYPE
    SYNTAX      INTEGER {
                    ok (1),
                    alarm (2) }
    MAX-ACCESS  read-only
    STATUS      current
    DESCRIPTION
        "Loss of pointer detected on the trunk-side.
        Applicable for SDH/Sonet signal formats.

        A: A loss of pointer is detected.

        D: SDH signal recovered.

"
    ::= { muxVc4Entry 18 }

muxVc4RxSignalStatus OBJECT-TYPE
    SYNTAX      INTEGER {
                        down (1),
                        degraded (2),
                        up (3) }
    MAX-ACCESS  read-only
    STATUS      current
    DESCRIPTION
        "The operational state for incoming (RX) signal
        of the interface.

        down - A fault that would lead to a protection
        switch has occurred.

        degraded - The signal quality is impaired.

        up - The signal is OK.

"
    ::= { muxVc4Entry 19 }

muxVc4ConcatenationStatus OBJECT-TYPE
    SYNTAX      INTEGER {
                        on (1),
                        off (2) }
    MAX-ACCESS  read-only
    STATUS      current
    DESCRIPTION
        "Describes if the VC4s are concatenated.

        on - Concatenation is used.

        off - No concatenation is used.

"
    ::= { muxVc4Entry 20 }

muxVc4PayloadStatus OBJECT-TYPE
    SYNTAX      INTEGER {
                        equipped (1),
                        unequipped (2) }
    MAX-ACCESS  read-only
    STATUS      current
    DESCRIPTION
        "Describes if the VC4 contains payload.

        equipped - VC4 contains payload.

        unequipped - No payload in VC4.

"
    ::= { muxVc4Entry 21 }

muxVc4AdminStatus OBJECT-TYPE
    SYNTAX  INTEGER {
        down (1),
        up (2) }
    MAX-ACCESS  read-write
    STATUS      current
    DESCRIPTION
        "The administrative state for the interface.

        down - The interface should be inactive.

        up - The interface should be activated when
        it becomes available. Alarms are not suppressed.

"
    DEFVAL { up }
    ::= { muxVc4Entry 22 }

-- ----------------------------------------------------
-- Notifications
-- ----------------------------------------------------

-- n/a


-- ----------------------------------------------------
-- Object and event groups
-- ----------------------------------------------------

muxGeneralGroup OBJECT-GROUP
    OBJECTS {
        muxGeneralLastChangeTime }
    STATUS      current
    DESCRIPTION
        "The general objects."
    ::= { lumMuxGroups 1 }


muxIfGroup OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow }
    STATUS      current
    DESCRIPTION
        "The general objects."
    ::= { lumMuxGroups 2 }

muxIfGroupV2 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfJ0PathTrace }
    STATUS      deprecated
    DESCRIPTION
        "The general objects."
    ::= { lumMuxGroups 3 }

muxIfGroupV3 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfJ0PathTrace,
        muxIfAlarmIndicationSignal,
        muxIfLossOfFrame }
    STATUS      deprecated
    DESCRIPTION
        "The mux trunk interface objects V3."
    ::= { lumMuxGroups 4 }

muxIfGroupV4 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfJ0PathTrace,
        muxIfAlarmIndicationSignal,
        muxIfLossOfFrame,
        muxIfLaserStatus }
    STATUS      deprecated
    DESCRIPTION
        "The mux trunk interface objects V4."
    ::= { lumMuxGroups 5 }

muxGeneralGroupV2 OBJECT-GROUP
    OBJECTS {
        muxGeneralLastChangeTime,
        muxGeneralStateLastChangeTime }
    STATUS      deprecated
    DESCRIPTION
        "The general objects."
    ::= { lumMuxGroups 6 }

muxVc4Group OBJECT-GROUP
    OBJECTS {
        muxVc4Index,
        muxVc4Name,
        muxVc4Descr,
        muxVc4Subrack,
        muxVc4Slot,
        muxVc4TxPort,
        muxVc4RxPort,
        muxVc4Vc4,
        muxVc4Mode,
        muxVc4ClientDropPort }
    STATUS      deprecated
    DESCRIPTION
        "The vc4 objects."
    ::= { lumMuxGroups 7 }

muxIfGroupV5 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfJ0PathTrace,
        muxIfAlarmIndicationSignal,
        muxIfLossOfFrame,
        muxIfLaserStatus,
        muxIfTxDirection }
    STATUS      deprecated
    DESCRIPTION
        "The mux trunk interface objects V5."
    ::= { lumMuxGroups 8 }

muxVc4GroupV2 OBJECT-GROUP
    OBJECTS {
        muxVc4Index,
        muxVc4Name,
        muxVc4Descr,
        muxVc4Subrack,
        muxVc4Slot,
        muxVc4TxPort,
        muxVc4RxPort,
        muxVc4Vc4,
        muxVc4Mode,
        muxVc4ClientDropPort,
        muxVc4TxDirection,
        muxVc4ClientAddPort }
    STATUS      deprecated
    DESCRIPTION
        "The vc4 objects."
    ::= { lumMuxGroups 9 }

muxIfGroupV6 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfJ0PathTrace,
        muxIfAlarmIndicationSignal,
        muxIfLossOfFrame,
        muxIfLaserStatus,
        muxIfTxDirection,
        muxIfExpectedTxLambda,
        muxIfTxLambda }
    STATUS      deprecated
    DESCRIPTION
        "The mux trunk interface objects V6."
    ::= { lumMuxGroups 10 }

muxIfGroupV7 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfJ0PathTrace,
        muxIfAlarmIndicationSignal,
        muxIfLossOfFrame,
        muxIfLaserStatus,
        muxIfTxDirection,
        muxIfExpectedTxLambda,
        muxIfTxLambda,
        muxIfTraceIntrusionMode,
        muxIfTraceTransmitted,
        muxIfTraceReceived,
        muxIfTraceExpected,
        muxIfTraceAlarmMode,
        muxIfTraceMismatch }
    STATUS      deprecated
    DESCRIPTION
        "The mux trunk interface objects V7."
    ::= { lumMuxGroups 11 }

muxIfGroupV8 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfJ0PathTrace,
        muxIfAlarmIndicationSignal,
        muxIfLossOfFrame,
        muxIfLaserStatus,
        muxIfTxDirection,
        muxIfExpectedTxLambda,
        muxIfTxLambda,
        muxIfTraceIntrusionMode,
        muxIfTraceTransmitted,
        muxIfTraceReceived,
        muxIfTraceExpected,
        muxIfTraceAlarmMode,
        muxIfTraceMismatch }
    STATUS      deprecated
    DESCRIPTION
        "The mux trunk interface objects V8."
    ::= { lumMuxGroups 12 }


muxVc4GroupV3 OBJECT-GROUP
    OBJECTS {
        muxVc4Index,
        muxVc4Name,
        muxVc4Descr,
        muxVc4Subrack,
        muxVc4Slot,
        muxVc4TxPort,
        muxVc4RxPort,
        muxVc4Vc4,
        muxVc4Mode,
        muxVc4ClientDropPort,
        muxVc4TxDirection,
        muxVc4ClientAddPort,
        muxVc4ConnectionMode,
        muxVc4ConnectionStatus }
    STATUS      deprecated
    DESCRIPTION
        "The vc4 objects."
    ::= { lumMuxGroups 13 }

muxVc4GroupV4 OBJECT-GROUP
    OBJECTS {
        muxVc4Index,
        muxVc4Name,
        muxVc4Descr,
        muxVc4Subrack,
        muxVc4Slot,
        muxVc4TxPort,
        muxVc4RxPort,
        muxVc4Vc4,
        muxVc4ClientDropPort,
        muxVc4TxDirection,
        muxVc4ClientAddPort,
        muxVc4ConnectionMode,
        muxVc4ConnectionStatus,
        muxVc4ConnectionOverview }
    STATUS      deprecated
    DESCRIPTION
        "The vc4 objects."
    ::= { lumMuxGroups 14 }

muxVc4GroupV5 OBJECT-GROUP
    OBJECTS {
        muxVc4Index,
        muxVc4Name,
        muxVc4Descr,
        muxVc4Subrack,
        muxVc4Slot,
        muxVc4TxPort,
        muxVc4RxPort,
        muxVc4Vc4,
        muxVc4ClientDropPort,
        muxVc4TxDirection,
        muxVc4ClientAddPort,
        muxVc4ConnectionOverview }
    STATUS      deprecated
    DESCRIPTION
        "The vc4 objects."
    ::= { lumMuxGroups 15 }

muxIfGroupV9 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfJ0PathTrace,
        muxIfAlarmIndicationSignal,
        muxIfLossOfFrame,
        muxIfLaserStatus,
        muxIfTxDirection,
        muxIfExpectedTxLambda,
        muxIfTxLambda,
        muxIfTraceIntrusionMode,
        muxIfTraceTransmitted,
        muxIfTraceReceived,
        muxIfTraceExpected,
        muxIfTraceAlarmMode,
        muxIfTraceMismatch,
        muxIfSuppressRemoteAlarms }
    STATUS      deprecated
    DESCRIPTION
        "The mux trunk interface objects V9."
    ::= { lumMuxGroups 16 }

muxIfGroupV10 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfAlarmIndicationSignal,
        muxIfLossOfFrame,
        muxIfLaserStatus,
        muxIfTxDirection,
        muxIfExpectedTxLambda,
        muxIfTxLambda,
        muxIfTraceIntrusionMode,
        muxIfTraceTransmitted,
        muxIfTraceReceived,
        muxIfTraceExpected,
        muxIfTraceAlarmMode,
        muxIfTraceMismatch,
        muxIfOHTransparency,
        muxIfSuppressRemoteAlarms,
        muxIfHighSpeedMin,
        muxIfHighSpeedMax,
        muxIfTrxCodeMismatch,
        muxIfTrxBitrateUnavailable,
        muxIfTrxMissing,
        muxIfTrxClass,
        muxIfTransmitterFailed }
    STATUS      deprecated
    DESCRIPTION
        "The mux trunk interface objects V10."
    ::= { lumMuxGroups 17 }

muxIfGroupV11 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfAlarmIndicationSignal,
        muxIfLossOfFrame,
        muxIfLaserStatus,
        muxIfTxDirection,
        muxIfExpectedTxLambda,
        muxIfTxLambda,
        muxIfTraceIntrusionMode,
        muxIfTraceTransmitted,
        muxIfTraceReceived,
        muxIfTraceExpected,
        muxIfTraceAlarmMode,
        muxIfTraceMismatch,
        muxIfOHTransparency,
        muxIfSuppressRemoteAlarms,
        muxIfHighSpeedMin,
        muxIfHighSpeedMax,
        muxIfTrxCodeMismatch,
        muxIfTrxBitrateUnavailable,
        muxIfTrxMissing,
        muxIfTrxClass,
        muxIfTransmitterFailed,
        -- muxIfUnexpectedTxLambda,
        muxIfIllegalFrequency,
        muxIfReceiverSensitivity,
        muxIfPowerLevelLowRelativeThreshold }
    STATUS      deprecated
    DESCRIPTION
        "The mux trunk interface objects V11. (2.2)"
    ::= { lumMuxGroups 18 }

muxGeneralGroupV3 OBJECT-GROUP
    OBJECTS {
        muxGeneralLastChangeTime,
        muxGeneralStateLastChangeTime,
        muxGeneralMuxIfTableSize,
        muxGeneralMuxVc4TableSize }
    STATUS      current
    DESCRIPTION
        "The general objects."
    ::= { lumMuxGroups 19 }

muxIfGroupV12 OBJECT-GROUP
    OBJECTS {
        muxIfIndex,
        muxIfName,
        muxIfDescr,
        muxIfSubrack,
        muxIfSlot,
        muxIfTxPort,
        muxIfRxPort,
        muxIfInvPhysIndexOrZero,
        muxIfPowerLevel,
        muxIfPowerLevelHighThreshold,
        muxIfPowerLevelLowThreshold,
        muxIfAdminStatus,
        muxIfOperStatus,
        muxIfLossOfSignal,
        muxIfReceivedPowerHigh,
        muxIfReceivedPowerLow,
        muxIfBitrateMismatch,
        muxIfLaserBias,
        muxIfLaserBiasThreshold,
        muxIfAlarmIndicationSignal,
        muxIfLossOfFrame,
        muxIfLaserStatus,
        muxIfTxDirection,
        muxIfExpectedTxLambda,
        muxIfTxLambda,
        muxIfTraceIntrusionMode,
        muxIfTraceTransmitted,
        muxIfTraceReceived,
        muxIfTraceExpected,
        muxIfTraceAlarmMode,
        muxIfTraceMismatch,
        muxIfOHTransparency,
        muxIfSuppressRemoteAlarms,
        muxIfHighSpeedMin,
        muxIfHighSpeedMax,
        muxIfTrxCodeMismatch,
        muxIfTrxBitrateUnavailable,
        muxIfTrxMissing,
        muxIfTrxClass,
        muxIfTransmitterFailed,
	muxIfUnexpectedFrequency,
        muxIfIllegalFrequency,
        muxIfReceiverSensitivity,
        muxIfPowerLevelLowRelativeThreshold,
        muxIfObjectProperty,
        muxIfTxPowerLevel,
        muxIfLaserTempActual }
    STATUS      current
    DESCRIPTION
        "The mux trunk interface objects V12. (4.0)"
    ::= { lumMuxGroups 20 }

muxVc4GroupV6 OBJECT-GROUP
    OBJECTS {
        muxVc4Index,
        muxVc4Name,
        muxVc4Descr,
        muxVc4Subrack,
        muxVc4Slot,
        muxVc4TxPort,
        muxVc4RxPort,
        muxVc4Vc4,
        muxVc4ClientDropPort,
        muxVc4TxDirection,
        muxVc4ClientAddPort,
        muxVc4ConnectionOverview,
        muxVc4ObjectProperty }
    STATUS      deprecated
    DESCRIPTION
        "The vc4 objects (4.0)."
    ::= { lumMuxGroups 21 }

muxVc4GroupV7 OBJECT-GROUP
    OBJECTS {
        muxVc4Index,
        muxVc4Name,
        muxVc4Descr,
        muxVc4Subrack,
        muxVc4Slot,
        muxVc4TxPort,
        muxVc4RxPort,
        muxVc4Vc4,
        muxVc4ClientDropPort,
        muxVc4TxDirection,
        muxVc4ClientAddPort,
        muxVc4ConnectionOverview,
        muxVc4ObjectProperty,
        muxVc4AuAlarmIndicationSignalW2C,
        muxVc4AuLossOfPointerW2C,
        muxVc4RxSignalStatus,
        muxVc4ConcatenationStatus,
        muxVc4PayloadStatus,
        muxVc4AdminStatus }
    STATUS      current
    DESCRIPTION
        "The vc4 objects (8.0)."
    ::= { lumMuxGroups 22 }


-- ----------------------------------------------------
-- Compliance
-- ----------------------------------------------------

lumMuxBasicComplV1 MODULE-COMPLIANCE
    STATUS      current
    DESCRIPTION
        "Basic implementation requirements for the muxponder MIB."
    MODULE
        MANDATORY-GROUPS {
            muxGeneralGroup,
            muxIfGroup }
    ::= { lumMuxCompl 1 }

lumMuxBasicComplV2 MODULE-COMPLIANCE
    STATUS      deprecated
    DESCRIPTION
        "Basic implementation requirements for the muxponder MIB V2."
    MODULE
        MANDATORY-GROUPS {
            muxGeneralGroup,
            muxIfGroupV2 }
    ::= { lumMuxCompl 2 }

lumMuxBasicComplV3 MODULE-COMPLIANCE
    STATUS      deprecated
    DESCRIPTION
        "Basic implementation requirements for the muxponder MIB V3."
    MODULE
        MANDATORY-GROUPS {
            muxGeneralGroup,
            muxIfGroupV3 }
    ::= { lumMuxCompl 3 }

lumMuxBasicComplV4 MODULE-COMPLIANCE
    STATUS      deprecated
    DESCRIPTION
        "Basic implementation requirements for the muxponder MIB V4."
    MODULE
        MANDATORY-GROUPS {
            muxGeneralGroup,
            muxIfGroupV4 }
    ::= { lumMuxCompl 4 }

lumMuxBasicComplV5 MODULE-COMPLIANCE
    STATUS      deprecated
    DESCRIPTION
        "Basic implementation requirements for the muxponder MIB V5."
    MODULE
        MANDATORY-GROUPS {
            muxGeneralGroupV2,
            muxIfGroupV4 }
    ::= { lumMuxCompl 5 }

lumMuxBasicComplV6 MODULE-COMPLIANCE
    STATUS      deprecated
    DESCRIPTION
        "Basic implementation requirements for the muxponder MIB V6."
    MODULE
        MANDATORY-GROUPS {
            muxGeneralGroupV2,
            muxIfGroupV4,
            muxVc4Group }
    ::= { lumMuxCompl 6 }

lumMuxBasicComplV7 MODULE-COMPLIANCE
    STATUS      deprecated
    DESCRIPTION
        "Basic implementation requirements for the muxponder MIB V7."
    MODULE
        MANDATORY-GROUPS {
            muxGeneralGroupV2,
            muxIfGroupV5,
            muxVc4Group }
    ::= { lumMuxCompl 7 }

lumMuxBasicComplV8 MODULE-COMPLIANCE
    STATUS      deprecated
    DESCRIPTION
        "Basic implementation requirements for the muxponder MIB V8."
    MODULE
        MANDATORY-GROUPS {
            muxGeneralGroupV2,
            muxIfGroupV5,
            muxVc4GroupV2 }
    ::= { lumMuxCompl 8 }

lumMuxBasicComplV9 MODULE-COMPLIANCE
    STATUS      deprecated
    DESCRIPTION
        "Basic implementation requirements for the muxponder MIB V9."
    MODULE
        MANDATORY-GROUPS {
            muxGeneralGroupV2,
            muxIfGroupV6,
            muxVc4GroupV2 }
    ::= { lumMuxCompl 9 }

lumMuxBasicComplV10 MODULE-COMPLIANCE
    STATUS      deprecated
    DESCRIPTION
        "Basic implementation requirements for the muxponder MIB V10."
    MODULE
        MANDATORY-GROUPS {
            muxGeneralGroupV2,
            muxIfGroupV7,
            muxVc4GroupV2 }
    ::= { lumMuxCompl 10 }

lumMuxBasicComplV11 MODULE-COMPLIANCE
    STATUS      deprecated
    DESCRIPTION
        "Basic implementation requirements for the muxponder MIB V11."
    MODULE
        MANDATORY-GROUPS {
            muxGeneralGroupV2,
            muxIfGroupV8,
            muxVc4GroupV2 }
    ::= { lumMuxCompl 11 }

lumMuxBasicComplV12 MODULE-COMPLIANCE
    STATUS      deprecated
    DESCRIPTION
        "Basic implementation requirements for the muxponder MIB V12."
    MODULE
        MANDATORY-GROUPS {
            muxGeneralGroupV2,
            muxIfGroupV8,
            muxVc4GroupV3 }
    ::= { lumMuxCompl 12 }

lumMuxBasicComplV13 MODULE-COMPLIANCE
    STATUS      deprecated
    DESCRIPTION
        "Basic implementation requirements for the muxponder MIB V13."
    MODULE
        MANDATORY-GROUPS {
            muxGeneralGroupV2,
            muxIfGroupV8,
            muxVc4GroupV4 }
    ::= { lumMuxCompl 13 }

lumMuxBasicComplV14 MODULE-COMPLIANCE
    STATUS      deprecated
    DESCRIPTION
        "Basic implementation requirements for the muxponder MIB V14."
    MODULE
        MANDATORY-GROUPS {
            muxGeneralGroupV2,
            muxIfGroupV8,
            muxVc4GroupV5 }
    ::= { lumMuxCompl 14 }

lumMuxBasicComplV15 MODULE-COMPLIANCE
    STATUS      deprecated
    DESCRIPTION
        "Basic implementation requirements for the muxponder MIB V15."
    MODULE
        MANDATORY-GROUPS {
            muxGeneralGroupV2,
            muxIfGroupV9,
            muxVc4GroupV5 }
    ::= { lumMuxCompl 15 }

lumMuxBasicComplV16 MODULE-COMPLIANCE
    STATUS      deprecated
    DESCRIPTION
        "Basic implementation requirements for the muxponder MIB V16."
    MODULE
        MANDATORY-GROUPS {
            muxGeneralGroupV2,
            muxIfGroupV10,
            muxVc4GroupV5 }
    ::= { lumMuxCompl 16 }

lumMuxBasicComplV17 MODULE-COMPLIANCE
    STATUS     deprecated
    DESCRIPTION
        "Basic implementation requirements for the muxponder MIB V17. (2.2)"
    MODULE
        MANDATORY-GROUPS {
            muxGeneralGroupV2,
            muxIfGroupV11,
            muxVc4GroupV5 }
    ::= { lumMuxCompl 17 }

lumMuxBasicComplV18 MODULE-COMPLIANCE
    STATUS      deprecated
    DESCRIPTION
        "Basic implementation requirements for the muxponder MIB V18. (3.1)"
    MODULE
        MANDATORY-GROUPS {
            muxGeneralGroupV3,
            muxIfGroupV11,
            muxVc4GroupV5 }
    ::= { lumMuxCompl 18 }

lumMuxBasicComplV19 MODULE-COMPLIANCE
    STATUS      deprecated
    DESCRIPTION
        "Basic implementation requirements for the muxponder MIB V19. (4.0)"
    MODULE
        MANDATORY-GROUPS {
            muxGeneralGroupV3,
            muxIfGroupV12,
            muxVc4GroupV6 }
    ::= { lumMuxCompl 19 }

lumMuxBasicComplV20 MODULE-COMPLIANCE
    STATUS      deprecated
    DESCRIPTION
        "Basic implementation requirements for the muxponder MIB V20. (8.0)"
    MODULE
        MANDATORY-GROUPS {
            muxGeneralGroupV3,
            muxIfGroupV12,
            muxVc4GroupV7 }
    ::= { lumMuxCompl 20 }

lumMuxBasicComplV21 MODULE-COMPLIANCE
    STATUS      current
    DESCRIPTION
        "Basic implementation requirements for the muxponder MIB V21. (17.0)"
    MODULE
        MANDATORY-GROUPS {
            muxGeneralGroupV3,
            muxIfGroupV12,
            muxVc4GroupV7 }
    ::= { lumMuxCompl 21 }

END

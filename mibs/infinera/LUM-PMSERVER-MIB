LUM-PMSERVER-MIB DEFINITIONS ::= BEGIN

IMPORTS
    MODULE-IDENTITY, OBJECT-TYPE, Unsigned32
        FROM SNMPv2-SMI
    OBJECT-GROUP, MODULE-COMPLIANCE
        FROM SNMPv2-CONF
    DateAndTime
        FROM SNMPv2-TC
    lumModules, lumPmServerMIB
        FROM LUM-REG
    FaultStatus
        FROM LUM-TC;

lumPmServerMIBModule MODULE-IDENTITY
    LAST-UPDATED
        "201706150000Z" -- June 15th 2017
    ORGANIZATION
        "Infinera Corporation"
    CONTACT-INFO
        "techsupport@infinera.com"
    DESCRIPTION
        "The PM Server MIB.

        - General

        - PM Server status

"

    REVISION
        "201706150000Z" -- June 15th 2017
    DESCRIPTION
        "Changes made for release r29.0:
         - Changed ORGANIZATION and CONTACT-INFO"
    REVISION
        "201207180000Z" -- July 18th 2012
    DESCRIPTION
        "The initial revision of this module."
    ::= { lumModules 49 }


-- ----------------------------------------------------
-- Conformance area, containing groups and complicance
-- specifications.
-- ----------------------------------------------------

lumPmServerConfs OBJECT IDENTIFIER ::= { lumPmServerMIB 1 }
lumPmServerGroups OBJECT IDENTIFIER ::= { lumPmServerConfs 1 }
lumPmServerCompl OBJECT IDENTIFIER ::= { lumPmServerConfs 2 }


-- ----------------------------------------------------
-- Root for objects in the PM Server MIB
-- ----------------------------------------------------

lumPmServerMIBObjects OBJECT IDENTIFIER ::= { lumPmServerMIB 2 }

-- ----------------------------------------------------
-- This MIB contains the following groups:
-- ----------------------------------------------------

pmServerGeneral OBJECT IDENTIFIER ::= { lumPmServerMIBObjects 1 }
pmServerStatusList OBJECT IDENTIFIER ::= { lumPmServerMIBObjects 2 }

-- ----------------------------------------------------
-- Textual Conventions
-- ----------------------------------------------------

-- n/a

-------------------------------------------------------
-- General group
-- ----------------------------------------------------

pmServerGeneralConfigLastChangeTime OBJECT-TYPE
    SYNTAX      DateAndTime
    MAX-ACCESS  read-only
    STATUS      current
    DESCRIPTION
        "The time when the configuration of the MIB was
        last changed.

"
    ::= { pmServerGeneral 1 }

pmServerGeneralStateLastChangeTime OBJECT-TYPE
    SYNTAX      DateAndTime
    MAX-ACCESS  read-only
    STATUS      current
    DESCRIPTION
        "The time when the state of the MIB was last
        changed.

"
    ::= { pmServerGeneral 2 }

pmServerGeneralStatusTableSize OBJECT-TYPE
    SYNTAX      Unsigned32
    MAX-ACCESS  read-only
    STATUS      current
    DESCRIPTION
        "Size of table.

"
    ::= { pmServerGeneral 3 }

-------------------------------------------------------
-- PM Server status table
-- ----------------------------------------------------

pmServerStatusTable  OBJECT-TYPE
    SYNTAX      SEQUENCE OF PmServerStatusEntry
    MAX-ACCESS  not-accessible
    STATUS      current
    DESCRIPTION
        "The status list."
    ::= { pmServerStatusList 1 }

pmServerStatusEntry OBJECT-TYPE
    SYNTAX      PmServerStatusEntry
    MAX-ACCESS  not-accessible
    STATUS      current
    DESCRIPTION
        "An entry in the status list.

"
    INDEX { pmServerStatusIndex }
    ::= { pmServerStatusTable 1 }

PmServerStatusEntry ::=
    SEQUENCE {
        pmServerStatusIndex			 Unsigned32,
        pmServerStatusFaultyEduReportFilesExist	 FaultStatus }

pmServerStatusIndex OBJECT-TYPE
    SYNTAX      Unsigned32 (1..2147483647)
    MAX-ACCESS  read-only
    STATUS      current
    DESCRIPTION
        "An arbitrary index assigned to each entry.

"
   ::= { pmServerStatusEntry 1 }

pmServerStatusFaultyEduReportFilesExist  OBJECT-TYPE
    SYNTAX      FaultStatus
    MAX-ACCESS  read-only
    STATUS      current
    DESCRIPTION
        "tbd

"
   ::= { pmServerStatusEntry 2 }


-- ----------------------------------------------------
-- Object and event groups
-- ----------------------------------------------------

pmServerGeneralGroup OBJECT-GROUP
    OBJECTS {
        pmServerGeneralConfigLastChangeTime,
        pmServerGeneralStateLastChangeTime,
        pmServerGeneralStatusTableSize }
    STATUS      current
    DESCRIPTION
        "The general objects."
    ::= { lumPmServerGroups 1 }

pmServerStatusGroup OBJECT-GROUP
    OBJECTS {
        pmServerStatusIndex,
        pmServerStatusFaultyEduReportFilesExist }
    STATUS      current
    DESCRIPTION
        "The general objects."
    ::= { lumPmServerGroups 2 }


-- ----------------------------------------------------
-- Compliance
-- ----------------------------------------------------

lumPmServerBasicComplV1 MODULE-COMPLIANCE
    STATUS      current
    DESCRIPTION
        "Basic implementation requirements for the PM Server MIB V1."
    MODULE
        MANDATORY-GROUPS {
            pmServerGeneralGroup,
            pmServerStatusGroup }
    ::= { lumPmServerCompl 1 }



END

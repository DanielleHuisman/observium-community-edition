LUM-SATELLITE-MIB DEFINITIONS ::= BEGIN

IMPORTS
    MODULE-IDENTITY, OBJECT-TYPE, Unsigned32
        FROM SNMPv2-SMI
    OBJECT-GROUP, MODULE-COMPLIANCE
        FROM SNMPv2-CONF
    DisplayString, DateAndTime
        FROM SNMPv2-TC
    lumModules, lumSatelliteMIB
        FROM LUM-REG
    MgmtNameString
        FROM LUM-TC;

lumSatelliteMIBModule MODULE-IDENTITY
    LAST-UPDATED
        "201706150000Z" -- June 15th 2017
    ORGANIZATION
        "Infinera Corporation"
    CONTACT-INFO
        "techsupport@infinera.com"
    DESCRIPTION
        "The SATELLITE interface and protection group MIB.

        - General

        - SATELLITE interfaces

"
    REVISION
        "201706150000Z" -- June 15th 2017
    DESCRIPTION
        "Changes made for release r29.0:
         - Changed ORGANIZATION and CONTACT-INFO"
    REVISION
        "200906150000Z" -- June 15th 2009
    DESCRIPTION
        "The initial revision of this module."
    ::= { lumModules 36 }


-- ----------------------------------------------------
-- Conformance area, containing groups and complicance
-- specifications.
-- ----------------------------------------------------

lumSatelliteConfs OBJECT IDENTIFIER ::= { lumSatelliteMIB 1 }
lumSatelliteGroups OBJECT IDENTIFIER ::= { lumSatelliteConfs 1 }
lumSatelliteCompl OBJECT IDENTIFIER ::= { lumSatelliteConfs 2 }


-- ----------------------------------------------------
-- Root for objects in the satellite MIB
-- ----------------------------------------------------

lumSatelliteMIBObjects OBJECT IDENTIFIER ::= { lumSatelliteMIB 2 }


-- ----------------------------------------------------
-- This MIB contains the following groups:
-- ----------------------------------------------------

satelliteGeneral OBJECT IDENTIFIER ::= { lumSatelliteMIBObjects 1 }
satelliteSatelliteList OBJECT IDENTIFIER ::= { lumSatelliteMIBObjects 2}

-- ----------------------------------------------------
-- Textual Conventions
-- ----------------------------------------------------

-- ----------------------------------------------------
-- General group
-- ----------------------------------------------------

satelliteGeneralLastChangeTime OBJECT-TYPE
    SYNTAX      DateAndTime
    MAX-ACCESS  read-only
    STATUS      current
    DESCRIPTION
        "The time when the configuration of the MIB was
        last changed.

"
    ::= { satelliteGeneral 1 }

satelliteGeneralStateLastChangeTime OBJECT-TYPE
    SYNTAX      DateAndTime
    MAX-ACCESS  read-only
    STATUS      current
    DESCRIPTION
        "The time when the state of the MIB was last
        changed.

"
    ::= { satelliteGeneral 2 }

satelliteGeneralSatelliteTableSize OBJECT-TYPE
    SYNTAX      Unsigned32
    MAX-ACCESS  read-only
    STATUS      current
    DESCRIPTION
        "Size of table

"
    ::= { satelliteGeneral 3 }

-- ----------------------------------------------------
-- Satellite SATELLITE definitions
-- ----------------------------------------------------

satelliteSatelliteTable  OBJECT-TYPE
    SYNTAX      SEQUENCE OF SatelliteSatelliteEntry
    MAX-ACCESS  not-accessible
    STATUS      current
    DESCRIPTION
        "The SATELLITE table."
    ::= { satelliteSatelliteList 1 }

satelliteSatelliteEntry OBJECT-TYPE
    SYNTAX      SatelliteSatelliteEntry
    MAX-ACCESS  not-accessible
    STATUS      current
    DESCRIPTION
        "An entry in the SATELLITE table.
"
    INDEX { satelliteSatelliteIndex }
    ::= { satelliteSatelliteTable 1 }

SatelliteSatelliteEntry ::=
    SEQUENCE {
    satelliteSatelliteIndex			  Unsigned32,
    satelliteSatelliteName  		          MgmtNameString,
    satelliteSatelliteDescr			  DisplayString,
    satelliteSatelliteExpectedBoardType           INTEGER
    }

satelliteSatelliteIndex OBJECT-TYPE
    SYNTAX      Unsigned32 (1..2147483647)
    MAX-ACCESS  read-only
    STATUS      current
    DESCRIPTION
        "An arbitrary index assigned to each entry.

"
    ::= { satelliteSatelliteEntry 1 }

satelliteSatelliteName OBJECT-TYPE
    SYNTAX      MgmtNameString
    MAX-ACCESS  read-only
    STATUS      current
    DESCRIPTION
	"The name of the object, for example
	'satellite:1:2:1-2', where the numbers indicate the
	subrack, slot and port numbers.

"
    DEFVAL { "" }
    ::= { satelliteSatelliteEntry 2 }

satelliteSatelliteDescr OBJECT-TYPE
    SYNTAX      DisplayString
    MAX-ACCESS  read-write
    STATUS      current
    DESCRIPTION
        "User configurable label.

"
    DEFVAL { "" }
    ::= { satelliteSatelliteEntry 3 }

satelliteSatelliteExpectedBoardType OBJECT-TYPE
    SYNTAX      INTEGER {
    		    mba1     (1),
		    mba2     (2) }
    MAX-ACCESS  read-write
    STATUS      current
    DESCRIPTION
        "State which access board that is expected.
	This is used to show correct number of	
	channels in crossConnect dialogue.

"
    DEFVAL { mba2 }
    ::= { satelliteSatelliteEntry 4 }


-- ----------------------------------------------------
-- Object and event groups
-- ----------------------------------------------------

satelliteGeneralGroup OBJECT-GROUP
    OBJECTS {
        satelliteGeneralLastChangeTime,
	satelliteGeneralStateLastChangeTime,
	satelliteGeneralSatelliteTableSize }
    STATUS      current
    DESCRIPTION
        "The general objects."
    ::= { lumSatelliteGroups 1 }

satelliteSatelliteGroup OBJECT-GROUP
    OBJECTS {
    satelliteSatelliteIndex,
    satelliteSatelliteName,
    satelliteSatelliteDescr,
    satelliteSatelliteExpectedBoardType
    }
    STATUS      current
    DESCRIPTION
        "The SATELLITE SATELLITE objects. (15.0) "
    ::= { lumSatelliteGroups 2 }

-- ----------------------------------------------------
-- Compliance
-- ----------------------------------------------------

lumSatelliteBasicCompl1 MODULE-COMPLIANCE
    STATUS     current
    DESCRIPTION
        "Basic implementation requirements for the SATELLITE MIB V1. (15.0)"
    MODULE
        MANDATORY-GROUPS {
	    satelliteGeneralGroup,
            satelliteSatelliteGroup
 }
    ::= { lumSatelliteCompl 1 }


END

LUM-TOPOLOGY-MIB DEFINITIONS ::= BEGIN

IMPORTS
    MODULE-IDENTITY, OBJECT-TYPE, Unsigned32
        FROM SNMPv2-SMI
    OBJECT-GROUP, MODULE-COMPLIANCE
        FROM SNMPv2-CONF
    RowStatus, TestAndIncr, DisplayString, DateAndTime, TEXTUAL-CONVENTION
        FROM SNMPv2-TC
    lumModules, lumTopologyMIB
        FROM LUM-REG
    SubrackNumber, SlotNumber, PortNumber, PortType, LambdaFrequency,
        LambdaType, CommandString, MgmtNameString
        FROM LUM-TC;

lumTopologyMIBModule MODULE-IDENTITY
    LAST-UPDATED
        "201706150000Z" -- June 15th 2017
    ORGANIZATION
        "Infinera Corporation"
    CONTACT-INFO
        "techsupport@infinera.com"
    DESCRIPTION
        "The topology MIB.

        - General

        - Internal connections

        - Peer connections

        - Client connections

        - Segments

"
    REVISION
        "201706150000Z" -- June 15th 2017
    DESCRIPTION
        "Changes made for release r29.0:
         - Changed ORGANIZATION and CONTACT-INFO"
    REVISION
        "201603150000Z" -- March 2016
    DESCRIPTION
        "Changes for r26.1:
        - Added ifNo for EMXP3; topoClientLocalOutIfNo,
          topoClientLocalInIfNo, topoIntFromIfNo, topoIntToIfNo,
          topoPeerLocalIfNo, topoPeerRemoteIfNo."
    REVISION
        "200209260000Z" -- September 26th 2002
    DESCRIPTION
        "Added topoClientChannelId."
    REVISION
        "200112110000Z" -- December 11th 2001
    DESCRIPTION
        "Added outgoing and incoming port attributes to the client
        objects."
    REVISION
        "200111080000Z" -- November 8th 2001
    DESCRIPTION
        "Deprecated direction objects for all tables."
    REVISION
        "200110260000Z" -- October 26th 2001
    DESCRIPTION
        "Added name attributes to all entries.
        Proposal for overview objects."
    REVISION
        "200110220000Z" -- October 22nd 2001
    DESCRIPTION
        "Changed from right and left to from and to."
    REVISION
        "200110110000Z" -- October 11th 2001
    DESCRIPTION
        "Removed InterfaceIndexOrZero, caused a warning when compiling...
        Updated after changes in other MIBs.
        Changed subrack, slot and port-number defaults to 0."
    REVISION
        "200108140000Z" -- August 14th 2001
    DESCRIPTION
        "Changes after review.
        Added lambdaDirection attribute for topo entries.
        Added lastChange attribute.
        Added compliance info.
        Indices are no longer persistent.
        Added default values."
    REVISION
        "200108080000Z" -- August 9th 2001
    DESCRIPTION
        "The initial revision of this module."
    ::= { lumModules 10 }

-- ----------------------------------------------------
-- Conformance area, containing groups and complicance
-- specifications.
-- ----------------------------------------------------

lumTopologyConfs OBJECT IDENTIFIER ::= { lumTopologyMIB 1 }
lumTopologyGroups OBJECT IDENTIFIER ::= { lumTopologyConfs 1 }
lumTopologyCompl OBJECT IDENTIFIER ::= { lumTopologyConfs 2 }


-- ----------------------------------------------------
-- Root for objects in the topology MIB
-- ----------------------------------------------------

lumTopologyMIBObjects OBJECT IDENTIFIER ::= { lumTopologyMIB 2 }


-- ----------------------------------------------------
-- This MIB contains the following groups:
-- ----------------------------------------------------

topoGeneral OBJECT IDENTIFIER ::= { lumTopologyMIBObjects 1 }
topoIntList OBJECT IDENTIFIER ::= { lumTopologyMIBObjects 2 }
topoPeerList OBJECT IDENTIFIER ::= { lumTopologyMIBObjects 3 }
topoClientList OBJECT IDENTIFIER ::= { lumTopologyMIBObjects 4 }
topoSegmentList OBJECT IDENTIFIER ::= { lumTopologyMIBObjects 5 }


-- ----------------------------------------------------
-- Textual Conventions
-- ----------------------------------------------------

SegmentEndPoint ::= TEXTUAL-CONVENTION
    STATUS current
    DESCRIPTION
        "Indicates the type of the segment end point"
    SYNTAX INTEGER {
           undefined (0),
           trunc (1),
           client (2),
           crossConnect (3),
           incomplete(4) }

ConnSegmentDirType ::= TEXTUAL-CONVENTION
    STATUS current
    DESCRIPTION
        "Direction of segment."

    SYNTAX INTEGER {
        undefined (0),
        rx (1),
        tx (2),
        biDi (3),
        unused (4),
        txRx (5)  }



-- ----------------------------------------------------
-- General group
-- ----------------------------------------------------

topoGeneralTestAndIncr OBJECT-TYPE
    SYNTAX      TestAndIncr
    MAX-ACCESS  read-write
    STATUS      current
    DESCRIPTION
        "Protection against simultaneous access from
        multiple managers. See SNMPv2-TC.

"
    ::= { topoGeneral 1 }

topoGeneralMibSpecVersion OBJECT-TYPE
    SYNTAX      DisplayString
    MAX-ACCESS  read-write
    STATUS      current
    DESCRIPTION
        "The MIB specification version.

        tbd: persistent?

"
    DEFVAL { "" }
    ::= { topoGeneral 2 }

topoGeneralMibImplVersion OBJECT-TYPE
    SYNTAX      DisplayString
    MAX-ACCESS  read-write
    STATUS      current
    DESCRIPTION
        "The MIB implementation version.

        tbd: persistent?

"
    DEFVAL { "" }
    ::= { topoGeneral 3 }

topoGeneralLastChangeTime OBJECT-TYPE
    SYNTAX      DateAndTime
    MAX-ACCESS  read-only
    STATUS      current
    DESCRIPTION
        "The time when the configuration of the MIB was
        last changed.

"
    ::= { topoGeneral 4 }

topoGeneralStateLastChangeTime OBJECT-TYPE
    SYNTAX      DateAndTime
    MAX-ACCESS  read-only
    STATUS      current
    DESCRIPTION
        "The time when the state of the MIB was last
        changed.

"
    ::= { topoGeneral 5 }

topoGeneralTopoClientTableSize OBJECT-TYPE
    SYNTAX      Unsigned32
    MAX-ACCESS  read-only
    STATUS      current
    DESCRIPTION
        "Size of table

"
    ::= { topoGeneral 6 }

topoGeneralTopoPeerTableSize OBJECT-TYPE
    SYNTAX      Unsigned32
    MAX-ACCESS  read-only
    STATUS      current
    DESCRIPTION
        "Size of table

"
    ::= { topoGeneral 7 }

topoGeneralTopoInternalTableSize OBJECT-TYPE
    SYNTAX      Unsigned32
    MAX-ACCESS  read-only
    STATUS      current
    DESCRIPTION
        "Size of table

"
    ::= { topoGeneral 8 }

topoGeneralTopoSegmentTableSize OBJECT-TYPE
    SYNTAX      Unsigned32
    MAX-ACCESS  read-only
    STATUS      current
    DESCRIPTION
        "Size of table

"
    ::= { topoGeneral 9 }


-- ----------------------------------------------------
-- Internal topology information
-- ----------------------------------------------------

topoIntTable  OBJECT-TYPE
    SYNTAX      SEQUENCE OF TopoIntEntry
    MAX-ACCESS  not-accessible
    STATUS      current
    DESCRIPTION
        "The internal connection list."
    ::= { topoIntList 1 }

topoIntEntry OBJECT-TYPE
    SYNTAX      TopoIntEntry
    MAX-ACCESS  not-accessible
    STATUS      current
    DESCRIPTION
        "An entry in the internal connection list.

        Describes a physical connection between two ports
        within the same network element.

        Connections between rxTx ports are
        implicitly bi-directional, only one definition is
        necessary.

"
    INDEX { topoIntIndex }
    ::= { topoIntTable 1 }

TopoIntEntry ::=
    SEQUENCE {
        topoIntIndex                    Unsigned32,
        topoIntFromSubrack              SubrackNumber,
        topoIntFromSlot                 SlotNumber,
        topoIntFromPort                 PortNumber,
        topoIntToSubrack                SubrackNumber,
        topoIntToSlot                   SlotNumber,
        topoIntToPort                   PortNumber,
        topoIntDescr                    DisplayString,
        topoIntDirection                PortType,
        topoIntRowStatus                RowStatus,
        topoIntName                     DisplayString,
        topoIntFromIfNo                 PortNumber,
        topoIntToIfNo                   PortNumber
        }

topoIntIndex OBJECT-TYPE
    SYNTAX      Unsigned32 (1..4294967295)
    MAX-ACCESS  read-only
    STATUS      current
    DESCRIPTION
        "An arbitrary index assigned to each entry.

"
    ::= { topoIntEntry 1 }

topoIntFromSubrack OBJECT-TYPE
    SYNTAX      SubrackNumber
    MAX-ACCESS  read-create
    STATUS      current
    DESCRIPTION
        "The subrack number for this end of the
        connection.

    This attribute can be written via SNMP.
"
    DEFVAL { 0 }
    ::= { topoIntEntry 2 }

topoIntFromSlot OBJECT-TYPE
    SYNTAX      SlotNumber
    MAX-ACCESS  read-create
    STATUS      current
    DESCRIPTION
        "The slot number for this end of the
        connection.

    This attribute can be written via SNMP.
"
    DEFVAL { 0 }
    ::= { topoIntEntry 3 }

topoIntFromPort OBJECT-TYPE
    SYNTAX      PortNumber
    MAX-ACCESS  read-create
    STATUS      current
    DESCRIPTION
        "The port number for this end of the connection.

    This attribute can be written via SNMP.
"
    DEFVAL { 0 }
    ::= { topoIntEntry 4 }

topoIntToSubrack OBJECT-TYPE
    SYNTAX      SubrackNumber
    MAX-ACCESS  read-create
    STATUS      current
    DESCRIPTION
        "The subrack number for the other end of the
        connection.

    This attribute can be written via SNMP.
"
    DEFVAL { 0 }
    ::= { topoIntEntry 5 }

topoIntToSlot OBJECT-TYPE
    SYNTAX      SlotNumber
    MAX-ACCESS  read-create
    STATUS      current
    DESCRIPTION
        "The slot number for the other end of the
        connection.

    This attribute can be written via SNMP.
"
    DEFVAL { 0 }
    ::= { topoIntEntry 6 }

topoIntToPort OBJECT-TYPE
    SYNTAX      PortNumber
    MAX-ACCESS  read-create
    STATUS      current
    DESCRIPTION
        "The port number for the other end of the
        connection.

        This attribute can be written via SNMP.
"
    DEFVAL { 0 }
    ::= { topoIntEntry 7 }

topoIntDescr OBJECT-TYPE
    SYNTAX      DisplayString
    MAX-ACCESS  read-write
    STATUS      current
    DESCRIPTION
        "User configurable description.

"
    DEFVAL { "" }
    ::= { topoIntEntry 8 }

topoIntDirection OBJECT-TYPE
    SYNTAX      PortType
    MAX-ACCESS  read-only
    STATUS      deprecated
    DESCRIPTION
        "Note: Deprecated!
        Indicates what type of ports are connected.

"
    ::= { topoIntEntry 9 }

topoIntRowStatus OBJECT-TYPE
    SYNTAX      RowStatus
    MAX-ACCESS  read-create
    STATUS      current
    DESCRIPTION
        "Manages creation and deletion of conceptual rows.
        See also SNMPv2-TC.

        This attribute can be written via SNMP.

        Note: The newly created object will not necessarily
        receive the same index as used in the create
        procedure.
"
    ::= { topoIntEntry 10 }

topoIntName OBJECT-TYPE
    SYNTAX      DisplayString
    MAX-ACCESS  read-only
    STATUS      current
    DESCRIPTION
        "The name of the topology entry.

"
    ::= { topoIntEntry 11 }


topoIntFromIfNo OBJECT-TYPE
    SYNTAX      PortNumber
    MAX-ACCESS  read-create
    STATUS      current
    DESCRIPTION
        "The interface number for this end of the connection.
        The local physical interface number of the actual multi-connector port.

"
    DEFVAL { 0 }
    ::= { topoIntEntry 12 }


topoIntToIfNo OBJECT-TYPE
    SYNTAX      PortNumber
    MAX-ACCESS  read-create
    STATUS      current
    DESCRIPTION
        "The interface number for the far end of the connection.
        The local physical interface number of the actual multi-connector port.

"
    DEFVAL { 0 }
    ::= { topoIntEntry 13 }


-- ----------------------------------------------------
-- External peer topology information
-- ----------------------------------------------------

topoPeerTable  OBJECT-TYPE
    SYNTAX      SEQUENCE OF TopoPeerEntry
    MAX-ACCESS  not-accessible
    STATUS      current
    DESCRIPTION
        "The peer connection list."
    ::= { topoPeerList 1 }

topoPeerEntry OBJECT-TYPE
    SYNTAX      TopoPeerEntry
    MAX-ACCESS  not-accessible
    STATUS      current
    DESCRIPTION
        "An entry in the peer connection list.

        Describes a physical connection between two ports
        on two network elements. The definition should be
        present in both network elements.

"
    INDEX { topoPeerIndex }
    ::= { topoPeerTable 1 }

TopoPeerEntry ::=
    SEQUENCE {
        topoPeerIndex                   Unsigned32,
        topoPeerLocalSubrack            SubrackNumber,
        topoPeerLocalSlot               SlotNumber,
        topoPeerLocalIfNo               PortNumber,
        topoPeerLocalPort               PortNumber,
        topoPeerRemoteIpAddress         DisplayString,
        topoPeerRemoteSubrack           SubrackNumber,
        topoPeerRemoteSlot              SlotNumber,
        topoPeerRemoteIfNo              PortNumber,
        topoPeerRemotePort              PortNumber,
        topoPeerDescr                   DisplayString,
        topoPeerDirection               PortType,
        topoPeerRowStatus               RowStatus,
        topoPeerName                    DisplayString,
        topoPeerLinkAttenuation         Unsigned32,
        topoPeerLocalLabel              DisplayString,
        topoPeerRemoteLabel             DisplayString
        }

topoPeerIndex OBJECT-TYPE
    SYNTAX      Unsigned32 (1..4294967295)
    MAX-ACCESS  read-only
    STATUS      current
    DESCRIPTION
        "An arbitrary index assigned to each entry.

"
    ::= { topoPeerEntry 1 }

topoPeerLocalSubrack OBJECT-TYPE
    SYNTAX      SubrackNumber
    MAX-ACCESS  read-create
    STATUS      current
    DESCRIPTION
        "Local subrack number.

    This attribute can be written via SNMP.
"
    DEFVAL { 0 }
    ::= { topoPeerEntry 2 }

topoPeerLocalSlot OBJECT-TYPE
    SYNTAX      SlotNumber
    MAX-ACCESS  read-create
    STATUS      current
    DESCRIPTION
        "Local slot number.

    This attribute can be written via SNMP.
"
    DEFVAL { 0 }
    ::= { topoPeerEntry 3 }

topoPeerLocalPort OBJECT-TYPE
    SYNTAX      PortNumber
    MAX-ACCESS  read-create
    STATUS      current
    DESCRIPTION
        "Local port number.

    This attribute can be written via SNMP.
"
    DEFVAL { 0 }
    ::= { topoPeerEntry 4 }

topoPeerRemoteIpAddress OBJECT-TYPE
    SYNTAX      DisplayString
    MAX-ACCESS  read-write
    STATUS      current
    DESCRIPTION
        "The IP address of the remote network element.

    This attribute can be written via SNMP.
"
    DEFVAL { "" }
    ::= { topoPeerEntry 5 }

topoPeerRemoteSubrack OBJECT-TYPE
    SYNTAX      SubrackNumber
    MAX-ACCESS  read-create
    STATUS      current
    DESCRIPTION
        "Remote subrack number.

    This attribute can be written via SNMP.
"
    DEFVAL { 0 }
    ::= { topoPeerEntry 6 }

topoPeerRemoteSlot OBJECT-TYPE
    SYNTAX      SlotNumber
    MAX-ACCESS  read-create
    STATUS      current
    DESCRIPTION
        "Remote slot number.

    This attribute can be written via SNMP.
"
    DEFVAL { 0 }
    ::= { topoPeerEntry 7 }

topoPeerRemotePort OBJECT-TYPE
    SYNTAX      PortNumber
    MAX-ACCESS  read-create
    STATUS      current
    DESCRIPTION
        "Remote port number.

    This attribute can be written via SNMP.
"
    DEFVAL { 0 }
    ::= { topoPeerEntry 8 }

topoPeerDescr OBJECT-TYPE
    SYNTAX      DisplayString
    MAX-ACCESS  read-write
    STATUS      current
    DESCRIPTION
        "User configurable description.

    This attribute can be written via SNMP.
"
    ::= { topoPeerEntry 9 }

topoPeerDirection OBJECT-TYPE
    SYNTAX      PortType
    MAX-ACCESS  read-only
    STATUS      deprecated
    DESCRIPTION
        "Note: Deprecated!
        Indicates what type of port is connected in the
        local network element.

"
    ::= { topoPeerEntry 10 }

topoPeerRowStatus OBJECT-TYPE
    SYNTAX      RowStatus
    MAX-ACCESS  read-create
    STATUS      current
    DESCRIPTION
        "Manages creation and deletion of conceptual rows.
        See also SNMPv2-TC.

        This attribute can be written via SNMP.

        Note: The newly created object will not necessarily
        receive the same index as used in the create
        procedure.
"
    ::= { topoPeerEntry 11 }

topoPeerName OBJECT-TYPE
    SYNTAX      DisplayString
    MAX-ACCESS  read-only
    STATUS      current
    DESCRIPTION
        "The name of the topology entry.

"
    ::= { topoPeerEntry 12 }

topoPeerLinkAttenuation OBJECT-TYPE
    SYNTAX      Unsigned32(0..1000)
    MAX-ACCESS  read-write
    STATUS      current
    DESCRIPTION
        "Value describing the attenuation of the
         fiber carrying the peer.

         The value must be supplied by the user,
         typically done at installation.

"
    DEFVAL { 0 }
    ::= { topoPeerEntry 13 }

topoPeerLocalLabel OBJECT-TYPE
    SYNTAX      DisplayString
    MAX-ACCESS  read-write
    STATUS      current
    DESCRIPTION
        "A label identifying the local
         end of the peer.

"
    ::= { topoPeerEntry 14 }

topoPeerRemoteLabel OBJECT-TYPE
    SYNTAX      DisplayString
    MAX-ACCESS  read-write
    STATUS      current
    DESCRIPTION
        "A label identifying the remote
         end of the peer.

"
    ::= { topoPeerEntry 15 }

topoPeerLocalIfNo OBJECT-TYPE
    SYNTAX      PortNumber
    MAX-ACCESS  read-create
    STATUS      current
    DESCRIPTION
        "Local ifNo.

"
    DEFVAL { 0 }
    ::= { topoPeerEntry 16 }

topoPeerRemoteIfNo OBJECT-TYPE
    SYNTAX      PortNumber
    MAX-ACCESS  read-create
    STATUS      current
    DESCRIPTION
        "Remote ifNo.

"
    DEFVAL { 0 }
    ::= { topoPeerEntry 17 }

-- ----------------------------------------------------
-- External client topology information
-- ----------------------------------------------------

topoClientTable  OBJECT-TYPE
    SYNTAX      SEQUENCE OF TopoClientEntry
    MAX-ACCESS  not-accessible
    STATUS      current
    DESCRIPTION
        "The client list."
    ::= { topoClientList 1 }

topoClientEntry OBJECT-TYPE
    SYNTAX      TopoClientEntry
    MAX-ACCESS  not-accessible
    STATUS      current
    DESCRIPTION
        "An entry in the client connection list.

        Describes a physical connection between a
        network element and a client node.

"
    INDEX { topoClientIndex }
    ::= { topoClientTable 1 }

TopoClientEntry ::=
    SEQUENCE {
        topoClientIndex                 Unsigned32,
        topoClientLocalInSubrack        SubrackNumber,
        topoClientLocalInSlot           SlotNumber,
        topoClientLocalInPort           PortNumber,
        topoClientRemoteIpAddress       DisplayString,
        topoClientRemoteIfIndex         Unsigned32,
        topoClientDescr                 DisplayString,
        topoClientDirection             PortType,
        topoClientRowStatus             RowStatus,
        topoClientName                  DisplayString,
        topoClientLocalOutSubrack       SubrackNumber,
        topoClientLocalOutSlot          SlotNumber,
        topoClientLocalOutPort          PortNumber,
        topoClientChannelId             Unsigned32,
        topoClientInterfaceRepresentation Unsigned32,
        topoClientLocalOutIfNo          PortNumber,
        topoClientLocalInIfNo           PortNumber
        }

topoClientIndex OBJECT-TYPE
    SYNTAX      Unsigned32 (1..2147483647)
    MAX-ACCESS  read-only
    STATUS      current
    DESCRIPTION
        "An arbitrary index assigned to each entry.

"
    ::= { topoClientEntry 1 }

topoClientLocalInSubrack OBJECT-TYPE
    SYNTAX      SubrackNumber
    MAX-ACCESS  read-create
    STATUS      current
    DESCRIPTION
        "Local incoming sub-rack number for the
        connection.

    This attribute can be written via SNMP.
"
    DEFVAL { 0 }
    ::= { topoClientEntry 2 }

topoClientLocalInSlot OBJECT-TYPE
    SYNTAX      SlotNumber
    MAX-ACCESS  read-create
    STATUS      current
    DESCRIPTION
        "Local incoming slot number for the
        connection.

    This attribute can be written via SNMP.
"
    DEFVAL { 0 }
    ::= { topoClientEntry 3 }

topoClientLocalInPort OBJECT-TYPE
    SYNTAX      PortNumber
    MAX-ACCESS  read-create
    STATUS      current
    DESCRIPTION
        "Local incoming port number for the
        connection.

    This attribute can be written via SNMP.
"
    DEFVAL { 0 }
    ::= { topoClientEntry 4 }

topoClientRemoteIpAddress OBJECT-TYPE
    SYNTAX      DisplayString
    MAX-ACCESS  read-write
    STATUS      current
    DESCRIPTION
        "The client IP address.

    This attribute can be written via SNMP.
"
    DEFVAL { "" }
    ::= { topoClientEntry 5 }

topoClientRemoteIfIndex OBJECT-TYPE
    SYNTAX      Unsigned32 (0..2147483647)
    MAX-ACCESS  read-write
    STATUS      current
    DESCRIPTION
        "The client interface index.

    This attribute can be written via SNMP.
"
    DEFVAL { 0 }
    ::= { topoClientEntry 6 }

topoClientDescr OBJECT-TYPE
    SYNTAX      DisplayString
    MAX-ACCESS  read-write
    STATUS      current
    DESCRIPTION
        "User configurable description.

    This attribute can be written via SNMP.
"
    DEFVAL { "" }
    ::= { topoClientEntry 7 }

topoClientDirection OBJECT-TYPE
    SYNTAX      PortType
    MAX-ACCESS  read-only
    STATUS      deprecated
    DESCRIPTION
        "Note: Deprecated!
        Indicates what type of port is connected in the
        local network element.

"
    ::= { topoClientEntry 8 }

topoClientRowStatus OBJECT-TYPE
    SYNTAX      RowStatus
    MAX-ACCESS  read-create
    STATUS      current
    DESCRIPTION
        "Manages creation and deletion of conceptual rows.
        See also SNMPv2-TC.

        This attribute can be written via SNMP.

        Note: The newly created object will not necessarily
        receive the same index as used in the create
        procedure.
"
    ::= { topoClientEntry 9 }

topoClientName OBJECT-TYPE
    SYNTAX      DisplayString
    MAX-ACCESS  read-only
    STATUS      current
    DESCRIPTION
        "The name of the topology entry.

"
    ::= { topoClientEntry 10 }

topoClientLocalOutSubrack OBJECT-TYPE
    SYNTAX      SubrackNumber
    MAX-ACCESS  read-create
    STATUS      current
    DESCRIPTION
        "Local out-going sub-rack number.

    This attribute can be written via SNMP.
"
    DEFVAL { 0 }
    ::= { topoClientEntry 11 }

topoClientLocalOutSlot OBJECT-TYPE
    SYNTAX      SlotNumber
    MAX-ACCESS  read-create
    STATUS      current
    DESCRIPTION
        "Local out-going slot number for the
        connection.

    This attribute can be written via SNMP.
"
    DEFVAL { 0 }
    ::= { topoClientEntry 12 }

topoClientLocalOutPort OBJECT-TYPE
    SYNTAX      PortNumber
    MAX-ACCESS  read-create
    STATUS      current
    DESCRIPTION
        "Local out-going port number for the
        connection.

    This attribute can be written via SNMP.
"
    DEFVAL { 0 }
    ::= { topoClientEntry 13 }

topoClientChannelId OBJECT-TYPE
    SYNTAX      Unsigned32 (0..4095)
    MAX-ACCESS  read-create
    STATUS      current
    DESCRIPTION
        "Defines the channel in the port that is
        referred to. Only to be used when referring to a
        sub-channel on a multiplexed interface, e.g.
        for muxponders.

    This attribute can be written via SNMP.
"
    DEFVAL { 0 }
    ::= { topoClientEntry 14 }

topoClientInterfaceRepresentation OBJECT-TYPE
    SYNTAX      Unsigned32 (0..4294967295)
    MAX-ACCESS  read-create
    STATUS      current
    DESCRIPTION
        "Compact representation of

               localOutSubrack/Slot/Port
               localInSubrack/Slot/Port
               not used for ifNo

     Used in the backup.

"
    DEFVAL { 0 }
    ::= { topoClientEntry 15 }


topoClientLocalOutIfNo OBJECT-TYPE
    SYNTAX      PortNumber
    MAX-ACCESS  read-create
    STATUS      current
    DESCRIPTION
        "The local physical interface number of the actual multi-connector port.

"
    DEFVAL { 0 }
    ::= { topoClientEntry 16 }

topoClientLocalInIfNo OBJECT-TYPE
    SYNTAX      PortNumber
    MAX-ACCESS  read-create
    STATUS      current
    DESCRIPTION
        "The local physical interface number of the actual multi-connector port.

"
    DEFVAL { 0 }
    ::= { topoClientEntry 17 }


-- ----------------------------------------------------
-- Segments
-- ----------------------------------------------------

topoSegmentTable  OBJECT-TYPE
    SYNTAX      SEQUENCE OF TopoSegmentEntry
    MAX-ACCESS  not-accessible
    STATUS      current
    DESCRIPTION
        "The segment list."
    ::= { topoSegmentList 1 }

topoSegmentEntry OBJECT-TYPE
    SYNTAX      TopoSegmentEntry
    MAX-ACCESS  not-accessible
    STATUS      current
    DESCRIPTION
        "An entry in the segment list.

"
    INDEX { topoSegmentIndex }
    ::= { topoSegmentTable 1 }

TopoSegmentEntry ::=
    SEQUENCE {
        topoSegmentIndex           Unsigned32,
        topoSegmentName            MgmtNameString,
        topoSegmentInSubrack       SubrackNumber,
        topoSegmentInSlot          SlotNumber,
        topoSegmentInPort          PortNumber,
        topoSegmentOutSubrack      SubrackNumber,
        topoSegmentOutSlot         SlotNumber,
        topoSegmentOutPort         PortNumber,
        topoSegmentFrequencyType   LambdaType,
        topoSegmentFrequency       LambdaFrequency,
        topoSegmentSubChannelId    Unsigned32,
        topoSegmentBegin           SegmentEndPoint,
        topoSegmentType            SegmentEndPoint,
        topoSegmentInEntityId      Unsigned32,
        topoSegmentOutEntityId     Unsigned32,
        topoSegmentEntityList      DisplayString,
        topoSegmentObjectList      DisplayString,
        topoSegmentDirection       ConnSegmentDirType,
        topoSegmentEntryPointsCommand     CommandString ,
        topoSegmentSubSegmentsCommand     CommandString,
        topoSegmentUniqId           Unsigned32   }


topoSegmentIndex OBJECT-TYPE
    SYNTAX      Unsigned32 (1..2147483647)
    MAX-ACCESS  read-only
    STATUS      current
    DESCRIPTION
        "An arbitrary index assigned to each entry.

"
    ::= { topoSegmentEntry 1 }

topoSegmentName OBJECT-TYPE
    SYNTAX      MgmtNameString
    MAX-ACCESS  read-only
    STATUS      current
    DESCRIPTION
        "Name of segment

"
    ::= { topoSegmentEntry 2 }

topoSegmentInSubrack OBJECT-TYPE
    SYNTAX      SubrackNumber
    MAX-ACCESS  read-only
    STATUS      current
    DESCRIPTION
        "The number of the subrack where the segment
        starts.

"
    ::= { topoSegmentEntry 3 }

topoSegmentInSlot OBJECT-TYPE
    SYNTAX      SlotNumber
    MAX-ACCESS  read-only
    STATUS      current
    DESCRIPTION
        "The number of the slot where the segment
        starts.

"
    ::= { topoSegmentEntry 4 }

topoSegmentInPort OBJECT-TYPE
    SYNTAX      PortNumber
    MAX-ACCESS  read-only
    STATUS      current
    DESCRIPTION
        "The number of the port where the segment
        starts.

"
    ::= { topoSegmentEntry 5 }

topoSegmentOutSubrack OBJECT-TYPE
    SYNTAX      SubrackNumber
    MAX-ACCESS  read-only
    STATUS      current
    DESCRIPTION
        "The number of the subrack where the segment ends.

"
    ::= { topoSegmentEntry 6 }

topoSegmentOutSlot OBJECT-TYPE
    SYNTAX      SlotNumber
    MAX-ACCESS  read-only
    STATUS      current
    DESCRIPTION
        "The number of the slot where the segment ends.

"
    ::= { topoSegmentEntry 7 }

topoSegmentOutPort OBJECT-TYPE
    SYNTAX      PortNumber
    MAX-ACCESS  read-only
    STATUS      current
    DESCRIPTION
        "The number of the port where the segment ends.

"
    ::= { topoSegmentEntry 8 }

topoSegmentFrequencyType OBJECT-TYPE
    SYNTAX      LambdaType
    MAX-ACCESS  read-only
    STATUS      current
    DESCRIPTION
        "The wavelength/frequency associated with the segment.
        0 if no wavelength is applicable

"
    ::= { topoSegmentEntry 9 }

topoSegmentFrequency OBJECT-TYPE
    SYNTAX      LambdaFrequency
    MAX-ACCESS  read-only
    STATUS      current
    DESCRIPTION
        "The wavelength/frequency associated with the segment.
        0 if no wavelength is applicable

"
    ::= { topoSegmentEntry 10 }

topoSegmentSubChannelId OBJECT-TYPE
    SYNTAX      Unsigned32
    MAX-ACCESS  read-only
    STATUS      current
    DESCRIPTION
        "The subchannel of the segment.

        Applicable if several signals are multiplexed on
        the same wavelength

"
    ::= { topoSegmentEntry 11 }

topoSegmentBegin OBJECT-TYPE
    SYNTAX      SegmentEndPoint
    MAX-ACCESS  read-only
    STATUS      current
    DESCRIPTION
        "The start point of the segment.

"
    ::= { topoSegmentEntry 12 }

topoSegmentType OBJECT-TYPE
    SYNTAX      SegmentEndPoint
    MAX-ACCESS  read-only
    STATUS      current
    DESCRIPTION
        "The end point of the segment.

"
    ::= { topoSegmentEntry 13 }

topoSegmentInEntityId OBJECT-TYPE
    SYNTAX      Unsigned32
    MAX-ACCESS  read-only
    STATUS      current
    DESCRIPTION
        "The entity ID of the first port.

"
    ::= { topoSegmentEntry 14 }

topoSegmentOutEntityId OBJECT-TYPE
    SYNTAX      Unsigned32
    MAX-ACCESS  read-only
    STATUS      current
    DESCRIPTION
        "The entity ID of the last port.

"
    ::= { topoSegmentEntry 15 }

topoSegmentEntityList OBJECT-TYPE
    SYNTAX      DisplayString
    MAX-ACCESS  read-only
    STATUS      current
    DESCRIPTION
        "A list of all entities

"
    ::= { topoSegmentEntry 16 }

topoSegmentObjectList OBJECT-TYPE
    SYNTAX      DisplayString
    MAX-ACCESS  read-only
    STATUS      current
    DESCRIPTION
        "A list of all ports

"
    ::= { topoSegmentEntry 17 }

topoSegmentDirection OBJECT-TYPE
    SYNTAX      ConnSegmentDirType
    MAX-ACCESS  read-only
    STATUS      current
    DESCRIPTION
        "Direction of segment with respect to the
         cross connect, if any.

"
   ::= { topoSegmentEntry 18 }

topoSegmentEntryPointsCommand OBJECT-TYPE
    SYNTAX      CommandString
    MAX-ACCESS  read-only
    STATUS      current
    DESCRIPTION
        "Command to list entry points.

"
   ::= { topoSegmentEntry 19 }

topoSegmentSubSegmentsCommand OBJECT-TYPE
    SYNTAX      CommandString
    MAX-ACCESS  read-only
    STATUS      current
    DESCRIPTION
        "Command to list subsegments

"
   ::= { topoSegmentEntry 20 }

topoSegmentUniqId OBJECT-TYPE
    SYNTAX      Unsigned32
    MAX-ACCESS  read-only
    STATUS      current
    DESCRIPTION
        "The entity ID of the last port.

"
    ::= { topoSegmentEntry 21 }


-- ----------------------------------------------------
-- Notifications
-- ----------------------------------------------------

-- n/a


-- ----------------------------------------------------
-- Object and event groups
-- ----------------------------------------------------

topoGeneralGroup OBJECT-GROUP
    OBJECTS {
        topoGeneralTestAndIncr,
        topoGeneralMibSpecVersion,
        topoGeneralMibImplVersion,
        topoGeneralLastChangeTime }
    STATUS      deprecated
    DESCRIPTION
        "The general objects."
    ::= { lumTopologyGroups 1 }

topoIntGroup OBJECT-GROUP
    OBJECTS {
        topoIntIndex,
        topoIntName,
        topoIntFromSubrack,
        topoIntFromSlot,
        topoIntFromPort,
        topoIntToSubrack,
        topoIntToSlot,
        topoIntToPort,
        topoIntDescr,
        topoIntDirection,
        topoIntRowStatus }
    STATUS      deprecated
    DESCRIPTION
        "The internal objects."
    ::= { lumTopologyGroups 2 }

topoPeerGroup OBJECT-GROUP
    OBJECTS {
        topoPeerIndex,
        topoPeerName,
        topoPeerLocalSubrack,
        topoPeerLocalSlot,
        topoPeerLocalPort,
        topoPeerRemoteIpAddress,
        topoPeerRemoteSubrack,
        topoPeerRemoteSlot,
        topoPeerRemotePort,
        topoPeerDescr,
        topoPeerDirection,
        topoPeerRowStatus }
    STATUS      deprecated
    DESCRIPTION
        "The peer objects."
    ::= { lumTopologyGroups 3 }

topoClientGroup OBJECT-GROUP
    OBJECTS {
        topoClientIndex,
        topoClientName,
        topoClientLocalInSubrack,
        topoClientLocalInSlot,
        topoClientLocalInPort,
        topoClientRemoteIpAddress,
        topoClientRemoteIfIndex,
        topoClientDescr,
        topoClientDirection,
        topoClientRowStatus }
    STATUS      deprecated
    DESCRIPTION
        "The client objects."
    ::= { lumTopologyGroups 4 }

topoGeneralGroupV2 OBJECT-GROUP
    OBJECTS {
        topoGeneralLastChangeTime }
    STATUS      deprecated
    DESCRIPTION
        "The general objects v2."
    ::= { lumTopologyGroups 5 }

topoIntGroupV2 OBJECT-GROUP
    OBJECTS {
        topoIntIndex,
        topoIntName,
        topoIntFromSubrack,
        topoIntFromSlot,
        topoIntFromPort,
        topoIntToSubrack,
        topoIntToSlot,
        topoIntToPort,
        topoIntDescr,
        topoIntRowStatus }
    STATUS      deprecated
    DESCRIPTION
        "The internal objects."
    ::= { lumTopologyGroups 6 }

topoPeerGroupV2 OBJECT-GROUP
    OBJECTS {
        topoPeerIndex,
        topoPeerName,
        topoPeerLocalSubrack,
        topoPeerLocalSlot,
        topoPeerLocalPort,
        topoPeerRemoteIpAddress,
        topoPeerRemoteSubrack,
        topoPeerRemoteSlot,
        topoPeerRemotePort,
        topoPeerDescr,
        topoPeerRowStatus }
    STATUS      deprecated
    DESCRIPTION
        "The peer objects."
    ::= { lumTopologyGroups 7 }

topoClientGroupV2 OBJECT-GROUP
    OBJECTS {
        topoClientIndex,
        topoClientName,
        topoClientLocalInSubrack,
        topoClientLocalInSlot,
        topoClientLocalInPort,
        topoClientRemoteIpAddress,
        topoClientRemoteIfIndex,
        topoClientDescr,
        topoClientRowStatus }
    STATUS      deprecated
    DESCRIPTION
        "The client objects."
    ::= { lumTopologyGroups 8 }

topoClientGroupV3 OBJECT-GROUP
    OBJECTS {
        topoClientIndex,
        topoClientName,
        topoClientLocalInSubrack,
        topoClientLocalInSlot,
        topoClientLocalInPort,
        topoClientRemoteIpAddress,
        topoClientRemoteIfIndex,
        topoClientDescr,
        topoClientRowStatus,
        topoClientLocalOutSubrack,
        topoClientLocalOutSlot,
        topoClientLocalOutPort }
    STATUS      deprecated
    DESCRIPTION
        "The client objects."
    ::= { lumTopologyGroups 9 }

topoGeneralGroupV3 OBJECT-GROUP
    OBJECTS {
        topoGeneralLastChangeTime,
        topoGeneralStateLastChangeTime }
    STATUS      deprecated
    DESCRIPTION
        "The general objects v3."
    ::= { lumTopologyGroups 10 }

topoClientGroupV4 OBJECT-GROUP
    OBJECTS {
        topoClientIndex,
        topoClientName,
        topoClientLocalInSubrack,
        topoClientLocalInSlot,
        topoClientLocalInPort,
        topoClientRemoteIpAddress,
        topoClientRemoteIfIndex,
        topoClientDescr,
        topoClientRowStatus,
        topoClientLocalOutSubrack,
        topoClientLocalOutSlot,
        topoClientLocalOutPort,
        topoClientChannelId }
    STATUS      deprecated
    DESCRIPTION
        "The client objects."
    ::= { lumTopologyGroups 11 }

topoPeerGroupV3 OBJECT-GROUP
    OBJECTS {
        topoPeerIndex,
        topoPeerName,
        topoPeerLocalSubrack,
        topoPeerLocalSlot,
        topoPeerLocalPort,
        topoPeerRemoteIpAddress,
        topoPeerRemoteSubrack,
        topoPeerRemoteSlot,
        topoPeerRemotePort,
        topoPeerDescr,
        topoPeerRowStatus,
        topoPeerLinkAttenuation,
        topoPeerLocalLabel,
        topoPeerRemoteLabel }
    STATUS      deprecated
    DESCRIPTION
        "The peer objects."
    ::= { lumTopologyGroups 12 }

topoSegmentGroup OBJECT-GROUP
    OBJECTS {
        topoSegmentIndex,
        topoSegmentName,
        topoSegmentInSubrack,
        topoSegmentInSlot,
        topoSegmentInPort,
        topoSegmentOutSubrack,
        topoSegmentOutSlot,
        topoSegmentOutPort,
        topoSegmentFrequencyType,
        topoSegmentFrequency,
        topoSegmentSubChannelId,
        topoSegmentBegin,
        topoSegmentInEntityId,
        topoSegmentOutEntityId,
        topoSegmentEntityList,
        topoSegmentObjectList,
        topoSegmentDirection,
        topoSegmentEntryPointsCommand,
        topoSegmentSubSegmentsCommand,
        topoSegmentUniqId }
    STATUS      deprecated
    DESCRIPTION
        "The connection segment objects."
    ::= { lumTopologyGroups 13 }

topoGeneralGroupV4 OBJECT-GROUP
    OBJECTS {
        topoGeneralLastChangeTime,
        topoGeneralStateLastChangeTime,
        topoGeneralTopoClientTableSize,
        topoGeneralTopoPeerTableSize,
        topoGeneralTopoInternalTableSize,
        topoGeneralTopoSegmentTableSize }
    STATUS      current
    DESCRIPTION
        "The general objects v4 (3.1)."
    ::= { lumTopologyGroups 14 }

topoSegmentGroupV2 OBJECT-GROUP
    OBJECTS {
        topoSegmentIndex,
        topoSegmentName,
        topoSegmentInSubrack,
        topoSegmentInSlot,
        topoSegmentInPort,
        topoSegmentOutSubrack,
        topoSegmentOutSlot,
        topoSegmentOutPort,
        topoSegmentFrequencyType,
        topoSegmentFrequency,
        topoSegmentSubChannelId,
        topoSegmentBegin,
        topoSegmentType,
        topoSegmentInEntityId,
        topoSegmentOutEntityId,
        topoSegmentEntityList,
        topoSegmentObjectList,
        topoSegmentDirection,
        topoSegmentEntryPointsCommand,
        topoSegmentSubSegmentsCommand,
        topoSegmentUniqId }
    STATUS      current
    DESCRIPTION
        "The connection segment objects V2 (7.0)."
    ::= { lumTopologyGroups 15 }

topoClientGroupV5 OBJECT-GROUP
    OBJECTS {
        topoClientIndex,
        topoClientName,
        topoClientLocalInSubrack,
        topoClientLocalInSlot,
        topoClientLocalInPort,
        topoClientRemoteIpAddress,
        topoClientRemoteIfIndex,
        topoClientDescr,
        topoClientRowStatus,
        topoClientLocalOutSubrack,
        topoClientLocalOutSlot,
        topoClientLocalOutPort,
        topoClientChannelId,
        topoClientInterfaceRepresentation }
    STATUS      deprecated
    DESCRIPTION
        "The client objects. (12.0)"
    ::= { lumTopologyGroups 16 }

topoPeerGroupV4 OBJECT-GROUP
    OBJECTS {
        topoPeerIndex,
        topoPeerName,
        topoPeerLocalSubrack,
        topoPeerLocalSlot,
        topoPeerLocalPort,
        topoPeerRemoteIpAddress,
        topoPeerRemoteSubrack,
        topoPeerRemoteSlot,
        topoPeerRemotePort,
        topoPeerDescr,
        topoPeerRowStatus,
        topoPeerLinkAttenuation,
        topoPeerLocalLabel,
        topoPeerRemoteLabel }
    STATUS      deprecated
    DESCRIPTION
        "The peer objects. (12.0)"
    ::= { lumTopologyGroups 17 }

topoIntGroupV3 OBJECT-GROUP
    OBJECTS {
        topoIntIndex,
        topoIntName,
        topoIntFromSubrack,
        topoIntFromSlot,
        topoIntFromPort,
        topoIntToSubrack,
        topoIntToSlot,
        topoIntToPort,
        topoIntDescr,
        topoIntRowStatus }
    STATUS      deprecated
    DESCRIPTION
        "The internal objects. (12.0)"
    ::= { lumTopologyGroups 18 }

topoClientGroupV6 OBJECT-GROUP
    OBJECTS {
        topoClientIndex,
        topoClientName,
        topoClientLocalInSubrack,
        topoClientLocalInSlot,
        topoClientLocalInPort,
        topoClientRemoteIpAddress,
        topoClientRemoteIfIndex,
        topoClientDescr,
        topoClientRowStatus,
        topoClientLocalOutSubrack,
        topoClientLocalOutSlot,
        topoClientLocalOutPort,
        topoClientChannelId,
        topoClientInterfaceRepresentation,
        topoClientLocalOutIfNo,
        topoClientLocalInIfNo
    }
    STATUS      current
    DESCRIPTION
        "The client objects. (26.1)"
    ::= { lumTopologyGroups 19 }

topoIntGroupV4 OBJECT-GROUP
    OBJECTS {
        topoIntIndex,
        topoIntName,
        topoIntFromSubrack,
        topoIntFromSlot,
        topoIntFromPort,
        topoIntToSubrack,
        topoIntToSlot,
        topoIntToPort,
        topoIntDescr,
        topoIntRowStatus,
        topoIntFromIfNo,
        topoIntToIfNo
        }
    STATUS      current
    DESCRIPTION
        "The internal objects. (26.1)"
    ::= { lumTopologyGroups 20 }

topoPeerGroupV5 OBJECT-GROUP
    OBJECTS {
        topoPeerIndex,
        topoPeerName,
        topoPeerLocalSubrack,
        topoPeerLocalSlot,
        topoPeerLocalPort,
        topoPeerRemoteIpAddress,
        topoPeerRemoteSubrack,
        topoPeerRemoteSlot,
        topoPeerRemotePort,
        topoPeerDescr,
        topoPeerRowStatus,
        topoPeerLinkAttenuation,
        topoPeerLocalLabel,
        topoPeerRemoteLabel,
        topoPeerLocalIfNo,
        topoPeerRemoteIfNo
         }
    STATUS      current
    DESCRIPTION
        "The peer objects. (26.1)"
    ::= { lumTopologyGroups 21 }

-- ----------------------------------------------------
-- Compliance
-- ----------------------------------------------------

lumTopoBasicComplV1 MODULE-COMPLIANCE
    STATUS      deprecated
    DESCRIPTION
        "Basic implementation requirements for the topo MIB."
    MODULE
        MANDATORY-GROUPS {
            topoGeneralGroup,
            topoIntGroup,
            topoPeerGroup,
            topoClientGroup }
    ::= { lumTopologyCompl 1 }

lumTopoBasicComplV2 MODULE-COMPLIANCE
    STATUS      deprecated
    DESCRIPTION
        "Basic implementation requirements for the topo MIB V2."
    MODULE
        MANDATORY-GROUPS {
            topoGeneralGroupV2,
            topoIntGroup,
            topoPeerGroup,
            topoClientGroup }
    ::= { lumTopologyCompl 2 }

lumTopoBasicComplV3 MODULE-COMPLIANCE
    STATUS      deprecated
    DESCRIPTION
        "Basic implementation requirements for the topo MIB V3."
    MODULE
        MANDATORY-GROUPS {
            topoGeneralGroupV2,
            topoIntGroupV2,
            topoPeerGroupV2,
            topoClientGroupV2 }
    ::= { lumTopologyCompl 3 }

lumTopoBasicComplV4 MODULE-COMPLIANCE
    STATUS      deprecated
    DESCRIPTION
        "Basic implementation requirements for the topo MIB V4."
    MODULE
        MANDATORY-GROUPS {
            topoGeneralGroupV2,
            topoIntGroupV2,
            topoPeerGroupV2,
            topoClientGroupV3 }
    ::= { lumTopologyCompl 4 }

lumTopoBasicComplV5 MODULE-COMPLIANCE
    STATUS      deprecated
    DESCRIPTION
        "Basic implementation requirements for the topo MIB V5."
    MODULE
        MANDATORY-GROUPS {
            topoGeneralGroupV3,
            topoIntGroupV2,
            topoPeerGroupV2,
            topoClientGroupV3 }
    ::= { lumTopologyCompl 5 }

lumTopoBasicComplV6 MODULE-COMPLIANCE
    STATUS      deprecated
    DESCRIPTION
        "Basic implementation requirements for the topo MIB V6."
    MODULE
        MANDATORY-GROUPS {
            topoGeneralGroupV3,
            topoIntGroupV2,
            topoPeerGroupV2,
            topoClientGroupV4 }
    ::= { lumTopologyCompl 6 }

lumTopoBasicComplV7 MODULE-COMPLIANCE
    STATUS      deprecated
    DESCRIPTION
        "Basic implementation requirements for the topo MIB V7 (3.0)."
    MODULE
        MANDATORY-GROUPS {
            topoGeneralGroupV3,
            topoIntGroupV2,
            topoPeerGroupV3,
            topoClientGroupV4 }
    ::= { lumTopologyCompl 7 }

lumTopoBasicComplV8 MODULE-COMPLIANCE
    STATUS      deprecated
    DESCRIPTION
        "Basic implementation requirements for the topo MIB V8 (3.1)."
    MODULE
        MANDATORY-GROUPS {
            topoGeneralGroupV4,
            topoIntGroupV2,
            topoPeerGroupV3,
            topoClientGroupV4,
            topoSegmentGroup }
    ::= { lumTopologyCompl 8 }

lumTopoBasicComplV9 MODULE-COMPLIANCE
    STATUS      deprecated
    DESCRIPTION
        "Basic implementation requirements for the topo MIB V9 (7.0)."
    MODULE
        MANDATORY-GROUPS {
            topoGeneralGroupV4,
            topoIntGroupV2,
            topoPeerGroupV3,
            topoClientGroupV4,
            topoSegmentGroupV2 }
    ::= { lumTopologyCompl 9 }

lumTopoBasicComplV10 MODULE-COMPLIANCE
    STATUS      deprecated
    DESCRIPTION
        "Basic implementation requirements for the topo MIB V10 (12.0)."
    MODULE
        MANDATORY-GROUPS {
            topoGeneralGroupV4,
            topoIntGroupV3,
            topoPeerGroupV4,
            topoClientGroupV5,
            topoSegmentGroupV2 }
    ::= { lumTopologyCompl 10 }

lumTopoBasicComplV11 MODULE-COMPLIANCE
    STATUS      current
    DESCRIPTION
        "Basic implementation requirements for the topo MIB V11 (26.1)."
    MODULE
        MANDATORY-GROUPS {
            topoGeneralGroupV4,
            topoIntGroupV4,
            topoPeerGroupV5,
            topoClientGroupV6,
            topoSegmentGroupV2 }
    ::= { lumTopologyCompl 11 }

END

AQUAMINT-MIB DEFINITIONS ::= BEGIN

IMPORTS
	wanflex
		FROM INFINET-MIB
	sysSerialNumber,
	sysTrapSequence
		FROM AQUASYSTEM-MIB
	DisplayString,
	MacAddress
		FROM SNMPv2-TC
	MODULE-IDENTITY,
	OBJECT-TYPE,
	NOTIFICATION-TYPE,
	Counter32,
	Integer32,
	Unsigned32
		FROM SNMPv2-SMI
	OBJECT-GROUP,
	NOTIFICATION-GROUP
		FROM SNMPv2-CONF;

aquamintMIB MODULE-IDENTITY
	LAST-UPDATED "201604040735Z"
	ORGANIZATION "Infinet Wireless Ltd."
	CONTACT-INFO
		"Anthony Berzin

		Postal: Infinet Wireless,
		        Russia, Ekaterinburg,
		        Serafimi Deryabinoi st, 24

		Phone:  +7 343 253 1533
		Email:  aberzin@infinetwireless.com"
	DESCRIPTION
		"The mib module for MINT."
	REVISION "201604040735Z"
	DESCRIPTION
		"Added mintLinkStatus"
	REVISION "201508250654Z"
	DESCRIPTION
		"Added link distance in meters to PtP link scalars"
	REVISION "201508170602Z"
	DESCRIPTION
		"Added link distance in meters to mint links table"
	REVISION "201001280937Z"
	DESCRIPTION
		"Added transmit power to mint links table"
	REVISION "200902040548Z"
	DESCRIPTION
		"Use proper MACAddress type."
	REVISION "200812040718Z"
	DESCRIPTION
		"Added secret key to mint nodes table."
	REVISION "200807210540Z"
	DESCRIPTION
		"Added RX retries and RX errors on link."
	REVISION "200805220404Z"
	DESCRIPTION
		"Added neighbor address to topology notification."
	REVISION "200805211336Z"
	DESCRIPTION
		"Added nodeInterfaceId to topology notification."
	REVISION "200805041141Z"
	DESCRIPTION
		"Noise floor variable added."
	REVISION "200610261225Z"
	DESCRIPTION
		"The mib module for MINT."
	::= { wanflex 5 }


mintMIBObjects OBJECT IDENTIFIER 	::= { aquamintMIB 1 }

mint OBJECT IDENTIFIER 	::= { mintMIBObjects 1 }

--- Nodes Table --------------------------------

mintNodesTable OBJECT-TYPE
	SYNTAX  SEQUENCE OF MintNodesEntry
	MAX-ACCESS not-accessible
	STATUS  current
	DESCRIPTION
		"A table of mint nodes."
	::= { mint 1 }


mintNodesEntry OBJECT-TYPE
	SYNTAX  MintNodesEntry
	MAX-ACCESS not-accessible
	STATUS  current
	DESCRIPTION
		"Each entry contains one interface's settings"
	INDEX {
		nodeInterfaceId }
	::= { mintNodesTable 1 }


MintNodesEntry ::= SEQUENCE {

	netAddress              MacAddress,
	nodeType                INTEGER,
	nodeMode                INTEGER,
	linksCount              Integer32,
	nodesCount              Integer32,
	nodeInterfaceId         Integer32,
	protocolEnabled         INTEGER,
	nodeName                DisplayString,
	autoBitrateEnable       INTEGER,
	autoBitrateAddition     Integer32,
	autoBitrateMinLevel     Integer32,
	extraCost               Integer32,
	fixedCost               Integer32,
	nodeID                  Integer32,
	ampLow                  Integer32,
	ampHigh                 Integer32,
	authMode                INTEGER,
	authRelay               INTEGER,
	scrambling              INTEGER,
	compress                INTEGER,
	overTheAirUpgradeEnable INTEGER,
	overTheAirUpgradeSpeed  INTEGER,
	roaming                 INTEGER,
	polling                 INTEGER,
	mintBroadcastRate       Unsigned32,
	noiseFloor              Integer32,
	secretKey               DisplayString,
	linksCountReal          Integer32,
	rxCapacity              Integer32,
	txCapacity              Integer32}


netAddress OBJECT-TYPE
	SYNTAX  MacAddress
	MAX-ACCESS read-only
	STATUS  current
	DESCRIPTION
		"This value contains node's unique network MAC address."
	::= { mintNodesEntry 1 }


nodeType OBJECT-TYPE
	SYNTAX  INTEGER {
			master(1),
			slave(2),
			mesh(3) }
	MAX-ACCESS read-write
	STATUS  current
	DESCRIPTION
		"Node type - master, mesh or slave"
	::= { mintNodesEntry 2 }


nodeMode OBJECT-TYPE
	SYNTAX  INTEGER {
			fixed(1),
			nomadic(2),
			mobile(3) }
	MAX-ACCESS read-write
	STATUS  current
	DESCRIPTION
		"Node mode - fixed, nomadic or mobile"
	::= { mintNodesEntry 3 }


linksCount OBJECT-TYPE
	SYNTAX  Integer32
	MAX-ACCESS read-only
	STATUS  current
	DESCRIPTION
		"The parameter represents current number of neighbors"
	::= { mintNodesEntry 4 }


nodesCount OBJECT-TYPE
	SYNTAX  Integer32
	MAX-ACCESS read-only
	STATUS  current
	DESCRIPTION
		"This value contains total network nodes count."
	::= { mintNodesEntry 5 }


nodeInterfaceId OBJECT-TYPE
	SYNTAX  Integer32 (0..2147483647)
	MAX-ACCESS read-only
	STATUS  current
	DESCRIPTION
		"The index value which uniquely identifies the interface to
		which this entry is applicable.  The interface identified by
		a particular value of this index is the same interface as
		identified by the same value of RFC 1573's ifIndex."
	::= { mintNodesEntry 6 }


protocolEnabled OBJECT-TYPE
	SYNTAX  INTEGER {
			on(1),
			off(2) }
	MAX-ACCESS read-write
	STATUS  current
	DESCRIPTION
		"MINT protocol state - started or stopped"
	::= { mintNodesEntry 7 }


nodeName OBJECT-TYPE
	SYNTAX  DisplayString (SIZE (1..16))
	MAX-ACCESS read-write
	STATUS  current
	DESCRIPTION
		"This value contains human-readable string identifying
		the node unit."
	::= { mintNodesEntry 8 }


autoBitrateEnable OBJECT-TYPE
	SYNTAX  INTEGER {
			on(1),
			off(2) }
	MAX-ACCESS read-write
	STATUS  current
	DESCRIPTION
		"Autobitrate mechanism is either on or off"
	::= { mintNodesEntry 9 }


autoBitrateAddition OBJECT-TYPE
	SYNTAX  Integer32
	MAX-ACCESS read-write
	STATUS  current
	DESCRIPTION
		"Correction factor in dB to autobitrate mechanism"
	::= { mintNodesEntry 10 }


autoBitrateMinLevel OBJECT-TYPE
	SYNTAX  Integer32
	MAX-ACCESS read-write
	STATUS  current
	DESCRIPTION
		"Minimal bitrate level for autobitrate mechanism"
	::= { mintNodesEntry 11 }


extraCost OBJECT-TYPE
	SYNTAX  Integer32 (0..65535)
	MAX-ACCESS read-write
	STATUS  current
	DESCRIPTION
		"Additional cost to all unit's links to neighbors"
	::= { mintNodesEntry 12 }


fixedCost OBJECT-TYPE
	SYNTAX  Integer32 (0..65535)
	MAX-ACCESS read-write
	STATUS  current
	DESCRIPTION
		"Fixed cost to all unit's links to neighbors"
	::= { mintNodesEntry 13 }


nodeID OBJECT-TYPE
	SYNTAX  Integer32 (0..65535)
	MAX-ACCESS read-write
	STATUS  current
	DESCRIPTION
		"Node identification number"
	::= { mintNodesEntry 14 }


ampLow OBJECT-TYPE
	SYNTAX  Integer32
	MAX-ACCESS read-write
	STATUS  current
	DESCRIPTION
		"Signal level threshold in dB below which neighbor is unregistred"
	::= { mintNodesEntry 15 }


ampHigh OBJECT-TYPE
	SYNTAX  Integer32
	MAX-ACCESS read-write
	STATUS  current
	DESCRIPTION
		"Signal level exceeding which the unit might become unit's neighbor"
	::= { mintNodesEntry 16 }


authMode OBJECT-TYPE
	SYNTAX  INTEGER {
			public(1),
			static(2),
			remote(3) }
	MAX-ACCESS read-write
	STATUS  current
	DESCRIPTION
		"Authentication type used - public, static or remote"
	::= { mintNodesEntry 17 }


authRelay OBJECT-TYPE
	SYNTAX  INTEGER {
			on(1),
			off(2) }
	MAX-ACCESS read-write
	STATUS  current
	DESCRIPTION
		"Shows if the unit is used as an authentication relay"
	::= { mintNodesEntry 18 }


scrambling OBJECT-TYPE
	SYNTAX  INTEGER {
			on(1),
			off(2) }
	MAX-ACCESS read-write
	STATUS  current
	DESCRIPTION
		"Shows if data scrambling is enabled or disabled"
	::= { mintNodesEntry 19 }


compress OBJECT-TYPE
	SYNTAX  INTEGER {
			on(1),
			off(2) }
	MAX-ACCESS read-write
	STATUS  current
	DESCRIPTION
		"Shows if data compression is enabled or disabled"
	::= { mintNodesEntry 20 }


overTheAirUpgradeEnable OBJECT-TYPE
	SYNTAX  INTEGER {
			passive(1),
			off(2),
			active(3) }
	MAX-ACCESS read-write
	STATUS  current
	DESCRIPTION
		"Shows the mode of Over-the-Air firmware upgrade mechanism - passive, active or off"
	::= { mintNodesEntry 21 }


overTheAirUpgradeSpeed OBJECT-TYPE
	SYNTAX  INTEGER {
			fast(1),
			normal(2),
			slow(3) }
	MAX-ACCESS read-write
	STATUS  current
	DESCRIPTION
		"Over-the-Air firmware upgrade speed - fast, normal or slow"
	::= { mintNodesEntry 22 }


roaming OBJECT-TYPE
	SYNTAX  INTEGER {
			slave(1),
			off(2),
			leader(3),
			global_leader(4),
			slave_multibs(5),
			slave_global(6),
			slave_multibs_global(7) }
	MAX-ACCESS read-write
	STATUS  current
	DESCRIPTION
		"Current roaming state"
	::= { mintNodesEntry 23 }


polling OBJECT-TYPE
	SYNTAX  INTEGER {
			on(1),
			off(2) }
	MAX-ACCESS read-write
	STATUS  current
	DESCRIPTION
		"State of polling mechanism. On - polling is on, off - polling is off.
                For Polling based firmware only."
	::= { mintNodesEntry 24 }


mintBroadcastRate OBJECT-TYPE
	SYNTAX  Unsigned32
	MAX-ACCESS read-only
	STATUS  current
	DESCRIPTION
		"Broadcast rate index."
	::= { mintNodesEntry 25 }


noiseFloor OBJECT-TYPE
	SYNTAX  Integer32
	MAX-ACCESS read-only
	STATUS  current
	DESCRIPTION
		"The current noise floor in dBm."
	::= { mintNodesEntry 26 }


secretKey OBJECT-TYPE
	SYNTAX  DisplayString (SIZE (0..256))
	MAX-ACCESS read-write
	STATUS  current
	DESCRIPTION
		"The secret key for authentication and data scrambling."
	::= { mintNodesEntry 27 }

linksCountReal OBJECT-TYPE
	SYNTAX  Integer32
	MAX-ACCESS read-only
	STATUS  current
	DESCRIPTION
		"The parameter represents current number of real neighbors (exclude joins)"
	::= { mintNodesEntry 28 }

rxCapacity OBJECT-TYPE
	SYNTAX  Integer32
	MAX-ACCESS read-only
	STATUS  current
	DESCRIPTION
		"The parameter represents current estimated RX capacity in Kbps.
                For TDMA based firmware only."
	::= { mintNodesEntry 29 }

txCapacity OBJECT-TYPE
	SYNTAX  Integer32
	MAX-ACCESS read-only
	STATUS  current
	DESCRIPTION
		"The parameter represents current estimated TX capacity in Kbps.
                For TDMA based firmware only."
	::= { mintNodesEntry 30 }

--- Links Table --------------------------------

mintLinksTable OBJECT-TYPE
	SYNTAX  SEQUENCE OF MintLinksEntry
	MAX-ACCESS not-accessible
	STATUS  current
	DESCRIPTION
		"A table of links"
	::= { mint 2 }


mintLinksEntry OBJECT-TYPE
	SYNTAX  MintLinksEntry
	MAX-ACCESS not-accessible
	STATUS  current
	DESCRIPTION
		"Each entry contains one interface's settings"
	INDEX {
		mintInterfaceId,
		neighborAddress }
	::= { mintLinksTable 1 }


MintLinksEntry ::= SEQUENCE {

	mintInterfaceId   Integer32,
	neighborAddress   MacAddress,
	linkName          DisplayString,
	linkCost          Integer32,
	monitorAmpIn      Integer32,
	monitorAmpOut     Integer32,
	workingAmpIn      Integer32,
	workingAmpOut     Integer32,
	curBitrateRX      Integer32,
	curBitrateTX      Integer32,
	curLoadRX         Integer32,
	curLoadPPSRX      Integer32,
	curLoadTX         Integer32,
	curLoadPPSTX      Integer32,
	outputBytes       Counter32,
	outputPackets     Counter32,
	inputBytes        Counter32,
	inputPackets      Counter32,
	retriesPercentTX  Unsigned32,
	errorsPercentTX   Unsigned32,
	linkDistance      Integer32,
	curBitrateRXindex Integer32,
	curBitrateTXindex Integer32,
	retriesPercentRX  Unsigned32,
	errorsPercentRX   Unsigned32,
	neighborIfIndex   Unsigned32,
	curRXpower        Integer32,
	curTXpower        Integer32,
	linkDistanceMeters Integer32,
	rxRSSI Integer32 }


mintInterfaceId OBJECT-TYPE
	SYNTAX  Integer32 (0..2147483647)
	MAX-ACCESS read-only
	STATUS  current
	DESCRIPTION
		"The index value which uniquely identifies the interface to
		which this entry is applicable.  The interface identified by
		a particular value of this index is the same interface as
		identified by the same value of RFC 1573's ifIndex."
	::= { mintLinksEntry 1 }


neighborAddress OBJECT-TYPE
	SYNTAX  MacAddress
	MAX-ACCESS read-only
	STATUS  current
	DESCRIPTION
		"This value contains MAC address of node's neighbor"
	::= { mintLinksEntry 2 }


linkName OBJECT-TYPE
	SYNTAX  DisplayString
	MAX-ACCESS read-only
	STATUS  current
	DESCRIPTION
		"Link name."
	::= { mintLinksEntry 3 }


linkCost OBJECT-TYPE
	SYNTAX  Integer32
	MAX-ACCESS read-only
	STATUS  current
	DESCRIPTION
		"The cost of the connection to the neighbor"
	::= { mintLinksEntry 4 }


monitorAmpIn OBJECT-TYPE
	SYNTAX  Integer32
	MAX-ACCESS read-only
	STATUS  current
	DESCRIPTION
		"Input reference signal level (SNR) in dB"
	::= { mintLinksEntry 5 }


monitorAmpOut OBJECT-TYPE
	SYNTAX  Integer32
	MAX-ACCESS read-only
	STATUS  current
	DESCRIPTION
		"Output reference signal level (SNR) in dB"
	::= { mintLinksEntry 6 }


workingAmpIn OBJECT-TYPE
	SYNTAX  Integer32
	MAX-ACCESS read-only
	STATUS  current
	DESCRIPTION
		"Input signal level in dB for current RX bitrate"
	::= { mintLinksEntry 7 }


workingAmpOut OBJECT-TYPE
	SYNTAX  Integer32
	MAX-ACCESS read-only
	STATUS  current
	DESCRIPTION
		"Output signal level in dB for current TX bitrate"
	::= { mintLinksEntry 8 }


curBitrateRX OBJECT-TYPE
	SYNTAX  Integer32
	MAX-ACCESS read-only
	STATUS  current
	DESCRIPTION
		"Current RX bitrate in Kb/s"
	::= { mintLinksEntry 9 }


curBitrateTX OBJECT-TYPE
	SYNTAX  Integer32
	MAX-ACCESS read-only
	STATUS  current
	DESCRIPTION
		"Current TX bitrate in Kb/s"
	::= { mintLinksEntry 10 }


curLoadRX OBJECT-TYPE
	SYNTAX  Integer32
	MAX-ACCESS read-only
	STATUS  current
	DESCRIPTION
		"Current RX link load from the neighbor in Kbit/s"
	::= { mintLinksEntry 11 }


curLoadPPSRX OBJECT-TYPE
	SYNTAX  Integer32
	MAX-ACCESS read-only
	STATUS  current
	DESCRIPTION
		"Current RX link load from the neighbor in PPS"
	::= { mintLinksEntry 12 }


curLoadTX OBJECT-TYPE
	SYNTAX  Integer32
	MAX-ACCESS read-only
	STATUS  current
	DESCRIPTION
		"Current TX link load to the neighbor in Kbit/s"
	::= { mintLinksEntry 13 }


curLoadPPSTX OBJECT-TYPE
	SYNTAX  Integer32
	MAX-ACCESS read-only
	STATUS  current
	DESCRIPTION
		"Current TX link load to the neighbor in PPS"
	::= { mintLinksEntry 14 }


outputBytes OBJECT-TYPE
	SYNTAX  Counter32
	MAX-ACCESS read-only
	STATUS  current
	DESCRIPTION
		"Output bytes number to the neighbor"
	::= { mintLinksEntry 15 }


outputPackets OBJECT-TYPE
	SYNTAX  Counter32
	MAX-ACCESS read-only
	STATUS  current
	DESCRIPTION
		"Output packets number to the neighbor"
	::= { mintLinksEntry 16 }


inputBytes OBJECT-TYPE
	SYNTAX  Counter32
	MAX-ACCESS read-only
	STATUS  current
	DESCRIPTION
		"Input bytes number from the neighbor"
	::= { mintLinksEntry 17 }


inputPackets OBJECT-TYPE
	SYNTAX  Counter32
	MAX-ACCESS read-only
	STATUS  current
	DESCRIPTION
		"Input packets number from the neighbor"
	::= { mintLinksEntry 18 }


retriesPercentTX OBJECT-TYPE
	SYNTAX  Unsigned32
	MAX-ACCESS read-only
	STATUS  current
	DESCRIPTION
		"Transmit retries percent."
	::= { mintLinksEntry 19 }


errorsPercentTX OBJECT-TYPE
	SYNTAX  Unsigned32
	MAX-ACCESS read-only
	STATUS  current
	DESCRIPTION
		"Transmit errors percent."
	::= { mintLinksEntry 20 }


linkDistance OBJECT-TYPE
	SYNTAX  Integer32
	MAX-ACCESS read-only
	STATUS  current
	DESCRIPTION
		"Link distance in Km."
	::= { mintLinksEntry 21 }


curBitrateRXindex OBJECT-TYPE
	SYNTAX  Integer32
	MAX-ACCESS read-only
	STATUS  current
	DESCRIPTION
		"Current RX bitrate index"
	::= { mintLinksEntry 22 }


curBitrateTXindex OBJECT-TYPE
	SYNTAX  Integer32
	MAX-ACCESS read-only
	STATUS  current
	DESCRIPTION
		"Current TX bitrate index"
	::= { mintLinksEntry 23 }


retriesPercentRX OBJECT-TYPE
	SYNTAX  Unsigned32
	MAX-ACCESS read-only
	STATUS  current
	DESCRIPTION
		"Transmit retries percent on remote side."
	::= { mintLinksEntry 24 }


errorsPercentRX OBJECT-TYPE
	SYNTAX  Unsigned32
	MAX-ACCESS read-only
	STATUS  current
	DESCRIPTION
		"Transmit errors percent on remote side."
	::= { mintLinksEntry 25 }


neighborIfIndex OBJECT-TYPE
	SYNTAX  Unsigned32
	MAX-ACCESS read-only
	STATUS  current
	DESCRIPTION
		"The interface index of neighbor."
	::= { mintLinksEntry 26 }


curRXpower OBJECT-TYPE
	SYNTAX  Integer32
	MAX-ACCESS read-only
	STATUS  current
	DESCRIPTION
		"Current transmit power from remote side in tenth of dBm."
	::= { mintLinksEntry 27 }


curTXpower OBJECT-TYPE
	SYNTAX  Integer32
	MAX-ACCESS read-only
	STATUS  current
	DESCRIPTION
		"Current transmit power in tenth of dBm."
	::= { mintLinksEntry 28 }


linkDistanceMeters OBJECT-TYPE
	SYNTAX  Integer32
	MAX-ACCESS read-only
	STATUS  current
	DESCRIPTION
		"Link distance in meters."
	::= { mintLinksEntry 29 }

rxRSSI  OBJECT-TYPE
	SYNTAX  Integer32
	MAX-ACCESS read-only
	STATUS  current
	DESCRIPTION
		"Link RX RSSI in dBm"
	::= { mintLinksEntry 30 }


mintLostNeighbor OBJECT IDENTIFIER 	::= { mint 3 }

lostNeighborIfIndex OBJECT-TYPE
	SYNTAX  Integer32
	MAX-ACCESS accessible-for-notify
	STATUS  current
	DESCRIPTION
		"The index value which uniquely identifies the interface to
		which this entry is applicable.  The interface identified by
		a particular value of this index is the same interface as
		identified by the same value of RFC 1573's ifIndex."
	::= { mintLostNeighbor 1 }


lostNeighborNetAddress OBJECT-TYPE
	SYNTAX  OCTET STRING (SIZE (6))
	MAX-ACCESS accessible-for-notify
	STATUS  current
	DESCRIPTION
		"This value contains node's unique network MAC address."
	::= { mintLostNeighbor 2 }


lostNeighborReason OBJECT-TYPE
	SYNTAX  INTEGER {
			broken(1),
			lost(2),
			other(3) }
	MAX-ACCESS accessible-for-notify
	STATUS  current
	DESCRIPTION
		"This value contains reason, due to which connection to neighbour was lost."
	::= { mintLostNeighbor 3 }


lostNeighborName OBJECT-TYPE
	SYNTAX  DisplayString
	MAX-ACCESS accessible-for-notify
	STATUS  current
	DESCRIPTION
		"This value contains node's name."
	::= { mintLostNeighbor 4 }


mintPtpLink OBJECT IDENTIFIER 	::= { mint 4 }

ptpInterfaceId OBJECT-TYPE
	SYNTAX  Integer32 (0..2147483647)
	MAX-ACCESS read-only
	STATUS  current
	DESCRIPTION
		"The index value which uniquely identifies the interface to
		which this entry is applicable.  The interface identified by
		a particular value of this index is the same interface as
		identified by the same value of RFC 1573's ifIndex."
	::= { mintPtpLink 1 }


ptpNeighborAddress OBJECT-TYPE
	SYNTAX  MacAddress
	MAX-ACCESS read-only
	STATUS  current
	DESCRIPTION
		"This value contains MAC address of node's neighbor"
	::= { mintPtpLink 2 }


ptpLinkName OBJECT-TYPE
	SYNTAX  DisplayString
	MAX-ACCESS read-only
	STATUS  current
	DESCRIPTION
		"Link name."
	::= { mintPtpLink 3 }


ptpLinkCost OBJECT-TYPE
	SYNTAX  Integer32
	MAX-ACCESS read-only
	STATUS  current
	DESCRIPTION
		"The cost of the connection to the neighbor"
	::= { mintPtpLink 4 }


ptpMonitorAmpIn OBJECT-TYPE
	SYNTAX  Integer32
	MAX-ACCESS read-only
	STATUS  current
	DESCRIPTION
		"Reference input signal level (SNR) in dB"
	::= { mintPtpLink 5 }


ptpMonitorAmpOut OBJECT-TYPE
	SYNTAX  Integer32
	MAX-ACCESS read-only
	STATUS  current
	DESCRIPTION
		"Reference output signal level (SNR) in dB"
	::= { mintPtpLink 6 }


ptpWorkingAmpIn OBJECT-TYPE
	SYNTAX  Integer32
	MAX-ACCESS read-only
	STATUS  current
	DESCRIPTION
		"Input signal level in dB for current RX bitrate"
	::= { mintPtpLink 7 }


ptpWorkingAmpOut OBJECT-TYPE
	SYNTAX  Integer32
	MAX-ACCESS read-only
	STATUS  current
	DESCRIPTION
		"Output signal level in dB for current TX bitrate"
	::= { mintPtpLink 8 }


ptpCurBitrateRX OBJECT-TYPE
	SYNTAX  Integer32
	MAX-ACCESS read-only
	STATUS  current
	DESCRIPTION
		"Current RX bitrate in Kb/s"
	::= { mintPtpLink 9 }


ptpCurBitrateTX OBJECT-TYPE
	SYNTAX  Integer32
	MAX-ACCESS read-only
	STATUS  current
	DESCRIPTION
		"Current TX bitrate in Kb/s"
	::= { mintPtpLink 10 }


ptpCurLoadRX OBJECT-TYPE
	SYNTAX  Integer32
	MAX-ACCESS read-only
	STATUS  current
	DESCRIPTION
		"Current RX link load in Kbit/ss"
	::= { mintPtpLink 11 }


ptpCurLoadPPSRX OBJECT-TYPE
	SYNTAX  Integer32
	MAX-ACCESS read-only
	STATUS  current
	DESCRIPTION
		"Current RX link load in PPS"
	::= { mintPtpLink 12 }


ptpCurLoadTX OBJECT-TYPE
	SYNTAX  Integer32
	MAX-ACCESS read-only
	STATUS  current
	DESCRIPTION
		"Current TX link load Kbit/s"
	::= { mintPtpLink 13 }


ptpCurLoadPPSTX OBJECT-TYPE
	SYNTAX  Integer32
	MAX-ACCESS read-only
	STATUS  current
	DESCRIPTION
		"Current TX link load in PPS"
	::= { mintPtpLink 14 }


ptpOutputBytes OBJECT-TYPE
	SYNTAX  Counter32
	MAX-ACCESS read-only
	STATUS  current
	DESCRIPTION
		"Output bytes number from the neighbor"
	::= { mintPtpLink 15 }


ptpOutputPackets OBJECT-TYPE
	SYNTAX  Counter32
	MAX-ACCESS read-only
	STATUS  current
	DESCRIPTION
		"Output packets number from the neighbor"
	::= { mintPtpLink 16 }


ptpInputBytes OBJECT-TYPE
	SYNTAX  Counter32
	MAX-ACCESS read-only
	STATUS  current
	DESCRIPTION
		"Input bytes number from the neighbor"
	::= { mintPtpLink 17 }


ptpInputPackets OBJECT-TYPE
	SYNTAX  Counter32
	MAX-ACCESS read-only
	STATUS  current
	DESCRIPTION
		"Input packets number from the neighbor"
	::= { mintPtpLink 18 }


ptpRetriesPercentTX OBJECT-TYPE
	SYNTAX  Unsigned32
	MAX-ACCESS read-only
	STATUS  current
	DESCRIPTION
		"Transmit retries percent."
	::= { mintPtpLink 19 }


ptpErrorsPercentTX OBJECT-TYPE
	SYNTAX  Unsigned32
	MAX-ACCESS read-only
	STATUS  current
	DESCRIPTION
		"Transmit errors percent."
	::= { mintPtpLink 20 }


ptpLinkDistance OBJECT-TYPE
	SYNTAX  Integer32
	MAX-ACCESS read-only
	STATUS  current
	DESCRIPTION
		"Link distance in km."
	::= { mintPtpLink 21 }


ptpCurBitrateRXindex OBJECT-TYPE
	SYNTAX  Integer32
	MAX-ACCESS read-only
	STATUS  current
	DESCRIPTION
		"Current RX bitrate index"
	::= { mintPtpLink 22 }


ptpCurBitrateTXindex OBJECT-TYPE
	SYNTAX  Integer32
	MAX-ACCESS read-only
	STATUS  current
	DESCRIPTION
		"Current TX bitrate index"
	::= { mintPtpLink 23 }


ptpRetriesPercentRX OBJECT-TYPE
	SYNTAX  Unsigned32
	MAX-ACCESS read-only
	STATUS  current
	DESCRIPTION
		"Transmit retries percent from remote side."
	::= { mintPtpLink 24 }


ptpErrorsPercentRX OBJECT-TYPE
	SYNTAX  Unsigned32
	MAX-ACCESS read-only
	STATUS  current
	DESCRIPTION
		"Transmit errors percent from remote side."
	::= { mintPtpLink 25 }


ptpNeighborIfIndex OBJECT-TYPE
	SYNTAX  Unsigned32
	MAX-ACCESS read-only
	STATUS  current
	DESCRIPTION
		"The interface index of neighbor."
	::= { mintPtpLink 26 }


ptpCurRXpower OBJECT-TYPE
	SYNTAX  Integer32
	MAX-ACCESS read-only
	STATUS  current
	DESCRIPTION
		"Current transmit power on remote side in tenth of dBm."
	::= { mintPtpLink 27 }


ptpCurTXpower OBJECT-TYPE
	SYNTAX  Integer32
	MAX-ACCESS read-only
	STATUS  current
	DESCRIPTION
		"Current transmit power in tenth of dBm."
	::= { mintPtpLink 28 }


ptpLinkDistanceMeters OBJECT-TYPE
	SYNTAX  Integer32
	MAX-ACCESS read-only
	STATUS  current
	DESCRIPTION
		"Link distance in meters."
	::= { mintPtpLink 29 }

ptpLinkRxRSSI OBJECT-TYPE
	SYNTAX  Integer32
	MAX-ACCESS read-only
	STATUS  current
	DESCRIPTION
		"Link RX RSSI in dBm."
	::= { mintPtpLink 30 }


mintLinkStatus OBJECT-TYPE
	SYNTAX  INTEGER {
			up(1),
			down(2),
			multipoint(3) }
	MAX-ACCESS read-only
	STATUS  current
	DESCRIPTION
		"Status of ptp MINT radio link.
		Multipoint(3) is returned when
		device has multiple radio links."
	::= { mint 5 }


mintMIBNotificationsPrefix OBJECT IDENTIFIER 	::= { aquamintMIB 2 }

mintMIBNotifications OBJECT IDENTIFIER 	::= { mintMIBNotificationsPrefix 0 }

mintMIBConformance OBJECT IDENTIFIER 	::= { aquamintMIB 3 }


mintTopologyNotification NOTIFICATION-TYPE
	OBJECTS {
		sysSerialNumber,
		sysTrapSequence,
		nodeInterfaceId,
		netAddress,
		neighborAddress,
		linkCost,
		neighborIfIndex}
	STATUS  current
	DESCRIPTION
		"A mintTopologyNotification is sent  at the MESH Topology information changed."
	::= { mintMIBNotifications 1 }


mintNewNeighborNotification NOTIFICATION-TYPE
	OBJECTS {
		sysSerialNumber,
		sysTrapSequence,
		mintInterfaceId,
		neighborAddress,
		linkName}
	STATUS  current
	DESCRIPTION
		"A mintNewNeighborNotification is sent at the new neighbor appeared."
	::= { mintMIBNotifications 2 }


mintNeighborLostNotification NOTIFICATION-TYPE
	OBJECTS {
		sysSerialNumber,
		sysTrapSequence,
		lostNeighborIfIndex,
		lostNeighborNetAddress,
		lostNeighborReason,
		lostNeighborName}
	STATUS  current
	DESCRIPTION
		"A mintNeighborLostNotification is sent at the Neighbor disappeared."
	::= { mintMIBNotifications 3 }


mintLinkRetriesChanged NOTIFICATION-TYPE
	OBJECTS {
		sysSerialNumber,
		sysTrapSequence,
		retriesPercentTX,
		mintInterfaceId,
		neighborAddress}
	STATUS  current
	DESCRIPTION
		"A mintLinkRetriesChanged is sent at the retries move to other level."
	::= { mintMIBNotifications 4 }


mintLinkBitrateChanged NOTIFICATION-TYPE
	OBJECTS {
		sysSerialNumber,
		sysTrapSequence,
		curBitrateTX,
		nodeInterfaceId,
		neighborAddress}
	STATUS  current
	DESCRIPTION
		"A mintLinkBitrateChanged is sent at the Bitrate on Link changed."
	::= { mintMIBNotifications 5 }


minLinkSignalLevelChanged NOTIFICATION-TYPE
	OBJECTS {
		sysSerialNumber,
		sysTrapSequence,
		monitorAmpOut,
		mintInterfaceId,
		neighborAddress}
	STATUS  current
	DESCRIPTION
		"A minLinkSignalLevelChanged is sent at the level of signal changed on specified link."
	::= { mintMIBNotifications 6 }

mintMIBGroup OBJECT-GROUP
	OBJECTS {
		netAddress,
		nodeType,
		nodeMode,
		linksCount,
		nodesCount,
		nodeInterfaceId,
		protocolEnabled,
		nodeName,
		autoBitrateEnable,
		autoBitrateAddition,
		autoBitrateMinLevel,
		extraCost,
		fixedCost,
		nodeID,
		ampLow,
		ampHigh,
		authMode,
		authRelay,
		scrambling,
		compress,
		overTheAirUpgradeEnable,
		overTheAirUpgradeSpeed,
		roaming,
		polling,
		mintInterfaceId,
		neighborAddress,
		linkName,
		linkCost,
		monitorAmpIn,
		monitorAmpOut,
		workingAmpIn,
		workingAmpOut,
		curBitrateRX,
		curBitrateTX,
		curLoadRX,
		curLoadPPSRX,
		curLoadTX,
		curLoadPPSTX,
		outputBytes,
		outputPackets,
		inputBytes,
		inputPackets,
		retriesPercentTX,
		errorsPercentTX,
		linkDistance,
		curBitrateRXindex,
		curBitrateTXindex,
		lostNeighborIfIndex,
		lostNeighborNetAddress,
		lostNeighborReason,
		lostNeighborName,
		mintBroadcastRate,
		noiseFloor,
		retriesPercentRX,
		errorsPercentRX,
		neighborIfIndex,
		curRXpower,
		curTXpower,
		secretKey,
                linksCountReal,
		linkDistanceMeters,
		ptpInterfaceId,
		ptpNeighborAddress,
		ptpLinkName,
		ptpLinkCost,
		ptpMonitorAmpIn,
		ptpMonitorAmpOut,
		ptpWorkingAmpIn,
		ptpWorkingAmpOut,
		ptpCurBitrateRX,
		ptpCurBitrateTX,
		ptpCurLoadRX,
		ptpCurLoadPPSRX,
		ptpCurLoadTX,
		ptpCurLoadPPSTX,
		ptpOutputBytes,
		ptpOutputPackets,
		ptpInputBytes,
		ptpInputPackets,
		ptpRetriesPercentTX,
		ptpErrorsPercentTX,
		ptpLinkDistance,
		ptpCurBitrateRXindex,
		ptpCurBitrateTXindex,
		ptpRetriesPercentRX,
		ptpErrorsPercentRX,
		ptpNeighborIfIndex,
		ptpCurRXpower,
		ptpCurTXpower,
		ptpLinkDistanceMeters,
		ptpLinkRxRSSI,
		mintLinkStatus }
	STATUS  current
	DESCRIPTION ""
	::= { mintMIBConformance 2 }

mintNotifications NOTIFICATION-GROUP
	NOTIFICATIONS {
		mintTopologyNotification,
		mintNewNeighborNotification,
		mintNeighborLostNotification,
		mintLinkRetriesChanged,
		mintLinkBitrateChanged,
		minLinkSignalLevelChanged }
	STATUS  current
	DESCRIPTION ""
	::= { mintMIBConformance 1 }

END

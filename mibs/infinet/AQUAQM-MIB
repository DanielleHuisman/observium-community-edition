AQUAQM-MIB DEFINITIONS ::= BEGIN

IMPORTS
	wanflex
		FROM INFINET-MIB
	MODULE-IDENTITY,
	OBJECT-TYPE,
	Counter32,
	Integer32,
	IpAddress
		FROM SNMPv2-SMI
	OBJECT-GROUP,
	MODULE-COMPLIANCE
		FROM SNMPv2-CONF;

aquaqmMIB MODULE-IDENTITY
	LAST-UPDATED "201102160826Z"
	ORGANIZATION "Infinet Wireless Ltd."
	CONTACT-INFO
		"Andrew Nesheret

		Postal: Infinet Wireless Ltd.,
		        Russia, Ekaterinburg,
		        Serafimi Deryabinoi st, 24

		Phone:  +7 343 253 1533
		Email:  A.Nesheret@infinetwireless.com"
	DESCRIPTION
		"The mib module, containing various WanFlex options."
	REVISION "201102160826Z"
	DESCRIPTION
		"HTB branch added."
	REVISION "200711081255Z"
	DESCRIPTION
		"Contact information changed."
	REVISION "200408161910Z"
	DESCRIPTION
		"The mib module, containing Quality-of-Service manager statistics."
	::= { wanflex 4 }


qmTable OBJECT-TYPE
	SYNTAX  SEQUENCE OF QmEntry
	MAX-ACCESS not-accessible
	STATUS  current
	DESCRIPTION
		"A table of Quality Manager statistics by QoS channel number"
	::= { aquaqmMIB 1 }


qmEntry OBJECT-TYPE
	SYNTAX  QmEntry
	MAX-ACCESS not-accessible
	STATUS  current
	DESCRIPTION
		"Each entry contains one channel statistics"
	INDEX {
		qmChannel }
	::= { qmTable 1 }


QmEntry ::= SEQUENCE {

	qmChannel        INTEGER,
	qmPriority       INTEGER,
	qmClass          INTEGER,
	qmTo             IpAddress,
	qmMax            INTEGER,
	qmMaxPps         INTEGER,
	qmCur            Integer32,
	qmCurPps         Integer32,
	qmPackets        Counter32,
	qmPacketsDropped Counter32,
	qmBytes          Counter32,
	qmBytesDropped   Counter32 }


qmChannel OBJECT-TYPE
	SYNTAX  INTEGER (1..200)
	MAX-ACCESS read-only
	STATUS  current
	DESCRIPTION
		"Quality Manager channel number, ranging from 1 to 200"
	::= { qmEntry 1 }


qmPriority OBJECT-TYPE
	SYNTAX  INTEGER (0..16)
	MAX-ACCESS read-only
	STATUS  current
	DESCRIPTION
		"Priority setting for this channel, where 0 - highest priority,
                16 - lowest priority."
	::= { qmEntry 2 }


qmClass OBJECT-TYPE
	SYNTAX  INTEGER (0..64)
	MAX-ACCESS read-only
	STATUS  current
	DESCRIPTION
		"Abstract service class for this channel, where 0 - no specific
		class, 1-64 - class number."
	::= { qmEntry 3 }


qmTo OBJECT-TYPE
	SYNTAX  IpAddress
	MAX-ACCESS read-only
	STATUS  current
	DESCRIPTION
		"The address, all this class traffic is redirected to."
	::= { qmEntry 4 }


qmMax OBJECT-TYPE
	SYNTAX  INTEGER (0..10000)
	MAX-ACCESS read-only
	STATUS  current
	DESCRIPTION
		"Maximum bandwidth for this channel, where values 10-10000 are
		bandwidth limited to in kbits per second, 0 - no limit for
		this channel."
	::= { qmEntry 5 }


qmMaxPps OBJECT-TYPE
	SYNTAX  INTEGER (0..2147483647)
	MAX-ACCESS read-only
	STATUS  current
	DESCRIPTION
		"Maximum packets per second rate for this channel, where values
		50-2147483647 are the limit, 0 - no limit for this channel."
	::= { qmEntry 6 }


qmCur OBJECT-TYPE
	SYNTAX  Integer32
	MAX-ACCESS read-only
	STATUS  current
	DESCRIPTION
		"Current flow for this channel in kbits per second."
	::= { qmEntry 7 }


qmCurPps OBJECT-TYPE
	SYNTAX  Integer32
	MAX-ACCESS read-only
	STATUS  current
	DESCRIPTION
		"Current flow for this channel in packets per second."
	::= { qmEntry 8 }


qmPackets OBJECT-TYPE
	SYNTAX  Counter32
	MAX-ACCESS read-only
	STATUS  current
	DESCRIPTION
		"Total number of packets tried to pass thorough this channel."
	::= { qmEntry 9 }


qmPacketsDropped OBJECT-TYPE
	SYNTAX  Counter32
	MAX-ACCESS read-only
	STATUS  current
	DESCRIPTION
		"Number of packets dropped by this channel."
	::= { qmEntry 10 }


qmBytes OBJECT-TYPE
	SYNTAX  Counter32
	MAX-ACCESS read-only
	STATUS  current
	DESCRIPTION
		"Total number of octets tried to pass thorough this channel."
	::= { qmEntry 11 }


qmBytesDropped OBJECT-TYPE
	SYNTAX  Counter32
	MAX-ACCESS read-only
	STATUS  current
	DESCRIPTION
		"Number of octets dropped by this channel."
	::= { qmEntry 12 }


qmHTB OBJECT IDENTIFIER 	::= { aquaqmMIB 2 }

qmHtbCurrentQL OBJECT-TYPE
	SYNTAX  Gauge32
	MAX-ACCESS read-only
	STATUS  current
	DESCRIPTION
		"Current number of packets in all packet queues
		 managed by Hierarchical Token Bucket algorithm."
	::= { qmHTB 1 }


qmHtbMaxQL OBJECT-TYPE
	SYNTAX  Gauge32
	MAX-ACCESS read-only
	STATUS  current
	DESCRIPTION
		"Maximum known total number of packets in all HTB
		 packet queues since last qm statistics clearing."
	::= { qmHTB 2 }


qmHtbSystemDrop OBJECT-TYPE
	SYNTAX  Gauge32
	MAX-ACCESS read-only
	STATUS  current
	DESCRIPTION
		"Number of packets dropped due to accidental overflow
		 of global transmission queue while enqueuing the packets
		 shaped by Hierarchical Token Bucket algorithm."
	::= { qmHTB 3 }


aquaqmMIBConformance OBJECT IDENTIFIER 	::= { aquaqmMIB 3 }

aquaqmMIBCompliances OBJECT IDENTIFIER 	::= { aquaqmMIBConformance 1 }

aquaqmMIBGroups OBJECT IDENTIFIER 	::= { aquaqmMIBConformance 2 }


-- compliance statements

aquaqmMIBCompliance MODULE-COMPLIANCE
	STATUS  current
	DESCRIPTION
		"The compliance statement for Infinet wireless routers."
	MODULE
	MANDATORY-GROUPS {
			qmGroup }
	::= { aquaqmMIBCompliances 1 }

-- units of conformance

qmGroup OBJECT-GROUP
	OBJECTS {
		qmChannel,
		qmPriority,
		qmClass,
		qmTo,
		qmMax,
		qmMaxPps,
		qmCur,
		qmCurPps,
		qmPackets,
		qmPacketsDropped,
		qmBytes,
		qmBytesDropped,
		qmHtbCurrentQL,
		qmHtbMaxQL,
		qmHtbSystemDrop }
	STATUS  current
	DESCRIPTION
		"The qm group of objects provided for observation of various
		QoS statistics."
	::= { aquaqmMIBGroups 1 }

END

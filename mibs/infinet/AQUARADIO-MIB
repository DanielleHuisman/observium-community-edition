AQUARADIO-MIB DEFINITIONS ::= BEGIN

IMPORTS
	DisplayString,
	MacAddress,
	TEXTUAL-CONVENTION
		FROM SNMPv2-TC
	ifIndex
		FROM IF-MIB
	wanflex
		FROM INFINET-MIB
	sysSerialNumber,
	sysTrapSequence
		FROM AQUASYSTEM-MIB
	MODULE-IDENTITY,
	OBJECT-TYPE,
	NOTIFICATION-TYPE,
	Counter32,
	Integer32,
	Unsigned32
		FROM SNMPv2-SMI
	OBJECT-GROUP,
	NOTIFICATION-GROUP,
	MODULE-COMPLIANCE
		FROM SNMPv2-CONF;

aquaradioMIB MODULE-IDENTITY
	LAST-UPDATED "201409220556Z"
	ORGANIZATION "Infinet Wireless Ltd."
	CONTACT-INFO
		"Andrew Nesheret

		Postal: Infinet Wireless Ltd,
		        Russia, Ekaterinburg,
		        Serafimi Deryabinoi st, 24

		Phone:  +7 343 253 1533
		Email:  support@infinetwireless.com"
	DESCRIPTION
		"The mib module for Revolution radio modules. Based on IEEE802dot11
		mib module."
	REVISION "201409220556Z"
	DESCRIPTION
		"irrelevant(0) value added to rmModulation."
	REVISION "201307260427Z"
	DESCRIPTION
		"dot11OperationTable and dot11CountersTable removed."
	REVISION "201304081140Z"
	DESCRIPTION
		"radioNotifications added"
	REVISION "201304081059Z"
	DESCRIPTION
		"rmSelectChannel added in rmPropertiesTable"
	REVISION "200911101156Z"
	DESCRIPTION
		"Power in tenth dBm."
	REVISION "200910300838Z"
	DESCRIPTION
		"Added RF Bandwidth"
	REVISION "200905121122Z"
	DESCRIPTION
		"Display HINT for rSID"
	REVISION "200711081309Z"
	DESCRIPTION
		"Contact Info changed, SMI syntax corrected."
	REVISION "200410111628Z"
	DESCRIPTION
		"The mib module for Revolution radio modules. Based on IEEE802dot11
		mib module."
	::= { wanflex 2 }


RadioSID ::= TEXTUAL-CONVENTION
	DISPLAY-HINT "x"
	STATUS  current
	DESCRIPTION
		"Represents Radio System Identifier"
	SYNTAX Integer32


rmPropertiesTable OBJECT-TYPE
	SYNTAX  SEQUENCE OF RmPropertiesEntry
	MAX-ACCESS not-accessible
	STATUS  current
	DESCRIPTION
		"This table contains various radiomodule operation mode settings."
	::= { aquaradioMIB 1 }


rmPropertiesEntry OBJECT-TYPE
	SYNTAX  RmPropertiesEntry
	MAX-ACCESS not-accessible
	STATUS  current
	DESCRIPTION
		"An entry in the rmPropertiesTable Table."
	INDEX {
		rmPropertiesIfIndex }
	::= { rmPropertiesTable 1 }


RmPropertiesEntry ::= SEQUENCE {

	rmPropertiesIfIndex Integer32,
	rmType              OCTET STRING,
	rmFrequency         Integer32,
	rmBitRate           Integer32,
	rmSid               RadioSID,
	rmCurPowerLevel     Integer32,
	rmModulation        INTEGER,
	rmAntenna           INTEGER,
	rmDistance          Integer32,
	rmBurst             INTEGER,
	rmLongRange         INTEGER,
	rmPowerCtl          INTEGER,
	rmTXRT              Integer32,
	rmTXVRT             Integer32,
	rmPTP               INTEGER,
	rmWOCD              INTEGER,
	rmBCsid             INTEGER,
	rmDistanceAuto      INTEGER,
	rmNoiseFloor        Integer32,
	rmBandwidth         Unsigned32,
	rmChainMode         INTEGER,
	rmSelectChannel     INTEGER }


rmPropertiesIfIndex OBJECT-TYPE
	SYNTAX  Integer32 (0..2147483647)
	MAX-ACCESS read-only
	STATUS  current
	DESCRIPTION
		"The index value which uniquely identifies the interface to
		which this entry is applicable.  The interface identified by
		a particular value of this index is the same interface as
		identified by the same value of RFC 1573's ifIndex."
	::= { rmPropertiesEntry 1 }


rmType OBJECT-TYPE
	SYNTAX  OCTET STRING
	MAX-ACCESS read-only
	STATUS  current
	DESCRIPTION
		"Radiomodule type."
	::= { rmPropertiesEntry 2 }


rmFrequency OBJECT-TYPE
	SYNTAX  Integer32
	UNITS
		"KHz"
	MAX-ACCESS read-write
	STATUS  current
	DESCRIPTION
		"This value indicates radiomodule's operating frequency in KHz."
	::= { rmPropertiesEntry 3 }


rmBitRate OBJECT-TYPE
	SYNTAX  Integer32
	MAX-ACCESS read-write
	STATUS  current
	DESCRIPTION
		"This value indicates radiomodule's current bitrate in kbits
		per second."
	::= { rmPropertiesEntry 4 }


rmSid OBJECT-TYPE
	SYNTAX  RadioSID
	MAX-ACCESS read-write
	STATUS  current
	DESCRIPTION
		"This value indicates radiomodule's sid."
	::= { rmPropertiesEntry 5 }


rmCurPowerLevel OBJECT-TYPE
	SYNTAX  Integer32
	UNITS
		"tenth dBm."
	MAX-ACCESS read-write
	STATUS  current
	DESCRIPTION
		"This value indicates radiomodule's power output level (tenth dBm)."
	::= { rmPropertiesEntry 6 }


rmModulation OBJECT-TYPE
	SYNTAX  INTEGER {
			irrelevant(0),
			cck(1),
			mok(2) }
	MAX-ACCESS read-write
	STATUS  current
	DESCRIPTION
		"This value indicates radiomodule's modulation type."
	::= { rmPropertiesEntry 7 }


rmAntenna OBJECT-TYPE
	SYNTAX  INTEGER {
			right(1),
			left(2),
			div(3),
			both(4),
			txr(5),
			txl(6) }
	MAX-ACCESS read-write
	STATUS  current
	DESCRIPTION
		"This value defines what antenna is used for receiving
		and transmission."
	::= { rmPropertiesEntry 8 }


rmDistance OBJECT-TYPE
	SYNTAX  Integer32
	UNITS
		"kilometers"
	MAX-ACCESS read-write
	STATUS  current
	DESCRIPTION
		"This value indicates radiomodule's distance parameter
		in kilometers"
	::= { rmPropertiesEntry 9 }


rmBurst OBJECT-TYPE
	SYNTAX  INTEGER {
			on(1),
			off(2) }
	MAX-ACCESS read-write
	STATUS  current
	DESCRIPTION
		"This value indicates whether burst mode support is turned on
		or off. The burst mode will be active when using MINT protocol
		and burst mode support is turned on both base station
		and CPE."
	::= { rmPropertiesEntry 10 }


rmLongRange OBJECT-TYPE
	SYNTAX  INTEGER {
			on(1),
			off(2) }
	MAX-ACCESS read-write
	STATUS  current
	DESCRIPTION
		"This value indicates whether long range mode is turned
		on or off. Long range mode allows to establish links
		at long distances. Regretfully, implementation of 802.11b
		protocol at Aironet/Cisco radiomodules is intended for use
		at short distances and not allows to establish stable links
		at more than 10-15 km. Long range mode obviates this
		limitations, allowing any link distances as long as line
		of sight is maintained."
	::= { rmPropertiesEntry 11 }


rmPowerCtl OBJECT-TYPE
	SYNTAX  INTEGER {
			on(1),
			off(2) }
	MAX-ACCESS read-write
	STATUS  current
	DESCRIPTION
		"This value indicates whether automatic power control mode
		is turned on or off."
	::= { rmPropertiesEntry 12 }


rmTXRT OBJECT-TYPE
	SYNTAX  Integer32
	MAX-ACCESS read-write
	STATUS  current
	DESCRIPTION
		"This attribute shall indicate the maximum number of
		transmission attempts of a unicast packet that shall be made
		before a failure condition is indicated. The default value
		of this attribute is 16."
	::= { rmPropertiesEntry 13 }


rmTXVRT OBJECT-TYPE
	SYNTAX  Integer32
	MAX-ACCESS read-write
	STATUS  current
	DESCRIPTION
		"This attribute shall indicate the maximum number of
		transmission attempts of a unicast packet that shall be made
		before a failure condition is indicated, when voice mode
		is active. Voice mode is activated automatically when VoIP
		traffic appears. The default value of this attribute is 5."
	::= { rmPropertiesEntry 14 }


rmPTP OBJECT-TYPE
	SYNTAX  INTEGER {
			on(1),
			off(2) }
	MAX-ACCESS read-write
	STATUS  current
	DESCRIPTION
		"Turns on or off maximum air utilization mode. Can be used
		for high-speed point-to-point link, unsuitable for cell
		organization. (For 2Mbit radiomodules or radiomodules
		in LongRange mode only)"
	::= { rmPropertiesEntry 15 }


rmWOCD OBJECT-TYPE
	SYNTAX  INTEGER {
			on(1),
			off(2) }
	MAX-ACCESS read-write
	STATUS  current
	DESCRIPTION
		"Turns on or off WOCD(without carrier detect) mode. Can be used
		on base station with marker access only. Allows to decrease
		retry packets number and therefore increase the performance
		of the cell. (For 2Mbit or 54Mbit radiomodules only)"
	::= { rmPropertiesEntry 16 }


rmBCsid OBJECT-TYPE
	SYNTAX  INTEGER {
			on(1),
			off(2) }
	MAX-ACCESS read-write
	STATUS  current
	DESCRIPTION
		"Turns on or off sid broadcast mode for greater security of the
		network. When sid broadcast is turned off, all devices
		in the network must have sid value set explicitly."
	::= { rmPropertiesEntry 17 }


rmDistanceAuto OBJECT-TYPE
	SYNTAX  INTEGER {
			on(1),
			off(2) }
	MAX-ACCESS read-write
	STATUS  current
	DESCRIPTION
		"Turns on or off automatic adjustment of distance parameter."
	::= { rmPropertiesEntry 18 }


rmNoiseFloor OBJECT-TYPE
	SYNTAX  Integer32
	MAX-ACCESS read-only
	STATUS  current
	DESCRIPTION
		"The current noise floor in dBm."
	::= { rmPropertiesEntry 19 }


rmBandwidth OBJECT-TYPE
	SYNTAX  Unsigned32
	UNITS
		"KHz"
	MAX-ACCESS read-write
	STATUS  current
	DESCRIPTION
		"Current radio channel size in KHz."
	::= { rmPropertiesEntry 20 }


rmChainMode OBJECT-TYPE
	SYNTAX  INTEGER {
			miso(1),
			mimo(2) }
	MAX-ACCESS read-only
	STATUS  current
	DESCRIPTION
		"Radio channel technology."
	::= { rmPropertiesEntry 21 }


rmSelectChannel OBJECT-TYPE
	SYNTAX  INTEGER {
			reading-stub(0),
			new(1),
			renew(2) }
	MAX-ACCESS read-write
	STATUS  current
	DESCRIPTION
		"0 is always returned for GET operations.
		For SET operation:
		1 means 'change frequency if better choice exists,
		else keep current value';
		2 means 'change frequency in any case,
		then use the best choice among the remaining values'"
	::= { rmPropertiesEntry 22 }


rmPowerLevelsTable OBJECT-TYPE
	SYNTAX  SEQUENCE OF RmPowerLevelsEntry
	MAX-ACCESS not-accessible
	STATUS  current
	DESCRIPTION
		"This table contains radiomodule power level capabilities."
	::= { aquaradioMIB 4 }


rmPowerLevelsEntry OBJECT-TYPE
	SYNTAX  RmPowerLevelsEntry
	MAX-ACCESS not-accessible
	STATUS  current
	DESCRIPTION
		"An entry in the rmPowerLevelsTable table."
	INDEX {
		rmPowerLevelsIfIndex,
		rmPowerLevelsValIndex }
	::= { rmPowerLevelsTable 1 }


RmPowerLevelsEntry ::= SEQUENCE {

	rmPowerLevelsIfIndex  Integer32,
	rmPowerLevelsValIndex Integer32,
	rmPowerLevelsPower    Integer32 }


rmPowerLevelsIfIndex OBJECT-TYPE
	SYNTAX  Integer32 (1..2147483647)
	MAX-ACCESS read-only
	STATUS  current
	DESCRIPTION
		"The index value which uniquely identifies the interface to
		which this entry is applicable.  The interface identified by
		a particular value of this index is the same interface as
		identified by the same value of RFC 1573's ifIndex."
	::= { rmPowerLevelsEntry 1 }


rmPowerLevelsValIndex OBJECT-TYPE
	SYNTAX  Integer32 (1..2147483647)
	MAX-ACCESS read-only
	STATUS  current
	DESCRIPTION
		"The index value which uniquely identifies one of possible
		values of power level for interface selected by
		rmPowerLevelsIfIndex."
	::= { rmPowerLevelsEntry 2 }


rmPowerLevelsPower OBJECT-TYPE
	SYNTAX  Integer32
	UNITS
		"tenth dBm."
	MAX-ACCESS read-only
	STATUS  current
	DESCRIPTION
		"This value indicates possible power level (tenth dBm)."
	::= { rmPowerLevelsEntry 3 }


rmFrequenciesTable OBJECT-TYPE
	SYNTAX  SEQUENCE OF RmFrequenciesEntry
	MAX-ACCESS not-accessible
	STATUS  current
	DESCRIPTION
		"This table contains radiomodule frequency capabilities."
	::= { aquaradioMIB 5 }


rmFrequenciesEntry OBJECT-TYPE
	SYNTAX  RmFrequenciesEntry
	MAX-ACCESS not-accessible
	STATUS  current
	DESCRIPTION
		"An entry in the rmFrequenciesTable table."
	INDEX {
		rmFrequenciesIfIndex,
		rmFrequenciesValIndex }
	::= { rmFrequenciesTable 1 }


RmFrequenciesEntry ::= SEQUENCE {

	rmFrequenciesIfIndex  Integer32,
	rmFrequenciesValIndex Integer32,
	rmFrequenciesFreq     Integer32 }


rmFrequenciesIfIndex OBJECT-TYPE
	SYNTAX  Integer32 (1..2147483647)
	MAX-ACCESS read-only
	STATUS  current
	DESCRIPTION
		"The index value which uniquely identifies the interface to
		which this entry is applicable.  The interface identified by
		a particular value of this index is the same interface as
		identified by the same value of RFC 1573's ifIndex."
	::= { rmFrequenciesEntry 1 }


rmFrequenciesValIndex OBJECT-TYPE
	SYNTAX  Integer32 (1..2147483647)
	MAX-ACCESS read-only
	STATUS  current
	DESCRIPTION
		"The index value which uniquely identifies one of possible
		values of frequency for interface selected by
		rmFrequenciesIfIndex."
	::= { rmFrequenciesEntry 2 }


rmFrequenciesFreq OBJECT-TYPE
	SYNTAX  Integer32
	MAX-ACCESS read-only
	STATUS  current
	DESCRIPTION
		"This value indicates possible frequency in MHz."
	::= { rmFrequenciesEntry 3 }


rmBitratesTable OBJECT-TYPE
	SYNTAX  SEQUENCE OF RmBitratesEntry
	MAX-ACCESS not-accessible
	STATUS  current
	DESCRIPTION
		"This table contains radiomodule bitrate capabilities."
	::= { aquaradioMIB 6 }


rmBitratesEntry OBJECT-TYPE
	SYNTAX  RmBitratesEntry
	MAX-ACCESS not-accessible
	STATUS  current
	DESCRIPTION
		"An entry in the rmBitratesTable table."
	INDEX {
		rmBitratesIfIndex,
		rmBitratesValIndex }
	::= { rmBitratesTable 1 }


RmBitratesEntry ::= SEQUENCE {

	rmBitratesIfIndex  Integer32,
	rmBitratesValIndex Integer32,
	rmBitratesBitrate  Integer32 }


rmBitratesIfIndex OBJECT-TYPE
	SYNTAX  Integer32 (1..2147483647)
	MAX-ACCESS read-only
	STATUS  current
	DESCRIPTION
		"The index value which uniquely identifies the interface to
		which this entry is applicable.  The interface identified by
		a particular value of this index is the same interface as
		identified by the same value of RFC 1573's ifIndex."
	::= { rmBitratesEntry 1 }


rmBitratesValIndex OBJECT-TYPE
	SYNTAX  Integer32 (1..2147483647)
	MAX-ACCESS read-only
	STATUS  current
	DESCRIPTION
		"The index value which uniquely identifies one of possible
		values of bitrate for interface selected by
		rmBitratesIfIndex."
	::= { rmBitratesEntry 2 }


rmBitratesBitrate OBJECT-TYPE
	SYNTAX  Integer32
	MAX-ACCESS read-only
	STATUS  current
	DESCRIPTION
		"This value indicates possible bitrate in bits per second."
	::= { rmBitratesEntry 3 }


radioStatTable OBJECT-TYPE
	SYNTAX  SEQUENCE OF RadioStatEntry
	MAX-ACCESS not-accessible
	STATUS  current
	DESCRIPTION
		"A table of packet statistics for each of the links
		(by MAC address)."
	::= { aquaradioMIB 7 }


radioStatEntry OBJECT-TYPE
	SYNTAX  RadioStatEntry
	MAX-ACCESS not-accessible
	STATUS  current
	DESCRIPTION
		"Each entry contains statistics for one link (MAC address)."
	INDEX {
		radioStatMacAddress }
	::= { radioStatTable 1 }


RadioStatEntry ::= SEQUENCE {

	radioStatMacAddress    OCTET STRING,
	radioStatPackets       Counter32,
	radioStatRepeats       Counter32,
	radioStatRepeatPackets Counter32,
	radioStatBytes         Counter32,
	radioStatRepeatBytes   Counter32,
	radioStatErrors        Counter32,
	radioStatRecvPackets   Counter32,
	radioStatRecvBytes     Counter32 }


radioStatMacAddress OBJECT-TYPE
	SYNTAX  OCTET STRING (SIZE (6))
	MAX-ACCESS read-only
	STATUS  current
	DESCRIPTION
		"MAC address of the rf interface link is established with."
	::= { radioStatEntry 1 }


radioStatPackets OBJECT-TYPE
	SYNTAX  Counter32
	MAX-ACCESS read-only
	STATUS  current
	DESCRIPTION
		"Number of unique packets sent to this MAC address."
	::= { radioStatEntry 2 }


radioStatRepeats OBJECT-TYPE
	SYNTAX  Counter32
	MAX-ACCESS read-only
	STATUS  current
	DESCRIPTION
		"Number of repeat packets tries sent to this MAC address."
	::= { radioStatEntry 3 }


radioStatRepeatPackets OBJECT-TYPE
	SYNTAX  Counter32
	MAX-ACCESS read-only
	STATUS  current
	DESCRIPTION
		"Number of unique repeat packets sent to this MAC address."
	::= { radioStatEntry 4 }


radioStatBytes OBJECT-TYPE
	SYNTAX  Counter32
	MAX-ACCESS read-only
	STATUS  current
	DESCRIPTION
		"Number of bytes in unique packets sent to this MAC address."
	::= { radioStatEntry 5 }


radioStatRepeatBytes OBJECT-TYPE
	SYNTAX  Counter32
	MAX-ACCESS read-only
	STATUS  current
	DESCRIPTION
		"Number of bytes in repeat packets tries sent to this MAC address."
	::= { radioStatEntry 6 }


radioStatErrors OBJECT-TYPE
	SYNTAX  Counter32
	MAX-ACCESS read-only
	STATUS  current
	DESCRIPTION
		"Number of errors when attempted to send a packet to this
		MAC address."
	::= { radioStatEntry 7 }


radioStatRecvPackets OBJECT-TYPE
	SYNTAX  Counter32
	MAX-ACCESS read-only
	STATUS  current
	DESCRIPTION
		"Number of unique packets received from this MAC address."
	::= { radioStatEntry 8 }


radioStatRecvBytes OBJECT-TYPE
	SYNTAX  Counter32
	MAX-ACCESS read-only
	STATUS  current
	DESCRIPTION
		"Number of bytes in unique packets received from this MAC address."
	::= { radioStatEntry 9 }


rmBandsTable OBJECT-TYPE
	SYNTAX  SEQUENCE OF RmBandsEntry
	MAX-ACCESS not-accessible
	STATUS  current
	DESCRIPTION
		"This table contains radiomodule possible bandwidths."
	::= { aquaradioMIB 8 }


rmBandsEntry OBJECT-TYPE
	SYNTAX  RmBandsEntry
	MAX-ACCESS not-accessible
	STATUS  current
	DESCRIPTION
		"An entry in the rmBandsTable."
	INDEX {
		rmBandsIfIndex,
		rmBandsValIndex }
	::= { rmBandsTable 1 }


RmBandsEntry ::= SEQUENCE {

	rmBandsIfIndex  Integer32,
	rmBandsValIndex Integer32,
	rmBandsBand     Integer32 }


rmBandsIfIndex OBJECT-TYPE
	SYNTAX  Integer32 (1..2147483647)
	MAX-ACCESS read-only
	STATUS  current
	DESCRIPTION
		"The index value which uniquely identifies the interface to
		which this entry is applicable.  The interface identified by
		a particular value of this index is the same interface as
		identified by the same value of RFC 1573's ifIndex."
	::= { rmBandsEntry 1 }


rmBandsValIndex OBJECT-TYPE
	SYNTAX  Integer32 (1..2147483647)
	MAX-ACCESS read-only
	STATUS  current
	DESCRIPTION
		"The index value which uniquely identifies one of possible
		values of bandwidth for interface selected by
		rmBandsIfIndex."
	::= { rmBandsEntry 2 }


rmBandsBand OBJECT-TYPE
	SYNTAX  Integer32
	UNITS
		"Hz"
	MAX-ACCESS read-only
	STATUS  current
	DESCRIPTION
		"This value indicates one of possible bandwidth in Hz for
		interface selected by rmBandsIfIndex."
	::= { rmBandsEntry 3 }


aquaradioMIBNotificationsPrefix OBJECT IDENTIFIER 	::= { aquaradioMIB 17 }

aquaradioMIBnotifications OBJECT IDENTIFIER 	::= { aquaradioMIBNotificationsPrefix 0 }


radioFreqChanged NOTIFICATION-TYPE
	OBJECTS {
		sysSerialNumber,
		sysTrapSequence,
		rmFrequency,
		rmPropertiesIfIndex}
	STATUS  current
	DESCRIPTION
		"A radioFreqChangedNotification is sent when frequency is changed on radio interface."
	::= { aquaradioMIBnotifications 1 }


radioBandChanged NOTIFICATION-TYPE
	OBJECTS {
		sysSerialNumber,
		sysTrapSequence,
		rmBandwidth,
		rmPropertiesIfIndex}
	STATUS  current
	DESCRIPTION
		"A radioBandChangedNotification is sent when bandwidth is changed on radio interface."
	::= { aquaradioMIBnotifications 2 }

aquaradioMIBConformance OBJECT IDENTIFIER 	::= { aquaradioMIB 18 }

aquaradioMIBCompliances OBJECT IDENTIFIER 	::= { aquaradioMIBConformance 1 }

aquaradioMIBGroups OBJECT IDENTIFIER 	::= { aquaradioMIBConformance 2 }


-- compliance statements

aquaradioMIBCompliance MODULE-COMPLIANCE
	STATUS  current
	DESCRIPTION
		"The compliance statement for Infinet wireless routers."

	MODULE
	MANDATORY-GROUPS {
			radioGroup }

	::= { aquaradioMIBCompliances 1 }

-- units of conformance

radioGroup OBJECT-GROUP
	OBJECTS {
		rmPropertiesIfIndex,
		rmType,
		rmFrequency,
		rmBitRate,
		rmSid,
		rmCurPowerLevel,
		rmModulation,
		rmAntenna,
		rmDistance,
		rmBurst,
		rmLongRange,
		rmPowerCtl,
		rmTXRT,
		rmTXVRT,
		rmPTP,
		rmWOCD,
		rmBCsid,
		rmPowerLevelsIfIndex,
		rmPowerLevelsValIndex,
		rmPowerLevelsPower,
		rmFrequenciesIfIndex,
		rmFrequenciesValIndex,
		rmFrequenciesFreq,
		rmBitratesIfIndex,
		rmBitratesValIndex,
		rmBitratesBitrate,
		radioStatMacAddress,
		radioStatPackets,
		radioStatRepeats,
		radioStatRepeatPackets,
		radioStatBytes,
		radioStatRepeatBytes,
		radioStatErrors,
		radioStatRecvPackets,
		radioStatRecvBytes,
		rmDistanceAuto,
		rmNoiseFloor,
		rmBandwidth,
		rmChainMode,
		rmBandsIfIndex,
		rmBandsValIndex,
		rmBandsBand,
		rmSelectChannel }
	STATUS  current
	DESCRIPTION
		"The radio group of objects providing for management of radiomodule
		parameters, including IEEE 802.11 parameters and proprietary
		parameters."
	::= { aquaradioMIBGroups 1 }

aquaradioNotifications NOTIFICATION-GROUP
	NOTIFICATIONS {
		radioFreqChanged,
		radioBandChanged }
	STATUS  current
	DESCRIPTION ""
	::= { aquaradioMIBConformance 3 }

END

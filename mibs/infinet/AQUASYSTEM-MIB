AQUASYSTEM-MIB DEFINITIONS ::= BEGIN

IMPORTS
    wanflex
        FROM INFINET-MIB
    ifEntry
        FROM IF-MIB
    DisplayString
        FROM SNMPv2-TC
    MODULE-IDENTITY,
    OBJECT-TYPE,
    Counter32,
    Gauge32,
    Integer32,
    Unsigned32,
    IpAddress
        FROM SNMPv2-SMI
    OBJECT-GROUP,
    MODULE-COMPLIANCE
        FROM SNMPv2-CONF;

aquasystemMIB MODULE-IDENTITY
    LAST-UPDATED "201407290657Z"
    ORGANIZATION "Infinet Wireless Ltd."
    CONTACT-INFO
        "Andrew Nesheret

        Postal: Infinet Wireless Ltd.,
                Russia, Ekaterinburg,
                Serafimi Deryabinoi st, 24

        Phone:  +7 343 253 1533
        Email:  aberzin@infinetwireless.com"
    DESCRIPTION
        "The mib module, containing various WanFlex options."
    REVISION "201802261030Z"
    DESCRIPTION
        "added sysBuildDate and sysBuidTime"
    REVISION "201407290657Z"
    DESCRIPTION
        "sysMgmtAccess accees changed to read-only;
        description changed for
        sysMgmtFrmwDlPath, sysMgmtFrmwUlPath,
        sysMgmtLicDlPath, sysMgmtLicUlPath,
        sysMgmtCfgDlPath, sysMgmtCfgUlPath
        concerning SNMP error codes and
        optional usage of operative ftp account."
    REVISION "201406030350Z"
    DESCRIPTION
        "sysFirmwareID added in aquasystemMIB 16."
    REVISION "201401210721Z"
    DESCRIPTION
        "'hold' value added to sysMgmtCurrentState.
        'blocked' value added to result state
        of every management action."
    REVISION "201401150438Z"
    DESCRIPTION
        "sysMgmt brunch added in aquasystemMIB 23"
    REVISION "201307221104Z"
    DESCRIPTION
        "sysSoftwareVersion added in aquasystemMIB 14.
        sysModel added in aquasystemMIB 15"
    REVISION "201306191622Z"
    DESCRIPTION
        "sysLastRebootReason added in aquasystemMIB 13."
    REVISION "201206130816Z"
    DESCRIPTION
        "sysSerialNumberStr added in aquasystemMIB 11.
        sysNote moved to aquasystemMIB 12."
    REVISION "201102160934Z"
    DESCRIPTION
        "sysNote added.
        sysIf, sysMem, sysQueue branches added."
    REVISION "200805050900Z"
    DESCRIPTION
        "Restart Timer added."
    REVISION "200711081116Z"
    DESCRIPTION
        "Contact information changed."
    REVISION "200708231732Z"
    DESCRIPTION
        "The mib module, containing various WanFlex options."
    ::= { wanflex 3 }


sysGPSXY OBJECT-TYPE
    SYNTAX  OCTET STRING
    MAX-ACCESS read-write
    STATUS  current
    DESCRIPTION
        "Geographical coordinates of the unit (longitude and latitude)
        in degrees. This parameter is used for automatic tweaking
        of radio module parameters."
    ::= { aquasystemMIB 1 }


sysFastRoute OBJECT-TYPE
    SYNTAX  INTEGER {
            on(1),
            off(2) }
    MAX-ACCESS read-write
    STATUS  current
    DESCRIPTION
        "This value indicates whether fast routing mode is turned on or off.
        A router in fast routing mode effectively does not decrement
        the value in TTL field of IP packet, thus making itself invisible
        to route tracing programs, like tracert. It is not recommended
        to use fast routing mode on two or more devices in the same network
        segment to avoid IP storms."
    ::= { aquasystemMIB 2 }


sysICMPLimit OBJECT-TYPE
    SYNTAX  Integer32 (0..2147483647)
    MAX-ACCESS read-write
    STATUS  current
    DESCRIPTION
        "Sets limit on outgoing ICMP packets per second (200 by default).
        This feature is used to avoid unit overload when network scanners
        are used. When this value is set to zero, this limit is lifted."
    ::= { aquasystemMIB 3 }


sysSendRedirects OBJECT-TYPE
    SYNTAX  INTEGER {
            on(1),
            off(2) }
    MAX-ACCESS read-write
    STATUS  current
    DESCRIPTION
        "This value indicates whether the system is allowed to send ICMP
        redirect messages."
    ::= { aquasystemMIB 4 }


sysDropRedirects OBJECT-TYPE
    SYNTAX  INTEGER {
            on(1),
            off(2) }
    MAX-ACCESS read-write
    STATUS  current
    DESCRIPTION
        "This value indicates whether the system ignores incoming ICMP
        redirect messages."
    ::= { aquasystemMIB 5 }


sysCpu OBJECT-TYPE
    SYNTAX  Gauge32
    MAX-ACCESS read-only
    STATUS  current
    DESCRIPTION
        "This value indicates current CPU load rate in per cent."
    ::= { aquasystemMIB 6 }


sysTemperature OBJECT-TYPE
    SYNTAX  Integer32
    MAX-ACCESS read-only
    STATUS  current
    DESCRIPTION
        "This value indicates current board temperature in tenth of degrees Celsius."
    ::= { aquasystemMIB 7 }


sysTrapSequence OBJECT-TYPE
    SYNTAX  Counter32
    MAX-ACCESS accessible-for-notify
    STATUS  current
    DESCRIPTION
        "This value indicates sequence number of the trap last sent."
    ::= { aquasystemMIB 8 }


sysSerialNumber OBJECT-TYPE
    SYNTAX  Integer32
    MAX-ACCESS read-only
    STATUS  current
    DESCRIPTION
        "This value indicates device's serial number."
    ::= { aquasystemMIB 9 }


sysRestartTimer OBJECT-TYPE
    SYNTAX  Unsigned32 (0..107374)
    MAX-ACCESS read-write
    STATUS  current
    DESCRIPTION
        "This variable defines system timer counter that sets time in seconds left till device reboot.
        To cancel time counter set variable to '0'."
    ::= { aquasystemMIB 10 }


sysSerialNumberStr OBJECT-TYPE
    SYNTAX  DisplayString
    MAX-ACCESS read-only
    STATUS  current
    DESCRIPTION
        "This value indicates device's serial number as character string."
    ::= { aquasystemMIB 11 }


sysNote OBJECT-TYPE
    SYNTAX  OCTET STRING
    MAX-ACCESS read-write
    STATUS  current
    DESCRIPTION
        "This variable holds administrative note."
    ::= { aquasystemMIB 12 }


sysLastRebootReason OBJECT-TYPE
    SYNTAX  DisplayString
    MAX-ACCESS read-only
    STATUS  current
    DESCRIPTION
        "This value indicates device's last reboot reason."
    ::= { aquasystemMIB 13 }


sysSoftwareVersion OBJECT-TYPE
    SYNTAX  DisplayString
    MAX-ACCESS read-only
    STATUS  current
    DESCRIPTION
        "Dot-separated string compiled of integers for OS version, subversion and build version."
    ::= { aquasystemMIB 14 }


sysModel OBJECT-TYPE
    SYNTAX  DisplayString
    MAX-ACCESS read-only
    STATUS  current
    DESCRIPTION
        "PN field from License."
    ::= { aquasystemMIB 15 }


sysFirmwareID OBJECT-TYPE
    SYNTAX  DisplayString
    MAX-ACCESS read-only
    STATUS  current
    DESCRIPTION
        "system Firmware ID"
    ::= { aquasystemMIB 16 }


sysBuildDate OBJECT-TYPE
    SYNTAX  DisplayString
    MAX-ACCESS read-only
    STATUS  current
    DESCRIPTION
        "system Firmware build date"
    ::= { aquasystemMIB 17 }


sysBuildTime OBJECT-TYPE
    SYNTAX  DisplayString
    MAX-ACCESS read-only
    STATUS  current
    DESCRIPTION
        "system Firmware build time"
    ::= { aquasystemMIB 18 }


sysIf OBJECT IDENTIFIER     ::= { aquasystemMIB 20 }

sysIfTable OBJECT-TYPE
    SYNTAX  SEQUENCE OF SysIfEntry
    MAX-ACCESS not-accessible
    STATUS  current
    DESCRIPTION
        "This table contains additional objects for RFC2863
        ifTable."
    ::= { sysIf 1 }


sysIfEntry OBJECT-TYPE
    SYNTAX  SysIfEntry
    MAX-ACCESS not-accessible
    STATUS  current
    DESCRIPTION
        "An entry containing additional management information
        applicable to a particular interface."
    AUGMENTS {
        ifEntry }
    ::= { sysIfTable 1 }


SysIfEntry ::= SEQUENCE {

    sysIfCurPpsRx  Gauge32,
    sysIfCurPpsTx  Gauge32,
    sysIfCurLoadRx Gauge32,
    sysIfCurLoadTx Gauge32 }


sysIfCurPpsRx OBJECT-TYPE
    SYNTAX  Gauge32
    MAX-ACCESS read-only
    STATUS  current
    DESCRIPTION
        "Current rate of inbound traffic on interface
        measured in packets per second."
    ::= { sysIfEntry 1 }


sysIfCurPpsTx OBJECT-TYPE
    SYNTAX  Gauge32
    MAX-ACCESS read-only
    STATUS  current
    DESCRIPTION
        "Current rate of outbound traffic on interface
        measured in packets per second."
    ::= { sysIfEntry 2 }


sysIfCurLoadRx OBJECT-TYPE
    SYNTAX  Gauge32
    MAX-ACCESS read-only
    STATUS  current
    DESCRIPTION
        "Current rate of inbound traffic on interface
        measured in kilobits per second."
    ::= { sysIfEntry 3 }


sysIfCurLoadTx OBJECT-TYPE
    SYNTAX  Gauge32
    MAX-ACCESS read-only
    STATUS  current
    DESCRIPTION
        "Current rate of outbound traffic on interface
        measured in kilobits per second."
    ::= { sysIfEntry 4 }


sysMem OBJECT IDENTIFIER    ::= { aquasystemMIB 21 }

sysMemTotal OBJECT-TYPE
    SYNTAX  Gauge32
    MAX-ACCESS read-only
    STATUS  current
    DESCRIPTION
        "Total memory in bytes."
    ::= { sysMem 1 }


sysMemFree OBJECT-TYPE
    SYNTAX  Gauge32
    MAX-ACCESS read-only
    STATUS  current
    DESCRIPTION
        "Free memory in bytes."
    ::= { sysMem 2 }


sysNetBufsInUse OBJECT-TYPE
    SYNTAX  Gauge32
    MAX-ACCESS read-only
    STATUS  current
    DESCRIPTION
        "Number of network buffers currently in use."
    ::= { sysMem 3 }


sysNetPagesTotal OBJECT-TYPE
    SYNTAX  Gauge32
    MAX-ACCESS read-only
    STATUS  current
    DESCRIPTION
        "Total number of pages."
    ::= { sysMem 4 }


sysNetPagesInUse OBJECT-TYPE
    SYNTAX  Gauge32
    MAX-ACCESS read-only
    STATUS  current
    DESCRIPTION
        "Number of pages currently in use."
    ::= { sysMem 5 }


sysQueue OBJECT IDENTIFIER  ::= { aquasystemMIB 22 }

sysQueueTable OBJECT-TYPE
    SYNTAX  SEQUENCE OF SysQueueEntry
    MAX-ACCESS not-accessible
    STATUS  current
    DESCRIPTION
        "Statistics of system queues."
    ::= { sysQueue 1 }


sysQueueEntry OBJECT-TYPE
    SYNTAX  SysQueueEntry
    MAX-ACCESS not-accessible
    STATUS  current
    DESCRIPTION ""
    INDEX {
        sysQueueIndex }
    ::= { sysQueueTable 1 }


SysQueueEntry ::= SEQUENCE {

    sysQueueIndex  Integer32,
    sysQueueName   OCTET STRING,
    sysQueueLen    Unsigned32,
    sysQueueMaxLen Unsigned32,
    sysQueueDrops  Unsigned32 }


sysQueueIndex OBJECT-TYPE
    SYNTAX  Integer32 (0..2147483647)
    MAX-ACCESS read-only
    STATUS  current
    DESCRIPTION
        "The index value which uniquely identifies
        system packet queue to which statistics
        in this entry is applicable."
    ::= { sysQueueEntry 1 }


sysQueueName OBJECT-TYPE
    SYNTAX  OCTET STRING
    MAX-ACCESS read-only
    STATUS  current
    DESCRIPTION
        "Symbol name of system packet queue."
    ::= { sysQueueEntry 2 }


sysQueueLen OBJECT-TYPE
    SYNTAX  Unsigned32
    MAX-ACCESS read-only
    STATUS  current
    DESCRIPTION
        "Current queue length."
    ::= { sysQueueEntry 3 }


sysQueueMaxLen OBJECT-TYPE
    SYNTAX  Unsigned32
    MAX-ACCESS read-only
    STATUS  current
    DESCRIPTION
        "Maximum known queue length."
    ::= { sysQueueEntry 4 }


sysQueueDrops OBJECT-TYPE
    SYNTAX  Unsigned32
    MAX-ACCESS read-only
    STATUS  current
    DESCRIPTION
        "Queue drops."
    ::= { sysQueueEntry 5 }


sysMgmt OBJECT IDENTIFIER   ::= { aquasystemMIB 23 }

sysMgmtGlobals OBJECT IDENTIFIER    ::= { sysMgmt 1 }

sysMgmtAccess OBJECT-TYPE
    SYNTAX  DisplayString
    MAX-ACCESS read-only
    STATUS  current
    DESCRIPTION
        "String with ftp access details
        in the form 'username:password@ftpserverIP'
        used as default ftp account for management
        operations."
    ::= { sysMgmtGlobals 1 }


sysMgmtSrcIp OBJECT-TYPE
    SYNTAX  IpAddress
    MAX-ACCESS read-write
    STATUS  current
    DESCRIPTION
        "Actual device address to use as source IP address
        in ftp sessions for management data transfer."
    ::= { sysMgmtGlobals 2 }



sysMgmtCurrentState OBJECT-TYPE
    SYNTAX  INTEGER {
            idle(0),
            busy(1),
            hold(2) }
    MAX-ACCESS read-only
    STATUS  current
    DESCRIPTION
        "Current state is 'busy' while any management action is active
        and immediately goes either to 'idle' when current action is failed
        or to 'hold' if action succeeded. 'Hold' state is kept for 15s,
        even if performed management action implies system reboot.
        Only occasional reboot for another reason can break this sequence.
        Next management action can start only if this state is 'idle'.
        It prevents concurrent management actions via SNMP."
    ::= { sysMgmtGlobals 3 }


sysMgmtOperProgress OBJECT-TYPE
    SYNTAX  Integer32 (0..100)
    MAX-ACCESS read-only
    STATUS  current
    DESCRIPTION
        "This indicator value corresponds to action progress in percentage.
        If action fails, this value immediately is frozen until
        sysMgmtCurrentState goes to 'idle'.
        If action is successfuly completed, this value is 100 and is frozen
        while sysMgmtCurrentState is 'hold', then returns to zero."
    ::= { sysMgmtGlobals 4 }


sysMgmtErrorString OBJECT-TYPE
    SYNTAX  DisplayString
    MAX-ACCESS read-only
    STATUS  current
    DESCRIPTION
        "Error string providing more details
        about error reasons indicated by
        sysMgmtFrmwDlResult, sysMgmtFrmwUlResult,
        sysMgmtLicDlResult, sysMgmtLicUlResult,
        sysMgmtCfgDlResult, sysMgmtCfgUlResult.
        This string is kept unchanged
        until any next management action is started."
    ::= { sysMgmtGlobals 5 }


sysMgmtHoldTimer OBJECT-TYPE
    SYNTAX  Gauge32 (0..15)
    MAX-ACCESS read-only
    STATUS  current
    DESCRIPTION
        "This countdown timer shows the value in seconds
        left till result of previous management action is hold intact.
        This timer also means time remaining until device reboot
        after management action which implies the reboot."
    ::= { sysMgmtGlobals 6 }


sysMgmtFrmw OBJECT IDENTIFIER   ::= { sysMgmt 2 }

sysMgmtFrmwDlPath OBJECT-TYPE
    SYNTAX  DisplayString (SIZE (1..255))
    MAX-ACCESS read-write
    STATUS  current
    DESCRIPTION
        "Filename (with optional path w/o leading '/')
        of downloadable firmare file at ftp server.

        Any successful SET operation on sysMgmtFrmwDlPath
        starts management action of downloading
        firmware file from ftp server.

        Optionally, operative ftp account in the same format
        as described for sysMgmtAccess can be supplied to
        overwrite default ftp account for current operation only.
        If so, such account string, followed by single
        whitespace, should be prepended to optional path and
        required filename.

        SET operation will return inconsistentValue error
        if sysMgmtCurrentState is not 'idle'.
        SET operation will return wrongLength error
        if new value is empty.
        SET operation will return wrongValue error
        if any of the following is true:
        - sysMgmtAccess is empty and no ftp account is
        present in the string,
        - used ftp account (either sysMgmtAccess or
        specified in the string) has invalid format,
        - full path to file has illegal chars or double slashes.

        Otherwise SET operation is successful, but
        ftp connection can fail later if either used ftp account
        is invalid or provided filepath and|or filename are
        inconsistent with ftp-server file locations or permissions.

        If ftp transfer succeded and firmware checks passed,
        then old firmware is overwritten with new one and
        device is auto rebooted.

        The value of sysMgmtFrmwDlPath is kept unchanged
        till next invocation of firmware downloading action."
    ::= { sysMgmtFrmw 1 }


sysMgmtFrmwDlResult OBJECT-TYPE
    SYNTAX  INTEGER {
            success(0),
            system-error(1),
            ftp-error(2),
            firmware-error(3),
            blocked(4) }
    MAX-ACCESS read-only
    STATUS  current
    DESCRIPTION
        "The result code of firmware downloading action.
        More verbose description of an error
        can be found in sysMgmtErrorString.
        This result code is kept unchanged
        till next firmware downloading action is started."
    ::= { sysMgmtFrmw 2 }


sysMgmtFrmwUlPath OBJECT-TYPE
    SYNTAX  DisplayString
    MAX-ACCESS read-write
    STATUS  current
    DESCRIPTION
        "Filename (with optional path w/o leading '/')
        of firmare file which should be uploaded to ftp server.

        Any successful SET operation on sysMgmtFrmwUlPath
        starts next management action of uploading
        firmware file to ftp server.

        Filename will be auto-prepended with 'SN-nnnn.' string
        to distinct uploaded files from other devices, e.g.
        if provided filename and path are 'uploads/fmw',
        then SN-nnnn.fmw file will be created in 'uploads' folder
        at ftp server, where nnnn is value of sysSerialNumber.

        Optionally, operative ftp account in the same format
        as described for sysMgmtAccess can be supplied to
        overwrite default ftp account for current operation only.
        If so, such account string, followed by single
        whitespace, should be prepended to optional path and
        required filename.

        SET operation will return inconsistentValue error
        if sysMgmtCurrentState is not 'idle'.
        SET operation will return wrongLength error
        if new value is empty.
        SET operation will return wrongValue error
        if any of the following is true:
        - sysMgmtAccess is empty and no ftp account is
        present in the string,
        - used ftp account (either sysMgmtAccess or
        specified in the string) has invalid format,
        - full path to file has illegal chars or double slashes.

        Otherwise SET operation is successful, but
        ftp connection can fail later if either used ftp account
        is invalid or provided filepath and|or filename are
        inconsistent with ftp-server file locations or permissions.

        The value of sysMgmtFrmwUlPath is kept unchanged
        till next invocation of firmware uploading action."
    ::= { sysMgmtFrmw 3 }


sysMgmtFrmwUlResult OBJECT-TYPE
    SYNTAX  INTEGER {
            success(0),
            system-error(1),
            ftp-error(2),
            blocked(3) }
    MAX-ACCESS read-only
    STATUS  current
    DESCRIPTION
        "The result code of firmware uploading action.
        More verbose description of an error
        can be found in sysMgmtErrorString.
        This result code is kept unchanged
        till next firmware uploading action is started."
    ::= { sysMgmtFrmw 4 }


sysMgmtLic OBJECT IDENTIFIER    ::= { sysMgmt 3 }

sysMgmtLicDlPath OBJECT-TYPE
    SYNTAX  DisplayString
    MAX-ACCESS read-write
    STATUS  current
    DESCRIPTION
        "Filename (with optional path w/o leading '/')
        of downloadable license file at ftp server.

        Any successful SET operation on sysMgmtLicDlPath
        starts management action of downloading
        license file from ftp server.

        Optionally, operative ftp account in the same format
        as described for sysMgmtAccess can be supplied to
        overwrite default ftp account for current operation only.
        If so, such account string, followed by single
        whitespace, should be prepended to optional path and
        required filename.

        SET operation will return inconsistentValue error
        if sysMgmtCurrentState is not 'idle'.
        SET operation will return wrongLength error
        if new value is empty.
        SET operation will return wrongValue error
        if any of the following is true:
        - sysMgmtAccess is empty and no ftp account is
        present in the string,
        - used ftp account (either sysMgmtAccess or
        specified in the string) has invalid format,
        - full path to file has illegal chars or double slashes.

        Otherwise SET operation is successful, but
        ftp connection can fail later if either used ftp account
        is invalid or provided filepath and|or filename are
        inconsistent with ftp-server file locations or permissions.

        If ftp transfer succeded and licence check passed,
        then licence is applied and device is auto rebooted.

        The value of sysMgmtLicDlPath is kept unchanged
        till next invocation of license downloading action."
    ::= { sysMgmtLic 1 }


sysMgmtLicDlResult OBJECT-TYPE
    SYNTAX  INTEGER {
            success(0),
            system-error(1),
            ftp-error(2),
            license-error(3),
            blocked(4) }
    MAX-ACCESS read-only
    STATUS  current
    DESCRIPTION
        "The result code of license downloading action.
        More verbose description of an error
        can be found in sysMgmtErrorString.
        This result code is kept unchanged
        till next license downloading action is started."
    ::= { sysMgmtLic 2 }


sysMgmtLicUlPath OBJECT-TYPE
    SYNTAX  DisplayString
    MAX-ACCESS read-write
    STATUS  current
    DESCRIPTION
        "Filename (with optional path w/o leading '/')
        of license file which should be uploaded to ftp server.

        Any successful SET operation on sysMgmtLicUlPath
        starts next management action of uploading
        license file to ftp server.

        Filename will be auto-prepended with 'SN-nnnn.' string
        to distinct uploaded files from other devices, e.g.
        if provided filename and path are 'uploads/lic',
        then SN-nnnn.lic file will be created in 'uploads' folder
        at ftp server, where nnnn is value of sysSerialNumber.

        Optionally, operative ftp account in the same format
        as described for sysMgmtAccess can be supplied to
        overwrite used ftp account for current operation only.
        If so, such account string, followed by single
        whitespace, should be prepended to optional path and
        required filename.

        SET operation will return inconsistentValue error
        if sysMgmtCurrentState is not 'idle'.
        SET operation will return wrongLength error
        if new value is empty.
        SET operation will return wrongValue error
        if any of the following is true:
        - sysMgmtAccess is empty and no ftp account is
        present in the string,
        - used ftp account (either sysMgmtAccess or
        specified in the string) has invalid format,
        - full path to file has illegal chars or double slashes.

        Otherwise SET operation is successful, but
        ftp connection can fail later if either used ftp account
        is invalid or provided filepath and|or filename are
        inconsistent with ftp-server file locations or permissions.

        The value of sysMgmtLicUlPath is kept unchanged
        till next invocation of license uploading action."
    ::= { sysMgmtLic 3 }


sysMgmtLicUlResult OBJECT-TYPE
    SYNTAX  INTEGER {
            success(0),
            system-error(1),
            ftp-error(2),
            blocked(3) }
    MAX-ACCESS read-only
    STATUS  current
    DESCRIPTION
        "The result code of license uploading action.
        More verbose description of an error
        can be found in sysMgmtErrorString.
        This result code is kept unchanged
        till next license uploading action is started."
    ::= { sysMgmtLic 4 }


sysMgmtCfg OBJECT IDENTIFIER    ::= { sysMgmt 4 }

sysMgmtCfgDlPath OBJECT-TYPE
    SYNTAX  DisplayString
    MAX-ACCESS read-write
    STATUS  current
    DESCRIPTION
        "Filename (with optional path w/o leading '/')
        of downloadable config file at ftp server.

        Any successful SET operation on sysMgmtCfgDlPath
        starts management action of downloading
        configuration file from ftp server.

        Optionally, operative ftp account in the same format
        as described for sysMgmtAccess can be supplied to
        overwrite used ftp account for current operation only.
        If so, such account string, followed by single
        whitespace, should be prepended to optional path and
        required filename.

        SET operation will return inconsistentValue error
        if sysMgmtCurrentState is not 'idle'.
        SET operation will return wrongLength error
        if new value is empty.
        SET operation will return wrongValue error
        if any of the following is true:
        - sysMgmtAccess is empty and no ftp account is
        present in the string,
        - used ftp account (either sysMgmtAccess or
        specified in the string) has invalid format,
        - full path to file has illegal chars or double slashes.

        Otherwise SET operation is successful, but
        ftp connection can fail later if either used ftp account
        is invalid or provided filepath and|or filename are
        inconsistent with ftp-server file locations or permissions.

        If ftp transfer succeded and configuration check passed,
        then configuration is applied and device is auto rebooted.

        The value of sysMgmtCfgDlPath is kept unchanged
        till next invocation of config downloading action."
    ::= { sysMgmtCfg 1 }


sysMgmtCfgDlResult OBJECT-TYPE
    SYNTAX  INTEGER {
            success(0),
            system-error(1),
            ftp-error(2),
            config-error(3),
            blocked(4) }
    MAX-ACCESS read-only
    STATUS  current
    DESCRIPTION
        "The result code of config downloading action.
        More verbose description of an error
        can be found in sysMgmtErrorString.
        This result code is kept unchanged
        till next config downloading action is started."
    ::= { sysMgmtCfg 2 }


sysMgmtCfgUlPath OBJECT-TYPE
    SYNTAX  DisplayString
    MAX-ACCESS read-write
    STATUS  current
    DESCRIPTION
        "Filename (with optional path w/o leading '/')
        of configuration file which should be uploaded to ftp server.

        Any successful SET operation on sysMgmtCfgUlPath
        starts next management action of uploading
        current configuration to ftp server.

        Filename will be auto-prepended with 'SN-nnnn.' string
        to distinct uploaded files from other devices, e.g.
        if provided filename and path are 'uploads/cfg',
        then SN-nnnn.cfg file will be created in 'uploads' folder
        at ftp server, where nnnn is value of sysSerialNumber.

        Optionally, operative ftp account in the same format
        as described for sysMgmtAccess can be supplied to
        overwrite used ftp account for current operation only.
        If so, such account string, followed by single
        whitespace, should be prepended to optional path and
        required filename.

        SET operation will return inconsistentValue error
        if sysMgmtCurrentState is not 'idle'.
        SET operation will return wrongLength error
        if new value is empty.
        SET operation will return wrongValue error
        if any of the following is true:
        - sysMgmtAccess is empty and no ftp account is
        present in the string,
        - used ftp account (either sysMgmtAccess or
        specified in the string) has invalid format,
        - full path to file has illegal chars or double slashes.

        Otherwise SET operation is successful, but
        ftp connection can fail later if either used ftp account
        is invalid or provided filepath and|or filename are
        inconsistent with ftp-server file locations or permissions.

        The value of sysMgmtCfgUlPath is kept unchanged
        till next invocation of config uploading action."
    ::= { sysMgmtCfg 3 }


sysMgmtCfgUlResult OBJECT-TYPE
    SYNTAX  INTEGER {
            success(0),
            system-error(1),
            ftp-error(2),
            blocked(3) }
    MAX-ACCESS read-only
    STATUS  current
    DESCRIPTION
        "The result code of config uploading action.
        More verbose description of an error
        can be found in sysMgmtErrorString.
        This result code is kept unchanged
        till next config uploading action is started."
    ::= { sysMgmtCfg 4 }


aquasystemMIBConformance OBJECT IDENTIFIER  ::= { aquasystemMIB 100 }

aquasystemMIBCompliances OBJECT IDENTIFIER  ::= { aquasystemMIBConformance 1 }

aquasystemMIBGroups OBJECT IDENTIFIER   ::= { aquasystemMIBConformance 2 }


-- compliance statements

aquasystemMIBCompliance MODULE-COMPLIANCE
    STATUS  current
    DESCRIPTION
        "The compliance statement for Infinet wireless routers."

    MODULE
    MANDATORY-GROUPS {
            systemGroup }

    ::= { aquasystemMIBCompliances 1 }

-- units of conformance

systemGroup OBJECT-GROUP
    OBJECTS {
        sysGPSXY,
        sysFastRoute,
        sysICMPLimit,
        sysSendRedirects,
        sysDropRedirects,
        sysCpu,
        sysTemperature,
        sysTrapSequence,
        sysSerialNumber,
        sysRestartTimer,
        sysSerialNumberStr,
        sysNote,
        sysLastRebootReason,
        sysSoftwareVersion,
        sysModel,
        sysFirmwareID,
        sysBuildDate,
        sysBuildTime,
        sysIfCurPpsRx,
        sysIfCurPpsTx,
        sysIfCurLoadRx,
        sysIfCurLoadTx,
        sysMemFree,
        sysMemTotal,
        sysNetBufsInUse,
        sysNetPagesTotal,
        sysNetPagesInUse,
        sysQueueIndex,
        sysQueueName,
        sysQueueLen,
        sysQueueMaxLen,
        sysQueueDrops,
        sysMgmtAccess,
        sysMgmtSrcIp,
        sysMgmtCurrentState,
        sysMgmtOperProgress,
        sysMgmtErrorString,
        sysMgmtHoldTimer,
        sysMgmtFrmwDlPath,
        sysMgmtFrmwDlResult,
        sysMgmtFrmwUlPath,
        sysMgmtFrmwUlResult,
        sysMgmtLicDlPath,
        sysMgmtLicDlResult,
        sysMgmtLicUlPath,
        sysMgmtLicUlResult,
        sysMgmtCfgDlPath,
        sysMgmtCfgDlResult,
        sysMgmtCfgUlPath,
        sysMgmtCfgUlResult }
    STATUS  current
    DESCRIPTION
        "The system group of objects provided for
        management of various WanFlex system parameters."
    ::= { aquasystemMIBGroups 1 }

END

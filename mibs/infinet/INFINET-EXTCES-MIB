INFINET-EXTCES-MIB DEFINITIONS ::= BEGIN

IMPORTS
	externalDevices
		FROM INFINET-EXTDEVICES-MIB
	MODULE-IDENTITY,
	OBJECT-TYPE,
	Unsigned32
		FROM SNMPv2-SMI
	OBJECT-GROUP
		FROM SNMPv2-CONF;

cesOverWlan MODULE-IDENTITY
	LAST-UPDATED "200706181910Z"
	ORGANIZATION "Infinet Wireless Ltd."
	CONTACT-INFO
		"Dmitry Petukhov

		Postal: Infinet Wireless Ltd,
		        Russia, Ekaterinburg,
		        Serafimi Deryabinoi st, 24

		Phone:  +7 343 217 9317
		Email:  d.petukhov@infinetwireless.com"
	DESCRIPTION
		"The mib module, containing various WanFlex options."
	REVISION "200706181910Z"
	DESCRIPTION
		"The mib module, containing settings for Circut Emulation Services over WLAN."
	::= { externalDevices 1 }


cesOverWlanUnit0 OBJECT IDENTIFIER 	::= { cesOverWlan 1 }

cesOverWlanUnit0Settings OBJECT IDENTIFIER 	::= { cesOverWlanUnit0 1 }

cesOverWlanUnit0Enabled OBJECT-TYPE
	SYNTAX  INTEGER {
			on(1),
			off(2) }
	MAX-ACCESS read-write
	STATUS  current
	DESCRIPTION
		"Unit functional state - started or stopped.
		writing to any of subsequent settings disabled if state is 'on'."
	::= { cesOverWlanUnit0Settings 1 }


cesOverWlanUnit0Mode OBJECT-TYPE
	SYNTAX  INTEGER {
			e1-internal(0),
			e1-loopback(2),
			e1-recovery(3),
			e1-line(4),
			t1-internal(6),
			t1-loopback(8),
			t1-recovery(9),
			t1-line(10) }
	MAX-ACCESS read-write
	STATUS  current
	DESCRIPTION
		"This parameter determines bitstream mode and timing mode of CES unit."
	::= { cesOverWlanUnit0Settings 2 }


cesOverWlanUnit0MaxJitter OBJECT-TYPE
	SYNTAX  INTEGER (1..200)
	UNITS
		"milliseconds"
	MAX-ACCESS read-write
	STATUS  current
	DESCRIPTION
		"The size of buffer to allow accommodation to packet
		delay variation."
	::= { cesOverWlanUnit0Settings 3 }


cesOverWlanUnit0FramesPerPacket OBJECT-TYPE
	SYNTAX  INTEGER (1..32)
	UNITS
		"frames"
	MAX-ACCESS read-write
	STATUS  current
	DESCRIPTION
		"Number of TDM frames per CES packet."
	::= { cesOverWlanUnit0Settings 4 }


cesOverWlanUnit0BandwithLimit OBJECT-TYPE
	SYNTAX  Unsigned32
	MAX-ACCESS read-write
	STATUS  current
	DESCRIPTION
		"Size of data padding allowed for each CES packet sent from this unit"
	::= { cesOverWlanUnit0Settings 5 }


cesOverWlanUnit0PortMap OBJECT-TYPE
	SYNTAX  Unsigned32
	MAX-ACCESS read-write
	STATUS  current
	DESCRIPTION
		"Bit map of ports enabled on this unit.
		bit 0 is set - port 0 is enabled
		bit 1 is set - port 1 is enabled
		...
		etc.

		"
	::= { cesOverWlanUnit0Settings 6 }


cesOverWlanMIBConformance OBJECT IDENTIFIER 	::= { cesOverWlan 2 }

cesOverWlanGroups OBJECT-GROUP
	OBJECTS {
		cesOverWlanUnit0Enabled,
		cesOverWlanUnit0Mode,
		cesOverWlanUnit0MaxJitter,
		cesOverWlanUnit0FramesPerPacket,
		cesOverWlanUnit0BandwithLimit,
		cesOverWlanUnit0PortMap }
	STATUS  current
	DESCRIPTION
		""
	::= { cesOverWlanMIBConformance 1 }

END

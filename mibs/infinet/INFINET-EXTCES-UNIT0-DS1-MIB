INFINET-EXTCES-UNIT0-DS1-MIB DEFINITIONS ::= BEGIN

IMPORTS
	transmission,
	MODULE-IDENTITY,
	OBJECT-TYPE,
	NOTIFICATION-TYPE
		FROM SNMPv2-SMI		-- [RFC2578]
	DisplayString,
	TimeStamp,
	TruthValue
		FROM SNMPv2-TC		-- [RFC2579]
	InterfaceIndex,
	ifIndex
		FROM IF-MIB		-- [RFC2863]
	PerfCurrentCount,
	PerfIntervalCount,
	PerfTotalCount
		FROM PerfHist-TC-MIB		-- [RFC3593]
	cesOverWlanUnit0
		FROM INFINET-EXTCES-MIB
	OBJECT-GROUP,
	NOTIFICATION-GROUP
		FROM SNMPv2-CONF;

cesOverWlanUnit0Ds1 MODULE-IDENTITY
	LAST-UPDATED "200706181910Z"
	ORGANIZATION "Infinet Wireless Ltd."
	CONTACT-INFO
		"Dmitry Petukhov

		Postal: Infinet Wireless Ltd,
		        Russia, Ekaterinburg,
		        Serafimi Deryabinoi st, 24

		Phone:  +7 343 217 9317
		Email:  d.petukhov@infinetwireless.com"
	DESCRIPTION
		"The mib module, containing various WanFlex options."
	REVISION "200408161910Z"
	DESCRIPTION
		"The mib module, containing DS1 objects for CesOverWlan unit. (adapted from rfc4805.txt)"
	::= { cesOverWlanUnit0 2 }


cesOverWlanUnit0Dsx1ConfigTable OBJECT-TYPE
	SYNTAX  SEQUENCE OF CesOverWlanUnit0Dsx1ConfigEntry
	MAX-ACCESS not-accessible
	STATUS  current
	DESCRIPTION
		"The DS1 Configuration table."
	::= { cesOverWlanUnit0Ds1 6 }


cesOverWlanUnit0Dsx1ConfigEntry OBJECT-TYPE
	SYNTAX  CesOverWlanUnit0Dsx1ConfigEntry
	MAX-ACCESS not-accessible
	STATUS  current
	DESCRIPTION
		"An entry in the DS1 Configuration table."
	INDEX {
		cesOverWlanUnit0Dsx1LineIndex }
	::= { cesOverWlanUnit0Dsx1ConfigTable 1 }


CesOverWlanUnit0Dsx1ConfigEntry ::= SEQUENCE {

	cesOverWlanUnit0Dsx1LineIndex                  InterfaceIndex,
	cesOverWlanUnit0Dsx1IfIndex                    InterfaceIndex,
	cesOverWlanUnit0Dsx1TimeElapsed                INTEGER,
	cesOverWlanUnit0Dsx1ValidIntervals             INTEGER,
	cesOverWlanUnit0Dsx1LineType                   INTEGER,
	cesOverWlanUnit0Dsx1LineCoding                 INTEGER,
	cesOverWlanUnit0Dsx1SendCode                   INTEGER,
	cesOverWlanUnit0Dsx1CircuitIdentifier          DisplayString,
	cesOverWlanUnit0Dsx1LoopbackConfig             INTEGER,
	cesOverWlanUnit0Dsx1LineStatus                 INTEGER,
	cesOverWlanUnit0Dsx1SignalMode                 INTEGER,
	cesOverWlanUnit0Dsx1TransmitClockSource        INTEGER,
	cesOverWlanUnit0Dsx1Fdl                        INTEGER,
	cesOverWlanUnit0Dsx1InvalidIntervals           INTEGER,
	cesOverWlanUnit0Dsx1LineLength                 INTEGER,
	cesOverWlanUnit0Dsx1LineStatusLastChange       TimeStamp,
	cesOverWlanUnit0Dsx1LineStatusChangeTrapEnable INTEGER,
	cesOverWlanUnit0Dsx1LoopbackStatus             INTEGER,
	cesOverWlanUnit0Dsx1Ds1ChannelNumber           INTEGER,
	cesOverWlanUnit0Dsx1Channelization             INTEGER,
	cesOverWlanUnit0Dsx1LineMode                   INTEGER,
	cesOverWlanUnit0Dsx1LineBuildOut               INTEGER,
	cesOverWlanUnit0Dsx1LineImpedance              INTEGER }


cesOverWlanUnit0Dsx1LineIndex OBJECT-TYPE
	SYNTAX  InterfaceIndex
	MAX-ACCESS read-only
	STATUS  current
	DESCRIPTION
		"This object should be made equal to ifIndex.  The
		next paragraph describes its previous usage.
		Making the object equal to ifIndex allows proper
		use of the ifStackTable and ds0/ds0bundle MIBs.

		Previously, this object was the identifier of a DS1
		interface on a managed device.  If there is an
		ifEntry that is directly associated with this and
		only this DS1 interface, it should have the same
		value as ifIndex.  Otherwise, number the
		dsx1LineIndices with a unique identifier
		following the rules of choosing a number that is
		greater than ifNumber and numbering the inside
		interfaces (e.g., equipment side) with even
		numbers and outside interfaces (e.g., network
		side) with odd numbers."
	::= { cesOverWlanUnit0Dsx1ConfigEntry 1 }


cesOverWlanUnit0Dsx1IfIndex OBJECT-TYPE
	SYNTAX  InterfaceIndex
	MAX-ACCESS read-only
	STATUS  deprecated
	DESCRIPTION
		"This value for this object is equal to the value
		of ifIndex from the Interfaces table (RFC 2863)."
	::= { cesOverWlanUnit0Dsx1ConfigEntry 2 }


cesOverWlanUnit0Dsx1TimeElapsed OBJECT-TYPE
	SYNTAX  INTEGER (0..899)
	MAX-ACCESS read-only
	STATUS  current
	DESCRIPTION
		"The number of seconds that have elapsed since the
		beginning of the near-end current error-
		measurement period.  If, for some reason, such as
		an adjustment in the system's time-of-day clock,
		the current interval exceeds the maximum value,
		the agent will return the maximum value."
	::= { cesOverWlanUnit0Dsx1ConfigEntry 3 }


cesOverWlanUnit0Dsx1ValidIntervals OBJECT-TYPE
	SYNTAX  INTEGER (0..96)
	MAX-ACCESS read-only
	STATUS  current
	DESCRIPTION
		"The number of previous near-end intervals for
		which data was collected.  The value will be 96
		unless the interface was brought online within the
		last 24 hours, in which case the value will be the
		number of complete 15-minute near-end intervals
		since the interface has been online.  In the case
		where the agent is a proxy, it is possible that
		some intervals are unavailable.  In this case,
		this interval is the maximum interval number for
		which data is available."
	::= { cesOverWlanUnit0Dsx1ConfigEntry 4 }


cesOverWlanUnit0Dsx1LineType OBJECT-TYPE
	SYNTAX  INTEGER {
			other(1),
			dsx1ESF(2),
			dsx1D4(3),
			dsx1E1(4),
			dsx1E1CRC(5),
			dsx1E1MF(6),
			dsx1E1CRCMF(7),
			dsx1Unframed(8),
			dsx1E1Unframed(9),
			dsx1DS2M12(10),
			dsx1E2(11),
			dsx1E1Q50(12),
			dsx1E1Q50CRC(13),
			dsx1J1ESF(14),
			dsx1J1Unframed(16) }
	MAX-ACCESS read-only
	STATUS  current
	DESCRIPTION
		"This variable indicates the variety of DS1
		Line implementing this circuit.  The type of
		circuit affects the number of bits per second
		that the circuit can reasonably carry, as well
		as the interpretation of the usage and error
		statistics.  The values, in sequence, describe:

		      TITLE:          SPECIFICATION:
		      dsx1ESF         Extended SuperFrame DS1
		                             (T1.107)
		      dsx1D4          AT&T D4 format DS1 (T1.107)
		      dsx1E1          ITU-T G.704, (Table 5A)
		      dsx1E1-CRC      ITU-T G.704, (Table 5B)
		      dsxE1-MF        G.704 (Table 5A) with TS16
		                             multiframing enabled
		      dsx1E1-CRC-MF   G.704 (Table 5B) with TS16
		                             multiframing enabled
		      dsx1Unframed    DS1 with No Framing
		      dsx1E1Unframed  E1 with No Framing (G.703)
		      dsx1DS2M12      DS2 frame format (T1.107)
		      dsx1E2          E2 frame format (G.704)
		      dsx1E1Q50       TS16 bits 5,7,8 set to 101,
		                      [in all other cases it is set
		                      to 111.] (G.704, table 14)
		      dsx1E1Q50CRC    E1Q50 with CRC
		      dsx1J1ESF       J1 according to (JT-G704,
		                             JT-G706, and JT-I431)
		      dsx1J1Unframed  J1 with No Framing

		For clarification, the capacity for each E1 type
		is as listed below:
		dsx1E1Unframed - E1, no framing = 32 x 64k = 2048k
		dsx1E1 or dsx1E1CRC - E1, with framing,
		no signalling = 31 x 64k = 1984k
		dsx1E1MF or dsx1E1CRCMF - E1, with framing,
		signalling = 30 x 64k = 1920k"
	REFERENCE
		"American National Standard for
		     telecommunications -
		     digital hierarchy - formats specification,
		     ANSI T1.107- 1988.
		ITU-T G.703: Physical/Electrical Characteristics
		     of Hierarchical Digital Interfaces, November
		     2001.
		ITU-T G.704: Synchronous frame structures used at
		     1544, 6312, 2048, 8488 and 44 736 kbit/s
		     Hierarchical Levels, July 1995.
		JT-G704: Synchronous frame structures used at
		     Primary and Secondary Hierarchical Levels,2002.
		JT-G706. Frame Alignment and Cyclic Redundancy
		     Check (CRC) Procedures.
		JT-I431. ISDN Primary Rate User-Network Interface,
		     Layer 1 Specifications, 2002"
	::= { cesOverWlanUnit0Dsx1ConfigEntry 5 }


cesOverWlanUnit0Dsx1LineCoding OBJECT-TYPE
	SYNTAX  INTEGER {
			dsx1JBZS(1),
			dsx1B8ZS(2),
			dsx1HDB3(3),
			dsx1ZBTSI(4),
			dsx1AMI(5),
			other(6),
			dsx1B6ZS(7) }
	MAX-ACCESS read-only
	STATUS  current
	DESCRIPTION
		"This variable describes the variety of Zero Code
		Suppression used on this interface, which in turn
		affects a number of its characteristics.

		dsx1JBZS refers the Jammed Bit Zero Suppression,
		in which the AT&T specification of at least one
		pulse every 8-bit period is literally implemented
		by forcing a pulse in bit 8 of each channel.
		Thus, only 7 bits per channel, or 1.344 Mbps,
		are available for data.

		dsx1B8ZS refers to the use of a specified pattern
		of normal bits and bipolar violations that are
		used to replace a sequence of 8 zero bits.
		ANSI Clear Channels may use dsx1ZBTSI, or Zero
		Byte Time Slot Interchange.

		E1 links, with or without CRC, use dsx1HDB3 or
		dsx1AMI.

		dsx1AMI refers to a mode wherein no Zero Code
		Suppression is present and the line encoding does
		not solve the problem directly.  In this
		application, the higher layer must provide data
		that meets or exceeds the pulse density
		requirements, such as inverting HDLC data.

		dsx1B6ZS refers to the user of a specified pattern
		of normal bits and bipolar violations that are
		used to replace a sequence of 6 zero bits.  Used
		for DS2.
		For more information about line coding see
		[ANSI-T1.102]"
	::= { cesOverWlanUnit0Dsx1ConfigEntry 6 }


cesOverWlanUnit0Dsx1SendCode OBJECT-TYPE
	SYNTAX  INTEGER {
			dsx1SendNoCode(1),
			dsx1SendLineCode(2),
			dsx1SendPayloadCode(3),
			dsx1SendResetCode(4),
			dsx1SendQRS(5),
			dsx1Send511Pattern(6),
			dsx1Send3in24Pattern(7),
			dsx1SendOtherTestPattern(8) }
	MAX-ACCESS read-only
	STATUS  current
	DESCRIPTION
		"This variable indicates what type of code is
		      being sent across the DS1 interface by the device.
		      The values mean the following:

		dsx1SendNoCode
		     sending looped or normal data

		dsx1SendLineCode
		     sending a request for a line loopback

		dsx1SendPayloadCode
		     sending a request for a payload loopback

		dsx1SendResetCode
		     sending a loopback termination request

		dsx1SendQRS
		     sending a Quasi-Random Signal (QRS) test
		     pattern

		dsx1Send511Pattern
		     sending a 511-bit fixed test pattern

		dsx1Send3in24Pattern
		     sending a fixed test pattern of 3 bits set
		     in 24

		dsx1SendOtherTestPattern
		     sending a test pattern other than those
		     described by this object"
	::= { cesOverWlanUnit0Dsx1ConfigEntry 7 }


cesOverWlanUnit0Dsx1CircuitIdentifier OBJECT-TYPE
	SYNTAX  DisplayString (SIZE (0..255))
	MAX-ACCESS read-only
	STATUS  current
	DESCRIPTION
		"This variable contains the transmission vendor's
		circuit identifier, for the purpose of
		facilitating troubleshooting."
	REFERENCE
		"ITU-T M.1400"
	::= { cesOverWlanUnit0Dsx1ConfigEntry 8 }


cesOverWlanUnit0Dsx1LoopbackConfig OBJECT-TYPE
	SYNTAX  INTEGER {
			dsx1NoLoop(1),
			dsx1PayloadLoop(2),
			dsx1LineLoop(3),
			dsx1OtherLoop(4),
			dsx1InwardLoop(5),
			dsx1DualLoop(6) }
	MAX-ACCESS read-only
	STATUS  current
	DESCRIPTION
		"This variable represents the desired loopback
		      configuration of the DS1 interface.  Agents
		      supporting read/write access should return
		      inconsistentValue in response to a requested
		      loopback state that the interface does not
		      support.  The values mean:

		dsx1NoLoop
		      not in the loopback state.  A device that is not
		      capable of performing a loopback on the interface
		      shall always return this as its value.

		dsx1PayloadLoop
		      the received signal at this interface is looped
		      through the device.  Typically, the received signal
		      is looped back for retransmission after it has
		      passed through the device's framing function.

		dsx1LineLoop
		      the received signal at this interface does not go
		      through the device (minimum penetration) but is
		      looped back out.

		dsx1OtherLoop
		      loopbacks that are not defined here.

		dsx1InwardLoop
		      the transmitted signal at this interface is
		      looped back and received by the same interface.
		      What is transmitted onto the line is product
		      dependent.

		dsx1DualLoop
		      both dsx1LineLoop and dsx1InwardLoop will be
		      active simultaneously."
	::= { cesOverWlanUnit0Dsx1ConfigEntry 9 }


cesOverWlanUnit0Dsx1LineStatus OBJECT-TYPE
	SYNTAX  INTEGER (1..131071)
	MAX-ACCESS read-only
	STATUS  current
	DESCRIPTION
		"This variable indicates the line status of the
		          interface.  It contains loopback, failure,
		          received alarm and transmitted alarms
		          information.

		          The cesOverWlanUnit0Dsx1LineStatus is a bitmap represented as a
		          sum; therefore, it can represent multiple failures
		          (alarms) and a LoopbackState simultaneously.

		          dsx1NoAlarm must be set if and only if no other
		          flag is set.

		          If the dsx1loopbackState bit is set, the loopback
		          in effect can be determined from the
		          dsx1loopbackConfig object.  The various bit
		          positions are as follows:

		    1     dsx1NoAlarm           No alarm present
		    2     dsx1RcvFarEndLOF      Far end LOF (a.k.a.
		                                Yellow Alarm)
		    4     dsx1XmtFarEndLOF      Near end sending LOF
		                                indication
		    8     dsx1RcvAIS            Far end sending AIS
		   16     dsx1XmtAIS            Near end sending AIS
		   32     dsx1LossOfFrame       Near end LOF (a.k.a.
		                                Red Alarm)
		   64     dsx1LossOfSignal      Near end Loss of Signal
		  128     dsx1LoopbackState     Near end is looped
		  256     dsx1T16AIS            E1 TS16 AIS
		  512     dsx1RcvFarEndLOMF     Far end sending TS16 LOMF
		 1024     dsx1XmtFarEndLOMF     Near end sending TS16 LOMF
		 2048     dsx1RcvTestCode       Near end detects a test code
		 4096     dsx1OtherFailure      Any line status not defined
		                                here
		 8192     dsx1UnavailSigState   Near end in unavailable
		                                signal state
		16384     dsx1NetEquipOOS       Carrier equipment out of
		                                service
		32768     dsx1RcvPayloadAIS     DS2 payload AIS
		65536     dsx1Ds2PerfThreshold  DS2 performance threshold
		                                exceeded"
	::= { cesOverWlanUnit0Dsx1ConfigEntry 10 }


cesOverWlanUnit0Dsx1SignalMode OBJECT-TYPE
	SYNTAX  INTEGER {
			none(1),
			robbedBit(2),
			bitOriented(3),
			messageOriented(4),
			other(5) }
	MAX-ACCESS read-only
	STATUS  current
	DESCRIPTION
		"'none' indicates that no bits are reserved for
		signaling on this channel.

		'robbedBit' indicates that DS1 Robbed Bit Signaling
		is in use.

		'bitOriented' indicates that E1 Channel Associated
		Signaling is in use.

		'messageOriented' indicates that Common Channel
		Signaling is in use on either channel 16 of
		an E1 link or channel 24 of a DS1."
	::= { cesOverWlanUnit0Dsx1ConfigEntry 11 }


cesOverWlanUnit0Dsx1TransmitClockSource OBJECT-TYPE
	SYNTAX  INTEGER {
			loopTiming(1),
			localTiming(2),
			throughTiming(3),
			adaptive(4) }
	MAX-ACCESS read-only
	STATUS  current
	DESCRIPTION
		"The source of transmit clock.

		 'loopTiming' indicates that the recovered
		 receive clock is used as the transmit clock.

		 'localTiming' indicates that a local clock
		source is used or when an external clock is
		attached to the box containing the interface.

		 'throughTiming' indicates that recovered
		receive clock from another interface is used as
		the transmit clock.

		 'adaptive' indicates that the clock is recovered
		based on the data flow and not based on the
		physical layer"
	::= { cesOverWlanUnit0Dsx1ConfigEntry 12 }


cesOverWlanUnit0Dsx1Fdl OBJECT-TYPE
	SYNTAX  INTEGER (1..15)
	MAX-ACCESS read-only
	STATUS  current
	DESCRIPTION
		"This bitmap describes the use of the
		facilities data link and is the sum of the
		capabilities.  Set any bits that are appropriate:

		other(1),
		dsx1AnsiT1403(2),
		dsx1Att54016(4),
		dsx1FdlNone(8)

		 'other' indicates that a protocol other than
		one of the following is used.

		 'dsx1AnsiT1403' refers to the FDL exchange
		recommended by ANSI.
		 'dsx1Att54016' refers to ESF FDL exchanges.

		 'dsx1FdlNone' indicates that the device does
		not use the FDL."
	::= { cesOverWlanUnit0Dsx1ConfigEntry 13 }


cesOverWlanUnit0Dsx1InvalidIntervals OBJECT-TYPE
	SYNTAX  INTEGER (0..96)
	MAX-ACCESS read-only
	STATUS  current
	DESCRIPTION
		"The number of intervals in the range from 0 to
		cesOverWlanUnit0Dsx1ValidIntervals for which no data is available.
		This object will typically be zero except in cases
		where the data for some intervals is not
		available (e.g., in proxy situations)."
	::= { cesOverWlanUnit0Dsx1ConfigEntry 14 }


cesOverWlanUnit0Dsx1LineLength OBJECT-TYPE
	SYNTAX  INTEGER (0..64000)
	UNITS
		"meters"
	MAX-ACCESS read-only
	STATUS  current
	DESCRIPTION
		"The length of the DS1 line in meters.  This
		object provides information for line build-out
		circuitry.  This object is only useful if the
		interface has configurable line build-out
		circuitry."
	::= { cesOverWlanUnit0Dsx1ConfigEntry 15 }


cesOverWlanUnit0Dsx1LineStatusLastChange OBJECT-TYPE
	SYNTAX  TimeStamp
	MAX-ACCESS read-only
	STATUS  current
	DESCRIPTION
		"The value of MIB II's sysUpTime object at the
		time this DS1 entered its current line status
		state.  If the current state was entered prior to
		the last re-initialization of the proxy-agent,
		then this object contains a zero value."
	::= { cesOverWlanUnit0Dsx1ConfigEntry 16 }


cesOverWlanUnit0Dsx1LineStatusChangeTrapEnable OBJECT-TYPE
	SYNTAX  INTEGER {
			enabled(1),
			disabled(2) }
	MAX-ACCESS read-only
	STATUS  current
	DESCRIPTION
		"Indicates whether cesOverWlanUnit0Dsx1LineStatusChange traps
		should be generated for this interface."
	DEFVAL { disabled }
	::= { cesOverWlanUnit0Dsx1ConfigEntry 17 }


cesOverWlanUnit0Dsx1LoopbackStatus OBJECT-TYPE
	SYNTAX  INTEGER (1..127)
	MAX-ACCESS read-only
	STATUS  current
	DESCRIPTION
		"This variable represents the current state of the
		loopback on the DS1 interface.  It contains
		information about loopbacks established by a
		manager and remotely from the far end.

		The cesOverWlanUnit0Dsx1LoopbackStatus is a bitmap represented as
		a sum; therefore, it can represent multiple
		loopbacks simultaneously.

		The various bit positions are as follows:
		 1  dsx1NoLoopback
		 2  dsx1NearEndPayloadLoopback
		 4  dsx1NearEndLineLoopback
		 8  dsx1NearEndOtherLoopback
		16  dsx1NearEndInwardLoopback
		32  dsx1FarEndPayloadLoopback
		64  dsx1FarEndLineLoopback"
	::= { cesOverWlanUnit0Dsx1ConfigEntry 18 }


cesOverWlanUnit0Dsx1Ds1ChannelNumber OBJECT-TYPE
	SYNTAX  INTEGER (0..28)
	MAX-ACCESS read-only
	STATUS  current
	DESCRIPTION
		"This variable represents the channel number of
		the DS1/E1 on its parent DS2/E2 or DS3/E3.  A
		value of 0 indicates that this DS1/E1 does not
		have a parent DS3/E3."
	::= { cesOverWlanUnit0Dsx1ConfigEntry 19 }


cesOverWlanUnit0Dsx1Channelization OBJECT-TYPE
	SYNTAX  INTEGER {
			disabled(1),
			enabledDs0(2),
			enabledDs1(3) }
	MAX-ACCESS read-only
	STATUS  current
	DESCRIPTION
		"Indicates whether this DS1/E1 or DS2 is
		channelized or unchannelized.

		The value of enabledDs0(2) indicates that this is a
		DS1 channelized into DS0s.  Setting this value will
		cause the creation, and resetting it to disabled(1)
		will cause the deletion of entries in the ifTable
		for the DS0s that are within the DS1.

		The value of enabledDs1(3) indicates that this is a
		DS2 channelized into DS1s.  Setting this value will
		cause the creation, and resetting it to disabled(1)
		will cause the deletion of entries in the ifTable
		for the DS1s that are within the DS2."
	::= { cesOverWlanUnit0Dsx1ConfigEntry 20 }


cesOverWlanUnit0Dsx1LineMode OBJECT-TYPE
	SYNTAX  INTEGER {
			csu(1),
			dsu(2) }
	MAX-ACCESS read-only
	STATUS  current
	DESCRIPTION
		"This setting puts the T1 framer into either
		long-haul (CSU) mode or short-haul (DSU) mode."
	::= { cesOverWlanUnit0Dsx1ConfigEntry 21 }


cesOverWlanUnit0Dsx1LineBuildOut OBJECT-TYPE
	SYNTAX  INTEGER {
			notApplicable(1),
			neg75dB(2),
			neg15dB(3),
			neg225dB(4),
			zerodB(5) }
	MAX-ACCESS read-only
	STATUS  current
	DESCRIPTION
		"Attenuation setting for T1 framer in long haul
		(CSU) mode.  The optional values are -7.5dB,
		-15dB, -22.5dB, and 0dB."
	::= { cesOverWlanUnit0Dsx1ConfigEntry 22 }


cesOverWlanUnit0Dsx1LineImpedance OBJECT-TYPE
	SYNTAX  INTEGER {
			notApplicable(1),
			unbalanced75ohms(2),
			balanced100ohms(3),
			balanced120ohms(4) }
	MAX-ACCESS read-only
	STATUS  current
	DESCRIPTION
		"Nominal line impedance.  For T1 and J1 lines, the
		value is typically balanced100ohms(3).  For E1
		lines, the value is typically unbalanced75ohms(2)
		and balanced120ohms(4).  When this object does not
		apply, or when the appropriate value is not known,
		the value should be set to notApplicable(1)."
	::= { cesOverWlanUnit0Dsx1ConfigEntry 23 }


-- The DS1 Current Table

cesOverWlanUnit0Dsx1CurrentTable OBJECT-TYPE
	SYNTAX  SEQUENCE OF CesOverWlanUnit0Dsx1CurrentEntry
	MAX-ACCESS not-accessible
	STATUS  current
	DESCRIPTION
		"The DS1 Current table contains various statistics
		being collected for the current 15-minute
		interval."
	::= { cesOverWlanUnit0Ds1 7 }


cesOverWlanUnit0Dsx1CurrentEntry OBJECT-TYPE
	SYNTAX  CesOverWlanUnit0Dsx1CurrentEntry
	MAX-ACCESS not-accessible
	STATUS  current
	DESCRIPTION
		"An entry in the DS1 Current table."
	INDEX {
		cesOverWlanUnit0Dsx1CurrentIndex }
	::= { cesOverWlanUnit0Dsx1CurrentTable 1 }


CesOverWlanUnit0Dsx1CurrentEntry ::= SEQUENCE {

	cesOverWlanUnit0Dsx1CurrentIndex InterfaceIndex,
	cesOverWlanUnit0Dsx1CurrentESs   PerfCurrentCount,
	cesOverWlanUnit0Dsx1CurrentSESs  PerfCurrentCount,
	cesOverWlanUnit0Dsx1CurrentSEFSs PerfCurrentCount,
	cesOverWlanUnit0Dsx1CurrentUASs  PerfCurrentCount,
	cesOverWlanUnit0Dsx1CurrentCSSs  PerfCurrentCount,
	cesOverWlanUnit0Dsx1CurrentPCVs  PerfCurrentCount,
	cesOverWlanUnit0Dsx1CurrentLESs  PerfCurrentCount,
	cesOverWlanUnit0Dsx1CurrentBESs  PerfCurrentCount,
	cesOverWlanUnit0Dsx1CurrentDMs   PerfCurrentCount,
	cesOverWlanUnit0Dsx1CurrentLCVs  PerfCurrentCount }


cesOverWlanUnit0Dsx1CurrentIndex OBJECT-TYPE
	SYNTAX  InterfaceIndex
	MAX-ACCESS read-only
	STATUS  current
	DESCRIPTION
		"The index value that uniquely identifies the DS1
		interface to which this entry is applicable.  The
		interface identified by a particular value of this
		index is the same interface as identified by the
		same value as a cesOverWlanUnit0Dsx1LineIndex object instance."
	::= { cesOverWlanUnit0Dsx1CurrentEntry 1 }


cesOverWlanUnit0Dsx1CurrentESs OBJECT-TYPE
	SYNTAX  PerfCurrentCount
	MAX-ACCESS read-only
	STATUS  current
	DESCRIPTION
		"The number of Errored Seconds."
	::= { cesOverWlanUnit0Dsx1CurrentEntry 2 }


cesOverWlanUnit0Dsx1CurrentSESs OBJECT-TYPE
	SYNTAX  PerfCurrentCount
	MAX-ACCESS read-only
	STATUS  current
	DESCRIPTION
		"The number of Severely Errored Seconds."
	::= { cesOverWlanUnit0Dsx1CurrentEntry 3 }


cesOverWlanUnit0Dsx1CurrentSEFSs OBJECT-TYPE
	SYNTAX  PerfCurrentCount
	MAX-ACCESS read-only
	STATUS  current
	DESCRIPTION
		"The number of Severely Errored Framing Seconds."
	::= { cesOverWlanUnit0Dsx1CurrentEntry 4 }


cesOverWlanUnit0Dsx1CurrentUASs OBJECT-TYPE
	SYNTAX  PerfCurrentCount
	MAX-ACCESS read-only
	STATUS  current
	DESCRIPTION
		"The number of Unavailable Seconds."
	::= { cesOverWlanUnit0Dsx1CurrentEntry 5 }


cesOverWlanUnit0Dsx1CurrentCSSs OBJECT-TYPE
	SYNTAX  PerfCurrentCount
	MAX-ACCESS read-only
	STATUS  current
	DESCRIPTION
		"The number of Controlled Slip Seconds."
	::= { cesOverWlanUnit0Dsx1CurrentEntry 6 }


cesOverWlanUnit0Dsx1CurrentPCVs OBJECT-TYPE
	SYNTAX  PerfCurrentCount
	MAX-ACCESS read-only
	STATUS  current
	DESCRIPTION
		"The number of Path Coding Violations."
	::= { cesOverWlanUnit0Dsx1CurrentEntry 7 }


cesOverWlanUnit0Dsx1CurrentLESs OBJECT-TYPE
	SYNTAX  PerfCurrentCount
	MAX-ACCESS read-only
	STATUS  current
	DESCRIPTION
		"The number of Line Errored Seconds."
	::= { cesOverWlanUnit0Dsx1CurrentEntry 8 }


cesOverWlanUnit0Dsx1CurrentBESs OBJECT-TYPE
	SYNTAX  PerfCurrentCount
	MAX-ACCESS read-only
	STATUS  current
	DESCRIPTION
		"The number of Bursty Errored Seconds."
	::= { cesOverWlanUnit0Dsx1CurrentEntry 9 }


cesOverWlanUnit0Dsx1CurrentDMs OBJECT-TYPE
	SYNTAX  PerfCurrentCount
	MAX-ACCESS read-only
	STATUS  deprecated
	DESCRIPTION
		"The number of Degraded Minutes."
	::= { cesOverWlanUnit0Dsx1CurrentEntry 10 }


cesOverWlanUnit0Dsx1CurrentLCVs OBJECT-TYPE
	SYNTAX  PerfCurrentCount
	MAX-ACCESS read-only
	STATUS  current
	DESCRIPTION
		"The number of Line Coding Violations (LCVs)."
	::= { cesOverWlanUnit0Dsx1CurrentEntry 11 }


-- The DS1 Interval Table

cesOverWlanUnit0Dsx1IntervalTable OBJECT-TYPE
	SYNTAX  SEQUENCE OF CesOverWlanUnit0Dsx1IntervalEntry
	MAX-ACCESS not-accessible
	STATUS  current
	DESCRIPTION
		"The DS1 Interval table contains various
		statistics collected by each DS1 interface over
		the previous 24 hours of operation.  The past 24
		hours are broken into 96 completed 15-minute
		intervals.  Each row in this table represents one
		such interval (identified by cesOverWlanUnit0Dsx1IntervalNumber)
		for one specific instance (identified by
		cesOverWlanUnit0Dsx1IntervalIndex)."
	::= { cesOverWlanUnit0Ds1 8 }


cesOverWlanUnit0Dsx1IntervalEntry OBJECT-TYPE
	SYNTAX  CesOverWlanUnit0Dsx1IntervalEntry
	MAX-ACCESS not-accessible
	STATUS  current
	DESCRIPTION
		"An entry in the DS1 Interval table."
	INDEX {
		cesOverWlanUnit0Dsx1IntervalIndex,
		cesOverWlanUnit0Dsx1IntervalNumber }
	::= { cesOverWlanUnit0Dsx1IntervalTable 1 }


CesOverWlanUnit0Dsx1IntervalEntry ::= SEQUENCE {

	cesOverWlanUnit0Dsx1IntervalIndex     InterfaceIndex,
	cesOverWlanUnit0Dsx1IntervalNumber    INTEGER,
	cesOverWlanUnit0Dsx1IntervalESs       PerfIntervalCount,
	cesOverWlanUnit0Dsx1IntervalSESs      PerfIntervalCount,
	cesOverWlanUnit0Dsx1IntervalSEFSs     PerfIntervalCount,
	cesOverWlanUnit0Dsx1IntervalUASs      PerfIntervalCount,
	cesOverWlanUnit0Dsx1IntervalCSSs      PerfIntervalCount,
	cesOverWlanUnit0Dsx1IntervalPCVs      PerfIntervalCount,
	cesOverWlanUnit0Dsx1IntervalLESs      PerfIntervalCount,
	cesOverWlanUnit0Dsx1IntervalBESs      PerfIntervalCount,
	cesOverWlanUnit0Dsx1IntervalDMs       PerfIntervalCount,
	cesOverWlanUnit0Dsx1IntervalLCVs      PerfIntervalCount,
	cesOverWlanUnit0Dsx1IntervalValidData TruthValue }


cesOverWlanUnit0Dsx1IntervalIndex OBJECT-TYPE
	SYNTAX  InterfaceIndex
	MAX-ACCESS read-only
	STATUS  current
	DESCRIPTION
		"The index value that uniquely identifies the DS1
		interface to which this entry is applicable.  The
		interface identified by a particular value of this
		index is the same interface as identified by the
		same value as a cesOverWlanUnit0Dsx1LineIndex object instance."
	::= { cesOverWlanUnit0Dsx1IntervalEntry 1 }


cesOverWlanUnit0Dsx1IntervalNumber OBJECT-TYPE
	SYNTAX  INTEGER (1..96)
	MAX-ACCESS read-only
	STATUS  current
	DESCRIPTION
		"A number between 1 and 96, where 1 is the most
		recently completed 15-minute interval and 96 is
		the 15-minute interval completed 23 hours and 45
		minutes prior to interval 1."
	::= { cesOverWlanUnit0Dsx1IntervalEntry 2 }


cesOverWlanUnit0Dsx1IntervalESs OBJECT-TYPE
	SYNTAX  PerfIntervalCount
	MAX-ACCESS read-only
	STATUS  current
	DESCRIPTION
		"The number of Errored Seconds."
	::= { cesOverWlanUnit0Dsx1IntervalEntry 3 }


cesOverWlanUnit0Dsx1IntervalSESs OBJECT-TYPE
	SYNTAX  PerfIntervalCount
	MAX-ACCESS read-only
	STATUS  current
	DESCRIPTION
		"The number of Severely Errored Seconds."
	::= { cesOverWlanUnit0Dsx1IntervalEntry 4 }


cesOverWlanUnit0Dsx1IntervalSEFSs OBJECT-TYPE
	SYNTAX  PerfIntervalCount
	MAX-ACCESS read-only
	STATUS  current
	DESCRIPTION
		"The number of Severely Errored Framing Seconds."
	::= { cesOverWlanUnit0Dsx1IntervalEntry 5 }


cesOverWlanUnit0Dsx1IntervalUASs OBJECT-TYPE
	SYNTAX  PerfIntervalCount
	MAX-ACCESS read-only
	STATUS  current
	DESCRIPTION
		"The number of Unavailable Seconds.  This object
		may decrease if the occurrence of unavailable
		seconds occurs across an interval boundary."
	::= { cesOverWlanUnit0Dsx1IntervalEntry 6 }


cesOverWlanUnit0Dsx1IntervalCSSs OBJECT-TYPE
	SYNTAX  PerfIntervalCount
	MAX-ACCESS read-only
	STATUS  current
	DESCRIPTION
		"The number of Controlled Slip Seconds."
	::= { cesOverWlanUnit0Dsx1IntervalEntry 7 }


cesOverWlanUnit0Dsx1IntervalPCVs OBJECT-TYPE
	SYNTAX  PerfIntervalCount
	MAX-ACCESS read-only
	STATUS  current
	DESCRIPTION
		"The number of Path Coding Violations."
	::= { cesOverWlanUnit0Dsx1IntervalEntry 8 }


cesOverWlanUnit0Dsx1IntervalLESs OBJECT-TYPE
	SYNTAX  PerfIntervalCount
	MAX-ACCESS read-only
	STATUS  current
	DESCRIPTION
		"The number of Line Errored Seconds."
	::= { cesOverWlanUnit0Dsx1IntervalEntry 9 }


cesOverWlanUnit0Dsx1IntervalBESs OBJECT-TYPE
	SYNTAX  PerfIntervalCount
	MAX-ACCESS read-only
	STATUS  current
	DESCRIPTION
		"The number of Bursty Errored Seconds."
	::= { cesOverWlanUnit0Dsx1IntervalEntry 10 }


cesOverWlanUnit0Dsx1IntervalDMs OBJECT-TYPE
	SYNTAX  PerfIntervalCount
	MAX-ACCESS read-only
	STATUS  deprecated
	DESCRIPTION
		"The number of Degraded Minutes."
	::= { cesOverWlanUnit0Dsx1IntervalEntry 11 }


cesOverWlanUnit0Dsx1IntervalLCVs OBJECT-TYPE
	SYNTAX  PerfIntervalCount
	MAX-ACCESS read-only
	STATUS  current
	DESCRIPTION
		"The number of Line Coding Violations."
	::= { cesOverWlanUnit0Dsx1IntervalEntry 12 }


cesOverWlanUnit0Dsx1IntervalValidData OBJECT-TYPE
	SYNTAX  TruthValue
	MAX-ACCESS read-only
	STATUS  current
	DESCRIPTION
		"This variable indicates whether the data for this
		interval is valid."
	::= { cesOverWlanUnit0Dsx1IntervalEntry 13 }


-- The DS1 Total Table

cesOverWlanUnit0Dsx1TotalTable OBJECT-TYPE
	SYNTAX  SEQUENCE OF CesOverWlanUnit0Dsx1TotalEntry
	MAX-ACCESS not-accessible
	STATUS  current
	DESCRIPTION
		"The DS1 Total table contains the cumulative sum
		of the various statistics for the 24-hour period
		preceding the current interval."
	::= { cesOverWlanUnit0Ds1 9 }


cesOverWlanUnit0Dsx1TotalEntry OBJECT-TYPE
	SYNTAX  CesOverWlanUnit0Dsx1TotalEntry
	MAX-ACCESS not-accessible
	STATUS  current
	DESCRIPTION
		"An entry in the DS1 Total table."
	INDEX {
		cesOverWlanUnit0Dsx1TotalIndex }
	::= { cesOverWlanUnit0Dsx1TotalTable 1 }


CesOverWlanUnit0Dsx1TotalEntry ::= SEQUENCE {

	cesOverWlanUnit0Dsx1TotalIndex InterfaceIndex,
	cesOverWlanUnit0Dsx1TotalESs   PerfTotalCount,
	cesOverWlanUnit0Dsx1TotalSESs  PerfTotalCount,
	cesOverWlanUnit0Dsx1TotalSEFSs PerfTotalCount,
	cesOverWlanUnit0Dsx1TotalUASs  PerfTotalCount,
	cesOverWlanUnit0Dsx1TotalCSSs  PerfTotalCount,
	cesOverWlanUnit0Dsx1TotalPCVs  PerfTotalCount,
	cesOverWlanUnit0Dsx1TotalLESs  PerfTotalCount,
	cesOverWlanUnit0Dsx1TotalBESs  PerfTotalCount,
	cesOverWlanUnit0Dsx1TotalDMs   PerfTotalCount,
	cesOverWlanUnit0Dsx1TotalLCVs  PerfTotalCount }


cesOverWlanUnit0Dsx1TotalIndex OBJECT-TYPE
	SYNTAX  InterfaceIndex
	MAX-ACCESS read-only
	STATUS  current
	DESCRIPTION
		"The index value that uniquely identifies the DS1
		interface to which this entry is applicable.  The
		interface identified by a particular value of this
		index is the same interface as identified by the
		same value as a cesOverWlanUnit0Dsx1LineIndex object instance."
	::= { cesOverWlanUnit0Dsx1TotalEntry 1 }


cesOverWlanUnit0Dsx1TotalESs OBJECT-TYPE
	SYNTAX  PerfTotalCount
	MAX-ACCESS read-only
	STATUS  current
	DESCRIPTION
		"The number of Errored Seconds encountered by a DS1
		interface in the previous 24-hour interval.
		Invalid 15-minute intervals count as 0."
	::= { cesOverWlanUnit0Dsx1TotalEntry 2 }


cesOverWlanUnit0Dsx1TotalSESs OBJECT-TYPE
	SYNTAX  PerfTotalCount
	MAX-ACCESS read-only
	STATUS  current
	DESCRIPTION
		"The number of Severely Errored Seconds
		encountered by a DS1 interface in the previous
		24-hour interval.  Invalid 15-minute intervals
		count as 0."
	::= { cesOverWlanUnit0Dsx1TotalEntry 3 }


cesOverWlanUnit0Dsx1TotalSEFSs OBJECT-TYPE
	SYNTAX  PerfTotalCount
	MAX-ACCESS read-only
	STATUS  current
	DESCRIPTION
		"The number of Severely Errored Framing Seconds
		encountered by a DS1 interface in the previous
		24-hour interval.  Invalid 15-minute intervals
		count as 0."
	::= { cesOverWlanUnit0Dsx1TotalEntry 4 }


cesOverWlanUnit0Dsx1TotalUASs OBJECT-TYPE
	SYNTAX  PerfTotalCount
	MAX-ACCESS read-only
	STATUS  current
	DESCRIPTION
		"The number of Unavailable Seconds encountered by
		a DS1 interface in the previous 24-hour interval.
		Invalid 15-minute intervals count as 0."
	::= { cesOverWlanUnit0Dsx1TotalEntry 5 }


cesOverWlanUnit0Dsx1TotalCSSs OBJECT-TYPE
	SYNTAX  PerfTotalCount
	MAX-ACCESS read-only
	STATUS  current
	DESCRIPTION
		"The number of Controlled Slip Seconds encountered
		by a DS1 interface in the previous 24-hour
		interval.  Invalid 15-minute intervals count as
		0."
	::= { cesOverWlanUnit0Dsx1TotalEntry 6 }


cesOverWlanUnit0Dsx1TotalPCVs OBJECT-TYPE
	SYNTAX  PerfTotalCount
	MAX-ACCESS read-only
	STATUS  current
	DESCRIPTION
		"The number of Path Coding Violations encountered
		by a DS1 interface in the previous 24-hour
		interval.  Invalid 15-minute intervals count as
		0."
	::= { cesOverWlanUnit0Dsx1TotalEntry 7 }


cesOverWlanUnit0Dsx1TotalLESs OBJECT-TYPE
	SYNTAX  PerfTotalCount
	MAX-ACCESS read-only
	STATUS  current
	DESCRIPTION
		"The number of Line Errored Seconds encountered by
		a DS1 interface in the previous 24-hour interval.
		Invalid 15-minute intervals count as 0."
	::= { cesOverWlanUnit0Dsx1TotalEntry 8 }


cesOverWlanUnit0Dsx1TotalBESs OBJECT-TYPE
	SYNTAX  PerfTotalCount
	MAX-ACCESS read-only
	STATUS  current
	DESCRIPTION
		"The number of Bursty Errored Seconds (BESs)
		encountered by a DS1 interface in the previous
		24-hour interval.  Invalid 15-minute intervals count
		as 0."
	::= { cesOverWlanUnit0Dsx1TotalEntry 9 }


cesOverWlanUnit0Dsx1TotalDMs OBJECT-TYPE
	SYNTAX  PerfTotalCount
	MAX-ACCESS read-only
	STATUS  deprecated
	DESCRIPTION
		"The number of Degraded Minutes (DMs) encountered
		by a DS1 interface in the previous 24-hour
		interval.  Invalid 15-minute intervals count as
		0."
	::= { cesOverWlanUnit0Dsx1TotalEntry 10 }


cesOverWlanUnit0Dsx1TotalLCVs OBJECT-TYPE
	SYNTAX  PerfTotalCount
	MAX-ACCESS read-only
	STATUS  current
	DESCRIPTION
		"The number of Line Coding Violations (LCVs)
		encountered by a DS1 interface in the current
		15-minute interval.  Invalid 15-minute intervals
		count as 0."
	::= { cesOverWlanUnit0Dsx1TotalEntry 11 }


cesOverWlanUnit0Ds1TrapsPrefix OBJECT IDENTIFIER 	::= { cesOverWlanUnit0Ds1 15 }

-- DS1 TRAPS

cesOverWlanUnit0Ds1Traps OBJECT IDENTIFIER 	::= { cesOverWlanUnit0Ds1TrapsPrefix 0 }

cesOverWlanUnit0Dsx1LineStatusChange NOTIFICATION-TYPE
	OBJECTS {
		cesOverWlanUnit0Dsx1LineStatus,
		cesOverWlanUnit0Dsx1LineStatusLastChange}
	STATUS  current
	DESCRIPTION
		"A cesOverWlanUnit0Dsx1LineStatusChange trap is sent when the
		value of an instance dsx1LineStatus changes.  It
		can be utilized by an Network Management Station
		(NMS) to trigger polls.  When the line status
		change results from a higher-level line status
		change (i.e., DS3), then no traps for the DS1
		are sent."
	::= { cesOverWlanUnit0Ds1Traps 1 }


cesOverWlanUnit0MIBConformance OBJECT IDENTIFIER 	::= { cesOverWlanUnit0Ds1 16 }

cesOverWlanUnit0Group OBJECT-GROUP
	OBJECTS {
		cesOverWlanUnit0Dsx1LineIndex,
		cesOverWlanUnit0Dsx1IfIndex,
		cesOverWlanUnit0Dsx1TimeElapsed,
		cesOverWlanUnit0Dsx1ValidIntervals,
		cesOverWlanUnit0Dsx1LineType,
		cesOverWlanUnit0Dsx1LineCoding,
		cesOverWlanUnit0Dsx1SendCode,
		cesOverWlanUnit0Dsx1CircuitIdentifier,
		cesOverWlanUnit0Dsx1LoopbackConfig,
		cesOverWlanUnit0Dsx1LineStatus,
		cesOverWlanUnit0Dsx1SignalMode,
		cesOverWlanUnit0Dsx1TransmitClockSource,
		cesOverWlanUnit0Dsx1Fdl,
		cesOverWlanUnit0Dsx1InvalidIntervals,
		cesOverWlanUnit0Dsx1LineLength,
		cesOverWlanUnit0Dsx1LineStatusLastChange,
		cesOverWlanUnit0Dsx1LineStatusChangeTrapEnable,
		cesOverWlanUnit0Dsx1LoopbackStatus,
		cesOverWlanUnit0Dsx1Ds1ChannelNumber,
		cesOverWlanUnit0Dsx1Channelization,
		cesOverWlanUnit0Dsx1LineMode,
		cesOverWlanUnit0Dsx1LineBuildOut,
		cesOverWlanUnit0Dsx1LineImpedance,
		cesOverWlanUnit0Dsx1CurrentIndex,
		cesOverWlanUnit0Dsx1CurrentESs,
		cesOverWlanUnit0Dsx1CurrentSESs,
		cesOverWlanUnit0Dsx1CurrentSEFSs,
		cesOverWlanUnit0Dsx1CurrentUASs,
		cesOverWlanUnit0Dsx1CurrentCSSs,
		cesOverWlanUnit0Dsx1CurrentPCVs,
		cesOverWlanUnit0Dsx1CurrentLESs,
		cesOverWlanUnit0Dsx1CurrentBESs,
		cesOverWlanUnit0Dsx1CurrentDMs,
		cesOverWlanUnit0Dsx1CurrentLCVs,
		cesOverWlanUnit0Dsx1IntervalIndex,
		cesOverWlanUnit0Dsx1IntervalNumber,
		cesOverWlanUnit0Dsx1IntervalESs,
		cesOverWlanUnit0Dsx1IntervalSESs,
		cesOverWlanUnit0Dsx1IntervalSEFSs,
		cesOverWlanUnit0Dsx1IntervalUASs,
		cesOverWlanUnit0Dsx1IntervalCSSs,
		cesOverWlanUnit0Dsx1IntervalPCVs,
		cesOverWlanUnit0Dsx1IntervalLESs,
		cesOverWlanUnit0Dsx1IntervalBESs,
		cesOverWlanUnit0Dsx1IntervalDMs,
		cesOverWlanUnit0Dsx1IntervalLCVs,
		cesOverWlanUnit0Dsx1IntervalValidData,
		cesOverWlanUnit0Dsx1TotalIndex,
		cesOverWlanUnit0Dsx1TotalESs,
		cesOverWlanUnit0Dsx1TotalSESs,
		cesOverWlanUnit0Dsx1TotalSEFSs,
		cesOverWlanUnit0Dsx1TotalUASs,
		cesOverWlanUnit0Dsx1TotalCSSs,
		cesOverWlanUnit0Dsx1TotalPCVs,
		cesOverWlanUnit0Dsx1TotalLESs,
		cesOverWlanUnit0Dsx1TotalBESs,
		cesOverWlanUnit0Dsx1TotalDMs,
		cesOverWlanUnit0Dsx1TotalLCVs }
	STATUS  current
	DESCRIPTION
		""
	::= { cesOverWlanUnit0MIBConformance 2 }

cesOverWlanUnit0Notifications NOTIFICATION-GROUP
	NOTIFICATIONS {
		cesOverWlanUnit0Dsx1LineStatusChange }
	STATUS  current
	DESCRIPTION
		""
	::= { cesOverWlanUnit0MIBConformance 1 }

END

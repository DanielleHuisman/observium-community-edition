INFINET-EXTCES-UNIT0-PACKET-MIB DEFINITIONS ::= BEGIN

IMPORTS
	TimeStamp
		FROM SNMPv2-TC		-- [RFC2579]
	cesOverWlanUnit0
		FROM INFINET-EXTCES-MIB
	MODULE-IDENTITY,
	OBJECT-TYPE,
	NOTIFICATION-TYPE,
	Counter32,
	Integer32,
	Unsigned32
		FROM SNMPv2-SMI
	OBJECT-GROUP,
	NOTIFICATION-GROUP
		FROM SNMPv2-CONF;

cesOverWlanUnit0Packet MODULE-IDENTITY
	LAST-UPDATED "200706181910Z"
	ORGANIZATION "Infinet Wireless Ltd."
	CONTACT-INFO
		"Dmitry Petukhov

		Postal: Infinet Wireless Ltd,
		        Russia, Ekaterinburg,
		        Serafimi Deryabinoi st, 24

		Phone:  +7 343 217 9317
		Email:  d.petukhov@infinetwireless.com"
	DESCRIPTION
		"The mib module, containing various WanFlex options."
	REVISION "200408161910Z"
	DESCRIPTION
		"The mib module, containing Packet interface objects for CesOverWlan unit."
	::= { cesOverWlanUnit0 3 }


cesOverWlanUnit0PacketTable OBJECT-TYPE
	SYNTAX  SEQUENCE OF CesOverWlanUnit0PacketEntry
	MAX-ACCESS not-accessible
	STATUS  current
	DESCRIPTION
		"The Packet protocol table."
	::= { cesOverWlanUnit0Packet 1 }


cesOverWlanUnit0PacketEntry OBJECT-TYPE
	SYNTAX  CesOverWlanUnit0PacketEntry
	MAX-ACCESS not-accessible
	STATUS  current
	DESCRIPTION
		"An entry in the Packet protocol table."
	INDEX {
		cesOverWlanUnit0PacketPortNumber }
	::= { cesOverWlanUnit0PacketTable 1 }


CesOverWlanUnit0PacketEntry ::= SEQUENCE {

	cesOverWlanUnit0PacketPortNumber                   Unsigned32,
	cesOverWlanUnit0PacketTxState                      INTEGER,
	cesOverWlanUnit0PacketRxState                      INTEGER,
	cesOverWlanUnit0PacketTxRestarts                   Counter32,
	cesOverWlanUnit0PacketRxRestarts                   Counter32,
	cesOverWlanUnit0PacketJitterCur                    Integer32,
	cesOverWlanUnit0PacketJitterMin                    Integer32,
	cesOverWlanUnit0PacketJitterMax                    Integer32,
	cesOverWlanUnit0PacketTotalInPackets               Counter32,
	cesOverWlanUnit0PacketValidPackets                 Counter32,
	cesOverWlanUnit0PacketRbitPackets                  Counter32,
	cesOverWlanUnit0PacketLbitPackets                  Counter32,
	cesOverWlanUnit0PacketLatePackets                  Counter32,
	cesOverWlanUnit0PacketLostPackets                  Counter32,
	cesOverWlanUnit0PacketOutOfOrderPackets            Counter32,
	cesOverWlanUnit0PacketUnderrunPackets              Counter32,
	cesOverWlanUnit0PacketOverrunPackets               Counter32,
	cesOverWlanUnit0PacketInvalidSequencePackets       Counter32,
	cesOverWlanUnit0PacketDuplicatePackets             Counter32,
	cesOverWlanUnit0PacketMalformedPackets             Counter32,
	cesOverWlanUnit0PacketJitterBufferStatus           INTEGER,
	cesOverWlanUnit0PacketJitterBufferStatusLastChange TimeStamp }


cesOverWlanUnit0PacketPortNumber OBJECT-TYPE
	SYNTAX  Unsigned32
	MAX-ACCESS read-only
	STATUS  current
	DESCRIPTION
		"Port number for which this packet protocol statistics is relevant."
	::= { cesOverWlanUnit0PacketEntry 1 }


cesOverWlanUnit0PacketTxState OBJECT-TYPE
	SYNTAX  INTEGER {
			on(1),
			off(2) }
	MAX-ACCESS read-only
	STATUS  current
	DESCRIPTION
		"State of transmit of packet protocol."
	::= { cesOverWlanUnit0PacketEntry 2 }


cesOverWlanUnit0PacketRxState OBJECT-TYPE
	SYNTAX  INTEGER {
			on(1),
			off(2) }
	MAX-ACCESS read-only
	STATUS  current
	DESCRIPTION
		"State of receive of packet protocol."
	::= { cesOverWlanUnit0PacketEntry 3 }


cesOverWlanUnit0PacketTxRestarts OBJECT-TYPE
	SYNTAX  Counter32
	MAX-ACCESS read-only
	STATUS  current
	DESCRIPTION
		"Number of transmit restarts."
	::= { cesOverWlanUnit0PacketEntry 4 }


cesOverWlanUnit0PacketRxRestarts OBJECT-TYPE
	SYNTAX  Counter32
	MAX-ACCESS read-only
	STATUS  current
	DESCRIPTION
		"Number of receive restarts."
	::= { cesOverWlanUnit0PacketEntry 5 }


cesOverWlanUnit0PacketJitterCur OBJECT-TYPE
	SYNTAX  Integer32
	UNITS
		"microseconds"
	MAX-ACCESS read-write
	STATUS  current
	DESCRIPTION
		"Current jitter buffer level, in microseconds."
	::= { cesOverWlanUnit0PacketEntry 6 }


cesOverWlanUnit0PacketJitterMin OBJECT-TYPE
	SYNTAX  Integer32
	UNITS
		"microseconds"
	MAX-ACCESS read-only
	STATUS  current
	DESCRIPTION
		"Minimum jitter buffer level, in microseconds."
	::= { cesOverWlanUnit0PacketEntry 7 }


cesOverWlanUnit0PacketJitterMax OBJECT-TYPE
	SYNTAX  Integer32
	UNITS
		"microseconds"
	MAX-ACCESS read-only
	STATUS  current
	DESCRIPTION
		"Maximum jitter buffer level, in microseconds."
	::= { cesOverWlanUnit0PacketEntry 8 }


cesOverWlanUnit0PacketTotalInPackets OBJECT-TYPE
	SYNTAX  Counter32
	MAX-ACCESS read-only
	STATUS  current
	DESCRIPTION
		"Total packet-protocol packets received."
	::= { cesOverWlanUnit0PacketEntry 9 }


cesOverWlanUnit0PacketValidPackets OBJECT-TYPE
	SYNTAX  Counter32
	MAX-ACCESS read-only
	STATUS  current
	DESCRIPTION
		"percent of valid packet-protocol packets received."
	::= { cesOverWlanUnit0PacketEntry 10 }


cesOverWlanUnit0PacketRbitPackets OBJECT-TYPE
	SYNTAX  Counter32
	MAX-ACCESS read-only
	STATUS  current
	DESCRIPTION
		"number of packet-protocol packets received with R bit set."
	::= { cesOverWlanUnit0PacketEntry 11 }


cesOverWlanUnit0PacketLbitPackets OBJECT-TYPE
	SYNTAX  Counter32
	MAX-ACCESS read-only
	STATUS  current
	DESCRIPTION
		"number of packet-protocol packets received with L bit set."
	::= { cesOverWlanUnit0PacketEntry 12 }


cesOverWlanUnit0PacketLatePackets OBJECT-TYPE
	SYNTAX  Counter32
	MAX-ACCESS read-only
	STATUS  current
	DESCRIPTION
		"number of packet-protocol packets received too late."
	::= { cesOverWlanUnit0PacketEntry 13 }


cesOverWlanUnit0PacketLostPackets OBJECT-TYPE
	SYNTAX  Counter32
	MAX-ACCESS read-only
	STATUS  current
	DESCRIPTION
		"number of packet-protocol packets what was lost."
	::= { cesOverWlanUnit0PacketEntry 14 }


cesOverWlanUnit0PacketOutOfOrderPackets OBJECT-TYPE
	SYNTAX  Counter32
	MAX-ACCESS read-only
	STATUS  current
	DESCRIPTION
		"number of packet-protocol packets received out of order."
	::= { cesOverWlanUnit0PacketEntry 15 }


cesOverWlanUnit0PacketUnderrunPackets OBJECT-TYPE
	SYNTAX  Counter32
	MAX-ACCESS read-only
	STATUS  current
	DESCRIPTION
		"number of times no packet was available while jitter buffer empty."
	::= { cesOverWlanUnit0PacketEntry 16 }


cesOverWlanUnit0PacketOverrunPackets OBJECT-TYPE
	SYNTAX  Counter32
	MAX-ACCESS read-only
	STATUS  current
	DESCRIPTION
		"number of times no packet received while jitter buffer full."
	::= { cesOverWlanUnit0PacketEntry 17 }


cesOverWlanUnit0PacketInvalidSequencePackets OBJECT-TYPE
	SYNTAX  Counter32
	MAX-ACCESS read-only
	STATUS  current
	DESCRIPTION
		"number of packet-protocol packets received with invalid sequence number."
	::= { cesOverWlanUnit0PacketEntry 18 }


cesOverWlanUnit0PacketDuplicatePackets OBJECT-TYPE
	SYNTAX  Counter32
	MAX-ACCESS read-only
	STATUS  current
	DESCRIPTION
		"number of duplicate packet-protocol packets received."
	::= { cesOverWlanUnit0PacketEntry 19 }


cesOverWlanUnit0PacketMalformedPackets OBJECT-TYPE
	SYNTAX  Counter32
	MAX-ACCESS read-only
	STATUS  current
	DESCRIPTION
		"number of malformed packet-protocol packets received."
	::= { cesOverWlanUnit0PacketEntry 20 }


cesOverWlanUnit0PacketJitterBufferStatus OBJECT-TYPE
	SYNTAX  INTEGER {
			unknown(0),
			undeflow(1),
			overflow(2),
			normal(3) }
	MAX-ACCESS read-only
	STATUS  current
	DESCRIPTION
		"Status of jitter buffer, available only within cesOverWlanUnit0PacketJitterStatusChange trap."
	::= { cesOverWlanUnit0PacketEntry 21 }


cesOverWlanUnit0PacketJitterBufferStatusLastChange OBJECT-TYPE
	SYNTAX  TimeStamp
	MAX-ACCESS read-only
	STATUS  current
	DESCRIPTION
		"The value of MIB II's sysUpTime object at the
		time jitter buffer entered its current status state.
		If the current state was entered prior to
		the last re-initialization of the proxy-agent,
		then this object contains a zero value."
	::= { cesOverWlanUnit0PacketEntry 22 }


cesOverWlanUnit0PacketTrapsPrefix OBJECT IDENTIFIER 	::= { cesOverWlanUnit0Packet 2 }

-- PACKET TRAPS

cesOverWlanUnit0PacketTraps OBJECT IDENTIFIER 	::= { cesOverWlanUnit0PacketTrapsPrefix 0 }

cesOverWlanUnit0PacketMIBConformance OBJECT IDENTIFIER 	::= { cesOverWlanUnit0Packet 4 }


cesOverWlanUnit0PacketJitterStatusChange NOTIFICATION-TYPE
	OBJECTS {
		cesOverWlanUnit0PacketJitterBufferStatus,
		cesOverWlanUnit0PacketJitterBufferStatusLastChange}
	STATUS  current
	DESCRIPTION
		"A cesOverWlanUnit0PacketJitterStatusChange trap is sent when
		status of jitter buffer changes."
	::= { cesOverWlanUnit0PacketTraps 1 }

cesOverWlanUnit0PacketGroup OBJECT-GROUP
	OBJECTS {
		cesOverWlanUnit0PacketPortNumber,
		cesOverWlanUnit0PacketTxState,
		cesOverWlanUnit0PacketRxState,
		cesOverWlanUnit0PacketTxRestarts,
		cesOverWlanUnit0PacketRxRestarts,
		cesOverWlanUnit0PacketJitterCur,
		cesOverWlanUnit0PacketJitterMin,
		cesOverWlanUnit0PacketJitterMax,
		cesOverWlanUnit0PacketTotalInPackets,
		cesOverWlanUnit0PacketValidPackets,
		cesOverWlanUnit0PacketRbitPackets,
		cesOverWlanUnit0PacketLbitPackets,
		cesOverWlanUnit0PacketLatePackets,
		cesOverWlanUnit0PacketLostPackets,
		cesOverWlanUnit0PacketOutOfOrderPackets,
		cesOverWlanUnit0PacketUnderrunPackets,
		cesOverWlanUnit0PacketOverrunPackets,
		cesOverWlanUnit0PacketInvalidSequencePackets,
		cesOverWlanUnit0PacketDuplicatePackets,
		cesOverWlanUnit0PacketMalformedPackets,
		cesOverWlanUnit0PacketJitterBufferStatus,
		cesOverWlanUnit0PacketJitterBufferStatusLastChange }
	STATUS  current
	DESCRIPTION
		""
	::= { cesOverWlanUnit0PacketMIBConformance 2 }

cesOverWlanUnit0PacketNotifications NOTIFICATION-GROUP
	NOTIFICATIONS {
		cesOverWlanUnit0PacketJitterStatusChange }
	STATUS  current
	DESCRIPTION
		""
	::= { cesOverWlanUnit0PacketMIBConformance 1 }

END

INFINET-EXTDEVICES-MIB DEFINITIONS ::= BEGIN

IMPORTS
	infinet
		FROM INFINET-MIB
	MODULE-IDENTITY
		FROM SNMPv2-SMI;

externalDevices MODULE-IDENTITY
	LAST-UPDATED "200706181910Z"
	ORGANIZATION "Infinet Wireless Ltd."
	CONTACT-INFO
		"Dmitry Petukhov

		Postal: Infinet Wireless Ltd,
		        Russia, Ekaterinburg,
		        Serafimi Deryabinoi st, 24

		Phone:  +7 343 217 9317
		Email:  d.petukhov@infinetwireless.com"
	DESCRIPTION
		"The mib module, containing various WanFlex options."
	REVISION "200408161910Z"
	DESCRIPTION
		"The mib module, containing infinet MIB OIDs for external devices branch."
	::= { infinet 2 }


END

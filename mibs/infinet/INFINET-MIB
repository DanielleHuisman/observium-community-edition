INFINET-MIB DEFINITIONS ::= BEGIN

IMPORTS
	enterprises
		FROM RFC1155-SMI
	MODULE-IDENTITY
		FROM SNMPv2-SMI;

infinet MODULE-IDENTITY
	LAST-UPDATED "200711081104Z"
	ORGANIZATION "Infinet Wireless Ltd."
	CONTACT-INFO
		"Andrew Nesheret

		Postal: Infinet Wireless Ltd,
		        Russia, Ekaterinburg,
		        Serafimi Deryabinoi st, 24

		Phone:  +7 343 253 1533
		Email:  A.Nesheret@infinetwireless.com"
	DESCRIPTION
		"The mib module containing infinet mib oids."
	REVISION "200711081104Z"
	DESCRIPTION
		"Contact changed"
	REVISION "200408161910Z"
	DESCRIPTION
		"First revision"
	::= { enterprises 3942 }


-- Infinet wireless router

iwrouter OBJECT IDENTIFIER 	::= { infinet 1 }

-- Wanflex OS for Infinet wireless router

wanflex OBJECT IDENTIFIER 	::= { iwrouter 1 }

END

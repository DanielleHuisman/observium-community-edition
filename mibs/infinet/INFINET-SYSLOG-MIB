INFINET-SYSLOG-MIB DEFINITIONS ::= BEGIN

IMPORTS
	wanflex
		FROM INFINET-MIB
        sysSerialNumber,
        sysTrapSequence
                FROM AQUASYSTEM-MIB
	DisplayString,
	DateAndTime,
	TEXTUAL-CONVENTION
		FROM SNMPv2-TC
	MODULE-IDENTITY,
	OBJECT-TYPE,
	NOTIFICATION-TYPE,
	Counter32,
	IpAddress
		FROM SNMPv2-SMI
	OBJECT-GROUP,
	NOTIFICATION-GROUP
		FROM SNMPv2-CONF;

infinetSyslogMIB MODULE-IDENTITY
	LAST-UPDATED "200802071136Z"
	ORGANIZATION "Infinet Wireless Ltd."
	CONTACT-INFO
		"Andrew Nesheret
		Postal: Infinet Wireless Ltd,
		        Russia, Ekaterinburg,
		        Serafimi Deryabinoi st, 24

		Phone:  +7 343 253 1533
		Email:  A.Nesheret@infinetwireless.com"
	DESCRIPTION
		"The module contains objects and notifications
		associated with WANFlex system journal."
	REVISION "200802071136Z"
	DESCRIPTION
		"Initial version."
	::= { wanflex 6 }


InfinetSyslogFacility ::= TEXTUAL-CONVENTION
	STATUS  current
	DESCRIPTION
		"The facility source of syslog message."
	REFERENCE
		"RFC 3164, Section 4.1 - syslog Message Parts"
	SYNTAX INTEGER {
			kernel(0),         	-- kernel messages
			user(1),           	-- random user-level messages
			mail(2),           	-- mail system
			daemon(3),         	-- system daemons
			authentication(4), 	-- security/authorization messages
			syslog(5),         	-- messages generated internally by syslogd
			lpr(6),            	-- line printer subsystem
			news(7),           	-- network news subsystem
			uucp(8),           	-- UUCP subsystem
			cron(9),           	-- clock daemon
			authpriv(10),      	-- security/authorization messages (private)
			ftp(11),           	-- ftp daemon
			ntp(12),           	-- NTP subsystem
			security(13),      	-- security subsystems (firewalling, etc.)
			console(14),       	-- /dev/console output
			local0(16),        	-- reserved for local use
			local1(17),        	-- reserved for local use
			local2(18),        	-- reserved for local use
			local3(19),        	-- reserved for local use
			local4(20),        	-- reserved for local use
			local5(21),        	-- reserved for local use
			local6(22),        	-- reserved for local use
			local7(23)        	-- reserved for local use
			}


InfinetSyslogSeverity ::= TEXTUAL-CONVENTION
	STATUS  current
	DESCRIPTION
		"The severity of a syslog message.
			'emergency' : system is unusable
			'alert'     : action must be taken immediately
			'critical'  : critical conditions
			'error'     : error conditions
			'warning'   : warning conditions
			'notice'    : normal but significant condition
			'informational': informational messages
			'debug'        : debug-level messages."
	REFERENCE
		"RFC 3164, Section 4.1 - syslog Message Parts"
	SYNTAX INTEGER {
			emergency(0), 	-- system is unusable
			alert(1),     	-- action must be taken immediately
			critical(2),  	-- critical conditions
			error(3),     	-- error conditions
			warning(4),   	-- warning conditions
			notice(5),    	-- normal but significant condition
			info(6),      	-- informational messages
			debug(7)     	-- debug-level messages
			}


-- Scalars and Tables
--

infinetSyslogObjects OBJECT IDENTIFIER 	::= { infinetSyslogMIB 1 }

infinetSyslogServerAddress OBJECT-TYPE
	SYNTAX  IpAddress
	MAX-ACCESS read-write
	STATUS  current
	DESCRIPTION
		"The Internet address of syslog server."
	::= { infinetSyslogObjects 1 }


infinetSyslogMessagesTable OBJECT-TYPE
	SYNTAX  SEQUENCE OF InfinetSyslogMessageEntry
	MAX-ACCESS not-accessible
	STATUS  current
	DESCRIPTION
		"A table of syslog messages generated by this device."
	::= { infinetSyslogObjects 2 }


infinetSyslogMessageEntry OBJECT-TYPE
	SYNTAX  InfinetSyslogMessageEntry
	MAX-ACCESS not-accessible
	STATUS  current
	DESCRIPTION
		"A message generated by device, each entry indexed by message index."
	INDEX {
		infinetSyslogMessageIndex }
	::= { infinetSyslogMessagesTable 1 }


InfinetSyslogMessageEntry ::= SEQUENCE {

	infinetSyslogMessageIndex     Counter32,
	infinetSyslogMessageSeverity  InfinetSyslogSeverity,
	infinetSyslogMessageFacility  InfinetSyslogFacility,
	infinetSyslogMessageTimestamp DateAndTime,
	infinetSyslogMessageIdentity  DisplayString,
	infinetSyslogMessageText      DisplayString }


infinetSyslogMessageIndex OBJECT-TYPE
	SYNTAX  Counter32
	MAX-ACCESS read-only
	STATUS  current
	DESCRIPTION
		"A monotonically increasing integer for the sole
		purpose of indexing messages.  When it reaches the
		maximum value the agent flushes the table and wraps
		the value back to 0."
	::= { infinetSyslogMessageEntry 1 }


infinetSyslogMessageSeverity OBJECT-TYPE
	SYNTAX  InfinetSyslogSeverity
	MAX-ACCESS read-only
	STATUS  current
	DESCRIPTION
		"The Severity of the message."
	::= { infinetSyslogMessageEntry 2 }


infinetSyslogMessageFacility OBJECT-TYPE
	SYNTAX  InfinetSyslogFacility
	MAX-ACCESS read-only
	STATUS  current
	DESCRIPTION
		"Source of the message from."
	::= { infinetSyslogMessageEntry 3 }


infinetSyslogMessageTimestamp OBJECT-TYPE
	SYNTAX  DateAndTime
	MAX-ACCESS read-only
	STATUS  current
	DESCRIPTION
		"The message timestamp."
	::= { infinetSyslogMessageEntry 4 }


infinetSyslogMessageIdentity OBJECT-TYPE
	SYNTAX  DisplayString
	MAX-ACCESS read-only
	STATUS  current
	DESCRIPTION
		"The name of Process or Facility."
	::= { infinetSyslogMessageEntry 5 }


infinetSyslogMessageText OBJECT-TYPE
	SYNTAX  DisplayString (SIZE (0..1024))
	MAX-ACCESS read-only
	STATUS  current
	DESCRIPTION
		"The text of the Message."
	::= { infinetSyslogMessageEntry 6 }


-- Notification Types
--

infinetSyslogEventsPrefix OBJECT IDENTIFIER 	::= { infinetSyslogMIB 2 }

infinetSyslogEvents OBJECT IDENTIFIER 	::= { infinetSyslogEventsPrefix 0 }

-- Conformance
--

infinetSyslogConf OBJECT IDENTIFIER 	::= { infinetSyslogMIB 3 }

-- Groups
--

infinetSyslogGroups OBJECT IDENTIFIER 	::= { infinetSyslogConf 1 }

-- Compliance
--

infinetSyslogCompls OBJECT IDENTIFIER 	::= { infinetSyslogConf 2 }


infinetSyslogMessageGenerated NOTIFICATION-TYPE
	OBJECTS {
                sysSerialNumber,
                sysTrapSequence,
		infinetSyslogMessageIndex,
		infinetSyslogMessageSeverity,
		infinetSyslogMessageFacility,
		infinetSyslogMessageTimestamp,
		infinetSyslogMessageIdentity,
		infinetSyslogMessageText}
	STATUS  current
	DESCRIPTION
		"When a syslog message is generated by the device a
		infinetSyslogMessageGenerated notification is sent."
	::= { infinetSyslogEvents 1 }

infinetSyslogBasicGroup OBJECT-GROUP
	OBJECTS {
		infinetSyslogServerAddress,
		infinetSyslogMessageIndex,
		infinetSyslogMessageSeverity,
		infinetSyslogMessageText,
		infinetSyslogMessageFacility,
		infinetSyslogMessageTimestamp,
		infinetSyslogMessageIdentity }
	STATUS  current
	DESCRIPTION
		"Basic objects."
	::= { infinetSyslogGroups 1 }

infinetSyslogBasicEvents NOTIFICATION-GROUP
	NOTIFICATIONS {
		infinetSyslogMessageGenerated }
	STATUS  current
	DESCRIPTION
		"Basic notifications."
	::= { infinetSyslogGroups 2 }

END

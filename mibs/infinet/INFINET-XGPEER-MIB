INFINET-XGPEER-MIB DEFINITIONS ::= BEGIN

IMPORTS
        xg
                FROM INFINET-XG-MIB
        DisplayString,
        MacAddress
                FROM SNMPv2-TC
        MODULE-IDENTITY,
        OBJECT-TYPE,
        Counter32,
        Integer32,
        IpAddress
                FROM SNMPv2-SMI
        OBJECT-GROUP,
        MODULE-COMPLIANCE
                FROM SNMPv2-CONF;

xgPeer  MODULE-IDENTITY
        LAST-UPDATED "201510080835Z"
        ORGANIZATION "Infinet Wireless Ltd."
        CONTACT-INFO
                "Anthony Berzin

                Postal: Infinet Wireless Ltd.,
                        Russia, Ekaterinburg,
                        Serafimi Deryabinoi st, 24

                Phone:  +7 343 253 1533
                Email:  aberzin@infinetwireless.com"
        DESCRIPTION
                "The mib module, containing XG peer data."
        REVISION "201510080835Z"
        DESCRIPTION
                "First revision."
       ::= { xg 2 }


xgPeerSerialNumber OBJECT-TYPE
    SYNTAX  Integer32
    MAX-ACCESS read-only
    STATUS  current
    DESCRIPTION
        "Peer device's serial number."
    ::= { xgPeer 1 }


xgPeerSysName OBJECT-TYPE
    SYNTAX  DisplayString
    MAX-ACCESS read-only
    STATUS  current
    DESCRIPTION
        "Peer device's sysName."
    ::= { xgPeer 2 }


xgPeerIpAddrTable OBJECT-TYPE
    SYNTAX  SEQUENCE OF XgPeerIpAddrEntry
    MAX-ACCESS not-accessible
    STATUS  current
    DESCRIPTION
        "The table of peer's IP addresses."
    ::= { xgPeer 3 }

xgPeerIpAddrEntry OBJECT-TYPE
    SYNTAX  XgPeerIpAddrEntry
    MAX-ACCESS not-accessible
    STATUS  current
    DESCRIPTION
        "The addressing information for one of
        peer's IP addresses."
    INDEX   { xgPeerIpAddress }
    ::= { xgPeerIpAddrTable 1 }

XgPeerIpAddrEntry ::=
    SEQUENCE {
        xgPeerIpAddress
            IpAddress
    }

xgPeerIpAddress OBJECT-TYPE
    SYNTAX  IpAddress
    MAX-ACCESS  read-only
    STATUS  current
    DESCRIPTION
        "IP address of peer"
    ::= { xgPeerIpAddrEntry 1 }


xgPeerMIBConformance OBJECT IDENTIFIER         ::= { xgPeer 10 }

xgPeerMIBCompliances OBJECT IDENTIFIER         ::= { xgPeerMIBConformance 1 }

xgPeerMIBGroups OBJECT IDENTIFIER       ::= { xgPeerMIBConformance 2 }


-- compliance statements

xgPeerMIBCompliance MODULE-COMPLIANCE
        STATUS  current
        DESCRIPTION
                "The compliance statement for Infinet XG peer."

        MODULE
        MANDATORY-GROUPS {
                        xgPeerGroup }

        ::= { xgPeerMIBCompliances 1 }

-- units of conformance

xgPeerGroup OBJECT-GROUP
        OBJECTS {
                xgPeerSerialNumber,
                xgPeerSysName,
                xgPeerIpAddress }
        STATUS  current
        DESCRIPTION
                "The xgPeer group of objects provided
                for observation and manipulation with
                XG peer parameters."
        ::= { xgPeerMIBGroups 1 }

END

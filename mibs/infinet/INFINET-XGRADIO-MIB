INFINET-XGRADIO-MIB DEFINITIONS ::= BEGIN

IMPORTS
        xg
                FROM INFINET-XG-MIB
        DisplayString
                FROM SNMPv2-TC
        MODULE-IDENTITY,
        OBJECT-TYPE,
        Counter32,
        Integer32
                FROM SNMPv2-SMI
        OBJECT-GROUP,
        MODULE-COMPLIANCE
                FROM SNMPv2-CONF;

xgRadio MODULE-IDENTITY
        LAST-UPDATED "201705240413Z"
        ORGANIZATION "Infinet Wireless Ltd."
        CONTACT-INFO
                "Anthony Berzin

                Postal: Infinet Wireless Ltd.,
                        Russia, Ekaterinburg,
                        Serafimi Deryabinoi st, 24

                Phone:  +7 343 253 1533
                Email:  aberzin@infinetwireless.com"
        DESCRIPTION
                "The mib module, containing XG radio options."
        REVISION "201705240413Z"
        DESCRIPTION
                "Added value 'phy' to xgLinkStatus."
        REVISION "201703231139Z"
        DESCRIPTION
                "xgRfTxFrequency, xgRfRxFrequency,
                xgRfDfsStatus, xgRfAccFER added
                to xgRfCarrierStatTable.
                xgDlQuota is deprecated."
        REVISION "201511021129Z"
        DESCRIPTION
                "xgTotalTxOctets and xgTotalRxOctets
                added to xgRfStat subtree;
                fixed some typos."
        REVISION "201510131101Z"
        DESCRIPTION
                "xgOwnRadioIfIndex added to xgRfCfg subtree."
        REVISION "201410280550Z"
        DESCRIPTION
                "xgRfGoodRxFrames and xgRfBadRxFrames
                added to xgRfCarrierStatTable."
        REVISION "201409300350Z"
        DESCRIPTION
                "xgADCRSSI renamed to xgABSRSSI."
        REVISION "201409290645Z"
        DESCRIPTION
                "xgRSSI renamed to xgADCRSSI."
        REVISION "201409040502Z"
        DESCRIPTION
                "xgTotalDlCapacity and xgTotalUlCapacity
                units changed from Mbps to Kbps."
        REVISION "201409031048Z"
        DESCRIPTION
                "xgTxPwrActual moved from xgRfCarrierStatTable
                to xgRfChainStatTable."
        REVISION "201408290240Z"
        DESCRIPTION
                "The mib module, containing XG radio options."
       ::= { xg 1 }


xgRfCfg OBJECT IDENTIFIER       ::= { xgRadio 1 }


xgUnitType OBJECT-TYPE
        SYNTAX  INTEGER {
                        master(0),
                        slave(1) }
        MAX-ACCESS read-write
        STATUS  current
        DESCRIPTION
                "This value indicates XG unit role in radio link."
        ::= { xgRfCfg 1 }


xgCellId OBJECT-TYPE
        SYNTAX  Integer32 (0..167)
        MAX-ACCESS read-write
        STATUS  current
        DESCRIPTION
                "This value indicates cell id."
        ::= { xgRfCfg 2 }


xgQosStrategy OBJECT-TYPE
        SYNTAX  INTEGER {
                        normal(0),
                        conservative(1),
                        aggressive(2),
                        off(3) }
        MAX-ACCESS read-write
        STATUS  current
        DESCRIPTION
                "This value indicates QoS strategy."
        ::= { xgRfCfg 3 }


xgDlQuota OBJECT-TYPE
        SYNTAX  Integer32 (1..99)
        MAX-ACCESS read-write
        STATUS  deprecated
        DESCRIPTION
                "Desirable ratio of downlink traffic
                related to all traffic in percents."
        ::= { xgRfCfg 4 }


xgFrameLength OBJECT-TYPE
        SYNTAX  INTEGER {
                        len-1-ms(1),
                        len-2-ms(2),
                        len-4-ms(4),
                        len-5-ms(5),
                        len-8-ms(8),
                        len-10-ms(10) }
        MAX-ACCESS read-write
        STATUS  current
        DESCRIPTION
                "Radio frame length in milliseconds."
        ::= { xgRfCfg 5 }


xgMaxDistance OBJECT-TYPE
        SYNTAX  Integer32 (0..59600)
        MAX-ACCESS read-write
        STATUS  current
        DESCRIPTION
                "This value indicates maximum allowed
                length of radio link in meters for
                auto-ranging algorithm."
        ::= { xgRfCfg 6 }


xgChannelWidth OBJECT-TYPE
        SYNTAX  INTEGER {
                        band-10-mhz(10),
                        band-20-mhz(20),
                        band-40-mhz(40) }
        MAX-ACCESS read-only
        STATUS  current
        DESCRIPTION
                "Selected radio channel
                width in MHz."
        ::= { xgRfCfg 7 }




xgCarrierCfgTable OBJECT-TYPE
        SYNTAX  SEQUENCE OF XgCarrierCfgEntry
        MAX-ACCESS not-accessible
        STATUS  current
        DESCRIPTION
                "A table of radio
                configuration options
                by carrier index."
        ::= { xgRfCfg 8 }

xgCarrierCfgEntry OBJECT-TYPE
        SYNTAX  XgCarrierCfgEntry
        MAX-ACCESS not-accessible
        STATUS  current
        DESCRIPTION
                "Each entry contains
                configuration options
                for separate radio carrier."
        INDEX {
                xgCCIndex }
        ::= { xgCarrierCfgTable 1 }

XgCarrierCfgEntry ::= SEQUENCE {
        xgCCIndex Integer32,
        xgCcMaxTxPwr Integer32,
        xgCcFreqDl Integer32,
        xgCcFreqUl Integer32,
        xgCcAmcMode INTEGER,
        xgCcAmcStrategy INTEGER }

xgCCIndex OBJECT-TYPE
        SYNTAX  Integer32 (1..2)
        MAX-ACCESS read-only
        STATUS  current
        DESCRIPTION
                "Radio carrier index,
                ranging from 1 to maximum
                carrier number used."
        ::= { xgCarrierCfgEntry 1 }

xgCcMaxTxPwr OBJECT-TYPE
        SYNTAX  Integer32 (0..27000)
        MAX-ACCESS read-write
        STATUS  current
        DESCRIPTION
                "Maximum allowed TX power
                in thousandths of dB,
                stepping by 250."
        ::= { xgCarrierCfgEntry 2 }

xgCcFreqDl OBJECT-TYPE
        SYNTAX  Integer32
        MAX-ACCESS read-write
        STATUS  current
        DESCRIPTION
                "Radio carrier frequency in MHz
                for downlink traffic."
        ::= { xgCarrierCfgEntry 3 }

xgCcFreqUl OBJECT-TYPE
        SYNTAX  Integer32
        MAX-ACCESS read-write
        STATUS  current
        DESCRIPTION
                "Radio carrier frequency in MHz
                for uplink traffic."
        ::= { xgCarrierCfgEntry 4 }

xgCcAmcMode OBJECT-TYPE
        SYNTAX  INTEGER {
                        auto(0),
                        manual(1) }
        MAX-ACCESS read-write
        STATUS  current
        DESCRIPTION
                "If auto, then TX MCS is set
                 to be upper value that is
                 chosen by adaptive algorithm.
                 If manual, then TX MCS is set
                 to be equal to that value."
        ::= { xgCarrierCfgEntry 5 }

xgCcAmcStrategy OBJECT-TYPE
        SYNTAX  INTEGER {
                        normal(0),
                        conservative(1),
                        agressive(2) }
        MAX-ACCESS read-write
        STATUS  current
        DESCRIPTION
                "Instructs MCS adaptive algorithm
                to prefer maximum radio bandwidth
                over radio transport block error
                rate or vice versa."
        ::= { xgCarrierCfgEntry 6 }


xgOwnRadioIfIndex OBJECT-TYPE
        SYNTAX  Integer32 (0..2147483647)
        MAX-ACCESS read-only
        STATUS  current
        DESCRIPTION
                "XG Radio Interface index. The interface identified by
                a particular value of this index is the same interface as
                identified by the same value of RFC 1573's ifIndex."
        ::= { xgRfCfg 9 }




xgRfStat OBJECT IDENTIFIER      ::= { xgRadio 2 }


xgLinkStatus OBJECT-TYPE
        SYNTAX  INTEGER {
                        stopped(0),
                        starting(1),
                        down(2),
                        up(3),
                        error(4),
                        phy(5) }
        MAX-ACCESS read-only
        STATUS  current
        DESCRIPTION
                "XG radio link status."
        ::= { xgRfStat 1 }

xgDistance OBJECT-TYPE
        SYNTAX  Integer32
        MAX-ACCESS read-only
        STATUS  current
        DESCRIPTION
                "Estimated length of
                radio link in meters."
        ::= { xgRfStat 2 }

xgDlQuotaActual OBJECT-TYPE
        SYNTAX  Integer32 (1..99)
        MAX-ACCESS read-only
        STATUS  current
        DESCRIPTION
                "Estimated portion of allowed downlink
                traffic related to all traffic in percents."
        ::= { xgRfStat 3 }

xgTotalTxAirFrames OBJECT-TYPE
        SYNTAX  Counter32
        MAX-ACCESS read-only
        STATUS  current
        DESCRIPTION
                "Amount of transmitted radio frames."
        ::= { xgRfStat 4 }

xgTotalTxPackets OBJECT-TYPE
        SYNTAX  Counter32
        MAX-ACCESS read-only
        STATUS  current
        DESCRIPTION
                "Amount of Ethernet packets
                transmitted via radio interface."
        ::= { xgRfStat 5 }

xgTotalRxAirFrames OBJECT-TYPE
        SYNTAX  Counter32
        MAX-ACCESS read-only
        STATUS  current
        DESCRIPTION
                "Amount of received radio frames."
        ::= { xgRfStat 6 }

xgTotalRxPackets OBJECT-TYPE
        SYNTAX  Counter32
        MAX-ACCESS read-only
        STATUS  current
        DESCRIPTION
                "Amount of Ethernet packets
                received from radio interface."
        ::= { xgRfStat 7 }

xgTotalRxOkABs OBJECT-TYPE
        SYNTAX  Counter32
        MAX-ACCESS read-only
        STATUS  current
        DESCRIPTION
                "Amount of received valid air blocks."
        ::= { xgRfStat 8 }

xgTotalRxErrorABs OBJECT-TYPE
        SYNTAX  Counter32
        MAX-ACCESS read-only
        STATUS  current
        DESCRIPTION
                "Amount of received invalid air blocks."
        ::= { xgRfStat 9 }

xgTotalDlCapacity OBJECT-TYPE
        SYNTAX  Integer32
        MAX-ACCESS read-only
        STATUS  current
        DESCRIPTION
                "Estimated capacity for
                downlink traffic in Kbps."
        ::= { xgRfStat 10 }

xgTotalUlCapacity OBJECT-TYPE
        SYNTAX  Integer32
        MAX-ACCESS read-only
        STATUS  current
        DESCRIPTION
                "Estimated capacity for
                uplink traffic in Kbps."
        ::= { xgRfStat 11 }


xgRfCarrierStatTable OBJECT-TYPE
        SYNTAX  SEQUENCE OF XgRfCarrierStatEntry
        MAX-ACCESS not-accessible
        STATUS  current
        DESCRIPTION
                "A table of radio data
                by carrier index."
        ::= { xgRfStat 12 }

xgRfCarrierStatEntry OBJECT-TYPE
        SYNTAX  XgRfCarrierStatEntry
        MAX-ACCESS not-accessible
        STATUS  current
        DESCRIPTION
                "Each entry contains
                carrier-specific data
                by carrier index."
        INDEX {
                xgRfCarrierIndex }
        ::= { xgRfCarrierStatTable 1 }

XgRfCarrierStatEntry ::= SEQUENCE {
        xgRfCarrierIndex Integer32,
        xgRfGoodRxFrames Counter32,
        xgRfBadRxFrames Counter32,
        xgRfTxFrequency Integer32,
        xgRfRxFrequency Integer32,
        xgRfDfsStatus INTEGER,
        xgRfRxAccFER Integer32 }

xgRfCarrierIndex OBJECT-TYPE
        SYNTAX  Integer32 (1..2)
        MAX-ACCESS read-only
        STATUS  current
        DESCRIPTION
                "Radio carrier index,
                ranging from 1 to maximum
                carrier number used."
        ::= { xgRfCarrierStatEntry 1 }

xgRfGoodRxFrames OBJECT-TYPE
        SYNTAX  Counter32
        MAX-ACCESS read-only
        STATUS  current
        DESCRIPTION
                "Good Rx Frames counter."
        ::= { xgRfCarrierStatEntry 2 }

xgRfBadRxFrames OBJECT-TYPE
        SYNTAX  Counter32
        MAX-ACCESS read-only
        STATUS  current
        DESCRIPTION
                "Bad Rx Frames counter."
        ::= { xgRfCarrierStatEntry 3 }

xgRfTxFrequency OBJECT-TYPE
        SYNTAX  Integer32
        MAX-ACCESS read-only
        STATUS  current
        DESCRIPTION
                "Tx frequency, MHz"
        ::= { xgRfCarrierStatEntry 4 }

xgRfRxFrequency OBJECT-TYPE
        SYNTAX  Integer32
        MAX-ACCESS read-only
        STATUS  current
        DESCRIPTION
                "Rx frequency, MHz"
        ::= { xgRfCarrierStatEntry 5 }

xgRfDfsStatus OBJECT-TYPE
        SYNTAX  INTEGER {
                dfs-no-init(0),
                dfs-disabled(1),
                dfs-enabled(2),
                dfs-fg-radar-search(3),
                dfs-fg-rssi-scan(4),
                dfs-radar-found(5),
                dfs-bg-rssi-v(6),
                dfs-bg-rssi-h(7),
                dfs-bg-rdrdt-main(8),
                dfs-bg-rdrdt-announce(9),
                dfs-bg-FF-ul(10),
                dfs-bg-FF-dl(11) }
        MAX-ACCESS read-only
        STATUS  current
        DESCRIPTION
                "DFS status:
                dfs-no-init(0),
                dfs-disabled(1),
                dfs-enabled(2),
                dfs-fg-radar-search(3),
                dfs-fg-rssi-scan(4),
                dfs-radar-found(5),
                dfs-bg-rssi-v(6),
                dfs-bg-rssi-h(7),
                dfs-bg-rdrdt-main(8),
                dfs-bg-rdrdt-announce(9),
                dfs-bg-FF-ul(10),
                dfs-bg-FF-dl(11)."
        ::= { xgRfCarrierStatEntry 6 }

xgRfRxAccFER OBJECT-TYPE
        SYNTAX  Integer32
        MAX-ACCESS read-only
        STATUS  current
        DESCRIPTION
                "Rx accumulated bit error rate
                as 100000000 * <absolute ratio>."
        ::= { xgRfCarrierStatEntry 7 }


xgRfChainStatTable OBJECT-TYPE
        SYNTAX  SEQUENCE OF XgRfChainStatEntry
        MAX-ACCESS not-accessible
        STATUS  current
        DESCRIPTION
                "A table of radio statistics
                by carrier and stream index."
        ::= { xgRfStat 13 }

xgRfChainStatEntry OBJECT-TYPE
        SYNTAX  XgRfChainStatEntry
        MAX-ACCESS not-accessible
        STATUS  current
        DESCRIPTION
                "Each entry contains statistics
                by carrier and stream index.
                These indexes coupled together
                give unique index of radio chain."
        INDEX {
                xgRfChainCarrierIndex,
                xgRfChainStreamIndex }
        ::= { xgRfChainStatTable 1 }

XgRfChainStatEntry ::= SEQUENCE {
        xgRfChainCarrierIndex Integer32,
        xgRfChainStreamIndex Integer32,
        xgTxMCS INTEGER,
        xgRxMCS INTEGER,
        xgCINR Integer32,
        xgABSRSSI Integer32,
        xgRxOkABs Counter32,
        xgRxErrorABs Counter32,
        xgTxPwrActual Integer32,
        xgADCRSSI Integer32,
        xgTxGain Integer32,
        xgBerAmcCorrection Integer32,
        xgBerAmcWindowErr Integer32,
        xgBerAmcOneMinuteErr Integer32,
        xgBerAmcTenMinutesErr Integer32,
        xgBerAmcOneHourErr Integer32,
        xgSTOD Integer32 }

xgRfChainCarrierIndex OBJECT-TYPE
        SYNTAX  Integer32 (1..2)
        MAX-ACCESS read-only
        STATUS  current
        DESCRIPTION
                "Radio carrier index,
                ranging from 1 to maximum
                carrier number used."
        ::= { xgRfChainStatEntry 1 }

xgRfChainStreamIndex OBJECT-TYPE
        SYNTAX  Integer32 (1..2)
        MAX-ACCESS read-only
        STATUS  current
        DESCRIPTION
                "Radio stream index,
                ranging from 1 to maximum
                streams per carrier.
                Streams count varies depending
                on anthenna metod used:
                SISO, MIMO, double SISO, etc."
        ::= { xgRfChainStatEntry 2 }

xgTxMCS OBJECT-TYPE
        SYNTAX  INTEGER {
                        qpsk-1-4(1),
                        qpsk-1-2(2),
                        qpsk-3-4(3),
                        qam16-1-2(4),
                        qam16-3-4(5),
                        qam64-4-6(6),
                        qam256-5-8(7),
                        qam256-6-8(8),
                        qam256-7-8(9),
                        qam256-30-32(10),
                        qam1024-8-10(11) }
        MAX-ACCESS read-only
        STATUS  current
        DESCRIPTION
                "Tx modulation index."
        ::= { xgRfChainStatEntry 3 }

xgRxMCS OBJECT-TYPE
        SYNTAX  INTEGER {
                        qpsk-1-4(1),
                        qpsk-1-2(2),
                        qpsk-3-4(3),
                        qam16-1-2(4),
                        qam16-3-4(5),
                        qam64-4-6(6),
                        qam256-5-8(7),
                        qam256-6-8(8),
                        qam256-7-8(9),
                        qam256-30-32(10),
                        qam1024-8-10(11) }
        MAX-ACCESS read-only
        STATUS  current
        DESCRIPTION
                "Rx modulation index."
        ::= { xgRfChainStatEntry 4 }

xgCINR OBJECT-TYPE
        SYNTAX  Integer32
        MAX-ACCESS read-only
        STATUS  current
        DESCRIPTION
                "Carrier to Interference + Noise Ratio"
        ::= { xgRfChainStatEntry 5 }

xgABSRSSI OBJECT-TYPE
        SYNTAX  Integer32
        MAX-ACCESS read-only
        STATUS  current
        DESCRIPTION
                "Absolute Received Signal Strength Indicator"
        ::= { xgRfChainStatEntry 6 }

xgRxOkABs OBJECT-TYPE
        SYNTAX  Counter32
        MAX-ACCESS read-only
        STATUS  current
        DESCRIPTION
                "Valid air block counter"
        ::= { xgRfChainStatEntry 7 }

xgRxErrorABs OBJECT-TYPE
        SYNTAX  Counter32
        MAX-ACCESS read-only
        STATUS  current
        DESCRIPTION
                "Invalid air block counter"
        ::= { xgRfChainStatEntry 8 }

xgTxPwrActual OBJECT-TYPE
        SYNTAX  Integer32 (0..2700)
        MAX-ACCESS read-only
        STATUS  current
        DESCRIPTION
                "Measured TX power
                in hundredths of dB."
        ::= { xgRfChainStatEntry 9 }

xgADCRSSI OBJECT-TYPE
        SYNTAX  Integer32
        MAX-ACCESS read-only
        STATUS  current
        DESCRIPTION
                "RSSI at ADC input per stream in dB"
        ::= { xgRfChainStatEntry 10 }

xgTxGain OBJECT-TYPE
        SYNTAX  Integer32
        MAX-ACCESS read-only
        STATUS  current
        DESCRIPTION
                "TX gain in hundredth of dB,
                stepping by 0.25 dB"
        ::= { xgRfChainStatEntry 11 }

xgBerAmcCorrection OBJECT-TYPE
        SYNTAX  Integer32
        MAX-ACCESS read-only
        STATUS  current
        DESCRIPTION
                "Deliberate CINR addition 
                used to shift MCS selection
                while keeping BER as close
                as possible below allowed level."
        ::= { xgRfChainStatEntry 12 }

xgBerAmcWindowErr OBJECT-TYPE
        SYNTAX  Integer32 (-1..100000000)
        MAX-ACCESS read-only
        STATUS  current
        DESCRIPTION
                "Bit Error rate:
                least detectable value 1 correspomds to 1e-8;
                most possible value 100000000 means 1.0
                special value -1 is used when
                no data for estimation are available"
        ::= { xgRfChainStatEntry 13 }

xgBerAmcOneMinuteErr OBJECT-TYPE
        SYNTAX  Integer32 (-1..100000000)
        MAX-ACCESS read-only
        STATUS  current
        DESCRIPTION
                "BER AMC 1 minute Error:
                least detectable value 1 correspomds to 1e-8;
                most possible value 100000000 means 1.0
                special value -1 is used when
                no data for estimation are available"
        ::= { xgRfChainStatEntry 14 }

xgBerAmcTenMinutesErr OBJECT-TYPE
        SYNTAX  Integer32 (-1..100000000)
        MAX-ACCESS read-only
        STATUS  current
        DESCRIPTION
                "BER AMC 10 minutes Error:
                least detectable value 1 correspomds to 1e-8;
                most possible value 100000000 means 1.0
                special value -1 is used when
                no data for estimation are available"
        ::= { xgRfChainStatEntry 15 }

xgBerAmcOneHourErr OBJECT-TYPE
        SYNTAX  Integer32 (-1..100000000)
        MAX-ACCESS read-only
        STATUS  current
        DESCRIPTION
                "BER AMC 1 hour Error:
                least detectable value 1 correspomds to 1e-8;
                most possible value 100000000 means 1.0
                special value -1 is used when
                no data for estimation are available"
        ::= { xgRfChainStatEntry 16 }

xgSTOD OBJECT-TYPE
        SYNTAX  Integer32
        MAX-ACCESS read-only
        STATUS  current
        DESCRIPTION
                "symbol time offset deviation,
                measured in tenths of sample"
        ::= { xgRfChainStatEntry 17 }


xgCatalinaTemp OBJECT-TYPE
        SYNTAX  Integer32
        MAX-ACCESS read-only
        STATUS  current
        DESCRIPTION
                "Catalina temperature
                in degrees Celsius."
        ::= { xgRfStat 14 }

xgTotalTxOctets OBJECT-TYPE
        SYNTAX  Counter32
        MAX-ACCESS read-only
        STATUS  current
        DESCRIPTION
                "Amount of octets tramsmitted
                via radio interface."
        ::= { xgRfStat 15 }

xgTotalRxOctets OBJECT-TYPE
        SYNTAX  Counter32
        MAX-ACCESS read-only
        STATUS  current
        DESCRIPTION
                "Amount of octets received
                from radio interface."
        ::= { xgRfStat 16 }


xgRadioMIBConformance OBJECT IDENTIFIER         ::= { xgRadio 3 }

xgRadioMIBCompliances OBJECT IDENTIFIER         ::= { xgRadioMIBConformance 1 }

xgRadioMIBGroups OBJECT IDENTIFIER      ::= { xgRadioMIBConformance 2 }


-- compliance statements

xgRadioMIBCompliance MODULE-COMPLIANCE
        STATUS  current
        DESCRIPTION
                "The compliance statement for Infinet XG bridge."

        MODULE
        MANDATORY-GROUPS {
                        xgRadioGroup }

        ::= { xgRadioMIBCompliances 1 }

-- units of conformance

xgRadioGroup OBJECT-GROUP
        OBJECTS {
                xgUnitType,
                xgCellId,
                xgQosStrategy,
                xgDlQuota,
                xgFrameLength,
                xgMaxDistance,
                xgChannelWidth,
                xgCCIndex,
                xgCcMaxTxPwr,
                xgCcFreqDl,
                xgCcFreqUl,
                xgCcAmcMode,
                xgCcAmcStrategy,
                xgOwnRadioIfIndex,
                xgLinkStatus,
                xgDistance,
                xgDlQuotaActual,
                xgTotalTxAirFrames,
                xgTotalTxPackets,
                xgTotalRxAirFrames,
                xgTotalRxPackets,
                xgTotalRxOkABs,
                xgTotalRxErrorABs,
                xgTotalDlCapacity,
                xgTotalUlCapacity,
                xgRfCarrierIndex,
                xgRfGoodRxFrames,
                xgRfBadRxFrames,
                xgRfTxFrequency,
                xgRfRxFrequency,
                xgRfDfsStatus,
                xgRfRxAccFER,
                xgRfChainCarrierIndex,
                xgRfChainStreamIndex,
                xgTxMCS,
                xgRxMCS,
                xgCINR,
                xgABSRSSI,
                xgRxOkABs,
                xgRxErrorABs,
                xgTxPwrActual,
                xgADCRSSI,
				xgTxGain,
				xgBerAmcCorrection,
				xgBerAmcWindowErr,
				xgBerAmcOneMinuteErr,
				xgBerAmcTenMinutesErr,
				xgBerAmcOneHourErr,
				xgSTOD,
				xgCatalinaTemp,
                xgTotalTxOctets,
                xgTotalRxOctets }
        STATUS  current
        DESCRIPTION
                "The xgRadio group of objects provided
                for observation and manipulation with
                XG radio parameters."
        ::= { xgRadioMIBGroups 1 }

END

IPI-ACL-MIB DEFINITIONS ::= BEGIN

IMPORTS
    OBJECT-TYPE, enterprises,
    Counter64, Unsigned32 FROM SNMPv2-SMI
    DisplayString    FROM SNMPv2-TC
    ipi FROM OCNOS-IPI-MODULE-MIB;

ipiACLMib MODULE-IDENTITY
    LAST-UPDATED "201709181200Z"  -- Sep 30, 2017 11:30:00 GMT
    ORGANIZATION "IP Infusion"
    CONTACT-INFO "www.ipinfusion.com"
    DESCRIPTION
       "IPI ACL MIB. "
    ::= { ipi 106 }

ipiAclObjects OBJECT IDENTIFIER ::={ ipiACLMib 1 }

ipiMacACLTable  OBJECT-TYPE
    SYNTAX      SEQUENCE OF IpiMacACLEntry
    MAX-ACCESS  not-accessible
    STATUS      current
    DESCRIPTION
            "A Table object containing MAC ACL information
             given by the ACL number."
    ::= { ipiAclObjects 1 }

ipiMacACLEntry  OBJECT-TYPE
    SYNTAX      IpiMacACLEntry
    MAX-ACCESS  not-accessible
    STATUS      current
    DESCRIPTION
            "A Table object containing MAC ACL information
             given by the ACL number."
    INDEX   { macAclNumber }
    ::= { ipiMacACLTable 1 }

IpiMacACLEntry ::=
    SEQUENCE {
              macAclNumber                 Unsigned32,
              macACLName                   DisplayString,
              macACLFilterCount            Unsigned32,
              macACLDefaultFilterMatchPkts Counter64
             }

macAclNumber  OBJECT-TYPE
    SYNTAX      Unsigned32 (1..4294967295)
    MAX-ACCESS  not-accessible
    STATUS      current
    DESCRIPTION
            "A unique number corresponding to an ACL."
    ::= { ipiMacACLEntry 1 }

macACLName  OBJECT-TYPE
    SYNTAX      DisplayString
    MAX-ACCESS  read-only
    STATUS      current
    DESCRIPTION
            "Name given to the MAC ACL."
    ::= { ipiMacACLEntry 2 }

macACLFilterCount  OBJECT-TYPE
    SYNTAX      Unsigned32
    MAX-ACCESS  read-only
    STATUS      current
    DESCRIPTION
            "The total number of rules in the MAC ACL."
    ::= { ipiMacACLEntry 3 }

macACLDefaultFilterMatchPkts  OBJECT-TYPE
    SYNTAX      Counter64
    MAX-ACCESS  read-only
    STATUS      current
    DESCRIPTION
            "The number of matched packets for the default rule on the MAC ACL."
    ::= { ipiMacACLEntry 4 }

ipiMacACLFilterTable  OBJECT-TYPE
    SYNTAX      SEQUENCE OF IpiMacACLFilterEntry
    MAX-ACCESS  not-accessible
    STATUS      current
    DESCRIPTION
            "A Table object containing MAC ACL information
             given by the ACL number."
    ::= { ipiAclObjects 2 }

ipiMacACLFilterEntry  OBJECT-TYPE
    SYNTAX      IpiMacACLFilterEntry
    MAX-ACCESS  not-accessible
    STATUS      current
    DESCRIPTION
            "A Table object containing MAC ACL information
             given by the ACL number."
    INDEX   { macAclNumber, macAclFilterSequenceNumber }
    ::= { ipiMacACLFilterTable 1 }

IpiMacACLFilterEntry ::=
    SEQUENCE {
               macAclFilterSequenceNumber  Unsigned32,
               macACLFilterMatchPkts       Counter64
             }

macAclFilterSequenceNumber  OBJECT-TYPE
    SYNTAX      Unsigned32 (1..4294967295)
    MAX-ACCESS  not-accessible
    STATUS      current
    DESCRIPTION
            "A unique number corresponding to a rule in mac ACL."
    ::= { ipiMacACLFilterEntry 1 }

macACLFilterMatchPkts  OBJECT-TYPE
    SYNTAX      Counter64
    MAX-ACCESS  read-only
    STATUS      current
    DESCRIPTION
            "The number of matched packets based on the MAC ACL rule."
    ::= { ipiMacACLFilterEntry 2 }


ipiIpACLTable  OBJECT-TYPE
    SYNTAX      SEQUENCE OF IpiIpACLEntry
    MAX-ACCESS  not-accessible
    STATUS      current
    DESCRIPTION
            "A Table object containing IP ACL information
             given by the ACL number."
    ::= { ipiAclObjects 3 }

ipiIpACLEntry  OBJECT-TYPE
    SYNTAX      IpiIpACLEntry
    MAX-ACCESS  not-accessible
    STATUS      current
    DESCRIPTION
            "A Table object containing IP ACL information
             given by the ACL number."
    INDEX   { ipAclNumber }
    ::= { ipiIpACLTable 1 }

IpiIpACLEntry ::=
    SEQUENCE {
              ipAclNumber                  Unsigned32,
              ipACLName                    DisplayString,
              ipACLFilterCount             Unsigned32,
              ipACLDefaultFilterMatchPkts  Counter64
             }

ipAclNumber  OBJECT-TYPE
    SYNTAX      Unsigned32 (1..4294967295)
    MAX-ACCESS  not-accessible
    STATUS      current
    DESCRIPTION
            "A unique number corresponding to an ACL."
    ::= { ipiIpACLEntry 1 }

ipACLName  OBJECT-TYPE
    SYNTAX      DisplayString
    MAX-ACCESS  read-only
    STATUS      current
    DESCRIPTION
            "Name given to the IP ACL."
    ::= { ipiIpACLEntry 2 }

ipACLFilterCount  OBJECT-TYPE
    SYNTAX      Unsigned32
    MAX-ACCESS  read-only
    STATUS      current
    DESCRIPTION
            "The total number of rules in the IP ACL."
    ::= { ipiIpACLEntry 3 }

ipACLDefaultFilterMatchPkts  OBJECT-TYPE
    SYNTAX      Counter64
    MAX-ACCESS  read-only
    STATUS      current
    DESCRIPTION
            "The number of matched packets for the default rule on the IP ACL."
    ::= { ipiIpACLEntry 4 }


ipiIpACLFilterTable  OBJECT-TYPE
    SYNTAX      SEQUENCE OF IpiIpACLFilterEntry
    MAX-ACCESS  not-accessible
    STATUS      current
    DESCRIPTION
            "A Table object containing IP ACL information
             given by the ACL number."
    ::= { ipiAclObjects 4 }

ipiIpACLFilterEntry  OBJECT-TYPE
    SYNTAX      IpiIpACLFilterEntry
    MAX-ACCESS  not-accessible
    STATUS      current
    DESCRIPTION
            "A Table object containing IP ACL information
             given by the ACL number."
    INDEX   { ipAclNumber, ipAclFilterSequenceNumber }
    ::= { ipiIpACLFilterTable 1 }

IpiIpACLFilterEntry ::=
    SEQUENCE {
              ipAclFilterSequenceNumber   Unsigned32,
              ipACLFilterMatchPkts        Counter64
             }

ipAclFilterSequenceNumber  OBJECT-TYPE
    SYNTAX      Unsigned32 (1..4294967295)
    MAX-ACCESS  not-accessible
    STATUS      current
    DESCRIPTION
            "A unique number corresponding to a rule in IP ACL."
    ::= { ipiIpACLFilterEntry 1 }

ipACLFilterMatchPkts  OBJECT-TYPE
    SYNTAX      Counter64
    MAX-ACCESS  read-only
    STATUS      current
    DESCRIPTION
            "The number of matched packets based on the IP ACL rule."
    ::= { ipiIpACLFilterEntry 2 }


ipiIpv6ACLTable  OBJECT-TYPE
    SYNTAX      SEQUENCE OF IpiIpv6ACLEntry
    MAX-ACCESS  not-accessible
    STATUS      current
    DESCRIPTION
            "A Table object containing IPv6 ACL information
             given by the ACL number."
    ::= { ipiAclObjects 5 }

ipiIpv6ACLEntry  OBJECT-TYPE
    SYNTAX      IpiIpv6ACLEntry
    MAX-ACCESS  not-accessible
    STATUS      current
    DESCRIPTION
            "A Table object containing IPv6 ACL information
             given by the ACL number."
    INDEX   { ipv6AclNumber }
    ::= { ipiIpv6ACLTable 1 }

IpiIpv6ACLEntry ::=
    SEQUENCE {
              ipv6AclNumber                  Unsigned32,
              ipv6ACLName                    DisplayString,
              ipv6ACLFilterCount             Unsigned32,
              ipv6ACLDefaultFilterMatchPkts  Counter64
             }

ipv6AclNumber  OBJECT-TYPE
    SYNTAX      Unsigned32 (1..4294967295)
    MAX-ACCESS  not-accessible
    STATUS      current
    DESCRIPTION
            "A unique number corresponding to an ACL."
    ::= { ipiIpv6ACLEntry 1 }

ipv6ACLName  OBJECT-TYPE
    SYNTAX      DisplayString
    MAX-ACCESS  read-only
    STATUS      current
    DESCRIPTION
            "Name given to the IPv6 ACL."
    ::= { ipiIpv6ACLEntry 2 }

ipv6ACLFilterCount  OBJECT-TYPE
    SYNTAX      Unsigned32
    MAX-ACCESS  read-only
    STATUS      current
    DESCRIPTION
            "The total number of rules in the IPv6 ACL rule."
    ::= { ipiIpv6ACLEntry 3 }

ipv6ACLDefaultFilterMatchPkts  OBJECT-TYPE
    SYNTAX      Counter64
    MAX-ACCESS  read-only
    STATUS      current
    DESCRIPTION
            "The number of matched packets for the default rule on the IPv6 ACL."
    ::= { ipiIpv6ACLEntry 4 }


ipiIpv6ACLFilterTable  OBJECT-TYPE
    SYNTAX      SEQUENCE OF IpiIpv6ACLFilterEntry
    MAX-ACCESS  not-accessible
    STATUS      current
    DESCRIPTION
            "A Table object containing IPv6 ACL information
             given by the ACL number."
    ::= { ipiAclObjects 6 }

ipiIpv6ACLFilterEntry  OBJECT-TYPE
    SYNTAX      IpiIpv6ACLFilterEntry
    MAX-ACCESS  not-accessible
    STATUS      current
    DESCRIPTION
            "A Table object containing IPv6 ACL information
             given by the ACL number."
    INDEX   { ipv6AclNumber, ipv6AclFilterSequenceNumber }
    ::= { ipiIpv6ACLFilterTable 1 }

IpiIpv6ACLFilterEntry ::=
    SEQUENCE {
              ipv6AclFilterSequenceNumber   Unsigned32,
              ipv6ACLFilterMatchPkts        Counter64
             }

ipv6AclFilterSequenceNumber  OBJECT-TYPE
    SYNTAX      Unsigned32 (1..4294967295)
    MAX-ACCESS  not-accessible
    STATUS      current
    DESCRIPTION
            "A unique number corresponding to a rule in IPv6 ACL."
    ::= { ipiIpv6ACLFilterEntry 1 }

ipv6ACLFilterMatchPkts  OBJECT-TYPE
    SYNTAX      Counter64
    MAX-ACCESS  read-only
    STATUS      current
    DESCRIPTION
            "The number of matched packets based on the IPv6 ACL rule."
    ::= { ipiIpv6ACLFilterEntry 2 }
END

IPI-HQOS-MIB DEFINITIONS ::= BEGIN

--  This module provides authoritative definitions for hqos statistics modules
--
--  This module will be extended, as needed.
--

IMPORTS
   MODULE-IDENTITY, OBJECT-TYPE,enterprises,
   Gauge32, Counter32, Counter64, Unsigned32
   FROM SNMPv2-SMI
   ifIndex FROM IF-MIB
   ipi FROM OCNOS-IPI-MODULE-MIB;

ipiHqosMib MODULE-IDENTITY
   LAST-UPDATED "201709181200Z"  -- Oct 25, 2017 12:00:00 GMT
   ORGANIZATION "IP Infusion"
   CONTACT-INFO "www.ipinfusion.com"
   DESCRIPTION
   "IPI HQOS CLASS-MAP STATISTICS MIB."
   ::= { ipi 107 }

ipiHqosTable OBJECT IDENTIFIER ::={ ipiHqosMib 1 }

ipiHqosCmapTable OBJECT-TYPE
   SYNTAX       SEQUENCE OF IPIHqosCmapStatsEntry
   MAX-ACCESS   not-accessible
   STATUS       current
   DESCRIPTION
   "A Table containing Hierarchical quality of service information."
   ::= { ipiHqosTable 1 }

ipiHqosCmapEntry OBJECT-TYPE
   SYNTAX       IPIHqosCmapStatsEntry
   MAX-ACCESS   not-accessible
   STATUS       current
   DESCRIPTION
   "A Table object containing information of class-maps attached to interfaces through service policy."
   INDEX   { ifIndex, hqosDirection, hqosCmapId }
   ::= { ipiHqosCmapTable 1 }

IPIHqosCmapEntry::=
  SEQUENCE {
            hqosDirection        Unsigned32,
            hqosCmapId           Unsigned32,
            hqosCmapMatchPkts    Counter64,
            hqosCmapMatchBytes   Counter64,
            hqosCmapDropPkts     Counter64,
            hqosCmapDropBytes    Counter64
           }

hqosDirection OBJECT-TYPE
   SYNTAX       Unsigned32
   MAX-ACCESS   not-accessible
   STATUS       current
   DESCRIPTION
   " The direction in which service policy is attached on the interface. 1 - input, 2 - output"
   ::= { ipiHqosCmapEntry 1 }

hqosCmapId OBJECT-TYPE
   SYNTAX       Unsigned32
   MAX-ACCESS   not-accessible
   STATUS       current
   DESCRIPTION
   "A unique number corresponding to a class-map."
   ::= { ipiHqosCmapEntry 2 }

hqosCmapMatchPkts OBJECT-TYPE
   SYNTAX       Counter64
   MAX-ACCESS   read-only
   STATUS       current
   DESCRIPTION
   " The number of packets that matched the rules of class-map on the attached interface"
   ::= { ipiHqosCmapEntry 3 }

hqosCmapMatchBytes OBJECT-TYPE
   SYNTAX       Counter64
   MAX-ACCESS   read-only
   STATUS       current
   DESCRIPTION
   " The number of bytes that matched the rules of class-map on the attached interface"
   ::= { ipiHqosCmapEntry 4 }

hqosCmapDropPkts OBJECT-TYPE
   SYNTAX       Counter64
   MAX-ACCESS   read-only
   STATUS       current
   DESCRIPTION
   "The number of packets that were dropped on the attached interface due to policer action on the class-map."
   ::= { ipiHqosCmapEntry 5 }

hqosCmapDropBytes OBJECT-TYPE
   SYNTAX       Counter64
   MAX-ACCESS   read-only
   STATUS       current
   DESCRIPTION
   "The number of bytes that were dropped on the attached interface due to policer action on the class-map"
   ::= { ipiHqosCmapEntry 6 }

END

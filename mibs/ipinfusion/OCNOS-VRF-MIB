OCNOS-VRF-MIB DEFINITIONS ::= BEGIN

IMPORTS
      OBJECT-TYPE, MODULE-IDENTITY,
      Gauge32, Counter32, Integer32, Unsigned32,
      IpAddress, Counter64,
      TimeTicks, NOTIFICATION-TYPE
          FROM SNMPv2-SMI
      DateAndTime, DisplayString,
      PhysAddress, RowStatus, TEXTUAL-CONVENTION
          FROM SNMPv2-TC
      MODULE-COMPLIANCE, OBJECT-GROUP, NOTIFICATION-GROUP
          FROM SNMPv2-CONF
      snmpTraps
          FROM SNMPv2-MIB
      enterprises, OBJECT-IDENTITY
          FROM SNMPv2-SMI
      Ipv6Address
          FROM IPV6-TC
      ipi  FROM OCNOS-IPI-MODULE-MIB
        vrVrId
                FROM OCNOS-VR-MIB;

vrf MODULE-IDENTITY
   LAST-UPDATED "201806210000Z"
   ORGANIZATION "IP Infusion Inc."
   CONTACT-INFO 
       "postal: 3965 Freedom Circle, Suite 200, Santa Clara, CA 95054

        email: support@ipinfusion.com

        telephone: +1 408-400-1900
        website: http://www.ipinfusion.com/"
   DESCRIPTION 
      "This MIB module is for managing VPN Routing/Forwarding"

   REVISION      "201806210000Z"
   DESCRIPTION 
      "Initial Version"
   ::= { ipi  3 } 


vrfVrfTable OBJECT-TYPE 
	SYNTAX SEQUENCE OF VrfVrfEntry
	MAX-ACCESS not-accessible
	STATUS current
	DESCRIPTION 
		"This table provides information for vrf"
	::= { vrf 1 }

vrfVrfEntry OBJECT-TYPE
	SYNTAX VrfVrfEntry
	MAX-ACCESS not-accessible
	STATUS current
	DESCRIPTION 
		"An entry containing information for vrf"
	INDEX { vrVrId,vrfVrfName }
	::= { vrfVrfTable 1 }

VrfVrfEntry::= SEQUENCE {
	vrfVrfName OCTET STRING,
	vrfMacVrf INTEGER,
	vrfVrfId Unsigned32,
	vrfFibId Unsigned32,
	vrfDescription OCTET STRING,
	vrfRouterId IpAddress	}

vrfVrfName OBJECT-TYPE
	SYNTAX OCTET STRING 
	MAX-ACCESS read-write
	STATUS current 
	DESCRIPTION 
		""
	::= { vrfVrfEntry 1 }

vrfMacVrf OBJECT-TYPE
	SYNTAX INTEGER { false(0), true(1) } 
	MAX-ACCESS read-write
	STATUS current 
	DESCRIPTION 
		""
	::= { vrfVrfEntry 2 }

vrfVrfId OBJECT-TYPE
	SYNTAX Unsigned32 
	MAX-ACCESS read-only
	STATUS current 
	DESCRIPTION 
		""
	::= { vrfVrfEntry 3 }

vrfFibId OBJECT-TYPE
	SYNTAX Unsigned32 
	MAX-ACCESS read-only
	STATUS current 
	DESCRIPTION 
		""
	::= { vrfVrfEntry 4 }

vrfDescription OBJECT-TYPE
	SYNTAX OCTET STRING 
	MAX-ACCESS read-write
	STATUS current 
	DESCRIPTION 
		""
	::= { vrfVrfEntry 5 }

vrfRouterId OBJECT-TYPE
	SYNTAX IpAddress 
	MAX-ACCESS read-write
	STATUS current 
	DESCRIPTION 
		"vrf router id"
	::= { vrfVrfEntry 6 }


END

ISILON-TRAP-MIB DEFINITIONS ::= BEGIN

IMPORTS
    MODULE-IDENTITY, NOTIFICATION-TYPE, OBJECT-TYPE, Integer32, Counter64
        FROM SNMPv2-SMI
    NOTIFICATION-GROUP, OBJECT-GROUP, MODULE-COMPLIANCE
        FROM SNMPv2-CONF
    isilon
        FROM ISILON-MIB
;

isilonTraps MODULE-IDENTITY
    LAST-UPDATED "201512180000Z"    --18 DEC 2015--
    ORGANIZATION "Isilon Systems LLC"
    CONTACT-INFO
        "Isilon Systems LLC
         Support phone: 1-800.782.4362 
         Support website: http://support.emc.com
        "
    DESCRIPTION
        "Traps for Isilon Systems OneFS operating system."
    REVISION "201504080000Z"    --07 APR 2015--
    DESCRIPTION
        "MIB maintenance, added compliance groups and reorder positions, 
        but not OIDs."
    REVISION "201306210000Z"    --21 JUN 2013--
    DESCRIPTION
        "Traps for Isilon Systems CloudPools."
    REVISION "201303210000Z"    --02 APR 2013--
    DESCRIPTION
        "Added trap for missing required bootdisk mirror failures.
         Added: bootdiskMirrorReqMissingCrit"
    REVISION "201209210000Z"    --21 SEP 2012--
    DESCRIPTION
        "Updated some traps that were wrong.
         Removed: sasPhyErrorWarn, sasPhyErrorCrit
         Added: sasPhyErrorExpanderWarn, sasPhyErrorControllerWarn"
    REVISION "201208010000Z"    --01 AUG 2012--
    DESCRIPTION
        "Add instanceIdentifier to object list for all traps."
    REVISION "201205230000Z"    --23 MAY 2012--
    DESCRIPTION
        "Renamed FlexProtectRunning* objects to be lower case
         per SMI/SNMP standards. Added OBJECTS list to traps.
         Minor cleanup and formatting."
    REVISION "201204300000Z"    --30 APRIL 2012--
    DESCRIPTION
        "Added traps for different priority job failures."
    REVISION "201109290000Z"    --29 SEPTEMBER 2011--
    DESCRIPTION
        "Added storage transport traps."
    REVISION "200911120000Z"    --12 NOVEMBER 2009
    DESCRIPTION
        "Reworked to align with the new event management and notification
         system"
    REVISION "200911100000Z"    --10 NOVEMBER 2009--
    DESCRIPTION
        "Initial revision."
    ::= { isilon 250 }

groupStateTraps OBJECT IDENTIFIER ::= { isilonTraps 10 }
filesystemTraps OBJECT IDENTIFIER ::= { isilonTraps 11 }
smartQuotaTraps OBJECT IDENTIFIER ::= { isilonTraps 12 }
snapshotTraps   OBJECT IDENTIFIER ::= { isilonTraps 13 }
syncIQTraps     OBJECT IDENTIFIER ::= { isilonTraps 14 }
softwareTraps   OBJECT IDENTIFIER ::= { isilonTraps 15 }
avscanTraps     OBJECT IDENTIFIER ::= { isilonTraps 16 }
netProtoTraps   OBJECT IDENTIFIER ::= { isilonTraps 17 }
networkingTraps OBJECT IDENTIFIER ::= { isilonTraps 18 }
hardwareTraps   OBJECT IDENTIFIER ::= { isilonTraps 19 }
systemDiskTraps OBJECT IDENTIFIER ::= { isilonTraps 20 }
sensorTraps     OBJECT IDENTIFIER ::= { isilonTraps 21 }
storageTransportTraps   OBJECT IDENTIFIER ::= { isilonTraps 22 }
cloudPoolsTraps OBJECT IDENTIFIER ::= { isilonTraps 23 }
upgradeTraps    OBJECT IDENTIFIER ::= { isilonTraps 24 }
variables       OBJECT IDENTIFIER ::= { isilonTraps 50 }
trapConformance OBJECT IDENTIFIER ::= { isilonTraps 51 }
trapCompliance  OBJECT IDENTIFIER ::= { isilonTraps 52 }

nodeIdentifier OBJECT-TYPE
    SYNTAX     Integer32
    MAX-ACCESS accessible-for-notify
    STATUS     current
    DESCRIPTION
        "The Logical Node Number of the node referenced in the notification.
        "
    ::= { variables 1 }

measuredValue OBJECT-TYPE
    SYNTAX     Integer32
    MAX-ACCESS accessible-for-notify
    STATUS     current
    DESCRIPTION
        "The measured value that triggered the event
        "
    ::= { variables 2 }

units OBJECT-TYPE
    SYNTAX      OCTET STRING
    MAX-ACCESS accessible-for-notify
    STATUS     current
    DESCRIPTION
        "The units of the measurement
        "
    ::= { variables 3 }

oid OBJECT-TYPE
    SYNTAX      OBJECT IDENTIFIER
    MAX-ACCESS accessible-for-notify
    STATUS     current
    DESCRIPTION
        "The OID of the sensor reporting a problem
        "
    ::= { variables 4 }

bay OBJECT-TYPE
    SYNTAX      Integer32
    MAX-ACCESS accessible-for-notify
    STATUS     current
    DESCRIPTION
        "Drive bay number
        "
    ::= { variables 5 }

ifName OBJECT-TYPE
    SYNTAX      OCTET STRING
    MAX-ACCESS accessible-for-notify
    STATUS     current
    DESCRIPTION
        "Interface name
        "
    ::= { variables 6 }

phy OBJECT-TYPE
    SYNTAX      Integer32
    MAX-ACCESS accessible-for-notify
    STATUS     current
    DESCRIPTION
        "PHY connection
        "
    ::= { variables 7 }

errorMessage OBJECT-TYPE
    SYNTAX      OCTET STRING
    MAX-ACCESS accessible-for-notify
    STATUS     current
    DESCRIPTION
        "Error message
        "
    ::= { variables 8 }

errno OBJECT-TYPE
    SYNTAX      Integer32
    MAX-ACCESS accessible-for-notify
    STATUS     current
    DESCRIPTION
        "Error number
        "
    ::= { variables 9 }

stringArg OBJECT-TYPE
    SYNTAX      OCTET STRING
    MAX-ACCESS accessible-for-notify
    STATUS     current
    DESCRIPTION
        "A trap-related string argument.
        "
    ::= { variables 10 }

message OBJECT-TYPE
    SYNTAX      OCTET STRING
    MAX-ACCESS accessible-for-notify
    STATUS     current
    DESCRIPTION
        "A trap-related message string.
        "
    ::= { variables 11 }

i64Arg OBJECT-TYPE
    SYNTAX      Counter64
    MAX-ACCESS accessible-for-notify
    STATUS     current
    DESCRIPTION
        "Error number
        "
    ::= { variables 12 }

i32Arg OBJECT-TYPE
    SYNTAX      Integer32
    MAX-ACCESS accessible-for-notify
    STATUS     current
    DESCRIPTION
        "Integer argument
        "
    ::= { variables 13 }

measuredValueStr OBJECT-TYPE
    SYNTAX     OCTET STRING
    MAX-ACCESS accessible-for-notify
    STATUS     current
    DESCRIPTION
        "The measured value that triggered the event represented as string
        "
    ::= { variables 14 }

instanceIdentifier OBJECT-TYPE
    SYNTAX      OCTET STRING
    MAX-ACCESS accessible-for-notify
    STATUS     current
    DESCRIPTION
        "Instance ID of event generating the trap
        "
    ::= { variables 15 }

deviceIdentifier OBJECT-TYPE
    SYNTAX     Integer32
    MAX-ACCESS accessible-for-notify
    STATUS     current
    DESCRIPTION
        "The Device Node Number of the node referenced in the notification.
        "
    ::= { variables 16 }

nodeStatus  OBJECT IDENTIFIER ::= { groupStateTraps 1 }

nodeStatusCrit NOTIFICATION-TYPE
    OBJECTS     { nodeIdentifier, instanceIdentifier }
    STATUS      current
    DESCRIPTION
        "A critical node status event has occurred.
        "
    ::= { nodeStatus 3 }

nodeStatusInfo NOTIFICATION-TYPE
    OBJECTS     { nodeIdentifier, instanceIdentifier }
    STATUS      current
    DESCRIPTION
        "A node status event has occurred.
        "
    ::= { nodeStatus 7 }

nodeExpStatus   OBJECT IDENTIFIER ::= { groupStateTraps 2 }

nodeExpStatusCrit NOTIFICATION-TYPE
    OBJECTS     { nodeIdentifier, instanceIdentifier }
    STATUS      current
    DESCRIPTION
        "A disk-only node has gone offline and cannot be contacted by the cluster.
        "
    ::= { nodeExpStatus 3 }

nodeShutdown OBJECT IDENTIFIER ::= { groupStateTraps 3 }

nodeShutdownInfo NOTIFICATION-TYPE
    OBJECTS     { nodeIdentifier, stringArg, instanceIdentifier }
    STATUS      current
    DESCRIPTION
        "A node is being shut down or rebooted.
        "
    ::= { nodeShutdown 7 }

nodeShutdownFail OBJECT IDENTIFIER ::= { groupStateTraps 4 }

nodeShutdownFailCrit NOTIFICATION-TYPE
    OBJECTS     { nodeIdentifier, stringArg, instanceIdentifier }
    STATUS      current
    DESCRIPTION
        "Shut down or reboot failed for a node.
        "
    ::= { nodeShutdownFail 3 }

nodeRebootCoalesced OBJECT IDENTIFIER ::= { groupStateTraps 20 }

nodeRebootCoalescedInfo NOTIFICATION-TYPE
    OBJECTS     { stringArg, instanceIdentifier }
    STATUS      current
    DESCRIPTION
        "A node is being rebooted.
        "
    ::= { nodeRebootCoalesced 7 }

nodeStatusCoalescing OBJECT IDENTIFIER ::= { groupStateTraps 21 }

nodeStatusCoalescingCrit NOTIFICATION-TYPE
    OBJECTS     { stringArg, instanceIdentifier }
    STATUS      current
    DESCRIPTION
        "Critical node status events are occurring
        "
    ::= { nodeStatusCoalescing 3 }

nodeStatusCoalescingWarn NOTIFICATION-TYPE
    OBJECTS     { stringArg, instanceIdentifier }
    STATUS      current
    DESCRIPTION
        "Warning node status events are occurring
        "
    ::= { nodeStatusCoalescing 5 }

partitionUsage OBJECT IDENTIFIER ::= { filesystemTraps 1 }

partitionUsageCrit NOTIFICATION-TYPE
    OBJECTS     { units, nodeIdentifier, measuredValueStr, stringArg, instanceIdentifier }
    STATUS      current
    DESCRIPTION
        "A partition is over the critical threshold percentage.
        "
    ::= { partitionUsage 3 }

partitionUsageWarn NOTIFICATION-TYPE
    OBJECTS     { units, nodeIdentifier, measuredValueStr, stringArg, instanceIdentifier }
    STATUS      current
    DESCRIPTION
        "A partition is over the warning threshold percentage.
        "
    ::= { partitionUsage 5 }

partitionUsageInfo NOTIFICATION-TYPE
    OBJECTS     { units, nodeIdentifier, measuredValueStr, stringArg, instanceIdentifier }
    STATUS      current
    DESCRIPTION
        "A partition is over the info threshold percentage.
        "
    ::= { partitionUsage 7 }

clusterStorageUsage OBJECT IDENTIFIER ::= { filesystemTraps 2 }

clusterStorageUsageCrit NOTIFICATION-TYPE
    OBJECTS     { instanceIdentifier }
    STATUS      current
    DESCRIPTION
        "The /ifs partition is near capacity.
        "
    ::= { clusterStorageUsage 3 }

clusterStorageUsageWarn NOTIFICATION-TYPE
    OBJECTS     { instanceIdentifier }
    STATUS      current
    DESCRIPTION
        "The /ifs partition is near capacity.
        "
    ::= { clusterStorageUsage 5 }

filesysError    OBJECT IDENTIFIER ::= { filesystemTraps 3 }

filesysErrorCrit    NOTIFICATION-TYPE
    OBJECTS     { stringArg, instanceIdentifier }
    STATUS      current
    DESCRIPTION
        "A critical /ifs filesystem error has occurred
        "
    ::= { filesysError 3 }

filesysErrorWarn    NOTIFICATION-TYPE
    OBJECTS     { stringArg, instanceIdentifier }
    STATUS      current
    DESCRIPTION
        "A warning-level /ifs filesystem error has occurred
        "
    ::= { filesysError 5 }

filesysErrorInfo    NOTIFICATION-TYPE
    OBJECTS     { stringArg, instanceIdentifier }
    STATUS      current
    DESCRIPTION
        "An /ifs filesystem error has occurred.
        "
    ::= { filesysError 7 }

diskPoolUsage OBJECT IDENTIFIER ::= { filesystemTraps 4 }

diskPoolUsageCrit NOTIFICATION-TYPE
    OBJECTS     { units, stringArg, measuredValueStr, instanceIdentifier }
    STATUS      current
    DESCRIPTION
        "A disk pool is near capacity.
        "
    ::= { diskPoolUsage 3 }

diskPoolUsageWarn NOTIFICATION-TYPE
    OBJECTS     { units, stringArg, measuredValueStr, instanceIdentifier }
    STATUS      current
    DESCRIPTION
        "A disk pool is near capacity.
        "
    ::= { diskPoolUsage 5 }

diskPoolOldDbVersion OBJECT IDENTIFIER ::= { filesystemTraps 5 }

diskPoolOldDbVersionWarn NOTIFICATION-TYPE
    OBJECTS     { stringArg, instanceIdentifier }
    STATUS      current
    DESCRIPTION
        "The SmartPools upgrade has not completed.
        "
    ::= { diskPoolOldDbVersion 5 }

ssdUsage OBJECT IDENTIFIER ::= { filesystemTraps 6 }

ssdUsageCrit NOTIFICATION-TYPE
    OBJECTS     { measuredValueStr, units, instanceIdentifier }
    STATUS      current
    DESCRIPTION
        "The SSD drives are at capacity.
        "
    ::= { ssdUsage 1 }

ssdUsageWarn NOTIFICATION-TYPE
    OBJECTS     { measuredValueStr, units, instanceIdentifier }
    STATUS      current
    DESCRIPTION
        "The SSD drives are near capacity.
        "
    ::= { ssdUsage 2 }

ssdUsageInfo NOTIFICATION-TYPE
    OBJECTS     { measuredValueStr, units, instanceIdentifier }
    STATUS      current
    DESCRIPTION
        "The SSD drives are near capacity.
        "
    ::= { ssdUsage 3 }

filesysCoalesce OBJECT IDENTIFIER ::= { filesystemTraps 20 }

filesysCoalesceCrit NOTIFICATION-TYPE
    OBJECTS     { stringArg, instanceIdentifier }
    STATUS      current
    DESCRIPTION
        "Filesystem issues are occurring at a critical level
        "
    ::= { filesysCoalesce 3 }

filesysCoalesceWarn NOTIFICATION-TYPE
    OBJECTS     { stringArg, instanceIdentifier }
    STATUS      current
    DESCRIPTION
        "Filesystem issues are occurring at a warning level
        "
    ::= { filesysCoalesce 5 }

quotaThreshError OBJECT IDENTIFIER ::= { smartQuotaTraps    1 }

quotaThreshErrorInfo    NOTIFICATION-TYPE
    OBJECTS     { stringArg, stringArg, instanceIdentifier }
    STATUS      current
    DESCRIPTION
        "SmartQuotas threshold violation
        "
    ::= { quotaThreshError 7 }

quotaNotifyError OBJECT IDENTIFIER ::= { smartQuotaTraps    2 }

quotaNotifyErrorWarn    NOTIFICATION-TYPE
    OBJECTS     { stringArg, stringArg, instanceIdentifier }
    STATUS      current
    DESCRIPTION
        "SmartQuotas threshold notification failed
        "
    ::= { quotaNotifyError 5 }

quotaError OBJECT IDENTIFIER ::= { smartQuotaTraps  3 }

quotaErrorWarn  NOTIFICATION-TYPE
    OBJECTS     { stringArg, instanceIdentifier }
    STATUS      current
    DESCRIPTION
        "SmartQuotas error
        "
    ::= { quotaError 5 }

snapshotError   OBJECT IDENTIFIER ::= { snapshotTraps 1 }

snapshotErrorWarn   NOTIFICATION-TYPE
    OBJECTS     { errno, stringArg, instanceIdentifier }
    STATUS      current
    DESCRIPTION
        "Snapshot error
        "
    ::= { snapshotError 5 }

snapshotReserve OBJECT IDENTIFIER ::= { snapshotTraps 2 }

snapshotReserveCrit NOTIFICATION-TYPE
    OBJECTS     { units, measuredValueStr, instanceIdentifier }
    STATUS      current
    DESCRIPTION
        "Snapshot reserve space is over its critical limit
        "
    ::= { snapshotReserve 3 }

snapshotReserveWarn NOTIFICATION-TYPE
    OBJECTS     { units, measuredValueStr, instanceIdentifier }
    STATUS      current
    DESCRIPTION
        "Snapshot reserve space is over its warning limit
        "
    ::= { snapshotReserve 5 }

siqEvent OBJECT IDENTIFIER ::= { syncIQTraps 1 }

siqEventCrit    NOTIFICATION-TYPE
    OBJECTS     { instanceIdentifier }
    STATUS      current
    DESCRIPTION
        "SyncIQ event
        "
    ::= { siqEvent 3 }

siqEventWarn    NOTIFICATION-TYPE
    OBJECTS     { instanceIdentifier }
    STATUS      current
    DESCRIPTION
        "SyncIQ event
        "
    ::= { siqEvent 5 }

siqError OBJECT IDENTIFIER ::= { syncIQTraps 2 }

siqErrorWarn    NOTIFICATION-TYPE
    OBJECTS     { stringArg, stringArg, instanceIdentifier }
    STATUS      current
    DESCRIPTION
        "SyncIQ error
        "
    ::= { siqError 5 }

siqPolicyCoalesced OBJECT IDENTIFIER ::= { syncIQTraps 20 }

siqPolicyCoalescedCrit  NOTIFICATION-TYPE
    OBJECTS     { stringArg, instanceIdentifier }
    STATUS      current
    DESCRIPTION
        "SyncIQ policy errors are occurring
        "
    ::= { siqPolicyCoalesced 3 }

siqPolicyCoalescedWarn  NOTIFICATION-TYPE
    OBJECTS     { stringArg, instanceIdentifier }
    STATUS      current
    DESCRIPTION
        "SyncIQ policy errors are occurring
        "
    ::= { siqPolicyCoalesced 5 }

siqTargetCoalesced OBJECT IDENTIFIER ::= { syncIQTraps 21 }

siqTargetCoalescedCrit  NOTIFICATION-TYPE
    OBJECTS     { instanceIdentifier }
    STATUS      current
    DESCRIPTION
        "SyncIQ errors are occurring for target
        "
    ::= { siqTargetCoalesced 3 }

siqTargetCoalescedWarn  NOTIFICATION-TYPE
    OBJECTS     { instanceIdentifier }
    STATUS      current
    DESCRIPTION
        "SyncIQ errors are occurring for target
        "
    ::= { siqTargetCoalesced 5 }

jobEngineError  OBJECT IDENTIFIER ::= { softwareTraps 1 }

jobEngineErrorEmerg NOTIFICATION-TYPE
    OBJECTS     { stringArg, nodeIdentifier, instanceIdentifier }
    STATUS      current
    DESCRIPTION
        "The cluster encountered one or more job failures.
        "
    ::= { jobEngineError 1 }

jobEngineErrorCrit NOTIFICATION-TYPE
    OBJECTS     { stringArg, nodeIdentifier, instanceIdentifier }
    STATUS      current
    DESCRIPTION
        "The cluster encountered one or more job failures.
        "
    ::= { jobEngineError 3 }

jobEngineErrorWarn NOTIFICATION-TYPE
    OBJECTS     { stringArg, nodeIdentifier, instanceIdentifier }
    STATUS      current
    DESCRIPTION
        "The cluster encountered one or more job failures.
        "
    ::= { jobEngineError 5 }

jobEngineErrorInfo NOTIFICATION-TYPE
    OBJECTS     { stringArg, nodeIdentifier, instanceIdentifier }
    STATUS      current
    DESCRIPTION
        "The cluster encountered one or more job failures.
        "
    ::= { jobEngineError 7 }

flexProtectRunning OBJECT IDENTIFIER ::= { softwareTraps 2 }

flexProtectRunningCrit  NOTIFICATION-TYPE
    OBJECTS     { instanceIdentifier }
    STATUS      current
    DESCRIPTION
        "Cluster is in need of restripe but FlexProtect is not running
        "
    ::= { flexProtectRunning 3 }

flexProtectRunningWarn  NOTIFICATION-TYPE
    OBJECTS     { instanceIdentifier }
    STATUS      current
    DESCRIPTION
        "Cluster is in need of restripe but FlexProtect is not running
        "
    ::= { flexProtectRunning 5 }

flexProtectRunningInfo  NOTIFICATION-TYPE
    OBJECTS     { instanceIdentifier }
    STATUS      current
    DESCRIPTION
        "Cluster is in need of restripe but FlexProtect is not running
        "
    ::= { flexProtectRunning 7 }

mcpProcFailed OBJECT IDENTIFIER ::= { softwareTraps 5 }

mcpProcFailedWarn   NOTIFICATION-TYPE
    OBJECTS     { nodeIdentifier, stringArg, instanceIdentifier }
    STATUS      current
    DESCRIPTION
        "MCP reports a process has failed on a node
        "
    ::= { mcpProcFailed 5 }

mcpProcKilled OBJECT IDENTIFIER ::= { softwareTraps 6 }

mcpProcKilledWarn   NOTIFICATION-TYPE
    OBJECTS     { nodeIdentifier, stringArg, instanceIdentifier }
    STATUS      current
    DESCRIPTION
        "MCP killed a process on a node
        "
    ::= { mcpProcKilled 5 }

licenseExpiration OBJECT IDENTIFIER ::= { softwareTraps 7 }

licenseExpirationWarn   NOTIFICATION-TYPE
    OBJECTS     { stringArg, instanceIdentifier }
    STATUS      current
    DESCRIPTION
        "One or more licenses has expired
        "
    ::= { licenseExpiration 5 }

licenseExpirationInfo   NOTIFICATION-TYPE
    OBJECTS     { stringArg, instanceIdentifier }
    STATUS      current
    DESCRIPTION
        "One or more licenses is about to expire
        "
    ::= { licenseExpiration 7 }

firmwareUpdateIncomplete OBJECT IDENTIFIER ::= { softwareTraps 8 }

firmwareUpdateIncompleteWarn    NOTIFICATION-TYPE
    OBJECTS     { instanceIdentifier }
    STATUS      current
    DESCRIPTION
        "A firmware update was not completely applied
        "
    ::= { firmwareUpdateIncomplete 5 }

testEvent OBJECT IDENTIFIER ::= { softwareTraps 9 }

testEventCrit   NOTIFICATION-TYPE
    OBJECTS     { instanceIdentifier }
    STATUS      current
    DESCRIPTION
        "Test event
        "
    ::= { testEvent 3 }

nodeCPU OBJECT IDENTIFIER ::= { softwareTraps   10 }

nodeCPUWarn NOTIFICATION-TYPE
    OBJECTS     { nodeIdentifier, instanceIdentifier }
    STATUS      current
    DESCRIPTION
        "A node has exceeded the Warning-level CPU utilization.
        "
    ::= { nodeCPU 5 }

nodeCPUInfo NOTIFICATION-TYPE
    OBJECTS     { nodeIdentifier, instanceIdentifier }
    STATUS      current
    DESCRIPTION
        "A node has exceeded the Info-level CPU utilization.
        "
    ::= { nodeCPU 7 }

mountdClientMountFailed OBJECT IDENTIFIER ::= { softwareTraps 11 }

mountdClientMountFailedInfo NOTIFICATION-TYPE
    OBJECTS     { stringArg, instanceIdentifier }
    STATUS      current
    DESCRIPTION
        "Mountd denied client mount request
        "
    ::= { mountdClientMountFailed 7 }

mountdHostLookupFailed OBJECT IDENTIFIER ::= { softwareTraps 12 }

mountdHostLookupFailedInfo  NOTIFICATION-TYPE
    OBJECTS     { stringArg, instanceIdentifier }
    STATUS      current
    DESCRIPTION
        "Mountd host lookup failed
        "
    ::= { mountdHostLookupFailed 7 }

nfsCookieTranslationFailed OBJECT IDENTIFIER ::= { softwareTraps 15 }

nfsCookieTranslationFailedInfo NOTIFICATION-TYPE
    OBJECTS { stringArg, instanceIdentifier }
    STATUS      current
    DESCRIPTION
        "64bit to 32bit cookie translation failed"
    ::= { nfsCookieTranslationFailed 1 }

mixedSedNonSedCluster OBJECT IDENTIFIER ::= { softwareTraps 13 }

mixedSedNonSedClusterCrit  NOTIFICATION-TYPE
    OBJECTS     { stringArg, instanceIdentifier }
    STATUS      current
    DESCRIPTION
        "Cluster contains a mix of encrypting nodes and non-encrypting nodes
        "
    ::= { mixedSedNonSedCluster 3 }

avscanNoServersConf OBJECT IDENTIFIER ::= { avscanTraps 1 }

avscanNoServersConfCrit NOTIFICATION-TYPE
    OBJECTS     { stringArg, instanceIdentifier }
    STATUS      current
    DESCRIPTION
        "No ICAP servers configured for AVScan
        "
    ::= { avscanNoServersConf 3 }

avscanNoServersConfWarn NOTIFICATION-TYPE
    OBJECTS     { stringArg, instanceIdentifier }
    STATUS      current
    DESCRIPTION
        "No ICAP servers configured for AVScan
        "
    ::= { avscanNoServersConf 5 }

avscanNoServersConfInfo NOTIFICATION-TYPE
    OBJECTS     { stringArg, instanceIdentifier }
    STATUS      current
    DESCRIPTION
        "No ICAP servers configured for AVScan
        "
    ::= { avscanNoServersConf 7 }

avscanError OBJECT IDENTIFIER ::= { avscanTraps 2 }

avscanErrorCrit NOTIFICATION-TYPE
    OBJECTS     { instanceIdentifier }
    STATUS      current
    DESCRIPTION
        "AVscan has encountered an error
        "
    ::= { avscanError 3 }

avscanErrorWarn NOTIFICATION-TYPE
    OBJECTS     { stringArg, instanceIdentifier }
    STATUS      current
    DESCRIPTION
        "AVscan has encountered an error
        "
    ::= { avscanError 5 }

avscanErrorInfo NOTIFICATION-TYPE
    OBJECTS     { instanceIdentifier }
    STATUS      current
    DESCRIPTION
        "AVscan has encountered an error
        "
    ::= { avscanError 7 }

avscanInfectedFile OBJECT IDENTIFIER ::= { softwareTraps 3 }

avscanInfectedFileCrit  NOTIFICATION-TYPE
    OBJECTS     { instanceIdentifier }
    STATUS      current
    DESCRIPTION
        "AVScan found an infected file
        "
    ::= { avscanInfectedFile 3 }

avscanInfectedFileWarn  NOTIFICATION-TYPE
    OBJECTS     { instanceIdentifier }
    STATUS      current
    DESCRIPTION
        "AVScan found an infected file
        "
    ::= { avscanInfectedFile 5 }

avscanInfectedFileInfo  NOTIFICATION-TYPE
    OBJECTS     { instanceIdentifier }
    STATUS      current
    DESCRIPTION
        "AVScan found an infected file
        "
    ::= { avscanInfectedFile 7 }

avscanCoalesced OBJECT IDENTIFIER ::= { avscanTraps 20 }

avscanCoalescedInfo NOTIFICATION-TYPE
    OBJECTS     { stringArg, instanceIdentifier }
    STATUS      current
    DESCRIPTION
        "AVScan is detecting problems
        "
    ::= { avscanCoalesced 3 }

avscanCoalescedWarn NOTIFICATION-TYPE
    OBJECTS     { stringArg, instanceIdentifier }
    STATUS      current
    DESCRIPTION
        "AVScan is detecting problems
        "
    ::= { avscanCoalesced 5 }

avscanCoalescedCrit NOTIFICATION-TYPE
    OBJECTS     { stringArg, instanceIdentifier }
    STATUS      current
    DESCRIPTION
        "AVscan is detecting critical problems
        "
    ::= { avscanCoalesced 7 }

clockSkew   OBJECT IDENTIFIER ::= { netProtoTraps 1 }

clockSkewCrit   NOTIFICATION-TYPE
    OBJECTS     { i32Arg, instanceIdentifier }
    STATUS      current
    DESCRIPTION
        "Windows ADS time skew outside limits.
        "
    ::= { clockSkew 3 }

sharePermsUpgradeFail   OBJECT IDENTIFIER ::= { netProtoTraps 2 }

sharePermsUpgradeFailCrit   NOTIFICATION-TYPE
    OBJECTS     { instanceIdentifier }
    STATUS      current
    DESCRIPTION
        "Windows share permissions upgrade failed
        "
    ::= { sharePermsUpgradeFail 3 }

winTimeConnectivityLost OBJECT IDENTIFIER ::= { netProtoTraps 3 }

winTimeConnectivityLostWarn NOTIFICATION-TYPE
    OBJECTS     { stringArg, instanceIdentifier }
    STATUS      current
    DESCRIPTION
        "Connectivity to the Windows Time server was lost
        "
    ::= { winTimeConnectivityLost 5 }

winNetMapFull   OBJECT IDENTIFIER ::= { netProtoTraps 4 }

winNetMapFullCrit   NOTIFICATION-TYPE
    OBJECTS     { stringArg, instanceIdentifier }
    STATUS      current
    DESCRIPTION
        "Windows ID map range is full.  Authentication may fail.
        "
    ::= { winNetMapFull 3 }

winNetAuth  OBJECT IDENTIFIER ::= { netProtoTraps 5 }

winNetAuthCrit  NOTIFICATION-TYPE
    OBJECTS     { stringArg, instanceIdentifier }
    STATUS      current
    DESCRIPTION
        "Active Directory connectivity failure
        "
    ::= { winNetAuth 3 }

winNetAuthWarn  NOTIFICATION-TYPE
    OBJECTS     { stringArg, instanceIdentifier }
    STATUS      current
    DESCRIPTION
        "Active Directory connectivity issue
        "
    ::= { winNetAuth 5 }

lwioParam       OBJECT IDENTIFIER ::= { netProtoTraps 6 }

lwioParamCrit   NOTIFICATION-TYPE
    OBJECTS     { instanceIdentifier }
    STATUS      current
    DESCRIPTION
        "LWIO Parameter Invalid
        "
    ::= { lwioParam 3 }

winSmbUpgrade   OBJECT IDENTIFIER ::= { netProtoTraps 7 }

winSmbUpgradeWarn   NOTIFICATION-TYPE
    OBJECTS     { nodeIdentifier, instanceIdentifier }
    STATUS      current
    DESCRIPTION
        "Windows networking 
        "
    ::= { winSmbUpgrade 2 }

winSmbUpgradeCrit   NOTIFICATION-TYPE
    OBJECTS     { nodeIdentifier, instanceIdentifier }
    STATUS      current
    DESCRIPTION
        "Windows networking 
        "
    ::= { winSmbUpgrade 3 }

winNetworkCoalesce  OBJECT IDENTIFIER ::= { netProtoTraps 20 }

winNetworkCoalesceCrit  NOTIFICATION-TYPE
    OBJECTS     { stringArg, instanceIdentifier }
    STATUS      current
    DESCRIPTION
        "There are problems with Windows networking components
        "
    ::= { winNetworkCoalesce 3 }

winNetworkCoalesceWarn  NOTIFICATION-TYPE
    OBJECTS     { stringArg, instanceIdentifier }
    STATUS      current
    DESCRIPTION
        "There are problems with Windows networking components
        "
    ::= { winNetworkCoalesce 5 }

winIDmapCoalesce    OBJECT IDENTIFIER ::= { netProtoTraps 21 }

winIDmapCoalesceCrit    NOTIFICATION-TYPE
    OBJECTS     { stringArg, instanceIdentifier }
    STATUS      current
    DESCRIPTION
        "There are problems with the Windows ID map
        "
    ::= { winIDmapCoalesce 3 }

winIDmapCoalesceWarn    NOTIFICATION-TYPE
    OBJECTS     { stringArg, instanceIdentifier }
    STATUS      current
    DESCRIPTION
        "There are problems with the Windows ID map
        "
    ::= { winIDmapCoalesce 5 }

winAuthCoalesce OBJECT IDENTIFIER ::= { netProtoTraps 22 }

winAuthCoalesceCrit NOTIFICATION-TYPE
    OBJECTS     { stringArg, instanceIdentifier }
    STATUS      current
    DESCRIPTION
        "There are problems with Windows authentication components
        "
    ::= { winAuthCoalesce 3 }

winAuthCoalesceWarn NOTIFICATION-TYPE
    OBJECTS     { stringArg, instanceIdentifier }
    STATUS      current
    DESCRIPTION
        "There are problems with Windows authentication components
        "
    ::= { winAuthCoalesce 5 }

winAuthUpgrade OBJECT IDENTIFIER ::= { netProtoTraps 23 }

winAuthUpgradeCrit NOTIFICATION-TYPE
    OBJECTS     { instanceIdentifier }
    STATUS      current
    DESCRIPTION
        "There are problems with upgrading authentication components
        "
    ::= { winAuthUpgrade 3 }

netStatus OBJECT IDENTIFIER ::= { networkingTraps 1 }

netStatusCrit NOTIFICATION-TYPE
    OBJECTS     { ifName, nodeIdentifier, instanceIdentifier }
    STATUS      current
    DESCRIPTION
        "A network interface is down
        "
    ::= { netStatus 3 }

netStatusWarn NOTIFICATION-TYPE
    OBJECTS     { ifName, nodeIdentifier, instanceIdentifier }
    STATUS      current
    DESCRIPTION
        "A network interface is degraded or down
        "
    ::= { netStatus 5 }

netStatusCoalescing OBJECT IDENTIFIER ::= { networkingTraps 20 }

netStatusCoalescingCrit NOTIFICATION-TYPE
    OBJECTS     { stringArg, instanceIdentifier }
    STATUS      current
    DESCRIPTION
        "Critical network problems are occurring
        "
    ::= { netStatusCoalescing 3 }

netStatusCoalescingWarn NOTIFICATION-TYPE
    OBJECTS     { stringArg, instanceIdentifier }
    STATUS      current
    DESCRIPTION
        "Warning network problems are occurring
        "
    ::= { netStatusCoalescing 5 }

hardwareError OBJECT IDENTIFIER ::= { hardwareTraps 1 }

hardwareErrorMsg OBJECT IDENTIFIER ::= { hardwareError 1 }

hardwareErrorCrit   NOTIFICATION-TYPE
    OBJECTS     { nodeIdentifier, stringArg, instanceIdentifier }
    STATUS      current
    DESCRIPTION
        "A critical hardware error has occurred.
        "
    ::= { hardwareError 3 }

hardwareErrorWarn   NOTIFICATION-TYPE
    OBJECTS     { nodeIdentifier, stringArg, instanceIdentifier }
    STATUS      current
    DESCRIPTION
        "A node has a hardware error
        "
    ::= { hardwareError 5 }

hardwareErrorInfo   NOTIFICATION-TYPE
    OBJECTS     { nodeIdentifier, stringArg, instanceIdentifier }
    STATUS      current
    DESCRIPTION
        "A hardware problem is occurring.
        "
    ::= { hardwareError 7 }

hardwareErrorMsgCrit   NOTIFICATION-TYPE
    OBJECTS     { nodeIdentifier, errorMessage, stringArg, instanceIdentifier }
    STATUS      current
    DESCRIPTION
        "There is a message concerning a hardware faliure
        "
    ::= { hardwareErrorMsg 3 }

hardwareErrorMsgWarn   NOTIFICATION-TYPE
    OBJECTS     { nodeIdentifier, errorMessage, stringArg, instanceIdentifier }
    STATUS      current
    DESCRIPTION
        "There is a message concerning a potential hardware faliure
        "
    ::= { hardwareErrorMsg 5 }

hwError OBJECT IDENTIFIER ::= { hardwareTraps 2 }

hwErrorCrit NOTIFICATION-TYPE
    OBJECTS     { nodeIdentifier, stringArg, instanceIdentifier }
    STATUS      current
    DESCRIPTION
        "Power Supply AC Failiure.
        "
    ::= { hwError 3 }

diskNodeOffline OBJECT IDENTIFIER ::= { hardwareTraps 10 }

diskNodeOfflineCrit NOTIFICATION-TYPE
    OBJECTS     { nodeIdentifier, instanceIdentifier }
    STATUS      current
    DESCRIPTION
        "The expander is offline
        "
    ::= { diskNodeOffline 3 }

hardwareCoalesced OBJECT IDENTIFIER ::= { hardwareTraps 20 }

hardwareCoalescedEmerg  NOTIFICATION-TYPE
    OBJECTS     { stringArg, instanceIdentifier }
    STATUS      current
    DESCRIPTION
        "There are hardware issues on a node
        "
    ::= { hardwareCoalesced 1 }

hardwareCoalescedCrit   NOTIFICATION-TYPE
    OBJECTS     { stringArg, instanceIdentifier }
    STATUS      current
    DESCRIPTION
        "There are hardware issues on a node
        "
    ::= { hardwareCoalesced 3 }

hardwareCoalescedWarn   NOTIFICATION-TYPE
    OBJECTS     { stringArg, instanceIdentifier }
    STATUS      current
    DESCRIPTION
        "There are hardware issues on a node
        "
    ::= { hardwareCoalesced 5 }

sasPhyError OBJECT IDENTIFIER ::= { storageTransportTraps 1 }

sasPhyErrorExpanderWarn NOTIFICATION-TYPE
    OBJECTS     { nodeIdentifier, stringArg, instanceIdentifier }
    STATUS      current
    DESCRIPTION
        "A SAS PHY error was detected in the expander.
        "
    ::= { sasPhyError 5 }

sasPhyErrorControllerWarn NOTIFICATION-TYPE
    OBJECTS     { nodeIdentifier, stringArg, instanceIdentifier }
    STATUS      current
    DESCRIPTION
        "A SAS PHY error was detected in the controller.
        "
    ::= { sasPhyError 7 }

driveStatus OBJECT IDENTIFIER ::= { systemDiskTraps 1 }

driveStatusInfo NOTIFICATION-TYPE
    OBJECTS     { nodeIdentifier, bay, instanceIdentifier }
    STATUS      current
    DESCRIPTION
        "A node has detected a problem with a drive
        "
    ::= { driveStatus 1 }

driveStatusCrit NOTIFICATION-TYPE
    OBJECTS     { nodeIdentifier, bay, instanceIdentifier }
    STATUS      current
    DESCRIPTION
        "A node has detected a problem with a drive
        "
    ::= { driveStatus 3 }

driveStatusWarn NOTIFICATION-TYPE
    OBJECTS     { nodeIdentifier, bay, instanceIdentifier }
    STATUS      current
    DESCRIPTION
        "A node has detected a problem with a drive
        "
    ::= { driveStatus 5 }

bootDiskFail OBJECT IDENTIFIER ::= { systemDiskTraps 2 }

bootDiskFailCrit NOTIFICATION-TYPE
    OBJECTS     { nodeIdentifier, instanceIdentifier }
    STATUS      current
    DESCRIPTION
        "Unhealthy boot disks, mirror is degraded.
        "
    ::= { bootDiskFail 3 }

bootDiskFailWarn NOTIFICATION-TYPE
    OBJECTS     { nodeIdentifier, instanceIdentifier }
    STATUS      current
    DESCRIPTION
        "Unhealthy boot disks, mirror is degraded.
        "
    ::= { bootDiskFail 5 }

diskError OBJECT IDENTIFIER ::= { systemDiskTraps 3 }

diskErrorWarn NOTIFICATION-TYPE
    OBJECTS     { stringArg, nodeIdentifier, instanceIdentifier }
    STATUS      current
    DESCRIPTION
        "A node's disks are having problems
        "
    ::= { diskError 3 }

bootDiskMirrorReqMissing OBJECT IDENTIFIER ::= { systemDiskTraps 4 }

bootdiskMirrorReqMissingCrit NOTIFICATION-TYPE
    OBJECTS     { nodeIdentifier, instanceIdentifier, stringArg, stringArg }
    STATUS      current
    DESCRIPTION
        "Error creating mirror on bootdisks.
        "
    ::= { bootDiskMirrorReqMissing 3 }

diskErrorCoalesced OBJECT IDENTIFIER ::= { systemDiskTraps 20 }

diskErrorCoalescedCrit NOTIFICATION-TYPE
    OBJECTS     { stringArg, instanceIdentifier }
    STATUS      current
    DESCRIPTION
        "A node's disks are having critical problems
        "
    ::= { diskErrorCoalesced 3 }

diskErrorCoalescedWarn NOTIFICATION-TYPE
    OBJECTS     { stringArg, instanceIdentifier }
    STATUS      current
    DESCRIPTION
        "A node's disks are having warning level problems
        "
    ::= { diskErrorCoalesced 5 }


hwPwrSupply OBJECT IDENTIFIER ::= { sensorTraps 1 }
hwPwrSupplyOver OBJECT IDENTIFIER ::= { hwPwrSupply 1 }

hwPwrSupplyOverCrit NOTIFICATION-TYPE
    OBJECTS     { measuredValueStr, nodeIdentifier, i32Arg, instanceIdentifier }
    STATUS      current
    DESCRIPTION
        "Power supply current over critical threshold
        "
    ::= { hwPwrSupplyOver 3 }

hwPwrSupplyOverWarn NOTIFICATION-TYPE
    OBJECTS     { measuredValueStr, nodeIdentifier, i32Arg, instanceIdentifier }
    STATUS      current
    DESCRIPTION
        "Power supply current over warning threshold
        "
    ::= { hwPwrSupplyOver 5 }

hwPwrSupplyUnder OBJECT IDENTIFIER ::= { hwPwrSupply 2 }

hwPwrSupplyUnderCrit    NOTIFICATION-TYPE
    OBJECTS     { measuredValueStr, nodeIdentifier, i32Arg, instanceIdentifier }
    STATUS      current
    DESCRIPTION
        "Power supply current under critical threshold
        "
    ::= { hwPwrSupplyUnder 3 }

hwPwrSupplyUnderWarn    NOTIFICATION-TYPE
    OBJECTS     { measuredValueStr, nodeIdentifier, i32Arg, instanceIdentifier }
    STATUS      current
    DESCRIPTION
        "Power supply current under warning threshold
        "
    ::= { hwPwrSupplyUnder 5 }

hwFan OBJECT IDENTIFIER ::= { sensorTraps 2 }
hwFanOver OBJECT IDENTIFIER ::= { hwFan 1 }

hwFanOverCrit   NOTIFICATION-TYPE
    OBJECTS     { measuredValueStr, nodeIdentifier, instanceIdentifier }
    STATUS      current
    DESCRIPTION
        "A node's fan is over critical threshold
        "
    ::= { hwFanOver 3 }

hwFanOverWarn   NOTIFICATION-TYPE
    OBJECTS     { measuredValueStr, nodeIdentifier, instanceIdentifier }
    STATUS      current
    DESCRIPTION
        "A node's fan is over warning threshold
        "
    ::= { hwFanOver 5 }

hwFanOverInfo   NOTIFICATION-TYPE
    OBJECTS     { measuredValueStr, nodeIdentifier, instanceIdentifier }
    STATUS      current
    DESCRIPTION
        "A node's fan is over warning threshold
        "
    ::= { hwFanOver 7 }

hwFanUnder OBJECT IDENTIFIER ::= { hwFan 2 }

hwFanUnderCrit  NOTIFICATION-TYPE
    OBJECTS     { measuredValueStr, nodeIdentifier, instanceIdentifier }
    STATUS      current
    DESCRIPTION
        "A node's fan is under critical threshold
        "
    ::= { hwFanUnder 3 }

hwFanUnderWarn  NOTIFICATION-TYPE
    OBJECTS     { measuredValueStr, nodeIdentifier, instanceIdentifier }
    STATUS      current
    DESCRIPTION
        "A node's fan is under warning threshold
        "
    ::= { hwFanUnder 5 }

hwFanUnderInfo  NOTIFICATION-TYPE
    OBJECTS     { measuredValueStr, nodeIdentifier, instanceIdentifier }
    STATUS      current
    DESCRIPTION
        "A node's fan is under warning threshold
        "
    ::= { hwFanUnder 7 }

hwFanCrit   NOTIFICATION-TYPE
    OBJECTS     { nodeIdentifier, stringArg, i32Arg, instanceIdentifier }
    STATUS      current
    DESCRIPTION
        "A node's fan failed
        "
    ::= { hwFan 3 }

hwFanWarn   NOTIFICATION-TYPE
    OBJECTS     { nodeIdentifier, stringArg, i32Arg, instanceIdentifier }
    STATUS      current
    DESCRIPTION
        "A node's fan monitor is about to fail
        "
    ::= { hwFan 5 }

hwVoltage OBJECT IDENTIFIER ::= { sensorTraps 10 }
hwVoltageOver OBJECT IDENTIFIER ::= { hwVoltage 1 }

hwVoltageOverCrit   NOTIFICATION-TYPE
    OBJECTS     { measuredValueStr, nodeIdentifier, stringArg, instanceIdentifier }
    STATUS      current
    DESCRIPTION
        "A node's voltage is over critical threshold
        "
    ::= { hwVoltageOver 3 }

hwVoltageOverWarn   NOTIFICATION-TYPE
    OBJECTS     { measuredValueStr, nodeIdentifier, stringArg, instanceIdentifier }
    STATUS      current
    DESCRIPTION
        "A node's voltage is over warning threshold
        "
    ::= { hwVoltageOver 5 }

hwVoltageOverInfo   NOTIFICATION-TYPE
    OBJECTS     { measuredValueStr, nodeIdentifier, stringArg, instanceIdentifier }
    STATUS      current
    DESCRIPTION
        "A node's voltage is over a threshold
        "
    ::= { hwVoltageOver 7 }

hwVoltageUnder OBJECT IDENTIFIER ::= { hwVoltage 2 }

hwVoltageUnderCrit  NOTIFICATION-TYPE
    OBJECTS     { measuredValueStr, nodeIdentifier, stringArg, instanceIdentifier }
    STATUS      current
    DESCRIPTION
        "A node's voltage is under critical threshold
        "
    ::= { hwVoltageUnder 3 }

hwVoltageUnderWarn  NOTIFICATION-TYPE
    OBJECTS     { measuredValueStr, nodeIdentifier, stringArg, instanceIdentifier }
    STATUS      current
    DESCRIPTION
        "A node's voltage is under warning threshold
        "
    ::= { hwVoltageUnder 5 }

hwVoltageUnderInfo  NOTIFICATION-TYPE
    OBJECTS     { measuredValueStr, nodeIdentifier, stringArg, instanceIdentifier }
    STATUS      current
    DESCRIPTION
        "A node's voltage is under a threshold
        "
    ::= { hwVoltageUnder 7 }

hwTemp OBJECT IDENTIFIER ::= { sensorTraps 11 }
hwTempOver OBJECT IDENTIFIER ::= { hwTemp 1 }

hwTempOverEmerg NOTIFICATION-TYPE
    OBJECTS     { measuredValueStr, nodeIdentifier, stringArg, i32Arg, instanceIdentifier }
    STATUS      current
    DESCRIPTION
        "A node's temperature is over emergency threshold
        "
    ::= { hwTempOver 1 }

hwTempOverCrit  NOTIFICATION-TYPE
    OBJECTS     { measuredValueStr, nodeIdentifier, stringArg, i32Arg, instanceIdentifier }
    STATUS      current
    DESCRIPTION
        "A node's temperature is over critical threshold
        "
    ::= { hwTempOver 3 }

hwTempOverWarn  NOTIFICATION-TYPE
    OBJECTS     { measuredValueStr, nodeIdentifier, stringArg, i32Arg, instanceIdentifier }
    STATUS      current
    DESCRIPTION
        "A node's temperature is over warning threshold
        "
    ::= { hwTempOver 5 }

hwTempOverInfo  NOTIFICATION-TYPE
    OBJECTS     { measuredValueStr, nodeIdentifier, stringArg, i32Arg, instanceIdentifier }
    STATUS      current
    DESCRIPTION
        "A node's temperature is over a threshold
        "
    ::= { hwTempOver 7 }

hwTempUnder OBJECT IDENTIFIER ::= { hwTemp 2 }

hwTempUnderEmerg    NOTIFICATION-TYPE
    OBJECTS     { measuredValueStr, nodeIdentifier, stringArg, i32Arg, instanceIdentifier }
    STATUS      current
    DESCRIPTION
        "A node's temperature is under emergency threshold
        "
    ::= { hwTempUnder 1 }

hwTempUnderCrit NOTIFICATION-TYPE
    OBJECTS     { measuredValueStr, nodeIdentifier, stringArg, i32Arg, instanceIdentifier }
    STATUS      current
    DESCRIPTION
        "A node's temperature is under critical threshold
        "
    ::= { hwTempUnder 3 }

hwTempUnderWarn NOTIFICATION-TYPE
    OBJECTS     { measuredValueStr, nodeIdentifier, stringArg, i32Arg, instanceIdentifier }
    STATUS      current
    DESCRIPTION
        "A node's temperature is under warning threshold
        "
    ::= { hwTempUnder 5 }

hwTempUnderInfo NOTIFICATION-TYPE
    OBJECTS     { measuredValueStr, nodeIdentifier, stringArg, i32Arg, instanceIdentifier }
    STATUS      current
    DESCRIPTION
        "A node's temperature is under a threshold
        "
    ::= { hwTempUnder 7 }

hwPower OBJECT IDENTIFIER ::= { sensorTraps 12 }

hwPowerCrit NOTIFICATION-TYPE
    OBJECTS     { stringArg, nodeIdentifier, instanceIdentifier }
    STATUS      current
    DESCRIPTION
        "A node has a power supply problem
        "
    ::= { hwPower 3 }

hwPowerWarn NOTIFICATION-TYPE
    OBJECTS     { instanceIdentifier }
    STATUS      current
    DESCRIPTION
        "A node has a power supply monitoring problem
        "
    ::= { hwPower 5 }

hwMem OBJECT IDENTIFIER ::= { sensorTraps 13 }

hwMemCrit   NOTIFICATION-TYPE
    OBJECTS     { measuredValueStr, nodeIdentifier, instanceIdentifier }
    STATUS      current
    DESCRIPTION
        "A node is low on memory
        "
    ::= { hwMem 3 }

hwCpuThrottle OBJECT IDENTIFIER ::= { sensorTraps 14 }

hwCpuThrottleCrit   NOTIFICATION-TYPE
    OBJECTS     { measuredValueStr, nodeIdentifier, instanceIdentifier }
    STATUS      current
    DESCRIPTION
        "A node is at 100% CPU utilization
        "
    ::= { hwCpuThrottle 3 }

sensorMonitor OBJECT IDENTIFIER ::= { sensorTraps 15 }

sensorMonitorCrit   NOTIFICATION-TYPE
    OBJECTS     { stringArg, stringArg, nodeIdentifier, instanceIdentifier }
    STATUS      current
    DESCRIPTION
        "A sensor failed
        "
    ::= { sensorMonitor 1 }

sensorMonitorWarn   NOTIFICATION-TYPE
    OBJECTS     { stringArg, stringArg, nodeIdentifier, instanceIdentifier }
    STATUS      current
    DESCRIPTION
        "A sensor is failing
        "
    ::= { sensorMonitor 2 }

sensorCoalesced OBJECT IDENTIFIER ::= { hardwareTraps 50 }

sensorCoalescedEmerg    NOTIFICATION-TYPE
    OBJECTS     { stringArg, instanceIdentifier }
    STATUS      current
    DESCRIPTION
        "There are sensor issues on a node
        "
    ::= { sensorCoalesced 1 }

sensorCoalescedCrit NOTIFICATION-TYPE
    OBJECTS     { stringArg, instanceIdentifier }
    STATUS      current
    DESCRIPTION
        "There are sensor issues on a node
        "
    ::= { sensorCoalesced 3 }

sensorCoalescedWarn NOTIFICATION-TYPE
    OBJECTS     { stringArg, instanceIdentifier }
    STATUS      current
    DESCRIPTION
        "There are sensor issues on a node
        "
    ::= { sensorCoalesced 5 }

fanCoalesced OBJECT IDENTIFIER ::= { hardwareTraps 51 }

fanCoalescedEmerg   NOTIFICATION-TYPE
    OBJECTS     { stringArg, instanceIdentifier }
    STATUS      current
    DESCRIPTION
        "There are fan issues on a node
        "
    ::= { fanCoalesced 1 }

fanCoalescedCrit    NOTIFICATION-TYPE
    OBJECTS     { stringArg, instanceIdentifier }
    STATUS      current
    DESCRIPTION
        "There are fan issues on a node
        "
    ::= { fanCoalesced 3 }

fanCoalescedWarn    NOTIFICATION-TYPE
    OBJECTS     { stringArg, instanceIdentifier }
    STATUS      current
    DESCRIPTION
        "There are fan issues on a node
        "
    ::= { fanCoalesced 5 }

tempCoalesced OBJECT IDENTIFIER ::= { hardwareTraps 52 }

tempCoalescedEmerg  NOTIFICATION-TYPE
    OBJECTS     { stringArg, instanceIdentifier }
    STATUS      current
    DESCRIPTION
        "There are temp issues on a node
        "
    ::= { tempCoalesced 1 }

tempCoalescedCrit   NOTIFICATION-TYPE
    OBJECTS     { stringArg, instanceIdentifier }
    STATUS      current
    DESCRIPTION
        "There are temp issues on a node
        "
    ::= { tempCoalesced 3 }

tempCoalescedWarn   NOTIFICATION-TYPE
    OBJECTS     { stringArg, instanceIdentifier }
    STATUS      current
    DESCRIPTION
        "There are temp issues on a node
        "
    ::= { tempCoalesced 5 }

voltsCoalesced OBJECT IDENTIFIER ::= { hardwareTraps 53 }

voltsCoalescedEmerg NOTIFICATION-TYPE
    OBJECTS     { stringArg, instanceIdentifier }
    STATUS      current
    DESCRIPTION
        "There are voltage issues on a node
        "
    ::= { voltsCoalesced 1 }

voltsCoalescedCrit  NOTIFICATION-TYPE
    OBJECTS     { stringArg, instanceIdentifier }
    STATUS      current
    DESCRIPTION
        "There are voltage issues on a node
        "
    ::= { voltsCoalesced 3 }

voltsCoalescedWarn  NOTIFICATION-TYPE
    OBJECTS     { stringArg, instanceIdentifier }
    STATUS      current
    DESCRIPTION
        "There are voltage issues on a node
        "
    ::= { voltsCoalesced 5 }

hwCurrent OBJECT IDENTIFIER ::= { sensorTraps 16 }
hwCurrentOver OBJECT IDENTIFIER ::= { hwCurrent 1 }

hwCurrentOverEmerg  NOTIFICATION-TYPE
    OBJECTS     { instanceIdentifier }
    STATUS      current
    DESCRIPTION
        "A node's current is over emergency threshold
        "
    ::= { hwCurrentOver 1 }

hwCurrentOverCrit   NOTIFICATION-TYPE
    OBJECTS     { instanceIdentifier }
    STATUS      current
    DESCRIPTION
        "A node's current is over critical threshold
        "
    ::= { hwCurrentOver 3 }

hwCurrentOverWarn   NOTIFICATION-TYPE
    OBJECTS     { instanceIdentifier }
    STATUS      current
    DESCRIPTION
        "A node's current is over warning threshold
        "
    ::= { hwCurrentOver 5 }

hwCurrentOverInfo   NOTIFICATION-TYPE
    OBJECTS     { instanceIdentifier }
    STATUS      current
    DESCRIPTION
        "A node's current is over a threshold
        "
    ::= { hwCurrentOver 7 }

hwCurrentUnder OBJECT IDENTIFIER ::= { hwCurrent 2 }

hwCurrentUnderEmerg NOTIFICATION-TYPE
    OBJECTS     { instanceIdentifier }
    STATUS      current
    DESCRIPTION
        "A node's current is under emergency threshold
        "
    ::= { hwCurrentUnder 1 }

hwCurrentUnderCrit  NOTIFICATION-TYPE
    OBJECTS     { instanceIdentifier }
    STATUS      current
    DESCRIPTION
        "A node's current is under critical threshold
        "
    ::= { hwCurrentUnder 3 }

hwCurrentUnderWarn  NOTIFICATION-TYPE
    OBJECTS     { instanceIdentifier }
    STATUS      current
    DESCRIPTION
        "A node's current is under warning threshold
        "
    ::= { hwCurrentUnder 5 }

hwCurrentUnderInfo  NOTIFICATION-TYPE
    OBJECTS     { instanceIdentifier }
    STATUS      current
    DESCRIPTION
        "A node's current is under a threshold
        "
    ::= { hwCurrentUnder 7 }

storageTransportCoalesced OBJECT IDENTIFIER ::= { storageTransportTraps 2 }

storageTransportCoalescedEmerg  NOTIFICATION-TYPE
    OBJECTS     { stringArg, instanceIdentifier }
    STATUS      current
    DESCRIPTION
        "There are storage transport issues on a node
        "
    ::= { storageTransportCoalesced 1 }

storageCoalescedCrit    NOTIFICATION-TYPE
    OBJECTS     { instanceIdentifier }
    STATUS      current
    DESCRIPTION
        "There are storage transport issues on a node
        "
    ::= { storageTransportCoalesced 3 }

storageCoalescedWarn    NOTIFICATION-TYPE
    OBJECTS     { instanceIdentifier }
    STATUS      current
    DESCRIPTION
        "There are storage transport issues on a node
        "
    ::= { storageTransportCoalesced 5 }

cloudpoolNetworkError OBJECT IDENTIFIER ::= { cloudPoolsTraps 1 }

cloudpoolNetworkErrorCrit  NOTIFICATION-TYPE
    OBJECTS     { stringArg, stringArg, deviceIdentifier, errorMessage, instanceIdentifier }
    STATUS      current
    DESCRIPTION
        "CloudPools network issues
        "
    ::= { cloudpoolNetworkError 3 }

cloudpoolAuthenticationError OBJECT IDENTIFIER ::= { cloudPoolsTraps 2 }

cloudpoolAuthenticationErrorCrit  NOTIFICATION-TYPE
    OBJECTS     { stringArg, stringArg, stringArg, errorMessage, instanceIdentifier }
    STATUS      current
    DESCRIPTION
        "CloudPools authentication issues
        "
    ::= { cloudpoolAuthenticationError 3 }

cloudpoolAuthorizationError OBJECT IDENTIFIER ::= { cloudPoolsTraps 3 }

cloudpoolAuthorizationErrorCrit  NOTIFICATION-TYPE
    OBJECTS     { stringArg, stringArg, stringArg, stringArg, errorMessage, instanceIdentifier }
    STATUS      current
    DESCRIPTION
        "CloudPools authorization issues
        "
    ::= { cloudpoolAuthorizationError 3 }

cloudpoolBucketNotFoundError OBJECT IDENTIFIER ::= { cloudPoolsTraps 4 }

cloudpoolBucketNotFoundErrorCrit  NOTIFICATION-TYPE
    OBJECTS     { stringArg, stringArg, stringArg, stringArg, errorMessage, instanceIdentifier }
    STATUS      current
    DESCRIPTION
        "CloudPools bucket not found issues
        "
    ::= { cloudpoolBucketNotFoundError 3 }

cloudpoolObjectNotFoundError OBJECT IDENTIFIER ::= { cloudPoolsTraps 5 }

cloudpoolObjectNotFoundErrorCrit  NOTIFICATION-TYPE
    OBJECTS     { stringArg, stringArg, stringArg, stringArg, errorMessage, instanceIdentifier }
    STATUS      current
    DESCRIPTION
        "CloudPools Object not found issues
        "
    ::= { cloudpoolObjectNotFoundError 3 }

cloudpoolDataCorruptionIntegrityError OBJECT IDENTIFIER ::= { cloudPoolsTraps 6 }

cloudpoolDataCorruptionIntegrityErrorEmerg  NOTIFICATION-TYPE
    OBJECTS     { stringArg, stringArg, stringArg, stringArg, stringArg, stringArg, errorMessage, instanceIdentifier }
    STATUS      current
    DESCRIPTION
        "CloudPools data corruption integrity emergency issues
        "
    ::= { cloudpoolDataCorruptionIntegrityError 1 }


cloudpoolNoUsableAccountFoundError OBJECT IDENTIFIER ::= { cloudPoolsTraps 7 }

cloudpoolNoUsableAccountFoundErrorCrit  NOTIFICATION-TYPE
    OBJECTS     { stringArg, stringArg, stringArg, stringArg, stringArg, instanceIdentifier }
    STATUS      current
    DESCRIPTION
        "CloudPools no usable account found for the policy, cloudpool
        "
    ::= { cloudpoolNoUsableAccountFoundError 3 }

cloudpoolCertificateError OBJECT IDENTIFIER ::= { cloudPoolsTraps 8 }

cloudpoolCertificateErrorCrit  NOTIFICATION-TYPE
    OBJECTS     { stringArg, stringArg, stringArg, errorMessage, instanceIdentifier }
    STATUS      current
    DESCRIPTION
        "CloudPools Certificate issues
        "
    ::= { cloudpoolCertificateError 3 }

upgradeStart OBJECT IDENTIFIER ::= { upgradeTraps 1 }

upgradeStartInfo NOTIFICATION-TYPE
    OBJECTS     { stringArg, stringArg, stringArg, stringArg }
    STATUS      current
    DESCRIPTION
        "An upgrade or rollback has been started."
    ::= { upgradeStart 7 }

upgradeFinish OBJECT IDENTIFIER ::= { upgradeTraps 2 }

upgradeFinishInfo NOTIFICATION-TYPE
    OBJECTS     { stringArg, stringArg, stringArg, stringArg }
    STATUS      current
    DESCRIPTION
        "An upgrade or rollback has finished."
    ::= { upgradeFinish 7 }

upgradeClusterEvent OBJECT IDENTIFIER ::= { upgradeTraps 3 }

upgradeClusterEventCrit NOTIFICATION-TYPE
    OBJECTS     { stringArg, stringArg, stringArg, stringArg }
    STATUS      current
    DESCRIPTION
        "Upgrade cluster event."
    ::= { upgradeClusterEvent 3 }

upgradeClusterEventWarn NOTIFICATION-TYPE
    OBJECTS     { stringArg, stringArg, stringArg, stringArg }
    STATUS      current
    DESCRIPTION
        "Upgrade cluster event."
    ::= { upgradeClusterEvent 5 }

upgradeClusterEventInfo NOTIFICATION-TYPE
    OBJECTS     { stringArg, stringArg, stringArg, stringArg }
    STATUS      current
    DESCRIPTION
        "Upgrade cluster event."
    ::= { upgradeClusterEvent 7 }

upgradeNodeEvent OBJECT IDENTIFIER ::= { upgradeTraps 4 }

upgradeNodeEventCrit NOTIFICATION-TYPE
    OBJECTS     { nodeIdentifier, stringArg, stringArg, stringArg, stringArg }
    STATUS      current
    DESCRIPTION
        "Upgrade node event."
    ::= { upgradeNodeEvent 3 }

upgradeNodeEventWarn NOTIFICATION-TYPE
    OBJECTS     { nodeIdentifier, stringArg, stringArg, stringArg, stringArg }
    STATUS      current
    DESCRIPTION
        "Upgrade node event."
    ::= { upgradeNodeEvent 5 }

upgradeNodeEventInfo NOTIFICATION-TYPE
    OBJECTS     { nodeIdentifier, stringArg, stringArg, stringArg, stringArg }
    STATUS      current
    DESCRIPTION
        "Upgrade node event."
    ::= { upgradeNodeEvent 7 }

upgradeRollbackStart OBJECT IDENTIFIER ::= { upgradeTraps 5 }

upgradeRollbackStartInfo NOTIFICATION-TYPE
    OBJECTS     { stringArg, stringArg, stringArg, stringArg }
    STATUS      current
    DESCRIPTION
        "Upgrade rollback start."
    ::= { upgradeRollbackStart 7 }

-- Conformance groups --

groupStateTrapsGroup NOTIFICATION-GROUP
    NOTIFICATIONS {
        nodeStatusCrit,
        nodeStatusInfo,
        nodeExpStatusCrit,
        nodeShutdownInfo,
        nodeShutdownFailCrit,
        nodeRebootCoalescedInfo,
        nodeStatusCoalescingCrit,
        nodeStatusCoalescingWarn }
    STATUS current
    DESCRIPTION
        "Collection of traps for group state."
    ::= { trapConformance 1 }

filesystemTrapsGroup NOTIFICATION-GROUP
    NOTIFICATIONS {
        partitionUsageCrit,
        partitionUsageWarn,
        partitionUsageInfo,
        clusterStorageUsageCrit,
        clusterStorageUsageWarn,
        filesysErrorCrit,
        filesysErrorWarn,
        filesysErrorInfo,
        diskPoolUsageCrit,
        diskPoolUsageWarn,
        diskPoolOldDbVersionWarn,
        ssdUsageCrit,
        ssdUsageWarn,
        ssdUsageInfo,
        filesysCoalesceCrit,
        filesysCoalesceWarn }
    STATUS current
    DESCRIPTION
        "Collection of filesystem traps."
    ::= { trapConformance 11 }

smartQuotaTrapsGroup NOTIFICATION-GROUP
    NOTIFICATIONS {
        quotaThreshErrorInfo,
        quotaNotifyErrorWarn,
        quotaErrorWarn }
    STATUS current
    DESCRIPTION
        "Collection of smartQuota traps."
    ::= { trapConformance 12 }

snapshotTrapsGroup NOTIFICATION-GROUP
    NOTIFICATIONS {
        snapshotErrorWarn,
        snapshotReserveCrit,
        snapshotReserveWarn }
    STATUS current
    DESCRIPTION
        "Collection of snapshot traps."
    ::= { trapConformance 13 }

syncIQTrapsGroup NOTIFICATION-GROUP
    NOTIFICATIONS {
        siqEventCrit,
        siqEventWarn,
        siqErrorWarn,
        siqPolicyCoalescedCrit,
        siqPolicyCoalescedWarn,
        siqTargetCoalescedCrit,
        siqTargetCoalescedWarn }
    STATUS current
    DESCRIPTION
        "Collection of syncIQ traps."
    ::= { trapConformance 14 }

softwareTrapsGroup NOTIFICATION-GROUP
    NOTIFICATIONS {
        jobEngineErrorEmerg,
        jobEngineErrorCrit,
        jobEngineErrorWarn,
        jobEngineErrorInfo,
        flexProtectRunningCrit,
        flexProtectRunningWarn,
        flexProtectRunningInfo,
        mcpProcFailedWarn,
        mcpProcKilledWarn,
        licenseExpirationWarn,
        licenseExpirationInfo,
        firmwareUpdateIncompleteWarn,
        testEventCrit,
        nodeCPUWarn,
        nodeCPUInfo,
        mountdClientMountFailedInfo,
        mountdHostLookupFailedInfo,
        nfsCookieTranslationFailedInfo,
        mixedSedNonSedClusterCrit }
    STATUS current
    DESCRIPTION
        "Collection of software traps."
    ::= { trapConformance 15 }

avscanTrapsGroup NOTIFICATION-GROUP
    NOTIFICATIONS {
        avscanNoServersConfCrit,
        avscanNoServersConfWarn,
        avscanNoServersConfInfo,
        avscanErrorCrit,
        avscanErrorWarn,
        avscanErrorInfo,
        avscanInfectedFileCrit,
        avscanInfectedFileWarn,
        avscanInfectedFileInfo,
        avscanCoalescedInfo,
        avscanCoalescedWarn,
        avscanCoalescedCrit }
    STATUS current
    DESCRIPTION
        "Collection of avscan traps."
    ::= { trapConformance 16 }

netProtoTrapsGroup NOTIFICATION-GROUP
    NOTIFICATIONS {
        clockSkewCrit,
        sharePermsUpgradeFailCrit,
        winTimeConnectivityLostWarn,
        winNetMapFullCrit,
        winNetAuthCrit,
        winNetAuthWarn,
        lwioParamCrit,
        winSmbUpgradeWarn,
        winSmbUpgradeCrit,
        winNetworkCoalesceCrit,
        winNetworkCoalesceWarn,
        winIDmapCoalesceCrit,
        winIDmapCoalesceWarn,
        winAuthUpgradeCrit,
        winAuthCoalesceCrit,
        winAuthCoalesceWarn }
    STATUS current
    DESCRIPTION
        "Collection of net protocol traps."
    ::= { trapConformance 17 }

networkingTrapsGroup NOTIFICATION-GROUP
    NOTIFICATIONS {
        netStatusCrit,
        netStatusWarn,
        netStatusCoalescingCrit,
        netStatusCoalescingWarn }
    STATUS current
    DESCRIPTION
        "Collection of networking traps."
    ::= { trapConformance 18 }

hardwareTrapsGroup NOTIFICATION-GROUP
    NOTIFICATIONS {
        hardwareErrorMsgCrit,
        hardwareErrorMsgWarn,
        hardwareErrorCrit,
        hardwareErrorWarn,
        hardwareErrorInfo,
        hwErrorCrit,
        diskNodeOfflineCrit,
        hardwareCoalescedEmerg,
        hardwareCoalescedCrit,
        hardwareCoalescedWarn,
        sensorCoalescedEmerg,
        sensorCoalescedCrit,
        sensorCoalescedWarn,
        fanCoalescedEmerg,
        fanCoalescedCrit,
        fanCoalescedWarn,
        tempCoalescedEmerg,
        tempCoalescedCrit,
        tempCoalescedWarn,
        voltsCoalescedEmerg,
        voltsCoalescedCrit,
        voltsCoalescedWarn }
    STATUS current
    DESCRIPTION
        "Collection of sensor traps."
    ::= { trapConformance 19 }

systemDiskTrapsGroup NOTIFICATION-GROUP
    NOTIFICATIONS {
        driveStatusInfo,
        driveStatusCrit,
        driveStatusWarn,
        bootDiskFailCrit,
        bootDiskFailWarn,
        diskErrorWarn,
        bootdiskMirrorReqMissingCrit,
        diskErrorCoalescedCrit,
        diskErrorCoalescedWarn }
    STATUS current
    DESCRIPTION
        "Collection of system disk traps."
    ::= { trapConformance 20 }

sensorTrapsGroup NOTIFICATION-GROUP
    NOTIFICATIONS {
        hwPwrSupplyOverCrit,
        hwPwrSupplyOverWarn,
        hwPwrSupplyUnderCrit,
        hwPwrSupplyUnderWarn,
        hwFanOverCrit,
        hwFanOverWarn,
        hwFanOverInfo,
        hwFanUnderCrit,
        hwFanUnderWarn,
        hwFanUnderInfo,
        hwVoltageOverCrit,
        hwVoltageOverWarn,
        hwVoltageOverInfo,
        hwVoltageUnderCrit,
        hwVoltageUnderWarn,
        hwVoltageUnderInfo,
        hwTempOverEmerg,
        hwTempOverCrit,
        hwTempOverWarn,
        hwTempOverInfo,
        hwTempUnderEmerg,
        hwTempUnderCrit,
        hwTempUnderWarn,
        hwTempUnderInfo,
        hwPowerCrit,
        hwPowerWarn,
        hwMemCrit,
        hwFanCrit,
        hwFanWarn,
        hwCpuThrottleCrit,
        sensorMonitorCrit,
        sensorMonitorWarn,
        hwCurrentOverEmerg,
        hwCurrentOverCrit,
        hwCurrentOverWarn,
        hwCurrentOverInfo,
        hwCurrentUnderEmerg,
        hwCurrentUnderCrit,
        hwCurrentUnderWarn,
        hwCurrentUnderInfo }
    STATUS current
    DESCRIPTION
        "Collection of sensor traps."
    ::= { trapConformance 21 }

storageTransportTrapsGroup NOTIFICATION-GROUP
    NOTIFICATIONS {
        sasPhyErrorExpanderWarn,
        sasPhyErrorControllerWarn,
        storageTransportCoalescedEmerg,
        storageCoalescedCrit,
        storageCoalescedWarn }
    STATUS current
    DESCRIPTION
        "Collection of storage transport traps."
    ::= { trapConformance 22 }

cloudPoolsTrapsGroup NOTIFICATION-GROUP
    NOTIFICATIONS {
        cloudpoolNetworkErrorCrit,
        cloudpoolAuthenticationErrorCrit,
        cloudpoolAuthorizationErrorCrit,
        cloudpoolBucketNotFoundErrorCrit,
        cloudpoolObjectNotFoundErrorCrit,
        cloudpoolDataCorruptionIntegrityErrorEmerg,
        cloudpoolNoUsableAccountFoundErrorCrit,
        cloudpoolCertificateErrorCrit }
    STATUS current
    DESCRIPTION
        "Collection of cloud pools traps."
    ::= { trapConformance 23 }

upgradeTrapsGroup NOTIFICATION-GROUP
    NOTIFICATIONS {
        upgradeStartInfo,
        upgradeFinishInfo,
        upgradeClusterEventCrit,
        upgradeClusterEventWarn,
        upgradeClusterEventInfo,
        upgradeNodeEventCrit,
        upgradeNodeEventWarn,
        upgradeNodeEventInfo,
        upgradeRollbackStartInfo }
    STATUS current
    DESCRIPTION
        "Collection of upgrade traps."
    ::= { trapConformance 24 }

variablesGroup OBJECT-GROUP
    OBJECTS {
        nodeIdentifier,
        measuredValue,
        units,
        oid,
        bay,
        ifName,
        phy,
        errorMessage,
        errno,
        stringArg,
        message,
        i64Arg,
        i32Arg,
        measuredValueStr,
        instanceIdentifier,
        deviceIdentifier }
    STATUS current
    DESCRIPTION
        "Collection of variable traps."
    ::= { trapConformance 50 }

trapGroupCompliance MODULE-COMPLIANCE
    STATUS current
    DESCRIPTION
        "Compliance statement for the Isilon traps."
    MODULE
        MANDATORY-GROUPS {
            groupStateTrapsGroup,
            filesystemTrapsGroup,
            smartQuotaTrapsGroup,
            snapshotTrapsGroup,
            syncIQTrapsGroup,
            softwareTrapsGroup,
            avscanTrapsGroup,
            netProtoTrapsGroup,
            networkingTrapsGroup,
            hardwareTrapsGroup,
            systemDiskTrapsGroup,
            sensorTrapsGroup,
            storageTransportTrapsGroup,
            cloudPoolsTrapsGroup,
            upgradeTrapsGroup,
            variablesGroup }
    ::= { trapCompliance 1 }

END

-- vim: set filetype=mib tabstop=4 expandtab nospell :miv --

--End - JUNIPER-WX-STATS-MIB Module

-- ========================================================================
-- Start - JUNIPER-WX-EVENT-MIB Module

JUNIPER-WX-EVENT-MIB DEFINITIONS ::= BEGIN

IMPORTS
	OBJECT-IDENTITY,
	OBJECT-TYPE, 
	NOTIFICATION-TYPE
		FROM SNMPv2-SMI
	DisplayString
		FROM SNMPv2-TC
	jnxWxGrpEvents
		FROM JUNIPER-WX-GLOBAL-MIB;

------------------------------
-- Events Group --
------------------------------

jnxWxGrpEventV2 OBJECT-IDENTITY
    STATUS    current
    DESCRIPTION
      "
       Branch for SNMPv2 events. The OIDs for SNMPv2 events should
       have a zero as the next-to-last sub-identifier (as specified
       in RFC1902).
       "
    ::= { jnxWxGrpEvents 0 }

  -- Objects sent only in events

jnxWxGrpEventDescr OBJECT-TYPE
    SYNTAX    DisplayString
    MAX-ACCESS  accessible-for-notify
    STATUS    current
    DESCRIPTION
      "
       String that provides a textual description of the event.
      "
    ::= { jnxWxGrpEvents 1 }

 -- Event descriptions

jnxWxGrpEventPowerSupplyFailure NOTIFICATION-TYPE
    STATUS  current
    DESCRIPTION
      "One or more sources of power to the system have failed.
      A redundant power-supply has presumably taken over.
      "
    ::= { jnxWxGrpEventV2 1 }

jnxWxGrpEventPowerSupplyOk NOTIFICATION-TYPE
    STATUS  current
    DESCRIPTION
      "One or more previously failed sources of power is now
      working normally. The transition to normal condition happened
      without the system having to be restarted.
      "
    ::= { jnxWxGrpEventV2 2 }

jnxWxGrpEventLicenseWillExpire NOTIFICATION-TYPE
    OBJECTS { jnxWxGrpEventDescr }
    STATUS  current
    DESCRIPTION
      "The license for the system is about to
      expire shortly. When it eventually does
      expire, the system will switch over to
      and stay in pass-through mode."
    ::= { jnxWxGrpEventV2 3 }

jnxWxGrpEventThruputLimitExceeded NOTIFICATION-TYPE
    OBJECTS { jnxWxGrpEventDescr }
    STATUS  current
    DESCRIPTION
      "The throughput of traffic through the device
      has exceeded the limit for which it has
      been licensed."
    ::= { jnxWxGrpEventV2 4 }

jnxWxGrpEventLicenseExpired NOTIFICATION-TYPE
    OBJECTS { jnxWxGrpEventDescr }
    STATUS  current
    DESCRIPTION
      "The license for the system expired.
      As a result, the system will switch over to
      and stay in pass-through mode."
    ::= { jnxWxGrpEventV2 5 }

jnxWxGrpEventClientLimitExceeded NOTIFICATION-TYPE
    OBJECTS { jnxWxGrpEventDescr }
    STATUS  current
    DESCRIPTION
      "Exceeded licensed maximum concurrent client connections. 
       Please contact Juniper Networks to obtain a new license 
       with higher number of concurrent client connections."
    ::= { jnxWxGrpEventV2 6 }

jnxWxGrpEventInFailSafeMode NOTIFICATION-TYPE
    STATUS  current
    DESCRIPTION
      "This trap is sent when the device boots up in fail-safe mode.
      This can happen for one of the following reasons:
      Fail-safe reboot was explicitly initiated by the user.
      The device rebooted automatically too many times because of
      the failure of internal consistency checks or the failure of
      tests that verify proper operation of the device."
    ::= { jnxWxGrpEventV2 7 }

jnxWxGrpEventInterfaceSpeedMismatch NOTIFICATION-TYPE
    OBJECTS { jnxWxGrpEventDescr }
    STATUS  current
    DESCRIPTION
      "A mismatch is detected between the local and remote
      interface settings. This can happen due to a mismatch
      in the local and remote interface speed or mode. "
    ::= { jnxWxGrpEventV2 8 }

jnxWxGrpEventInterfaceSpeedOk NOTIFICATION-TYPE
    OBJECTS { jnxWxGrpEventDescr }
    STATUS  current
    DESCRIPTION
      "A mismatch previously detected between the local and remote
      interface settings is now resolved. The local and remote 
      interface speed and mode are matched. "
    ::= { jnxWxGrpEventV2 9 }

jnxWxGrpEventInterfaceDuplexMismatch NOTIFICATION-TYPE
    OBJECTS { jnxWxGrpEventDescr }
    STATUS  current
    DESCRIPTION
      "A possible mismatch was detected between the duplex settings
      of either the local or remote interface and that of the
      device attached to that interface. The interface (local
      or remote) is identified by the 'ifIndex' object.

      Note that this notification is quite different from
      jnxWxGrpEventInterfaceSpeedMismatch, which compares the
      local and remote interfaces on the same WX device."
    ::= { jnxWxGrpEventV2 10 }

jnxWxGrpEventLoginFailure NOTIFICATION-TYPE
    OBJECTS { jnxWxGrpEventDescr }
    STATUS  current
    DESCRIPTION
      "A user's login attempt via the console/ssh/web server
      failed due to incorrect username or password."
    ::= { jnxWxGrpEventV2 11 }

jnxWxGrpEventDiskFailure NOTIFICATION-TYPE
    OBJECTS { jnxWxGrpEventDescr }
    STATUS  current
    DESCRIPTION
      "A hard disk failed on the system. The system was rebooted,
      and will now operate without the downed disk, at a degraded
      performance. Dictionary accumulated until this point was lost."
    ::= { jnxWxGrpEventV2 12 }
END

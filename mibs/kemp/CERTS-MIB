CERTS-MIB DEFINITIONS ::= BEGIN
IMPORTS
	OBJECT-TYPE, MODULE-IDENTITY, Integer32
		FROM SNMPv2-SMI
 
	one4net 
		FROM ONE4NET-MIB

	DateAndTime
			FROM SNMPv2-TC;

certs MODULE-IDENTITY
	LAST-UPDATED "201812070310Z"
	ORGANIZATION "Kemp Technologies"
	CONTACT-INFO "email: supportteam@kemptechnologies.com"
	DESCRIPTION "LoadMaster certificates information."
	REVISION "201812070310Z"
	DESCRIPTION "Version 1.8"
	::= { one4net 14 }


certsTable OBJECT-TYPE
	SYNTAX		SEQUENCE OF CERTSEntry
	MAX-ACCESS	not-accessible
	STATUS		current
	DESCRIPTION	"A table containing certificate specific information."
	::= { certs 1 }

--

certEntry OBJECT-TYPE
	SYNTAX		CERTSEntry
	MAX-ACCESS	not-accessible
	STATUS		current
	DESCRIPTION	"Information about a certificate"
	INDEX   { 	certIdx }
	::= { certsTable 1 }

CERTSEntry ::= SEQUENCE {
	certIdx		Integer32,
	certFileName	OCTET STRING,
	certSubjectName	OCTET STRING,
	certSerialNumber	OCTET STRING,
	certStartDate	DateAndTime,
	certEndDate	DateAndTime,
	certIssuer	OCTET STRING }

certIdx OBJECT-TYPE
	SYNTAX		Integer32 (0..1024)
	MAX-ACCESS	read-only
	STATUS		current
	DESCRIPTION	"The certificate index"
	::= { certEntry 1 }
    

certFileName OBJECT-TYPE
	SYNTAX		OCTET STRING (SIZE(0..1024))
	MAX-ACCESS	read-only
	STATUS		current
	DESCRIPTION	"The certificate file name"
	::= { certEntry 2 }

certSubjectName OBJECT-TYPE
	SYNTAX		OCTET STRING (SIZE(0..1024))
	MAX-ACCESS	read-only
	STATUS		current
	DESCRIPTION	"The certificate name"
	::= { certEntry 3 }

certSerialNumber OBJECT-TYPE
	SYNTAX		OCTET STRING (SIZE(0..1024))
	MAX-ACCESS	read-only
	STATUS		current
	DESCRIPTION	"The certificate serial number"
	::= { certEntry 4 }

certStartDate OBJECT-TYPE
	SYNTAX	DateAndTime
	MAX-ACCESS	read-only
	STATUS		current
	DESCRIPTION	"The certificate start date"
	::= { certEntry 5 }

certEndDate OBJECT-TYPE
	SYNTAX	DateAndTime
	MAX-ACCESS	read-only
	STATUS		current
	DESCRIPTION	"The certificate end date"
	::= { certEntry 6 }

certIssuer OBJECT-TYPE
	SYNTAX		OCTET STRING (SIZE(0..1024))
	MAX-ACCESS	read-only
	STATUS		current
	DESCRIPTION	"The certificate issuer"
	::= { certEntry 7 }

--

END

KMCOMMON-MIB DEFINITIONS ::= BEGIN
--
--	Release:
--		Mar 26, 2004
--			Release 1.50
--			Adds kmGeneralTable from DiscoveryMFP.
--
--	History:
--		Mar 06, 2003
--			Release 1.40
--			Adds new MIB for account standardization.
--			Adds kmGroupAccountErrorReport, kmGroupAccountErrorCancel, kmGroupAccountBalancePattern, 
--			kmGroupAccountPrintPermission and kmGroupAccountModeMain to kmGroupConfigTable.
--			Adds kmGroupSubCaption, kmGroupFAXReceiveCSetRef, kmGroupMediaKindCSetRef and kmGroupFAXSendTime
--			to kmGroupTable.
--			Changes max size of kmGroupCaption from 15 to 32 characters.
--			Adds kmGroupMediaKindTable.
--
--		Jan 10, 2003
--			Release 1.30
--			Adds kmMFPScanCounterTable and kmMFPScannerDocumentProcessorTable.
--
--		Aug 07, 2002
--			Release 1.20
--			Adds kmGroupAccountBalanceBase and kmGroupAccountBalanceMax to kmGroupConfigTable.
--			Adds kmAccountBalanceItem and kmAccountBalanceStatus to kmCounterSetTable.
--
--		Jul 04, 2002
--			Release 1.10
--			Adds kmMFPGeneral group to kmMFPDevice.
--
--		May 23, 2002
--			Release 1.00
--
--		May 08, 2002
--			Release 0.95
--			Adds kmGroupAccountMode and kmGroupChangeAdminCode to kmGroupConfigTable.
--
--		Jan 30, 2002
--			Release 0.94
--			Adds kmCounterColorModeRef to kmCounterSetTable.
--			Changes kmGroupUpdateCount ACCESS to read-only.
--
--		Dec 25, 2001
--			Release 0.93
--			Adds and changes kmAccounting group objects.
--			Adds kmMFPDevice group.
--
--		Aug 21, 2001
--			Release 0.92
--			Adds MFP color mode counter.
--
--		May 29, 2001
--			Release 0.91
--			Adds media size counter, color mode counter and function counter.
--
-- 		May 22, 2000
--			Release 0.90
--
--

--
--  Declare imports
--
    IMPORTS
	enterprises, OBJECT-TYPE
                FROM RFC1155-SMI
        hrDeviceIndex
            FROM HOST-RESOURCES-MIB
        DisplayString
            FROM RFC1213-MIB
        PresentOnOff, prtMarkerIndex
            FROM Printer-MIB;

--
--  Object identifier definition
--
    kyocera       OBJECT IDENTIFIER ::= { enterprises 1347 }
    kmCommon      OBJECT IDENTIFIER ::= { kyocera 42 }

    kmAccounting  OBJECT IDENTIFIER ::= { kmCommon 1 }
    kmCounterSet  OBJECT IDENTIFIER ::= { kmAccounting 1 }
    kmGroup       OBJECT IDENTIFIER ::= { kmAccounting 2 }
    kmGroupLevel1 OBJECT IDENTIFIER ::= { kmGroup 1 }

    kmResource    OBJECT IDENTIFIER ::= { kmCommon 2 }
    kmMedia       OBJECT IDENTIFIER ::= { kmResource 1 }
    kmColorMode   OBJECT IDENTIFIER ::= { kmResource 2 }

    kmMFP         OBJECT IDENTIFIER ::= { kmCommon 3 }
    kmMFPCounter  OBJECT IDENTIFIER ::= { kmMFP 1 }
    kmMFPDevice	  OBJECT IDENTIFIER ::= { kmMFP 2 }
    kmMFPDevicePrinter   OBJECT IDENTIFIER ::= { kmMFPDevice 1 }
    kmMFPDeviceCopier    OBJECT IDENTIFIER ::= { kmMFPDevice 2 }
    kmMFPDeviceScanner   OBJECT IDENTIFIER ::= { kmMFPDevice 3 }
    kmMFPDeviceFAX       OBJECT IDENTIFIER ::= { kmMFPDevice 4 }
    kmMFPDeviceGeneral   OBJECT IDENTIFIER ::= { kmMFPDevice 5 }

    kmGeneral      OBJECT IDENTIFIER ::= { kmCommon 5 }

--
--  kmCounterSetTable
--
    kmCounterSetTable   OBJECT-TYPE
        SYNTAX  SEQUENCE OF KmCounterSetEntry
        ACCESS  not-accessible
        STATUS  mandatory
        DESCRIPTION
            "This table manages counter informations based on acccounting feature."
        ::= { kmCounterSet 1 }

    kmCounterSetEntry   OBJECT-TYPE
        SYNTAX  KmCounterSetEntry
        ACCESS  not-accessible
        STATUS  mandatory
        DESCRIPTION
            "CounterSet handles multiple counter items"
        INDEX   { hrDeviceIndex, kmCounterSetIndex, kmCounterSetItemIndex }
        ::= { kmCounterSetTable 1 }

    KmCounterSetEntry ::= SEQUENCE {
        kmCounterSetIndex	INTEGER,
        kmCounterSetItemIndex	INTEGER,
        kmCounterItem		INTEGER,
        kmCounterMediaRef	INTEGER,
        kmCounterColorModeRef	INTEGER,
	kmAccountBalanceItem	INTEGER,
	kmAccountBalanceStatus	INTEGER,
	kmAccountRestriction	INTEGER

    }

    kmCounterSetIndex OBJECT-TYPE
        SYNTAX  INTEGER
        ACCESS  not-accessible
        STATUS  mandatory
        DESCRIPTION
            "ID to distinguish CounterSet."
        ::={ kmCounterSetEntry 1 }

    kmCounterSetItemIndex OBJECT-TYPE
        SYNTAX  INTEGER
        ACCESS  not-accessible
        STATUS  mandatory
        DESCRIPTION
            "ID to distinguish items within CounterSet."
        ::={ kmCounterSetEntry 2 }

    kmCounterItem OBJECT-TYPE
        SYNTAX  INTEGER
        ACCESS  read-only
        STATUS  mandatory
        DESCRIPTION
            "Number of items in CounterSet"
        ::={ kmCounterSetEntry 3 }

    kmCounterMediaRef OBJECT-TYPE
        SYNTAX  INTEGER
        ACCESS  read-only
        STATUS  mandatory
        DESCRIPTION
            "ID to associate CounterSet item and paper size."
        ::={ kmCounterSetEntry 4 }

    kmCounterColorModeRef OBJECT-TYPE
        SYNTAX  INTEGER
        ACCESS  read-only
        STATUS  mandatory
        DESCRIPTION
            "ID to associate CounterSet item and color mode."
        ::={ kmCounterSetEntry 5 }

    kmAccountBalanceItem OBJECT-TYPE
        SYNTAX  INTEGER
        ACCESS  read-write
        STATUS  optional
        DESCRIPTION
            "Printing limitation of associate Counter"
        ::={ kmCounterSetEntry 6 }

    kmAccountBalanceStatus OBJECT-TYPE
        SYNTAX  INTEGER  {
            active(0),
            locked(1)
        }
        ACCESS  read-only
        STATUS  optional
        DESCRIPTION
            "Returns status regarding print pages limitations. Returns active(0) if current status is not over limit.  
	     Returns locked(1) if current status is over the limit."
        ::={ kmCounterSetEntry 7 }

    kmAccountRestriction OBJECT-TYPE
        SYNTAX  INTEGER  {
            off(0),
            on(1)
        }
        ACCESS  read-write
        STATUS  optional
        DESCRIPTION
            "Function restriction"
        ::={ kmCounterSetEntry 8 }

--
--  kmGroupConfigTable
--
    kmGroupConfigTable   OBJECT-TYPE
        SYNTAX  SEQUENCE OF KmGroupConfigEntry
        ACCESS  not-accessible
        STATUS  mandatory
        DESCRIPTION
            "Group of objects equivalent to Account Management feature implemented in device."
        ::= { kmGroupLevel1 1 }

    kmGroupConfigEntry   OBJECT-TYPE
        SYNTAX  KmGroupConfigEntry
        ACCESS  not-accessible
        STATUS  mandatory
        DESCRIPTION
            "Regulates items required to control devices through network."
        INDEX   { hrDeviceIndex }
        ::= { kmGroupConfigTable 1 }

    KmGroupConfigEntry ::= SEQUENCE {
        kmGroupCodeWidth	INTEGER,
        kmGroupSecurityLock	DisplayString,
        kmGroupUpdateCount	INTEGER,
        kmGroupEntryCreate	DisplayString,
        kmGroupEntryPurge	DisplayString,
        kmGroupResetAll		DisplayString,
	kmGroupEntryNumber	INTEGER,
	kmGroupSecurityMode	INTEGER,
	kmGroupDataStatus	INTEGER,
	kmGroupAccountMode	INTEGER,
	kmGroupChangeAdminCode	DisplayString,
	kmGroupAccountBalanceBase	INTEGER,
	kmGroupAccountBalanceMax	INTEGER,
	kmGroupAccountErrorReport	INTEGER,
	kmGroupAccountErrorCancel	INTEGER,
	kmGroupAccountPrintPermission	INTEGER,
	kmGroupAccountBalancePattern	INTEGER,
	kmGroupAccountModeMain		INTEGER
    }

    kmGroupCodeWidth OBJECT-TYPE
        SYNTAX  INTEGER
        ACCESS  read-only
        STATUS  mandatory
        DESCRIPTION
            "Number of digits in Account Management code. Number of digit depends on each of 
             product specifications."
        ::={ kmGroupConfigEntry 1 }

    kmGroupSecurityLock OBJECT-TYPE
        SYNTAX  DisplayString   ( SIZE(0..15) )
        ACCESS  write-only
        STATUS  mandatory
        DESCRIPTION
            "Lock code for Account Management service.  Codes entered from MFP control panel 
             are notified to products going through network.  The code must be notified in order 
             to operate management table or retrieve account informations."
        ::={ kmGroupConfigEntry 2 }

    kmGroupUpdateCount OBJECT-TYPE
        SYNTAX  INTEGER
        ACCESS  read-only
        STATUS  mandatory
        DESCRIPTION
            "Counter showing change of account setting."
        ::={ kmGroupConfigEntry 3 }

    kmGroupEntryCreate OBJECT-TYPE
        SYNTAX  DisplayString   ( SIZE(0..8) )
        ACCESS  write-only
        STATUS  mandatory
        DESCRIPTION
            "Create account table entry"
        ::={ kmGroupConfigEntry 4 }

    kmGroupEntryPurge OBJECT-TYPE
        SYNTAX  DisplayString   ( SIZE(0..8) )
        ACCESS  write-only
        STATUS  mandatory
        DESCRIPTION
            "Delete account table entry"
        ::={ kmGroupConfigEntry 5 }

    kmGroupResetAll OBJECT-TYPE
        SYNTAX  DisplayString   ( SIZE(0..15) )
        ACCESS  write-only
        STATUS  mandatory
        DESCRIPTION
            "Reset all Account Management counters"
        ::={ kmGroupConfigEntry 6 }

    kmGroupEntryNumber OBJECT-TYPE
        SYNTAX  INTEGER
        ACCESS  read-only
        STATUS  mandatory
        DESCRIPTION
            "Number of group on account table."
        ::={ kmGroupConfigEntry 7 }

    kmGroupSecurityMode OBJECT-TYPE
        SYNTAX  INTEGER  {
            normal(0),
            strong(1)
        }
        ACCESS  read-write
        STATUS  mandatory
        DESCRIPTION
            "Security level for account informations."
        ::={ kmGroupConfigEntry 8 }

    kmGroupDataStatus OBJECT-TYPE
        SYNTAX  INTEGER
        ACCESS  read-only
        STATUS  mandatory
        DESCRIPTION
            "Data status for account informations."
        ::={ kmGroupConfigEntry 9 }

    kmGroupAccountMode OBJECT-TYPE
        SYNTAX  INTEGER
        ACCESS  read-write
        STATUS  mandatory
        DESCRIPTION
            "Account mode for each functions. (0:OFF, 1:ON)
             bit0: Printer account mode
             bit1: Copy account mode
             bit2: Scanner account mode
             bit3: FAX account mode"
        ::={ kmGroupConfigEntry 10 }

    kmGroupChangeAdminCode OBJECT-TYPE
        SYNTAX  DisplayString   ( SIZE(0..15) )
        ACCESS  write-only
        STATUS  mandatory
        DESCRIPTION
            "Change admin code for account informations."
        ::={ kmGroupConfigEntry 11 }

    kmGroupAccountBalanceBase OBJECT-TYPE
        SYNTAX  INTEGER
        ACCESS  read-only
        STATUS  mandatory
        DESCRIPTION
            "Base value of account balance."
        ::={ kmGroupConfigEntry 12 }

    kmGroupAccountBalanceMax OBJECT-TYPE
        SYNTAX  INTEGER
        ACCESS  read-only
        STATUS  mandatory
        DESCRIPTION
            "Max value of account balance."
        ::={ kmGroupConfigEntry 13 }

    kmGroupAccountErrorReport OBJECT-TYPE
        SYNTAX  INTEGER
        ACCESS  read-write
        STATUS  mandatory
        DESCRIPTION
            "Error report setting for error print job.
             bit0: When code mismatch is occured
             bit1: When limit over is occured
             0: OFF(not print), 1: ON(print error report)"
        ::={ kmGroupConfigEntry 14 }

    kmGroupAccountErrorCancel OBJECT-TYPE
        SYNTAX  INTEGER
        ACCESS  read-write
        STATUS  mandatory
        DESCRIPTION
            "Cancel setting for error print job.
             bit0: When code mismatch is occured
             bit1: When limit over is occured
             0: OFF(not cancel, only warning), 1: ON(cancel job)"
        ::={ kmGroupConfigEntry 15 }

    kmGroupAccountPrintPermission OBJECT-TYPE
        SYNTAX  INTEGER  {
            prohibit(0),
            permit(1)
        }
        ACCESS  read-write
        STATUS  mandatory
        DESCRIPTION
            "Print permission for no code job."
        ::={ kmGroupConfigEntry 16 }

    kmGroupAccountBalancePattern OBJECT-TYPE
        SYNTAX  INTEGER  {
            printCopy(1),
            eachFunction(2)
        }
        ACCESS  read-write
        STATUS  mandatory
        DESCRIPTION
            "Mode of account balance pattern."
        ::={ kmGroupConfigEntry 17 }

    kmGroupAccountModeMain OBJECT-TYPE
        SYNTAX  INTEGER  {
            off(0),
            on(1)
        }
        ACCESS  read-write
        STATUS  mandatory
        DESCRIPTION
            "Main switch for account mode."
        ::={ kmGroupConfigEntry 18 }

--
--  kmGroupTable
--
    kmGroupTable   OBJECT-TYPE
        SYNTAX  SEQUENCE OF KmGroupEntry
        ACCESS  not-accessible
        STATUS  mandatory
        DESCRIPTION
            "Object group equivalent to Account Management Report implemented on device. 
             User management code must be notified via KmGroupSecurityLock in order to retrieve 
             these informations."
        ::= { kmGroupLevel1 2 }

    kmGroupEntry   OBJECT-TYPE
        SYNTAX  KmGroupEntry
        ACCESS  not-accessible
        STATUS  mandatory
        DESCRIPTION
            "Regulates items required to retrieve informations of available devices that can print 
             Account Management Report."
        INDEX   { hrDeviceIndex, kmGroupIndex }
        ::= { kmGroupTable 1 }

    KmGroupEntry ::= SEQUENCE {
        kmGroupIndex		INTEGER,
        kmGroupAccountNumber	DisplayString,
        kmGroupCaption		DisplayString,
        kmGroupPrinterCSetRef	INTEGER,
        kmGroupCopierCSetRef	INTEGER,
        kmGroupFAXCSetRef	INTEGER,
        kmGroupScannerCSetRef	INTEGER,
        kmGroupAccountBalance	INTEGER,
        kmGroupAccountUnit	INTEGER,
        kmGroupAccountStatus	INTEGER,
	kmGroupAccountReset	DisplayString,
	kmGroupSubCaption	DisplayString,
	kmGroupFAXReceiveCSetRef	INTEGER,
	kmGroupMediaKindCSetRef		INTEGER,
	kmGroupFAXSendTime		INTEGER
    }

    kmGroupIndex OBJECT-TYPE
        SYNTAX  INTEGER
        ACCESS  not-accessible
        STATUS  mandatory
        DESCRIPTION
            "Identification number to distinguish each account table entries"
        ::={ kmGroupEntry 1 }

    kmGroupAccountNumber OBJECT-TYPE
        SYNTAX  DisplayString ( SIZE(0..8) )
        ACCESS  read-only
        STATUS  mandatory
        DESCRIPTION
            "Retrieve Account Management code."
        ::={ kmGroupEntry 2 }

    kmGroupCaption OBJECT-TYPE
        SYNTAX  DisplayString ( SIZE(0..32) )
        ACCESS  read-write
        STATUS  mandatory
        DESCRIPTION
            "Register/Retrieve department name associated with Account Management code."
        ::={ kmGroupEntry 3 }

    kmGroupPrinterCSetRef OBJECT-TYPE
        SYNTAX  INTEGER
        ACCESS  read-only
        STATUS  mandatory
        DESCRIPTION
            "Reads CounterSet values of printer"
        ::={ kmGroupEntry 4 }

    kmGroupCopierCSetRef OBJECT-TYPE
        SYNTAX  INTEGER
        ACCESS  read-only
        STATUS  mandatory
        DESCRIPTION
            "Reads CounterSet values of copier"
        ::={ kmGroupEntry 5 }

    kmGroupFAXCSetRef OBJECT-TYPE
        SYNTAX  INTEGER
        ACCESS  read-only
        STATUS  mandatory
        DESCRIPTION
            "Reads CounterSet values of FAX"
        ::={ kmGroupEntry 6 }

    kmGroupScannerCSetRef OBJECT-TYPE
        SYNTAX  INTEGER
        ACCESS  read-only
        STATUS  mandatory
        DESCRIPTION
            "Reads CounterSet values of scanner"
        ::={ kmGroupEntry 7 }

    kmGroupAccountBalance OBJECT-TYPE
        SYNTAX  INTEGER
        ACCESS  read-write
        STATUS  mandatory
        DESCRIPTION
            "Verify/Set printing limitions on Account Management."
        ::={ kmGroupEntry 8 }

    kmGroupAccountUnit OBJECT-TYPE
        SYNTAX  INTEGER  {
           impressions(7),
           sheets(8)
        }
        ACCESS  read-only
        STATUS  mandatory
        DESCRIPTION
            "Returns the unit of amount left on account."
        ::={ kmGroupEntry 9 }

    kmGroupAccountStatus OBJECT-TYPE
        SYNTAX  INTEGER  {
            active(0),
            locked(1)
        }
        ACCESS  read-only
        STATUS  mandatory
        DESCRIPTION
            "Returns status regarding print pages limitations on an account.  Returns active(0) if 
	     current status is not over limit.  Returns locked(1) if current status is over the limit."
        ::={ kmGroupEntry 10 }

    kmGroupAccountReset OBJECT-TYPE
        SYNTAX  DisplayString ( SIZE(0..15) )
        ACCESS  write-only
        STATUS  mandatory
        DESCRIPTION
            "Counter reset for each group."
        ::={ kmGroupEntry 11 }

    kmGroupSubCaption OBJECT-TYPE
        SYNTAX  DisplayString ( SIZE(0..32) )
        ACCESS  read-write
        STATUS  mandatory
        DESCRIPTION
            "Register/Retrieve department sub-name associated with Account Management code."
        ::={ kmGroupEntry 12 }

    kmGroupFAXReceiveCSetRef OBJECT-TYPE
        SYNTAX  INTEGER
        ACCESS  read-only
        STATUS  mandatory
        DESCRIPTION
            "Reads CounterSet values of FAX receive."
        ::={ kmGroupEntry 13 }

    kmGroupMediaKindCSetRef OBJECT-TYPE
        SYNTAX  INTEGER
        ACCESS  read-only
        STATUS  mandatory
        DESCRIPTION
            "Reads CounterSet values of Media kind."
        ::={ kmGroupEntry 14 }

    kmGroupFAXSendTime OBJECT-TYPE
        SYNTAX  INTEGER
        ACCESS  read-only
        STATUS  mandatory
        DESCRIPTION
            "Reads FAX send time for each group."
        ::={ kmGroupEntry 15 }

--
--  kmGroupMediaKindTable
--
    kmGroupMediaKindTable   OBJECT-TYPE
        SYNTAX  SEQUENCE OF KmGroupMediaKindEntry
        ACCESS  not-accessible
        STATUS  mandatory
        DESCRIPTION
            "Object group for account media kind information. 
             User management code must be notified via kmGroupSecurityLock in order to retrieve 
             these informations."
        ::= { kmGroupLevel1 3 }

    kmGroupMediaKindEntry   OBJECT-TYPE
        SYNTAX  KmGroupMediaKindEntry
        ACCESS  not-accessible
        STATUS  mandatory
        DESCRIPTION
            ""
        INDEX   { hrDeviceIndex, kmGroupMediaKindIndex }
        ::= { kmGroupMediaKindTable 1 }

    KmGroupMediaKindEntry ::= SEQUENCE {
        kmGroupMediaKindIndex	INTEGER,
        kmGroupMediaSizeIndex	INTEGER,
        kmGroupMediaTypeIndex	INTEGER
    }

    kmGroupMediaKindIndex OBJECT-TYPE
        SYNTAX  INTEGER
        ACCESS  not-accessible
        STATUS  mandatory
        DESCRIPTION
            "Code to distinguish media kind (size and type) for account."
        ::={ kmGroupMediaKindEntry 1 }

   kmGroupMediaSizeIndex OBJECT-TYPE
        SYNTAX  INTEGER
        ACCESS  read-write
        STATUS  mandatory
        DESCRIPTION
            "Paper size for account. Value of kmMediaIndex."
        ::={ kmGroupMediaKindEntry 2 }

   kmGroupMediaTypeIndex OBJECT-TYPE
        SYNTAX  INTEGER
        ACCESS  read-write
        STATUS  mandatory
        DESCRIPTION
            "Media type for account. Value of kcprtMediaIndex."
        ::={ kmGroupMediaKindEntry 3 }

--
--  kmMediaTable
--
    kmMediaTable   OBJECT-TYPE
        SYNTAX  SEQUENCE OF KmMediaEntry
        ACCESS  not-accessible
        STATUS  mandatory
        DESCRIPTION
            "This table shows supported paper sizes on a device and is used to determine which CounterSet 
             entry counts on each of paper sizes."
        ::= { kmMedia 1 }

    kmMediaEntry   OBJECT-TYPE
        SYNTAX  KmMediaEntry
        ACCESS  not-accessible
        STATUS  mandatory
        DESCRIPTION
            ""
        INDEX   { hrDeviceIndex, kmMediaIndex }
        ::= { kmMediaTable 1 }

    KmMediaEntry ::= SEQUENCE {
        kmMediaIndex		INTEGER,
        kmMediaName		DisplayString,
        kmMediaSizeUnit		INTEGER,
        kmMediaLongEdgeSize	INTEGER,
        kmMediaShortEdgeSize	INTEGER,
	kmMediaCounterItem	INTEGER	
    }

    kmMediaIndex OBJECT-TYPE
        SYNTAX  INTEGER
        ACCESS  not-accessible
        STATUS  mandatory
        DESCRIPTION
            "Code to distinguish paper size entries."
        ::={ kmMediaEntry 1 }

   kmMediaName OBJECT-TYPE
        SYNTAX  DisplayString ( SIZE(0..32) )
        ACCESS  read-only
        STATUS  mandatory
        DESCRIPTION
            "Paper size name"
        ::={ kmMediaEntry 2 }

    kmMediaSizeUnit OBJECT-TYPE
        SYNTAX  INTEGER  {
           tenThousandthsOfInches(3),
           micrometers(4)
        }
        ACCESS  read-only
        STATUS  mandatory
        DESCRIPTION
            "Unit used in paper size"
        ::={ kmMediaEntry 3 }

    kmMediaLongEdgeSize OBJECT-TYPE
        SYNTAX  INTEGER
        ACCESS  read-only
        STATUS  mandatory
        DESCRIPTION
            "Length of long edge"
        ::={ kmMediaEntry 4 }

    kmMediaShortEdgeSize OBJECT-TYPE
        SYNTAX  INTEGER
        ACCESS  read-only
        STATUS  mandatory
        DESCRIPTION
            "Length of short edge"
        ::={ kmMediaEntry 5 }

    kmMediaCounterItem OBJECT-TYPE
        SYNTAX  INTEGER
        ACCESS  read-only
        STATUS  mandatory
        DESCRIPTION
            "Counter values for each paper size"
        ::={ kmMediaEntry 6 }

--
--  kmColorModeTable
--
    kmColorModeTable   OBJECT-TYPE
        SYNTAX  SEQUENCE OF KmColorModeEntry
        ACCESS  not-accessible
        STATUS  mandatory
        DESCRIPTION
            ""
        ::= { kmColorMode 1 }

    kmColorModeEntry   OBJECT-TYPE
        SYNTAX  KmColorModeEntry
        ACCESS  not-accessible
        STATUS  mandatory
        DESCRIPTION
            ""
        INDEX   { hrDeviceIndex, kmColorModeIndex }
        ::= { kmColorModeTable 1 }

    KmColorModeEntry ::= SEQUENCE {
        kmColorModeIndex	INTEGER,
        kmColorModeName		DisplayString,
	kmColorModeCounterItem	INTEGER	
    }

    kmColorModeIndex OBJECT-TYPE
        SYNTAX  INTEGER
        ACCESS  not-accessible
        STATUS  mandatory
        DESCRIPTION
            "Code to distinguish output mode entries(per color)"
        ::={ kmColorModeEntry 1 }

   kmColorModeName OBJECT-TYPE
        SYNTAX  DisplayString ( SIZE(0..32) )
        ACCESS  read-only
        STATUS  mandatory
        DESCRIPTION
            "Output mode entry name (per color)"
        ::={ kmColorModeEntry 2 }

    kmColorModeCounterItem OBJECT-TYPE
        SYNTAX  INTEGER
        ACCESS  read-only
        STATUS  mandatory
        DESCRIPTION
            "Counter values for each color mode"
        ::={ kmColorModeEntry 3 }

--
--  kmMFPCounterTable
--
    kmMFPCounterTable   OBJECT-TYPE
        SYNTAX  SEQUENCE OF KmMFPCounterEntry
        ACCESS  not-accessible
        STATUS  mandatory
        DESCRIPTION
            ""
        ::= { kmMFPCounter 1 }

    kmMFPCounterEntry   OBJECT-TYPE
        SYNTAX  KmMFPCounterEntry
        ACCESS  not-accessible
        STATUS  mandatory
        DESCRIPTION
            ""
        INDEX   { hrDeviceIndex }
        ::= { kmMFPCounterTable 1 }

    KmMFPCounterEntry ::= SEQUENCE {
        kmMFPCounterItem	INTEGER
    }

    kmMFPCounterItem OBJECT-TYPE
        SYNTAX  INTEGER
        ACCESS  read-only
        STATUS  mandatory
        DESCRIPTION
            "Counter values for each functions"
        ::={ kmMFPCounterEntry 1 }

--
--  kmMFPColorModeCounterTable
--
    kmMFPColorModeCounterTable   OBJECT-TYPE
        SYNTAX  SEQUENCE OF KmMFPColorModeCounterEntry
        ACCESS  not-accessible
        STATUS  mandatory
        DESCRIPTION
            ""
        ::= { kmMFPCounter 2 }

     kmMFPColorModeCounterEntry   OBJECT-TYPE
        SYNTAX  KmMFPColorModeCounterEntry
        ACCESS  not-accessible
        STATUS  mandatory
        DESCRIPTION
            ""
        INDEX   { hrDeviceIndex, kmColorModeIndex }
        ::= { kmMFPColorModeCounterTable 1 }

    KmMFPColorModeCounterEntry ::= SEQUENCE {
         kmMFPColorModeCounterItem	INTEGER
    }

     kmMFPColorModeCounterItem OBJECT-TYPE
        SYNTAX  INTEGER
        ACCESS  read-only
        STATUS  mandatory
        DESCRIPTION
            "Counter values for each functions and color mode"
        ::={ kmMFPColorModeCounterEntry 1 }

--
--  kmMFPScanCounterTable
--
    kmMFPScanCounterTable   OBJECT-TYPE
        SYNTAX  SEQUENCE OF KmMFPScanCounterEntry
        ACCESS  not-accessible
        STATUS  mandatory
        DESCRIPTION
            ""
        ::= { kmMFPCounter 3 }

    kmMFPScanCounterEntry   OBJECT-TYPE
        SYNTAX  KmMFPScanCounterEntry
        ACCESS  not-accessible
        STATUS  mandatory
        DESCRIPTION
            ""
        INDEX   { hrDeviceIndex }
        ::= { kmMFPScanCounterTable 1 }

    KmMFPScanCounterEntry ::= SEQUENCE {
        kmMFPScanCounterItem	INTEGER
    }

    kmMFPScanCounterItem OBJECT-TYPE
        SYNTAX  INTEGER
        ACCESS  read-only
        STATUS  mandatory
        DESCRIPTION
            "Scan counter values for each functions"
        ::={ kmMFPScanCounterEntry 1 }

--
--  kmMFPPrinterGeneralTable
--
    kmMFPPrinterGeneralTable   OBJECT-TYPE
        SYNTAX  SEQUENCE OF KmMFPPrinterGeneralEntry
        ACCESS  not-accessible
        STATUS  mandatory
        DESCRIPTION
            ""
        ::= { kmMFPDevicePrinter 1 }

    kmMFPPrinterGeneralEntry   OBJECT-TYPE
        SYNTAX  KmMFPPrinterGeneralEntry
        ACCESS  not-accessible
        STATUS  mandatory
        DESCRIPTION
            ""
        INDEX   { hrDeviceIndex }
        ::= { kmMFPPrinterGeneralTable 1 }

    KmMFPPrinterGeneralEntry ::= SEQUENCE {
        kmMFPPrinterLocalization	INTEGER,
	kmMFPPrinterLocalSubCode	INTEGER
    }

    kmMFPPrinterLocalization OBJECT-TYPE
        SYNTAX  INTEGER  {
            overSea(1),
	    japan(81)
        }
        ACCESS  read-only
        STATUS  mandatory
        DESCRIPTION
            ""
        ::={ kmMFPPrinterGeneralEntry 1 }

    kmMFPPrinterLocalSubCode OBJECT-TYPE
        SYNTAX  INTEGER
        ACCESS  read-only
        STATUS  mandatory
        DESCRIPTION
            ""
        ::={ kmMFPPrinterGeneralEntry 2 }

--
--  kmMFPCopierGeneralTable
--
    kmMFPCopierGeneralTable   OBJECT-TYPE
        SYNTAX  SEQUENCE OF KmMFPCopierGeneralEntry
        ACCESS  not-accessible
        STATUS  mandatory
        DESCRIPTION
            ""
        ::= { kmMFPDeviceCopier 1 }

    kmMFPCopierGeneralEntry   OBJECT-TYPE
        SYNTAX  KmMFPCopierGeneralEntry
        ACCESS  not-accessible
        STATUS  mandatory
        DESCRIPTION
            ""
        INDEX   { hrDeviceIndex }
        ::= { kmMFPCopierGeneralTable 1 }

    KmMFPCopierGeneralEntry ::= SEQUENCE {
        kmMFPCopierLocalization	INTEGER,
	kmMFPCopierLocalSubCode	INTEGER
    }

    kmMFPCopierLocalization OBJECT-TYPE
        SYNTAX  INTEGER  {
            notInstalled(0),
            inch(1),
	    europeMetric(31),
	    asiaPacific(61),
	    japanMetric(81)
        }
        ACCESS  read-only
        STATUS  mandatory
        DESCRIPTION
            ""
        ::={ kmMFPCopierGeneralEntry 1 }

    kmMFPCopierLocalSubCode OBJECT-TYPE
        SYNTAX  INTEGER
        ACCESS  read-only
        STATUS  mandatory
        DESCRIPTION
            ""
        ::={ kmMFPCopierGeneralEntry 2 }

--
--  kmMFPScannerGeneralTable
--
    kmMFPScannerGeneralTable   OBJECT-TYPE
        SYNTAX  SEQUENCE OF KmMFPScannerGeneralEntry
        ACCESS  not-accessible
        STATUS  mandatory
        DESCRIPTION
            ""
        ::= { kmMFPDeviceScanner 1 }

    kmMFPScannerGeneralEntry   OBJECT-TYPE
        SYNTAX  KmMFPScannerGeneralEntry
        ACCESS  not-accessible
        STATUS  mandatory
        DESCRIPTION
            ""
        INDEX   { hrDeviceIndex }
        ::= { kmMFPScannerGeneralTable 1 }

    KmMFPScannerGeneralEntry ::= SEQUENCE {
        kmMFPScannerLocalization	INTEGER,
	kmMFPScannerLocalSubCode	INTEGER,
	kmMFPScannerAccountMode		INTEGER
    }

    kmMFPScannerLocalization OBJECT-TYPE
        SYNTAX  INTEGER  {
            notInstalled(0),
            inch(1),
	    europeMetric(31),
	    asiaPacific(61),
	    japanMetric(81)
        }
        ACCESS  read-only
        STATUS  mandatory
        DESCRIPTION
            ""
        ::={ kmMFPScannerGeneralEntry 1 }

    kmMFPScannerLocalSubCode OBJECT-TYPE
        SYNTAX  INTEGER
        ACCESS  read-only
        STATUS  mandatory
        DESCRIPTION
            ""
        ::={ kmMFPScannerGeneralEntry 2 }

    kmMFPScannerAccountMode OBJECT-TYPE
        SYNTAX  INTEGER  {
            imageScan(1),
	    networkScan(2)
        }
        ACCESS  read-only
        STATUS  mandatory
        DESCRIPTION
            ""
        ::={ kmMFPScannerGeneralEntry 3 }

--
--  kmMFPScannerDocProcessorTable
--
    kmMFPScannerDocProcessorTable   OBJECT-TYPE
        SYNTAX  SEQUENCE OF KmMFPScannerDocProcessorEntry
        ACCESS  not-accessible
        STATUS  mandatory
        DESCRIPTION
            ""
        ::= { kmMFPDeviceScanner 2 }

    kmMFPScannerDocProcessorEntry   OBJECT-TYPE
        SYNTAX  KmMFPScannerDocProcessorEntry
        ACCESS  not-accessible
        STATUS  mandatory
        DESCRIPTION
            ""
        INDEX   { hrDeviceIndex, kmMFPDocProcessorIndex }
        ::= { kmMFPScannerDocProcessorTable 1 }

    KmMFPScannerDocProcessorEntry ::= SEQUENCE {
        kmMFPDocProcessorIndex		INTEGER,
	kmMFPDocProcessorModel		DisplayString,
	kmMFPDocProcessorAbsolteModel	DisplayString
    }

    kmMFPDocProcessorIndex OBJECT-TYPE
        SYNTAX  INTEGER 
        ACCESS  not-accessible
        STATUS  mandatory
        DESCRIPTION
            "Identification number of Document Processor."
        ::={ kmMFPScannerDocProcessorEntry 1 }

    kmMFPDocProcessorModel OBJECT-TYPE
        SYNTAX  DisplayString ( SIZE(0..32) )
        ACCESS  read-only
        STATUS  mandatory
        DESCRIPTION
            "Document Processor model name."
        ::={ kmMFPScannerDocProcessorEntry 2 }

    kmMFPDocProcessorAbsolteModel OBJECT-TYPE
        SYNTAX  DisplayString ( SIZE(0..32) )
        ACCESS  read-only
        STATUS  mandatory
        DESCRIPTION
            "Document Processor absolte model name."
        ::={ kmMFPScannerDocProcessorEntry 3 }

--
--  kmMFPFAXGeneralTable
--
    kmMFPFAXGeneralTable   OBJECT-TYPE
        SYNTAX  SEQUENCE OF KmMFPFAXGeneralEntry
        ACCESS  not-accessible
        STATUS  mandatory
        DESCRIPTION
            ""
        ::= { kmMFPDeviceFAX 1 }

    kmMFPFAXGeneralEntry   OBJECT-TYPE
        SYNTAX  KmMFPFAXGeneralEntry
        ACCESS  not-accessible
        STATUS  mandatory
        DESCRIPTION
            ""
        INDEX   { hrDeviceIndex }
        ::= { kmMFPFAXGeneralTable 1 }

    KmMFPFAXGeneralEntry ::= SEQUENCE {
        kmMFPFAXLocalization	INTEGER,
	kmMFPFAXLocalSubCode	INTEGER
    }

    kmMFPFAXLocalization OBJECT-TYPE
        SYNTAX  INTEGER  {
            notInstalled(0),
            inch(1),
	    europeMetric(31),
	    asiaPacific(61),
	    japanMetric(81)
        }
        ACCESS  read-only
        STATUS  mandatory
        DESCRIPTION
            ""
        ::={ kmMFPFAXGeneralEntry 1 }

    kmMFPFAXLocalSubCode OBJECT-TYPE
        SYNTAX  INTEGER
        ACCESS  read-only
        STATUS  mandatory
        DESCRIPTION
            ""
        ::={ kmMFPFAXGeneralEntry 2 }

--
--  kmMFPGeneralTable
--
    kmMFPGeneralTable   OBJECT-TYPE
        SYNTAX  SEQUENCE OF KmMFPGeneralEntry
        ACCESS  not-accessible
        STATUS  mandatory
        DESCRIPTION
            ""
        ::= { kmMFPDeviceGeneral 1 }

    kmMFPGeneralEntry   OBJECT-TYPE
        SYNTAX  KmMFPGeneralEntry
        ACCESS  not-accessible
        STATUS  mandatory
        DESCRIPTION
            ""
        INDEX   { hrDeviceIndex }
        ::= { kmMFPGeneralTable 1 }

    KmMFPGeneralEntry ::= SEQUENCE {
        kmMFPFunctionControl	INTEGER,
	kmMFPDeviceDateTime	DisplayString
    }

    kmMFPFunctionControl OBJECT-TYPE
        SYNTAX  INTEGER
        ACCESS  read-write
        STATUS  optional
        DESCRIPTION
            ""
        ::={ kmMFPGeneralEntry 1 }

    kmMFPDeviceDateTime OBJECT-TYPE
        SYNTAX  DisplayString ( SIZE(0..20) )
        ACCESS  read-only
        STATUS  optional
        DESCRIPTION
            ""
        ::={ kmMFPGeneralEntry 2 }


--
--  kmGeneralTable
--
    kmGeneralTable  OBJECT-TYPE
        SYNTAX  SEQUENCE OF KMGENERALENTRY
        ACCESS  not-accessible
        STATUS  mandatory
        DESCRIPTION
        ""
        ::= { kmGeneral 1 }

    kmGeneralEntry  OBJECT-TYPE
        SYNTAX  KMGENERALENTRY
        ACCESS  not-accessible
        STATUS  mandatory
        DESCRIPTION
        ""
        INDEX  {hrDeviceIndex}
        ::= { kmGeneralTable 1 }

    KMGENERALENTRY ::= SEQUENCE {
        kmProductName  DisplayString,
        kmAbsoluteName  DisplayString,
        kmDefaultAgent  INTEGER,
        kmAgentResumeMode  PresentOnOff,
        kmAgentResumeTimeout  INTEGER,
        kmOneTouchKeyNum  INTEGER,
        kmOneTouchShiftNum  INTEGER,
        kmLocalTime  OCTET STRING,
        kmTimeFormat  OCTET STRING,
        kmTimeZone  INTEGER,
        kmPanelSizeUnit  INTEGER,
        kmPrescribeEscape  INTEGER,
        kmConsoleDisableEx  INTEGER
}

    kmProductName  OBJECT-TYPE
        SYNTAX  DisplayString (SIZE(0..32))
        ACCESS  read-only
        STATUS  mandatory
        DESCRIPTION
        ""
        ::= { kmGeneralEntry 1 }

    kmAbsoluteName  OBJECT-TYPE
        SYNTAX  DisplayString (SIZE(0..32))
        ACCESS  read-only
        STATUS  mandatory
        DESCRIPTION
        ""
        ::= { kmGeneralEntry 2 }

    kmDefaultAgent  OBJECT-TYPE
        SYNTAX  INTEGER { status(1), copy(2), send(3), docbox(4) }
        ACCESS  read-write
        STATUS  mandatory
        DESCRIPTION
        ""
        ::= { kmGeneralEntry 3 }

    kmAgentResumeMode  OBJECT-TYPE
        SYNTAX  PresentOnOff
        ACCESS  read-write
        STATUS  mandatory
        DESCRIPTION
        ""
        ::= { kmGeneralEntry 4 }

    kmAgentResumeTimeout  OBJECT-TYPE
        SYNTAX  INTEGER (0..300)
        ACCESS  read-write
        STATUS  mandatory
        DESCRIPTION
        ""
        ::= { kmGeneralEntry 5 }

    kmOneTouchKeyNum  OBJECT-TYPE
        SYNTAX  INTEGER
        ACCESS  read-only
        STATUS  mandatory
        DESCRIPTION
        ""
        ::= { kmGeneralEntry 8 }

    kmOneTouchShiftNum  OBJECT-TYPE
        SYNTAX  INTEGER
        ACCESS  read-only
        STATUS  mandatory
        DESCRIPTION
        ""
        ::= { kmGeneralEntry 9 }

    kmLocalTime  OBJECT-TYPE
        SYNTAX  OCTET STRING (SIZE(36))
        ACCESS  read-write
        STATUS  mandatory
        DESCRIPTION
        ""
        ::= { kmGeneralEntry 10 }

    kmTimeFormat  OBJECT-TYPE
        SYNTAX  OCTET STRING (SIZE(32))
        ACCESS  read-only
        STATUS  mandatory
        DESCRIPTION
        ""
        ::= { kmGeneralEntry 11 }

    kmTimeZone  OBJECT-TYPE
        SYNTAX  INTEGER
        ACCESS  read-write
        STATUS  mandatory
        DESCRIPTION
        ""
        ::= { kmGeneralEntry 12 }

    kmPanelSizeUnit  OBJECT-TYPE
        SYNTAX  INTEGER { tenThousandthsOfInches(3), micrometers(4) }
        ACCESS  read-write
        STATUS  mandatory
        DESCRIPTION
        ""
        ::= { kmGeneralEntry 13 }

    kmPrescribeEscape  OBJECT-TYPE
        SYNTAX  INTEGER
        ACCESS  read-write
        STATUS  mandatory
        DESCRIPTION
        ""
        ::= { kmGeneralEntry 14 }

    kmConsoleDisableEx  OBJECT-TYPE
        SYNTAX  INTEGER { partialLock(1), enabled(3), disabled(4) }
        ACCESS  read-write
        STATUS  mandatory
        DESCRIPTION
        ""
        ::= { kmGeneralEntry 15 }
END

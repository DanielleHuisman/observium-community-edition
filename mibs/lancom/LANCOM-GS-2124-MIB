LANCOM-GS-2124-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    MacAddress FROM BRIDGE-MIB
    ifIndex    FROM RFC1213-MIB;

lancomSystems MODULE-IDENTITY
 LAST-UPDATED "200902180000Z"
        ORGANIZATION "LANCOM Systems GmbH"
        CONTACT-INFO
         "Adenauerstrasse 20 / B2, 52146 Wuerselen, Germany
                 Email: info@lancom.de
                 TEL: +49 (0)2405 49936 0
                 FAX: +49 (0)2405 49936 99"
        DESCRIPTION
                "The MIB module is for LANCOM Systems"
        ::= { enterprises 2356 }

switchingSystems OBJECT IDENTIFIER ::= { lancomSystems 800 }

gigabitEthernetSwitches OBJECT IDENTIFIER ::= { switchingSystems 3 }

lancomGS2124 OBJECT IDENTIFIER ::= { gigabitEthernetSwitches 2124 }

gs2124Produces            OBJECT IDENTIFIER ::= { lancomGS2124 1 }

gs2124System            OBJECT IDENTIFIER ::= { gs2124Produces 1 }

gs2124CommonSys            OBJECT IDENTIFIER ::= { gs2124System 1 }

gs2124Reboot OBJECT-TYPE
 SYNTAX  INTEGER(0|1)
 MAX-ACCESS     read-write
 STATUS  current
 DESCRIPTION
  "Reboot the system. Get this OID always return zero.
            0 - do nothing
   1 - Reboot without saving start"
 ::= { gs2124CommonSys 1 }

gs2124BiosVsersion OBJECT-TYPE
 SYNTAX  DisplayString
 MAX-ACCESS     read-only
 STATUS  current
 DESCRIPTION
  "Get the BIOS version of the system."
 ::= { gs2124CommonSys 2 }

gs2124FirmwareVersion OBJECT-TYPE
 SYNTAX  DisplayString
 MAX-ACCESS     read-only
 STATUS  current
 DESCRIPTION
  "Get the firmware version of the system."
 ::= { gs2124CommonSys 3 }

gs2124HardwareVersion OBJECT-TYPE
 SYNTAX  DisplayString
 MAX-ACCESS     read-only
 STATUS  current
 DESCRIPTION
  "Get the hardware version of the system."
 ::= { gs2124CommonSys 4 }

gs2124MechanicalVersion OBJECT-TYPE
 SYNTAX  DisplayString
 MAX-ACCESS      read-only
 STATUS  current
 DESCRIPTION
  "Get the mechanical version of the system."
 ::= { gs2124CommonSys 5 }

gs2124SerialNumber OBJECT-TYPE
 SYNTAX  DisplayString
 MAX-ACCESS     read-only
 STATUS  current
 DESCRIPTION
  "Get the Serial number of the system."
 ::= { gs2124CommonSys 6 }

gs2124HostMacAddress OBJECT-TYPE
 SYNTAX  DisplayString
 MAX-ACCESS     read-only
 STATUS  current
 DESCRIPTION
  "Get the MAC address of the system."
 ::= { gs2124CommonSys 7 }

gs2124DevicePort OBJECT-TYPE
 SYNTAX  DisplayString
 MAX-ACCESS   read-only
 STATUS  current
 DESCRIPTION
  "Get the quantity of ports that this system owns now."
 ::= { gs2124CommonSys 8 }

gs2124RamSize  OBJECT-TYPE
    SYNTAX      DisplayString
    MAX-ACCESS      read-only
    STATUS      current
    DESCRIPTION
        "Get the RAM size of the system."
 ::= { gs2124CommonSys 9 }

gs2124FlashSize  OBJECT-TYPE
    SYNTAX      DisplayString
    MAX-ACCESS      read-only
    STATUS      current
    DESCRIPTION
        "Get the flash size of the system."
 ::= { gs2124CommonSys 10 }

gs2124DeviceName  OBJECT-TYPE
    SYNTAX      DisplayString
    MAX-ACCESS      read-write
    STATUS      current
    DESCRIPTION
        "Get/Set the device name of the system."
 ::= { gs2124CommonSys 11 }

gs2124SystemDescription  OBJECT-TYPE
    SYNTAX      DisplayString
    MAX-ACCESS      read-only
    STATUS      current
    DESCRIPTION
        "Get the system desctiption of the system."
 ::= { gs2124CommonSys 12 }

gs2124CpuLoad  OBJECT-TYPE
    SYNTAX      DisplayString
    MAX-ACCESS      read-only
    STATUS      current
    DESCRIPTION
        "Get the CPU Load."
 ::= { gs2124CommonSys 13 }

gs2124IP            OBJECT IDENTIFIER ::= { gs2124System 2 }

gs2124DhcpSetting OBJECT-TYPE
 SYNTAX      INTEGER(0|1)
 MAX-ACCESS         read-write
 STATUS      current
 DESCRIPTION
  "Get/Set DHCP status of the system.
   0 - DHCP disable
   1 - DHCP enable"
 ::= { gs2124IP 1 }

gs2124IPAddress OBJECT-TYPE
 SYNTAX      IpAddress
 MAX-ACCESS     read-write
 STATUS  current
 DESCRIPTION
  "Get/Set the IP address of the system.
   You can't set this OID if DHCP status is enabled."
 ::= { gs2124IP 2 }

gs2124NetMask OBJECT-TYPE
 SYNTAX      IpAddress
 MAX-ACCESS     read-write
 STATUS  current
 DESCRIPTION
  "Get/Set the subnet mask of the system.
   You can't set this OID if DHCP status is enabled."
 ::= { gs2124IP 3 }

gs2124DefaultGateway OBJECT-TYPE
 SYNTAX      IpAddress
 MAX-ACCESS     read-write
 STATUS  current
 DESCRIPTION
  "Get/Set the default gateway of the system.
   You can't set this OID if DHCP status is enabled."
 ::= { gs2124IP 4 }

gs2124DnsConf OBJECT-TYPE
 SYNTAX      INTEGER(0|1)
 MAX-ACCESS     read-write
 STATUS  current
 DESCRIPTION
  "Get/Set DNS state.
  Change of this value will be kept in buffer and only take effect while DHCP is enabled.
   0 - manual, the DNS server is from manual setting
            1 - auto, the DNS server is assigned by DHCP server."
 ::= { gs2124IP 5 }

gs2124DnsState OBJECT-TYPE
 SYNTAX      INTEGER(0|1)
 MAX-ACCESS     read-only
 STATUS  current
 DESCRIPTION
  "Get the DNS real state.
   0 - manual, the DNS server is from manual setting
   1 - auto, the DNS server is assigned by DHCP server."
 ::= { gs2124IP 6 }

gs2124DnsServer OBJECT-TYPE
 SYNTAX      IpAddress
 MAX-ACCESS     read-write
 STATUS  current
 DESCRIPTION
  "Get/Set the DNS server of the system."
 ::= { gs2124IP 7 }

gs2124Time            OBJECT IDENTIFIER ::= { gs2124System 3 }

gs2124SystemCurrentTime OBJECT-TYPE
 SYNTAX      DisplayString
 MAX-ACCESS     read-only
 STATUS  current
 DESCRIPTION
  "Get the current time of the system."
 ::= { gs2124Time 1 }

gs2124ManualTimeSetting OBJECT-TYPE
 SYNTAX      DisplayString
 MAX-ACCESS     read-write
 STATUS  current
 DESCRIPTION
  "Get/Set the system time of the device.
        The input format is 'Year/Month/Day/Hour/Minute/Second'.
        ex: 2004/1/1/12/34/25  means 2004/1/1 - 12:24:25 .
        The value range:
        Year    : 2000 - 2036,
        Mouth   : 1 - 12,
        Day     : 1 - 31,
        Hour    : 0 - 23,
        Minute  : 0 - 59,
        Sec     : 0 - 59."
 ::= { gs2124Time 2 }

gs2124NTPServer OBJECT-TYPE
 SYNTAX      DisplayString
 MAX-ACCESS     read-write
 STATUS  current
 DESCRIPTION
  "Get/Set the NTP Time Server. You can use the IP address or domain name."
 ::= { gs2124Time 3 }

gs2124NTPTimeZone OBJECT-TYPE
 SYNTAX      INTEGER(-12..13)
 MAX-ACCESS     read-write
 STATUS  current
 DESCRIPTION
  "Get/Set the NTP Time Zone.
  The value range is between -12 and 13
  -12 - GMT -12:00,
  -11 - GMT -11:00,
  -10 - GMT -10:00,
   -9 - GMT -09:00,
   -8 - GMT -08:00,
   -7 - GMT -07:00,
   -6 - GMT -06:00,
   -5 - GMT -05:00,
   -4 - GMT -04:00,
   -3 - GMT -03:00,
   -2 - GMT -02:00,
   -1 - GMT -01:00,
    0 - GMT +00:00,
    1 - GMT +01:00,
    2 - GMT +02:00,
    3 - GMT +03:00,
    4 - GMT +04:00,
    5 - GMT +05:00,
    6 - GMT +06:00,
    7 - GMT +07:00,
    8 - GMT +08:00,
    9 - GMT +09:00,
   10 - GMT +10:00,
   11 - GMT +11:00,
   12 - GMT +12:00,
   13 - GMT +13:00. "
 ::= { gs2124Time 4 }

gs2124NTPTimeSync OBJECT-TYPE
 SYNTAX      INTEGER(0|1)
 MAX-ACCESS     read-write
 STATUS  current
 DESCRIPTION
  "Sync time from NTP Server. Get this OID always return zero.
  Set the Time Server and Time Zone before doing time sync.
  Notice that time server must be correct!
  The value range (0|1):
  1 - sync.
        0 - do nothing."
 ::= { gs2124Time 5 }

gs2124DaylightSavingTime OBJECT-TYPE
 SYNTAX      INTEGER(-5..5)
 MAX-ACCESS     read-write
 STATUS  current
 DESCRIPTION
  "Get/Set the daylight saving time.
  The value range is between -5 and 5. (Unit: hour)"
 ::= { gs2124Time 6 }

gs2124DaylightStartTime OBJECT-TYPE
 SYNTAX      DisplayString
 MAX-ACCESS     read-write
 STATUS  current
 DESCRIPTION
  "Get/Set the Start time of Daylight Saving.
  The input format is 'MM/DD/HH',
  and daylight saving start month can't equal end month.
  example: month/day/hour   10/01/00
  month: 01~12, day: 01~31, hour: 00~23 ."
 ::= { gs2124Time 7 }

gs2124DaylightEndTime OBJECT-TYPE
 SYNTAX      DisplayString
 MAX-ACCESS     read-write
 STATUS  current
 DESCRIPTION
  "Get/Set the End time of Daylight Saving.
  The input format is 'MM/DD/HH',
  and daylight saving start month can't equal end month.
  example: month/day/hour   04/01/00
  month: 01~12, day: 01~31, hour: 00~23 ."
 ::= { gs2124Time 8 }


gs2124Account            OBJECT IDENTIFIER ::= { gs2124System 4 }

gs2124AccountNumber OBJECT-TYPE
 SYNTAX      INTEGER(1..5)
 MAX-ACCESS     read-only
 STATUS  current
 DESCRIPTION
  "Get the current account number(s) of the system."
 ::= { gs2124Account 1 }

gs2124AccountTable OBJECT-TYPE
 SYNTAX  SEQUENCE OF GS2124AccountEntry
 MAX-ACCESS not-accessible
 STATUS  current
 DESCRIPTION
  "This is a list of GS2124AccountEntry. The numbers of entries are given by
  the value of gs2124AccountNumber."
 ::= { gs2124Account 2 }

GS2124AccountEntry ::=
SEQUENCE {
    gs2124AccountIndex      INTEGER,
    gs2124AccountAuthorization DisplayString,
    gs2124AccountName             DisplayString,
    gs2124AccountPassword         DisplayString
}

gs2124AccountEntry OBJECT-TYPE
 SYNTAX  GS2124AccountEntry
 MAX-ACCESS     not-accessible
 STATUS  current
 DESCRIPTION
  "This is the Entry(s) for account information."
 INDEX {gs2124AccountIndex}
 ::= { gs2124AccountTable 1 }

gs2124AccountIndex OBJECT-TYPE
 SYNTAX  INTEGER(1..5)
 MAX-ACCESS     read-only
 STATUS  current
 DESCRIPTION
  "This is the index of the account entry."
 ::= { gs2124AccountEntry 1 }

gs2124AccountAuthorization OBJECT-TYPE
 SYNTAX  DisplayString
 MAX-ACCESS     read-only
 STATUS  current
 DESCRIPTION
  "This is the authorization of the account entry."
 ::= { gs2124AccountEntry 2 }

gs2124AccountName OBJECT-TYPE
 SYNTAX  DisplayString
 MAX-ACCESS     read-write
 STATUS  current
 DESCRIPTION
  "This is the username of the account entry."
 ::= { gs2124AccountEntry 3 }

gs2124AccountPassword OBJECT-TYPE
 SYNTAX  DisplayString
 MAX-ACCESS     read-write
 STATUS  current
 DESCRIPTION
  "This is the password of the account entry. The return value is always '********'."
 ::= { gs2124AccountEntry 4 }

gs2124AccountAddAuthorization OBJECT-TYPE
 SYNTAX      INTEGER(0..2)
 MAX-ACCESS     read-write
 STATUS  current
 DESCRIPTION
  "Specify the limits of authority when add an account. 0:guest, 1:operator."
 ::= { gs2124Account 3 }

gs2124AccountAddName OBJECT-TYPE
 SYNTAX      DisplayString
 MAX-ACCESS     read-write
 STATUS  current
 DESCRIPTION
  "This is the account name for adding operation."
 ::= { gs2124Account 4 }

gs2124AccountAddPassword OBJECT-TYPE
 SYNTAX      DisplayString
 MAX-ACCESS     read-write
 STATUS  current
 DESCRIPTION
  "This is the account password for adding operation. The return value is always '********'."
 ::= { gs2124Account 5 }

gs2124DoAccountAdd OBJECT-TYPE
 SYNTAX      INTEGER(0|1)
 MAX-ACCESS     read-write
 STATUS  current
 DESCRIPTION
  "Add account name. OID gs2124AccountAddName and gs2124AccountAddPassword must be
        filled first. Get this OID always return zero.
            1 - add account.
            0 - do nothing."
 ::= { gs2124Account 6 }

gs2124AccountDel OBJECT-TYPE
 SYNTAX  INTEGER(2..5)
 MAX-ACCESS     read-write
 STATUS  current
 DESCRIPTION
  "Delete account. The value is valid gs2124AccountIndex(Can't delete administrator)."
 ::= { gs2124Account 7 }

gs2124Vsm            OBJECT IDENTIFIER ::= { gs2124System 5 }

gs2124VsmState OBJECT-TYPE
 SYNTAX  INTEGER(0|1)
 MAX-ACCESS     read-write
 STATUS  current
 DESCRIPTION
  "VSM state.
   0 - Disable
   1 - Enable"
 ::= { gs2124Vsm 1 }

gs2124VsmRole OBJECT-TYPE
 SYNTAX  INTEGER(0|1)
 MAX-ACCESS     read-write
 STATUS  current
 DESCRIPTION
  "VSM Role.
   0 - Slave
   1 - Master"
 ::= { gs2124Vsm 2 }

gs2124VsmGroupid OBJECT-TYPE
 SYNTAX      DisplayString
 MAX-ACCESS     read-write
 STATUS  current
 DESCRIPTION
  "VSM Group ID."
 ::= { gs2124Vsm 3 }



gs2124Snmp            OBJECT IDENTIFIER ::= { gs2124Produces 2 }

gs2124GetCommunity OBJECT-TYPE
 SYNTAX      DisplayString
 MAX-ACCESS     read-write
 STATUS  current
 DESCRIPTION
  "Get/Set the get-community of the SNMP."
 ::= { gs2124Snmp 1 }

gs2124SetCommunity OBJECT-TYPE
 SYNTAX      DisplayString
 MAX-ACCESS     read-write
 STATUS  current
 DESCRIPTION
  "Get/Set the set-community of the SNMP."
 ::= { gs2124Snmp 2 }

gs2124TrapHostNumber OBJECT-TYPE
 SYNTAX      INTEGER(1..6)
 MAX-ACCESS     read-only
 STATUS  current
 DESCRIPTION
  "Get the number of trap hosts."
 ::= { gs2124Snmp 3 }

gs2124TrapHostTable OBJECT-TYPE
 SYNTAX  SEQUENCE OF GS2124TrapHostEntry
 MAX-ACCESS not-accessible
 STATUS  current
 DESCRIPTION
  "A list of trap host entry. The numbers of entries are given by the value of gs2124TrapHostNumber."
    ::= { gs2124Snmp 4 }

GS2124TrapHostEntry ::=
SEQUENCE {
    gs2124TrapHostIndex      INTEGER,
    gs2124TrapHostIP           IpAddress,
    gs2124TrapHostPort            INTEGER,
    gs2124TrapHostCommunity       DisplayString
}

gs2124TrapHostEntry OBJECT-TYPE
 SYNTAX  GS2124TrapHostEntry
 MAX-ACCESS     not-accessible
 STATUS  current
 DESCRIPTION
  "This is the entry information for trap host."
 INDEX {gs2124TrapHostIndex}
 ::= { gs2124TrapHostTable 1 }

gs2124TrapHostIndex OBJECT-TYPE
 SYNTAX  INTEGER(1..6)
 MAX-ACCESS     read-only
 STATUS  current
 DESCRIPTION
  "The index of the trap host entry."
 ::= { gs2124TrapHostEntry 1 }

gs2124TrapHostIP OBJECT-TYPE
 SYNTAX  IpAddress
 MAX-ACCESS     read-write
 STATUS  current
 DESCRIPTION
  "This is the IP of the trap host."
 ::= { gs2124TrapHostEntry 2 }


gs2124TrapHostPort OBJECT-TYPE
 SYNTAX  INTEGER(1..65535)
 MAX-ACCESS     read-write
 STATUS  current
 DESCRIPTION
  "This is the receiving-port number of the trap host."
 ::= { gs2124TrapHostEntry 3 }


gs2124TrapHostCommunity OBJECT-TYPE
 SYNTAX  DisplayString
 MAX-ACCESS     read-write
 STATUS  current
 DESCRIPTION
  "The community name for the trap PDU."
 ::= { gs2124TrapHostEntry 4 }



gs2124Alarm            OBJECT IDENTIFIER ::= { gs2124Produces 3 }

gs2124Event            OBJECT IDENTIFIER ::= { gs2124Alarm 1 }

gs2124EventNumber OBJECT-TYPE
 SYNTAX      INTEGER(1..2147483647)
 MAX-ACCESS     read-only
 STATUS  current
 DESCRIPTION
  "Get the total number of alarm events."
 ::= { gs2124Event 1 }

gs2124EventTable OBJECT-TYPE
 SYNTAX  SEQUENCE OF GS2124EventEntry
 MAX-ACCESS not-accessible
 STATUS  current
    DESCRIPTION
        "This is a list of alarm event entry. The numbers of entries are given by the value of gs2124EventNumber."
 ::= { gs2124Event 2 }

GS2124EventEntry ::=
SEQUENCE {
    gs2124EventIndex      INTEGER,
    gs2124EventName           DisplayString,
    gs2124EventSendEmail      INTEGER,
    gs2124EventSendTrap       INTEGER
}

gs2124EventEntry OBJECT-TYPE
 SYNTAX  GS2124EventEntry
 MAX-ACCESS     not-accessible
 STATUS  current
 DESCRIPTION
  "This is the entry information for alarm event."
 INDEX {gs2124EventIndex}
 ::= { gs2124EventTable 1 }

gs2124EventIndex OBJECT-TYPE
 SYNTAX  INTEGER(1..2147483647)
 MAX-ACCESS     read-only
 STATUS  current
 DESCRIPTION
  "This is the index of the alarm event entry."
 ::= { gs2124EventEntry 1 }

gs2124EventName OBJECT-TYPE
 SYNTAX  DisplayString
 MAX-ACCESS     read-only
 STATUS  current
 DESCRIPTION
  "This is the alarm event name."
 ::= { gs2124EventEntry 2 }

gs2124EventSendEmail OBJECT-TYPE
 SYNTAX  INTEGER(0|1)
 MAX-ACCESS     read-write
 STATUS  current
 DESCRIPTION
  "Send email when alarm event is triggered."
 ::= { gs2124EventEntry 3 }

gs2124EventSendTrap OBJECT-TYPE
 SYNTAX  INTEGER(0|1)
 MAX-ACCESS     read-write
 STATUS  current
 DESCRIPTION
  "Send trap when alarm event is triggered."
 ::= { gs2124EventEntry 4 }




gs2124Email            OBJECT IDENTIFIER ::= { gs2124Alarm 2 }

gs2124EmailServer OBJECT-TYPE
 SYNTAX      DisplayString
 MAX-ACCESS     read-write
 STATUS  current
 DESCRIPTION
  "This is the SMTP server for alarm event."
 ::= { gs2124Email 1 }

gs2124EmailUsername OBJECT-TYPE
 SYNTAX      DisplayString
 MAX-ACCESS     read-write
 STATUS  current
 DESCRIPTION
  "This is the Username of SMTP server."
 ::= { gs2124Email 2 }

gs2124EmailPassword OBJECT-TYPE
 SYNTAX      DisplayString
 MAX-ACCESS     read-write
 STATUS  current
 DESCRIPTION
  "This is the User Password of SMTP server."
 ::= { gs2124Email 3 }

gs2124EmailSender OBJECT-TYPE
 SYNTAX      DisplayString
 MAX-ACCESS     read-write
 STATUS  current
 DESCRIPTION
  "This is the Sender of SMTP server."
 ::= { gs2124Email 4 }

gs2124EmailReturnPath OBJECT-TYPE
 SYNTAX      DisplayString
 MAX-ACCESS     read-write
 STATUS  current
 DESCRIPTION
  "This is the return path of mail."
 ::= { gs2124Email 5 }

gs2124EmailUserNumber OBJECT-TYPE
 SYNTAX      INTEGER(1..6)
 MAX-ACCESS     read-only
 STATUS  current
 DESCRIPTION
  "The number of the email users that you want to send the alarm notification."
 ::= { gs2124Email 6 }

gs2124EmailUserTable OBJECT-TYPE
 SYNTAX  SEQUENCE OF GS2124EmailUserEntry
 MAX-ACCESS not-accessible
 STATUS  current
    DESCRIPTION
        "This is a list of email user entry. The numbers of entries are given by the value of gs2124EmailUserNumber."
 ::= { gs2124Email 7 }

GS2124EmailUserEntry ::=
SEQUENCE {
    gs2124EmailUserIndex      INTEGER,
    gs2124EmailUserAddress        DisplayString
}

gs2124EmailUserEntry OBJECT-TYPE
 SYNTAX  GS2124EmailUserEntry
 MAX-ACCESS     not-accessible
 STATUS  current
 DESCRIPTION
  "This is the Entry information for email user entry."
 INDEX {gs2124EmailUserIndex}
 ::= { gs2124EmailUserTable 1 }

gs2124EmailUserIndex OBJECT-TYPE
 SYNTAX  INTEGER(1..6)
 MAX-ACCESS     read-only
 STATUS  current
 DESCRIPTION
  "This is the index of the email user entry."
 ::= { gs2124EmailUserEntry 1 }

gs2124EmailUserAddress OBJECT-TYPE
 SYNTAX  DisplayString
 MAX-ACCESS     read-write
 STATUS  current
 DESCRIPTION
  "This is the email address of the email user entry."
 ::= { gs2124EmailUserEntry 2 }

gs2124Configuration            OBJECT IDENTIFIER ::= { gs2124Produces 5 }

gs2124SaveRestore            OBJECT IDENTIFIER ::= { gs2124Configuration 1 }

gs2124SaveStart OBJECT-TYPE
 SYNTAX      INTEGER(0|1)
 MAX-ACCESS     read-write
 STATUS  current
 DESCRIPTION
  "Save current configuration into flash memory (Save as Start Configuration).
        Get this OID always return zero.
            1 - save.
            0 - do nothing. "
 ::= { gs2124SaveRestore 1 }

gs2124SaveUser OBJECT-TYPE
 SYNTAX      INTEGER(0|1)
 MAX-ACCESS     read-write
 STATUS  current
 DESCRIPTION
  "Save current configuration into flash memory (Save as User Configuration).
        Get this OID always return zero.
            1 - save.
            0 - do nothing. "
 ::= { gs2124SaveRestore 2 }

gs2124RestoreDefault OBJECT-TYPE
 SYNTAX      INTEGER(0|1|2)
 MAX-ACCESS     read-write
 STATUS  current
 DESCRIPTION
  "Restore factory default configuration.
        Get this OID always return zero.
            2 - restore default included default ip address.
            1 - restore default without changing current ip address.
            0 - do nothing. "
 ::= { gs2124SaveRestore 3 }

gs2124RestoreUser OBJECT-TYPE
 SYNTAX      INTEGER(0|1)
 MAX-ACCESS     read-write
 STATUS  current
 DESCRIPTION
  "Restore user configuration.
        Get this OID always return zero.
            1 - restore.
            0 - do nothing. "
 ::= { gs2124SaveRestore 4 }




gs2124ConfigFile            OBJECT IDENTIFIER ::= { gs2124Configuration 2 }

gs2124ExportIpAddress OBJECT-TYPE
 SYNTAX      IpAddress
 MAX-ACCESS     read-write
 STATUS  current
 DESCRIPTION
  "Get/Set the export tftp server."
 ::= { gs2124ConfigFile 1 }

gs2124DoExportConfig OBJECT-TYPE
 SYNTAX      INTEGER(1|2)
 MAX-ACCESS     read-write
 STATUS  current
 DESCRIPTION
  "Do export-config.
        Get this OID always return zero.
   1 - export current section.
   2 - export user section."
 ::= { gs2124ConfigFile 2 }

gs2124ImportIpAddress OBJECT-TYPE
 SYNTAX      IpAddress
 MAX-ACCESS     read-write
 STATUS  current
 DESCRIPTION
  "Get/Set the import tftp server."
 ::= { gs2124ConfigFile 3 }

gs2124ImportConfigName OBJECT-TYPE
 SYNTAX      DisplayString
 MAX-ACCESS     read-write
 STATUS  current
 DESCRIPTION
        "Get/Set the import file path and name."
 ::= { gs2124ConfigFile 4 }

gs2124DoImportConfig OBJECT-TYPE
 SYNTAX      INTEGER(1|2)
 MAX-ACCESS     read-write
 STATUS  current
 DESCRIPTION
  "Do import-config.
        Get this OID always return zero.
   1 - import current section.
   2 - import user section."
 ::= { gs2124ConfigFile 5 }




gs2124Log            OBJECT IDENTIFIER ::= { gs2124Produces 7 }

gs2124ClearLog OBJECT-TYPE
 SYNTAX      INTEGER(0|1)
 MAX-ACCESS     read-write
 STATUS  current
 DESCRIPTION
  "Clear system log.
        Get this OID always return zero.
            1 - clear log.
            0 - do nothing. "
 ::= { gs2124Log 1 }


gs2124LogNumber OBJECT-TYPE
 SYNTAX      INTEGER(0..120)
 MAX-ACCESS     read-only
 STATUS  current
 DESCRIPTION
  "Get the number of current system log. "
 ::= { gs2124Log 4 }

gs2124LogTable OBJECT-TYPE
 SYNTAX  SEQUENCE OF GS2124LogEntry
 MAX-ACCESS not-accessible
 STATUS  current
    DESCRIPTION
        "This is a list of log entry. The numbers of entries are given by the value of gs2124LogNumber."
 ::= { gs2124Log 5 }

GS2124LogEntry ::=
SEQUENCE {
    gs2124LogIndex      INTEGER,
    gs2124LogEvent            DisplayString
}

gs2124LogEntry OBJECT-TYPE
 SYNTAX  GS2124LogEntry
 MAX-ACCESS     not-accessible
 STATUS  current
 DESCRIPTION
  "This is the Entry information for system log."
 INDEX {gs2124LogIndex}
 ::= { gs2124LogTable 1 }

gs2124LogIndex OBJECT-TYPE
 SYNTAX  INTEGER(1..120)
 MAX-ACCESS     not-accessible
 STATUS  current
 DESCRIPTION
  "This is the index of the log entry."
 ::= { gs2124LogEntry 1 }

gs2124LogEvent OBJECT-TYPE
 SYNTAX  DisplayString
 MAX-ACCESS     read-only
 STATUS  current
 DESCRIPTION
  "This is the detail information of the log entry."
 ::= { gs2124LogEntry 2 }



gs2124Firmware            OBJECT IDENTIFIER ::= { gs2124Produces 8 }

gs2124FirmwareIpAddress OBJECT-TYPE
 SYNTAX      IpAddress
 MAX-ACCESS     read-write
 STATUS  current
 DESCRIPTION
  "Get/Set the firmware tftp server."
 ::= { gs2124Firmware 1 }

gs2124FirmwareFileName OBJECT-TYPE
 SYNTAX      DisplayString
 MAX-ACCESS     read-write
 STATUS  current
 DESCRIPTION
  "Get/Set the path and filename for firmware upgrading."
 ::= { gs2124Firmware 2 }

gs2124DoFirmwareUpgrade OBJECT-TYPE
 SYNTAX      INTEGER(0|1)
 MAX-ACCESS     read-write
 STATUS  current
 DESCRIPTION
  "Do firmware upgrade. Get this OID always return zero.
            1 - do firmware upgrade.
            0 - do nothing."
 ::= { gs2124Firmware 3 }



gs2124Port            OBJECT IDENTIFIER ::= { gs2124Produces 9 }

gs2124PortStatus            OBJECT IDENTIFIER ::= { gs2124Port 1 }

gs2124PortStatusNumber OBJECT-TYPE
 SYNTAX      INTEGER(1..2147483647)
 MAX-ACCESS     read-only
 STATUS  current
 DESCRIPTION
  "Get the number of port."
 ::= { gs2124PortStatus 1 }

gs2124PortStatusTable OBJECT-TYPE
 SYNTAX  SEQUENCE OF GS2124PortStatusEntry
 MAX-ACCESS not-accessible
 STATUS  current
    DESCRIPTION
        "This is a list of port status entry. The numbers of entries are given by the value of gs2124PortStatusNumber."
 ::= { gs2124PortStatus 2 }

GS2124PortStatusEntry ::=
SEQUENCE {
    gs2124PortStatusIndex     INTEGER,
    gs2124PortStatusMedia          DisplayString,
    gs2124PortStatusPortState      DisplayString,
    gs2124PortStatusLink           DisplayString,
    gs2124PortStatusAutoNego       DisplayString,
    gs2124PortStatusSpdDpx         DisplayString,
    gs2124PortStatusFlwCtrlRx      DisplayString,
    gs2124PortStatusFlwCtrlTx      DisplayString,
    gs2124PortStatuDescription     DisplayString
}

gs2124PortStatusEntry OBJECT-TYPE
 SYNTAX  GS2124PortStatusEntry
 MAX-ACCESS     not-accessible
 STATUS  current
 DESCRIPTION
  "This is the entry(s) for port status information."
 INDEX {gs2124PortStatusIndex}
 ::= { gs2124PortStatusTable 1 }

gs2124PortStatusIndex OBJECT-TYPE
 SYNTAX  INTEGER(1..2147483647)
 MAX-ACCESS     read-only
 STATUS  current
 DESCRIPTION
  "This is the index of the port status entry."
 ::= { gs2124PortStatusEntry 1 }

gs2124PortStatusMedia OBJECT-TYPE
 SYNTAX  DisplayString
 MAX-ACCESS     read-only
 STATUS  current
 DESCRIPTION
  "The port media type of the port status entry."
 ::= { gs2124PortStatusEntry 2 }

gs2124PortStatusPortState        OBJECT-TYPE
        SYNTAX                DisplayString
        MAX-ACCESS            read-only
        STATUS                current
        DESCRIPTION
                "This is the port state of the port status entry."
        ::= { gs2124PortStatusEntry 3 }

gs2124PortStatusLink OBJECT-TYPE
 SYNTAX  DisplayString
 MAX-ACCESS     read-only
 STATUS  current
 DESCRIPTION
  "This is the port link of the port status entry."
 ::= { gs2124PortStatusEntry 4 }

gs2124PortStatusAutoNego        OBJECT-TYPE
        SYNTAX                DisplayString
        MAX-ACCESS            read-only
        STATUS                current
        DESCRIPTION
                "This is the auto negotiation of the port status entry."
        ::= { gs2124PortStatusEntry 5 }

gs2124PortStatusSpdDpx  OBJECT-TYPE
 SYNTAX  DisplayString
 MAX-ACCESS     read-only
 STATUS  current
 DESCRIPTION
  "This is the speed/duplex of the port status entry."
 ::= { gs2124PortStatusEntry 6 }

gs2124PortStatusFlwCtrlRx  OBJECT-TYPE
 SYNTAX  DisplayString
 MAX-ACCESS     read-only
 STATUS  current
 DESCRIPTION
  "This is the Rx flow control of the port status entry."
 ::= { gs2124PortStatusEntry 7 }

gs2124PortStatusFlwCtrlTx  OBJECT-TYPE
 SYNTAX  DisplayString
 MAX-ACCESS     read-only
 STATUS  current
 DESCRIPTION
  "This is the Tx flow control of the port status entry."
 ::= { gs2124PortStatusEntry 8 }

gs2124PortStatuDescription OBJECT-TYPE
 SYNTAX  DisplayString
 MAX-ACCESS     read-only
 STATUS  current
 DESCRIPTION
  "This is the description of port."
 ::= { gs2124PortStatusEntry 9 }

gs2124PortConf            OBJECT IDENTIFIER ::= { gs2124Port 2 }

gs2124PortConfNumber OBJECT-TYPE
 SYNTAX      INTEGER(1..2147483647)
 MAX-ACCESS     read-only
 STATUS  current
 DESCRIPTION
  "Get the number of port configuration."
 ::= { gs2124PortConf 1 }

gs2124PortConfTable OBJECT-TYPE
 SYNTAX  SEQUENCE OF GS2124PortConfEntry
 MAX-ACCESS not-accessible
 STATUS  current
    DESCRIPTION
        "This is a list of port configuration entry. The numbers of entries are given by the value of gs2124PortConfNumber."
 ::= { gs2124PortConf 2 }

GS2124PortConfEntry ::=
SEQUENCE {
    gs2124PortConfIndex      INTEGER,
    gs2124PortConfPortState        INTEGER,
    gs2124PortConfTPSpdDpx         INTEGER,
    gs2124PortConfSFPSpdDpx        INTEGER,
    gs2124PortConfFlwCtrl          INTEGER,
    gs2124PortConfExcessiveCollisionMode      INTEGER,
    gs2124PortConfDescription      DisplayString,
    gs2124PortConfPowerSaving      INTEGER
}

gs2124PortConfEntry OBJECT-TYPE
 SYNTAX  GS2124PortConfEntry
 MAX-ACCESS     not-accessible
 STATUS  current
 DESCRIPTION
  "This is the Entry(s) for port configuration information."
 INDEX {gs2124PortConfIndex}
 ::= { gs2124PortConfTable 1 }

gs2124PortConfIndex OBJECT-TYPE
 SYNTAX  INTEGER(1..2147483647)
 MAX-ACCESS     read-only
 STATUS  current
 DESCRIPTION
  "This is the index of the port configuration entry."
 ::= { gs2124PortConfEntry 1 }

gs2124PortConfPortState OBJECT-TYPE
 SYNTAX  INTEGER(0|1)
 MAX-ACCESS     read-write
 STATUS  current
 DESCRIPTION
  "This is the port state of the port configuration entry.
   0 - disabled.
   1 - enabled. "
 ::= { gs2124PortConfEntry 2 }

gs2124PortConfTPSpdDpx OBJECT-TYPE
 SYNTAX  INTEGER(0..5)
 MAX-ACCESS     read-write
 STATUS  current
 DESCRIPTION
  "This is the speed/duplex of the TP port configuration entry.
   0 - auto.
   1 - 10M/Half.
   2 - 10M/Full.
   3 - 100M/Half.
   4 - 100M/Full.
   5 - 1G/Full.
   -1 - no support."
 ::= { gs2124PortConfEntry 3 }

gs2124PortConfSFPSpdDpx OBJECT-TYPE
 SYNTAX  INTEGER(0|5)
 MAX-ACCESS     read-write
 STATUS  current
 DESCRIPTION
  "This is the speed/duplex of the SFP port configuration entry.
   0 - auto.
   5 - 1G/Full.
   -1 - no support."
 ::= { gs2124PortConfEntry 4 }

gs2124PortConfFlwCtrl OBJECT-TYPE
 SYNTAX  INTEGER(0|1)
 MAX-ACCESS     read-write
 STATUS  current
 DESCRIPTION
  "This is the flow control of the port configuration entry.
   0 - disabled.
   1 - symmetric.
         2 - asymmetric(Tx).
         3 - symmetric & asymmetric(Rx)."
 ::= { gs2124PortConfEntry 5 }

gs2124PortConfExcessiveCollisionMode OBJECT-TYPE
 SYNTAX  INTEGER(0|1)
 MAX-ACCESS     read-write
 STATUS  current
 DESCRIPTION
  "Set excessive collision mode.
   0 - Discard.
   1 - Restart.  "
 ::= { gs2124PortConfEntry 6 }

gs2124PortConfDescription OBJECT-TYPE
 SYNTAX  DisplayString
 MAX-ACCESS     read-write
 STATUS  current
 DESCRIPTION
  "This is the description of port."
 ::= { gs2124PortConfEntry 7 }

gs2124PortConfPowerSaving OBJECT-TYPE
 SYNTAX  INTEGER(0|1)
 MAX-ACCESS     read-write
 STATUS  current
 DESCRIPTION
  "Set port power saving mode.
   0 - Disable.
   1 - Enable.  "
 ::= { gs2124PortConfEntry 8 }

gs2124SFPInfo            OBJECT IDENTIFIER ::= { gs2124Port 3 }

gs2124SFPInfoNumber OBJECT-TYPE
 SYNTAX      INTEGER(1..2147483647)
 MAX-ACCESS     read-only
 STATUS  current
 DESCRIPTION
  "Get the number of sfp info entry."
 ::= { gs2124SFPInfo 1 }

gs2124SFPInfoTable OBJECT-TYPE
 SYNTAX  SEQUENCE OF GS2124SFPInfoEntry
 MAX-ACCESS not-accessible
 STATUS  current
    DESCRIPTION
        "A list of sfp info entry. The numbers of entries are given by the value of gs2124SFPInfoNumber."
 ::= { gs2124SFPInfo 2 }

GS2124SFPInfoEntry ::=
SEQUENCE {
    gs2124SFPInfoIndex INTEGER,
    gs2124SFPConnectorType DisplayString,
    gs2124SFPFiberType DisplayString,
    gs2124SFPWavelength DisplayString,
    gs2124SFPBaudRate DisplayString,
    gs2124SFPVendorOUI DisplayString,
    gs2124SFPVendorName DisplayString,
    gs2124SFPVendorPN DisplayString,
    gs2124SFPVendorRev DisplayString,
    gs2124SFPVendorSN DisplayString,
    gs2124SFPDateCode DisplayString,
    gs2124SFPTemperature DisplayString,
    gs2124SFPVcc DisplayString,
    gs2124SFPTxBias DisplayString,
    gs2124SFPTxPWR DisplayString,
    gs2124SFPRxPWR DisplayString
}

gs2124SFPInfoEntry OBJECT-TYPE
 SYNTAX  GS2124SFPInfoEntry
 MAX-ACCESS     not-accessible
 STATUS  current
 DESCRIPTION
  "Entry(s) for SFP information."
 INDEX {gs2124SFPInfoIndex}
 ::= { gs2124SFPInfoTable 1 }

gs2124SFPInfoIndex OBJECT-TYPE
 SYNTAX  INTEGER(1..2147483647)
 MAX-ACCESS     read-only
 STATUS  current
 DESCRIPTION
  "The index of the sfp info entry."
 ::= { gs2124SFPInfoEntry 1 }

gs2124SFPConnectorType OBJECT-TYPE
 SYNTAX  DisplayString
 MAX-ACCESS     read-only
 STATUS  current
 DESCRIPTION
  "Get connector type of the sfp."
 ::= { gs2124SFPInfoEntry 2 }

gs2124SFPFiberType OBJECT-TYPE
 SYNTAX  DisplayString
 MAX-ACCESS     read-only
 STATUS  current
 DESCRIPTION
  "Get fiber type of the sfp."
 ::= { gs2124SFPInfoEntry 3 }

gs2124SFPWavelength OBJECT-TYPE
 SYNTAX  DisplayString
 MAX-ACCESS     read-only
 STATUS  current
 DESCRIPTION
  "Get tx central wavelength of the sfp."
 ::= { gs2124SFPInfoEntry 4 }

gs2124SFPBaudRate OBJECT-TYPE
 SYNTAX  DisplayString
 MAX-ACCESS     read-only
 STATUS  current
 DESCRIPTION
  "Get baud rate of the sfp."
 ::= { gs2124SFPInfoEntry 5 }

gs2124SFPVendorOUI OBJECT-TYPE
 SYNTAX  DisplayString
 MAX-ACCESS     read-only
 STATUS  current
 DESCRIPTION
  "Get vendor OUI of the sfp."
 ::= { gs2124SFPInfoEntry 6 }

gs2124SFPVendorName OBJECT-TYPE
 SYNTAX  DisplayString
 MAX-ACCESS     read-only
 STATUS  current
 DESCRIPTION
  "Get vendor name of the sfp."
 ::= { gs2124SFPInfoEntry 7 }

gs2124SFPVendorPN OBJECT-TYPE
 SYNTAX  DisplayString
 MAX-ACCESS     read-only
 STATUS  current
 DESCRIPTION
  "Get vendor part number of the sfp."
 ::= { gs2124SFPInfoEntry 8 }

gs2124SFPVendorRev OBJECT-TYPE
 SYNTAX  DisplayString
 MAX-ACCESS     read-only
 STATUS  current
 DESCRIPTION
  "Get vendor revision number of the sfp."
 ::= { gs2124SFPInfoEntry 9 }

gs2124SFPVendorSN OBJECT-TYPE
 SYNTAX  DisplayString
 MAX-ACCESS     read-only
 STATUS  current
 DESCRIPTION
  "Get vendor serial number of the sfp."
 ::= { gs2124SFPInfoEntry 10 }

gs2124SFPDateCode OBJECT-TYPE
 SYNTAX  DisplayString
 MAX-ACCESS     read-only
 STATUS  current
 DESCRIPTION
  "Get data code of the sfp."
 ::= { gs2124SFPInfoEntry 11 }

gs2124SFPTemperature OBJECT-TYPE
 SYNTAX  DisplayString
 MAX-ACCESS     read-only
 STATUS  current
 DESCRIPTION
  "Get current temperature of the sfp."
 ::= { gs2124SFPInfoEntry 12 }

gs2124SFPVcc OBJECT-TYPE
 SYNTAX  DisplayString
 MAX-ACCESS     read-only
 STATUS  current
 DESCRIPTION
  "Get current internal supply voltage of the sfp."
 ::= { gs2124SFPInfoEntry 13 }

gs2124SFPTxBias OBJECT-TYPE
 SYNTAX  DisplayString
 MAX-ACCESS     read-only
 STATUS  current
 DESCRIPTION
  "Get current TX Bias of the sfp."
 ::= { gs2124SFPInfoEntry 14 }

gs2124SFPTxPWR OBJECT-TYPE
 SYNTAX  DisplayString
 MAX-ACCESS     read-only
 STATUS  current
 DESCRIPTION
  "Get current TX output power of the sfp."
 ::= { gs2124SFPInfoEntry 15 }

gs2124SFPRxPWR OBJECT-TYPE
 SYNTAX  DisplayString
 MAX-ACCESS     read-only
 STATUS  current
 DESCRIPTION
  "Get current Received Power of the sfp."
 ::= { gs2124SFPInfoEntry 16 }

gs2124Mirror            OBJECT IDENTIFIER ::= { gs2124Produces 10 }

gs2124MirroringPort OBJECT-TYPE
 SYNTAX      INTEGER(0..2147483647)
 MAX-ACCESS     read-write
 STATUS  current
 DESCRIPTION
  "Get/Set the mirroring port.
   The port range is from 1 to 24."
 ::= { gs2124Mirror 1 }

gs2124MirroredPortsTable OBJECT-TYPE
 SYNTAX  SEQUENCE OF GS2124MirroredPortsEntry
 MAX-ACCESS not-accessible
 STATUS  current
    DESCRIPTION
        "This is a list of port configuration entry. The numbers of entries are given by the value of gs2124PortConfNumber."
 ::= { gs2124Mirror 2 }

GS2124MirroredPortsEntry ::=
SEQUENCE {
    gs2124MirroredPortIndex       INTEGER,
    gs2124MirroredPortSrouceEnable         INTEGER,
    gs2124MirroredPortDestinationEnable        INTEGER
}

gs2124MirroredPortsEntry OBJECT-TYPE
 SYNTAX  GS2124MirroredPortsEntry
 MAX-ACCESS     not-accessible
 STATUS  current
 DESCRIPTION
  "This is the Entry(s) for port configuration information."
 INDEX {gs2124MirroredPortIndex}
 ::= { gs2124MirroredPortsTable 1 }

gs2124MirroredPortIndex OBJECT-TYPE
 SYNTAX  INTEGER(1..24)
 MAX-ACCESS     read-only
 STATUS  current
 DESCRIPTION
  "This is the index of the mirrored port."
 ::= { gs2124MirroredPortsEntry 1 }

gs2124MirroredPortSrouceEnable OBJECT-TYPE
 SYNTAX  INTEGER(0|1)
 MAX-ACCESS     read-write
 STATUS  current
 DESCRIPTION
  "Set monitor source port.
   0 - disabled.
   1 - enabled."
 ::= { gs2124MirroredPortsEntry 2 }

gs2124MirroredPortDestinationEnable OBJECT-TYPE
 SYNTAX  INTEGER(0|1)
 MAX-ACCESS     read-write
 STATUS  current
 DESCRIPTION
  "Set monitor destination port.
   0 - disabled.
   1 - enabled."
 ::= { gs2124MirroredPortsEntry 3 }

gs2124MaxPktLen            OBJECT IDENTIFIER ::= { gs2124Produces 11 }

gs2124MaxPktLenPortNumber OBJECT-TYPE
 SYNTAX      INTEGER(1..24)
 MAX-ACCESS     read-only
 STATUS  current
 DESCRIPTION
  "Get the number of Max. packet length."
 ::= { gs2124MaxPktLen 1 }

gs2124MaxPktLenConfTable OBJECT-TYPE
 SYNTAX  SEQUENCE OF GS2124MaxPktLenConfEntry
 MAX-ACCESS not-accessible
 STATUS  current
    DESCRIPTION
        "This is a list of Max. packet length entry. The numbers of entries are given by the value of gs2124MaxPktLenPortNumber."
 ::= { gs2124MaxPktLen 2 }

GS2124MaxPktLenConfEntry ::=
SEQUENCE {
    gs2124MaxPktLenConfIndex      INTEGER,
    gs2124MaxPktLenConfSetting         INTEGER
}

gs2124MaxPktLenConfEntry OBJECT-TYPE
 SYNTAX  GS2124MaxPktLenConfEntry
 MAX-ACCESS     not-accessible
 STATUS  current
 DESCRIPTION
  "Entry(s) for Max. packet length information."
 INDEX {gs2124MaxPktLenConfIndex}
 ::= { gs2124MaxPktLenConfTable 1 }

gs2124MaxPktLenConfIndex OBJECT-TYPE
 SYNTAX  INTEGER(1..24)
 MAX-ACCESS     read-only
 STATUS  current
 DESCRIPTION
  "This is the index of the Max. packet length entry."
 ::= { gs2124MaxPktLenConfEntry 1 }

gs2124MaxPktLenConfSetting OBJECT-TYPE
 SYNTAX  INTEGER(1518..9600)
 MAX-ACCESS     read-write
 STATUS  current
 DESCRIPTION
  "Get/Set the Max. packet length.
   The Max. packet length is 1518~9600.  "
 ::= { gs2124MaxPktLenConfEntry 2 }

gs2124LoopDetectedConf            OBJECT IDENTIFIER ::= { gs2124Produces 12 }

gs2124LoopDetectedNumber OBJECT-TYPE
 SYNTAX      INTEGER(1..2147483647)
 MAX-ACCESS     read-only
 STATUS  current
 DESCRIPTION
  "Get the number of loop detected entry."
 ::= { gs2124LoopDetectedConf 1 }

gs2124LoopDetectedTable OBJECT-TYPE
 SYNTAX  SEQUENCE OF GS2124LoopDetectedEntry
 MAX-ACCESS not-accessible
 STATUS  current
    DESCRIPTION
        "A list of loop detected entry. The numbers of entries are given by the value of gs2124LoopDetectedNumber."
 ::= { gs2124LoopDetectedConf 2 }

GS2124LoopDetectedEntry ::=
SEQUENCE {
    gs2124LoopDetectedfIndex           INTEGER,
    gs2124LoopDetectedPort             INTEGER,
    gs2124LoopDetectedLockedPort       INTEGER
}

gs2124LoopDetectedEntry OBJECT-TYPE
 SYNTAX  GS2124LoopDetectedEntry
 MAX-ACCESS     not-accessible
 STATUS  current
 DESCRIPTION
  "Entry(s) for loop detected information."
 INDEX {gs2124LoopDetectedfIndex}
 ::= { gs2124LoopDetectedTable 1 }

gs2124LoopDetectedfIndex OBJECT-TYPE
 SYNTAX  INTEGER(1..2147483647)
 MAX-ACCESS     read-only
 STATUS  current
 DESCRIPTION
  "The index of the loop detected entry."
 ::= { gs2124LoopDetectedEntry 1 }

gs2124LoopDetectedPort OBJECT-TYPE
 SYNTAX  INTEGER(0|1)
 MAX-ACCESS     read-write
 STATUS  current
 DESCRIPTION
  "The state of the loop detected entry.
   0 - disabled.
   1 - enabled. "
 ::= { gs2124LoopDetectedEntry 2 }

gs2124LoopDetectedLockedPort OBJECT-TYPE
 SYNTAX  INTEGER(0|1)
 MAX-ACCESS     read-write
 STATUS  current
 DESCRIPTION
  "The current status of the loop detected port.
   Get:
         0 - unlocked
         1 - locked due to the loop condition
         Set:
         0 - unlock the port
         1 - do nothing"
 ::= { gs2124LoopDetectedEntry 3 }


gs2124ManagementPolicy            OBJECT IDENTIFIER ::= { gs2124Produces 13 }

gs2124ManagementSecurityNumber OBJECT-TYPE
 SYNTAX      INTEGER(0..64)
 MAX-ACCESS     read-only
 STATUS  current
 DESCRIPTION
  "This is the index of the management security entry."
 ::= { gs2124ManagementPolicy 1 }

gs2124ManagementSecurityEntryCreate OBJECT-TYPE
 SYNTAX      INTEGER(0..64)
 MAX-ACCESS     read-write
 STATUS  current
 DESCRIPTION
  "Create management security entry"
 ::= { gs2124ManagementPolicy 2 }

gs2124ManagementSecurityTable OBJECT-TYPE
 SYNTAX  SEQUENCE OF GS2124ManagementSecurityEntry
 MAX-ACCESS not-accessible
 STATUS  current
    DESCRIPTION
        "This is a list of GS2124ManagementSecurityEntry. The numbers of entries are given by ManagementSecurityNumber."
 ::= { gs2124ManagementPolicy 3 }

GS2124ManagementSecurityEntry ::=
SEQUENCE {
    gs2124ManagementSecurityIndex         INTEGER,
    gs2124ManagementSecurityName            DisplayString,
    gs2124ManagementSecurityIpRange         DisplayString,
    gs2124ManagementSecurityIncomigPort     DisplayString,
    gs2124ManagementSecurityAccessType      DisplayString,
    gs2124ManagementSecurityAction          INTEGER,
    gs2124ManagementSecurityEntryAction     INTEGER
}

gs2124ManagementSecurityEntry OBJECT-TYPE
 SYNTAX  GS2124ManagementSecurityEntry
 MAX-ACCESS     not-accessible
 STATUS  current
 DESCRIPTION
  "This is the Entry(s) for Management Security configuration information."
 INDEX {gs2124ManagementSecurityIndex}
 ::= { gs2124ManagementSecurityTable 1 }

gs2124ManagementSecurityIndex OBJECT-TYPE
 SYNTAX  INTEGER(1..64)
 MAX-ACCESS     read-only
 STATUS  current
 DESCRIPTION
  "This is the index of the management policy configuration entry."
 ::= { gs2124ManagementSecurityEntry 1 }

gs2124ManagementSecurityName OBJECT-TYPE
 SYNTAX  DisplayString
 MAX-ACCESS     read-write
 STATUS  current
 DESCRIPTION
  "This is the username of the management security entry."
 ::= { gs2124ManagementSecurityEntry 2 }

gs2124ManagementSecurityIpRange OBJECT-TYPE
 SYNTAX  DisplayString
 MAX-ACCESS     read-write
 STATUS  current
 DESCRIPTION
  "This is the ip range of the management security entry."
 ::= { gs2124ManagementSecurityEntry 3 }

gs2124ManagementSecurityIncomigPort OBJECT-TYPE
 SYNTAX  DisplayString
 MAX-ACCESS     read-write
 STATUS  current
 DESCRIPTION
  "This is the incoming port of the management security entry."
 ::= { gs2124ManagementSecurityEntry 4 }

gs2124ManagementSecurityAccessType OBJECT-TYPE
 SYNTAX  DisplayString
 MAX-ACCESS     read-write
 STATUS  current
 DESCRIPTION
  "Set management security access type.
   0 - any.
   1 - http.
   2 - telnet
   3 - snmp"
 ::= { gs2124ManagementSecurityEntry 5 }

gs2124ManagementSecurityAction OBJECT-TYPE
 SYNTAX  INTEGER(0|1)
 MAX-ACCESS     read-write
 STATUS  current
 DESCRIPTION
  "Set management security action.
   0 - deny.
   1 - accept."
 ::= { gs2124ManagementSecurityEntry 6 }

gs2124ManagementSecurityEntryAction OBJECT-TYPE
 SYNTAX  INTEGER(1..3)
 MAX-ACCESS     read-write
 STATUS  current
 DESCRIPTION
  "The row status of management security entry.
   1 - active.
   2 - notInService.
   3 - delete."
 ::= { gs2124ManagementSecurityEntry 7 }



gs2124VLAN            OBJECT IDENTIFIER ::= { gs2124Produces 14 }

gs2124VlanConf            OBJECT IDENTIFIER ::= { gs2124VLAN 1 }

gs2124VlanMode OBJECT-TYPE
 SYNTAX      INTEGER(0|1)
 MAX-ACCESS     read-write
 STATUS  current
 DESCRIPTION
  "This is the VLAN Mode configuration, default is tag base.
   0 - tag-base
   1 - port-base"
 ::= { gs2124VlanConf 1 }

gs2124ManagementVlan OBJECT-TYPE
 SYNTAX      INTEGER(1..4094)
 MAX-ACCESS     read-write
 STATUS  current
 DESCRIPTION
  "To specify a vlan id that can communicate with the device."
 ::= { gs2124VlanConf 2 }

gs2124PortIsolation OBJECT-TYPE
 SYNTAX      DisplayString
 MAX-ACCESS     read-write
 STATUS  current
 DESCRIPTION
  "Selected port(s) only can communicate with unselected port(s).
  Selected port(s) will be isolated with each other."
 ::= { gs2124VlanConf 3 }

gs2124TagIdentifier OBJECT-TYPE
 SYNTAX      INTEGER(0|1)
 MAX-ACCESS     read-write
 STATUS  current
 DESCRIPTION
  "Set double tag type.
  0: 0x8100
  1: 0x88a8"
 ::= { gs2124VlanConf 4 }

gs2124TagBaseVlanGroup         OBJECT IDENTIFIER ::= { gs2124VLAN 2 }

gs2124TagBaseVlanNumber OBJECT-TYPE
 SYNTAX      INTEGER(1..4094)
 MAX-ACCESS     read-write
 STATUS  current
 DESCRIPTION
  "The number of tagged-based VLAN."
 ::= { gs2124TagBaseVlanGroup 1 }

gs2124TagBaseVlanGroupEntryCreate OBJECT-TYPE
 SYNTAX      INTEGER(0..4094)
 MAX-ACCESS     read-write
 STATUS  current
 DESCRIPTION
  "To create a VLAN entry in the tagged-based VLAN table.
         0 : none,
         1~4094 : specify the vid of the created VLAN."
 ::= { gs2124TagBaseVlanGroup 2 }

gs2124TagBaseVlanGroupTable OBJECT-TYPE
 SYNTAX  SEQUENCE OF GS2124TagBaseVlanGroupEntry
 MAX-ACCESS not-accessible
 STATUS  current
    DESCRIPTION
        "A list of tagged-based VLAN group entry. The number of entries can be taken from gs2124TagBaseVlanNumber."
 ::= { gs2124TagBaseVlanGroup 3 }

GS2124TagBaseVlanGroupEntry ::=
SEQUENCE {
    gs2124TagBaseVlanVid          INTEGER,
    gs2124TagBaseVlanName          DisplayString,
    gs2124TagBaseVlanIgmpProxy     INTEGER,
    gs2124TagBaseVlanPrivateVlan   INTEGER,
    gs2124TagBaseVlanGvrp     INTEGER,
    gs2124TagBaseVlanMemberPort    DisplayString,
    gs2124TagBaseVlanEntryAction   INTEGER
}

gs2124TagBaseVlanGroupEntry OBJECT-TYPE
 SYNTAX  GS2124TagBaseVlanGroupEntry
 MAX-ACCESS     not-accessible
 STATUS  current
 DESCRIPTION
  "This is the Entry(s) for Tag Base VLAN Group configuration information."
 INDEX {gs2124TagBaseVlanVid}
 ::= { gs2124TagBaseVlanGroupTable 1 }

gs2124TagBaseVlanVid OBJECT-TYPE
 SYNTAX  INTEGER(1..4094)
 MAX-ACCESS     not-accessible
 STATUS  current
 DESCRIPTION
  "This is the index of the Tag Base VLAN Group configuration entry."
 ::= { gs2124TagBaseVlanGroupEntry 1 }

gs2124TagBaseVlanName OBJECT-TYPE
 SYNTAX  DisplayString
 MAX-ACCESS     read-write
 STATUS  current
 DESCRIPTION
  "This is the name of the VLAN."
 ::= { gs2124TagBaseVlanGroupEntry 2 }

gs2124TagBaseVlanIgmpProxy OBJECT-TYPE
 SYNTAX  INTEGER(0|1)
 MAX-ACCESS     read-write
 STATUS  current
 DESCRIPTION
  "To support IGMP proxy in this VLAN.
   0 - Disable
   1 - Enable"
 ::= { gs2124TagBaseVlanGroupEntry 3 }

gs2124TagBaseVlanPrivateVlan OBJECT-TYPE
 SYNTAX  INTEGER(0|1)
 MAX-ACCESS     read-write
 STATUS  current
 DESCRIPTION
  "To apply the port isolation configuration.
   0 - Disable
   1 - Enable"
 ::= { gs2124TagBaseVlanGroupEntry 4 }

gs2124TagBaseVlanGvrp OBJECT-TYPE
 SYNTAX  INTEGER(0|1)
 MAX-ACCESS     read-write
 STATUS  current
 DESCRIPTION
  "This VLAN can be propagated by gvrp.
   0 - Disable
   1 - Enable"
 ::= { gs2124TagBaseVlanGroupEntry 5 }

gs2124TagBaseVlanMemberPort OBJECT-TYPE
 SYNTAX  DisplayString
 MAX-ACCESS     read-write
 STATUS  current
 DESCRIPTION
  "The member port(s) of this VLAN."
 ::= { gs2124TagBaseVlanGroupEntry 6 }

gs2124TagBaseVlanEntryAction OBJECT-TYPE
 SYNTAX  INTEGER(1..3)
 MAX-ACCESS     read-write
 STATUS  current
 DESCRIPTION
  "The row status of VLAN.
   1 - active
   2 - notInService
   3 - delete"
 ::= { gs2124TagBaseVlanGroupEntry 7 }

gs2124VlanPortConfTable OBJECT-TYPE
 SYNTAX  SEQUENCE OF GS2124VlanPortConfEntry
 MAX-ACCESS not-accessible
 STATUS  current
    DESCRIPTION
        "This is the port parameters for tagged-based VLAN."
 ::= { gs2124VLAN 3 }

GS2124VlanPortConfEntry ::=
SEQUENCE {
    gs2124VlanPortConfIndex              INTEGER,
    gs2124VlanPortConfVlanAware            INTEGER,
    gs2124VlanPortConfIngressFiltering     INTEGER,
    gs2124VlanPortConfFrameType            INTEGER,
    gs2124VlanPortConfPvid                 INTEGER,
    gs2124VlanPortConfRole                 INTEGER,
    gs2124VlanPortConfUntagVid             INTEGER,
    gs2124VlanPortConfDoubleTag            INTEGER
}

gs2124VlanPortConfEntry OBJECT-TYPE
 SYNTAX  GS2124VlanPortConfEntry
 MAX-ACCESS     not-accessible
 STATUS  current
 DESCRIPTION
  "These are the tagged-based VLAN parameters for each ports."
 INDEX {gs2124VlanPortConfIndex}
 ::= { gs2124VlanPortConfTable 1 }

gs2124VlanPortConfIndex OBJECT-TYPE
 SYNTAX  INTEGER(1..24)
 MAX-ACCESS     not-accessible
 STATUS  current
 DESCRIPTION
  "This is the index of the Port Base VLAN Group configuration entry."
 ::= { gs2124VlanPortConfEntry 1 }

gs2124VlanPortConfVlanAware OBJECT-TYPE
 SYNTAX  INTEGER(0|1)
 MAX-ACCESS     read-write
 STATUS  current
 DESCRIPTION
  "Set vlan awareness.
   0 - Ignore incoming VLAN tag, using pvid as VLAN classification.
   1 - Using VLAN tag information first."
 ::= { gs2124VlanPortConfEntry 2 }

gs2124VlanPortConfIngressFiltering OBJECT-TYPE
 SYNTAX  INTEGER(0|1)
 MAX-ACCESS     read-write
 STATUS  current
 DESCRIPTION
  "If the packet is tagged with VLAN information, the ingress port will first determine if the
   ingress port itself is a member of the tagged VLAN.
   0 - Disable, don't care about the VLAN information of the packet.
   1 - Enable."
 ::= { gs2124VlanPortConfEntry 3 }

gs2124VlanPortConfFrameType OBJECT-TYPE
 SYNTAX  INTEGER(0|1)
 MAX-ACCESS     read-write
 STATUS  current
 DESCRIPTION
  "To determine what kind of packet the port should accept.
   0 - All
   1 - Only tagged packet"
 ::= { gs2124VlanPortConfEntry 4 }

gs2124VlanPortConfPvid OBJECT-TYPE
 SYNTAX  INTEGER(1..4094)
 MAX-ACCESS     read-write
 STATUS  current
 DESCRIPTION
  "Each physical port has a parameter called PVID.
  All untagged frames are assigned to the LAN specified in the PVID parameter.
  When a tagged frame is received by a port, the tag is respected.
  If the frame is untagged, the value contained in the PVID is considered as a tag. "
 ::= { gs2124VlanPortConfEntry 5 }

gs2124VlanPortConfRole OBJECT-TYPE
 SYNTAX  INTEGER(0..2)
 MAX-ACCESS     read-write
 STATUS  current
 DESCRIPTION
  "Set egress rule: configure the port role.
   0 - Access: won't send packet with tag.
   1 - Trunk: always send packet with tag.
   2 - Hybrid: always send packet with tag but one."
 ::= { gs2124VlanPortConfEntry 6 }

gs2124VlanPortConfUntagVid OBJECT-TYPE
 SYNTAX  INTEGER(1..4094)
 MAX-ACCESS     read-write
 STATUS  current
 DESCRIPTION
  "Won't send packet with tag in one specific vid. Only available in hybrid mode.
   "
 ::= { gs2124VlanPortConfEntry 7 }

gs2124VlanPortConfDoubleTag OBJECT-TYPE
 SYNTAX  INTEGER(0..2)
 MAX-ACCESS     read-write
 STATUS  current
 DESCRIPTION
  "This is the double tag configuration for ports.
   0 -- Disable,
    1 -- Service,
    2 -- Customer
   "
 ::= { gs2124VlanPortConfEntry 8 }

gs2124PortBaseVlanGroup         OBJECT IDENTIFIER ::= { gs2124VLAN 4 }

gs2124PortBaseVlanNumber OBJECT-TYPE
 SYNTAX      INTEGER(1..24)
 MAX-ACCESS     read-write
 STATUS  current
 DESCRIPTION
  "Total numbers for port based vlan."
 ::= { gs2124PortBaseVlanGroup 1 }

gs2124PortBaseVlanGroupEntryCreate OBJECT-TYPE
 SYNTAX      INTEGER(0..24)
 MAX-ACCESS     read-write
 STATUS  current
 DESCRIPTION
  "Create a temp vlan in port-based vlan table.
         0 : none,
         1 : create a new port-based vlan."
 ::= { gs2124PortBaseVlanGroup 2 }

gs2124PortBaseVlanGroupTable OBJECT-TYPE
 SYNTAX  SEQUENCE OF GS2124PortBaseVlanGroupEntry
 MAX-ACCESS not-accessible
 STATUS  current
    DESCRIPTION
        "A list of port base vlan group entry. The numbers of entries are given by the value of gs2124PortBaseVlanNumber."
 ::= { gs2124PortBaseVlanGroup 3 }

GS2124PortBaseVlanGroupEntry ::=
SEQUENCE {
    gs2124PortBaseVlanGroupIndex        INTEGER,
    gs2124PortBaseVlanGroupName          DisplayString,
    gs2124PortBaseVlanGroupMembers       DisplayString,
    gs2124PortBaseVlanGroupEntryAction   INTEGER
}

gs2124PortBaseVlanGroupEntry OBJECT-TYPE
 SYNTAX  GS2124PortBaseVlanGroupEntry
 MAX-ACCESS     not-accessible
 STATUS  current
 DESCRIPTION
  "This is the Entry(s) for Port Base VLAN Group configuration information."
 INDEX {gs2124PortBaseVlanGroupIndex}
 ::= { gs2124PortBaseVlanGroupTable 1 }

gs2124PortBaseVlanGroupIndex OBJECT-TYPE
 SYNTAX  INTEGER(1..24)
 MAX-ACCESS     not-accessible
 STATUS  current
 DESCRIPTION
  "This is the index of the Port Base VLAN Group configuration entry."
 ::= { gs2124PortBaseVlanGroupEntry 1 }

gs2124PortBaseVlanGroupName OBJECT-TYPE
 SYNTAX  DisplayString
 MAX-ACCESS     read-write
 STATUS  current
 DESCRIPTION
  "The name of vlan."
 ::= { gs2124PortBaseVlanGroupEntry 2 }

gs2124PortBaseVlanGroupMembers OBJECT-TYPE
 SYNTAX  DisplayString
 MAX-ACCESS     read-write
 STATUS  current
 DESCRIPTION
  "The member of vlan."
 ::= { gs2124PortBaseVlanGroupEntry 3 }

gs2124PortBaseVlanGroupEntryAction OBJECT-TYPE
 SYNTAX  INTEGER(1..3)
 MAX-ACCESS     read-write
 STATUS  current
 DESCRIPTION
  "The row status of vlan.
   1 - active
   2 - notInService
   3 - delete"
 ::= { gs2124PortBaseVlanGroupEntry 4 }

gs2124MacTableInfo            OBJECT IDENTIFIER ::= { gs2124Produces 15 }

gs2124MacTableConf            OBJECT IDENTIFIER ::= { gs2124MacTableInfo 1 }

gs2124MacAgeTime OBJECT-TYPE
 SYNTAX      INTEGER(10..1000000)
 MAX-ACCESS     read-write
 STATUS  current
 DESCRIPTION
  "Set the Mac Table Aging Time (10~1000000 Secs).
         0 : Disable."
 ::= { gs2124MacTableConf 1 }

gs2124MacTableLearningConfTable OBJECT-TYPE
 SYNTAX  SEQUENCE OF GS2124MacTableLearningConfEntry
 MAX-ACCESS not-accessible
 STATUS  current
    DESCRIPTION
        "A list of Mac Learning entry."
 ::= { gs2124MacTableConf 2 }

GS2124MacTableLearningConfEntry ::=
SEQUENCE {
    gs2124MacTableLearningConfIndex   INTEGER,
    gs2124MacTableLearningConfstate   INTEGER
}

gs2124MacTableLearningConfEntry OBJECT-TYPE
 SYNTAX  GS2124MacTableLearningConfEntry
 MAX-ACCESS     not-accessible
 STATUS  current
 DESCRIPTION
  "This is the Entry(s) for Mac Learning table information."
 INDEX {gs2124MacTableLearningConfIndex}
 ::= { gs2124MacTableLearningConfTable 1 }

gs2124MacTableLearningConfIndex OBJECT-TYPE
 SYNTAX  INTEGER(1..24)
 MAX-ACCESS     not-accessible
 STATUS  current
 DESCRIPTION
  "This is the index of the Learning MAC Table Group configuration entry."
 ::= { gs2124MacTableLearningConfEntry 1 }

gs2124MacTableLearningConfstate OBJECT-TYPE
 SYNTAX  INTEGER(0|1|2)
 MAX-ACCESS     read-write
 STATUS  current
 DESCRIPTION
  "Set mac table learning.
   0 - Auto
   1 - Disable
   2 - Secure"
 ::= { gs2124MacTableLearningConfEntry 2 }

gs2124MacTableStaticFilter            OBJECT IDENTIFIER ::= { gs2124MacTableInfo 2 }

gs2124MacTableStaticFilterNumber OBJECT-TYPE
 SYNTAX      INTEGER(0..512)
 MAX-ACCESS     read-only
 STATUS  current
 DESCRIPTION
  "Total numbers for static filter entry of Mac Table."
 ::= { gs2124MacTableStaticFilter 1 }

gs2124MacTableStaticFilterEntryCreate OBJECT-TYPE
 SYNTAX      INTEGER(0..512)
 MAX-ACCESS     read-write
 STATUS  current
 DESCRIPTION
  "Create a temp Filter entry in Mac Table.
         0 : none,
         1 : create a new entry"
 ::= { gs2124MacTableStaticFilter 2 }

gs2124MacTableStaticFilterTable OBJECT-TYPE
 SYNTAX  SEQUENCE OF GS2124MacTableStaticFilterEntry
 MAX-ACCESS not-accessible
 STATUS  current
    DESCRIPTION
        "A list of static filter entry. The numbers of entries are given by the value of gs2124MacTableStaticFilterNumber."
 ::= { gs2124MacTableStaticFilter 3 }

GS2124MacTableStaticFilterEntry ::=
SEQUENCE {
    gs2124MacTableStaticFilterIndex         INTEGER,
    gs2124MacTableStaticFilterMac           DisplayString,
    gs2124MacTableStaticFilterVid           INTEGER,
    gs2124MacTableStaticFilterAlias         DisplayString,
    gs2124MacTableStaticFilterEntryAction   INTEGER
}

gs2124MacTableStaticFilterEntry OBJECT-TYPE
 SYNTAX  GS2124MacTableStaticFilterEntry
 MAX-ACCESS     not-accessible
 STATUS  current
 DESCRIPTION
  "This is the Entry(s) for static filter information."
 INDEX {gs2124MacTableStaticFilterIndex}
 ::= { gs2124MacTableStaticFilterTable 1 }

gs2124MacTableStaticFilterIndex OBJECT-TYPE
 SYNTAX  INTEGER(1..512)
 MAX-ACCESS     not-accessible
 STATUS  current
 DESCRIPTION
  "This is the index of the Static Filter MAC Table Group configuration entry."
 ::= { gs2124MacTableStaticFilterEntry 1 }

gs2124MacTableStaticFilterMac OBJECT-TYPE
 SYNTAX  DisplayString
 MAX-ACCESS     read-write
 STATUS  current
 DESCRIPTION
  "The static filter mac in Mac Table"
 ::= { gs2124MacTableStaticFilterEntry 2 }

gs2124MacTableStaticFilterVid OBJECT-TYPE
 SYNTAX  INTEGER(1..4094)
 MAX-ACCESS     read-write
 STATUS  current
 DESCRIPTION
  "The filter vid in Mac Table"
 ::= { gs2124MacTableStaticFilterEntry 3 }

gs2124MacTableStaticFilterAlias OBJECT-TYPE
 SYNTAX  DisplayString
 MAX-ACCESS     read-write
 STATUS  current
 DESCRIPTION
  "The filter alias name in Mac Table"
 ::= { gs2124MacTableStaticFilterEntry 4 }

gs2124MacTableStaticFilterEntryAction OBJECT-TYPE
 SYNTAX  INTEGER(1..3)
 MAX-ACCESS     read-write
 STATUS  current
 DESCRIPTION
  "The row status of filter entry.
   1 - active
   2 - notInService
   3 - delete"
 ::= { gs2124MacTableStaticFilterEntry 5 }

gs2124MacTableStaticForward            OBJECT IDENTIFIER ::= { gs2124MacTableInfo 3 }

gs2124MacTableStaticForwardNumber OBJECT-TYPE
 SYNTAX      INTEGER(0..512)
 MAX-ACCESS     read-only
 STATUS  current
 DESCRIPTION
  "Total numbers for static forward entry of Mac Table."
 ::= { gs2124MacTableStaticForward 1 }

gs2124MacTableStaticForwardEntryCreate OBJECT-TYPE
 SYNTAX      INTEGER(0..512)
 MAX-ACCESS     read-write
 STATUS  current
 DESCRIPTION
  "Create a temp forward entry in Mac Table.
         0 : none,
         1 : create a new entry"
 ::= { gs2124MacTableStaticForward 2 }

gs2124MacTableStaticForwardTable OBJECT-TYPE
 SYNTAX  SEQUENCE OF GS2124MacTableStaticForwardEntry
 MAX-ACCESS not-accessible
 STATUS  current
    DESCRIPTION
        "A list of static forward entry. The numbers of entries are given by the value of gs2124MacTableStaticForwardNumber."
 ::= { gs2124MacTableStaticForward 3 }

GS2124MacTableStaticForwardEntry ::=
SEQUENCE {
    gs2124MacTableStaticForwardIndex         INTEGER,
    gs2124MacTableStaticForwardMac           DisplayString,
    gs2124MacTableStaticForwardPort          INTEGER,
    gs2124MacTableStaticForwardVid           INTEGER,
    gs2124MacTableStaticForwardAlias         DisplayString,
    gs2124MacTableStaticForwardEntryAction   INTEGER
}

gs2124MacTableStaticForwardEntry OBJECT-TYPE
 SYNTAX  GS2124MacTableStaticForwardEntry
 MAX-ACCESS     not-accessible
 STATUS  current
 DESCRIPTION
  "A list of static forwarding table entry."
 INDEX {gs2124MacTableStaticForwardIndex}
 ::= { gs2124MacTableStaticForwardTable 1 }

gs2124MacTableStaticForwardIndex OBJECT-TYPE
 SYNTAX  INTEGER(1..512)
 MAX-ACCESS     not-accessible
 STATUS  current
 DESCRIPTION
  "This is the index of the Static Forward MAC Table Group configuration entry."
 ::= { gs2124MacTableStaticForwardEntry 1 }

gs2124MacTableStaticForwardMac OBJECT-TYPE
 SYNTAX  DisplayString
 MAX-ACCESS     read-write
 STATUS  current
 DESCRIPTION
  "The static forwarding Mac in Mac Table"
 ::= { gs2124MacTableStaticForwardEntry 2 }

gs2124MacTableStaticForwardPort OBJECT-TYPE
 SYNTAX  INTEGER(1..24)
 MAX-ACCESS     read-write
 STATUS  current
 DESCRIPTION
  "To specify a destination port for a mac address in mac table."
 ::= { gs2124MacTableStaticForwardEntry 3 }

gs2124MacTableStaticForwardVid OBJECT-TYPE
 SYNTAX  INTEGER(1..4094)
 MAX-ACCESS     read-write
 STATUS  current
 DESCRIPTION
  "To specify a VLAN ID for a mac address in mac table."
 ::= { gs2124MacTableStaticForwardEntry 4 }

gs2124MacTableStaticForwardAlias OBJECT-TYPE
 SYNTAX  DisplayString
 MAX-ACCESS     read-write
 STATUS  current
 DESCRIPTION
  "To specify an alias for a mac address in mac table."
 ::= { gs2124MacTableStaticForwardEntry 5 }

gs2124MacTableStaticForwardEntryAction OBJECT-TYPE
 SYNTAX  INTEGER(1..3)
 MAX-ACCESS     read-write
 STATUS  current
 DESCRIPTION
  "The row status of filter entry.
   1 - active
   2 - notInService
   3 - delete"
 ::= { gs2124MacTableStaticForwardEntry 6 }

gs2124MacAlias            OBJECT IDENTIFIER ::= { gs2124MacTableInfo 4 }

gs2124MacAliasNumber OBJECT-TYPE
 SYNTAX      INTEGER(0..1024)
 MAX-ACCESS     read-only
 STATUS  current
 DESCRIPTION
  "Mac Alias Total Number(0~1024)."
 ::= { gs2124MacAlias 1 }

gs2124MacAliasEntryCreate OBJECT-TYPE
 SYNTAX      INTEGER(0..1024)
 MAX-ACCESS     read-only
 STATUS  current
 DESCRIPTION
  "Create a temp Mac alias entry in Mac Table.
         0 : none,
         1 : create a new entry"
 ::= { gs2124MacAlias 2 }

gs2124MacAliasTable OBJECT-TYPE
 SYNTAX  SEQUENCE OF GS2124MacAliasEntry
 MAX-ACCESS not-accessible
 STATUS  current
    DESCRIPTION
        "A list of Mac Alias entry. The numbers of entries are given by the value of gs2124MacAliasNumber."
 ::= { gs2124MacAlias 3 }

GS2124MacAliasEntry ::=
SEQUENCE {
    gs2124MacAliasIndex         INTEGER,
    gs2124AliasMac              DisplayString,
    gs2124AliasName             DisplayString,
    gs2124MacAliasEntryAction   INTEGER
}

gs2124MacAliasEntry OBJECT-TYPE
 SYNTAX  GS2124MacAliasEntry
 MAX-ACCESS     not-accessible
 STATUS  current
 DESCRIPTION
  "Entry(s) for Mac Alias."
 INDEX {gs2124MacAliasIndex}
 ::= { gs2124MacAliasTable 1 }

gs2124MacAliasIndex OBJECT-TYPE
 SYNTAX  INTEGER(1..1024)
 MAX-ACCESS     not-accessible
 STATUS  current
 DESCRIPTION
  "The index of the static mac alias entry."
 ::= { gs2124MacAliasEntry 1 }

gs2124AliasMac OBJECT-TYPE
 SYNTAX  DisplayString
 MAX-ACCESS     read-write
 STATUS  current
 DESCRIPTION
  "The Mac of the static mac alias entry."
 ::= { gs2124MacAliasEntry 2 }

gs2124AliasName OBJECT-TYPE
 SYNTAX  DisplayString
 MAX-ACCESS     read-write
 STATUS  current
 DESCRIPTION
  "The alias name of the static mac alias entry."
 ::= { gs2124MacAliasEntry 3 }

gs2124MacAliasEntryAction OBJECT-TYPE
 SYNTAX  INTEGER(1..3)
 MAX-ACCESS     read-write
 STATUS  current
 DESCRIPTION
  "The row status of mac alias entry.
   1 - active
   2 - notInService
   3 - delete"
 ::= { gs2124MacAliasEntry 4 }


gs2124GVRPInfo            OBJECT IDENTIFIER ::= { gs2124Produces 16 }

gs2124GvrpConf            OBJECT IDENTIFIER ::= { gs2124GVRPInfo 1 }

gs2124GvrpConfState OBJECT-TYPE
 SYNTAX      INTEGER(0|1)
 MAX-ACCESS     read-write
 STATUS  current
 DESCRIPTION
  "The GVRP state
   0 - Disable
   1 - Enable
    "
 ::= { gs2124GvrpConf 1 }

gs2124GvrpConfTable OBJECT-TYPE
 SYNTAX  SEQUENCE OF GS2124GvrpConfEntry
 MAX-ACCESS not-accessible
 STATUS  current
    DESCRIPTION
        "A list of GVRP entry."
 ::= { gs2124GvrpConf 2 }

GS2124GvrpConfEntry ::=
SEQUENCE {
    gs2124GvrpConfIndex             INTEGER,
    gs2124GvrpConfJoinTime          INTEGER,
    gs2124GvrpConfLeaveTime         INTEGER,
    gs2124GvrpConfLeaveAllTime      INTEGER,
    gs2124GvrpConfDefaultAppMode    INTEGER,
    gs2124GvrpConfDefaultRegMode    INTEGER,
    gs2124GvrpConfRestrictedMode    INTEGER
}

gs2124GvrpConfEntry OBJECT-TYPE
 SYNTAX  GS2124GvrpConfEntry
 MAX-ACCESS     not-accessible
 STATUS  current
 DESCRIPTION
  "This is the Entry(s) for gvrp information."
 INDEX {gs2124GvrpConfIndex}
 ::= { gs2124GvrpConfTable 1 }

gs2124GvrpConfIndex OBJECT-TYPE
 SYNTAX  INTEGER(1..24)
 MAX-ACCESS     not-accessible
 STATUS  current
 DESCRIPTION
  "This is the index of the gvrp entry."
 ::= { gs2124GvrpConfEntry 1 }

gs2124GvrpConfJoinTime OBJECT-TYPE
 SYNTAX  INTEGER(20..100)
 MAX-ACCESS     read-write
 STATUS  current
 DESCRIPTION
  "This is the join-time of the gvrp entry."
 ::= { gs2124GvrpConfEntry 2 }

gs2124GvrpConfLeaveTime OBJECT-TYPE
 SYNTAX  INTEGER(60..300)
 MAX-ACCESS     read-write
 STATUS  current
 DESCRIPTION
  "This is the leave-time of the gvrp entry.
  default:60 centisecond"
 ::= { gs2124GvrpConfEntry 3 }

gs2124GvrpConfLeaveAllTime OBJECT-TYPE
 SYNTAX  INTEGER(1000..5000)
 MAX-ACCESS     read-write
 STATUS  current
 DESCRIPTION
  "Set GVRP leave_all_time.
   default: 1000 unit time"
 ::= { gs2124GvrpConfEntry 4 }

gs2124GvrpConfDefaultAppMode OBJECT-TYPE
 SYNTAX  INTEGER(0|1)
 MAX-ACCESS     read-write
 STATUS  current
 DESCRIPTION
  "Set GVRP applicant.
   [default: Normal]
   0 - Normal
   1 - Non-Participant"
 ::= { gs2124GvrpConfEntry 5 }

gs2124GvrpConfDefaultRegMode OBJECT-TYPE
 SYNTAX  INTEGER(0|1|2)
 MAX-ACCESS     read-write
 STATUS  current
 DESCRIPTION
  "Set GVRP registrar.
   [default: Normal]
   0 - Normal
   1 - Fixed
   2 - Forbidden"
 ::= { gs2124GvrpConfEntry 6 }

gs2124GvrpConfRestrictedMode OBJECT-TYPE
 SYNTAX  INTEGER(0|1)
 MAX-ACCESS     read-write
 STATUS  current
 DESCRIPTION
  "Set GVRP restricted.
   [default: Disable]
   0 - Disable
   1 - Enable"
 ::= { gs2124GvrpConfEntry 7 }

gs2124GvrpCounter            OBJECT IDENTIFIER ::= { gs2124GVRPInfo 2 }

gs2124GvrpCounterTable OBJECT-TYPE
 SYNTAX  SEQUENCE OF GS2124GvrpCounterEntry
 MAX-ACCESS not-accessible
 STATUS  current
    DESCRIPTION
        "This is a list of GS2124GvrpCounterEntry."
 ::= { gs2124GvrpCounter 1 }

GS2124GvrpCounterEntry ::=
SEQUENCE {
    gs2124GvrpCounterIndex              INTEGER,
    gs2124GvrpCounterRxTotalGvrpPkts    Counter32,
    gs2124GvrpCounterRxInvalidGvrpPkts  Counter32,
    gs2124GvrpCounterRxLeaveAllMsg      Counter32,
    gs2124GvrpCounterRxJoinEmptyMsg     Counter32,
    gs2124GvrpCounterRxJoinInMsg        Counter32,
    gs2124GvrpCounterRxLeaveEmptyMsg    Counter32,
    gs2124GvrpCounterRxEmptyMsg         Counter32,
    gs2124GvrpCounterTxTotalGvrpPkts    Counter32,
    gs2124GvrpCounterTxLeaveAllMsg      Counter32,
    gs2124GvrpCounterTxJoinEmptyMsg     Counter32,
    gs2124GvrpCounterTxJoinInMsg        Counter32,
    gs2124GvrpCounterTxLeaveEmptyMsg    Counter32,
    gs2124GvrpCounterTxEmptyMsg         Counter32
}

gs2124GvrpCounterEntry OBJECT-TYPE
 SYNTAX  GS2124GvrpCounterEntry
 MAX-ACCESS     not-accessible
 STATUS  current
 DESCRIPTION
  "This is the Entry(s) for gvrp counter information."
 INDEX {gs2124GvrpCounterIndex}
 ::= { gs2124GvrpCounterTable 1 }

gs2124GvrpCounterIndex OBJECT-TYPE
 SYNTAX  INTEGER(1..24)
 MAX-ACCESS     not-accessible
 STATUS  current
 DESCRIPTION
  "This is the index of the gvrp counter entry."
 ::= { gs2124GvrpCounterEntry 1 }

gs2124GvrpCounterRxTotalGvrpPkts OBJECT-TYPE
 SYNTAX  Counter32
 MAX-ACCESS     read-only
 STATUS  current
 DESCRIPTION
  "Get the amount of all received gvrp packets of the gvrp counter entry."
 ::= { gs2124GvrpCounterEntry 2 }

gs2124GvrpCounterRxInvalidGvrpPkts OBJECT-TYPE
 SYNTAX  Counter32
 MAX-ACCESS     read-only
 STATUS  current
 DESCRIPTION
  "Get the amount of received invalid gvrp packets of the gvrp counter entry."
 ::= { gs2124GvrpCounterEntry 3 }

gs2124GvrpCounterRxLeaveAllMsg OBJECT-TYPE
 SYNTAX  Counter32
 MAX-ACCESS     read-only
 STATUS  current
 DESCRIPTION
  "Get the amount of received leave-all-message of the gvrp counter entry."
 ::= { gs2124GvrpCounterEntry 4 }

gs2124GvrpCounterRxJoinEmptyMsg OBJECT-TYPE
 SYNTAX  Counter32
 MAX-ACCESS     read-only
 STATUS  current
 DESCRIPTION
  "Get the amount of received join-empty-message of the gvrp counter entry."
 ::= { gs2124GvrpCounterEntry 5 }

gs2124GvrpCounterRxJoinInMsg OBJECT-TYPE
 SYNTAX  Counter32
 MAX-ACCESS     read-only
 STATUS  current
 DESCRIPTION
  "Get the amount of received join-in-message of the gvrp counter entry."
 ::= { gs2124GvrpCounterEntry 6 }

gs2124GvrpCounterRxLeaveEmptyMsg OBJECT-TYPE
 SYNTAX  Counter32
 MAX-ACCESS     read-only
 STATUS  current
 DESCRIPTION
  "Get the amount of received leave-empty-message of the gvrp counter entry."
 ::= { gs2124GvrpCounterEntry 7 }

gs2124GvrpCounterRxEmptyMsg OBJECT-TYPE
 SYNTAX  Counter32
 MAX-ACCESS     read-only
 STATUS  current
 DESCRIPTION
  "Get the amount of received empty-message of the gvrp counter entry."
 ::= { gs2124GvrpCounterEntry 8 }

gs2124GvrpCounterTxTotalGvrpPkts OBJECT-TYPE
 SYNTAX  Counter32
 MAX-ACCESS     read-only
 STATUS  current
 DESCRIPTION
  "Get the amount of all transmitted gvrp packets of the gvrp counter entry."
 ::= { gs2124GvrpCounterEntry 9 }

gs2124GvrpCounterTxLeaveAllMsg OBJECT-TYPE
 SYNTAX  Counter32
 MAX-ACCESS     read-only
 STATUS  current
 DESCRIPTION
  "Get the amount of transmitted leave-all-message of the gvrp counter entry."
 ::= { gs2124GvrpCounterEntry 10 }

gs2124GvrpCounterTxJoinEmptyMsg OBJECT-TYPE
 SYNTAX  Counter32
 MAX-ACCESS     read-only
 STATUS  current
 DESCRIPTION
  "Get the amount of transmitted join-empty-message of the gvrp counter entry."
 ::= { gs2124GvrpCounterEntry 11 }

gs2124GvrpCounterTxJoinInMsg OBJECT-TYPE
 SYNTAX  Counter32
 MAX-ACCESS     read-only
 STATUS  current
 DESCRIPTION
  "Get the amount of transmitted join-in-message of the gvrp counter entry."
 ::= { gs2124GvrpCounterEntry 12 }

gs2124GvrpCounterTxLeaveEmptyMsg OBJECT-TYPE
 SYNTAX  Counter32
 MAX-ACCESS     read-only
 STATUS  current
 DESCRIPTION
  "Get the amount of transmitted leave-empty-message of the gvrp counter entry."
 ::= { gs2124GvrpCounterEntry 13 }

gs2124GvrpCounterTxEmptyMsg OBJECT-TYPE
 SYNTAX  Counter32
 MAX-ACCESS     read-only
 STATUS  current
 DESCRIPTION
  "Get the amount of transmitted empty-message of the gvrp counter entry."
 ::= { gs2124GvrpCounterEntry 14 }

gs2124GvrpGroup            OBJECT IDENTIFIER ::= { gs2124GVRPInfo 3 }

gs2124GvrpGroupNumber OBJECT-TYPE
 SYNTAX  INTEGER(0..4094)
 MAX-ACCESS     read-only
 STATUS  current
 DESCRIPTION
  "Get the number of the gvrp group entry."
 ::= { gs2124GvrpGroup 1 }

gs2124GvrpGroupTable OBJECT-TYPE
 SYNTAX  SEQUENCE OF GS2124GvrpGroupEntry
 MAX-ACCESS not-accessible
 STATUS  current
    DESCRIPTION
        "This is a list of GS2124GvrpGroupEntry."
 ::= { gs2124GvrpGroup 2 }

GS2124GvrpGroupEntry ::=
SEQUENCE {
    gs2124GvrpGroupId            INTEGER,
    gs2124GvrpGroupVid           INTEGER,
    gs2124GvrpGroupMemberPort    DisplayString
}

gs2124GvrpGroupEntry OBJECT-TYPE
 SYNTAX  GS2124GvrpGroupEntry
 MAX-ACCESS     not-accessible
 STATUS  current
 DESCRIPTION
  "This is the Entry(s) for gvrp group information."
 INDEX {gs2124GvrpGroupId}
 ::= { gs2124GvrpGroupTable 1 }

gs2124GvrpGroupId OBJECT-TYPE
 SYNTAX  INTEGER(1..4094)
 MAX-ACCESS     read-only
 STATUS  current
 DESCRIPTION
  "This is the index of the gvrp group entry."
 ::= { gs2124GvrpGroupEntry 1 }

gs2124GvrpGroupVid OBJECT-TYPE
 SYNTAX  INTEGER(1..4094)
 MAX-ACCESS     read-only
 STATUS  current
 DESCRIPTION
  "This is the vlan id of the gvrp grout entry."
 ::= { gs2124GvrpGroupEntry 2 }

gs2124GvrpGroupMemberPort OBJECT-TYPE
 SYNTAX  DisplayString
 MAX-ACCESS     read-only
 STATUS  current
 DESCRIPTION
  "The member ports of the gvrp grout entry."
 ::= { gs2124GvrpGroupEntry 3 }

gs2124GvrpGroupAdministrativeCtrlTable OBJECT-TYPE
 SYNTAX  SEQUENCE OF GS2124GvrpGroupAdministrativeCtrlEntry
 MAX-ACCESS not-accessible
 STATUS  current
    DESCRIPTION
        "This is a list of GS2124GvrpGroupAdministrativeCtrlEntry."
 ::= { gs2124GvrpGroup 3 }

GS2124GvrpGroupAdministrativeCtrlEntry ::=
SEQUENCE {
    gs2124GvrpGroupAdministrativeCtrlVid    INTEGER,
    gs2124GvrpGroupAdministrativeCtrlPort   INTEGER,
    gs2124GvrpGroupAdministrativeCtrlApp    INTEGER,
    gs2124GvrpGroupAdministrativeCtrlReg    INTEGER
}

gs2124GvrpGroupAdministrativeCtrlEntry OBJECT-TYPE
 SYNTAX  GS2124GvrpGroupAdministrativeCtrlEntry
 MAX-ACCESS     not-accessible
 STATUS  current
 DESCRIPTION
  "This is the Entry(s) for gvrp group administrative information."
 INDEX {gs2124GvrpGroupAdministrativeCtrlVid, gs2124GvrpGroupAdministrativeCtrlPort}
 ::= { gs2124GvrpGroupAdministrativeCtrlTable 1 }

gs2124GvrpGroupAdministrativeCtrlVid OBJECT-TYPE
 SYNTAX  INTEGER(1..4094)
 MAX-ACCESS     read-only
 STATUS  current
 DESCRIPTION
  "This is the vlan id of the gvrp-group-admin entry."
 ::= { gs2124GvrpGroupAdministrativeCtrlEntry 1 }

gs2124GvrpGroupAdministrativeCtrlPort OBJECT-TYPE
 SYNTAX  INTEGER(1..24)
 MAX-ACCESS     read-only
 STATUS  current
 DESCRIPTION
  "This is the port number of the gvrp-group-admin entry."
 ::= { gs2124GvrpGroupAdministrativeCtrlEntry 2 }

gs2124GvrpGroupAdministrativeCtrlApp OBJECT-TYPE
 SYNTAX  INTEGER(0|1)
 MAX-ACCESS     read-write
 STATUS  current
 DESCRIPTION
  "Set gvrp applicant.
   0 - Normal
   1 - Non-Participant"
 ::= { gs2124GvrpGroupAdministrativeCtrlEntry 3 }

gs2124GvrpGroupAdministrativeCtrlReg OBJECT-TYPE
 SYNTAX  INTEGER(0..2)
 MAX-ACCESS     read-write
 STATUS  current
 DESCRIPTION
  "Set gvrp registrar.
   0 - Normal
   1 - Fixed
   2 - Forbidden"
 ::= { gs2124GvrpGroupAdministrativeCtrlEntry 4 }

gs2124QosInfo            OBJECT IDENTIFIER ::= { gs2124Produces 17 }

gs2124QosPortConf            OBJECT IDENTIFIER ::= { gs2124QosInfo 1 }

gs2124QosNumOfClasses OBJECT-TYPE
 SYNTAX      INTEGER(1|2|4)
 MAX-ACCESS     read-write
 STATUS  current
 DESCRIPTION
  "Effective class number, it can be set 1, 2, or 4.
  1 means only one class available, all packets will be treat the same.
  2 means two classes available, packets will be divided into high and low queue.
  4 means for classes available, packets will be divided into low/normal/medium/high queue"
 ::= { gs2124QosPortConf 1 }

gs2124QosPortConfTable OBJECT-TYPE
 SYNTAX  SEQUENCE OF GS2124QosPortConfEntry
 MAX-ACCESS not-accessible
 STATUS  current
    DESCRIPTION
        "QoS parameter for ports."
 ::= { gs2124QosPortConf 2 }

GS2124QosPortConfEntry ::=
SEQUENCE {
    gs2124QosPortConfIndex                INTEGER,
    gs2124QosPortConfDefaultClasses       INTEGER,
    gs2124QosPortConfQCL                  INTEGER,
    gs2124QosPortConfUserPriority         INTEGER,
    gs2124QosPortConfQueuingMode          INTEGER,
    gs2124QosPortConfQueueWeightedLow     INTEGER,
    gs2124QosPortConfQueueWeightedNormal  INTEGER,
    gs2124QosPortConfQueueWeightedMedium  INTEGER,
    gs2124QosPortConfQueueWeightedHigh    INTEGER
}

gs2124QosPortConfEntry OBJECT-TYPE
 SYNTAX  GS2124QosPortConfEntry
 MAX-ACCESS     not-accessible
 STATUS  current
 DESCRIPTION
  "QoS parameter for ports."
 INDEX {gs2124QosPortConfIndex}
 ::= { gs2124QosPortConfTable 1 }

gs2124QosPortConfIndex OBJECT-TYPE
 SYNTAX  INTEGER(1..24)
 MAX-ACCESS     not-accessible
 STATUS  current
 DESCRIPTION
  "This is the port number for QoS configuration."
 ::= { gs2124QosPortConfEntry 1 }

gs2124QosPortConfDefaultClasses OBJECT-TYPE
 SYNTAX  INTEGER(0..3)
 MAX-ACCESS     read-write
 STATUS  current
 DESCRIPTION
  "This is the default class for packets mismatch the specified QCL setting.
   0 - Low
   1 - Normal
   2 - Medium
   3 - High"
 ::= { gs2124QosPortConfEntry 2 }

gs2124QosPortConfQCL OBJECT-TYPE
 SYNTAX  INTEGER(1..24)
 MAX-ACCESS     read-write
 STATUS  current
 DESCRIPTION
 "Designate the QCL for the specific port. QCL is from 1 to 24."
 ::= { gs2124QosPortConfEntry 3 }

gs2124QosPortConfUserPriority OBJECT-TYPE
 SYNTAX  INTEGER(0..7)
 MAX-ACCESS     read-write
 STATUS  current
 DESCRIPTION
		"This is the default ingress VLAN tag priority. Priority is from 0 to 7."
 ::= { gs2124QosPortConfEntry 4 }

gs2124QosPortConfQueuingMode OBJECT-TYPE
 SYNTAX  INTEGER(0|1)
 MAX-ACCESS     read-write
 STATUS  current
 DESCRIPTION
  "Set qos port queuing mode.
   0 - Strict Priority
   1 - Weighted Fair"
 ::= { gs2124QosPortConfEntry 5 }

gs2124QosPortConfQueueWeightedLow OBJECT-TYPE
 SYNTAX  INTEGER(1|2|4|8)
 MAX-ACCESS     read-write
 STATUS  current
 DESCRIPTION
  "To specify how many quotas the low queue can be distributed.
		 Only available when the queuing mode is Weighted Fair. QueueWeighted is 1, 2, 4, 8."
 ::= { gs2124QosPortConfEntry 6 }

gs2124QosPortConfQueueWeightedNormal OBJECT-TYPE
 SYNTAX  INTEGER(1|2|4|8)
 MAX-ACCESS     read-write
 STATUS  current
 DESCRIPTION
  "To specify how many quotas the normal queue can be distributed.
		 Only available when the queuing mode is Weighted Fair. QueueWeighted is 1, 2, 4, 8."
 ::= { gs2124QosPortConfEntry 7 }

gs2124QosPortConfQueueWeightedMedium OBJECT-TYPE
 SYNTAX  INTEGER(1|2|4|8)
 MAX-ACCESS     read-write
 STATUS  current
 DESCRIPTION
  "To specify how many quotas the medium queue can be distributed.
		 Only available when the queuing mode is Weighted Fair. QueueWeighted is 1, 2, 4, 8."
 ::= { gs2124QosPortConfEntry 8 }

gs2124QosPortConfQueueWeightedHigh OBJECT-TYPE
 SYNTAX  INTEGER(1|2|4|8)
 MAX-ACCESS     read-write
 STATUS  current
 DESCRIPTION
  "To specify how many quotas the high queue can be distributed.
		 Only available when the queuing mode is Weighted Fair. QueueWeighted is 1, 2, 4, 8."
 ::= { gs2124QosPortConfEntry 9 }

gs2124QosRateLimiters           OBJECT IDENTIFIER ::= { gs2124QosInfo 3 }

gs2124QosRateLimitersTable OBJECT-TYPE
 SYNTAX  SEQUENCE OF GS2124QosRateLimitersEntry
 MAX-ACCESS not-accessible
 STATUS  current
    DESCRIPTION
        "This is the port bandwidth configuration."
 ::= { gs2124QosRateLimiters 1 }

GS2124QosRateLimitersEntry ::=
SEQUENCE {
    gs2124QosRateLimitersIndex         INTEGER,
    gs2124QosRateLimitersPolicer       INTEGER,
    gs2124QosRateLimitersPolicerRate   INTEGER,
    gs2124QosRateLimitersShaper        INTEGER,
    gs2124QosRateLimitersShaperRate    INTEGER
}

gs2124QosRateLimitersEntry OBJECT-TYPE
 SYNTAX  GS2124QosRateLimitersEntry
 MAX-ACCESS     not-accessible
 STATUS  current
 DESCRIPTION
  "This is the port bandwidth configuration."
 INDEX {gs2124QosRateLimitersIndex}
 ::= { gs2124QosRateLimitersTable 1 }

gs2124QosRateLimitersIndex OBJECT-TYPE
 SYNTAX  INTEGER(1..24)
 MAX-ACCESS     not-accessible
 STATUS  current
 DESCRIPTION
  "This is the port number for rate limit configuration"
 ::= { gs2124QosRateLimitersEntry 1 }

gs2124QosRateLimitersPolicer OBJECT-TYPE
 SYNTAX  INTEGER(0|1)
 MAX-ACCESS     read-write
 STATUS  current
 DESCRIPTION
  "This is the ingress bandwidth function for specific port.
   0 - Disable
   1 - Enable"
 ::= { gs2124QosRateLimitersEntry 2 }

gs2124QosRateLimitersPolicerRate OBJECT-TYPE
 SYNTAX  INTEGER(1..1000000)
 MAX-ACCESS     read-write
 STATUS  current
 DESCRIPTION
  "To set the ingress bandwidth for specific port.
   Available value is from 500k to 1000000k"
 ::= { gs2124QosRateLimitersEntry 3 }


gs2124QosRateLimitersShaper OBJECT-TYPE
 SYNTAX  INTEGER(0|1)
 MAX-ACCESS     read-write
 STATUS  current
 DESCRIPTION
  "This is the egress bandwidth function for specific port.
   0 - Disable
   1 - Enable"
 ::= { gs2124QosRateLimitersEntry 4 }

gs2124QosRateLimitersShaperRate OBJECT-TYPE
 SYNTAX  INTEGER(1..1000000)
 MAX-ACCESS     read-write
 STATUS  current
 DESCRIPTION
  "To set the ingress bandwidth for specific port.
   Available value is from 500k to 1000000k"
 ::= { gs2124QosRateLimitersEntry 5 }


gs2124QosStormCtrl           OBJECT IDENTIFIER ::= { gs2124QosInfo 4 }

gs2124QosStromCtrlFloodedUnicastStatus OBJECT-TYPE
 SYNTAX      INTEGER(0|1)
 MAX-ACCESS     read-write
 STATUS  current
 DESCRIPTION
  "This is the flooded unicast suppression function for this device.
   0 - Disable
   1 - Enable"
 ::= { gs2124QosStormCtrl 1 }

gs2124QosStromCtrlFloodedUnicastRate OBJECT-TYPE
 SYNTAX      DisplayString
 MAX-ACCESS     read-write
 STATUS  current
 DESCRIPTION
  "To set the flooded unicast suppression for this device.
   1 | 2 | 4 | 8 | 16 | 32 | 64 | 128 | 256 | 512 | 1k | 2k | 4k | 8k | 16k | 32k |64k | 128k | 256k | 512k | 1024k(Rate:pps)
    "
 ::= { gs2124QosStormCtrl 2 }

gs2124QosStromCtrlMulticastStatus OBJECT-TYPE
 SYNTAX      INTEGER(0|1)
 MAX-ACCESS     read-write
 STATUS  current
 DESCRIPTION
  "This is the multicast suppression function for this device.
   0 - Disable
   1 - Enable"
 ::= { gs2124QosStormCtrl 3 }

gs2124QosStromCtrlMulticastRate OBJECT-TYPE
 SYNTAX      DisplayString
 MAX-ACCESS     read-write
 STATUS  current
 DESCRIPTION
  "To set the multicast suppression for this device.
   1 | 2 | 4 | 8 | 16 | 32 | 64 | 128 | 256 | 512 | 1k | 2k | 4k | 8k | 16k | 32k |64k | 128k | 256k | 512k | 1024k(Rate:pps)    "
 ::= { gs2124QosStormCtrl 4 }

gs2124QosStromCtrlBroadcastStatus OBJECT-TYPE
 SYNTAX      INTEGER(0|1)
 MAX-ACCESS     read-write
 STATUS  current
 DESCRIPTION
  "This is the broadcast suppression function for this device.
   0 - Disable
   1 - Enable"
 ::= { gs2124QosStormCtrl 5 }

gs2124QosStromCtrlBroadcastRate OBJECT-TYPE
 SYNTAX      DisplayString
 MAX-ACCESS     read-write
 STATUS  current
 DESCRIPTION
  "To set the broadcast suppression for this device.
   1 | 2 | 4 | 8 | 16 | 32 | 64 | 128 | 256 | 512 | 1k | 2k | 4k | 8k | 16k | 32k |64k | 128k | 256k | 512k | 1024k(Rate:pps)    "
 ::= { gs2124QosStormCtrl 6 }

gs2124QosQCL           OBJECT IDENTIFIER ::= { gs2124QosInfo 5 }

gs2124QosQclCreate OBJECT-TYPE
 SYNTAX      INTEGER(1..24)
 MAX-ACCESS     read-write
 STATUS  current
 DESCRIPTION
  "Specify a QCL number where the QCE will be created. Parameter is available from 1 ~ 24."
 ::= { gs2124QosQCL 1 }

gs2124QosQclTable OBJECT-TYPE
 SYNTAX  SEQUENCE OF GS2124QosQclEntry
 MAX-ACCESS not-accessible
 STATUS  current
    DESCRIPTION
        "This is the Qcl table."
 ::= { gs2124QosQCL 2 }

GS2124QosQclEntry ::=
SEQUENCE {
    gs2124QosQclNo                   INTEGER,
    gs2124QosQclQceListNo            INTEGER,
    gs2124QosQclQceMoveTo            INTEGER,
    gs2124QosQclQceType              INTEGER,
    gs2124QosQclQceValue             DisplayString,
    gs2124QosQclQceTrafficClass      DisplayString,
    gs2124QosQclQcePriority0Class    DisplayString,
    gs2124QosQclQcePriority1Class    DisplayString,
    gs2124QosQclQcePriority2Class    DisplayString,
    gs2124QosQclQcePriority3Class    DisplayString,
    gs2124QosQclQcePriority4Class    DisplayString,
    gs2124QosQclQcePriority5Class    DisplayString,
    gs2124QosQclQcePriority6Class    DisplayString,
    gs2124QosQclQcePriority7Class    DisplayString,
    gs2124QosQclQceEntryAction       INTEGER
}

gs2124QosQclEntry OBJECT-TYPE
 SYNTAX  GS2124QosQclEntry
 MAX-ACCESS     not-accessible
 STATUS  current
 DESCRIPTION
  "This is the Entry(s) for qcl entry information."
 INDEX {gs2124QosQclNo,gs2124QosQclQceListNo}
 ::= { gs2124QosQclTable 1 }

gs2124QosQclNo OBJECT-TYPE
 SYNTAX  INTEGER(1..24)
 MAX-ACCESS     not-accessible
 STATUS  current
 DESCRIPTION
  "Display which QCL is specified."
 ::= { gs2124QosQclEntry 1 }

gs2124QosQclQceListNo OBJECT-TYPE
 SYNTAX  INTEGER(1..24)
 MAX-ACCESS     not-accessible
 STATUS  current
 DESCRIPTION
  "Index of qce entry."
 ::= { gs2124QosQclEntry 2 }

gs2124QosQclQceMoveTo OBJECT-TYPE
 SYNTAX  INTEGER(1..24)
 MAX-ACCESS     not-accessible
 STATUS  current
 DESCRIPTION
  "Designate the position where the QCE will be moved to."
 ::= { gs2124QosQclEntry 3 }

gs2124QosQclQceType OBJECT-TYPE
 SYNTAX  INTEGER(0..5)
 MAX-ACCESS     read-write
 STATUS  current
 DESCRIPTION
  "Specify the qce type.
  0:EthernetType 1:VLAN ID 2:UDP/TCP Port
3:DSCP 4:Tos 5:TagPriority"
 ::= { gs2124QosQclEntry 4 }

gs2124QosQclQceValue OBJECT-TYPE
 SYNTAX  DisplayString
 MAX-ACCESS     read-write
 STATUS  current
 DESCRIPTION
  "Specify the qce entry value. Only available for 0:EthernetType 1:VLAN ID 2:UDP/TCP Port 3:DSCP.
  Input numbers in hexadecimal for 0:Ethernet Type, decimal for 1:VLAN ID 2:UDP/TCP Port 3:DSCP.
  You can also specify a range value for 2:UDP/TCP. EX: 5000-6000"
 ::= { gs2124QosQclEntry 5 }

gs2124QosQclQceTrafficClass OBJECT-TYPE
 SYNTAX  DisplayString
 MAX-ACCESS     read-write
 STATUS  current
 DESCRIPTION
  "Specify the qce entry traffic class. Available options are: low, normal, medium and high."
 ::= { gs2124QosQclEntry 6 }

gs2124QosQclQcePriority0Class OBJECT-TYPE
 SYNTAX  DisplayString
 MAX-ACCESS     read-write
 STATUS  current
 DESCRIPTION
  "Specify the qce entry traffic class. Available options are: low, normal, medium and high.
  Only works on 4:Tos 5:TagPriority."
 ::= { gs2124QosQclEntry 7 }

gs2124QosQclQcePriority1Class OBJECT-TYPE
 SYNTAX  DisplayString
 MAX-ACCESS     read-write
 STATUS  current
 DESCRIPTION
  "Specify the qce entry traffic class. Available options are: low, normal, medium and high.
  Only works on 4:Tos 5:TagPriority."
 ::= { gs2124QosQclEntry 8 }

gs2124QosQclQcePriority2Class OBJECT-TYPE
 SYNTAX  DisplayString
 MAX-ACCESS     read-write
 STATUS  current
 DESCRIPTION
  "Specify the qce entry traffic class. Available options are: low, normal, medium and high.
  Only works on 4:Tos 5:TagPriority."
 ::= { gs2124QosQclEntry 9 }

gs2124QosQclQcePriority3Class OBJECT-TYPE
 SYNTAX  DisplayString
 MAX-ACCESS     read-write
 STATUS  current
 DESCRIPTION
  "Specify the qce entry traffic class. Available options are: low, normal, medium and high.
  Only works on 4:Tos 5:TagPriority."
 ::= { gs2124QosQclEntry 10 }

gs2124QosQclQcePriority4Class OBJECT-TYPE
 SYNTAX  DisplayString
 MAX-ACCESS     read-write
 STATUS  current
 DESCRIPTION
  "Specify the qce entry traffic class. Available options are: low, normal, medium and high.
  Only works on 4:Tos 5:TagPriority."
 ::= { gs2124QosQclEntry 11 }

gs2124QosQclQcePriority5Class OBJECT-TYPE
 SYNTAX  DisplayString
 MAX-ACCESS     read-write
 STATUS  current
 DESCRIPTION
  "Specify the qce entry traffic class. Available options are: low, normal, medium and high.
  Only works on 4:Tos 5:TagPriority."
 ::= { gs2124QosQclEntry 12 }

gs2124QosQclQcePriority6Class OBJECT-TYPE
 SYNTAX  DisplayString
 MAX-ACCESS     read-write
 STATUS  current
 DESCRIPTION
  "Specify the qce entry traffic class. Available options are: low, normal, medium and high.
  Only works on 4:Tos 5:TagPriority."
 ::= { gs2124QosQclEntry 13 }

gs2124QosQclQcePriority7Class OBJECT-TYPE
 SYNTAX  DisplayString
 MAX-ACCESS     read-write
 STATUS  current
 DESCRIPTION
  "Specify the qce entry traffic class. Available options are: low, normal, medium and high.
  Only works on 4:Tos 5:TagPriority."
 ::= { gs2124QosQclEntry 14 }

gs2124QosQclQceEntryAction OBJECT-TYPE
 SYNTAX  INTEGER(1..3)
 MAX-ACCESS  read-write
 STATUS  current
 DESCRIPTION
  "Set qce entry state.
  1:active 2:notInService or edit 3:delete"
 ::= { gs2124QosQclEntry 15 }


gs2124AclInfo            OBJECT IDENTIFIER ::= { gs2124Produces 18 }

gs2124AclPortsConfTable OBJECT-TYPE
 SYNTAX  SEQUENCE OF GS2124AclPortsConfEntry
 MAX-ACCESS not-accessible
 STATUS  current
    DESCRIPTION
        "This is a list of port configuration entry. "
 ::= { gs2124AclInfo 1 }

GS2124AclPortsConfEntry ::=
SEQUENCE {
    gs2124AclPortsConfIndex           INTEGER,
    gs2124AclPortsConfPolicyId        INTEGER,
    gs2124AclPortsConfAction          INTEGER,
    gs2124AclPortsConfRateLimiterId   INTEGER,
    gs2124AclPortsConfPortCopy        INTEGER,
    gs2124AclPortsConfCounter         Counter32
}

gs2124AclPortsConfEntry OBJECT-TYPE
 SYNTAX  GS2124AclPortsConfEntry
 MAX-ACCESS     not-accessible
 STATUS  current
 DESCRIPTION
  "This is the Entry(s) for ACL port information."
 INDEX {gs2124AclPortsConfIndex}
 ::= { gs2124AclPortsConfTable 1 }

gs2124AclPortsConfIndex OBJECT-TYPE
 SYNTAX  INTEGER(1..24)
 MAX-ACCESS     not-accessible
 STATUS  current
 DESCRIPTION
  "This is the port number of the ACL port entry."
 ::= { gs2124AclPortsConfEntry 1 }

gs2124AclPortsConfPolicyId OBJECT-TYPE
 SYNTAX  INTEGER(1..8)
 MAX-ACCESS     read-write
 STATUS  current
 DESCRIPTION
  "This is the policy id of the ACL port entry.(1-8)"
 ::= { gs2124AclPortsConfEntry 2 }

gs2124AclPortsConfAction OBJECT-TYPE
 SYNTAX  INTEGER(0|1)
 MAX-ACCESS     read-write
 STATUS  current
 DESCRIPTION
  "Set the action of the ACL port entry.
   0 - Deny
   1 - Permit"
 ::= { gs2124AclPortsConfEntry 3 }

gs2124AclPortsConfRateLimiterId OBJECT-TYPE
 SYNTAX  INTEGER(0..24)
 MAX-ACCESS     read-write
 STATUS  current
 DESCRIPTION
  " Set the rate limiter id of the ACL port entry.(1-16)
   0 - Disable"
 ::= { gs2124AclPortsConfEntry 4 }

gs2124AclPortsConfPortCopy OBJECT-TYPE
 SYNTAX  INTEGER(0..24)
 MAX-ACCESS     read-write
 STATUS  current
 DESCRIPTION
  "Set the mirror port of the ACL port entry.(1-24)
   0 - Disable"
 ::= { gs2124AclPortsConfEntry 5 }

gs2124AclPortsConfCounter OBJECT-TYPE
 SYNTAX  Counter32
 MAX-ACCESS     read-only
 STATUS  current
 DESCRIPTION
  "This is the port counter of the ACL port entry."
 ::= { gs2124AclPortsConfEntry 6 }

gs2124AclRateLimiter           OBJECT IDENTIFIER ::= { gs2124AclInfo 2 }

gs2124AclRateLimiterTable OBJECT-TYPE
 SYNTAX  SEQUENCE OF GS2124AclRateLimiterEntry
 MAX-ACCESS not-accessible
 STATUS  current
    DESCRIPTION
        "This is a list of GS2124RateLimiterEntry."
 ::= { gs2124AclRateLimiter 1 }

GS2124AclRateLimiterEntry ::=
SEQUENCE {
    gs2124AclRateLimiterIndex        INTEGER,
    gs2124AclRateLimiterRate         DisplayString
}

gs2124AclRateLimiterEntry OBJECT-TYPE
 SYNTAX  GS2124AclRateLimiterEntry
 MAX-ACCESS     not-accessible
 STATUS  current
 DESCRIPTION
  "This is the Entry(s) for rate limiter information."
 INDEX {gs2124AclRateLimiterIndex}
 ::= { gs2124AclRateLimiterTable 1 }

gs2124AclRateLimiterIndex OBJECT-TYPE
 SYNTAX  INTEGER(1..24)
 MAX-ACCESS     not-accessible
 STATUS  current
 DESCRIPTION
  "This is the index of the rate limiter entry."
 ::= { gs2124AclRateLimiterEntry 1 }

gs2124AclRateLimiterRate OBJECT-TYPE
 SYNTAX  DisplayString
 MAX-ACCESS     read-write
 STATUS  current
 DESCRIPTION
  "Set acl rate limite.
  (pps) 1 | 2 | 4 | 8 | 16 | 32 | 64 | 128 | 256 | 512 | 1k | 2k | 4k | 8k | 16k | 32k |64k | 128k | 256k | 512k | 1024k"
 ::= { gs2124AclRateLimiterEntry 2 }

gs2124AclInfoViewTable OBJECT-TYPE
 SYNTAX  SEQUENCE OF GS2124AclInfoViewEntry
 MAX-ACCESS not-accessible
 STATUS  current
    DESCRIPTION
        "This is a list of GS2124AclInfoViewEntry."
 ::= { gs2124AclInfo 3 }

GS2124AclInfoViewEntry ::=
SEQUENCE {
    gs2124AclInfoViewNo              INTEGER,
    gs2124AceIngressPort             DisplayString,
    gs2124AceFrameType               DisplayString,
    gs2124AceAction                  DisplayString,
    gs2124AceRateLimiter             DisplayString,
    gs2124AcePortCopy                DisplayString,
    gs2124AceCounter                 Counter32,
    gs2124SmacFilter                 DisplayString,
    gs2124DmacFilter                 DisplayString,
    gs2124VlanIdFilter               DisplayString,
    gs2124VlanTagPriority            DisplayString,
    gs2124EtherTypeFilter            DisplayString,
    gs2124ArpRarp                    DisplayString,
    gs2124ArpRequestReply            DisplayString,
    gs2124ArpSenderIpFilter          DisplayString,
    gs2124ArpSenderIpAddress         DisplayString,
    gs2124ArpSenderIpMask            DisplayString,
    gs2124ArpTargetIpFilter          DisplayString,
    gs2124ArpTargetIpAddress         DisplayString,
    gs2124ArpTargetIpMask            DisplayString,
    gs2124ArpSmacMatch               DisplayString,
    gs2124ArpRarpDmacMatch           DisplayString,
    gs2124ArpIpEthernetLength        DisplayString,
    gs2124ArpIp                      DisplayString,
    gs2124ArpEthernet                DisplayString,
    gs2124IpProtocolFilter           DisplayString,
    gs2124IpProtocolValue            DisplayString,
    gs2124IpTTL                      DisplayString,
    gs2124IpFragment                 DisplayString,
    gs2124IpOption                   DisplayString,
    gs2124SipFilter                  DisplayString,
    gs2124SipAddress                 DisplayString,
    gs2124SipMask                    DisplayString,
    gs2124DipFilter                  DisplayString,
    gs2124DipAddress                 DisplayString,
    gs2124DipMask                    DisplayString,
    gs2124IcmpTypeFilter             DisplayString,
    gs2124IcmpCodeFilter             DisplayString,
    gs2124UdpSourcePortFilter        DisplayString,
    gs2124UdpDestPortFilter          DisplayString,
    gs2124TcpSourcePortFilter        DisplayString,
    gs2124TcpDestPortFilter          DisplayString,
    gs2124TcpFIN                     DisplayString,
    gs2124TcpSYN                     DisplayString,
    gs2124TcpRST                     DisplayString,
    gs2124TcpPSH                     DisplayString,
    gs2124TcpACK                     DisplayString,
    gs2124TcpURG                     DisplayString,
    gs2124AclInfoEntryAction         INTEGER
}

gs2124AclInfoViewEntry OBJECT-TYPE
 SYNTAX  GS2124AclInfoViewEntry
 MAX-ACCESS     not-accessible
 STATUS  current
 DESCRIPTION
  "Show acl entry information."
 INDEX {gs2124AclInfoViewNo}
 ::= { gs2124AclInfoViewTable 1 }


gs2124AclInfoViewNo OBJECT-TYPE
 SYNTAX  INTEGER(1..128)
 MAX-ACCESS     not-accessible
 STATUS  current
 DESCRIPTION
  "Index of the ACL entry."
 ::= { gs2124AclInfoViewEntry 1 }

gs2124AceIngressPort OBJECT-TYPE
 SYNTAX  DisplayString
 MAX-ACCESS     read-only
 STATUS  current
 DESCRIPTION
  "Ace ingress port number."
 ::= { gs2124AclInfoViewEntry 2 }

gs2124AceFrameType OBJECT-TYPE
 SYNTAX  DisplayString
 MAX-ACCESS     read-only
 STATUS  current
 DESCRIPTION
  "Ace frame type."
 ::= { gs2124AclInfoViewEntry 3 }

gs2124AceAction OBJECT-TYPE
 SYNTAX  DisplayString
 MAX-ACCESS     read-only
 STATUS  current
 DESCRIPTION
  "Ace action."
 ::= { gs2124AclInfoViewEntry 4 }

gs2124AceRateLimiter OBJECT-TYPE
 SYNTAX  DisplayString
 MAX-ACCESS     read-only
 STATUS  current
 DESCRIPTION
  "Ace rate limiter number."
 ::= { gs2124AclInfoViewEntry 5 }

gs2124AcePortCopy OBJECT-TYPE
 SYNTAX  DisplayString
 MAX-ACCESS     read-only
 STATUS  current
 DESCRIPTION
  "Specify the port which packet will be copied to."
 ::= { gs2124AclInfoViewEntry 6 }

gs2124AceCounter OBJECT-TYPE
 SYNTAX  Counter32
 MAX-ACCESS     read-only
 STATUS  current
 DESCRIPTION
  "Display the number of packets hit this ace."
 ::= { gs2124AclInfoViewEntry 7 }

gs2124SmacFilter OBJECT-TYPE
 SYNTAX  DisplayString
 MAX-ACCESS     read-only
 STATUS  current
 DESCRIPTION
  "Display the source mac field of the ace."
 ::= { gs2124AclInfoViewEntry 8 }

gs2124DmacFilter OBJECT-TYPE
 SYNTAX  DisplayString
 MAX-ACCESS     read-only
 STATUS  current
 DESCRIPTION
  "Display the destination mac field of the ace."
 ::= { gs2124AclInfoViewEntry 9 }

gs2124VlanIdFilter OBJECT-TYPE
 SYNTAX  DisplayString
 MAX-ACCESS     read-only
 STATUS  current
 DESCRIPTION
  "Display the vid field of the ace."
 ::= { gs2124AclInfoViewEntry 10 }

gs2124VlanTagPriority OBJECT-TYPE
 SYNTAX  DisplayString
 MAX-ACCESS     read-only
 STATUS  current
 DESCRIPTION
  "Display the vlan tag priority field of the ace."
 ::= { gs2124AclInfoViewEntry 11 }

gs2124EtherTypeFilter OBJECT-TYPE
 SYNTAX  DisplayString
 MAX-ACCESS     read-only
 STATUS  current
 DESCRIPTION
  "Display the ether type field of the ace."
 ::= { gs2124AclInfoViewEntry 12 }

gs2124ArpRarp OBJECT-TYPE
 SYNTAX  DisplayString
 MAX-ACCESS     read-only
 STATUS  current
 DESCRIPTION
  "Display the arp and rarp field of the ace."
 ::= { gs2124AclInfoViewEntry 13 }

gs2124ArpRequestReply OBJECT-TYPE
 SYNTAX  DisplayString
 MAX-ACCESS     read-only
 STATUS  current
 DESCRIPTION
  "Display the arp-request and arp-replay field of the ace."
 ::= { gs2124AclInfoViewEntry 14 }

gs2124ArpSenderIpFilter OBJECT-TYPE
 SYNTAX  DisplayString
 MAX-ACCESS     read-only
 STATUS  current
 DESCRIPTION
  "Display the arp sender ip filter field of the ace."
 ::= { gs2124AclInfoViewEntry 15 }

gs2124ArpSenderIpAddress OBJECT-TYPE
 SYNTAX  DisplayString
 MAX-ACCESS     read-only
 STATUS  current
 DESCRIPTION
  "Display the arp sender ip address field of the ace."
 ::= { gs2124AclInfoViewEntry 16 }

gs2124ArpSenderIpMask OBJECT-TYPE
 SYNTAX  DisplayString
 MAX-ACCESS     read-only
 STATUS  current
 DESCRIPTION
  "Display the arp sender ip mask field of the ace."
 ::= { gs2124AclInfoViewEntry 17 }

gs2124ArpTargetIpFilter OBJECT-TYPE
 SYNTAX  DisplayString
 MAX-ACCESS     read-only
 STATUS  current
 DESCRIPTION
  "Display the arp target ip filter field of the ace."
 ::= { gs2124AclInfoViewEntry 18 }

gs2124ArpTargetIpAddress OBJECT-TYPE
 SYNTAX  DisplayString
 MAX-ACCESS     read-only
 STATUS  current
 DESCRIPTION
  "Display the arp target ip address field of the ace."
 ::= { gs2124AclInfoViewEntry 19 }

gs2124ArpTargetIpMask OBJECT-TYPE
 SYNTAX  DisplayString
 MAX-ACCESS     read-only
 STATUS  current
 DESCRIPTION
  "Display the arp target ip mask field of the ace."
 ::= { gs2124AclInfoViewEntry 20 }

gs2124ArpSmacMatch OBJECT-TYPE
 SYNTAX  DisplayString
 MAX-ACCESS     read-only
 STATUS  current
 DESCRIPTION
  "Display the arp smac match field of the ace."
 ::= { gs2124AclInfoViewEntry 21 }

gs2124ArpRarpDmacMatch OBJECT-TYPE
 SYNTAX  DisplayString
 MAX-ACCESS     read-only
 STATUS  current
 DESCRIPTION
  "Display the rarp dmac match field of the ace."
 ::= { gs2124AclInfoViewEntry 22 }

gs2124ArpIpEthernetLength OBJECT-TYPE
 SYNTAX  DisplayString
 MAX-ACCESS     read-only
 STATUS  current
 DESCRIPTION
  "Display the rarp ethernet length field of the ace."
 ::= { gs2124AclInfoViewEntry 23 }

gs2124ArpIp OBJECT-TYPE
 SYNTAX  DisplayString
 MAX-ACCESS     read-only
 STATUS  current
 DESCRIPTION
  "Display the arp ip field of the ace."
 ::= { gs2124AclInfoViewEntry 24 }

gs2124ArpEthernet OBJECT-TYPE
 SYNTAX  DisplayString
 MAX-ACCESS     read-only
 STATUS  current
 DESCRIPTION
  "Display the arp ethernet field of the ace."
 ::= { gs2124AclInfoViewEntry 25 }

gs2124IpProtocolFilter OBJECT-TYPE
 SYNTAX  DisplayString
 MAX-ACCESS     read-only
 STATUS  current
 DESCRIPTION
  "Display the ip protocol filter field of the ace."
 ::= { gs2124AclInfoViewEntry 26 }

gs2124IpProtocolValue OBJECT-TYPE
 SYNTAX  DisplayString
 MAX-ACCESS     read-only
 STATUS  current
 DESCRIPTION
  "Display the ip protocol value field of the ace."
 ::= { gs2124AclInfoViewEntry 27 }

gs2124IpTTL OBJECT-TYPE
 SYNTAX  DisplayString
 MAX-ACCESS     read-only
 STATUS  current
 DESCRIPTION
  "Display the ip ttl field of the ace. "
 ::= { gs2124AclInfoViewEntry 28 }

gs2124IpFragment OBJECT-TYPE
 SYNTAX  DisplayString
 MAX-ACCESS     read-only
 STATUS  current
 DESCRIPTION
  "Display the ip fragment field of the ace."
 ::= { gs2124AclInfoViewEntry 29 }

gs2124IpOption OBJECT-TYPE
 SYNTAX  DisplayString
 MAX-ACCESS     read-only
 STATUS  current
 DESCRIPTION
  "Display the ip option field of the ace."
 ::= { gs2124AclInfoViewEntry 30 }

gs2124SipFilter OBJECT-TYPE
 SYNTAX  DisplayString
 MAX-ACCESS     read-only
 STATUS  current
 DESCRIPTION
  "Display the sip filter field of the ace."
 ::= { gs2124AclInfoViewEntry 31 }

gs2124SipAddress OBJECT-TYPE
 SYNTAX  DisplayString
 MAX-ACCESS     read-only
 STATUS  current
 DESCRIPTION
  "Display the sip address field of the ace."
 ::= { gs2124AclInfoViewEntry 32 }

gs2124SipMask OBJECT-TYPE
 SYNTAX  DisplayString
 MAX-ACCESS     read-only
 STATUS  current
 DESCRIPTION
  "Display the sip mask field of the ace."
 ::= { gs2124AclInfoViewEntry 33 }

gs2124DipFilter OBJECT-TYPE
 SYNTAX  DisplayString
 MAX-ACCESS     read-only
 STATUS  current
 DESCRIPTION
  "Display the dip filter field of the ace."
 ::= { gs2124AclInfoViewEntry 34 }

gs2124DipAddress OBJECT-TYPE
 SYNTAX  DisplayString
 MAX-ACCESS     read-only
 STATUS  current
 DESCRIPTION
  "Display the dip address field of the ace."
 ::= { gs2124AclInfoViewEntry 35 }

gs2124DipMask OBJECT-TYPE
 SYNTAX  DisplayString
 MAX-ACCESS     read-only
 STATUS  current
 DESCRIPTION
  "Display the dip mask field of the ace."
 ::= { gs2124AclInfoViewEntry 36 }

gs2124IcmpTypeFilter OBJECT-TYPE
 SYNTAX  DisplayString
 MAX-ACCESS     read-only
 STATUS  current
 DESCRIPTION
  "Display the icmp type field of the ace."
 ::= { gs2124AclInfoViewEntry 37 }

gs2124IcmpCodeFilter OBJECT-TYPE
 SYNTAX  DisplayString
 MAX-ACCESS     read-only
 STATUS  current
 DESCRIPTION
  "Display the icmp code field of the ace."
 ::= { gs2124AclInfoViewEntry 38 }

gs2124UdpSourcePortFilter OBJECT-TYPE
 SYNTAX  DisplayString
 MAX-ACCESS     read-only
 STATUS  current
 DESCRIPTION
  "Display the udp source port field of the ace."
 ::= { gs2124AclInfoViewEntry 39 }

gs2124UdpDestPortFilter OBJECT-TYPE
 SYNTAX  DisplayString
 MAX-ACCESS     read-only
 STATUS  current
 DESCRIPTION
  "Display the udp destination port field of the ace."
 ::= { gs2124AclInfoViewEntry 40 }

gs2124TcpSourcePortFilter OBJECT-TYPE
 SYNTAX  DisplayString
 MAX-ACCESS     read-only
 STATUS  current
 DESCRIPTION
  "Display the tcp source port field of the ace."
 ::= { gs2124AclInfoViewEntry 41 }

gs2124TcpDestPortFilter OBJECT-TYPE
 SYNTAX  DisplayString
 MAX-ACCESS     read-only
 STATUS  current
 DESCRIPTION
  "Display the tcp destination port field of the ace."
 ::= { gs2124AclInfoViewEntry 42 }

gs2124TcpFIN OBJECT-TYPE
 SYNTAX  DisplayString
 MAX-ACCESS     read-only
 STATUS  current
 DESCRIPTION
  "Display the tcp fin field of the ace."
 ::= { gs2124AclInfoViewEntry 43 }

gs2124TcpSYN OBJECT-TYPE
 SYNTAX  DisplayString
 MAX-ACCESS     read-only
 STATUS  current
 DESCRIPTION
  "Display the tcp syn field of the ace."
 ::= { gs2124AclInfoViewEntry 44 }

gs2124TcpRST OBJECT-TYPE
 SYNTAX  DisplayString
 MAX-ACCESS     read-only
 STATUS  current
 DESCRIPTION
  "Display the tcp rst field of the ace."
 ::= { gs2124AclInfoViewEntry 45 }

gs2124TcpPSH OBJECT-TYPE
 SYNTAX  DisplayString
 MAX-ACCESS     read-only
 STATUS  current
 DESCRIPTION
  "Display the tcp psh field of the ace."
 ::= { gs2124AclInfoViewEntry 46 }

gs2124TcpACK OBJECT-TYPE
 SYNTAX  DisplayString
 MAX-ACCESS     read-only
 STATUS  current
 DESCRIPTION
  "Display the tcp ack field of the ace."
 ::= { gs2124AclInfoViewEntry 47 }

gs2124TcpURG OBJECT-TYPE
 SYNTAX  DisplayString
 MAX-ACCESS     read-only
 STATUS  current
 DESCRIPTION
  "Display the tcp urg field of the ace."
 ::= { gs2124AclInfoViewEntry 48 }

gs2124AclInfoEntryAction OBJECT-TYPE
 SYNTAX  INTEGER(1..4)
 MAX-ACCESS     read-write
 STATUS  current
 DESCRIPTION
  "1. set the entry active / the entry is active when get state.
   2. edit the specific entry.
   3. delete the specific entry.
   4. undo. free the buffer."
 ::= { gs2124AclInfoViewEntry 49 }


gs2124AclInfoConf           OBJECT IDENTIFIER ::= { gs2124AclInfo 4 }

gs2124AceNo OBJECT-TYPE
 SYNTAX  INTEGER(0..128)
 MAX-ACCESS     read-write
 STATUS  current
 DESCRIPTION
  "set 1 will create an ACL entry for edit, and return the entry index.
  others will return 0."
 ::= { gs2124AclInfoConf 1 }

gs2124AceMoveTo OBJECT-TYPE
 SYNTAX  INTEGER(1..128)
 MAX-ACCESS     read-write
 STATUS  current
 DESCRIPTION
  "Move the ace entry."
 ::= { gs2124AclInfoConf 2 }

gs2124AceIngressPortConf OBJECT-TYPE
 SYNTAX  DisplayString
 MAX-ACCESS     read-write
 STATUS  current
 DESCRIPTION
  "This is the ingress port number of the ace.
  Available parameter: any, Policy1~8, Port1~24."
 ::= { gs2124AclInfoConf 3 }

gs2124AceFrameTypeConf OBJECT-TYPE
 SYNTAX  INTEGER(0..3)
 MAX-ACCESS     read-write
 STATUS  current
 DESCRIPTION
  "This is the frame type of the ace.
  0:any 1: ethernet type 2:ARP 3:Ipv4 [default:0]"
 ::= { gs2124AclInfoConf 4 }

gs2124AceFrameTypeParameters           OBJECT IDENTIFIER ::= { gs2124AclInfoConf 5 }

gs2124EthernetTypeFilter OBJECT-TYPE
 SYNTAX  DisplayString
 MAX-ACCESS     read-write
 STATUS  current
 DESCRIPTION
  "This is the ethernet type of the ace."
 ::= { gs2124AceFrameTypeParameters 1 }

gs2124AclArpParameters           OBJECT IDENTIFIER ::= { gs2124AceFrameTypeParameters 2 }

gs2124AceArpRarp OBJECT-TYPE
 SYNTAX  INTEGER(0..3)
 MAX-ACCESS     read-write
 STATUS  current
 DESCRIPTION
  "This is the arp type of the ace.
  0:Any 1:Arp 2:Rarp 3:Other [default:0] "
 ::= { gs2124AclArpParameters 1 }

gs2124AceArpRequestReply OBJECT-TYPE
 SYNTAX  INTEGER(0..2)
 MAX-ACCESS     read-write
 STATUS  current
 DESCRIPTION
  "0:Any 1:Request 2:Reply [default:0]  "
 ::= { gs2124AclArpParameters 2 }

gs2124AceArpSenderIpFilter OBJECT-TYPE
 SYNTAX  INTEGER(0..2)
 MAX-ACCESS     read-write
 STATUS  current
 DESCRIPTION
  "0:Any 1:Host 2:Network"
 ::= { gs2124AclArpParameters 3 }

gs2124AceArpSenderIpAddress OBJECT-TYPE
 SYNTAX  DisplayString
 MAX-ACCESS     read-write
 STATUS  current
 DESCRIPTION
  "This is the arp sender ip address of the ace."
 ::= { gs2124AclArpParameters 4 }

gs2124AceArpSenderIpMask OBJECT-TYPE
 SYNTAX  DisplayString
 MAX-ACCESS     read-write
 STATUS  current
 DESCRIPTION
  "This is the arp sender ip mask of the ace."
 ::= { gs2124AclArpParameters 5 }

gs2124AceArpTargetIpFilter OBJECT-TYPE
 SYNTAX  INTEGER(0..2)
 MAX-ACCESS     read-write
 STATUS  current
 DESCRIPTION
  "0:Any 1:Host 2:Network  "
 ::= { gs2124AclArpParameters 6 }

gs2124AceArpTargetIpAddress OBJECT-TYPE
 SYNTAX  DisplayString
 MAX-ACCESS     read-write
 STATUS  current
 DESCRIPTION
  "0:Any 1:Host 2:Network  "
 ::= { gs2124AclArpParameters 7 }

gs2124AceArpTargetIpMask OBJECT-TYPE
 SYNTAX  DisplayString
 MAX-ACCESS     read-write
 STATUS  current
 DESCRIPTION
  "This is the arp target ip address of the ace."
 ::= { gs2124AclArpParameters 8 }

gs2124AceArpSmacMatch OBJECT-TYPE
 SYNTAX  DisplayString
 MAX-ACCESS     read-write
 STATUS  current
 DESCRIPTION
  "any / 0 / 1"
 ::= { gs2124AclArpParameters 9 }

gs2124AceArpRarpDmacMatch OBJECT-TYPE
 SYNTAX  DisplayString
 MAX-ACCESS     read-write
 STATUS  current
 DESCRIPTION
  "any / 0 / 1"
 ::= { gs2124AclArpParameters 10 }

gs2124AceArpIpEthernetLength OBJECT-TYPE
 SYNTAX  DisplayString
 MAX-ACCESS     read-write
 STATUS  current
 DESCRIPTION
  "any / 0 / 1"
 ::= { gs2124AclArpParameters 11 }

gs2124AceArpIp OBJECT-TYPE
 SYNTAX  DisplayString
 MAX-ACCESS     read-write
 STATUS  current
 DESCRIPTION
  "any / 0 / 1"
 ::= { gs2124AclArpParameters 12 }

gs2124AceArpEthernet OBJECT-TYPE
 SYNTAX  DisplayString
 MAX-ACCESS     read-write
 STATUS  current
 DESCRIPTION
  "any / 0 / 1"
 ::= { gs2124AclArpParameters 13 }


gs2124AclIpParameters           OBJECT IDENTIFIER ::= { gs2124AceFrameTypeParameters 3 }

gs2124AceIpProtocolFilter OBJECT-TYPE
 SYNTAX  INTEGER(0..4)
 MAX-ACCESS     read-write
 STATUS  current
 DESCRIPTION
  "This is the ip protocol of the ace.
  0:Any 1:ICMP 2:UDP 3:TCP 4:Other "
 ::= { gs2124AclIpParameters 1 }

gs2124AceIpProtocolFilterParameters          OBJECT IDENTIFIER ::= { gs2124AclIpParameters 2 }

gs2124AceIcmpParameters          OBJECT IDENTIFIER ::= { gs2124AceIpProtocolFilterParameters 1 }

gs2124AceIcmpTypeFilter OBJECT-TYPE
 SYNTAX  DisplayString
 MAX-ACCESS     read-write
 STATUS  current
 DESCRIPTION
  "This is the icmp type filter of the ace."
 ::= { gs2124AceIcmpParameters 1 }

gs2124AceIcmpCodeFilter OBJECT-TYPE
 SYNTAX  DisplayString
 MAX-ACCESS     read-write
 STATUS  current
 DESCRIPTION
  "This is the icmp code filter of the ace."
 ::= { gs2124AceIcmpParameters 2 }

gs2124AceUdpParameters         OBJECT IDENTIFIER ::= { gs2124AceIpProtocolFilterParameters 2 }

gs2124UdpSourcePortFilterConf OBJECT-TYPE
 SYNTAX  DisplayString
 MAX-ACCESS     read-write
 STATUS  current
 DESCRIPTION
  "This is the udp source port of the ace."
 ::= { gs2124AceUdpParameters 1 }

gs2124UdpDestPortFilterConf OBJECT-TYPE
 SYNTAX  DisplayString
 MAX-ACCESS     read-write
 STATUS  current
 DESCRIPTION
  "This is the udp destination port of the ace."
 ::= { gs2124AceUdpParameters 2 }

gs2124AceTcpParameters          OBJECT IDENTIFIER ::= { gs2124AceIpProtocolFilterParameters 3 }

gs2124TcpSourcePortFilterConf OBJECT-TYPE
 SYNTAX  DisplayString
 MAX-ACCESS     read-write
 STATUS  current
 DESCRIPTION
  "This is the tcp source port of the ace."
 ::= { gs2124AceTcpParameters 1 }

gs2124TcpDestPortFilterConf OBJECT-TYPE
 SYNTAX  DisplayString
 MAX-ACCESS     read-write
 STATUS  current
 DESCRIPTION
  "This is the tcp destination port of the ace."
 ::= { gs2124AceTcpParameters 2 }

gs2124TcpFINConf OBJECT-TYPE
 SYNTAX  DisplayString
 MAX-ACCESS     read-write
 STATUS  current
 DESCRIPTION
  "This is the tcp fin of the ace."
 ::= { gs2124AceTcpParameters 3 }

gs2124TcpSYNConf OBJECT-TYPE
 SYNTAX  DisplayString
 MAX-ACCESS     read-write
 STATUS  current
 DESCRIPTION
  "This is the tcp syn of the ace."
 ::= { gs2124AceTcpParameters 4 }

gs2124TcpRSTConf OBJECT-TYPE
 SYNTAX  DisplayString
 MAX-ACCESS     read-write
 STATUS  current
 DESCRIPTION
  "This is the tcp rst of the ace."
 ::= { gs2124AceTcpParameters 5 }

gs2124TcpPSHConf OBJECT-TYPE
 SYNTAX  DisplayString
 MAX-ACCESS     read-write
 STATUS  current
 DESCRIPTION
  "This is the tcp psh of the ace."
 ::= { gs2124AceTcpParameters 6 }

gs2124TcpACKConf OBJECT-TYPE
 SYNTAX  DisplayString
 MAX-ACCESS     read-write
 STATUS  current
 DESCRIPTION
  "This is the tcp ack of the ace."
 ::= { gs2124AceTcpParameters 7 }

gs2124TcpURGConf OBJECT-TYPE
 SYNTAX  DisplayString
 MAX-ACCESS     read-write
 STATUS  current
 DESCRIPTION
  "This is the tcp urg of the ace."
 ::= { gs2124AceTcpParameters 8 }


gs2124AceIpProtocolValue OBJECT-TYPE
 SYNTAX  INTEGER(0..4)
 MAX-ACCESS     read-write
 STATUS  current
 DESCRIPTION
  "This is the tcp protocol value of the ace."
 ::= { gs2124AclIpParameters 3 }

gs2124AceIpTTL OBJECT-TYPE
 SYNTAX  DisplayString
 MAX-ACCESS     read-write
 STATUS  current
 DESCRIPTION
  "Any / Zero / Non-zero "
 ::= { gs2124AclIpParameters 4 }

gs2124AceIpFragment OBJECT-TYPE
 SYNTAX  DisplayString
 MAX-ACCESS     read-write
 STATUS  current
 DESCRIPTION
  "Any/ Yes / No  "
 ::= { gs2124AclIpParameters 5 }

gs2124AceIpOption OBJECT-TYPE
 SYNTAX  DisplayString
 MAX-ACCESS     read-write
 STATUS  current
 DESCRIPTION
  "Any/ Yes / No  "
 ::= { gs2124AclIpParameters 6 }

gs2124AceSipFilter OBJECT-TYPE
 SYNTAX  INTEGER(0..2)
 MAX-ACCESS     read-write
 STATUS  current
 DESCRIPTION
  "0:Any 1:Host 2:Network"
 ::= { gs2124AclIpParameters 7 }

gs2124AceSipAddress OBJECT-TYPE
 SYNTAX  DisplayString
 MAX-ACCESS     read-write
 STATUS  current
 DESCRIPTION
  "This is the source ip address of the ace."
 ::= { gs2124AclIpParameters 8 }

gs2124AceSipMask OBJECT-TYPE
 SYNTAX  DisplayString
 MAX-ACCESS     read-write
 STATUS  current
 DESCRIPTION
  "This is the source ip mask of the ace."
 ::= { gs2124AclIpParameters 9 }

gs2124AceDipFilter OBJECT-TYPE
 SYNTAX  INTEGER(0..2)
 MAX-ACCESS     read-write
 STATUS  current
 DESCRIPTION
  "0:Any 1:Host 2:Network"
 ::= { gs2124AclIpParameters 10 }

gs2124AceDipAddress OBJECT-TYPE
 SYNTAX  DisplayString
 MAX-ACCESS     read-write
 STATUS  current
 DESCRIPTION
  "This is the destination ip address of the ace."
 ::= { gs2124AclIpParameters 11 }

gs2124AceDipMask OBJECT-TYPE
 SYNTAX  DisplayString
 MAX-ACCESS     read-write
 STATUS  current
 DESCRIPTION
  "This is the destination ip mask of the ace."
 ::= { gs2124AclIpParameters 12 }


gs2124AceActionConf OBJECT-TYPE
 SYNTAX  INTEGER(0|1)
 MAX-ACCESS     read-write
 STATUS  current
 DESCRIPTION
  "0:Deny 1:Permit [default:1] "
 ::= { gs2124AclInfoConf 6 }

gs2124AceRateLimiterConf OBJECT-TYPE
 SYNTAX  INTEGER(0..16)
 MAX-ACCESS     read-write
 STATUS  current
 DESCRIPTION
  "Specify a rate limiter which is available from 0 to 16(0 means disable) for an ACE."
 ::= { gs2124AclInfoConf 7 }

gs2124AcePortCopyConf OBJECT-TYPE
 SYNTAX  INTEGER(0..24)
 MAX-ACCESS     read-write
 STATUS  current
 DESCRIPTION
  "Packets will be copied to this port if hit this ACE rule.
  Port number is available from 0 to 24(0 means disable)."
 ::= { gs2124AclInfoConf 8 }

gs2124AceMacParameters           OBJECT IDENTIFIER ::= { gs2124AclInfoConf 9 }

gs2124AceSmacFilter OBJECT-TYPE
 SYNTAX  DisplayString
 MAX-ACCESS     read-write
 STATUS  current
 DESCRIPTION
  "This is the source mac of the ace."
 ::= { gs2124AceMacParameters 1 }

gs2124AceDmacFilter OBJECT-TYPE
 SYNTAX  DisplayString
 MAX-ACCESS     read-write
 STATUS  current
 DESCRIPTION
  "This is the destination mac of the ace."
 ::= { gs2124AceMacParameters 2 }


gs2124AceVlanParameters           OBJECT IDENTIFIER ::= { gs2124AclInfoConf 10 }

gs2124AceVlanIdFilter OBJECT-TYPE
 SYNTAX  DisplayString
 MAX-ACCESS     read-write
 STATUS  current
 DESCRIPTION
  "Specify the VID for the ACE. Available parameter: any, 1~4094."
 ::= { gs2124AceVlanParameters 1 }

gs2124AceTagPriority OBJECT-TYPE
 SYNTAX  DisplayString
 MAX-ACCESS     read-write
 STATUS  current
 DESCRIPTION
  "Specify the tag priority for the ACE. Available parameter: any, 0~7."
 ::= { gs2124AceVlanParameters 2 }


gs2124AceInfoEntryAction OBJECT-TYPE
 SYNTAX  INTEGER(1..4)
 MAX-ACCESS     read-write
 STATUS  current
 DESCRIPTION
  "1:active 2:notInService 3:delete 4:Undo "
 ::= { gs2124AclInfoConf 11 }

gs2124IpMacBind            OBJECT IDENTIFIER ::= { gs2124Produces 19 }

gs2124IpMacBindConf           OBJECT IDENTIFIER ::= { gs2124IpMacBind 1 }

gs2124IpMacBindstate OBJECT-TYPE
 SYNTAX  INTEGER(0|1)
 MAX-ACCESS     read-write
 STATUS  current
 DESCRIPTION
  " Set ip mac binding state.
   0 - Disable
   1 - Enable"
 ::= { gs2124IpMacBindConf 1 }

gs2124IpMacBindTrustPort OBJECT-TYPE
 SYNTAX  DisplayString
 MAX-ACCESS     read-write
 STATUS  current
 DESCRIPTION
  "Set trustport,
   Port range : 1,5-7, available from 1 to 24"
 ::= { gs2124IpMacBindConf 2 }

gs2124IpMacBindSetting           OBJECT IDENTIFIER ::= { gs2124IpMacBind 2 }

gs2124IpMacBindSettingNumber OBJECT-TYPE
 SYNTAX  INTEGER(0..1024)
 MAX-ACCESS     read-write
 STATUS  current
 DESCRIPTION
  "Get the amount of ip_mac_binding entry."
 ::= { gs2124IpMacBindSetting 1 }

gs2124IpMacBindSettingEntryCreate OBJECT-TYPE
 SYNTAX  INTEGER(0|1)
 MAX-ACCESS     read-write
 STATUS  current
 DESCRIPTION
  "Create ip_mac_binding entry.
   0: none
   1: creat a entry."
 ::= { gs2124IpMacBindSetting 2 }

gs2124IpMacBindSettingTable OBJECT-TYPE
 SYNTAX  SEQUENCE OF GS2124IpMacBindSettingEntry
 MAX-ACCESS not-accessible
 STATUS  current
    DESCRIPTION
        "This is a list of GS2124IpMacBindSettingEntry."
 ::= { gs2124IpMacBindSetting 3 }

GS2124IpMacBindSettingEntry ::=
SEQUENCE {
    gs2124IpMacBindSettingIndex        INTEGER,
    gs2124IpMacBindSettingMAC          DisplayString,
    gs2124IpMacBindSettingIP           IpAddress,
    gs2124IpMacBindSettingPort         INTEGER,
    gs2124IpMacBindSettingVID          INTEGER,
    gs2124IpMacBindSettingEntryAction  INTEGER
}

gs2124IpMacBindSettingEntry OBJECT-TYPE
 SYNTAX  GS2124IpMacBindSettingEntry
 MAX-ACCESS     not-accessible
 STATUS  current
 DESCRIPTION
  "This is the entry of the ip_mac_binding information."
 INDEX {gs2124IpMacBindSettingIndex}
 ::= { gs2124IpMacBindSettingTable 1 }

gs2124IpMacBindSettingIndex OBJECT-TYPE
 SYNTAX  INTEGER(1..1024)
 MAX-ACCESS     not-accessible
 STATUS  current
 DESCRIPTION
  "This is the index of the ip_mac_binding entry."
 ::= { gs2124IpMacBindSettingEntry 1 }

gs2124IpMacBindSettingMAC OBJECT-TYPE
 SYNTAX  DisplayString
 MAX-ACCESS     read-write
 STATUS  current
 DESCRIPTION
  "This is the mac address of the ip_mac_binding entry."
 ::= { gs2124IpMacBindSettingEntry 2 }

gs2124IpMacBindSettingIP OBJECT-TYPE
 SYNTAX  IpAddress
 MAX-ACCESS     read-write
 STATUS  current
 DESCRIPTION
  "This is the ip address of the ip_mac_binding entry."
 ::= { gs2124IpMacBindSettingEntry 3 }

gs2124IpMacBindSettingPort OBJECT-TYPE
 SYNTAX  INTEGER(1..24)
 MAX-ACCESS     read-write
 STATUS  current
 DESCRIPTION
  "This is the port number of the ip_mac_binding entry."
 ::= { gs2124IpMacBindSettingEntry 4 }

gs2124IpMacBindSettingVID OBJECT-TYPE
 SYNTAX  INTEGER(1..4094)
 MAX-ACCESS     read-write
 STATUS  current
 DESCRIPTION
  "This is the vid of the ip_mac_binding entry."
 ::= { gs2124IpMacBindSettingEntry 5 }

gs2124IpMacBindSettingEntryAction OBJECT-TYPE
 SYNTAX  INTEGER(1..3)
 MAX-ACCESS     read-write
 STATUS  current
 DESCRIPTION
  "This is the action of the ip_mac_binding entry.
   1 - active
   2 - notInService
   3 - delete"
 ::= { gs2124IpMacBindSettingEntry 6 }

gs2124Dot1X            OBJECT IDENTIFIER ::= { gs2124Produces 23 }

gs2124Dot1XServerConf           OBJECT IDENTIFIER ::= { gs2124Dot1X 1 }

gs2124Dot1XServerConfAuthenticationServerIp OBJECT-TYPE
 SYNTAX  IpAddress
 MAX-ACCESS     read-write
 STATUS  current
 DESCRIPTION
  "Get/Set authentication server ip"
 ::= { gs2124Dot1XServerConf 1 }

gs2124Dot1XServerConfAuthenticationUdpPort OBJECT-TYPE
 SYNTAX  INTEGER(1..65535)
 MAX-ACCESS     read-write
 STATUS  current
 DESCRIPTION
  "Get/Set IEEE 802.1X authentication UDP port number"
 ::= { gs2124Dot1XServerConf 2 }

gs2124Dot1XServerConfAuthenticationServerIp2 OBJECT-TYPE
 SYNTAX  IpAddress
 MAX-ACCESS     read-write
 STATUS  current
 DESCRIPTION
  "Get/Set authentication server ip 2"
 ::= { gs2124Dot1XServerConf 3 }

gs2124Dot1XServerConfAuthenticationUdpPort2 OBJECT-TYPE
 SYNTAX  INTEGER(1..65535)
 MAX-ACCESS     read-write
 STATUS  current
 DESCRIPTION
  "Get/Set IEEE 802.1X authentication UDP port number"
 ::= { gs2124Dot1XServerConf 4 }

gs2124Dot1XServerConfAuthenticationSecretKey OBJECT-TYPE
 SYNTAX  DisplayString
 MAX-ACCESS     read-write
 STATUS  current
 DESCRIPTION
  "Get/Set IEEE 802.1X authentication secret key"
 ::= { gs2124Dot1XServerConf 5 }

gs2124Dot1XServerConfAccountingServerIp OBJECT-TYPE
 SYNTAX  IpAddress
 MAX-ACCESS     read-write
 STATUS  current
 DESCRIPTION
  "Get/Set IEEE 802.1X accounting service IP"
 ::= { gs2124Dot1XServerConf 6 }

gs2124Dot1XServerConfAccountingUdpPort OBJECT-TYPE
 SYNTAX  INTEGER(1..65535)
 MAX-ACCESS     read-write
 STATUS  current
 DESCRIPTION
  "Get/Set IEEE 802.1X accounting UDP port number"
 ::= { gs2124Dot1XServerConf 7 }

gs2124Dot1XServerConfAccountingServerIp2 OBJECT-TYPE
 SYNTAX  IpAddress
 MAX-ACCESS     read-write
 STATUS  current
 DESCRIPTION
  "Get/Set IEEE 802.1X accounting service IP 2"
 ::= { gs2124Dot1XServerConf 8 }

gs2124Dot1XServerConfAccountingUdpPort2 OBJECT-TYPE
 SYNTAX  INTEGER(1..65535)
 MAX-ACCESS     read-write
 STATUS  current
 DESCRIPTION
  "Get/Set IEEE 802.1X accounting UDP port number"
 ::= { gs2124Dot1XServerConf 9 }

gs2124Dot1XServerConfAccountingSecretKey OBJECT-TYPE
 SYNTAX  DisplayString
 MAX-ACCESS     read-write
 STATUS  current
 DESCRIPTION
  "Get/Set IEEE 802.1X accounting secret key"
 ::= { gs2124Dot1XServerConf 10 }

gs2124Dot1XPortConfTable OBJECT-TYPE
 SYNTAX  SEQUENCE OF GS2124Dot1XPortConfEntry
 MAX-ACCESS not-accessible
 STATUS  current
    DESCRIPTION
        "A table that contains the configuration objects for the
         Authenticator PAE associated with each port."
 ::= { gs2124Dot1X 2 }

GS2124Dot1XPortConfEntry ::=
SEQUENCE {
    gs2124Dot1XPort                INTEGER,
    gs2124Dot1XPortMode            INTEGER,
    gs2124Dot1XPortControl         INTEGER,
    gs2124Dot1XPortreAuthMax       INTEGER,
    gs2124Dot1XPorttxPeriod        INTEGER,
    gs2124Dot1XPortquietPeriod     INTEGER,
    gs2124Dot1XPortreAuthEnabled   INTEGER,
    gs2124Dot1XPortreAuthPeriod    INTEGER,
    gs2124Dot1XPortmaxReq          INTEGER,
    gs2124Dot1XPortsuppTimeout     INTEGER,
    gs2124Dot1XPortserverTimeout   INTEGER,
    gs2124Dot1XPortVlanAssignment  INTEGER,
    gs2124Dot1XPortGuestVlan       INTEGER,
    gs2124Dot1XPortAuthFailedVlan  INTEGER
}

gs2124Dot1XPortConfEntry OBJECT-TYPE
 SYNTAX  GS2124Dot1XPortConfEntry
 MAX-ACCESS     not-accessible
 STATUS  current
 DESCRIPTION
  "The configuration information for an Authenticator PAE."
 INDEX {gs2124Dot1XPort}
 ::= { gs2124Dot1XPortConfTable 1 }

gs2124Dot1XPort OBJECT-TYPE
 SYNTAX  INTEGER(1..24)
 MAX-ACCESS     read-write
 STATUS  current
 DESCRIPTION
   "The port index of 802.1X port configuration table."
 ::= { gs2124Dot1XPortConfEntry 1 }

gs2124Dot1XPortMode OBJECT-TYPE
 SYNTAX  INTEGER(0..4)
 MAX-ACCESS     read-write
 STATUS  current
 DESCRIPTION
  "Get/Set IEEE 802.1X port mode.
   0 - Disable
   1 - Normal
   2 - Advanced
   3 - Clientless
   4 - Auto"
 ::= { gs2124Dot1XPortConfEntry 2 }

gs2124Dot1XPortControl OBJECT-TYPE
 SYNTAX  INTEGER(0..2)
 MAX-ACCESS     read-write
 STATUS  current
 DESCRIPTION
  "The current value of the controlled Port
   control parameter of the Port.
  0 : ForceUnauthorized,
  1 : ForceAuthorized,
  2 : Auto
        "
 ::= { gs2124Dot1XPortConfEntry 3 }

gs2124Dot1XPortreAuthMax OBJECT-TYPE
 SYNTAX  INTEGER(1..10)
 MAX-ACCESS     read-write
 STATUS  current
 DESCRIPTION
  "The value of the reAuthMax constant currently in use by
   the Authenticator PAE state machine. Value : 1-10."
 ::= { gs2124Dot1XPortConfEntry 4 }


gs2124Dot1XPorttxPeriod OBJECT-TYPE
 SYNTAX  INTEGER(1..65535)
 MAX-ACCESS     read-write
 STATUS  current
 DESCRIPTION
  "The value, in seconds, of the txPeriod constant
   currently in use by the Authenticator PAE state
   machine. Value : 1-65535."
 ::= { gs2124Dot1XPortConfEntry 5 }

gs2124Dot1XPortquietPeriod OBJECT-TYPE
 SYNTAX  INTEGER(0..65535)
 MAX-ACCESS     read-write
 STATUS  current
 DESCRIPTION
  "The value, in seconds, of the quietPeriod constant
   currently in use by the Authenticator PAE state
   machine. Value : 0-65535."
 ::= { gs2124Dot1XPortConfEntry 6 }

gs2124Dot1XPortreAuthEnabled OBJECT-TYPE
 SYNTAX  INTEGER(0|1)
 MAX-ACCESS     read-write
 STATUS  current
 DESCRIPTION
  "The enable/disable control used by the Reauthentication
   Timer state machine.
   0 - Disable
   1 - Enable"
 ::= { gs2124Dot1XPortConfEntry 7 }

gs2124Dot1XPortreAuthPeriod OBJECT-TYPE
 SYNTAX  INTEGER(1..65535)
 MAX-ACCESS     read-write
 STATUS  current
 DESCRIPTION
		"The value(1..65535), in seconds, of the reAuthPeriod constant
   currently in use by the Reauthentication Timer state
   machine."
 ::= { gs2124Dot1XPortConfEntry 8 }

gs2124Dot1XPortmaxReq OBJECT-TYPE
 SYNTAX  INTEGER(1..10)
 MAX-ACCESS     read-write
 STATUS  current
 DESCRIPTION
		"The value(1..10) of the maxReq constant currently in use by
   the Backend Authentication state machine."
 ::= { gs2124Dot1XPortConfEntry 9 }

gs2124Dot1XPortsuppTimeout OBJECT-TYPE
 SYNTAX  INTEGER(1..255)
 MAX-ACCESS     read-write
 STATUS  current
 DESCRIPTION
		"The value(1..255), in seconds, of the suppTimeout constant
   currently in use by the Backend Authentication state
   machine."
 ::= { gs2124Dot1XPortConfEntry 10 }

gs2124Dot1XPortserverTimeout OBJECT-TYPE
 SYNTAX  INTEGER(1..255)
 MAX-ACCESS     read-write
 STATUS  current
 DESCRIPTION
		"The value(1..255), in seconds, of the serverTimeout constant
   currently in use by the Backend Authentication state
   machine."
 ::= { gs2124Dot1XPortConfEntry 11 }

gs2124Dot1XPortVlanAssignment OBJECT-TYPE
 SYNTAX  INTEGER(0..1)
 MAX-ACCESS     read-write
 STATUS  current
 DESCRIPTION
  "Get/Set IEEE 802.1X's VlanAssignment mode.
   0 - Disable
   1 - Enable"
 ::= { gs2124Dot1XPortConfEntry 12 }

gs2124Dot1XPortGuestVlan OBJECT-TYPE
 SYNTAX  INTEGER(0..4094)
 MAX-ACCESS     read-write
 STATUS  current
 DESCRIPTION
  "Get/Set IEEE 802.1X Guest Vlan.
   0 : N/A
   1~4094 : The VlanID"
 ::= { gs2124Dot1XPortConfEntry 13 }

gs2124Dot1XPortAuthFailedVlan OBJECT-TYPE
 SYNTAX  INTEGER(0..4094)
 MAX-ACCESS     read-write
 STATUS  current
 DESCRIPTION
  "Get/Set IEEE 802.1X Authentication Failed Vlan.
   0 : N/A
   1~4094 : The VlanID"
 ::= { gs2124Dot1XPortConfEntry 14 }

gs2124Dot1XStatusTable OBJECT-TYPE
 SYNTAX  SEQUENCE OF GS2124Dot1XStatusEntry
 MAX-ACCESS not-accessible
 STATUS  current
    DESCRIPTION
        "A table that contains the status objects for the
         Authenticator PAE associated with each port."
 ::= { gs2124Dot1X 3 }

GS2124Dot1XStatusEntry ::=
SEQUENCE {
    gs2124Dot1XStatusIndex   INTEGER,
    gs2124Dot1XStatusMode    DisplayString,
    gs2124Dot1XStatusStatus  DisplayString,
    gs2124Dot1XVlanPlicy     DisplayString
}

gs2124Dot1XStatusEntry OBJECT-TYPE
 SYNTAX  GS2124Dot1XStatusEntry
 MAX-ACCESS     not-accessible
 STATUS  current
 DESCRIPTION
  "The status information for an Authenticator PAE."
 INDEX {gs2124Dot1XStatusIndex}
 ::= { gs2124Dot1XStatusTable 1 }

gs2124Dot1XStatusIndex OBJECT-TYPE
 SYNTAX  INTEGER(1..24)
 MAX-ACCESS     not-accessible
 STATUS  current
 DESCRIPTION
  "The port index of 802.1X status table."
 ::= { gs2124Dot1XStatusEntry 1 }

gs2124Dot1XStatusMode OBJECT-TYPE
 SYNTAX  DisplayString
 MAX-ACCESS     read-only
 STATUS  current
 DESCRIPTION
  "The current mode of the controlled port."
 ::= { gs2124Dot1XStatusEntry 2 }

gs2124Dot1XStatusStatus OBJECT-TYPE
 SYNTAX  DisplayString
 MAX-ACCESS     read-only
 STATUS  current
 DESCRIPTION
  "The current status of the controlled port."
 ::= { gs2124Dot1XStatusEntry 3 }

gs2124Dot1XVlanPlicy OBJECT-TYPE
 SYNTAX  DisplayString
 MAX-ACCESS     read-only
 STATUS  current
 DESCRIPTION
  "The current Vlan Policy of the controlled port."
 ::= { gs2124Dot1XStatusEntry 4 }

gs2124Dot1XStatisticsTable OBJECT-TYPE
 SYNTAX  SEQUENCE OF GS2124Dot1XStatisticsEntry
 MAX-ACCESS not-accessible
 STATUS  current
    DESCRIPTION
        "A table that contains the statistics objects for the
         Authenticator PAE associated with each port."
 ::= { gs2124Dot1X 4 }

GS2124Dot1XStatisticsEntry ::=
SEQUENCE {
    gs2124Dot1XStatisticsIndex                        INTEGER,
    gs2124Dot1XClearCounter                           INTEGER,
    gs2124Dot1XAuthEntersConnecting                   Counter32,
    gs2124Dot1XauthEapLogoffsWhileConnecting          Counter32,
    gs2124Dot1XAuthEntersAuthenticating               Counter32,
    gs2124Dot1XAuthAuthSuccessesWhileAuthenticating   Counter32,
    gs2124Dot1XAuthAuthTimeoutsWhileAuthenticating    Counter32,
    gs2124Dot1XAuthAuthFailWhileAuthenticating        Counter32,
    gs2124Dot1XAuthAuthEapStartsWhileAuthenticating   Counter32,
    gs2124Dot1XAuthAuthEapLogoffWhileAuthenticating   Counter32,
    gs2124Dot1XAuthAuthReauthsWhileAuthenticated      Counter32,
    gs2124Dot1XAuthAuthEapStartsWhileAuthenticated    Counter32,
    gs2124Dot1XAuthAuthEapLogoffWhileAuthenticated    Counter32,
    gs2124Dot1XBackendResponses                       Counter32,
    gs2124Dot1XBackendAccessChallenges                Counter32,
    gs2124Dot1XBackendOtherRequestsToSupplicant       Counter32,
    gs2124Dot1XBackendAuthSuccesses                   Counter32,
    gs2124Dot1XBackendAuthFails                       Counter32,
    gs2124Dot1XAuthEapolFramesRx                      Counter32,
    gs2124Dot1XAuthEapolFramesTx                      Counter32,
    gs2124Dot1XAuthEapolStartFramesRx                 Counter32,
    gs2124Dot1XAuthEapolLogoffFramesRx                Counter32,
    gs2124Dot1XAuthEapolRespIdFramesRx                Counter32,
    gs2124Dot1XAuthEapolRespFramesRx                  Counter32,
    gs2124Dot1XAuthEapolReqIdFramesTx                 Counter32,
    gs2124Dot1XAuthEapolReqFramesTx                   Counter32,
    gs2124Dot1XAuthInvalidEapolFramesRx               Counter32,
    gs2124Dot1XAuthEapLengthErrorFramesRx             Counter32,
    gs2124Dot1XAuthLastEapolFrameVersion              Counter32,
    gs2124Dot1XAuthLastEapolFrameSource               DisplayString
}

gs2124Dot1XStatisticsEntry OBJECT-TYPE
 SYNTAX  GS2124Dot1XStatisticsEntry
 MAX-ACCESS     not-accessible
 STATUS  current
 DESCRIPTION
  "The statistics information for an Authenticator PAE."
 INDEX {gs2124Dot1XStatisticsIndex}
 ::= { gs2124Dot1XStatisticsTable 1 }

gs2124Dot1XStatisticsIndex OBJECT-TYPE
 SYNTAX  INTEGER(1..24)
 MAX-ACCESS     not-accessible
 STATUS  current
 DESCRIPTION
  "The port index of the 802.1X statistics table."
 ::= { gs2124Dot1XStatisticsEntry 1 }

gs2124Dot1XClearCounter OBJECT-TYPE
 SYNTAX  INTEGER(0|1)
 MAX-ACCESS     read-write
 STATUS  current
 DESCRIPTION
  "Reset the 802.1X counter associated with this port.
   0 - do nothing
   1 - clear "
 ::= { gs2124Dot1XStatisticsEntry 2 }

gs2124Dot1XAuthEntersConnecting OBJECT-TYPE
 SYNTAX  Counter32
 MAX-ACCESS     read-only
 STATUS  current
 DESCRIPTION
  "Counts the number of times that the state machine
   transitions to the CONNECTING state from any other
   state."
 ::= { gs2124Dot1XStatisticsEntry 3 }

gs2124Dot1XauthEapLogoffsWhileConnecting OBJECT-TYPE
 SYNTAX  Counter32
 MAX-ACCESS     read-only
 STATUS  current
 DESCRIPTION
  "Counts the number of times that the state machine
   transitions from CONNECTING to DISCONNECTED as a result
   of receiving an EAPOL-Logoff message."
 ::= { gs2124Dot1XStatisticsEntry 4 }

gs2124Dot1XAuthEntersAuthenticating OBJECT-TYPE
 SYNTAX  Counter32
 MAX-ACCESS     read-only
 STATUS  current
 DESCRIPTION
  "Counts the number of times that the state machine
   transitions from CONNECTING to AUTHENTICATING, as a
   result of an EAP-Response/Identity message being
   received from the Supplicant."
 ::= { gs2124Dot1XStatisticsEntry 5 }

gs2124Dot1XAuthAuthSuccessesWhileAuthenticating OBJECT-TYPE
 SYNTAX  Counter32
 MAX-ACCESS     read-only
 STATUS  current
 DESCRIPTION
  "Counts the number of times that the state machine
   transitions from AUTHENTICATING to AUTHENTICATED, as a
   result of the Backend Authentication state machine
   indicating successful authentication of the Supplicant."
 ::= { gs2124Dot1XStatisticsEntry 6 }

gs2124Dot1XAuthAuthTimeoutsWhileAuthenticating OBJECT-TYPE
 SYNTAX  Counter32
 MAX-ACCESS     read-only
 STATUS  current
 DESCRIPTION
  "Counts the number of times that the state machine
   transitions from AUTHENTICATING to ABORTING, as a result
   of the Backend Authentication state machine indicating
   authentication timeout."
 ::= { gs2124Dot1XStatisticsEntry 7 }

gs2124Dot1XAuthAuthFailWhileAuthenticating OBJECT-TYPE
 SYNTAX  Counter32
 MAX-ACCESS     read-only
 STATUS  current
 DESCRIPTION
  "Counts the number of times that the state machine
   transitions from AUTHENTICATING to HELD, as a result
   of the Backend Authentication state machine indicating
   authentication failure."
 ::= { gs2124Dot1XStatisticsEntry 8 }

gs2124Dot1XAuthAuthEapStartsWhileAuthenticating OBJECT-TYPE
 SYNTAX  Counter32
 MAX-ACCESS     read-only
 STATUS  current
 DESCRIPTION
  "Counts the number of times that the state machine
   transitions from AUTHENTICATING to ABORTING, as a result
   of an EAPOL-Start message being received from the
   Supplicant."
 ::= { gs2124Dot1XStatisticsEntry 9 }

gs2124Dot1XAuthAuthEapLogoffWhileAuthenticating OBJECT-TYPE
 SYNTAX  Counter32
 MAX-ACCESS     read-only
 STATUS  current
 DESCRIPTION
  "Counts the number of times that the state machine
   transitions from AUTHENTICATING to ABORTING, as a result
   of an EAPOL-Logoff message being received from the
   Supplicant."
 ::= { gs2124Dot1XStatisticsEntry 10 }

gs2124Dot1XAuthAuthReauthsWhileAuthenticated OBJECT-TYPE
 SYNTAX  Counter32
 MAX-ACCESS     read-only
 STATUS  current
 DESCRIPTION
  "Counts the number of times that the state machine
   transitions from AUTHENTICATED to CONNECTING, as a
   result of a reauthentication request."
 ::= { gs2124Dot1XStatisticsEntry 11 }

gs2124Dot1XAuthAuthEapStartsWhileAuthenticated OBJECT-TYPE
 SYNTAX  Counter32
 MAX-ACCESS     read-only
 STATUS  current
 DESCRIPTION
  "Counts the number of times that the state machine
   transitions from AUTHENTICATED to CONNECTING, as a
   result of an EAPOL-Start message being received from
   the Supplicant."
 ::= { gs2124Dot1XStatisticsEntry 12 }

gs2124Dot1XAuthAuthEapLogoffWhileAuthenticated OBJECT-TYPE
 SYNTAX  Counter32
 MAX-ACCESS     read-only
 STATUS  current
 DESCRIPTION
  "Counts the number of times that the state machine
   transitions from AUTHENTICATED to DISCONNECTED, as a
   result of an EAPOL-Logoff message being received from
   the Supplicant."
 ::= { gs2124Dot1XStatisticsEntry 13 }

gs2124Dot1XBackendResponses OBJECT-TYPE
 SYNTAX  Counter32
 MAX-ACCESS     read-only
 STATUS  current
 DESCRIPTION
  "Counts the number of times that the state machine sends
   an initial Access-Request packet to the Authentication
   server (i.e., executes sendRespToServer on entry to the
   RESPONSE state). Indicates that the Authenticator
   attempted communication with the Authentication Server."
 ::= { gs2124Dot1XStatisticsEntry 14 }

gs2124Dot1XBackendAccessChallenges OBJECT-TYPE
 SYNTAX  Counter32
 MAX-ACCESS     read-only
 STATUS  current
 DESCRIPTION
  "Counts the number of times that the state machine receives
   an initial Access-Challenge packet from the Authentication
   server (i.e., aReq becomes TRUE, causing exit from the
   RESPONSE state). Indicates that the Authentication Server
   has communication with the Authenticator."
 ::= { gs2124Dot1XStatisticsEntry 15 }

gs2124Dot1XBackendOtherRequestsToSupplicant OBJECT-TYPE
 SYNTAX  Counter32
 MAX-ACCESS     read-only
 STATUS  current
 DESCRIPTION
  "Counts the number of times that the state machine sends
   an EAP-Request packet (other than Identity, Notification,
   Failure or Success message) to the Supplicant (i.e.,
   executes txReq on entry to the REQUEST state). Indicates
   that Authenticator chose an EAP-method."
 ::= { gs2124Dot1XStatisticsEntry 16 }

gs2124Dot1XBackendAuthSuccesses OBJECT-TYPE
 SYNTAX  Counter32
 MAX-ACCESS     read-only
 STATUS  current
 DESCRIPTION
  "Counts the number of times that the state machine receives
   an EAP-Success message from the Authentication Server (i.e.,
   aSuccess becomes TRUE, causing a transitions from RESPONSE to
   SUCCESS). Indicates that the Supplicant has successfully
   authenticated to the Authentication Server."
 ::= { gs2124Dot1XStatisticsEntry 17 }

gs2124Dot1XBackendAuthFails OBJECT-TYPE
 SYNTAX  Counter32
 MAX-ACCESS     read-only
 STATUS  current
 DESCRIPTION
  "Counts the number of times that the state machine receives
   an EAP-Failure message from the Authentication Server (i.e.,
   aFail becomes TRUE, causing a transitions from RESPONSE to
   FAIL). Indicates that the Supplicant has not authenticated
   to the Authentication Server."
 ::= { gs2124Dot1XStatisticsEntry 18 }

gs2124Dot1XAuthEapolFramesRx OBJECT-TYPE
 SYNTAX  Counter32
 MAX-ACCESS     read-only
 STATUS  current
 DESCRIPTION
  "The number of valid EAPOL frames of any type
   that have been received by this Authenticator."
 ::= { gs2124Dot1XStatisticsEntry 19 }

gs2124Dot1XAuthEapolFramesTx OBJECT-TYPE
 SYNTAX  Counter32
 MAX-ACCESS     read-only
 STATUS  current
 DESCRIPTION
  "The number of valid EAPOL frames of any type
   that have been transmitted by this Authenticator."
 ::= { gs2124Dot1XStatisticsEntry 20 }

gs2124Dot1XAuthEapolStartFramesRx OBJECT-TYPE
 SYNTAX  Counter32
 MAX-ACCESS     read-only
 STATUS  current
 DESCRIPTION
  "The number of EAPOL Start frames that have
   been received by this Authenticator."
 ::= { gs2124Dot1XStatisticsEntry 21 }

gs2124Dot1XAuthEapolLogoffFramesRx OBJECT-TYPE
 SYNTAX  Counter32
 MAX-ACCESS     read-only
 STATUS  current
 DESCRIPTION
  "The number of EAPOL Logoff frames that have
   been received by this Authenticator."
 ::= { gs2124Dot1XStatisticsEntry 22 }

gs2124Dot1XAuthEapolRespIdFramesRx OBJECT-TYPE
 SYNTAX  Counter32
 MAX-ACCESS     read-only
 STATUS  current
 DESCRIPTION
  "The number of EAP Resp/Id frames that have
   been received by this Authenticator."
 ::= { gs2124Dot1XStatisticsEntry 23 }

gs2124Dot1XAuthEapolRespFramesRx OBJECT-TYPE
 SYNTAX  Counter32
 MAX-ACCESS     read-only
 STATUS  current
 DESCRIPTION
  "The number of valid EAP Response frames
   (other than Resp/Id frames) that have been
   received by this Authenticator."
 ::= { gs2124Dot1XStatisticsEntry 24 }

gs2124Dot1XAuthEapolReqIdFramesTx OBJECT-TYPE
 SYNTAX  Counter32
 MAX-ACCESS     read-only
 STATUS  current
 DESCRIPTION
  "The number of EAP Req/Id frames that have
   been transmitted by this Authenticator."
 ::= { gs2124Dot1XStatisticsEntry 25 }

gs2124Dot1XAuthEapolReqFramesTx OBJECT-TYPE
 SYNTAX  Counter32
 MAX-ACCESS     read-only
 STATUS  current
 DESCRIPTION
  "The number of valid EAP Request frames
   (other than Req/Id frames) that have been
   transmitted by this Authenticator."
 ::= { gs2124Dot1XStatisticsEntry 26 }

gs2124Dot1XAuthInvalidEapolFramesRx OBJECT-TYPE
 SYNTAX  Counter32
 MAX-ACCESS     read-only
 STATUS  current
 DESCRIPTION
  "The number of EAPOL frames that have been
   received by this Authenticator in which the
   frame type is not recognized."
 ::= { gs2124Dot1XStatisticsEntry 27 }

gs2124Dot1XAuthEapLengthErrorFramesRx OBJECT-TYPE
 SYNTAX  Counter32
 MAX-ACCESS     read-only
 STATUS  current
 DESCRIPTION
  "The number of EAPOL frames that have been
   received by this Authenticator in which the
   Packet Body Length field is invalid."
 ::= { gs2124Dot1XStatisticsEntry 28 }

gs2124Dot1XAuthLastEapolFrameVersion OBJECT-TYPE
 SYNTAX  Counter32
 MAX-ACCESS     read-only
 STATUS  current
 DESCRIPTION
  "The protocol version number carried in the
   most recently received EAPOL frames."
 ::= { gs2124Dot1XStatisticsEntry 29 }

gs2124Dot1XAuthLastEapolFrameSource OBJECT-TYPE
 SYNTAX  DisplayString
 MAX-ACCESS     read-only
 STATUS  current
 DESCRIPTION
  "The source MAC address carried in the
   most recently received EAPOL frames."
 ::= { gs2124Dot1XStatisticsEntry 30 }


gs2124TrunkInfo       OBJECT IDENTIFIER ::= { gs2124Produces 24 }

gs2124TrunkPort      OBJECT IDENTIFIER ::= { gs2124TrunkInfo 1 }

gs2124TrunkPortTable OBJECT-TYPE
 SYNTAX  SEQUENCE OF GS2124TrunkPortEntry
 MAX-ACCESS not-accessible
 STATUS  current
    DESCRIPTION
        "This is a list of GS2124TrunkPortEntry."
 ::= { gs2124TrunkPort 1 }

GS2124TrunkPortEntry ::=
SEQUENCE {
    gs2124TrunkPortIndex INTEGER,
    gs2124TrunkPortMethod    INTEGER,
    gs2124TrunkPortGroup  INTEGER,
    gs2124TrunkPortActiveLacp INTEGER,
    gs2124TrunkPortAggtr INTEGER,
    gs2124TrunkPortStatus INTEGER,
    gs2124TrunkPortCurrentMode INTEGER
}

gs2124TrunkPortEntry OBJECT-TYPE
 SYNTAX  GS2124TrunkPortEntry
 MAX-ACCESS     not-accessible
 STATUS  current
 DESCRIPTION
        "Entry(s) for trunk table."
 INDEX {gs2124TrunkPortIndex}
 ::= { gs2124TrunkPortTable 1 }

gs2124TrunkPortIndex OBJECT-TYPE
 SYNTAX  INTEGER(1..24)
 MAX-ACCESS     not-accessible
 STATUS  current
 DESCRIPTION
        "The port index of trunk table."
 ::= { gs2124TrunkPortEntry 1 }

gs2124TrunkPortMethod  OBJECT-TYPE
    SYNTAX      INTEGER(0..2)
    MAX-ACCESS  read-write
    STATUS      current
    DESCRIPTION
        "The method of trunk port.
  0 : None,
  1 : LACP,
  2 : Static.
        "
    ::= { gs2124TrunkPortEntry 2 }

gs2124TrunkPortGroup  OBJECT-TYPE
    SYNTAX      INTEGER(0..12)
    MAX-ACCESS  read-write
    STATUS      current
    DESCRIPTION
        "The group(0~12) of trunk port."
    ::= { gs2124TrunkPortEntry 3 }

gs2124TrunkPortActiveLacp  OBJECT-TYPE
    SYNTAX      INTEGER(0|1)
    MAX-ACCESS  read-write
    STATUS      current
    DESCRIPTION
        "The active lacp mode of trunk port.
  0 : Passive,
  1 : Active.
        "
    ::= { gs2124TrunkPortEntry 4 }

gs2124TrunkPortAggtr  OBJECT-TYPE
    SYNTAX      INTEGER(1..24)
    MAX-ACCESS  read-only
    STATUS      current
    DESCRIPTION
        "The Aggtr of trunk port."
    ::= { gs2124TrunkPortEntry 5 }

gs2124TrunkPortStatus  OBJECT-TYPE
    SYNTAX      INTEGER(0|1)
    MAX-ACCESS  read-only
    STATUS      current
    DESCRIPTION
        "The status of trunk port.
         0 : None,
         1 : Ready.
        "
    ::= { gs2124TrunkPortEntry 6 }

gs2124TrunkPortCurrentMode  OBJECT-TYPE
    SYNTAX      INTEGER(0..2)
    MAX-ACCESS  read-write
    STATUS      current
    DESCRIPTION
        "The current mode of trunk port entry.
  0 : Active mode,
  1 : Edit mode,
  2 : Do edit.
        "
    ::= { gs2124TrunkPortEntry 7 }

gs2124AggregatorView      OBJECT IDENTIFIER ::= { gs2124TrunkInfo 2 }

gs2124AggregatorViewTable  OBJECT-TYPE
    SYNTAX      SEQUENCE OF GS2124AggregatorViewEntry
    MAX-ACCESS  not-accessible
    STATUS      current
    DESCRIPTION
        "This is a list of GS2124AggregatorViewEntry."
    ::= { gs2124AggregatorView 1 }

GS2124AggregatorViewEntry ::=
SEQUENCE {
    gs2124AggregatorViewIndex  INTEGER,
    gs2124AggregatorViewMethod  INTEGER,
    gs2124AggregatorViewMemberPorts  DisplayString,
    gs2124AggregatorViewReadyPorts DisplayString
}

gs2124AggregatorViewEntry OBJECT-TYPE
    SYNTAX      GS2124AggregatorViewEntry
    MAX-ACCESS  not-accessible
    STATUS      current
    DESCRIPTION
        "Entry(s) for aggregator view table."
    INDEX {gs2124AggregatorViewIndex}
    ::= { gs2124AggregatorViewTable 1 }

gs2124AggregatorViewIndex  OBJECT-TYPE
    SYNTAX      INTEGER(1..24)
    MAX-ACCESS  not-accessible
    STATUS      current
    DESCRIPTION
        "The port index of aggregator view table."
    ::= { gs2124AggregatorViewEntry 1 }

gs2124AggregatorViewMethod  OBJECT-TYPE
    SYNTAX      INTEGER(0..2)
    MAX-ACCESS  read-only
    STATUS      current
    DESCRIPTION
        "The method of aggregator view table.
         0 : None,
  1 : LACP,
  2 : Static.
        "
    ::= { gs2124AggregatorViewEntry 2 }

gs2124AggregatorViewMemberPorts  OBJECT-TYPE
    SYNTAX      DisplayString
    MAX-ACCESS  read-only
    STATUS      current
    DESCRIPTION
        "The member ports of aggregator view table."
    ::= { gs2124AggregatorViewEntry 3 }

gs2124AggregatorViewReadyPorts  OBJECT-TYPE
    SYNTAX      DisplayString
    MAX-ACCESS  read-only
    STATUS      current
    DESCRIPTION
        "The ready ports of aggregator view table."
    ::= { gs2124AggregatorViewEntry 4 }

gs2124LacpSystemPriority OBJECT-TYPE
 SYNTAX  INTEGER(1..65535)
 MAX-ACCESS     read-write
 STATUS  current
 DESCRIPTION
  "Set lacp system priority. (Range:1~65535)"
 ::= { gs2124TrunkInfo 3 }

gs2124AggregationHashMode            OBJECT IDENTIFIER ::= { gs2124TrunkInfo 4 }

gs2124HashCodeSourceMacAddress OBJECT-TYPE
 SYNTAX  INTEGER(0|1)
 MAX-ACCESS     read-write
 STATUS  current
 DESCRIPTION
  "Set hash mode : Source MAC Hash Enable."
 ::= { gs2124AggregationHashMode 1 }

gs2124HashCodeDestinationMacAddress OBJECT-TYPE
 SYNTAX  INTEGER(0|1)
 MAX-ACCESS     read-write
 STATUS  current
 DESCRIPTION
  "Set hash mode : Destination MAC Hash Enable."
 ::= { gs2124AggregationHashMode 2 }

gs2124HashCodeIpAddress OBJECT-TYPE
 SYNTAX  INTEGER(0|1)
 MAX-ACCESS     read-write
 STATUS  current
 DESCRIPTION
  "Set hash mode : IP Hash Enable."
 ::= { gs2124AggregationHashMode 3 }

gs2124HashCodeTcpUdpPortNumber OBJECT-TYPE
 SYNTAX  INTEGER(0|1)
 MAX-ACCESS     read-write
 STATUS  current
 DESCRIPTION
  "Set hash mode : TCP/UDP Port Hash Enable."
 ::= { gs2124AggregationHashMode 4 }


gs2124MulticastInfo            OBJECT IDENTIFIER ::= { gs2124Produces 25 }

gs2124IGMPMode OBJECT-TYPE
 SYNTAX      INTEGER(0|1|2)
 MAX-ACCESS     read-write
 STATUS  current
 DESCRIPTION
  "Get/Set the IGMP Proxy/Snooping state.
   0 - disabled.
   1 - proxy.
   2 - snooping.  "
 ::= { gs2124MulticastInfo 1 }

gs2124IGMPGroupAllowConf         OBJECT IDENTIFIER ::= { gs2124MulticastInfo 2 }

gs2124IGMPGroupAllowNumber OBJECT-TYPE
 SYNTAX      INTEGER(1..16)
 MAX-ACCESS     read-only
 STATUS  current
 DESCRIPTION
  "Get the amount of the IGMP group allow."
 ::= { gs2124IGMPGroupAllowConf 1  }

gs2124IGMPGroupAllowEntryCreate  OBJECT-TYPE
 SYNTAX      INTEGER(0..4094)
 MAX-ACCESS     read-write
 STATUS  current
 DESCRIPTION
  "Create IGMP group allow entry."
 ::= { gs2124IGMPGroupAllowConf 2 }

gs2124IGMPGroupAllowTable OBJECT-TYPE
 SYNTAX  SEQUENCE OF GS2124IGMPGroupAllowEntry
 MAX-ACCESS not-accessible
 STATUS  current
    DESCRIPTION
        "Display IGMP group allow information."
 ::= { gs2124IGMPGroupAllowConf 3 }

GS2124IGMPGroupAllowEntry ::=
SEQUENCE {
    gs2124IGMPGroupAllowNo          INTEGER,
    gs2124IGMPGroupAllowVid        INTEGER,
    gs2124IGMPGroupAllowStartAddress     DisplayString,
    gs2124IGMPGroupAllowEndAddress      DisplayString,
    gs2124IGMPGroupAllowEntryAction   INTEGER
}

gs2124IGMPGroupAllowEntry OBJECT-TYPE
 SYNTAX  GS2124IGMPGroupAllowEntry
 MAX-ACCESS     not-accessible
 STATUS  current
 DESCRIPTION
  "This is the Entry(s) for IGMP Group Allow configuration information."
 INDEX {gs2124IGMPGroupAllowNo}
 ::= { gs2124IGMPGroupAllowTable 1 }

gs2124IGMPGroupAllowNo  OBJECT-TYPE
    SYNTAX      INTEGER(1..256)
    MAX-ACCESS  not-accessible
    STATUS      current
    DESCRIPTION
        "The index of IGMP Group Allow table."
    ::= { gs2124IGMPGroupAllowEntry 1 }

gs2124IGMPGroupAllowVid  OBJECT-TYPE
    SYNTAX      INTEGER(0..4094)
    MAX-ACCESS  read-write
    STATUS      current
    DESCRIPTION
        "Add group allow for this IGMP."
    ::= { gs2124IGMPGroupAllowEntry 2 }

gs2124IGMPGroupAllowStartAddress OBJECT-TYPE
 SYNTAX  DisplayString
 MAX-ACCESS     read-write
 STATUS  current
 DESCRIPTION
  "Add start address of IGMP group allow."
 ::= { gs2124IGMPGroupAllowEntry 3}

gs2124IGMPGroupAllowEndAddress OBJECT-TYPE
 SYNTAX  DisplayString
 MAX-ACCESS     read-write
 STATUS  current
 DESCRIPTION
  "Add end address of IGMP group allow."
 ::= { gs2124IGMPGroupAllowEntry 4 }

gs2124IGMPGroupAllowEntryAction OBJECT-TYPE
 SYNTAX  INTEGER(1..4)
 MAX-ACCESS     read-write
 STATUS  current
 DESCRIPTION
  "
   1 - active
   2 - notInService
   3 - delete
   4 - undo"
 ::= { gs2124IGMPGroupAllowEntry 5 }

gs2124IGMPProxy         OBJECT IDENTIFIER ::= { gs2124MulticastInfo 3 }

gs2124IgmpProxyConfGeneralQueryInterval OBJECT-TYPE
 SYNTAX      INTEGER(1..3600)
 MAX-ACCESS     read-write
 STATUS  current
 DESCRIPTION
  "Get/Set IGMP general query interval(Unit: second)."
 ::= { gs2124IGMPProxy 1 }

gs2124IgmpProxyConfGeneralQueryRepTimeout OBJECT-TYPE
 SYNTAX      INTEGER(1..25)
 MAX-ACCESS     read-write
 STATUS  current
 DESCRIPTION
  "Get/Set IGMP general query response timeout(Unit: second)."
 ::= { gs2124IGMPProxy 2 }

gs2124IgmpProxyConfGeneralQueryMaxRepTime OBJECT-TYPE
 SYNTAX      INTEGER(1..25)
 MAX-ACCESS     read-write
 STATUS  current
 DESCRIPTION
  "Get/Set IGMP general query maximum response time(Unit: second)."
 ::= { gs2124IGMPProxy 3 }

gs2124IgmpProxyConfLastMemberQueryCount OBJECT-TYPE
 SYNTAX      INTEGER(1..16)
 MAX-ACCESS     read-write
 STATUS  current
 DESCRIPTION
  "Get/Set IGMP specific query robust count."
 ::= { gs2124IGMPProxy 4 }

gs2124IgmpProxyConfLastMemberQueryInterval OBJECT-TYPE
 SYNTAX      INTEGER(1..25)
 MAX-ACCESS     read-write
 STATUS  current
 DESCRIPTION
  "Get/Set IGMP specific query interval(Unit: second)."
 ::= { gs2124IGMPProxy 5 }

gs2124IgmpProxyConfLastMemberQueryMaxRepTime OBJECT-TYPE
 SYNTAX      INTEGER(1..25)
 MAX-ACCESS     read-write
 STATUS  current
 DESCRIPTION
  "Get/Set IGMP specific query maximum response time(Unit: second)."
 ::= { gs2124IGMPProxy 6 }

gs2124IgmpProxyConfRouterPorts OBJECT-TYPE
 SYNTAX      DisplayString
 MAX-ACCESS     read-write
 STATUS  current
 DESCRIPTION
  " Get/Set IGMP router port(s)."
 ::= { gs2124IGMPProxy 7 }

gs2124IgmpProxyGroupMembershipNumber OBJECT-TYPE
 SYNTAX      INTEGER(0..1024)
 MAX-ACCESS     read-write
 STATUS  current
 DESCRIPTION
  "Get the amount of multicast group membership."
 ::= { gs2124IGMPProxy 8 }

gs2124IgmpProxyGroupMembershipTable  OBJECT-TYPE
    SYNTAX      SEQUENCE OF GS2124IgmpProxyGroupMembershipEntry
    MAX-ACCESS  not-accessible
    STATUS      current
    DESCRIPTION
        "Get multicast group membership."
    ::= { gs2124IGMPProxy 9 }

GS2124IgmpProxyGroupMembershipEntry ::=
SEQUENCE {
    gs2124IgmpProxyGroupNo         INTEGER,
    gs2124IgmpProxyGroupAddress     DisplayString,
    gs2124IgmpProxyGroupVLANId      INTEGER,
    gs2124IgmpProxyGroupPortMembers  DisplayString
}

gs2124IgmpProxyGroupMembershipEntry OBJECT-TYPE
    SYNTAX      GS2124IgmpProxyGroupMembershipEntry
    MAX-ACCESS  not-accessible
    STATUS      current
    DESCRIPTION
        "Entry(s) for Igmp Proxy Group Membership table."
    INDEX {gs2124IgmpProxyGroupNo}
    ::= { gs2124IgmpProxyGroupMembershipTable 1 }

gs2124IgmpProxyGroupNo  OBJECT-TYPE
    SYNTAX      INTEGER(1..1024)
    MAX-ACCESS  not-accessible
    STATUS      current
    DESCRIPTION
        "The port index of Igmp Proxy Group Membership table."
    ::= { gs2124IgmpProxyGroupMembershipEntry 1 }

gs2124IgmpProxyGroupAddress  OBJECT-TYPE
    SYNTAX      DisplayString
    MAX-ACCESS  read-only
    STATUS      current
    DESCRIPTION
        "The group address of multicast group membership entry."
    ::= { gs2124IgmpProxyGroupMembershipEntry 2 }

gs2124IgmpProxyGroupVLANId  OBJECT-TYPE
    SYNTAX      INTEGER(1..4094)
    MAX-ACCESS  read-only
    STATUS      current
    DESCRIPTION
        "The vlan id of multicast group membership entry."
    ::= { gs2124IgmpProxyGroupMembershipEntry 3 }

gs2124IgmpProxyGroupPortMembers  OBJECT-TYPE
    SYNTAX      DisplayString
    MAX-ACCESS  read-only
    STATUS      current
    DESCRIPTION
        "The port member of multicast group membership entry."
    ::= { gs2124IgmpProxyGroupMembershipEntry 4 }

gs2124IGMPSnooping         OBJECT IDENTIFIER ::= { gs2124MulticastInfo 4 }

gs2124IgmpSnoopingConfHostTimeout OBJECT-TYPE
 SYNTAX      INTEGER(1..65535)
 MAX-ACCESS     read-write
 STATUS  current
 DESCRIPTION
  "This is the host timeout of the igmp snooping."
 ::= { gs2124IGMPSnooping 1 }


gs2124IgmpSnoopingConfFastLeave OBJECT-TYPE
 SYNTAX      DisplayString
 MAX-ACCESS     read-write
 STATUS  current
 DESCRIPTION
  "This is the fast-leave of the igmp snooping."
 ::= { gs2124IGMPSnooping 2 }

gs2124IgmpSnoopingConfRouterPorts  OBJECT-TYPE
 SYNTAX      DisplayString
 MAX-ACCESS     read-write
 STATUS  current
 DESCRIPTION
  "These ports are router ports of the igmp snooping."
 ::= { gs2124IGMPSnooping 3 }

gs2124IgmpSnoopingGroupMembershipNumber OBJECT-TYPE
 SYNTAX      INTEGER(0..1024)
 MAX-ACCESS     read-write
 STATUS  current
 DESCRIPTION
  "These are groups membership of the igmp snooping."
 ::= { gs2124IGMPSnooping 4 }

gs2124IgmpSnoopingGroupMembershipTable  OBJECT-TYPE
    SYNTAX      SEQUENCE OF GS2124IgmpSnoopingGroupMembershipEntry
    MAX-ACCESS  not-accessible
    STATUS      current
    DESCRIPTION
        "Display group menbership information."
 ::= { gs2124IGMPSnooping 5 }


GS2124IgmpSnoopingGroupMembershipEntry ::=
SEQUENCE {
    gs2124IgmpSnoopingGroupNo         INTEGER,
    gs2124IgmpSnoopingGroupAddress     DisplayString,
    gs2124IgmpSnoopingGroupVLANId      INTEGER,
    gs2124IgmpSnoopingGroupPortMembers  DisplayString
}

gs2124IgmpSnoopingGroupMembershipEntry OBJECT-TYPE
    SYNTAX      GS2124IgmpSnoopingGroupMembershipEntry
    MAX-ACCESS  not-accessible
    STATUS      current
    DESCRIPTION
        "Entry(s) for Igmp Snooping Group Membership table."
    INDEX {gs2124IgmpSnoopingGroupNo}
    ::= { gs2124IgmpSnoopingGroupMembershipTable 1 }

gs2124IgmpSnoopingGroupNo  OBJECT-TYPE
    SYNTAX      INTEGER(1..1024)
    MAX-ACCESS  not-accessible
    STATUS      current
    DESCRIPTION
        "The port index of Igmp Snooping Group Membership table."
    ::= { gs2124IgmpSnoopingGroupMembershipEntry 1 }

gs2124IgmpSnoopingGroupAddress  OBJECT-TYPE
    SYNTAX      DisplayString
    MAX-ACCESS  read-only
    STATUS      current
    DESCRIPTION
        "This is the group address of the igmp snooping."
    ::= { gs2124IgmpSnoopingGroupMembershipEntry 2 }

gs2124IgmpSnoopingGroupVLANId  OBJECT-TYPE
    SYNTAX      INTEGER(1..4094)
    MAX-ACCESS  read-only
    STATUS      current
    DESCRIPTION
        "The vlan id of igmp snooping group."
    ::= { gs2124IgmpSnoopingGroupMembershipEntry 3 }

gs2124IgmpSnoopingGroupPortMembers  OBJECT-TYPE
    SYNTAX      DisplayString
    MAX-ACCESS  read-only
    STATUS      current
    DESCRIPTION
        "The members of igmp snooping group."
    ::= { gs2124IgmpSnoopingGroupMembershipEntry 4 }


gs2124MVR         OBJECT IDENTIFIER ::= { gs2124MulticastInfo 5 }

gs2124MVRMode OBJECT-TYPE
 SYNTAX      INTEGER(0|1)
 MAX-ACCESS     read-write
 STATUS  current
 DESCRIPTION
  "Get/Set the MVR state.
   0 - disabled.
   1 - enabled.  "
 ::= { gs2124MVR 1 }

gs2124MVRConfHostTimeout OBJECT-TYPE
 SYNTAX      INTEGER(1..65535)
 MAX-ACCESS     read-write
 STATUS  current
 DESCRIPTION
  "This is the host timeout of the mvr."
 ::= { gs2124MVR 2 }

gs2124MVRConfFastLeave OBJECT-TYPE
 SYNTAX      DisplayString
 MAX-ACCESS     read-write
 STATUS  current
 DESCRIPTION
  "This is the fast-leave of the mvr."
 ::= { gs2124MVR 3 }


gs2124MVIDConf         OBJECT IDENTIFIER ::= { gs2124MVR 4 }

gs2124MVIDNumber OBJECT-TYPE
 SYNTAX      INTEGER(1..4094)
 MAX-ACCESS     read-only
 STATUS  current
 DESCRIPTION
  "The vid of mvr group."
 ::= { gs2124MVIDConf 1 }

gs2124MVIDEntryCreate OBJECT-TYPE
 SYNTAX      INTEGER(0..4094)
 MAX-ACCESS     read-write
 STATUS  current
 DESCRIPTION
  "Create mvr group entry."
 ::= { gs2124MVIDConf 2 }

gs2124MVIDGroupTable OBJECT-TYPE
 SYNTAX  SEQUENCE OF GS2124MVIDGroupEntry
 MAX-ACCESS not-accessible
 STATUS  current
    DESCRIPTION
        "Display mvid group information."
 ::= { gs2124MVIDConf 3 }

GS2124MVIDGroupEntry ::=
SEQUENCE {
    gs2124MVID          INTEGER,
    gs2124MVIDMemberPort      DisplayString,
    gs2124MVIDRouterPorts     DisplayString,
    gs2124MVIDEntryAction     INTEGER
}

gs2124MVIDGroupEntry OBJECT-TYPE
 SYNTAX  GS2124MVIDGroupEntry
 MAX-ACCESS     not-accessible
 STATUS  current
 DESCRIPTION
  "This is the Entry(s) for MVID Group configuration information."
 INDEX {gs2124MVID}
 ::= { gs2124MVIDGroupTable 1 }

gs2124MVID OBJECT-TYPE
 SYNTAX  INTEGER(1..4094)
 MAX-ACCESS     not-accessible
 STATUS  current
 DESCRIPTION
  "This is the index of the MVID Group configuration entry."
 ::= { gs2124MVIDGroupEntry 1 }

gs2124MVIDMemberPort OBJECT-TYPE
 SYNTAX  DisplayString
 MAX-ACCESS     read-write
 STATUS  current
 DESCRIPTION
  "Member ports of the mvid group."
 ::= { gs2124MVIDGroupEntry 2 }

gs2124MVIDRouterPorts  OBJECT-TYPE
 SYNTAX  DisplayString
 MAX-ACCESS     read-write
 STATUS  current
 DESCRIPTION
  "Router ports of the mvid group."
 ::= { gs2124MVIDGroupEntry 3 }

gs2124MVIDEntryAction OBJECT-TYPE
 SYNTAX  INTEGER(1..4)
 MAX-ACCESS     read-write
 STATUS  current
 DESCRIPTION
  "
   1 - active
   2 - notInService
   3 - delete
   4 - undo"
 ::= { gs2124MVIDGroupEntry 4 }


gs2124MVIDGroupAllowConf         OBJECT IDENTIFIER ::= { gs2124MVR 5 }

gs2124MVIDGroupAllowNumber OBJECT-TYPE
 SYNTAX      INTEGER(1..16)
 MAX-ACCESS     read-only
 STATUS  current
 DESCRIPTION
  "Get the amount of the mvid group allow."
 ::= { gs2124MVIDGroupAllowConf 1  }

gs2124MVIDGroupAllowEntryCreate  OBJECT-TYPE
 SYNTAX      INTEGER(0..4094)
 MAX-ACCESS     read-write
 STATUS  current
 DESCRIPTION
  "Create mvid group allow entry."
 ::= { gs2124MVIDGroupAllowConf 2 }

gs2124MVIDGroupAllowTable OBJECT-TYPE
 SYNTAX  SEQUENCE OF GS2124MVIDGroupAllowEntry
 MAX-ACCESS not-accessible
 STATUS  current
    DESCRIPTION
        "Display mvid group allow information."
 ::= { gs2124MVIDGroupAllowConf 3 }

GS2124MVIDGroupAllowEntry ::=
SEQUENCE {
    gs2124MVIDGroupAllowNo          INTEGER,
    gs2124MVIDGroupAllowMvid        INTEGER,
    gs2124MVIDGroupAllowStartAddress     DisplayString,
    gs2124MVIDGroupAllowEndAddress      DisplayString,
    gs2124MVIDGroupAllowEntryAction   INTEGER
}

gs2124MVIDGroupAllowEntry OBJECT-TYPE
 SYNTAX  GS2124MVIDGroupAllowEntry
 MAX-ACCESS     not-accessible
 STATUS  current
 DESCRIPTION
  "This is the Entry(s) for MVID Group Allow configuration information."
 INDEX {gs2124MVIDGroupAllowNo}
 ::= { gs2124MVIDGroupAllowTable 1 }

gs2124MVIDGroupAllowNo  OBJECT-TYPE
    SYNTAX      INTEGER(1..256)
    MAX-ACCESS  not-accessible
    STATUS      current
    DESCRIPTION
        "The index of MVID Group Allow table."
    ::= { gs2124MVIDGroupAllowEntry 1 }

gs2124MVIDGroupAllowMvid  OBJECT-TYPE
    SYNTAX      INTEGER(0..4094)
    MAX-ACCESS  read-write
    STATUS      current
    DESCRIPTION
        "Add group allow for this mvid."
    ::= { gs2124MVIDGroupAllowEntry 2 }

gs2124MVIDGroupAllowStartAddress OBJECT-TYPE
 SYNTAX  DisplayString
 MAX-ACCESS     read-write
 STATUS  current
 DESCRIPTION
  "Add start address of mvid group allow."
 ::= { gs2124MVIDGroupAllowEntry 3}

gs2124MVIDGroupAllowEndAddress OBJECT-TYPE
 SYNTAX  DisplayString
 MAX-ACCESS     read-write
 STATUS  current
 DESCRIPTION
  "Add end address of mvid group allow."
 ::= { gs2124MVIDGroupAllowEntry 4 }

gs2124MVIDGroupAllowEntryAction OBJECT-TYPE
 SYNTAX  INTEGER(1..4)
 MAX-ACCESS     read-write
 STATUS  current
 DESCRIPTION
  "
   1 - active
   2 - notInService
   3 - delete
   4 - undo"
 ::= { gs2124MVIDGroupAllowEntry 5 }

gs2124MVRGroupMembershipNumber OBJECT-TYPE
 SYNTAX      INTEGER(0..1024)
 MAX-ACCESS     read-only
 STATUS  current
 DESCRIPTION
  "Get the amount of mvr group membership."
 ::= { gs2124MVR 6 }

gs2124MVRGroupMembershipTable  OBJECT-TYPE
    SYNTAX      SEQUENCE OF GS2124MVRGroupMembershipEntry
    MAX-ACCESS  not-accessible
    STATUS      current
    DESCRIPTION
        "Get mvr group membership."
 ::= { gs2124MVR 7 }


GS2124MVRGroupMembershipEntry ::=
SEQUENCE {
    gs2124MVRGroupNo         INTEGER,
    gs2124MVRGroupAddress     DisplayString,
    gs2124MVRGroupVLANId      INTEGER,
    gs2124MVRGroupPortMembers  DisplayString
}

gs2124MVRGroupMembershipEntry OBJECT-TYPE
    SYNTAX      GS2124MVRGroupMembershipEntry
    MAX-ACCESS  not-accessible
    STATUS      current
    DESCRIPTION
        "Entry(s) for MVR Group Membership table."
    INDEX {gs2124MVRGroupNo}
    ::= { gs2124MVRGroupMembershipTable 1 }

gs2124MVRGroupNo  OBJECT-TYPE
    SYNTAX      INTEGER(1..1024)
    MAX-ACCESS  not-accessible
    STATUS      current
    DESCRIPTION
        "The port index of MVR Group Membership table."
    ::= { gs2124MVRGroupMembershipEntry 1 }

gs2124MVRGroupAddress  OBJECT-TYPE
    SYNTAX      DisplayString
    MAX-ACCESS  read-only
    STATUS      current
    DESCRIPTION
        "The group address of mvr group membership entry."
    ::= { gs2124MVRGroupMembershipEntry 2 }

gs2124MVRGroupVLANId  OBJECT-TYPE
    SYNTAX      INTEGER(1..4094)
    MAX-ACCESS  read-only
    STATUS      current
    DESCRIPTION
        "The vlan id of mvr group membership entry."
    ::= { gs2124MVRGroupMembershipEntry 3 }

gs2124MVRGroupPortMembers  OBJECT-TYPE
    SYNTAX      DisplayString
    MAX-ACCESS  read-only
    STATUS      current
    DESCRIPTION
        "The port member of mvr group membership entry."
    ::= { gs2124MVRGroupMembershipEntry 4 }

gs2124DhcpSnooping            OBJECT IDENTIFIER ::= { gs2124Produces 26 }

gs2124DhcpSnoopingState OBJECT-TYPE
 SYNTAX      INTEGER(0|1)
 MAX-ACCESS     read-write
 STATUS  current
 DESCRIPTION
  "Get/Set the Dhcp Snooping state.
   0 - disabled.
   1 - enable."
 ::= { gs2124DhcpSnooping 1 }

gs2124DhcpSnoopingInfo         OBJECT IDENTIFIER ::= { gs2124DhcpSnooping 2 }

gs2124DhcpSnoopingCreate OBJECT-TYPE
 SYNTAX      INTEGER(0|1)
 MAX-ACCESS     read-write
 STATUS  current
 DESCRIPTION
  "create DHCP Snooping entry.
   0 - none.
   1 - create."
 ::= { gs2124DhcpSnoopingInfo 1 }

gs2124DhcpSnoopingTable  OBJECT-TYPE
    SYNTAX      SEQUENCE OF GS2124DhcpSnoopingEntry
    MAX-ACCESS  not-accessible
    STATUS      current
    DESCRIPTION
        "This is a list of DhcpSnoopingEntry."
 ::= { gs2124DhcpSnoopingInfo 2 }


GS2124DhcpSnoopingEntry ::=
SEQUENCE {
    gs2124DhcpSnoopingIndex                   INTEGER,
    gs2124DhcpSnoopingVID                     INTEGER,
    gs2124DhcpSnoopingTrustPort1              INTEGER,
    gs2124DhcpSnoopingTrustPort2              INTEGER,
    gs2124DhcpSnoopingServerIP                IpAddress,
    gs2124DhcpSnoopingOption82                INTEGER,
    gs2124DhcpSnoopingAction                INTEGER,
    gs2124DhcpSnoopingEntryAction             INTEGER
}

gs2124DhcpSnoopingEntry OBJECT-TYPE
    SYNTAX      GS2124DhcpSnoopingEntry
    MAX-ACCESS  not-accessible
    STATUS      current
    DESCRIPTION
        "Entry(s) for Dhcp Snooping table."
    INDEX {gs2124DhcpSnoopingIndex}
    ::= { gs2124DhcpSnoopingTable 1 }

gs2124DhcpSnoopingIndex  OBJECT-TYPE
    SYNTAX      INTEGER(1..256)
    MAX-ACCESS  not-accessible
    STATUS      current
    DESCRIPTION
        "The index of Dhcp Snooping table."
    ::= { gs2124DhcpSnoopingEntry 1 }

gs2124DhcpSnoopingVID  OBJECT-TYPE
    SYNTAX      INTEGER(1..4094)
    MAX-ACCESS  read-write
    STATUS      current
    DESCRIPTION
        "The vid of the dhcp snooping entry."
    ::= { gs2124DhcpSnoopingEntry 2 }

gs2124DhcpSnoopingTrustPort1 OBJECT-TYPE
 SYNTAX      INTEGER(0..24)
 MAX-ACCESS     read-write
 STATUS  current
 DESCRIPTION
  "The trust port1 of the dhcp snooping entry.
  0:disable"
 ::= { gs2124DhcpSnoopingEntry 3 }

gs2124DhcpSnoopingTrustPort2 OBJECT-TYPE
 SYNTAX      INTEGER(0..24)
 MAX-ACCESS     read-write
 STATUS  current
 DESCRIPTION
  "The trust port2 of the dhcp snooping entry.
  0:disable"
 ::= { gs2124DhcpSnoopingEntry 4 }

gs2124DhcpSnoopingServerIP OBJECT-TYPE
 SYNTAX      IpAddress
 MAX-ACCESS     read-write
 STATUS  current
 DESCRIPTION
  "The server ip of the dhcp snooping entry."
 ::= { gs2124DhcpSnoopingEntry 5 }

gs2124DhcpSnoopingOption82 OBJECT-TYPE
 SYNTAX      INTEGER(0|1)
 MAX-ACCESS     read-write
 STATUS  current
 DESCRIPTION
  "0:disable
   1:enable"
 ::= { gs2124DhcpSnoopingEntry 6 }

gs2124DhcpSnoopingAction OBJECT-TYPE
 SYNTAX      INTEGER(0..2)
 MAX-ACCESS     read-write
 STATUS  current
 DESCRIPTION
  "0:keep
   1: drop
   2: replace"
 ::= { gs2124DhcpSnoopingEntry 7 }

gs2124DhcpSnoopingEntryAction  OBJECT-TYPE
    SYNTAX      INTEGER(0..2)
    MAX-ACCESS  read-write
    STATUS      current
    DESCRIPTION
        "The current mode of Dhcp Snooping default entry.
  0 : Active mode,
  1 : Edit mode,
  2 : Do edit. "
 ::= { gs2124DhcpSnoopingEntry 8 }


gs2124DhcpSnoopingDefaultData     OBJECT IDENTIFIER ::= { gs2124DhcpSnoopingInfo 3 }

gs2124DhcpSnoopingDefaultVID OBJECT-TYPE
 SYNTAX      INTEGER(1..4094)
 MAX-ACCESS     read-write
 STATUS  current
 DESCRIPTION
  "The vid of the dhcp_snooping default entry."
 ::= { gs2124DhcpSnoopingDefaultData 1 }

gs2124DhcpSnoopingDefaultTrustPort1 OBJECT-TYPE
 SYNTAX      INTEGER(0..24)
 MAX-ACCESS     read-write
 STATUS  current
 DESCRIPTION
  "The trust port1 of the dhcp_snooping default entry.
  0:disable"
 ::= { gs2124DhcpSnoopingDefaultData 2 }

gs2124DhcpSnoopingDefaultTrustPort2 OBJECT-TYPE
 SYNTAX      INTEGER(0..24)
 MAX-ACCESS     read-write
 STATUS  current
 DESCRIPTION
  "The trust port2 of the dhcp_snooping default entry.
  0:disable"
 ::= { gs2124DhcpSnoopingDefaultData 3 }

gs2124DhcpSnoopingDefaultServerIP OBJECT-TYPE
 SYNTAX      IpAddress
 MAX-ACCESS     read-write
 STATUS  current
 DESCRIPTION
  "The server ip of the dhcp_snooping default entry."
 ::= { gs2124DhcpSnoopingDefaultData 4 }

gs2124DhcpSnoopingDefaultOption82 OBJECT-TYPE
 SYNTAX      INTEGER(0|1)
 MAX-ACCESS     read-write
 STATUS  current
 DESCRIPTION
  "0:disable
   1:enable"
 ::= { gs2124DhcpSnoopingDefaultData 5 }

gs2124DhcpSnoopingDefaultAction OBJECT-TYPE
 SYNTAX      INTEGER(0..2)
 MAX-ACCESS     read-write
 STATUS  current
 DESCRIPTION
  "0:keep
   1: drop
   2: replace"
 ::= { gs2124DhcpSnoopingDefaultData 6 }

gs2124DhcpSnoopingDefaultEntryAction  OBJECT-TYPE
    SYNTAX      INTEGER(0..2)
    MAX-ACCESS  read-write
    STATUS      current
    DESCRIPTION
        "The current mode of Dhcp Snooping default entry.
  0 : Active mode,
  1 : Edit mode,
  2 : Do edit,
  3 : Undo."
 ::= { gs2124DhcpSnoopingDefaultData 7 }

gs2124DhcpSnoopingClientTable  OBJECT-TYPE
    SYNTAX      SEQUENCE OF GS2124DhcpSnoopingClientEntry
    MAX-ACCESS  not-accessible
    STATUS      current
    DESCRIPTION
        "The list of the DhcpSnoopingClientEntry."
 ::= { gs2124DhcpSnooping 3 }

GS2124DhcpSnoopingClientEntry ::=
SEQUENCE {
    gs2124DhcpSnoopingClientIndex    INTEGER,
    gs2124DhcpSnoopingClientMac      DisplayString,
    gs2124DhcpSnoopingClientVID      INTEGER,
    gs2124DhcpSnoopingClientPort     INTEGER,
    gs2124DhcpSnoopingClientIP       IpAddress,
    gs2124DhcpSnoopingClientLease    DisplayString
}

gs2124DhcpSnoopingClientEntry OBJECT-TYPE
    SYNTAX      GS2124DhcpSnoopingClientEntry
    MAX-ACCESS  not-accessible
    STATUS      current
    DESCRIPTION
        "Entry(s) for Dhcp Snooping Client table."
    INDEX {gs2124DhcpSnoopingClientIndex}
    ::= { gs2124DhcpSnoopingClientTable 1 }

gs2124DhcpSnoopingClientIndex  OBJECT-TYPE
    SYNTAX      INTEGER(1..10000)
    MAX-ACCESS  not-accessible
    STATUS      current
    DESCRIPTION
        "The index of Dhcp Snooping Client table."
    ::= { gs2124DhcpSnoopingClientEntry 1 }

gs2124DhcpSnoopingClientMac  OBJECT-TYPE
    SYNTAX      DisplayString
    MAX-ACCESS  read-only
    STATUS      current
    DESCRIPTION
        "The mac address of the dhcp_snooping client entry."
    ::= { gs2124DhcpSnoopingClientEntry 2 }

gs2124DhcpSnoopingClientVID  OBJECT-TYPE
    SYNTAX      INTEGER(1..4094)
    MAX-ACCESS  read-only
    STATUS      current
    DESCRIPTION
        "The vid of the dhcp_snooping client entry."
    ::= { gs2124DhcpSnoopingClientEntry 3 }

gs2124DhcpSnoopingClientPort  OBJECT-TYPE
    SYNTAX      INTEGER(1..24)
    MAX-ACCESS  read-only
    STATUS      current
    DESCRIPTION
        "The port number of the dhcp_snooping client entry."
    ::= { gs2124DhcpSnoopingClientEntry 4 }

gs2124DhcpSnoopingClientIP  OBJECT-TYPE
    SYNTAX      IpAddress
    MAX-ACCESS  read-only
    STATUS      current
    DESCRIPTION
        "The ip address of the dhcp_snooping client entry."
    ::= { gs2124DhcpSnoopingClientEntry 5 }

gs2124DhcpSnoopingClientLease  OBJECT-TYPE
    SYNTAX      DisplayString
    MAX-ACCESS  read-only
    STATUS      current
    DESCRIPTION
        "The dhcp lease time of the dhcp_snooping client entry."
    ::= { gs2124DhcpSnoopingClientEntry 6 }


gs2124TrapEntry        OBJECT IDENTIFIER ::= { gs2124Produces 20 }

gs2124UserLogin NOTIFICATION-TYPE
    OBJECTS   {username}
 STATUS  current
 DESCRIPTION
    "Send the trap when one user logins the system."
 ::= { gs2124TrapEntry 1 }

gs2124UserLogout NOTIFICATION-TYPE
    OBJECTS   {username}
 STATUS  current
 DESCRIPTION
    "Send the trap when one user logouts the system."
 ::= { gs2124TrapEntry 2 }

gs2124ModuleInserted NOTIFICATION-TYPE
    OBJECTS { ifIndex }
 STATUS    current
 DESCRIPTION
     "Send the trap when a module is inserted to the system. The OID value means
      the port number."
 ::= { gs2124TrapEntry 3 }

gs2124ModuleRemoved NOTIFICATION-TYPE
    OBJECTS { ifIndex }
 STATUS    current
 DESCRIPTION
     "Send the trap when a module is removed from the system. The OID value means
      the port number."
 ::= { gs2124TrapEntry 4 }

gs2124DualMediaSwapped NOTIFICATION-TYPE
    OBJECTS { ifIndex, swapto }
 STATUS    current
 DESCRIPTION
     "Send the trap when the dual media port changed. The OID value means the port number."
 ::= { gs2124TrapEntry 5 }

gs2124LoopDetected NOTIFICATION-TYPE
    OBJECTS { ifIndex }
 STATUS    current
 DESCRIPTION
     "Send the trap when loop condition has been detected. The OID value means the port number."
 ::= { gs2124TrapEntry 6 }

gs2124StpStateDisabled NOTIFICATION-TYPE
 STATUS  current
 DESCRIPTION
    "Send the trap when the operational state of STP is from enabled to disabled. "
 ::= { gs2124TrapEntry 7 }

gs2124StpStateEnabled NOTIFICATION-TYPE
 STATUS  current
 DESCRIPTION
    "Send the trap when the operational state of STP is from disabled to enabled. "
 ::= { gs2124TrapEntry 8 }

gs2124StpTopologyChanged NOTIFICATION-TYPE
    OBJECTS { ifIndex }
 STATUS  current
 DESCRIPTION
    "Send the trap when RSTP determines a port should enter the FORWARDING state
     (a topology change occurs). The OID value is the ifIndex of the port that
     produces the topology change."
 ::= { gs2124TrapEntry 9 }

gs2124LacpStateDisabled NOTIFICATION-TYPE
    OBJECTS {ifIndex, groupId}
 STATUS  current
 DESCRIPTION
    "Send the trap when the operational state of LACP is from enabled to disabled.
     The OID value means the disabled Group ID."
 ::= { gs2124TrapEntry 10 }

gs2124LacpStateEnabled NOTIFICATION-TYPE
    OBJECTS {ifIndex, groupId}
 STATUS  current
 DESCRIPTION
    "Send the trap when the operational state of LACP is from disabled to enabled.
     The OID value means the disabled Group ID."
 ::= { gs2124TrapEntry 11 }

gs2124LacpPortAdded NOTIFICATION-TYPE
    OBJECTS   { ifIndex, actorkey, partnerkey }
 STATUS  current
 DESCRIPTION
    "Send the trap when the state of port is in 'trunk ready'."
 ::= { gs2124TrapEntry 12 }

gs2124LacpPortTrunkFailure NOTIFICATION-TYPE
    OBJECTS   { ifIndex, actorkey, partnerkey}
 STATUS  current
 DESCRIPTION
    "Send the trap when one port is not able to be aggregated
     due to duplex-mode of the port."
 ::= { gs2124TrapEntry 13 }

gs2124GvrpStateDisabled NOTIFICATION-TYPE
 STATUS  current
 DESCRIPTION
    "Send the trap when the operational state of GVRP is from enabled to disabled."
 ::= { gs2124TrapEntry 14 }

gs2124GvrpStateEnabled NOTIFICATION-TYPE
 STATUS  current
 DESCRIPTION
    "Send the trap when the operational state of LACP is from disabled to enabled. "
 ::= { gs2124TrapEntry 15 }

gs2124VlanPortBaseEnabled NOTIFICATION-TYPE
 STATUS  current
 DESCRIPTION
    "Send the trap when the operational state of vlan is changed to port-based vlan."
 ::= { gs2124TrapEntry 17 }

gs2124VlanTagBaseEnabled NOTIFICATION-TYPE
 STATUS  current
 DESCRIPTION
    "Send the trap when the operational state of vlan is changed to tag-based vlan."
 ::= { gs2124TrapEntry 18 }

gs2124IpmbStateEnabled NOTIFICATION-TYPE
 STATUS  current
 DESCRIPTION
    "Send trap when ip_mac_binding is enabled."
 ::= { gs2124TrapEntry 19 }

gs2124IpmbStateDisabled NOTIFICATION-TYPE
 STATUS  current
 DESCRIPTION
    "Send trap when ip_mac_binding is disabled."
 ::= { gs2124TrapEntry 20 }

gs2124IpmbEntryFailure NOTIFICATION-TYPE
    OBJECTS   { ipmacIp, ipmacMac, ifIndex}
 STATUS  current
 DESCRIPTION
    "Send trap when ip_mac_binding entry is not exist."
 ::= { gs2124TrapEntry 21 }

gs2124TrapVariable OBJECT IDENTIFIER ::= { gs2124Produces 21 }

username OBJECT-TYPE
    SYNTAX      DisplayString
 MAX-ACCESS  read-only
 STATUS      current
 DESCRIPTION
     "System account name."
 ::= { gs2124TrapVariable 1 }

groupId OBJECT-TYPE
    SYNTAX      INTEGER(1..2147483647)
 MAX-ACCESS  read-only
 STATUS      current
 DESCRIPTION
     "The Trunk group ID of LACP."
 ::= { gs2124TrapVariable 2 }

actorkey OBJECT-TYPE
    SYNTAX INTEGER(1..2147483647)
 MAX-ACCESS  read-only
 STATUS      current
 DESCRIPTION
     "This is the actor key information for LACP."
 ::= { gs2124TrapVariable 3 }

partnerkey OBJECT-TYPE
    SYNTAX INTEGER(1..2147483647)
 MAX-ACCESS  read-only
 STATUS      current
 DESCRIPTION
     "This is the partner key information for LACP."
 ::= { gs2124TrapVariable 4 }

swapto OBJECT-TYPE
    SYNTAX      DisplayString
 MAX-ACCESS  read-only
 STATUS      current
 DESCRIPTION
     "A notification for dual port changes media type."
 ::= { gs2124TrapVariable 6 }

ipmacIp OBJECT-TYPE
    SYNTAX DisplayString
 MAX-ACCESS  read-only
 STATUS      current
 DESCRIPTION
     "IP address of the ip_mac_binding entry."
 ::= { gs2124TrapVariable 7 }

ipmacMac OBJECT-TYPE
    SYNTAX DisplayString
 MAX-ACCESS  read-only
 STATUS      current
 DESCRIPTION
     "MAC address of the ip_mac_binding entry."
 ::= { gs2124TrapVariable 8 }


gs2124mstpMIB        OBJECT IDENTIFIER ::= { gs2124Produces 200 }

gs2124mstpInstanceView            OBJECT IDENTIFIER ::= { gs2124mstpMIB 1 }

gs2124mstpInstanceEntryCreate OBJECT-TYPE
 SYNTAX      INTEGER(0..4094)
 MAX-ACCESS     read-write
 STATUS  current
 DESCRIPTION
  "This oid will be used in created a instance entry. Input: new Instance id."
 ::= { gs2124mstpInstanceView 1 }

gs2124mstpInstanceViewTable   OBJECT-TYPE
                          SYNTAX      SEQUENCE OF GS2124MstpInstanceViewEntry
                          MAX-ACCESS  not-accessible
                          STATUS      current
                          DESCRIPTION
                            "This table contains Instance entry for the MSTP."
                          ::= { gs2124mstpInstanceView 2 }

gs2124mstpInstanceViewEntry   OBJECT-TYPE
                          SYNTAX      GS2124MstpInstanceViewEntry
                          MAX-ACCESS  not-accessible
                          STATUS      current
                          DESCRIPTION
                              "Information regarding the instance to which each Vlan is mapped."
                          INDEX  { gs2124mstpInstanceViewIndex }
                          ::= { gs2124mstpInstanceViewTable 1 }

GS2124MstpInstanceViewEntry ::= SEQUENCE {
                   gs2124mstpInstanceViewIndex                Integer32,
                   gs2124mstpInstanceViewInstance             Integer32,
                   gs2124mstpInstanceViewCorrespondingVlans   DisplayString,
                   gs2124mstpInstanceViewEntryAction          INTEGER
               }

gs2124mstpInstanceViewIndex       OBJECT-TYPE
                              SYNTAX      Integer32(1..65)
                              MAX-ACCESS  not-accessible
                              STATUS      current
                              DESCRIPTION
                                 "The index of instance View table."
                              ::= { gs2124mstpInstanceViewEntry 1 }

gs2124mstpInstanceViewInstance       OBJECT-TYPE
                              SYNTAX      Integer32
                              MAX-ACCESS  read-write
                              STATUS      current
                              DESCRIPTION
                                 "An integer with values ranging from 0 to 4094 that identify
                      the CIST/MSTI instance to which this VLAN is mapped."
                              ::= { gs2124mstpInstanceViewEntry 2 }

gs2124mstpInstanceViewCorrespondingVlans   OBJECT-TYPE
                           SYNTAX      DisplayString
                           MAX-ACCESS  read-write
                           STATUS      current
                           DESCRIPTION
                              "Information regarding the instance which is Vlan mapped.
                              syntax example: 2.5-7.100-200
                                   available from 1 to 4094"
                           ::= { gs2124mstpInstanceViewEntry 3 }

gs2124mstpInstanceViewEntryAction OBJECT-TYPE
 SYNTAX  INTEGER(1..3)
 MAX-ACCESS     read-write
 STATUS  current
 DESCRIPTION
  "This is RowState.
   1 - active.
   2 - notInService.
   3 - delete."
 ::= { gs2124mstpInstanceViewEntry 4 }


gs2124mstpGen            OBJECT IDENTIFIER ::= { gs2124mstpMIB 2 }
-- mstpGen group reflects configurations/statuses
-- the Bridge as a unit

gs2124mstpGenSupported  OBJECT-TYPE
                SYNTAX      INTEGER(0|1)
                MAX-ACCESS  read-write
                STATUS      current
                DESCRIPTION
                  "Enable/Disable Multiple Spanning Tree Protocol
                  0:disable
                  1:enable"
                ::= { gs2124mstpGen 1 }

gs2124mstpGenVersion  OBJECT-TYPE
                SYNTAX      INTEGER(1|2|3)
                MAX-ACCESS  read-write
                STATUS      current
                DESCRIPTION
                  "The version of (Multiple/Rapid) Spanning Tree Protocol the bridge is
            currently running.  The value 'STP(1)'
            indicates the Spanning Tree Protocol specified in
            IEEE 802.1D-1998 , 'RSTP(2)' indicates the Rapid
            Spanning Tree Protocol specified in IEEE 802.1w and
            clause 17 of 802.1D-2004, and 'MSTP(3)' indicates the
            Multiple Spanning Tree Protocol.  The values are directly from
            the IEEE standard.  New values may be defined as future
            versions of the protocol become available.

            The value of this object MUST be retained across
            reinitializations of the management system."
                ::= { gs2124mstpGen 2 }

gs2124mstpGenCfgIdFmtSel OBJECT-TYPE
                   SYNTAX      Integer32
                   MAX-ACCESS  read-only
                   STATUS      current
                   DESCRIPTION
                     "Configuration Identificator Format Selector."
                   ::= { gs2124mstpGen 3 }

gs2124mstpGenCfgIdName   OBJECT-TYPE
                   SYNTAX      DisplayString (SIZE (32))
                   MAX-ACCESS  read-write
                   STATUS      current
                   DESCRIPTION
                     "The configuration name that identifies the MST
                      region and is used as one of the inputs in the
                      computation of the MST Configuration Identifier."
                   ::= { gs2124mstpGen 4 }

gs2124mstpGenCfgIdRevLevel OBJECT-TYPE
                   SYNTAX      Integer32(0..65535)
                   MAX-ACCESS  read-write
                   STATUS      current
                   DESCRIPTION
                     "This object identifies the MST revision that
                      identifies the MST region and is used as one
                      of the inputs in the computation of the MST
                      configuration Identifier."
                   ::= { gs2124mstpGen 5 }

gs2124mstpGenBridgeMaxAge  OBJECT-TYPE
                         SYNTAX      Integer32 (0..255)
                         MAX-ACCESS  read-only
                         STATUS      current
                         DESCRIPTION
                           "The maximum age of MSTP information learned from the
                           network on any port before it is discarded.  This is
                           the actual value that this bridge is currently using."
                         ::= { gs2124mstpGen 6 }

gs2124mstpGenBridgeFwdDelay  OBJECT-TYPE
                         SYNTAX      Integer32
                         MAX-ACCESS  read-only
                         STATUS      current
                         DESCRIPTION
                           "This time value controls how fast a port changes its
                      spanning state when moving towards the Forwarding
                      state.  The value determines how long the port
                      stays in each of the Listening and Learning
                      states, which precede the Forwarding state.  This
                      value is also used, when a topology change has
                      been detected and is underway, to age all dynamic
                      entries in the Forwarding Database."
                         ::= { gs2124mstpGen 7 }

gs2124mstpGenBridgeMaxHops  OBJECT-TYPE
                SYNTAX      Integer32
                MAX-ACCESS  read-only
                STATUS      current
                DESCRIPTION
                  "The hop count is assigned by the CIST/MSTI Regional Root and decremented by each receiving Port.
                  Received information is discarded and the port made a Designated Port if the hop count reaches
                  zero."
                ::= { gs2124mstpGen 8 }


gs2124mstpGenInstancePriority OBJECT-TYPE
                         SYNTAX      Integer32
                         MAX-ACCESS  read-only
                         STATUS      current
                         DESCRIPTION
                           "That is the current Instance Priority ID."
                         ::= { gs2124mstpGen 9 }

gs2124mstpGenCistRootPriority OBJECT-TYPE
                         SYNTAX      Integer32
                         MAX-ACCESS  read-only
                         STATUS      current
                         DESCRIPTION
                           "The Priority ID of CIST Root Bridge."
                         ::= { gs2124mstpGen 10 }


gs2124mstpGenCistRootMac OBJECT-TYPE
                         SYNTAX      MacAddress
                         MAX-ACCESS  read-only
                         STATUS      current
                         DESCRIPTION
                           "The MAC of CIST Root Bridge. That is last 6 octets of Bridge
                           ID."
                         ::= { gs2124mstpGen 11 }


gs2124mstpGenCistExtRootPathCost OBJECT-TYPE
                         SYNTAX      Integer32
                         MAX-ACCESS  read-only
                         STATUS      current
                         DESCRIPTION
                           "The path cost between MST Regions from the transmitting Bridge to the CIST Root."
                         ::= { gs2124mstpGen 12 }

gs2124mstpGenCistRootPortId OBJECT-TYPE
                         SYNTAX      Integer32
                         MAX-ACCESS  read-only
                         STATUS      current
                         DESCRIPTION
                           "The Port ID of Bridge Identifier of the single bridge in a Region whose CIST Root Port is a
                            Boundary Port, or the Bridge Identifier of the CIST Root if that is within the Region."
                         ::= { gs2124mstpGen 13 }

gs2124mstpGenCistRegionalRootPriority OBJECT-TYPE
                         SYNTAX      Integer32
                         MAX-ACCESS  read-only
                         STATUS      current
                         DESCRIPTION
                           "That is current Root Priority of Cist."
                         ::= { gs2124mstpGen 14 }

gs2124mstpGenCistRegionalRootMac OBJECT-TYPE
                         SYNTAX      MacAddress
                         MAX-ACCESS  read-only
                         STATUS      current
                         DESCRIPTION
                           "The MAC of Bridge Identifier of the single bridge in a Region whose CIST Root Port is a
                            Boundary Port, or the Bridge Identifier of the CIST Root if that is within the Region."
                         ::= { gs2124mstpGen 15 }

gs2124mstpGenCistInternalRootPathCost OBJECT-TYPE
                         SYNTAX      Integer32
                         MAX-ACCESS  read-only
                         STATUS      current
                         DESCRIPTION
                           "The path cost of the CIST Regional Root"
                         ::= { gs2124mstpGen 16 }

gs2124mstpGenCistCurrentMaxAge OBJECT-TYPE
                         SYNTAX      Integer32
                         MAX-ACCESS  read-only
                         STATUS      current
                         DESCRIPTION
                           "The maximum age of Cist information learned from the network on any port
                      before it is discarded.  This is the actual value that this
                      bridge is currently using."
                         ::= { gs2124mstpGen 17 }

gs2124mstpGenCistCurrentFwdDelay  OBJECT-TYPE
                         SYNTAX      Integer32
                         MAX-ACCESS  read-only
                         STATUS      current
                         DESCRIPTION
                           "This time value controls how fast a port changes its
                      Cist spanning state when moving towards the Forwarding
                      state.  The value determines how long the port
                      stays in each of the Listening and Learning
                      states, which precede the Forwarding state.  This
                      value is also used, when a topology change has
                      been detected and is underway, to age all dynamic
                      entries in the Forwarding Database."
                         ::= { gs2124mstpGen 18 }

gs2124mstpGenTimeSinceLastTopoChange  OBJECT-TYPE
                         SYNTAX      Integer32
                         MAX-ACCESS  read-only
                         STATUS      current
                         DESCRIPTION
                           "The time (SECs) since the last time a topology change
                           was detected by the bridge entity."
                         ::= { gs2124mstpGen 19 }

gs2124mstpGenTopoChangeCount  OBJECT-TYPE
                         SYNTAX      Integer32
                         MAX-ACCESS  read-only
                         STATUS      current
                         DESCRIPTION
                           "The total number of topology changes detected by
                      this bridge since the management entity was last
                      reset or initialized. Unit:SECs"
                         ::= { gs2124mstpGen 20 }

gs2124mstpMstiStatusTable        OBJECT-TYPE
                   SYNTAX      SEQUENCE OF GS2124MstpMstiStatusEntry
                   MAX-ACCESS  not-accessible
                   STATUS      current
                   DESCRIPTION
                     "This table contains the status entry for each instance of the MSTP."
                   ::= { gs2124mstpMIB 3 }

gs2124mstpMstiStatusEntry        OBJECT-TYPE
                   SYNTAX      GS2124MstpMstiStatusEntry
                   MAX-ACCESS  not-accessible
                   STATUS      current
                   DESCRIPTION
                       "A conceptual row containing the port status of the MSTP instance."
                   INDEX  { gs2124mstpMstiStatusInstanceIndex }
                   ::= { gs2124mstpMstiStatusTable 1 }


GS2124MstpMstiStatusEntry ::= SEQUENCE {
                   gs2124mstpMstiStatusInstanceIndex        Integer32,
                   gs2124mstpMstiStatusState                DisplayString,
                   gs2124mstpMstiStatusPriority             Integer32,
                   gs2124mstpMstiStatusBridgeMac            MacAddress,
                   gs2124mstpMstiStatusRegionalRootPriority Integer32,
                   gs2124mstpMstiStatusRegionalRootMac      MacAddress,
                   gs2124mstpMstiStatusInternalRootPathCost Integer32,
                   gs2124mstpMstiStatusRootPortId           Integer32,
                   gs2124mstpMstiStatusTimeSinceLastTopoChg Integer32,
                   gs2124mstpMstiStatusTopochgcount         Integer32
               }

gs2124mstpMstiStatusInstanceIndex        OBJECT-TYPE
                   SYNTAX      Integer32 (1..4094)
                   MAX-ACCESS  not-accessible
                   STATUS      current
                   DESCRIPTION
                     "A unique value, greater than zero, for each Instance."
                   ::= { gs2124mstpMstiStatusEntry 1 }

gs2124mstpMstiStatusState     OBJECT-TYPE
                         SYNTAX      DisplayString
                         MAX-ACCESS  read-only
                         STATUS      current
                         DESCRIPTION
                            "The status of each MSTI."
                         ::= { gs2124mstpMstiStatusEntry 2 }

gs2124mstpMstiStatusPriority     OBJECT-TYPE
                         SYNTAX      Integer32
                         MAX-ACCESS  read-only
                         STATUS      current
                         DESCRIPTION
                            "That is current Priority of MSTI."
                         ::= { gs2124mstpMstiStatusEntry 3 }

gs2124mstpMstiStatusBridgeMac     OBJECT-TYPE
                         SYNTAX      MacAddress
                         MAX-ACCESS  read-only
                         STATUS      current
                         DESCRIPTION
                            "The bridge MAC of MSTI."
                         ::= { gs2124mstpMstiStatusEntry 4 }

gs2124mstpMstiStatusRegionalRootPriority     OBJECT-TYPE
                         SYNTAX      Integer32
                         MAX-ACCESS  read-only
                         STATUS      current
                         DESCRIPTION
                            "The Priority of the MSTI Region Root."
                         ::= { gs2124mstpMstiStatusEntry 5 }

gs2124mstpMstiStatusRegionalRootMac     OBJECT-TYPE
                         SYNTAX      MacAddress
                         MAX-ACCESS  read-only
                         STATUS      current
                         DESCRIPTION
                            "The bridge MAC of MSTI Region Root."
                         ::= { gs2124mstpMstiStatusEntry 6 }

gs2124mstpMstiStatusInternalRootPathCost     OBJECT-TYPE
                         SYNTAX      Integer32
                         MAX-ACCESS  read-only
                         STATUS      current
                         DESCRIPTION
                            "The Internal Path Cost of each MSTI."
                         ::= { gs2124mstpMstiStatusEntry 7 }

gs2124mstpMstiStatusRootPortId     OBJECT-TYPE
                         SYNTAX      Integer32
                         MAX-ACCESS  read-only
                         STATUS      current
                         DESCRIPTION
                            "The port number of the port which offers the
                      lowest cost path from this region to the root
                      bridge"
                         ::= { gs2124mstpMstiStatusEntry 8 }

gs2124mstpMstiStatusTimeSinceLastTopoChg     OBJECT-TYPE
                         SYNTAX      Integer32
                         MAX-ACCESS  read-only
                         STATUS      current
                         DESCRIPTION
                            "The time (SECs) since the last time a topology change
                           was detected by the MSTI entity."
                         ::= { gs2124mstpMstiStatusEntry 9 }

gs2124mstpMstiStatusTopochgcount     OBJECT-TYPE
                         SYNTAX      Integer32
                         MAX-ACCESS  read-only
                         STATUS      current
                         DESCRIPTION
                            "The total number of topology changes detected by
                      this Msti since the management entity was last
                      reset or initialized. Unit:SECs"
                         ::= { gs2124mstpMstiStatusEntry 10 }


gs2124mstpPortCfg            OBJECT IDENTIFIER ::= { gs2124mstpMIB 4 }

gs2124mstpCistPortCfgTable   OBJECT-TYPE
                          SYNTAX      SEQUENCE OF GS2124MstpCistPortCfgEntry
                          MAX-ACCESS  not-accessible
                          STATUS      current
                          DESCRIPTION
                            "This table contains port config entry for the CIST of MSTP."
                          ::= { gs2124mstpPortCfg 1 }

gs2124mstpCistPortCfgEntry   OBJECT-TYPE
                          SYNTAX      GS2124MstpCistPortCfgEntry
                          MAX-ACCESS  not-accessible
                          STATUS      current
                          DESCRIPTION
                              "A conceptual row containing the port status of the MSTP instance 0."
                          INDEX  { gs2124mstpCistPortCfgPortIndex }
                          ::= { gs2124mstpCistPortCfgTable 1 }


GS2124MstpCistPortCfgEntry ::= SEQUENCE {
                   gs2124mstpCistPortCfgPortIndex        Integer32,
                   gs2124mstpCistPortCfgPathCost         Integer32,
                   gs2124mstpCistPortCfgPriority         Integer32,
                   gs2124mstpCistPortCfgHelloTime        Integer32,
                   gs2124mstpCistPortCfgAdminEdge        Integer32,
                   gs2124mstpCistPortCfgP2P              Integer32,
                   gs2124mstpCistPortCfgRestrictedRole   Integer32,
                   gs2124mstpCistPortCfgRestrictedTcn    Integer32,
                   gs2124mstpCistPortCfgMigrationCheck   Integer32
               }

gs2124mstpCistPortCfgPortIndex   OBJECT-TYPE
                              SYNTAX      Integer32 (1..4094)
                              MAX-ACCESS  not-accessible
                              STATUS      current
                              DESCRIPTION
                                 "That is index of the port, greater than zero in
                                 the managed Bridge.  It is a unique value."
                              ::= { gs2124mstpCistPortCfgEntry 1 }

gs2124mstpCistPortCfgPathCost   OBJECT-TYPE
                           SYNTAX      Integer32
                           MAX-ACCESS  read-write
                           STATUS      current
                           DESCRIPTION
                              "The path cost of each port in CIST."
                           ::= { gs2124mstpCistPortCfgEntry 2 }

gs2124mstpCistPortCfgPriority   OBJECT-TYPE
                           SYNTAX      Integer32
                           MAX-ACCESS  read-write
                           STATUS      current
                           DESCRIPTION
                              "The priority of each port in CIST."
                           ::= { gs2124mstpCistPortCfgEntry 3 }

gs2124mstpCistPortCfgHelloTime   OBJECT-TYPE
                           SYNTAX      Integer32
                           MAX-ACCESS  read-write
                           STATUS      current
                           DESCRIPTION
                              "The amount of time between the transmission of
                      Configuration bridge PDUs by this node on any port
                      when it is the root of the spanning tree or trying
                      to become so."
                           ::= { gs2124mstpCistPortCfgEntry 4 }

gs2124mstpCistPortCfgAdminEdge   OBJECT-TYPE
                           SYNTAX      Integer32
                           MAX-ACCESS  read-write
                           STATUS      current
                           DESCRIPTION
                              "The administrative value of the Edge Port parameter.  A
            value of true(1) indicates that this port should be
            assumed as an edge-port, and a value of false(2) indicates
            that this port should be assumed as a non-edge-port.

            Setting this object will also cause the corresponding
            instance of mstpCistPortStatusOperEdge to change to the
            same value.  Note that even when this object's value
            is true, the value of the corresponding instance of
            mstpCistPortStatusOperEdge can be false if a BPDU has
            been received.

            The value of this object MUST be retained across
            reinitializations of the management system."
                           ::= { gs2124mstpCistPortCfgEntry 5 }

gs2124mstpCistPortCfgP2P   OBJECT-TYPE
                           SYNTAX      Integer32
                           MAX-ACCESS  read-write
                           STATUS      current
                           DESCRIPTION
                              "The administrative point-to-point status of the LAN segment
            attached to this port, using the enumeration values of the
            IEEE 802.1w clause.  A value of forceTrue(0) indicates
            that this port should always be treated as if it is
            connected to a point-to-point link.  A value of
            forceFalse(1) indicates that this port should be treated as
            having a shared media connection.  A value of auto(2)
            indicates that this port is considered to have a
            point-to-point link if it is an Aggregator and all of its

            members are aggregatable, or if the MAC entity
            is configured for full duplex operation, either through
            auto-negotiation or by management means.

            The value of this object MUST be retained across
            reinitializations of the management system."
                           ::= { gs2124mstpCistPortCfgEntry 6 }

gs2124mstpCistPortCfgRestrictedRole   OBJECT-TYPE
                           SYNTAX      Integer32
                           MAX-ACCESS  read-write
                           STATUS      current
                           DESCRIPTION
                              "A Boolean value set by management.
                               0: False
                               1: True"
                           ::= { gs2124mstpCistPortCfgEntry 7 }

gs2124mstpCistPortCfgRestrictedTcn   OBJECT-TYPE
                           SYNTAX      Integer32
                           MAX-ACCESS  read-write
                           STATUS      current
                           DESCRIPTION
                              "A Boolean value set by management.
                               0: False
                               1: True"
                           ::= { gs2124mstpCistPortCfgEntry 8 }

gs2124mstpCistPortCfgMigrationCheck   OBJECT-TYPE
                           SYNTAX      Integer32
                           MAX-ACCESS  read-write
                           STATUS      current
                           DESCRIPTION
                              "When operating in MSTP mode, writing true(1)
            to this object forces this port to transmit MSTP BPDUs.
            Any other operation on this object has no effect and
            it always returns false(0) when read."
                           ::= { gs2124mstpCistPortCfgEntry 9 }



gs2124mstpMstiPortCfgTable   OBJECT-TYPE
                          SYNTAX      SEQUENCE OF GS2124MstpMstiPortCfgEntry
                          MAX-ACCESS  not-accessible
                          STATUS      current
                          DESCRIPTION
                            "This table contains port config entry for the Msti of the MSTP."
                          ::= { gs2124mstpPortCfg 2 }

gs2124mstpMstiPortCfgEntry   OBJECT-TYPE
                          SYNTAX      GS2124MstpMstiPortCfgEntry
                          MAX-ACCESS  not-accessible
                          STATUS      current
                          DESCRIPTION
                              "A conceptual row containing the port status of the MSTP instance."
                          INDEX  { gs2124mstpMstiPortCfgInstanceIndex , gs2124mstpMstiPortCfgPortIndex}
                          ::= { gs2124mstpMstiPortCfgTable 1 }


GS2124MstpMstiPortCfgEntry ::= SEQUENCE {
                   gs2124mstpMstiPortCfgInstanceIndex    Integer32,
                   gs2124mstpMstiPortCfgPortIndex        Integer32,
                   gs2124mstpMstiPortCfgPathCost         Integer32,
                   gs2124mstpMstiPortCfgPriority         Integer32
               }


gs2124mstpMstiPortCfgInstanceIndex        OBJECT-TYPE
                   SYNTAX      Integer32 (1..4094)
                   MAX-ACCESS  not-accessible
                   STATUS      current
                   DESCRIPTION
                     "A unique value, greater than zero, for each Instance."
                   ::= { gs2124mstpMstiPortCfgEntry 1 }


gs2124mstpMstiPortCfgPortIndex       OBJECT-TYPE
                              SYNTAX      Integer32 (1..4094)
                              MAX-ACCESS  not-accessible
                              STATUS      current
                              DESCRIPTION
                                 "A unique value, greater than zero, for each Port.
                                 The value for each interface sub-layer
                                 must remain constant at least from one re-initialization
                                 of the entity's network management system to the next re-
                                 initialization."
                              ::= { gs2124mstpMstiPortCfgEntry 2 }

gs2124mstpMstiPortCfgPathCost   OBJECT-TYPE
                           SYNTAX      Integer32
                           MAX-ACCESS  read-write
                           STATUS      current
                           DESCRIPTION
                              "The path cost of each port in the MSTI Regional."
                           ::= { gs2124mstpMstiPortCfgEntry 3 }

gs2124mstpMstiPortCfgPriority   OBJECT-TYPE
                           SYNTAX      Integer32
                           MAX-ACCESS  read-write
                           STATUS      current
                           DESCRIPTION
                              "The Priority of each port in the MSTI Regional."
                           ::= { gs2124mstpMstiPortCfgEntry 4 }


gs2124mstpCfg            OBJECT IDENTIFIER ::= { gs2124mstpMIB 5 }

gs2124mstpCfgCist            OBJECT IDENTIFIER ::= { gs2124mstpCfg 1 }

gs2124mstpCfgCistPriority   OBJECT-TYPE
                           SYNTAX      Integer32(0..61440)
                           MAX-ACCESS  read-write
                           STATUS      current
                           DESCRIPTION
                              "The Priority of the CIST Regional."
                           ::= { gs2124mstpCfgCist 1 }

gs2124mstpCfgCistMaxAge   OBJECT-TYPE
                           SYNTAX      Integer32(6..40)
                           MAX-ACCESS  read-write
                           STATUS      current
                           DESCRIPTION
                              "The maximum age of CIST. The range from 6 to 40.
                              The value that all bridges use for MaxAge when
                              this bridge is acting as the root."
                           ::= { gs2124mstpCfgCist 2 }

gs2124mstpCfgCistFwdDelay   OBJECT-TYPE
                           SYNTAX      Integer32(4..30)
                           MAX-ACCESS  read-write
                           STATUS      current
                           DESCRIPTION
                              "The value that all bridges use for ForwardDelay
                      when this bridge is acting as the root.
                      An agent may return a badValue error if a set is
                      attempted to a value which is not a whole number
                      of seconds."
                           ::= { gs2124mstpCfgCist 3 }

gs2124mstpCfgCistMaxHops   OBJECT-TYPE
                           SYNTAX      Integer32(6..40)
                           MAX-ACCESS  read-write
                           STATUS      current
                           DESCRIPTION
                             "That is Max hop count of the CIST.  If the bridge is
                             the CIST Regional Root"
                           ::= { gs2124mstpCfgCist 4 }


gs2124mstpCfgMstiTable   OBJECT-TYPE
                          SYNTAX      SEQUENCE OF GS2124MstpCfgMstiEntry
                          MAX-ACCESS  not-accessible
                          STATUS      current
                          DESCRIPTION
                            "This table contains port config entry for the Msti of MSTP."
                          ::= { gs2124mstpCfg 2 }

gs2124mstpCfgMstiEntry   OBJECT-TYPE
                          SYNTAX      GS2124MstpCfgMstiEntry
                          MAX-ACCESS  not-accessible
                          STATUS      current
                          DESCRIPTION
                              "A conceptual row containing the Msti Config of the MSTP instance."
                          INDEX  { gs2124mstpCfgMstiInstanceIndex }
                          ::= { gs2124mstpCfgMstiTable 1 }


GS2124MstpCfgMstiEntry ::= SEQUENCE {
                   gs2124mstpCfgMstiInstanceIndex    Integer32 ,
                   gs2124mstpCfgMstiPriority         Integer32
               }


gs2124mstpCfgMstiInstanceIndex       OBJECT-TYPE
                              SYNTAX      Integer32 (1..4094)
                              MAX-ACCESS  not-accessible
                              STATUS      current
                              DESCRIPTION
                                 "A unique value, greater than zero, for each Port.
                                 The value for each interface sub-layer
                                 must remain constant at least from one re-initialization
                                 of the entity's network management system to the next re-
                                 initialization."
                              ::= { gs2124mstpCfgMstiEntry 1 }

gs2124mstpCfgMstiPriority   OBJECT-TYPE
                           SYNTAX      Integer32
                           MAX-ACCESS  read-write
                           STATUS      current
                           DESCRIPTION
                              "The Priority of the MSTI Regional.
                               that is a multiple of 4096."
                           ::= { gs2124mstpCfgMstiEntry 2 }

gs2124mstpPortStatus            OBJECT IDENTIFIER ::= { gs2124mstpMIB 6 }

gs2124mstpCistPortStatusTable   OBJECT-TYPE
                          SYNTAX      SEQUENCE OF GS2124MstpCistPortStatusEntry
                          MAX-ACCESS  not-accessible
                          STATUS      current
                          DESCRIPTION
                            "This table contains port status entry for the CIST of MSTP."
                          ::= { gs2124mstpPortStatus 1 }

gs2124mstpCistPortStatusEntry   OBJECT-TYPE
                          SYNTAX      GS2124MstpCistPortStatusEntry
                          MAX-ACCESS  not-accessible
                          STATUS      current
                          DESCRIPTION
                              "A conceptual row containing the port status of the MSTP instance 0."
                          INDEX  { gs2124mstpCistPortStatusPortIndex }
                          ::= { gs2124mstpCistPortStatusTable 1 }


GS2124MstpCistPortStatusEntry ::= SEQUENCE {
                   gs2124mstpCistPortStatusPortIndex        Integer32,
                   gs2124mstpCistPortStatusStatus           DisplayString,
                   gs2124mstpCistPortStatusRole             DisplayString,
                   gs2124mstpCistPortStatusPathCost         Integer32,
                   gs2124mstpCistPortStatusPriority         Integer32,
                   gs2124mstpCistPortStatusHelloTime        DisplayString,
                   gs2124mstpCistPortStatusOperEdge         DisplayString,
                   gs2124mstpCistPortStatusOperP2P          DisplayString,
                   gs2124mstpCistPortStatusRestrictedRole   DisplayString,
                   gs2124mstpCistPortStatusRestrictedTcn    DisplayString
               }

gs2124mstpCistPortStatusPortIndex   OBJECT-TYPE
                              SYNTAX      Integer32 (1..4094)
                              MAX-ACCESS  not-accessible
                              STATUS      current
                              DESCRIPTION
                                 "A unique value, greater than zero, for each Port.
                                 The value for each interface sub-layer
                                 must remain constant at least from one re-initialization
                                 of the entity's network management system to the next re-
                                 initialization."
                              ::= { gs2124mstpCistPortStatusEntry 1 }

gs2124mstpCistPortStatusStatus   OBJECT-TYPE
                           SYNTAX      DisplayString
                           MAX-ACCESS  read-only
                           STATUS      current
                           DESCRIPTION
                              "That is status of the CIST (each port)."
                           ::= { gs2124mstpCistPortStatusEntry 2 }

gs2124mstpCistPortStatusRole   OBJECT-TYPE
                         SYNTAX      DisplayString
                         MAX-ACCESS  read-only
                         STATUS      current
                         DESCRIPTION
                            "That is the status role of each port in the CIST."
                         ::= { gs2124mstpCistPortStatusEntry 3 }

gs2124mstpCistPortStatusPathCost   OBJECT-TYPE
                         SYNTAX      Integer32
                         MAX-ACCESS  read-only
                         STATUS      current
                         DESCRIPTION
                            "The current path cost of each port in CIST."
                         ::= { gs2124mstpCistPortStatusEntry 4 }

gs2124mstpCistPortStatusPriority   OBJECT-TYPE
                             SYNTAX      Integer32
                             MAX-ACCESS  read-only
                             STATUS      current
                             DESCRIPTION
                                "The current priority of the each port in CIST."
                             ::= { gs2124mstpCistPortStatusEntry 5 }

gs2124mstpCistPortStatusHelloTime   OBJECT-TYPE
                              SYNTAX      DisplayString
                              MAX-ACCESS  read-only
                              STATUS      current
                              DESCRIPTION
                                 "The amount of time between the transmission of
                      Configuration bridge PDUs by this node on any port
                      when it is the root of the spanning tree or trying
                      to become so. This is the actual value that this bridge is
                      currently using."
                              ::= { gs2124mstpCistPortStatusEntry 6 }

gs2124mstpCistPortStatusOperEdge   OBJECT-TYPE
                             SYNTAX      DisplayString
                             MAX-ACCESS  read-only
                             STATUS      current
                             DESCRIPTION
                                "The operational value of the Edge Port parameter.  The
            object is initialized to the value of the corresponding
            instance of dot1dStpPortAdminEdgePort.  When the
            corresponding instance of mstpCistPortCfgAdminEdge is
            set, this object will be changed as well.  This object
            will also be changed to false on reception of a BPDU."
                             ::= { gs2124mstpCistPortStatusEntry 7 }

gs2124mstpCistPortStatusOperP2P   OBJECT-TYPE
                            SYNTAX      DisplayString
                            MAX-ACCESS  read-only
                            STATUS      current
                            DESCRIPTION
                               "The operational point-to-point status of the LAN segment
            attached to this port.  It indicates whether a port is
            considered to have a point-to-point connection.
            If adminPointToPointMAC is set to auto(2), then the value
            of operPointToPointMAC is determined in accordance with the
            specific procedures defined for the MAC entity concerned.  The value is
            determined dynamically; that is, it is re-evaluated whenever
            the value of adminPointToPointMAC changes, and whenever
            the specific procedures defined for the MAC entity evaluate
            a change in its point-to-point status."
                            ::= { gs2124mstpCistPortStatusEntry 8 }

gs2124mstpCistPortStatusRestrictedRole   OBJECT-TYPE
                                   SYNTAX      DisplayString
                                   MAX-ACCESS  read-only
                                   STATUS      current
                                   DESCRIPTION
                                      "The restricted Role of each port for the CIST."
                                   ::= { gs2124mstpCistPortStatusEntry 9 }

gs2124mstpCistPortStatusRestrictedTcn   OBJECT-TYPE
                                  SYNTAX      DisplayString
                                  MAX-ACCESS  read-only
                                  STATUS      current
                                  DESCRIPTION
                                      "The restricted Tcn of each port for the CIST."
                                  ::= { gs2124mstpCistPortStatusEntry 10 }


gs2124mstpMstiPortStatusTable        OBJECT-TYPE
                   SYNTAX      SEQUENCE OF GS2124MstpMstiPortStatusEntry
                   MAX-ACCESS  not-accessible
                   STATUS      current
                   DESCRIPTION
                     "This table contains port status entry for each instance of MSTP."
                   ::= { gs2124mstpPortStatus 2 }

gs2124mstpMstiPortStatusEntry        OBJECT-TYPE
                   SYNTAX      GS2124MstpMstiPortStatusEntry
                   MAX-ACCESS  not-accessible
                   STATUS      current
                   DESCRIPTION
                       "A conceptual row containing the port status of the MSTP instance."
                   INDEX  { gs2124mstpMstiPortStatusInstanceIndex, gs2124mstpMstiPortStatusPortIndex }
                   ::= { gs2124mstpMstiPortStatusTable 1 }


GS2124MstpMstiPortStatusEntry ::= SEQUENCE {
                   gs2124mstpMstiPortStatusInstanceIndex    Integer32,
                   gs2124mstpMstiPortStatusPortIndex        Integer32,
                   gs2124mstpMstiPortStatusStatus           DisplayString,
                   gs2124mstpMstiPortStatusRole             DisplayString,
                   gs2124mstpMstiPortStatusPathCost         DisplayString,
                   gs2124mstpMstiPortStatusPriority         DisplayString,
                   gs2124mstpMstiPortStatusHelloTime        DisplayString,
                   gs2124mstpMstiPortStatusOperEdge         DisplayString,
                   gs2124mstpMstiPortStatusOperP2P          DisplayString,
                   gs2124mstpMstiPortStatusRestrictedRole   DisplayString,
                   gs2124mstpMstiPortStatusRestrictedTcn    DisplayString
               }

gs2124mstpMstiPortStatusInstanceIndex        OBJECT-TYPE
                   SYNTAX      Integer32 (1..4094)
                   MAX-ACCESS  not-accessible
                   STATUS      current
                   DESCRIPTION
                     "A unique value, greater than zero, for each Instance."
                   ::= { gs2124mstpMstiPortStatusEntry 1 }


gs2124mstpMstiPortStatusPortIndex       OBJECT-TYPE
                              SYNTAX      Integer32 (1..4094)
                              MAX-ACCESS  not-accessible
                              STATUS      current
                              DESCRIPTION
                                 "A unique value, greater than zero, for each Port.
                                 The value for each interface sub-layer
                                 must remain constant at least from one re-initialization
                                 of the entity's network management system to the next re-
                                 initialization."
                              ::= { gs2124mstpMstiPortStatusEntry 2 }

gs2124mstpMstiPortStatusStatus     OBJECT-TYPE
                         SYNTAX      DisplayString
                         MAX-ACCESS  read-only
                         STATUS      current
                         DESCRIPTION
                            "That is status of the MSTI (each port)."
                         ::= { gs2124mstpMstiPortStatusEntry 3 }

gs2124mstpMstiPortStatusRole     OBJECT-TYPE
                       SYNTAX      DisplayString
                       MAX-ACCESS  read-only
                       STATUS      current
                       DESCRIPTION
                          "That is the status role of each port for the MSTI."
                       ::= { gs2124mstpMstiPortStatusEntry 4 }

gs2124mstpMstiPortStatusPathCost     OBJECT-TYPE
                           SYNTAX      DisplayString
                           MAX-ACCESS  read-only
                           STATUS      current
                           DESCRIPTION
                              "The current path cost of each port for the MSTI."
                           ::= { gs2124mstpMstiPortStatusEntry 5 }

gs2124mstpMstiPortStatusPriority     OBJECT-TYPE
                           SYNTAX      DisplayString
                           MAX-ACCESS  read-only
                           STATUS      current
                           DESCRIPTION
                              "The current priority of the each port for the MSTI."
                           ::= { gs2124mstpMstiPortStatusEntry 6 }

gs2124mstpMstiPortStatusHelloTime     OBJECT-TYPE
                            SYNTAX      DisplayString
                            MAX-ACCESS  read-only
                            STATUS      current
                            DESCRIPTION
                               "The amount of time between the transmission of
                      Configuration bridge PDUs by this node on any port
                      when it is the root of the MSTI spanning tree or trying
                      to become so. This is the actual value that this bridge is
                      currently using."
                            ::= { gs2124mstpMstiPortStatusEntry 7 }

gs2124mstpMstiPortStatusOperEdge     OBJECT-TYPE
                           SYNTAX      DisplayString
                           MAX-ACCESS  read-only
                           STATUS      current
                           DESCRIPTION
                              "The operational value of the Edge Port parameter."
                           ::= { gs2124mstpMstiPortStatusEntry 8 }

gs2124mstpMstiPortStatusOperP2P     OBJECT-TYPE
                          SYNTAX      DisplayString
                          MAX-ACCESS  read-only
                          STATUS      current
                          DESCRIPTION
                             "The operational point-to-point status of the LAN segment
            attached to this port.  It indicates whether a port is
            considered to have a point-to-point connection."
                          ::= { gs2124mstpMstiPortStatusEntry 9 }

gs2124mstpMstiPortStatusRestrictedRole     OBJECT-TYPE
                                 SYNTAX      DisplayString
                                 MAX-ACCESS  read-only
                                 STATUS      current
                                 DESCRIPTION
                                      "The restricted Role of each port for the MSTI."
                                 ::= { gs2124mstpMstiPortStatusEntry 10 }

gs2124mstpMstiPortStatusRestrictedTcn     OBJECT-TYPE
                                SYNTAX      DisplayString
                                MAX-ACCESS  read-only
                                STATUS      current
                                DESCRIPTION
                                      "The restricted Tcn of each port for the MSTI."
                                ::= { gs2124mstpMstiPortStatusEntry 11 }


END

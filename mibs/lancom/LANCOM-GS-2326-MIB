LANCOM-GS-2326-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2326                                                OBJECT IDENTIFIER ::= { gigabitEthernetSwitches 2326 }

gs2326System                                                OBJECT IDENTIFIER ::= { lancomGS2326  1 }

gs2326SystemInformation                                     OBJECT IDENTIFIER ::= { gs2326System 1 }

gs2326ModelName OBJECT-TYPE
   SYNTAX       DisplayString
   MAX-ACCESS   read-only
   STATUS       current
   DESCRIPTION
       ""
 ::= { gs2326SystemInformation 1 }

gs2326BIOSVersion OBJECT-TYPE
   SYNTAX       DisplayString
   MAX-ACCESS   read-only
   STATUS       current
   DESCRIPTION
       ""
   ::= { gs2326SystemInformation 2 }

gs2326FirmwareVersion OBJECT-TYPE
   SYNTAX       DisplayString
   MAX-ACCESS   read-only
   STATUS       current
   DESCRIPTION
       ""
   ::= { gs2326SystemInformation 3 }

gs2326HardwareMechanicalVersion OBJECT-TYPE
   SYNTAX       DisplayString
   MAX-ACCESS   read-only
   STATUS       current
   DESCRIPTION
       ""
   ::= { gs2326SystemInformation 4 }

gs2326SerialNumber OBJECT-TYPE
   SYNTAX       DisplayString
   MAX-ACCESS   read-only
   STATUS       current
   DESCRIPTION
       ""
   ::= { gs2326SystemInformation 5 }

gs2326HostMACAddress OBJECT-TYPE
   SYNTAX       MacAddress
   MAX-ACCESS   read-only
   STATUS       current
   DESCRIPTION
       ""
   ::= { gs2326SystemInformation 6 }

gs2326ConsoleBaudrate OBJECT-TYPE
   SYNTAX       DisplayString
   MAX-ACCESS   read-only
   STATUS       current
   DESCRIPTION
       ""
   ::= { gs2326SystemInformation 7 }

gs2326RAMSize OBJECT-TYPE
   SYNTAX       DisplayString
   MAX-ACCESS   read-only
   STATUS       current
   DESCRIPTION
       ""
   ::= { gs2326SystemInformation 8 }

gs2326FlashSize OBJECT-TYPE
   SYNTAX       DisplayString
   MAX-ACCESS   read-only
   STATUS       current
   DESCRIPTION
       ""
   ::= { gs2326SystemInformation 9 }

gs2326BridgeFDBSize OBJECT-TYPE
   SYNTAX       DisplayString
   MAX-ACCESS   read-only
   STATUS       current
   DESCRIPTION
       ""
   ::= { gs2326SystemInformation 10 }

gs2326TransmitQueue OBJECT-TYPE
   SYNTAX       DisplayString
   MAX-ACCESS   read-only
   STATUS       current
   DESCRIPTION
       ""
   ::= { gs2326SystemInformation 11 }

gs2326MaximumFrameSize OBJECT-TYPE
   SYNTAX       DisplayString
   MAX-ACCESS   read-only
   STATUS       current
   DESCRIPTION
       ""
   ::= { gs2326SystemInformation 12 }

gs2326CPULoad OBJECT-TYPE
   SYNTAX       DisplayString
   MAX-ACCESS   read-only
   STATUS       current
   DESCRIPTION
       ""
   ::= { gs2326SystemInformation 13 }

gs2326SystemDescription OBJECT-TYPE
   SYNTAX       DisplayString
   MAX-ACCESS   read-only
   STATUS       current
   DESCRIPTION
       ""
   ::= { gs2326SystemInformation 21 }
   
gs2326Location OBJECT-TYPE
   SYNTAX       DisplayString
   MAX-ACCESS   read-only
   STATUS       current
   DESCRIPTION
       ""
   ::= { gs2326SystemInformation 22 }
   
gs2326Contact OBJECT-TYPE
   SYNTAX       DisplayString
   MAX-ACCESS   read-only
   STATUS       current
   DESCRIPTION
       ""
   ::= { gs2326SystemInformation 23 }
   
gs2326DeviceName OBJECT-TYPE
   SYNTAX       DisplayString
   MAX-ACCESS   read-only
   STATUS       current
   DESCRIPTION
       ""
   ::= { gs2326SystemInformation 24 }
   
gs2326SystemDate OBJECT-TYPE
   SYNTAX       DisplayString
   MAX-ACCESS   read-only
   STATUS       current
   DESCRIPTION
       ""
   ::= { gs2326SystemInformation 25 }
   
gs2326SystemUptime OBJECT-TYPE
   SYNTAX       DisplayString
   MAX-ACCESS   read-only
   STATUS       current
   DESCRIPTION
       ""
   ::= { gs2326SystemInformation 26 }
   
gs2326SystemIPv4Address OBJECT-TYPE
   SYNTAX       DisplayString
   MAX-ACCESS   read-only
   STATUS       current
   DESCRIPTION
       ""
   ::= { gs2326SystemInformation 27 }

gs2326SystemIPv4SubnetMask OBJECT-TYPE
   SYNTAX       DisplayString
   MAX-ACCESS   read-only
   STATUS       current
   DESCRIPTION
       ""
   ::= { gs2326SystemInformation 28 }
   
gs2326SystemIPv4Gateway OBJECT-TYPE
   SYNTAX       DisplayString
   MAX-ACCESS   read-only
   STATUS       current
   DESCRIPTION
       ""
   ::= { gs2326SystemInformation 29 }

gs2326IPv6LinkLocalAddress OBJECT-TYPE
   SYNTAX       DisplayString
   MAX-ACCESS   read-only
   STATUS       current
   DESCRIPTION
       ""
   ::= { gs2326SystemInformation 30 }

gs2326IPv6Address OBJECT-TYPE
   SYNTAX       DisplayString
   MAX-ACCESS   read-only
   STATUS       current
   DESCRIPTION
       ""
   ::= { gs2326SystemInformation 31 }

gs2326IPv6Prefix OBJECT-TYPE
   SYNTAX       DisplayString
   MAX-ACCESS   read-only
   STATUS       current
   DESCRIPTION
       ""
   ::= { gs2326SystemInformation 32 }
   
gs2326IPv6Gateway OBJECT-TYPE
   SYNTAX       DisplayString
   MAX-ACCESS   read-only
   STATUS       current
   DESCRIPTION
       ""
   ::= { gs2326SystemInformation 33 }

gs2326LargestFreeMemBlock OBJECT-TYPE
   SYNTAX       Integer32
   MAX-ACCESS   read-only
   STATUS       current
   DESCRIPTION
       "Largest free memory block in Kb"
   ::= { gs2326SystemInformation 1500 }   
   
gs2326MemFree  OBJECT-TYPE
   SYNTAX       Integer32
   MAX-ACCESS   read-only
   STATUS       current
   DESCRIPTION
       "Free memory in Kb"
   ::= { gs2326SystemInformation 1501 }

gs2326SystemTime                                            OBJECT IDENTIFIER ::= { gs2326System 2 }

gs2326SystemTimeManual                                      OBJECT IDENTIFIER ::= { gs2326SystemTime 1 }

gs2326SystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2326SystemTimeManual 1 }
   
gs2326SystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2326SystemTimeManual 2 }

gs2326SystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2326SystemTimeManual 3 }
   
gs2326SystemTimeManualDaylightSavings OBJECT-TYPE
   SYNTAX       INTEGER { disable(0), enable(1) }
   MAX-ACCESS   read-write
   STATUS       current
   DESCRIPTION
       "default: 0,
        0 : Disable,
        1 : Enable."
   ::= { gs2326SystemTimeManual 4 }
   
gs2326SystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2326SystemTimeManual 5 }
   
gs2326SystemTimeManualDaylightSavingsType OBJECT-TYPE
   SYNTAX       INTEGER { byDates(0), recurring(1) }
   MAX-ACCESS   read-write
   STATUS       current
   DESCRIPTION
       "default: 0,
        0 : By dates,
        1 : Recurring."
   ::= { gs2326SystemTimeManual 6 }
   
gs2326SystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2326SystemTimeManual 7 }
   
gs2326SystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2326SystemTimeManual 8 }

gs2326SystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2326SystemTimeManual 9 }

gs2326SystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2326SystemTimeManual 10 }
   
gs2326SystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2326SystemTimeManual 11 }

gs2326SystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2326SystemTimeManual 12 }
   
gs2326SystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2326SystemTimeManual 13 }

gs2326SystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2326SystemTimeManual 14 }
   
gs2326SystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2326SystemTimeManual 15 }

gs2326SystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2326SystemTimeManual 16 }

gs2326SystemTimeNTP                                     OBJECT IDENTIFIER ::= { gs2326SystemTime 2 }

gs2326SystemTimeNTPTable OBJECT-TYPE
   SYNTAX      SEQUENCE OF GS2326SystemTimeNTPEntry
   MAX-ACCESS  not-accessible
   STATUS      current
   DESCRIPTION
       " "
   ::= { gs2326SystemTimeNTP 1 }

gs2326SystemTimeNTPEntry OBJECT-TYPE
   SYNTAX      GS2326SystemTimeNTPEntry
   MAX-ACCESS  not-accessible
   STATUS      current
   DESCRIPTION
       ""
   INDEX    { gs2326SystemTimeNTPIndex  }
   ::= { gs2326SystemTimeNTPTable 1 }

GS2326SystemTimeNTPEntry ::= SEQUENCE {
   gs2326SystemTimeNTPIndex             Integer32,
   gs2326SystemTimeNTPServerIPType      INTEGER,
   gs2326SystemTimeNTPServer            DisplayString,
   gs2326SystemTimeNTPCurrentMode       INTEGER
}

gs2326SystemTimeNTPIndex OBJECT-TYPE
   SYNTAX      Integer32(1..5)
   MAX-ACCESS  not-accessible
   STATUS      current
   DESCRIPTION
       " The index of the ntp entry. "
   ::= { gs2326SystemTimeNTPEntry 1 }

gs2326SystemTimeNTPServerIPType OBJECT-TYPE
   SYNTAX       INTEGER { ipv4(0), ipv6(1) }
   MAX-ACCESS   read-write
   STATUS       current
   DESCRIPTION
       "Default: 0,
        0 : IPv4,
        1 : IPv6."
   ::= { gs2326SystemTimeNTPEntry 2 }

gs2326SystemTimeNTPServer OBJECT-TYPE
   SYNTAX       DisplayString
   MAX-ACCESS   read-write
   STATUS       current
   DESCRIPTION
       "Get/Set the NTP Time Server1. You can use the IP address or domain name."
   ::= { gs2326SystemTimeNTPEntry 3 }

gs2326SystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2326SystemTimeNTPEntry 4 }

gs2326SystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2326SystemTimeNTP 2 }
   
gs2326SystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2326SystemTimeNTP 3 }
    

gs2326SystemAccount                                         OBJECT IDENTIFIER ::= { gs2326System 3 }

gs2326SystemAccountUsers                                    OBJECT IDENTIFIER ::= { gs2326SystemAccount 1 }

gs2326SystemAccountUserCreate OBJECT-TYPE
   SYNTAX       INTEGER { none(0), create(1) }
   MAX-ACCESS   read-write
   STATUS       current
   DESCRIPTION
       "default: 0
        0 : None  (read only)
        1 : Create a user account"
   ::= { gs2326SystemAccountUsers 1 }

gs2326SystemAccountUsersTable OBJECT-TYPE
   SYNTAX      SEQUENCE OF GS2326SystemAccountUsersEntry
   MAX-ACCESS  not-accessible
   STATUS      current
   DESCRIPTION
       " "
   ::= { gs2326SystemAccountUsers 2 }

gs2326SystemAccountUsersEntry OBJECT-TYPE
   SYNTAX      GS2326SystemAccountUsersEntry
   MAX-ACCESS  not-accessible
   STATUS      current
   DESCRIPTION
       ""
   INDEX    { gs2326UserIndex  }
   ::= { gs2326SystemAccountUsersTable 1 }


GS2326SystemAccountUsersEntry ::= SEQUENCE {
   gs2326UserIndex              Integer32 ,
   gs2326UserName               DisplayString,
   gs2326Password               DisplayString,
   gs2326UserPrivilegeLevel     Integer32 ,
   gs2326AccountUserRowStatus   INTEGER
}


gs2326UserIndex OBJECT-TYPE
   SYNTAX      Integer32 (1..20)
   MAX-ACCESS  not-accessible
   STATUS      current
   DESCRIPTION
       " "
   ::= { gs2326SystemAccountUsersEntry 1 }

gs2326UserName OBJECT-TYPE
   SYNTAX      DisplayString (SIZE (1..32))
   MAX-ACCESS  read-write
   STATUS      current
   DESCRIPTION
       "Please use a combination of letters, numbers and underscores"
   ::= { gs2326SystemAccountUsersEntry 2 }

gs2326Password OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2326SystemAccountUsersEntry 3 }

gs2326UserPrivilegeLevel OBJECT-TYPE
   SYNTAX      Integer32 (1..15)
   MAX-ACCESS  read-write
   STATUS      current
   DESCRIPTION
       "default:1 
        User privilege level range : 1 - 15"
   ::= { gs2326SystemAccountUsersEntry 4 }

gs2326AccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2326SystemAccountUsersEntry 5 }

gs2326SystemAccountUsersSuperUserPassword OBJECT-TYPE
   SYNTAX      OCTET STRING (SIZE (0..32))
   MAX-ACCESS read-write
   STATUS      current
   DESCRIPTION
        "Super-User Password"
   ::= { gs2326SystemAccountUsers 1500 }

gs2326SystemAccountEnforcePasswordRules OBJECT-TYPE
   SYNTAX       INTEGER { yes(0), no(1) }
   MAX-ACCESS   read-write
   STATUS       current
   DESCRIPTION
       "default: 0
        0 : Do not enforce rules
        1 : enforce rules"
   ::= { gs2326SystemAccountUsers 1501 }

gs2326SystemAccountPrivilegeLevel                           OBJECT IDENTIFIER ::= { gs2326SystemAccount 2 }

gs2326AccountPrivilegeLevel OBJECT-TYPE
   SYNTAX      Integer32 (1..15)
   MAX-ACCESS  read-write
   STATUS      current
   DESCRIPTION
       "Default:15, Range : 1-15. "
   ::= { gs2326SystemAccountPrivilegeLevel 1 }

gs2326AggregationPrivilegeLevel OBJECT-TYPE
   SYNTAX      Integer32 (1..15)
   MAX-ACCESS  read-write
   STATUS      current
   DESCRIPTION
       "Default:15, Range : 1-15. "
   ::= { gs2326SystemAccountPrivilegeLevel 2 }

gs2326DiagnosticsPrivilegeLevel OBJECT-TYPE
   SYNTAX      Integer32 (1..15)
   MAX-ACCESS  read-write
   STATUS      current
   DESCRIPTION
       "Default:15, Range : 1-15. "
   ::= { gs2326SystemAccountPrivilegeLevel 3 }

gs2326EEEPrivilegeLevel OBJECT-TYPE
   SYNTAX      Integer32 (1..15)
   MAX-ACCESS  read-write
   STATUS      current
   DESCRIPTION
       "Default:15, Range : 1-15. "
   ::= { gs2326SystemAccountPrivilegeLevel 4 }

gs2326EasyportPrivilegeLevel OBJECT-TYPE
   SYNTAX      Integer32 (1..15)
   MAX-ACCESS  read-write
   STATUS      current
   DESCRIPTION
       "Default:15, Range : 1-15. "
   ::= { gs2326SystemAccountPrivilegeLevel 9 }

gs2326GARPPrivilegeLevel OBJECT-TYPE
   SYNTAX      Integer32 (1..15)
   MAX-ACCESS  read-write
   STATUS      current
   DESCRIPTION
       "Default:15, Range : 1-15. "
   ::= { gs2326SystemAccountPrivilegeLevel 10 }

gs2326GVRPPrivilegeLevel OBJECT-TYPE
   SYNTAX      Integer32 (1..15)
   MAX-ACCESS  read-write
   STATUS      current
   DESCRIPTION
       "Default:15, Range : 1-15. "
   ::= { gs2326SystemAccountPrivilegeLevel 11 }

gs2326IPPrivilegeLevel OBJECT-TYPE
   SYNTAX      Integer32 (1..15)
   MAX-ACCESS  read-write
   STATUS      current
   DESCRIPTION
       "Default:15, Range : 1-15. "
   ::= { gs2326SystemAccountPrivilegeLevel 12 }

gs2326IPMCSnoopingPrivilegeLevel OBJECT-TYPE
   SYNTAX      Integer32 (1..15)
   MAX-ACCESS  read-write
   STATUS      current
   DESCRIPTION
       "Default:15, Range : 1-15. "
   ::= { gs2326SystemAccountPrivilegeLevel 13 }

gs2326LACPPrivilegeLevel OBJECT-TYPE
   SYNTAX      Integer32 (1..15)
   MAX-ACCESS  read-write
   STATUS      current
   DESCRIPTION
       "Default:15, Range : 1-15. "
   ::= { gs2326SystemAccountPrivilegeLevel 14 }

gs2326LLDPPrivilegeLevel OBJECT-TYPE
   SYNTAX      Integer32 (1..15)
   MAX-ACCESS  read-write
   STATUS      current
   DESCRIPTION
       "Default:15, Range : 1-15. "
   ::= { gs2326SystemAccountPrivilegeLevel 15 }

gs2326LLDPMEDPrivilegeLevel OBJECT-TYPE
   SYNTAX      Integer32 (1..15)
   MAX-ACCESS  read-write
   STATUS      current
   DESCRIPTION
       "Default:15, Range : 1-15. "
   ::= { gs2326SystemAccountPrivilegeLevel 16 }

gs2326LoopProtectPrivilegeLevel OBJECT-TYPE
   SYNTAX      Integer32 (1..15)
   MAX-ACCESS  read-write
   STATUS      current
   DESCRIPTION
       "Default:15, Range : 1-15. "
   ::= { gs2326SystemAccountPrivilegeLevel 17 }

gs2326MACTablePrivilegeLevel OBJECT-TYPE
   SYNTAX      Integer32 (1..15)
   MAX-ACCESS  read-write
   STATUS      current
   DESCRIPTION
       "Default:15, Range : 1-15. "
   ::= { gs2326SystemAccountPrivilegeLevel 18 }

gs2326MVRPrivilegeLevel OBJECT-TYPE
   SYNTAX      Integer32 (1..15)
   MAX-ACCESS  read-write
   STATUS      current
   DESCRIPTION
       "Default:15, Range : 1-15. "
   ::= { gs2326SystemAccountPrivilegeLevel 22 }

gs2326MaintenancePrivilegeLevel OBJECT-TYPE
   SYNTAX      Integer32 (1..15)
   MAX-ACCESS  read-write
   STATUS      current
   DESCRIPTION
       "Default:15, Range : 1-15. "
   ::= { gs2326SystemAccountPrivilegeLevel 24 }

gs2326MirroringPrivilegeLevel OBJECT-TYPE
   SYNTAX      Integer32 (1..15)
   MAX-ACCESS  read-write
   STATUS      current
   DESCRIPTION
       "Default:15, Range : 1-15. "
   ::= { gs2326SystemAccountPrivilegeLevel 25 }

gs2326PortsPrivilegeLevel OBJECT-TYPE
   SYNTAX      Integer32 (1..15)
   MAX-ACCESS  read-write
   STATUS      current
   DESCRIPTION
       "Default:15, Range : 1-15. "
   ::= { gs2326SystemAccountPrivilegeLevel 27 }

gs2326PrivateVLANsPrivilegeLevel OBJECT-TYPE
   SYNTAX      Integer32 (1..15)
   MAX-ACCESS  read-write
   STATUS      current
   DESCRIPTION
       "Default:15, Range : 1-15. "
   ::= { gs2326SystemAccountPrivilegeLevel 28 }

gs2326QoSPrivilegeLevel OBJECT-TYPE
   SYNTAX      Integer32 (1..15)
   MAX-ACCESS  read-write
   STATUS      current
   DESCRIPTION
       "Default:15, Range : 1-15. "
   ::= { gs2326SystemAccountPrivilegeLevel 29 }

gs2326SFlowPrivilegeLevel OBJECT-TYPE
   SYNTAX      Integer32 (1..15)
   MAX-ACCESS  read-write
   STATUS      current
   DESCRIPTION
       "Default:15, Range : 1-15. "
   ::= { gs2326SystemAccountPrivilegeLevel 30 }

gs2326SMTPPrivilegeLevel OBJECT-TYPE
   SYNTAX      Integer32 (1..15)
   MAX-ACCESS  read-write
   STATUS      current
   DESCRIPTION
       "Default:15, Range : 1-15. "
   ::= { gs2326SystemAccountPrivilegeLevel 31 }

gs2326SNMPPrivilegeLevel OBJECT-TYPE
   SYNTAX      Integer32 (1..15)
   MAX-ACCESS  read-write
   STATUS      current
   DESCRIPTION
       "Default:15, Range : 1-15. "
   ::= { gs2326SystemAccountPrivilegeLevel 32 }

gs2326SecurityPrivilegeLevel OBJECT-TYPE
   SYNTAX      Integer32 (1..15)
   MAX-ACCESS  read-write
   STATUS      current
   DESCRIPTION
       "Default:15, Range : 1-15. "
   ::= { gs2326SystemAccountPrivilegeLevel 33 }

gs2326SingleIPPrivilegeLevel OBJECT-TYPE
   SYNTAX      Integer32 (1..15)
   MAX-ACCESS  read-write
   STATUS      current
   DESCRIPTION
       "Default:15, Range : 1-15. "
   ::= { gs2326SystemAccountPrivilegeLevel 34 }

gs2326SpanningTreePrivilegeLevel OBJECT-TYPE
   SYNTAX      Integer32 (1..15)
   MAX-ACCESS  read-write
   STATUS      current
   DESCRIPTION
       "Default:15, Range : 1-15. "
   ::= { gs2326SystemAccountPrivilegeLevel 35 }

gs2326SystemPrivilegeLevel OBJECT-TYPE
   SYNTAX      Integer32 (1..15)
   MAX-ACCESS  read-write
   STATUS      current
   DESCRIPTION
       "Default:15, Range : 1-15. "
   ::= { gs2326SystemAccountPrivilegeLevel 36 }

gs2326TrapEventPrivilegeLevel OBJECT-TYPE
   SYNTAX      Integer32 (1..15)
   MAX-ACCESS  read-write
   STATUS      current
   DESCRIPTION
       "Default:15, Range : 1-15. "
   ::= { gs2326SystemAccountPrivilegeLevel 37 }

gs2326UPnPPrivilegeLevel OBJECT-TYPE
   SYNTAX      Integer32 (1..15)
   MAX-ACCESS  read-write
   STATUS      current
   DESCRIPTION
       "Default:15, Range : 1-15. "
   ::= { gs2326SystemAccountPrivilegeLevel 38 }

gs2326VCLPrivilegeLevel OBJECT-TYPE
   SYNTAX      Integer32 (1..15)
   MAX-ACCESS  read-write
   STATUS      current
   DESCRIPTION
       "Default:15, Range : 1-15. "
   ::= { gs2326SystemAccountPrivilegeLevel 39 }

gs2326VLANsPrivilegeLevel OBJECT-TYPE
   SYNTAX      Integer32 (1..15)
   MAX-ACCESS  read-write
   STATUS      current
   DESCRIPTION
       "Default:15, Range : 1-15. "
   ::= { gs2326SystemAccountPrivilegeLevel 41 }

gs2326VoiceVLANPrivilegeLevel OBJECT-TYPE
   SYNTAX      Integer32 (1..15)
   MAX-ACCESS  read-write
   STATUS      current
   DESCRIPTION
       "Default:15, Range : 1-15. "
   ::= { gs2326SystemAccountPrivilegeLevel 42 }

gs2326IP                                                    OBJECT IDENTIFIER ::= { gs2326System 4 }

gs2326IPv4                                                  OBJECT IDENTIFIER ::= { gs2326IP 1 }

gs2326IPv4Configured                                                  OBJECT IDENTIFIER ::= { gs2326IPv4 1 }

gs2326Ipv4DHCPClient OBJECT-TYPE
   SYNTAX      INTEGER { disable(0), enable(1) }
   MAX-ACCESS  read-write
   STATUS      current
   DESCRIPTION
       "default:0
       0: disable
       1: enable"
   ::= { gs2326IPv4Configured 1 }

gs2326IPv4Address OBJECT-TYPE
   SYNTAX      IpAddress
   MAX-ACCESS  read-write
   STATUS      current
   DESCRIPTION
       ""
   ::= { gs2326IPv4Configured 2 }

gs2326IPv4Mask OBJECT-TYPE
   SYNTAX      IpAddress
   MAX-ACCESS  read-write
   STATUS      current
   DESCRIPTION
       ""
   ::= { gs2326IPv4Configured 3 }

gs2326IPv4Gateway OBJECT-TYPE
   SYNTAX      IpAddress
   MAX-ACCESS  read-write
   STATUS      current
   DESCRIPTION
       ""
   ::= { gs2326IPv4Configured 4 }

gs2326IPv4VLANId OBJECT-TYPE
   SYNTAX      Integer32(1..4094)
   MAX-ACCESS  read-write
   STATUS      current
   DESCRIPTION
       "default:1"
   ::= { gs2326IPv4Configured 5 }

gs2326IPv4DNSServer OBJECT-TYPE
   SYNTAX      IpAddress
   MAX-ACCESS  read-write
   STATUS      current
   DESCRIPTION
       ""
   ::= { gs2326IPv4Configured 6 }

gs2326IPv4DNSProxy OBJECT-TYPE
   SYNTAX      INTEGER { disable(0), enable(1) }
   MAX-ACCESS  read-write
   STATUS      current
   DESCRIPTION
       "0:disable, 1:enable "
   ::= { gs2326IPv4Configured 7 }

gs2326IPv4Current                                                  OBJECT IDENTIFIER ::= { gs2326IPv4 2 }

gs2326Ipv4CurrentDHCPClient OBJECT-TYPE
   SYNTAX      INTEGER { none(0), renew(1) }
   MAX-ACCESS  read-write
   STATUS      current
   DESCRIPTION
       "default:0
       0: none (for read)
       1: renew"
   ::= { gs2326IPv4Current 1 }

gs2326IPv4CurrentAddress OBJECT-TYPE
   SYNTAX      IpAddress
   MAX-ACCESS  read-only
   STATUS      current
   DESCRIPTION
       ""
   ::= { gs2326IPv4Current 2 }

gs2326IPv4CurrentMask OBJECT-TYPE
   SYNTAX      IpAddress
   MAX-ACCESS  read-only
   STATUS      current
   DESCRIPTION
       ""
   ::= { gs2326IPv4Current 3 }

gs2326IPv4CurrentGateway OBJECT-TYPE
   SYNTAX      IpAddress
   MAX-ACCESS  read-only
   STATUS      current
   DESCRIPTION
       ""
   ::= { gs2326IPv4Current 4 }

gs2326IPv4CurrentVLANId OBJECT-TYPE
   SYNTAX      Integer32(1..4094)
   MAX-ACCESS  read-only
   STATUS      current
   DESCRIPTION
       "default:1"
   ::= { gs2326IPv4Current 5 }

gs2326IPv4CurrentDNSServer OBJECT-TYPE
   SYNTAX      IpAddress
   MAX-ACCESS  read-only
   STATUS      current
   DESCRIPTION
       ""
   ::= { gs2326IPv4Current 6 }


gs2326IPv6                                                  OBJECT IDENTIFIER ::= { gs2326IP 2 }

gs2326IPv6Configured                                                  OBJECT IDENTIFIER ::= { gs2326IPv6 1 }

gs2326Ipv6AutoConfiguration OBJECT-TYPE
   SYNTAX      INTEGER { disable(0), enable(1) }
   MAX-ACCESS  read-write
   STATUS      current
   DESCRIPTION
       "default:0
       0: disable
       1: enable"
   ::= { gs2326IPv6Configured 1 }

gs2326Ipv6Address OBJECT-TYPE
   SYNTAX      DisplayString (SIZE (0..30))
   MAX-ACCESS  read-write
   STATUS      current
   DESCRIPTION
       ""
   ::= { gs2326IPv6Configured 2 }

gs2326Ipv6Prefix OBJECT-TYPE
   SYNTAX      Integer32 (1..128)
   MAX-ACCESS  read-write
   STATUS      current
   DESCRIPTION
       "default: 96"
   ::= { gs2326IPv6Configured 3 }

gs2326Ipv6Gateway OBJECT-TYPE
   SYNTAX      DisplayString (SIZE (0..30))
   MAX-ACCESS  read-write
   STATUS      current
   DESCRIPTION
       " "
   ::= { gs2326IPv6Configured 4 }

gs2326IPv6Current                                                  OBJECT IDENTIFIER ::= { gs2326IPv6 2 }

gs2326Ipv6CurrentAutoConfiguration OBJECT-TYPE
   SYNTAX      INTEGER { disable(0), enable(1) }
   MAX-ACCESS  read-only
   STATUS      current
   DESCRIPTION
       "default:0
       0: disable
       1: enable"
   ::= { gs2326IPv6Current 1 }

gs2326Ipv6CurrentAddress OBJECT-TYPE
   SYNTAX      DisplayString (SIZE (0..30))
   MAX-ACCESS  read-only
   STATUS      current
   DESCRIPTION
       ""
   ::= { gs2326IPv6Current 2 }


gs2326Ipv6CurrentLinkLocalAddress OBJECT-TYPE
   SYNTAX      DisplayString(SIZE (0..30))
   MAX-ACCESS  read-only
   STATUS      current
   DESCRIPTION
       ""
   ::= { gs2326IPv6Current 3 }


gs2326Ipv6CurrentPrefix OBJECT-TYPE
   SYNTAX      DisplayString(SIZE (0..64))
   MAX-ACCESS  read-only
   STATUS      current
   DESCRIPTION
       ""
   ::= { gs2326IPv6Current 4 }

gs2326Ipv6CurrentGateway OBJECT-TYPE
   SYNTAX      DisplayString (SIZE (0..30))
   MAX-ACCESS  read-only
   STATUS      current
   DESCRIPTION
       " "
   ::= { gs2326IPv6Current 5 }

gs2326Syslog                                                OBJECT IDENTIFIER ::= { gs2326System 5 }

gs2326SyslogConf                                            OBJECT IDENTIFIER ::= { gs2326Syslog 1 }

gs2326ServerMode OBJECT-TYPE
   SYNTAX      INTEGER { disable(0), enable(1) }
   MAX-ACCESS  read-write
   STATUS      current
   DESCRIPTION
       "default: 0
       0: disable
       1: enable "
   ::= { gs2326SyslogConf 1 }

gs2326ServerAddress1 OBJECT-TYPE
   SYNTAX      IpAddress
   MAX-ACCESS  read-write
   STATUS      current
   DESCRIPTION
       " "
   ::= { gs2326SyslogConf 2 }

gs2326ServerAddress2 OBJECT-TYPE
   SYNTAX      IpAddress
   MAX-ACCESS  read-write
   STATUS      current
   DESCRIPTION
       " "
   ::= { gs2326SyslogConf 3 }

gs2326SyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2326SyslogConf 4 }

gs2326SyslogDetailedInfo                                    OBJECT IDENTIFIER ::= { gs2326Syslog 2 }

gs2326SyslogDetailedInfoClear OBJECT-TYPE
   SYNTAX      INTEGER { none(0), clear(1) }
   MAX-ACCESS  read-write
   STATUS      current
   DESCRIPTION
      "default: 0
       0 : None  (read only)
       1 : Clear Syslog"
   ::= { gs2326SyslogDetailedInfo 1 }

gs2326SyslogDetailedInfoTable OBJECT-TYPE
  SYNTAX      SEQUENCE OF GS2326SyslogDetailedInfoEntry
  MAX-ACCESS  not-accessible
  STATUS      current
  DESCRIPTION
           " "
       ::= { gs2326SyslogDetailedInfo 2 }

gs2326SyslogDetailedInfoEntry OBJECT-TYPE
   SYNTAX      GS2326SyslogDetailedInfoEntry
   MAX-ACCESS  not-accessible
   STATUS      current
   DESCRIPTION
           ""
   INDEX    { gs2326SyslogDetailedInfoIndex  }
   ::= { gs2326SyslogDetailedInfoTable 1 }

GS2326SyslogDetailedInfoEntry ::= SEQUENCE {
   gs2326SyslogDetailedInfoIndex       Integer32,
   gs2326SyslogDetailedInfoLevel       DisplayString,
   gs2326SyslogDetailedInfoTime        DisplayString,
   gs2326SyslogDetailedInfoMessage     DisplayString
}

gs2326SyslogDetailedInfoIndex OBJECT-TYPE
   SYNTAX      Integer32(1..1024)
   MAX-ACCESS  not-accessible
   STATUS      current
   DESCRIPTION
       " "
   ::= { gs2326SyslogDetailedInfoEntry 1 }
   
gs2326SyslogDetailedInfoLevel OBJECT-TYPE
   SYNTAX      DisplayString
   MAX-ACCESS  read-only
   STATUS      current
   DESCRIPTION
       " "
   ::= { gs2326SyslogDetailedInfoEntry 2 }

gs2326SyslogDetailedInfoTime OBJECT-TYPE
   SYNTAX      DisplayString(SIZE (0..20))
   MAX-ACCESS  read-only
   STATUS      current
   DESCRIPTION
       " "
   ::= { gs2326SyslogDetailedInfoEntry 3 }

gs2326SyslogDetailedInfoMessage OBJECT-TYPE
   SYNTAX      DisplayString
   MAX-ACCESS  read-only
   STATUS      current
   DESCRIPTION
       " "
   ::= { gs2326SyslogDetailedInfoEntry 4 }


gs2326Snmp                                                OBJECT IDENTIFIER ::= { gs2326System 6 }

gs2326SnmpConf                                            OBJECT IDENTIFIER ::= { gs2326Snmp 1 }

gs2326GetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2326SnmpConf 1 }

gs2326GetCommunity OBJECT-TYPE
   SYNTAX       DisplayString
   MAX-ACCESS   read-write
   STATUS       current
   DESCRIPTION
       "Get/Set the get-community of the SNMP."
   ::= { gs2326SnmpConf 2 }

gs2326SetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2326SnmpConf 3 }

gs2326SetCommunity OBJECT-TYPE
   SYNTAX       DisplayString
   MAX-ACCESS   read-write
   STATUS       current
   DESCRIPTION
       "Get/Set the set-community of the SNMP."
   ::= { gs2326SnmpConf 4 }

gs2326GetCommunityConfTable OBJECT-TYPE
   SYNTAX      SEQUENCE OF GS2326GetCommunityConfEntry
   MAX-ACCESS  not-accessible
   STATUS      current
   DESCRIPTION
       " Show get-community of the SNMP. "
   ::= { gs2326SnmpConf 5 }

gs2326GetCommunityConfEntry OBJECT-TYPE
   SYNTAX      GS2326GetCommunityConfEntry
   MAX-ACCESS  not-accessible
   STATUS      current
   DESCRIPTION
       ""
   INDEX    { gs2326CommunityConfIndex  }
   ::= { gs2326GetCommunityConfTable 1 }

GS2326GetCommunityConfEntry ::= SEQUENCE {
   gs2326CommunityConfIndex				Integer32,
   gs2326CommunityConfGetCommunity			DisplayString
}

gs2326CommunityConfIndex OBJECT-TYPE
   SYNTAX      Integer32(1..4095)
   MAX-ACCESS  not-accessible
   STATUS      current
   DESCRIPTION
       " index, range : 1 - 5. "
   ::= { gs2326GetCommunityConfEntry 1 }
   
gs2326CommunityConfGetCommunity OBJECT-TYPE
   SYNTAX      DisplayString
   MAX-ACCESS  read-write
   STATUS      current
   DESCRIPTION
       " Get/Set the get-community of the SNMP."
   ::= { gs2326GetCommunityConfEntry 2 }

gs2326TrapHostConfTable OBJECT-TYPE
   SYNTAX      SEQUENCE OF GS2326TrapHostConfEntry
   MAX-ACCESS  not-accessible
   STATUS      current
   DESCRIPTION
       "A list of trap host entry. The numbers of entries are given by the value of gs2326TrapHostConfNumber."
   ::= { gs2326SnmpConf 6 }
   
gs2326TrapHostConfEntry OBJECT-TYPE
   SYNTAX      GS2326TrapHostConfEntry
   MAX-ACCESS  not-accessible
   STATUS      current
   DESCRIPTION
       "This is the entry information for trap host."
   INDEX    { gs2326TrapHostConfIndex  }
   ::= { gs2326TrapHostConfTable 1 }

GS2326TrapHostConfEntry ::= SEQUENCE {
    gs2326TrapHostConfIndex             Integer32,
    gs2326TrapHostConfVersion           INTEGER,
    gs2326TrapHostConfIPType            INTEGER,
    gs2326TrapHostConfIP                DisplayString,
    gs2326TrapHostConfPort              Integer32,
    gs2326TrapHostConfCommunity         DisplayString,
    gs2326TrapHostConfSeverityLevel     INTEGER,
    gs2326TrapHostConfSecurityLevel     INTEGER,
    gs2326TrapHostConfAuthPtc           INTEGER,
    gs2326TrapHostConfAuthPassword      DisplayString,
    gs2326TrapHostConfPrivPtc           INTEGER,
    gs2326TrapHostConfPrivPassword      DisplayString,
    gs2326TrapHostConfCurrentMode       INTEGER
}
   
gs2326TrapHostConfIndex OBJECT-TYPE
   SYNTAX      Integer32(1..6)
   MAX-ACCESS  not-accessible
   STATUS      current
   DESCRIPTION
       " The index of the trap host entry. "
   ::= { gs2326TrapHostConfEntry 1 }

gs2326TrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2326TrapHostConfEntry 2 }

gs2326TrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2326TrapHostConfEntry 3 }

gs2326TrapHostConfIP OBJECT-TYPE
   SYNTAX       DisplayString
   MAX-ACCESS   read-write
   STATUS       current
   DESCRIPTION
       "This is the IP of the trap host."
   ::= { gs2326TrapHostConfEntry 4 }

gs2326TrapHostConfPort OBJECT-TYPE
   SYNTAX       Integer32(1..65535)
   MAX-ACCESS   read-write
   STATUS       current
   DESCRIPTION
       "This is the receiving-port number of the trap host.
        range : 1 - 65535."
   ::= { gs2326TrapHostConfEntry 5 }

gs2326TrapHostConfCommunity OBJECT-TYPE
   SYNTAX       DisplayString (SIZE (1..32))
   MAX-ACCESS   read-write
   STATUS       current
   DESCRIPTION
       "The community/security name for the trap PDU."
   ::= { gs2326TrapHostConfEntry 6 }

gs2326TrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2326TrapHostConfEntry 7 }

gs2326TrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2326TrapHostConfEntry 8 }

gs2326TrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2326TrapHostConfEntry 9 }

gs2326TrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2326TrapHostConfEntry 10 }

gs2326TrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2326TrapHostConfEntry 11 }

gs2326TrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2326TrapHostConfEntry 12 }

gs2326TrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2326TrapHostConfEntry 13 }


gs2326SnmpSystem                                          OBJECT IDENTIFIER ::= { gs2326Snmp 2 }

gs2326SnmpState OBJECT-TYPE
   SYNTAX       INTEGER { disable(0), enable(1) }
   MAX-ACCESS   read-write
   STATUS       current
   DESCRIPTION
       "Get/Set the state of the SNMP.
        default : 1, 0: disable, 1: enable. "
   ::= { gs2326SnmpSystem 1 }

gs2326SnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2326SnmpSystem 2 }

gs2326SnmpCommunities                                          OBJECT IDENTIFIER ::= { gs2326Snmp 3 }

gs2326SnmpCommunitiesCreate OBJECT-TYPE
   SYNTAX       INTEGER { none(0), create(1) }
   MAX-ACCESS   read-write
   STATUS       current
   DESCRIPTION
       "default: 0
        0 : None  (read only)
        1 : Create entry"
   ::= { gs2326SnmpCommunities 1 }

gs2326SnmpCommunitiesTable OBJECT-TYPE
   SYNTAX      SEQUENCE OF GS2326SnmpCommunitiesEntry
   MAX-ACCESS  not-accessible
   STATUS      current
   DESCRIPTION
       " Create SNMPv1/v2 Communities entry."
   ::= { gs2326SnmpCommunities 2 }

gs2326SnmpCommunitiesEntry OBJECT-TYPE
   SYNTAX      GS2326SnmpCommunitiesEntry
   MAX-ACCESS  not-accessible
   STATUS      current
   DESCRIPTION
       ""
   INDEX    { gs2326SnmpCommunitiesIndex  }
   ::= { gs2326SnmpCommunitiesTable 1 }

GS2326SnmpCommunitiesEntry ::= SEQUENCE {
   gs2326SnmpCommunitiesIndex          Integer32,
   gs2326SnmpCommunitiesCommunity      DisplayString,
   gs2326SnmpCommunitiesUserName       DisplayString,
   gs2326SnmpCommunitiesSourceIP       IpAddress,
   gs2326SnmpCommunitiesSourceMask     IpAddress,
   gs2326SnmpCommunitiesRowStatus      INTEGER
}

gs2326SnmpCommunitiesIndex OBJECT-TYPE
   SYNTAX      Integer32(1..4)
   MAX-ACCESS  not-accessible
   STATUS      current
   DESCRIPTION
       " "
   ::= { gs2326SnmpCommunitiesEntry 1 }

gs2326SnmpCommunitiesCommunity OBJECT-TYPE
   SYNTAX      DisplayString (SIZE (1..32))
   MAX-ACCESS  read-write
   STATUS      current
   DESCRIPTION
       "Up to 32 characters describing Community."
   ::= { gs2326SnmpCommunitiesEntry 2 }

gs2326SnmpCommunitiesUserName OBJECT-TYPE
   SYNTAX      DisplayString (SIZE (1..32))
   MAX-ACCESS  read-write
   STATUS      current
   DESCRIPTION
       " Up to 32 characters describing User Name. "
   ::= { gs2326SnmpCommunitiesEntry 3 }

gs2326SnmpCommunitiesSourceIP OBJECT-TYPE
   SYNTAX      IpAddress
   MAX-ACCESS  read-write
   STATUS      current
   DESCRIPTION
       " SNMP access source ip. "
   ::= { gs2326SnmpCommunitiesEntry 4 }

gs2326SnmpCommunitiesSourceMask OBJECT-TYPE
   SYNTAX      IpAddress
   MAX-ACCESS  read-write
   STATUS      current
   DESCRIPTION
       " SNMP access source address mask. "
   ::= { gs2326SnmpCommunitiesEntry 5 }

gs2326SnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2326SnmpCommunitiesEntry 6 }


gs2326SnmpUsers                                          OBJECT IDENTIFIER ::= { gs2326Snmp 4 }

gs2326SnmpUsersCreate OBJECT-TYPE
   SYNTAX       INTEGER { none(0), create(1) }
   MAX-ACCESS   read-write
   STATUS       current
   DESCRIPTION
       "default: 0
        0 : None  (read only)
        1 : Create entry"
   ::= { gs2326SnmpUsers 1 }

gs2326SnmpUsersTable OBJECT-TYPE
   SYNTAX      SEQUENCE OF GS2326SnmpUsersEntry
   MAX-ACCESS  not-accessible
   STATUS      current
   DESCRIPTION
       " Create SNMPv3 users entry."
   ::= { gs2326SnmpUsers 2 }

gs2326SnmpUsersEntry OBJECT-TYPE
   SYNTAX      GS2326SnmpUsersEntry
   MAX-ACCESS  not-accessible
   STATUS      current
   DESCRIPTION
       ""
   INDEX    { gs2326SnmpUsersIndex  }
   ::= { gs2326SnmpUsersTable 1 }

GS2326SnmpUsersEntry ::= SEQUENCE {
   gs2326SnmpUsersIndex                    Integer32,
   gs2326SnmpUsersUserName                 DisplayString,
   gs2326SnmpUsersSecurityLevel            INTEGER,
   gs2326SnmpUsersAuthenticationProtocol   INTEGER,
   gs2326SnmpUsersAuthenticationPassword   DisplayString,
   gs2326SnmpUsersPrivacyProtocol          INTEGER,
   gs2326SnmpUsersPrivacyPassword          DisplayString,
   gs2326SnmpUsersRowStatus                INTEGER
}

gs2326SnmpUsersIndex OBJECT-TYPE
   SYNTAX      Integer32(1..10)
   MAX-ACCESS  not-accessible
   STATUS      current
   DESCRIPTION
       " "
   ::= { gs2326SnmpUsersEntry 1 }

gs2326SnmpUsersUserName OBJECT-TYPE
   SYNTAX      DisplayString (SIZE (1..32))
   MAX-ACCESS  read-write
   STATUS      current
   DESCRIPTION
       "Up to 32 characters describing User Name."
   ::= { gs2326SnmpUsersEntry 2 }

gs2326SnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy. 
         3: Authentication and privacy. "
   ::= { gs2326SnmpUsersEntry 3 }

gs2326SnmpUsersAuthenticationProtocol OBJECT-TYPE
   SYNTAX      INTEGER { none(0), md5(1), sha(2) }
   MAX-ACCESS  read-write
   STATUS      current
   DESCRIPTION
       " 0: None.
         1: MD5.
         2: SHA "
   ::= { gs2326SnmpUsersEntry 4 }

gs2326SnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2326SnmpUsersEntry 5 }
   
gs2326SnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2326SnmpUsersEntry 6 }

gs2326SnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2326SnmpUsersEntry 7 }
   
gs2326SnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2326SnmpUsersEntry 8 }


gs2326SnmpGroups                                          OBJECT IDENTIFIER ::= { gs2326Snmp 5 }

gs2326SnmpGroupsCreate OBJECT-TYPE
   SYNTAX       INTEGER { none(0), create(1) }
   MAX-ACCESS   read-write
   STATUS       current
   DESCRIPTION
       "default: 0
        0 : None  (read only)
        1 : Create entry"
   ::= { gs2326SnmpGroups 1 }

gs2326SnmpGroupsTable OBJECT-TYPE
   SYNTAX      SEQUENCE OF GS2326SnmpGroupsEntry
   MAX-ACCESS  not-accessible
   STATUS      current
   DESCRIPTION
       " Create SNMPv3 groups entry."
   ::= { gs2326SnmpGroups 2 }

gs2326SnmpGroupsEntry OBJECT-TYPE
   SYNTAX      GS2326SnmpGroupsEntry
   MAX-ACCESS  not-accessible
   STATUS      current
   DESCRIPTION
       ""
   INDEX    { gs2326SnmpGroupsIndex  }
   ::= { gs2326SnmpGroupsTable 1 }

GS2326SnmpGroupsEntry ::= SEQUENCE {
   gs2326SnmpGroupsIndex           Integer32,
   gs2326SnmpGroupsSecurityModel   INTEGER,
   gs2326SnmpGroupsSecurityName    DisplayString,
   gs2326SnmpGroupsGroupName       DisplayString,
   gs2326SnmpGroupsRowStatus       INTEGER
}

gs2326SnmpGroupsIndex OBJECT-TYPE
   SYNTAX      Integer32(1..14)
   MAX-ACCESS  not-accessible
   STATUS      current
   DESCRIPTION
       " "
   ::= { gs2326SnmpGroupsEntry 1 }

gs2326SnmpGroupsSecurityModel OBJECT-TYPE
   SYNTAX      INTEGER { v1(1), v2c(2), usm(3) }
   MAX-ACCESS  read-write
   STATUS      current
   DESCRIPTION
       " 1: v1.
         2: v2c. 
         3: usm."
   ::= { gs2326SnmpGroupsEntry 2 }

gs2326SnmpGroupsSecurityName OBJECT-TYPE
   SYNTAX      DisplayString (SIZE (1..32))
   MAX-ACCESS  read-write
   STATUS      current
   DESCRIPTION
       "Up to 32 characters describing User Name."
   ::= { gs2326SnmpGroupsEntry 3 }

gs2326SnmpGroupsGroupName OBJECT-TYPE
   SYNTAX      DisplayString (SIZE (1..32))
   MAX-ACCESS  read-write
   STATUS      current
   DESCRIPTION
       "Up to 32 characters describing Group Name."
   ::= { gs2326SnmpGroupsEntry 4 }
   
gs2326SnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2326SnmpGroupsEntry 5 }

gs2326SnmpViews                                              OBJECT IDENTIFIER ::= { gs2326Snmp 6 }

gs2326SnmpViewsCreate OBJECT-TYPE
   SYNTAX       INTEGER { none(0), create(1) }
   MAX-ACCESS   read-write
   STATUS       current
   DESCRIPTION
       "default: 0
        0 : None  (read only)
        1 : Create entry"
   ::= { gs2326SnmpViews 1 }

gs2326SnmpViewsTable OBJECT-TYPE
   SYNTAX      SEQUENCE OF GS2326SnmpViewsEntry
   MAX-ACCESS  not-accessible
   STATUS      current
   DESCRIPTION
       " Create SNMPv1/v2 Views entry."
   ::= { gs2326SnmpViews 2 }

gs2326SnmpViewsEntry OBJECT-TYPE
   SYNTAX      GS2326SnmpViewsEntry
   MAX-ACCESS  not-accessible
   STATUS      current
   DESCRIPTION
       ""
   INDEX    { gs2326SnmpViewsIndex  }
   ::= { gs2326SnmpViewsTable 1 }

GS2326SnmpViewsEntry ::= SEQUENCE {
   gs2326SnmpViewsIndex        Integer32,
   gs2326SnmpViewsName         DisplayString,
   gs2326SnmpViewsType         INTEGER,
   gs2326SnmpViewsOIDSubtree   DisplayString,
   gs2326SnmpViewsRowStatus    INTEGER
}
   
gs2326SnmpViewsIndex OBJECT-TYPE
   SYNTAX      Integer32(1..4)
   MAX-ACCESS  not-accessible
   STATUS      current
   DESCRIPTION
       " "
   ::= { gs2326SnmpViewsEntry 1 }

gs2326SnmpViewsName OBJECT-TYPE
   SYNTAX      DisplayString (SIZE (1..32))
   MAX-ACCESS  read-write
   STATUS      current
   DESCRIPTION
       "Up to 32 characters describing view Name."
   ::= { gs2326SnmpViewsEntry 2 }   

gs2326SnmpViewsType OBJECT-TYPE
   SYNTAX      INTEGER { included(1), excluded(2) }
   MAX-ACCESS  read-write
   STATUS      current
   DESCRIPTION
       "1: included, An optional flag to indicate that this view subtree should be included. 
	   2: excluded, An optional flag to indicate that this view subtree should be excluded."
   ::= { gs2326SnmpViewsEntry 3 } 
   
gs2326SnmpViewsOIDSubtree OBJECT-TYPE
   SYNTAX      DisplayString (SIZE (1..128))
   MAX-ACCESS  read-write
   STATUS      current
   DESCRIPTION
       "The OID defining the root of the subtree to add to the named view."
   ::= { gs2326SnmpViewsEntry 4 } 

gs2326SnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2326SnmpViewsEntry 5 }   


gs2326SnmpAccess                                          OBJECT IDENTIFIER ::= { gs2326Snmp 7 }

gs2326SnmpAccessCreate OBJECT-TYPE
   SYNTAX       INTEGER { none(0), create(1) }
   MAX-ACCESS   read-write
   STATUS       current
   DESCRIPTION
       "default: 0
        0 : None  (read only)
        1 : Create entry"
   ::= { gs2326SnmpAccess 1 }

gs2326SnmpAccessTable OBJECT-TYPE
   SYNTAX      SEQUENCE OF GS2326SnmpAccessEntry
   MAX-ACCESS  not-accessible
   STATUS      current
   DESCRIPTION
       " Create SNMPv3 Access entry."
   ::= { gs2326SnmpAccess 2 }

gs2326SnmpAccessEntry OBJECT-TYPE
   SYNTAX      GS2326SnmpAccessEntry
   MAX-ACCESS  not-accessible
   STATUS      current
   DESCRIPTION
       ""
   INDEX    { gs2326SnmpAccessIndex  }
   ::= { gs2326SnmpAccessTable 1 }

GS2326SnmpAccessEntry ::= SEQUENCE {
   gs2326SnmpAccessIndex             Integer32,
   gs2326SnmpAccessGroupName         DisplayString,
   gs2326SnmpAccessSecurityModel     INTEGER,
   gs2326SnmpAccessSecurityLevel     INTEGER,
   gs2326SnmpAccessReadViewName      DisplayString,
   gs2326SnmpAccessWriteViewName     DisplayString,  
   gs2326SnmpAccessRowStatus         INTEGER
}

gs2326SnmpAccessIndex OBJECT-TYPE
   SYNTAX      Integer32(1..14)
   MAX-ACCESS  not-accessible
   STATUS      current
   DESCRIPTION
       " "
   ::= { gs2326SnmpAccessEntry 1 }

gs2326SnmpAccessGroupName OBJECT-TYPE
   SYNTAX      DisplayString (SIZE (1..32))
   MAX-ACCESS  read-write
   STATUS      current
   DESCRIPTION
       "Up to 32 characters describing Group Name."
   ::= { gs2326SnmpAccessEntry 2 }

gs2326SnmpAccessSecurityModel OBJECT-TYPE
   SYNTAX      INTEGER { any(0), v1(1), v2c(2), usm(3) }
   MAX-ACCESS  read-write
   STATUS      current
   DESCRIPTION
       " 0: any.
         1: v1.
         2: v2c. 
         3: usm."
   ::= { gs2326SnmpAccessEntry 3 }

gs2326SnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy. 
         3: Authentication and privacy. "
   ::= { gs2326SnmpAccessEntry 4 }

gs2326SnmpAccessReadViewName OBJECT-TYPE
   SYNTAX      DisplayString (SIZE (1..32))
   MAX-ACCESS  read-write
   STATUS      current
   DESCRIPTION
       "Up to 32 characters describing Read View Name.
        None is reserved for Empty."
   ::= { gs2326SnmpAccessEntry 5 }
   
gs2326SnmpAccessWriteViewName OBJECT-TYPE
   SYNTAX      DisplayString (SIZE (1..32))
   MAX-ACCESS  read-write
   STATUS      current
   DESCRIPTION
       "Up to 32 characters describing Write View Name.
        None is reserved for Empty."
   ::= { gs2326SnmpAccessEntry 6 }
   
gs2326SnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2326SnmpAccessEntry 7 }


----------------------------------------------------------------------------------------------------

gs2326Configuration                                         OBJECT IDENTIFIER ::= { lancomGS2326  2 }

gs2326Port                                                  OBJECT IDENTIFIER ::= { gs2326Configuration 1 }

gs2326PortConfigurationTable OBJECT-TYPE
   SYNTAX      SEQUENCE OF GS2326PortConfigurationEntry
   MAX-ACCESS  not-accessible
   STATUS      current
   DESCRIPTION
       " Show port configurations. "
   ::= { gs2326Port 1 }

gs2326PortConfigurationEntry OBJECT-TYPE
   SYNTAX      GS2326PortConfigurationEntry
   MAX-ACCESS  not-accessible
   STATUS      current
   DESCRIPTION
       ""
   INDEX    { gs2326PortConfPort  }
   ::= { gs2326PortConfigurationTable 1 }

GS2326PortConfigurationEntry ::= SEQUENCE {
   gs2326PortConfPort                     Integer32,
   gs2326PortConfPortMedia                DisplayString,
   gs2326PortConfLink                     DisplayString,
   gs2326PortConfCurrentSpeed             DisplayString,
   gs2326PortConfSpeed                    INTEGER,
   gs2326PortConfCurrentFlowControlRx     INTEGER,
   gs2326PortConfCurrentFlowControlTx     INTEGER,
   gs2326PortConfFlowControl              INTEGER,
   gs2326PortConfMaxFrameSize             Integer32,
   gs2326PortConfExcessiveCollisionMode   INTEGER,
   gs2326PortConfPowerControl             INTEGER,
   gs2326PortConfDescription              DisplayString
}

gs2326PortConfPort OBJECT-TYPE
   SYNTAX      Integer32(1..4095)
   MAX-ACCESS  not-accessible
   STATUS      current
   DESCRIPTION
       " port, range : 1 - port number. "
   ::= { gs2326PortConfigurationEntry 1 }

gs2326PortConfPortMedia OBJECT-TYPE
   SYNTAX      DisplayString(SIZE (1..4))
   MAX-ACCESS  read-only
   STATUS      current
   DESCRIPTION
       " Show port media. "
   ::= { gs2326PortConfigurationEntry 2 }

gs2326PortConfLink OBJECT-TYPE
   SYNTAX      DisplayString(SIZE (2..4))
   MAX-ACCESS  read-only
   STATUS      current
   DESCRIPTION
       " The current link state. "
   ::= { gs2326PortConfigurationEntry 3 }

gs2326PortConfCurrentSpeed OBJECT-TYPE
   SYNTAX      DisplayString(SIZE (6..12))
   MAX-ACCESS  read-only
   STATUS      current
   DESCRIPTION
       " The current link speed of the port. "
   ::= { gs2326PortConfigurationEntry 4 }

gs2326PortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11)
                }
   MAX-ACCESS  read-write
   STATUS      current
   DESCRIPTION
       "default: 1,
        0: disable state, 
        1: auto, 
        2: 10 Half, 
        3: 10 Full, 
        4: 100 Half, 
        5: 100 Full, 
        6: 1G full, 
        only 'Dual Media' port have 7-11 option. 
        Dual Media port default: 7,  
        7: SFP_Auto_AMS, 
        8: 100FX_AMS, 
        9: 1000X_AMS, 
        10: 100FX, 
        11: 1000X "
   ::= { gs2326PortConfigurationEntry 5 }

gs2326PortConfCurrentFlowControlRx OBJECT-TYPE
   SYNTAX      INTEGER { disable(0), enable(1), noSupport(2) }
   MAX-ACCESS  read-only
   STATUS      current
   DESCRIPTION
       "0: disable
        1: enable
        2: no support.  "
   ::= { gs2326PortConfigurationEntry 6 }

gs2326PortConfCurrentFlowControlTx OBJECT-TYPE
   SYNTAX      INTEGER { disable(0), enable(1), noSupport(2) }
   MAX-ACCESS  read-only
   STATUS      current
   DESCRIPTION
       "0: disable
        1: enable
        2: no support.  "
   ::= { gs2326PortConfigurationEntry 7 }

gs2326PortConfFlowControl OBJECT-TYPE
   SYNTAX      INTEGER { disable(0), enable(1), noSupport(2) }
   MAX-ACCESS  read-write
   STATUS      current
   DESCRIPTION
       "default: 0,
        0: disable
        1: enable
        2: no support. "
   ::= { gs2326PortConfigurationEntry 8 }

gs2326PortConfMaxFrameSize OBJECT-TYPE
   SYNTAX      Integer32 (1518..9600)
   MAX-ACCESS  read-write
   STATUS      current
   DESCRIPTION
       "default: 9600 , range : 1518 - 9600 "
   ::= { gs2326PortConfigurationEntry 9 }

gs2326PortConfExcessiveCollisionMode OBJECT-TYPE
   SYNTAX      INTEGER { discard(0), restart(1), noSupport(2) }
   MAX-ACCESS  read-write
   STATUS      current
   DESCRIPTION
       "default: 0,
        Excessive Collision Mode : 
        0: Discard,
        1: Restart, 
        2: no support.
       "
   ::= { gs2326PortConfigurationEntry 10 }

gs2326PortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy, 
        2: Dynamic (perfectReach),
        3: Enable,
        4: no support.
       "
   ::= { gs2326PortConfigurationEntry 11 }

gs2326PortConfDescription OBJECT-TYPE
   SYNTAX      DisplayString
   MAX-ACCESS  read-write
   STATUS      current
   DESCRIPTION
       " Interface specific description.
         Up to 47 characters describing this interface. "
   ::= { gs2326PortConfigurationEntry 12 }


gs2326PortTrafficStatisticsTable OBJECT-TYPE
   SYNTAX      SEQUENCE OF GS2326PortTrafficStatisticsEntry
   MAX-ACCESS  not-accessible
   STATUS      current
   DESCRIPTION
       " "
   ::= { gs2326Port 2 }

gs2326PortTrafficStatisticsEntry OBJECT-TYPE
   SYNTAX      GS2326PortTrafficStatisticsEntry
   MAX-ACCESS  not-accessible
   STATUS      current
   DESCRIPTION
       ""
   INDEX    { gs2326PortTrafficStatisticsPort  }
   ::= { gs2326PortTrafficStatisticsTable 1 }

GS2326PortTrafficStatisticsEntry ::= SEQUENCE {
   gs2326PortTrafficStatisticsPort          Integer32,
   gs2326PortTrafficStatisticsClear         INTEGER,
   gs2326PortTrafficRxPackets               Counter64,
   gs2326PortTrafficRxOctets                Counter64,
   gs2326PortTrafficRxUnicast               Counter64,
   gs2326PortTrafficRxMulticast             Counter64,
   gs2326PortTrafficRxBroadcast             Counter64,
   gs2326PortTrafficRxPause                 Counter64,
   gs2326PortTrafficRx64Bytes               Counter64,
   gs2326PortTrafficRx65to127Bytes          Counter64,
   gs2326PortTrafficRx128to255Bytes         Counter64,
   gs2326PortTrafficRx256to511Bytes         Counter64,
   gs2326PortTrafficRx512to1023Bytes        Counter64,
   gs2326PortTrafficRx1024to1526Bytes       Counter64,
   gs2326PortTrafficRxExceecd1527Bytes      Counter64,
   gs2326PortTrafficRxQ0                    Counter64,
   gs2326PortTrafficRxQ1                    Counter64,
   gs2326PortTrafficRxQ2                    Counter64,
   gs2326PortTrafficRxQ3                    Counter64,
   gs2326PortTrafficRxQ4                    Counter64,
   gs2326PortTrafficRxQ5                    Counter64,
   gs2326PortTrafficRxQ6                    Counter64,
   gs2326PortTrafficRxQ7                    Counter64,
   gs2326PortTrafficRxDrops                 Counter64,
   gs2326PortTrafficRxCRCorAlignment        Counter64,
   gs2326PortTrafficRxUndersize             Counter64,
   gs2326PortTrafficRxOversize              Counter64,
   gs2326PortTrafficRxFragments             Counter64,
   gs2326PortTrafficRxJabber                Counter64,
   gs2326PortTrafficRxFiltered              Counter64,
   gs2326PortTrafficTxPackets               Counter64,
   gs2326PortTrafficTxOctets                Counter64,
   gs2326PortTrafficTxUnicast               Counter64,
   gs2326PortTrafficTxMulticast             Counter64,
   gs2326PortTrafficTxBroadcast             Counter64,
   gs2326PortTrafficTxPause                 Counter64,
   gs2326PortTrafficTx64Bytes               Counter64,
   gs2326PortTrafficTx65to127Bytes          Counter64,
   gs2326PortTrafficTx128to255Bytes         Counter64,
   gs2326PortTrafficTx256to511Bytes         Counter64,
   gs2326PortTrafficTx512to1023Bytes        Counter64,
   gs2326PortTrafficTx1024to1526Bytes       Counter64,
   gs2326PortTrafficTxExceecd1527Bytes      Counter64,
   gs2326PortTrafficTxQ0                    Counter64,
   gs2326PortTrafficTxQ1                    Counter64,
   gs2326PortTrafficTxQ2                    Counter64,
   gs2326PortTrafficTxQ3                    Counter64,
   gs2326PortTrafficTxQ4                    Counter64,
   gs2326PortTrafficTxQ5                    Counter64,
   gs2326PortTrafficTxQ6                    Counter64,
   gs2326PortTrafficTxQ7                    Counter64,
   gs2326PortTrafficTxDrops                 Counter64,
   gs2326PortTrafficTxLateOrExcColl         Counter64
}

gs2326PortTrafficStatisticsPort OBJECT-TYPE
   SYNTAX      Integer32 (1..4095)
   MAX-ACCESS  not-accessible
   STATUS      current
   DESCRIPTION
       " "
   ::= { gs2326PortTrafficStatisticsEntry 1 }

gs2326PortTrafficStatisticsClear OBJECT-TYPE
   SYNTAX      INTEGER { disable(0), enable(1) }
   MAX-ACCESS  read-write
   STATUS      current
   DESCRIPTION
       " "
   ::= { gs2326PortTrafficStatisticsEntry 2 }

gs2326PortTrafficRxPackets OBJECT-TYPE
   SYNTAX      Counter64
   MAX-ACCESS  read-only
   STATUS      current
   DESCRIPTION
       " "
   ::= { gs2326PortTrafficStatisticsEntry 3 }

gs2326PortTrafficRxOctets OBJECT-TYPE
   SYNTAX      Counter64
   MAX-ACCESS  read-only
   STATUS      current
   DESCRIPTION
       " "
   ::= { gs2326PortTrafficStatisticsEntry 4 }

gs2326PortTrafficRxUnicast OBJECT-TYPE
   SYNTAX      Counter64
   MAX-ACCESS  read-only
   STATUS      current
   DESCRIPTION
       " "
   ::= { gs2326PortTrafficStatisticsEntry 5 }

gs2326PortTrafficRxMulticast OBJECT-TYPE
   SYNTAX      Counter64
   MAX-ACCESS  read-only
   STATUS      current
   DESCRIPTION
       " "
   ::= { gs2326PortTrafficStatisticsEntry 6 }

gs2326PortTrafficRxBroadcast OBJECT-TYPE
   SYNTAX      Counter64
   MAX-ACCESS  read-only
   STATUS      current
   DESCRIPTION
       " "
   ::= { gs2326PortTrafficStatisticsEntry 7 }

gs2326PortTrafficRxPause OBJECT-TYPE
   SYNTAX      Counter64
   MAX-ACCESS  read-only
   STATUS      current
   DESCRIPTION
       " "
   ::= { gs2326PortTrafficStatisticsEntry 8 }

gs2326PortTrafficRx64Bytes OBJECT-TYPE
   SYNTAX      Counter64
   MAX-ACCESS  read-only
   STATUS      current
   DESCRIPTION
       " "
   ::= { gs2326PortTrafficStatisticsEntry 9 }

gs2326PortTrafficRx65to127Bytes OBJECT-TYPE
   SYNTAX      Counter64
   MAX-ACCESS  read-only
   STATUS      current
   DESCRIPTION
       " "
   ::= { gs2326PortTrafficStatisticsEntry 10 }

gs2326PortTrafficRx128to255Bytes OBJECT-TYPE
   SYNTAX      Counter64
   MAX-ACCESS  read-only
   STATUS      current
   DESCRIPTION
       " "
   ::= { gs2326PortTrafficStatisticsEntry 11 }

gs2326PortTrafficRx256to511Bytes OBJECT-TYPE
   SYNTAX      Counter64
   MAX-ACCESS  read-only
   STATUS      current
   DESCRIPTION
       " "
   ::= { gs2326PortTrafficStatisticsEntry 12 }

gs2326PortTrafficRx512to1023Bytes OBJECT-TYPE
   SYNTAX      Counter64
   MAX-ACCESS  read-only
   STATUS      current
   DESCRIPTION
       " "
   ::= { gs2326PortTrafficStatisticsEntry 13 }

gs2326PortTrafficRx1024to1526Bytes OBJECT-TYPE
   SYNTAX      Counter64
   MAX-ACCESS  read-only
   STATUS      current
   DESCRIPTION
       " "
   ::= { gs2326PortTrafficStatisticsEntry 14 }

gs2326PortTrafficRxExceecd1527Bytes OBJECT-TYPE
   SYNTAX      Counter64
   MAX-ACCESS  read-only
   STATUS      current
   DESCRIPTION
       " "
   ::= { gs2326PortTrafficStatisticsEntry 15 }

gs2326PortTrafficRxQ0 OBJECT-TYPE
   SYNTAX      Counter64
   MAX-ACCESS  read-only
   STATUS      current
   DESCRIPTION
       " "
   ::= { gs2326PortTrafficStatisticsEntry 16 }

gs2326PortTrafficRxQ1 OBJECT-TYPE
   SYNTAX      Counter64
   MAX-ACCESS  read-only
   STATUS      current
   DESCRIPTION
       " "
   ::= { gs2326PortTrafficStatisticsEntry 17 }

gs2326PortTrafficRxQ2 OBJECT-TYPE
   SYNTAX      Counter64
   MAX-ACCESS  read-only
   STATUS      current
   DESCRIPTION
       " "
   ::= { gs2326PortTrafficStatisticsEntry 18 }

gs2326PortTrafficRxQ3 OBJECT-TYPE
   SYNTAX      Counter64
   MAX-ACCESS  read-only
   STATUS      current
   DESCRIPTION
       " "
   ::= { gs2326PortTrafficStatisticsEntry 19 }

gs2326PortTrafficRxQ4 OBJECT-TYPE
   SYNTAX      Counter64
   MAX-ACCESS  read-only
   STATUS      current
   DESCRIPTION
       " "
   ::= { gs2326PortTrafficStatisticsEntry 20 }

gs2326PortTrafficRxQ5 OBJECT-TYPE
   SYNTAX      Counter64
   MAX-ACCESS  read-only
   STATUS      current
   DESCRIPTION
       " "
   ::= { gs2326PortTrafficStatisticsEntry 21 }

gs2326PortTrafficRxQ6 OBJECT-TYPE
   SYNTAX      Counter64
   MAX-ACCESS  read-only
   STATUS      current
   DESCRIPTION
       " "
   ::= { gs2326PortTrafficStatisticsEntry 22 }

gs2326PortTrafficRxQ7 OBJECT-TYPE
   SYNTAX      Counter64
   MAX-ACCESS  read-only
   STATUS      current
   DESCRIPTION
       " "
   ::= { gs2326PortTrafficStatisticsEntry 23 }

gs2326PortTrafficRxDrops OBJECT-TYPE
   SYNTAX      Counter64
   MAX-ACCESS  read-only
   STATUS      current
   DESCRIPTION
       " "
   ::= { gs2326PortTrafficStatisticsEntry 24 }

gs2326PortTrafficRxCRCorAlignment OBJECT-TYPE
   SYNTAX      Counter64
   MAX-ACCESS  read-only
   STATUS      current
   DESCRIPTION
       " "
   ::= { gs2326PortTrafficStatisticsEntry 25 }

gs2326PortTrafficRxUndersize OBJECT-TYPE
   SYNTAX      Counter64
   MAX-ACCESS  read-only
   STATUS      current
   DESCRIPTION
       " "
   ::= { gs2326PortTrafficStatisticsEntry 26 }

gs2326PortTrafficRxOversize OBJECT-TYPE
   SYNTAX      Counter64
   MAX-ACCESS  read-only
   STATUS      current
   DESCRIPTION
       " "
   ::= { gs2326PortTrafficStatisticsEntry 27 }

gs2326PortTrafficRxFragments OBJECT-TYPE
   SYNTAX      Counter64
   MAX-ACCESS  read-only
   STATUS      current
   DESCRIPTION
       " "
   ::= { gs2326PortTrafficStatisticsEntry 28 }

gs2326PortTrafficRxJabber OBJECT-TYPE
   SYNTAX      Counter64
   MAX-ACCESS  read-only
   STATUS      current
   DESCRIPTION
       " "
   ::= { gs2326PortTrafficStatisticsEntry 29 }

gs2326PortTrafficRxFiltered OBJECT-TYPE
   SYNTAX      Counter64
   MAX-ACCESS  read-only
   STATUS      current
   DESCRIPTION
       " "
   ::= { gs2326PortTrafficStatisticsEntry 30 }

gs2326PortTrafficTxPackets OBJECT-TYPE
   SYNTAX      Counter64
   MAX-ACCESS  read-only
   STATUS      current
   DESCRIPTION
       " "
   ::= { gs2326PortTrafficStatisticsEntry 31 }

gs2326PortTrafficTxOctets OBJECT-TYPE
   SYNTAX      Counter64
   MAX-ACCESS  read-only
   STATUS      current
   DESCRIPTION
       " "
   ::= { gs2326PortTrafficStatisticsEntry 32 }

gs2326PortTrafficTxUnicast OBJECT-TYPE
   SYNTAX      Counter64
   MAX-ACCESS  read-only
   STATUS      current
   DESCRIPTION
       " "
   ::= { gs2326PortTrafficStatisticsEntry 33 }

gs2326PortTrafficTxMulticast OBJECT-TYPE
   SYNTAX      Counter64
   MAX-ACCESS  read-only
   STATUS      current
   DESCRIPTION
       " "
   ::= { gs2326PortTrafficStatisticsEntry 34 }

gs2326PortTrafficTxBroadcast OBJECT-TYPE
   SYNTAX      Counter64
   MAX-ACCESS  read-only
   STATUS      current
   DESCRIPTION
       " "
   ::= { gs2326PortTrafficStatisticsEntry 35 }

gs2326PortTrafficTxPause OBJECT-TYPE
   SYNTAX      Counter64
   MAX-ACCESS  read-only
   STATUS      current
   DESCRIPTION
       " "
   ::= { gs2326PortTrafficStatisticsEntry 36 }

gs2326PortTrafficTx64Bytes OBJECT-TYPE
   SYNTAX      Counter64
   MAX-ACCESS  read-only
   STATUS      current
   DESCRIPTION
       " "
   ::= { gs2326PortTrafficStatisticsEntry 37 }

gs2326PortTrafficTx65to127Bytes OBJECT-TYPE
   SYNTAX      Counter64
   MAX-ACCESS  read-only
   STATUS      current
   DESCRIPTION
       " "
   ::= { gs2326PortTrafficStatisticsEntry 38 }

gs2326PortTrafficTx128to255Bytes OBJECT-TYPE
   SYNTAX      Counter64
   MAX-ACCESS  read-only
   STATUS      current
   DESCRIPTION
       " "
   ::= { gs2326PortTrafficStatisticsEntry 39 }

gs2326PortTrafficTx256to511Bytes OBJECT-TYPE
   SYNTAX      Counter64
   MAX-ACCESS  read-only
   STATUS      current
   DESCRIPTION
       " "
   ::= { gs2326PortTrafficStatisticsEntry 40 }

gs2326PortTrafficTx512to1023Bytes OBJECT-TYPE
   SYNTAX      Counter64
   MAX-ACCESS  read-only
   STATUS      current
   DESCRIPTION
       " "
   ::= { gs2326PortTrafficStatisticsEntry 41 }

gs2326PortTrafficTx1024to1526Bytes OBJECT-TYPE
   SYNTAX      Counter64
   MAX-ACCESS  read-only
   STATUS      current
   DESCRIPTION
       " "
   ::= { gs2326PortTrafficStatisticsEntry 42 }

gs2326PortTrafficTxExceecd1527Bytes OBJECT-TYPE
   SYNTAX      Counter64
   MAX-ACCESS  read-only
   STATUS      current
   DESCRIPTION
       " "
   ::= { gs2326PortTrafficStatisticsEntry 43 }

gs2326PortTrafficTxQ0 OBJECT-TYPE
   SYNTAX      Counter64
   MAX-ACCESS  read-only
   STATUS      current
   DESCRIPTION
       " "
   ::= { gs2326PortTrafficStatisticsEntry 44 }

gs2326PortTrafficTxQ1 OBJECT-TYPE
   SYNTAX      Counter64
   MAX-ACCESS  read-only
   STATUS      current
   DESCRIPTION
       " "
   ::= { gs2326PortTrafficStatisticsEntry 45 }

gs2326PortTrafficTxQ2 OBJECT-TYPE
   SYNTAX      Counter64
   MAX-ACCESS  read-only
   STATUS      current
   DESCRIPTION
       " "
   ::= { gs2326PortTrafficStatisticsEntry 46 }

gs2326PortTrafficTxQ3 OBJECT-TYPE
   SYNTAX      Counter64
   MAX-ACCESS  read-only
   STATUS      current
   DESCRIPTION
       " "
   ::= { gs2326PortTrafficStatisticsEntry 47 }

gs2326PortTrafficTxQ4 OBJECT-TYPE
   SYNTAX      Counter64
   MAX-ACCESS  read-only
   STATUS      current
   DESCRIPTION
       " "
   ::= { gs2326PortTrafficStatisticsEntry 48 }

gs2326PortTrafficTxQ5 OBJECT-TYPE
   SYNTAX      Counter64
   MAX-ACCESS  read-only
   STATUS      current
   DESCRIPTION
       " "
   ::= { gs2326PortTrafficStatisticsEntry 49 }

gs2326PortTrafficTxQ6 OBJECT-TYPE
   SYNTAX      Counter64
   MAX-ACCESS  read-only
   STATUS      current
   DESCRIPTION
       " "
   ::= { gs2326PortTrafficStatisticsEntry 50 }


gs2326PortTrafficTxQ7 OBJECT-TYPE
   SYNTAX      Counter64
   MAX-ACCESS  read-only
   STATUS      current
   DESCRIPTION
       " "
   ::= { gs2326PortTrafficStatisticsEntry 51 }

gs2326PortTrafficTxDrops OBJECT-TYPE
   SYNTAX      Counter64
   MAX-ACCESS  read-only
   STATUS      current
   DESCRIPTION
       " "
   ::= { gs2326PortTrafficStatisticsEntry 52 }

gs2326PortTrafficTxLateOrExcColl OBJECT-TYPE
   SYNTAX      Counter64
   MAX-ACCESS  read-only
   STATUS      current
   DESCRIPTION
       " "
   ::= { gs2326PortTrafficStatisticsEntry 53 }


gs2326PortQoSStatistics                                     OBJECT IDENTIFIER ::= { gs2326Port 3 }

gs2326PortQoSStatisticsClear OBJECT-TYPE
   SYNTAX      INTEGER { none(0), clear(1) }
   MAX-ACCESS  read-only
   STATUS      current
   DESCRIPTION
       "default: 0
       0: none
       1: clear "
   ::= { gs2326PortQoSStatistics 1 }

gs2326PortQoSStatisticsTable OBJECT-TYPE
   SYNTAX      SEQUENCE OF GS2326PortQoSStatisticsEntry
   MAX-ACCESS  not-accessible
   STATUS      current
   DESCRIPTION
       " "
   ::= { gs2326PortQoSStatistics 2 }

gs2326PortQoSStatisticsEntry OBJECT-TYPE
   SYNTAX      GS2326PortQoSStatisticsEntry
   MAX-ACCESS  not-accessible
   STATUS      current
   DESCRIPTION
       ""
   INDEX    { gs2326PortQoSStatisticsPort  }
   ::= { gs2326PortQoSStatisticsTable 1 }

GS2326PortQoSStatisticsEntry ::= SEQUENCE {
   gs2326PortQoSStatisticsPort      Integer32,
   gs2326PortQoSQ0Rx                Counter64,
   gs2326PortQoSQ0Tx                Counter64,
   gs2326PortQoSQ1Rx                Counter64,
   gs2326PortQoSQ1Tx                Counter64,
   gs2326PortQoSQ2Rx                Counter64,
   gs2326PortQoSQ2Tx                Counter64,
   gs2326PortQoSQ3Rx                Counter64,
   gs2326PortQoSQ3Tx                Counter64,
   gs2326PortQoSQ4Rx                Counter64,
   gs2326PortQoSQ4Tx                Counter64,
   gs2326PortQoSQ5Rx                Counter64,
   gs2326PortQoSQ5Tx                Counter64,
   gs2326PortQoSQ6Rx                Counter64,
   gs2326PortQoSQ6Tx                Counter64,
   gs2326PortQoSQ7Rx                Counter64,
   gs2326PortQoSQ7Tx                Counter64
}

gs2326PortQoSStatisticsPort OBJECT-TYPE
   SYNTAX      Integer32(1..4095)
   MAX-ACCESS  not-accessible
   STATUS      current
   DESCRIPTION
       " "
   ::= { gs2326PortQoSStatisticsEntry 1 }

gs2326PortQoSQ0Rx OBJECT-TYPE
   SYNTAX      Counter64
   MAX-ACCESS  read-only
   STATUS      current
   DESCRIPTION
       " "
   ::= { gs2326PortQoSStatisticsEntry 2 }

gs2326PortQoSQ0Tx OBJECT-TYPE
   SYNTAX      Counter64
   MAX-ACCESS  read-only
   STATUS      current
   DESCRIPTION
       " "
   ::= { gs2326PortQoSStatisticsEntry 3 }

gs2326PortQoSQ1Rx OBJECT-TYPE
   SYNTAX      Counter64
   MAX-ACCESS  read-only
   STATUS      current
   DESCRIPTION
       " "
   ::= { gs2326PortQoSStatisticsEntry 4 }

gs2326PortQoSQ1Tx OBJECT-TYPE
   SYNTAX      Counter64
   MAX-ACCESS  read-only
   STATUS      current
   DESCRIPTION
       " "
   ::= { gs2326PortQoSStatisticsEntry 5 }

gs2326PortQoSQ2Rx OBJECT-TYPE
   SYNTAX      Counter64
   MAX-ACCESS  read-only
   STATUS      current
   DESCRIPTION
       " "
   ::= { gs2326PortQoSStatisticsEntry 6 }

gs2326PortQoSQ2Tx OBJECT-TYPE
   SYNTAX      Counter64
   MAX-ACCESS  read-only
   STATUS      current
   DESCRIPTION
       " "
   ::= { gs2326PortQoSStatisticsEntry 7 }

gs2326PortQoSQ3Rx OBJECT-TYPE
   SYNTAX      Counter64
   MAX-ACCESS  read-only
   STATUS      current
   DESCRIPTION
       " "
   ::= { gs2326PortQoSStatisticsEntry 8 }

gs2326PortQoSQ3Tx OBJECT-TYPE
   SYNTAX      Counter64
   MAX-ACCESS  read-only
   STATUS      current
   DESCRIPTION
       " "
   ::= { gs2326PortQoSStatisticsEntry 9 }

gs2326PortQoSQ4Rx OBJECT-TYPE
   SYNTAX      Counter64
   MAX-ACCESS  read-only
   STATUS      current
   DESCRIPTION
       " "
   ::= { gs2326PortQoSStatisticsEntry 10 }

gs2326PortQoSQ4Tx OBJECT-TYPE
   SYNTAX      Counter64
   MAX-ACCESS  read-only
   STATUS      current
   DESCRIPTION
       " "
   ::= { gs2326PortQoSStatisticsEntry 11 }

gs2326PortQoSQ5Rx OBJECT-TYPE
   SYNTAX      Counter64
   MAX-ACCESS  read-only
   STATUS      current
   DESCRIPTION
       " "
   ::= { gs2326PortQoSStatisticsEntry 12 }

gs2326PortQoSQ5Tx OBJECT-TYPE
   SYNTAX      Counter64
   MAX-ACCESS  read-only
   STATUS      current
   DESCRIPTION
       " "
   ::= { gs2326PortQoSStatisticsEntry 13 }

gs2326PortQoSQ6Rx OBJECT-TYPE
   SYNTAX      Counter64
   MAX-ACCESS  read-only
   STATUS      current
   DESCRIPTION
       " "
   ::= { gs2326PortQoSStatisticsEntry 14 }

gs2326PortQoSQ6Tx OBJECT-TYPE
   SYNTAX      Counter64
   MAX-ACCESS  read-only
   STATUS      current
   DESCRIPTION
       " "
   ::= { gs2326PortQoSStatisticsEntry 15 }

gs2326PortQoSQ7Rx OBJECT-TYPE
   SYNTAX      Counter64
   MAX-ACCESS  read-only
   STATUS      current
   DESCRIPTION
       " "
   ::= { gs2326PortQoSStatisticsEntry 16 }

gs2326PortQoSQ7Tx OBJECT-TYPE
   SYNTAX      Counter64
   MAX-ACCESS  read-only
   STATUS      current
   DESCRIPTION
       " "
   ::= { gs2326PortQoSStatisticsEntry 17 }

gs2326SFPInfoTable OBJECT-TYPE
   SYNTAX      SEQUENCE OF GS2326SFPInfoEntry
   MAX-ACCESS  not-accessible
   STATUS      current
   DESCRIPTION
       " "
   ::= { gs2326Port 4 }

gs2326SFPInfoEntry OBJECT-TYPE
   SYNTAX      GS2326SFPInfoEntry
   MAX-ACCESS  not-accessible
   STATUS      current
   DESCRIPTION
       ""
   INDEX    { gs2326SFPInfoIndex }
   ::= { gs2326SFPInfoTable 1 }

GS2326SFPInfoEntry ::= SEQUENCE {
   gs2326SFPInfoIndex               Integer32,
   gs2326SFPInfoPort                DisplayString,
   gs2326SFPConnectorType           DisplayString,
   gs2326SFPFiberType               DisplayString,
   gs2326SFPTxCentralWavelength     DisplayString,
   gs2326SFPBaudRate                DisplayString,
   gs2326SFPVendorOUI               DisplayString,
   gs2326SFPVendorName              DisplayString,
   gs2326SFPVendorPN                DisplayString,
   gs2326SFPVendorRev               DisplayString,
   gs2326SFPVendorSN                DisplayString,
   gs2326SFPDateCode                DisplayString,
   gs2326SFPTemperature             DisplayString,
   gs2326SFPVcc                     DisplayString,
   gs2326SFPMon1Bias                DisplayString,
   gs2326SFPMon2TxPWR               DisplayString,
   gs2326SFPMon3RxPWR               DisplayString
}

gs2326SFPInfoIndex OBJECT-TYPE
   SYNTAX      Integer32(1..4095)
   MAX-ACCESS  not-accessible
   STATUS      current
   DESCRIPTION
       " "
   ::= { gs2326SFPInfoEntry 1 }

gs2326SFPInfoPort OBJECT-TYPE
   SYNTAX      DisplayString
   MAX-ACCESS  read-only
   STATUS      current
   DESCRIPTION
       " "
   ::= { gs2326SFPInfoEntry 2 }

gs2326SFPConnectorType OBJECT-TYPE
   SYNTAX      DisplayString
   MAX-ACCESS  read-only
   STATUS      current
   DESCRIPTION
       " "
   ::= { gs2326SFPInfoEntry 3 }

gs2326SFPFiberType OBJECT-TYPE
   SYNTAX      DisplayString
   MAX-ACCESS  read-only
   STATUS      current
   DESCRIPTION
       " "
   ::= { gs2326SFPInfoEntry 4 }

gs2326SFPTxCentralWavelength OBJECT-TYPE
   SYNTAX      DisplayString
   MAX-ACCESS  read-only
   STATUS      current
   DESCRIPTION
       " "
   ::= { gs2326SFPInfoEntry 5 }

gs2326SFPBaudRate OBJECT-TYPE
   SYNTAX      DisplayString
   MAX-ACCESS  read-only
   STATUS      current
   DESCRIPTION
       " "
   ::= { gs2326SFPInfoEntry 6 }

gs2326SFPVendorOUI OBJECT-TYPE
   SYNTAX      DisplayString
   MAX-ACCESS  read-only
   STATUS      current
   DESCRIPTION
       " "
   ::= { gs2326SFPInfoEntry 7 }

gs2326SFPVendorName OBJECT-TYPE
   SYNTAX      DisplayString
   MAX-ACCESS  read-only
   STATUS      current
   DESCRIPTION
       " "
   ::= { gs2326SFPInfoEntry 8 }

gs2326SFPVendorPN OBJECT-TYPE
   SYNTAX      DisplayString
   MAX-ACCESS  read-only
   STATUS      current
   DESCRIPTION
       " "
   ::= { gs2326SFPInfoEntry 9 }

gs2326SFPVendorRev OBJECT-TYPE
   SYNTAX      DisplayString
   MAX-ACCESS  read-only
   STATUS      current
   DESCRIPTION
       " "
   ::= { gs2326SFPInfoEntry 10 }

gs2326SFPVendorSN OBJECT-TYPE
   SYNTAX      DisplayString
   MAX-ACCESS  read-only
   STATUS      current
   DESCRIPTION
       " "
   ::= { gs2326SFPInfoEntry 11 }

gs2326SFPDateCode OBJECT-TYPE
   SYNTAX      DisplayString
   MAX-ACCESS  read-only
   STATUS      current
   DESCRIPTION
       " "
   ::= { gs2326SFPInfoEntry 12 }

gs2326SFPTemperature OBJECT-TYPE
   SYNTAX      DisplayString
   MAX-ACCESS  read-only
   STATUS      current
   DESCRIPTION
       " "
   ::= { gs2326SFPInfoEntry 13 }

gs2326SFPVcc OBJECT-TYPE
   SYNTAX      DisplayString
   MAX-ACCESS  read-only
   STATUS      current
   DESCRIPTION
       " "
   ::= { gs2326SFPInfoEntry 14 }
   
gs2326SFPMon1Bias OBJECT-TYPE
   SYNTAX      DisplayString
   MAX-ACCESS  read-only
   STATUS      current
   DESCRIPTION
       " "
   ::= { gs2326SFPInfoEntry 15 }
   
gs2326SFPMon2TxPWR OBJECT-TYPE
   SYNTAX      DisplayString
   MAX-ACCESS  read-only
   STATUS      current
   DESCRIPTION
       " "
   ::= { gs2326SFPInfoEntry 16 }

gs2326SFPMon3RxPWR OBJECT-TYPE
   SYNTAX      DisplayString
   MAX-ACCESS  read-only
   STATUS      current
   DESCRIPTION
       " "
   ::= { gs2326SFPInfoEntry 17 }


gs2326PortEEETable OBJECT-TYPE
   SYNTAX      SEQUENCE OF GS2326PortEEEEntry
   MAX-ACCESS  not-accessible
   STATUS      current
   DESCRIPTION
      " "
   ::= { gs2326Port 5 }

gs2326PortEEEEntry OBJECT-TYPE
   SYNTAX      GS2326PortEEEEntry
   MAX-ACCESS  not-accessible
   STATUS      current
   DESCRIPTION
       ""
   INDEX    { gs2326PortEEEPort }
   ::= { gs2326PortEEETable 1 }

GS2326PortEEEEntry ::= SEQUENCE {
   gs2326PortEEEPort		        Integer32,
   gs2326PortEEEMode		        INTEGER,
   gs2326PortEEEUrgentQueue1		INTEGER,
   gs2326PortEEEUrgentQueue2		INTEGER,
   gs2326PortEEEUrgentQueue3		INTEGER,
   gs2326PortEEEUrgentQueue4		INTEGER,
   gs2326PortEEEUrgentQueue5		INTEGER,
   gs2326PortEEEUrgentQueue6		INTEGER,
   gs2326PortEEEUrgentQueue7		INTEGER,
   gs2326PortEEEUrgentQueue8		INTEGER
}

gs2326PortEEEPort OBJECT-TYPE
   SYNTAX      Integer32(1..4095)
   MAX-ACCESS  not-accessible
   STATUS      current
   DESCRIPTION
       " "
   ::= { gs2326PortEEEEntry 1 }

gs2326PortEEEMode OBJECT-TYPE
   SYNTAX      INTEGER { disable(0), enable(1) }
   MAX-ACCESS  read-write
   STATUS      current
   DESCRIPTION
       "default: 0
       0:disable
       1:enable "
   ::= { gs2326PortEEEEntry 2 }

gs2326PortEEEUrgentQueue1 OBJECT-TYPE
   SYNTAX      INTEGER { disable(0), enable(1) }
   MAX-ACCESS  read-write
   STATUS      current
   DESCRIPTION
       "default: 0
       0:disable
       1:enable "
   ::= { gs2326PortEEEEntry 3 }

gs2326PortEEEUrgentQueue2 OBJECT-TYPE
   SYNTAX      INTEGER { disable(0), enable(1) }
   MAX-ACCESS  read-write
   STATUS      current
   DESCRIPTION
       "default: 0
       0:disable
       1:enable "
   ::= { gs2326PortEEEEntry 4 }

gs2326PortEEEUrgentQueue3 OBJECT-TYPE
   SYNTAX      INTEGER { disable(0), enable(1) }
   MAX-ACCESS  read-write
   STATUS      current
   DESCRIPTION
       "default: 0
       0:disable
       1:enable "
   ::= { gs2326PortEEEEntry 5 }

gs2326PortEEEUrgentQueue4 OBJECT-TYPE
   SYNTAX      INTEGER { disable(0), enable(1) }
   MAX-ACCESS  read-write
   STATUS      current
   DESCRIPTION
       "default: 0
       0:disable
       1:enable "
   ::= { gs2326PortEEEEntry 6 }

gs2326PortEEEUrgentQueue5 OBJECT-TYPE
   SYNTAX      INTEGER { disable(0), enable(1) }
   MAX-ACCESS  read-write
   STATUS      current
   DESCRIPTION
       "default: 0
       0:disable
       1:enable "
   ::= { gs2326PortEEEEntry 7 }

gs2326PortEEEUrgentQueue6 OBJECT-TYPE
   SYNTAX      INTEGER { disable(0), enable(1) }
   MAX-ACCESS  read-write
   STATUS      current
   DESCRIPTION
       "default: 0
       0:disable
       1:enable "
   ::= { gs2326PortEEEEntry 8 }

gs2326PortEEEUrgentQueue7 OBJECT-TYPE
   SYNTAX      INTEGER { disable(0), enable(1) }
   MAX-ACCESS  read-write
   STATUS      current
   DESCRIPTION
       "default: 0
       0:disable
       1:enable "
   ::= { gs2326PortEEEEntry 9 }

gs2326PortEEEUrgentQueue8 OBJECT-TYPE
   SYNTAX      INTEGER { disable(0), enable(1) }
   MAX-ACCESS  read-write
   STATUS      current
   DESCRIPTION
       "default: 0
       0:disable
       1:enable "
   ::= { gs2326PortEEEEntry 10 }


gs2326VoiceVLAN                                             OBJECT IDENTIFIER ::= { gs2326Configuration 2 }

gs2326VoiceVLANConf                                         OBJECT IDENTIFIER ::= { gs2326VoiceVLAN 1 }

gs2326VoiceVLANMode OBJECT-TYPE
   SYNTAX      INTEGER { disable(0), enable(1) }
   MAX-ACCESS  read-write
   STATUS      current
   DESCRIPTION
       " Voice VLAN mode operation.
       default: 0,
       0: disable
       1: enable"
   ::= { gs2326VoiceVLANConf 1 }

gs2326VoiceVLANVLANId OBJECT-TYPE
   SYNTAX      Integer32(1..4094)
   MAX-ACCESS  read-write
   STATUS      current
   DESCRIPTION
       "Voice VLAN ID.
        default: 1000,
        range : 1-4094. "
   ::= { gs2326VoiceVLANConf 2 }

gs2326VoiceVLANAgingTime OBJECT-TYPE
   SYNTAX      Integer32(10..1000000)
   MAX-ACCESS  read-write
   STATUS      current
   DESCRIPTION
       " Voice VLAN secure learning aging time. 
         default: 86400,
         range : 10 - 10000000. "
   ::= { gs2326VoiceVLANConf 3 }

gs2326VoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2326VoiceVLANConf 4 }


gs2326VoiceVLANPortTable OBJECT-TYPE
   SYNTAX      SEQUENCE OF GS2326VoiceVLANPortEntry
   MAX-ACCESS  not-accessible
   STATUS      current
   DESCRIPTION
       " Show Voice Vlan configuration. "
   ::= { gs2326VoiceVLANConf 5 }

gs2326VoiceVLANPortEntry OBJECT-TYPE
   SYNTAX      GS2326VoiceVLANPortEntry
   MAX-ACCESS  not-accessible
   STATUS      current
   DESCRIPTION
       ""
   INDEX    { gs2326VoiceVLANPort  }
   ::= { gs2326VoiceVLANPortTable 1 }

GS2326VoiceVLANPortEntry ::= SEQUENCE {
   gs2326VoiceVLANPort                    Integer32,
   gs2326VoiceVLANPortMode                INTEGER,
   gs2326VoiceVLANPortSecurity            INTEGER,
   gs2326VoiceVLANPortDiscoveryProtocol   INTEGER
}

gs2326VoiceVLANPort OBJECT-TYPE
   SYNTAX      Integer32(1..4095)
   MAX-ACCESS  not-accessible
   STATUS      current
   DESCRIPTION
       " port, range : 1 - port number. "
   ::= { gs2326VoiceVLANPortEntry 1 }

gs2326VoiceVLANPortMode OBJECT-TYPE
   SYNTAX      INTEGER { disable(0), auto(1), forced(2) }
   MAX-ACCESS  read-write
   STATUS      current
   DESCRIPTION
       " Voice VLAN port mode.  
         default: 0,
         0: Disable (Disjoin from Voice VLAN.)
         1: Auto (Enable auto detect mode. It detects whether there is VoIP phone attached to the specific port and configures the Voice VLAN members automatically.)
         2: Forced (Force join to Voice VLAN.)"
   ::= { gs2326VoiceVLANPortEntry 2 }

gs2326VoiceVLANPortSecurity OBJECT-TYPE
   SYNTAX      INTEGER { disable(0), enable(1) }
   MAX-ACCESS  read-write
   STATUS      current
   DESCRIPTION
       " Voice VLAN port security mode. 
         default: 0,
         0: Disable (Disjoin from Voice VLAN.)
         1: enable ( Enable Voice VLAN security mode. When the function is
                     enabled, all non-telephone MAC address in Voice VLAN
                     will be blocked 10 seconds.)"
   ::= { gs2326VoiceVLANPortEntry 3 }

gs2326VoiceVLANPortDiscoveryProtocol OBJECT-TYPE
   SYNTAX      INTEGER { oui(0), lldp(1), both(2) }
   MAX-ACCESS  read-write
   STATUS      current
   DESCRIPTION
       " Voice VLAN port discovery protocol.  
         default: 0
         0: OUI (Detect telephony device by OUI address.)
         1: LLDP (Detect telephony device by LLDP.)
         2: Both (Both OUI and LLDP.) "
   ::= { gs2326VoiceVLANPortEntry 4 }

gs2326VoiceVLANSkipNAS OBJECT-TYPE
   SYNTAX      INTEGER { disable(0), enable(1) }
   MAX-ACCESS  read-write
   STATUS      current
   DESCRIPTION
       " Voice VLAN skip NAS mode. 
         default: 0,
         0: Disable (Do not skip NAS on Voice VLAN.)
         1: enable (Enable skipping of NAS on Voice VLAN. When the function is
                    enabled, authentication through the NAS module is not
                    applied to the Voice VLAN, but clients are allowed without
                    authentication.)"
   ::= { gs2326VoiceVLANPortEntry 5 }


gs2326VoiceVLANOUI                                          OBJECT IDENTIFIER ::= { gs2326VoiceVLAN 2 }

gs2326VoiceVLANOUICreate OBJECT-TYPE
   SYNTAX       INTEGER { none(0), create(1) }
   MAX-ACCESS   read-write
   STATUS       current
   DESCRIPTION
       "default: 0
        0 : None  (read only)
        1 : Create an OUI entry"
   ::= { gs2326VoiceVLANOUI 1 }

gs2326VoiceVLANOUITable OBJECT-TYPE
   SYNTAX      SEQUENCE OF GS2326VoiceVLANOUIEntry
   MAX-ACCESS  not-accessible
   STATUS      current
   DESCRIPTION
       " Create Voice VLAN OUI entry. Modify OUI table will
         restart auto detect OUI process. "
   ::= { gs2326VoiceVLANOUI 2 }

gs2326VoiceVLANOUIEntry OBJECT-TYPE
   SYNTAX      GS2326VoiceVLANOUIEntry
   MAX-ACCESS  not-accessible
   STATUS      current
   DESCRIPTION
       ""
   INDEX    { gs2326VoiceVLANOUIIndex  }
   ::= { gs2326VoiceVLANOUITable 1 }

GS2326VoiceVLANOUIEntry ::= SEQUENCE {
   gs2326VoiceVLANOUIIndex         Integer32,
   gs2326VoiceVLANTelephonyOUI     OCTET STRING,
   gs2326VoiceVLANDescription      DisplayString,
   gs2326VoiceVLANOUIRowStatus     INTEGER
}

gs2326VoiceVLANOUIIndex OBJECT-TYPE
   SYNTAX      Integer32(1..16)
   MAX-ACCESS  not-accessible
   STATUS      current
   DESCRIPTION
       " "
   ::= { gs2326VoiceVLANOUIEntry 1 }

gs2326VoiceVLANTelephonyOUI OBJECT-TYPE
   SYNTAX      OCTET STRING (SIZE (1..32))
   MAX-ACCESS  read-write
   STATUS      current
   DESCRIPTION
       "OUI address, format : 0a 1b 2c "
   ::= { gs2326VoiceVLANOUIEntry 2 }

gs2326VoiceVLANDescription OBJECT-TYPE
   SYNTAX      DisplayString (SIZE (1..32))
   MAX-ACCESS  read-write
   STATUS      current
   DESCRIPTION
       " Up to 32 characters describing OUI address. "
   ::= { gs2326VoiceVLANOUIEntry 3 }

gs2326VoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2326VoiceVLANOUIEntry 4 }

gs2326GARP                                                   OBJECT IDENTIFIER ::= { gs2326Configuration 3 }

gs2326GARPConfTable OBJECT-TYPE
   SYNTAX      SEQUENCE OF GS2326GARPConfEntry
   MAX-ACCESS  not-accessible
   STATUS      current
   DESCRIPTION
       " "
   ::= { gs2326GARP 1 }

gs2326GARPConfEntry OBJECT-TYPE
   SYNTAX      GS2326GARPConfEntry
   MAX-ACCESS  not-accessible
   STATUS      current
   DESCRIPTION
       ""
   INDEX    { gs2326GARPConfPort  }
   ::= { gs2326GARPConfTable 1 }

GS2326GARPConfEntry ::= SEQUENCE {
   gs2326GARPConfPort           Integer32,
   gs2326GARPJoinTimer          Integer32,
   gs2326GARPLeaveTimer         Integer32,
   gs2326GARPLeaveAllTimer      Integer32,
   gs2326GARPApplicantion       INTEGER,
   gs2326GARPAttributeType      INTEGER,
   gs2326GARPApplicant          INTEGER
}

gs2326GARPConfPort OBJECT-TYPE
   SYNTAX      Integer32(1..4095)
   MAX-ACCESS  not-accessible
   STATUS      current
   DESCRIPTION
       " "
   ::= { gs2326GARPConfEntry 1 }

gs2326GARPJoinTimer OBJECT-TYPE
   SYNTAX      Integer32(200..1000)
   MAX-ACCESS  read-write
   STATUS      current
   DESCRIPTION
       "default: 200, range : 200 - 1000 "
   ::= { gs2326GARPConfEntry 2 }

gs2326GARPLeaveTimer OBJECT-TYPE
   SYNTAX      Integer32(600..3000)
   MAX-ACCESS  read-write
   STATUS      current
   DESCRIPTION
       "default: 600 , range : 600 - 3000"
   ::= { gs2326GARPConfEntry 3 }

gs2326GARPLeaveAllTimer OBJECT-TYPE
   SYNTAX      Integer32(10000..50000)
   MAX-ACCESS  read-write
   STATUS      current
   DESCRIPTION
       "default: 10000, range : 10000 - 50000 "
   ::= { gs2326GARPConfEntry 4 }

gs2326GARPApplicantion OBJECT-TYPE
   SYNTAX      INTEGER { gvrp(1)}
   MAX-ACCESS  read-write
   STATUS      current
   DESCRIPTION
       "default: 1
       1: GVRP"
   ::= { gs2326GARPConfEntry 5 }

gs2326GARPAttributeType OBJECT-TYPE
   SYNTAX      INTEGER { vlan(1)}
   MAX-ACCESS  read-write
   STATUS      current
   DESCRIPTION
       "default: 1
       1: VLAN"
   ::= { gs2326GARPConfEntry 6 }

gs2326GARPApplicant OBJECT-TYPE
   SYNTAX      INTEGER { participant(0), nonParticipant(1) }
   MAX-ACCESS  read-write
   STATUS      current
   DESCRIPTION
       "default: 0
       0: normal-participant
       1: non-participant"
   ::= { gs2326GARPConfEntry 7 }

gs2326GARPStatisticsTable OBJECT-TYPE
   SYNTAX      SEQUENCE OF GS2326GARPStatisticsEntry
   MAX-ACCESS  not-accessible
   STATUS      current
   DESCRIPTION
       " Show the basic GARP port statistics. "
   ::= { gs2326GARP 2 }

gs2326GARPStatisticsEntry OBJECT-TYPE
   SYNTAX      GS2326GARPStatisticsEntry
   MAX-ACCESS  not-accessible
   STATUS      current
   DESCRIPTION
       ""
   INDEX    { gs2326GARPStatisticsPort  }
   ::= { gs2326GARPStatisticsTable 1 }

GS2326GARPStatisticsEntry ::= SEQUENCE {
   gs2326GARPStatisticsPort             Integer32,
   gs2326GARPStatisticsPeerMAC          DisplayString,
   gs2326GARPStatisticsFailedCount      Counter32
}

gs2326GARPStatisticsPort OBJECT-TYPE
   SYNTAX      Integer32(1..4095)
   MAX-ACCESS  not-accessible
   STATUS      current
   DESCRIPTION
       " port, range : 1 - port number. "
   ::= { gs2326GARPStatisticsEntry 1 }

gs2326GARPStatisticsPeerMAC OBJECT-TYPE
   SYNTAX      DisplayString
   MAX-ACCESS  read-only
   STATUS      current
   DESCRIPTION
       " Peer MAC is MAC address of the neighbour Switch from with GARP frame is received.  "
   ::= { gs2326GARPStatisticsEntry 2 }

gs2326GARPStatisticsFailedCount OBJECT-TYPE
   SYNTAX      Counter32
   MAX-ACCESS  read-only
   STATUS      current
   DESCRIPTION
       " explain Failed count here. "
   ::= { gs2326GARPStatisticsEntry 3 }

gs2326GVRP                                                   OBJECT IDENTIFIER ::= { gs2326Configuration 4 }

gs2326GVRPConf                                                   OBJECT IDENTIFIER ::= { gs2326GVRP 1 }

gs2326GVRPMode OBJECT-TYPE
   SYNTAX      INTEGER { disable(0), enable(1) }
   MAX-ACCESS  read-write
   STATUS      current
   DESCRIPTION
       "default: 0,
        0: disable, 
        1: enable. "
   ::= { gs2326GVRPConf 1 }

gs2326GVRPConfTable OBJECT-TYPE
   SYNTAX      SEQUENCE OF GS2326GVRPConfEntry
   MAX-ACCESS  not-accessible
   STATUS      current
   DESCRIPTION
       " "
   ::= { gs2326GVRPConf 2 }

gs2326GVRPConfEntry OBJECT-TYPE
   SYNTAX      GS2326GVRPConfEntry
   MAX-ACCESS  not-accessible
   STATUS      current
   DESCRIPTION
       ""
   INDEX    { gs2326GVRPConfPort  }
   ::= { gs2326GVRPConfTable 1 }

GS2326GVRPConfEntry ::= SEQUENCE {
   gs2326GVRPConfPort           Integer32,
   gs2326GVRPConfPortMode       INTEGER,
   gs2326GVRPConfPortRRole      INTEGER
}

gs2326GVRPConfPort OBJECT-TYPE
   SYNTAX      Integer32(1..4095)
   MAX-ACCESS  not-accessible
   STATUS      current
   DESCRIPTION
       " "
   ::= { gs2326GVRPConfEntry 1 }

gs2326GVRPConfPortMode OBJECT-TYPE
   SYNTAX      INTEGER { disable(0), enable(1) }
   MAX-ACCESS  read-write
   STATUS      current
   DESCRIPTION
       "default: 0
       1: enable
       0: disable"
   ::= { gs2326GVRPConfEntry 2 }

gs2326GVRPConfPortRRole OBJECT-TYPE
   SYNTAX      INTEGER { disable(0), enable(1) }
   MAX-ACCESS  read-write
   STATUS      current
   DESCRIPTION
       "default: 0
       1: enable
       0: disable"
   ::= { gs2326GVRPConfEntry 3 }

gs2326GVRPStatisticsTable OBJECT-TYPE
   SYNTAX      SEQUENCE OF GS2326GVRPStatisticsEntry
   MAX-ACCESS  not-accessible
   STATUS      current
   DESCRIPTION
       " "
   ::= { gs2326GVRP 2 }

gs2326GVRPStatisticsEntry OBJECT-TYPE
   SYNTAX      GS2326GVRPStatisticsEntry
   MAX-ACCESS  not-accessible
   STATUS      current
   DESCRIPTION
       ""
   INDEX    { gs2326GVRPStatisticsPort  }
   ::= { gs2326GVRPStatisticsTable 1 }

GS2326GVRPStatisticsEntry ::= SEQUENCE {
   gs2326GVRPStatisticsPort         Integer32,
   gs2326GVRPStatisticsJoinTxCnt    Counter32,
   gs2326GVRPStatisticsLeaveTxCnt   Counter32
}

gs2326GVRPStatisticsPort OBJECT-TYPE
   SYNTAX      Integer32(1..4095)
   MAX-ACCESS  not-accessible
   STATUS      current
   DESCRIPTION
       " "
   ::= { gs2326GVRPStatisticsEntry 1 }

gs2326GVRPStatisticsJoinTxCnt OBJECT-TYPE
   SYNTAX      Counter32
   MAX-ACCESS  read-only
   STATUS      current
   DESCRIPTION
       ""
   ::= { gs2326GVRPStatisticsEntry 2 }

gs2326GVRPStatisticsLeaveTxCnt OBJECT-TYPE
   SYNTAX      Counter32
   MAX-ACCESS  read-only
   STATUS      current
   DESCRIPTION
       ""
   ::= { gs2326GVRPStatisticsEntry 3 }


gs2326Mirroring                                             OBJECT IDENTIFIER ::= { gs2326Configuration 6 }

gs2326PortToMirrorOn OBJECT-TYPE
   SYNTAX      Integer32(0..10)
   MAX-ACCESS  read-write
   STATUS      current
   DESCRIPTION
       "default: 0 
        0: disable,
        range : 1 - port number. "
   ::= { gs2326Mirroring 1 }

gs2326MirrorTable OBJECT-TYPE
   SYNTAX      SEQUENCE OF GS2326MirrorEntry
   MAX-ACCESS  not-accessible
   STATUS      current
   DESCRIPTION
       " "
   ::= { gs2326Mirroring 2 }

gs2326MirrorEntry OBJECT-TYPE
   SYNTAX      GS2326MirrorEntry
   MAX-ACCESS  not-accessible
   STATUS      current
   DESCRIPTION
       ""
   INDEX    { gs2326MirrorPort  }
   ::= { gs2326MirrorTable 1 }

GS2326MirrorEntry ::= SEQUENCE {
   gs2326MirrorPort		Integer32,
   gs2326MirrorMode		INTEGER
}

gs2326MirrorPort OBJECT-TYPE
   SYNTAX      Integer32(1..4095)
   MAX-ACCESS  not-accessible
   STATUS      current
   DESCRIPTION
       " "
   ::= { gs2326MirrorEntry 1 }

gs2326MirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2326MirrorEntry 2 }

gs2326TrapEventSeverity                                             OBJECT IDENTIFIER ::= { gs2326Configuration 7 }

gs2326TrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 1 }

gs2326TrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2326TrapEventSeverity 2 }

gs2326TrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 3 }

gs2326TrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326TrapEventSeverity 4 }

gs2326TrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326TrapEventSeverity 5 }

gs2326TrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 6 }

gs2326TrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 7 }

gs2326TrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 8 }

gs2326TrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 9 }

gs2326TrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326TrapEventSeverity 10 }

gs2326TrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 11 }

gs2326TrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 12 }

gs2326TrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 13 }

gs2326TrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 14 }

gs2326TrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2326TrapEventSeverity 15 }

gs2326TrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 16 }

gs2326TrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 17 }

gs2326TrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 18 }

gs2326TrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326TrapEventSeverity 20 }

gs2326TrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326TrapEventSeverity 21 }



gs2326TrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326TrapEventSeverity 25 }

gs2326TrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326TrapEventSeverity 27 }
   
gs2326TrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326TrapEventSeverity 28 }

gs2326SMTP                                             OBJECT IDENTIFIER ::= { gs2326Configuration 8 }

gs2326SMTPMailServer OBJECT-TYPE
   SYNTAX      DisplayString
   MAX-ACCESS  read-write
   STATUS      current
   DESCRIPTION
       " Up to 47 characters describing email server. "
   ::= { gs2326SMTP 1 }

gs2326SMTPUserName OBJECT-TYPE
   SYNTAX      DisplayString
   MAX-ACCESS  read-write
   STATUS      current
   DESCRIPTION
       " Up to 47 characters describing user name. "
   ::= { gs2326SMTP 2 }

gs2326SMTPPassword OBJECT-TYPE
   SYNTAX      DisplayString
   MAX-ACCESS  read-write
   STATUS      current
   DESCRIPTION
       " Up to 47 characters describing password. "
   ::= { gs2326SMTP 3 }

gs2326SMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2326SMTP 4 }

gs2326SMTPSender OBJECT-TYPE
   SYNTAX      DisplayString
   MAX-ACCESS  read-write
   STATUS      current
   DESCRIPTION
       " Up to 47 characters describing sender. "
   ::= { gs2326SMTP 5 }

gs2326SMTPReturnPath OBJECT-TYPE
   SYNTAX      DisplayString
   MAX-ACCESS  read-write
   STATUS      current
   DESCRIPTION
       " Up to 47 characters describing return path. "
   ::= { gs2326SMTP 6 }

gs2326SMTPEmailAddress1 OBJECT-TYPE
   SYNTAX      DisplayString
   MAX-ACCESS  read-write
   STATUS      current
   DESCRIPTION
       " Up to 47 characters describing mail address. "
   ::= { gs2326SMTP 7 }

gs2326SMTPEmailAddress2 OBJECT-TYPE
   SYNTAX      DisplayString
   MAX-ACCESS  read-write
   STATUS      current
   DESCRIPTION
       " Up to 47 characters describing mail address. "
   ::= { gs2326SMTP 8 }

gs2326SMTPEmailAddress3 OBJECT-TYPE
   SYNTAX      DisplayString
   MAX-ACCESS  read-write
   STATUS      current
   DESCRIPTION
       " Up to 47 characters describing mail address. "
   ::= { gs2326SMTP 9 }

gs2326SMTPEmailAddress4 OBJECT-TYPE
   SYNTAX      DisplayString
   MAX-ACCESS  read-write
   STATUS      current
   DESCRIPTION
       " Up to 47 characters describing mail address. "
   ::= { gs2326SMTP 10 }

gs2326SMTPEmailAddress5 OBJECT-TYPE
   SYNTAX      DisplayString
   MAX-ACCESS  read-write
   STATUS      current
   DESCRIPTION
       " Up to 47 characters describing mail address. "
   ::= { gs2326SMTP 11 }

gs2326SMTPEmailAddress6 OBJECT-TYPE
   SYNTAX      DisplayString
   MAX-ACCESS  read-write
   STATUS      current
   DESCRIPTION
       " Up to 47 characters describing mail address. "
   ::= { gs2326SMTP 12 }


gs2326ACL                                                   OBJECT IDENTIFIER ::= { gs2326Configuration 9 }

gs2326ACLPortsConfTable OBJECT-TYPE
   SYNTAX      SEQUENCE OF GS2326ACLPortsConfEntry
   MAX-ACCESS  not-accessible
   STATUS      current
   DESCRIPTION
       " "
   ::= { gs2326ACL 1 }

gs2326ACLPortsConfEntry OBJECT-TYPE
   SYNTAX      GS2326ACLPortsConfEntry
   MAX-ACCESS  not-accessible
   STATUS      current
   DESCRIPTION
       ""
   INDEX    { gs2326ACLPortsConfPort  }
   ::= { gs2326ACLPortsConfTable 1 }

GS2326ACLPortsConfEntry ::= SEQUENCE {
   gs2326ACLPortsConfPort               Integer32,
   gs2326ACLPortsConfPolicyID           Integer32,
   gs2326ACLPortsConfAction             INTEGER,
   gs2326ACLPortsConfRateLimiterID      Integer32,
   gs2326ACLPortsConfPortRedirect       Integer32,
   gs2326ACLPortsConfMirror             INTEGER,
   gs2326ACLPortsConfLogging            INTEGER,
   gs2326ACLPortsConfShutdown           INTEGER,
   gs2326ACLPortsConfState              INTEGER,
   gs2326ACLPortsConfCounter            Counter32
}

gs2326ACLPortsConfPort OBJECT-TYPE
   SYNTAX      Integer32 (1..4095)
   MAX-ACCESS  not-accessible
   STATUS      current
   DESCRIPTION
       " "
   ::= { gs2326ACLPortsConfEntry 1 }

gs2326ACLPortsConfPolicyID OBJECT-TYPE
   SYNTAX      Integer32 (0..255)
   MAX-ACCESS  read-write
   STATUS      current
   DESCRIPTION
       "default: 0, range : 0 - 255 "
   ::= { gs2326ACLPortsConfEntry 2 }

gs2326ACLPortsConfAction OBJECT-TYPE
   SYNTAX      INTEGER { deny(0), permit(1) }
   MAX-ACCESS  read-write
   STATUS      current
   DESCRIPTION
       "default: 1,
        0: Deny
        1: Permit"
   ::= { gs2326ACLPortsConfEntry 3 }

gs2326ACLPortsConfRateLimiterID OBJECT-TYPE
   SYNTAX      Integer32 (0..12)
   MAX-ACCESS  read-write
   STATUS      current
   DESCRIPTION
       "default: 0,
        0: Disable
        range : 0 - 12 "
   ::= { gs2326ACLPortsConfEntry 4 }

gs2326ACLPortsConfPortRedirect OBJECT-TYPE
   SYNTAX      Integer32 (0..4095)
   MAX-ACCESS  read-write
   STATUS      current
   DESCRIPTION
       "default: 0
        0: Disable
        range : 0 - end port number "
   ::= { gs2326ACLPortsConfEntry 5 }

gs2326ACLPortsConfMirror OBJECT-TYPE
   SYNTAX      INTEGER { disable(0), enable(1) }
   MAX-ACCESS  read-write
   STATUS      current
   DESCRIPTION
       "default: 0
        0: Disable
        1: Enable "
   ::= { gs2326ACLPortsConfEntry 6 }

gs2326ACLPortsConfLogging OBJECT-TYPE
   SYNTAX      INTEGER { disable(0), enable(1) }
   MAX-ACCESS  read-write
   STATUS      current
   DESCRIPTION
       "default: 0
        0: Disable
        1: Enable "
   ::= { gs2326ACLPortsConfEntry 7 }

gs2326ACLPortsConfShutdown OBJECT-TYPE
   SYNTAX      INTEGER { disable(0), enable(1) }
   MAX-ACCESS  read-write
   STATUS      current
   DESCRIPTION
       "default: 0
        0: Disable
        1: Enable "
   ::= { gs2326ACLPortsConfEntry 8 }
   
gs2326ACLPortsConfState OBJECT-TYPE
   SYNTAX      INTEGER { disable(0), enable(1) }
   MAX-ACCESS  read-write
   STATUS      current
   DESCRIPTION
       "default: 1
        0: Disable
        1: Enable "
   ::= { gs2326ACLPortsConfEntry 9 }

gs2326ACLPortsConfCounter OBJECT-TYPE
   SYNTAX      Counter32
   MAX-ACCESS  read-only
   STATUS      current
   DESCRIPTION
       "Counts the number of frames that match this ACE. "
   ::= { gs2326ACLPortsConfEntry 10 }


gs2326ACLRateLimiterTable OBJECT-TYPE
   SYNTAX      SEQUENCE OF GS2326ACLRateLimiterEntry
   MAX-ACCESS  not-accessible
   STATUS      current
   DESCRIPTION
       " "
   ::= { gs2326ACL 2 }

gs2326ACLRateLimiterEntry OBJECT-TYPE
   SYNTAX      GS2326ACLRateLimiterEntry
   MAX-ACCESS  not-accessible
   STATUS      current
   DESCRIPTION
       ""
   INDEX    { gs2326ACLRateLimiterID  }
   ::= { gs2326ACLRateLimiterTable 1 }

GS2326ACLRateLimiterEntry ::= SEQUENCE {
   gs2326ACLRateLimiterID       Integer32,
   gs2326ACLRateLimiterUnit     INTEGER,
   gs2326ACLRateLimiterRate     Integer32
}

gs2326ACLRateLimiterID OBJECT-TYPE
   SYNTAX      Integer32 (1..12)
   MAX-ACCESS  not-accessible
   STATUS      current
   DESCRIPTION
       " Rate Limiter ID.
         range : 1-12 "
   ::= { gs2326ACLRateLimiterEntry 1 }

gs2326ACLRateLimiterUnit OBJECT-TYPE
   SYNTAX      INTEGER { pps(0), kbps(1) }
   MAX-ACCESS  read-write
   STATUS      current
   DESCRIPTION
       "default: 0, 
        0: pps
        1: kbps"
   ::= { gs2326ACLRateLimiterEntry 2 }

gs2326ACLRateLimiterRate OBJECT-TYPE
   SYNTAX      Integer32(0..3276700)
   MAX-ACCESS  read-write
   STATUS      current
   DESCRIPTION
       "default: 1, 
        range : <0-3276700> pps
                <0-10000> kbps"
   ::= { gs2326ACLRateLimiterEntry 3 }


gs2326ACLACE                                          OBJECT IDENTIFIER ::= { gs2326ACL 3 }

gs2326ACLACECreate OBJECT-TYPE
   SYNTAX       INTEGER { none(0), create(1) }
   MAX-ACCESS   read-write
   STATUS       current
   DESCRIPTION
       "default: 0
        0 : None  (read only)
        1 : Create an ACE entry"
   ::= { gs2326ACLACE 1 }

gs2326ACLACETable OBJECT-TYPE
   SYNTAX      SEQUENCE OF GS2326ACLACEEntry
   MAX-ACCESS  not-accessible
   STATUS      current
   DESCRIPTION
       " Create ACL ACE entry. "
   ::= { gs2326ACLACE 2 }

gs2326ACLACEEntry OBJECT-TYPE
   SYNTAX      GS2326ACLACEEntry
   MAX-ACCESS  not-accessible
   STATUS      current
   DESCRIPTION
       ""
   INDEX    { gs2326ACLACEIndex  }
   ::= { gs2326ACLACETable 1 }

GS2326ACLACEEntry ::= SEQUENCE {
   gs2326ACLACEIndex                Integer32,
   gs2326ACLACEID                   Integer32,
   gs2326ACLACENextID               Integer32,
   gs2326ACLACEIngressPort          DisplayString,
   gs2326ACLACEPortPolicyNumber     Integer32,
   
   gs2326ACLACEPortPolicyBitmask    Integer32,
   gs2326ACLACEFrameType            INTEGER,
   gs2326ACLACEAction               INTEGER,
   gs2326ACLACEDenyPortRedirect     DisplayString,
   gs2326ACLACELogging              INTEGER,
   
   gs2326ACLACEMirror               INTEGER,
   gs2326ACLACERateLimiter          Integer32,
   gs2326ACLACEShutdown             INTEGER,
   gs2326ACLACEVLAN8021QTagged      INTEGER,
   gs2326ACLACEVLANTagPriority      Integer32,
   
   gs2326ACLACEVLANVID              Integer32,
   gs2326ACLACEEtherType            Integer32,
   gs2326ACLACESMAC                 DisplayString,
   gs2326ACLACEDMACType             INTEGER,
   gs2326ACLACEDMAC                 DisplayString,
   
   gs2326ACLACEArpOpcode            INTEGER,
   gs2326ACLACEArpFlagsRequestReply INTEGER,
   gs2326ACLACEArpFlagsArpSmac      INTEGER,
   gs2326ACLACEArpFlagsRarpDmac     INTEGER,
   gs2326ACLACEArpFlagsLength       INTEGER,
   
   gs2326ACLACEArpFlagsIp           INTEGER,
   gs2326ACLACEArpFlagsEthernet     INTEGER,
   gs2326ACLACESIPType              INTEGER,
   gs2326ACLACESIPIPAddress         IpAddress,                      
   gs2326ACLACESIPNetworkPrefix     Integer32,
   
   gs2326ACLACEDIPType              INTEGER,
   gs2326ACLACEDIPIPAddress         IpAddress,                      
   gs2326ACLACEDIPNetworkPrefix     Integer32,
   
   gs2326ACLACEIPProtocol           Integer32,
   gs2326ACLACEIPFlagsTTL           INTEGER,
   gs2326ACLACEIPFlagsOptions       INTEGER,
   gs2326ACLACEIPFlagsFragment      INTEGER,
   gs2326ACLACEICMPType             Integer32,
   
   gs2326ACLACEICMPCode             Integer32,
   gs2326ACLACESourcePortMin        Integer32,
   gs2326ACLACESourcePortMax        Integer32,
   gs2326ACLACEDestPortMin          Integer32,
   gs2326ACLACEDestPortMax          Integer32,
   
   gs2326ACLACETCPFlagsFin          INTEGER,
   gs2326ACLACETCPFlagsSyn          INTEGER,
   gs2326ACLACETCPFlagsRst          INTEGER,
   gs2326ACLACETCPFlagsPsh          INTEGER,
   gs2326ACLACETCPFlagsAck          INTEGER,
   
   gs2326ACLACETCPFlagsUrg          INTEGER,
   
   gs2326ACLACERowStatus            INTEGER
}

gs2326ACLACEIndex OBJECT-TYPE
   SYNTAX      Integer32(1..256)
   MAX-ACCESS  not-accessible
   STATUS      current
   DESCRIPTION
       " "
   ::= { gs2326ACLACEEntry 1 }

gs2326ACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2326ACLACEEntry 2 }

gs2326ACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2326ACLACEEntry 3 }

gs2326ACLACEIngressPort OBJECT-TYPE
   SYNTAX      DisplayString
   MAX-ACCESS  read-write
   STATUS      current
   DESCRIPTION
       " Indicates the ingress port of the ACE. Possible values are: 
         All: The ACE will match all ingress port. 
         Port: The ACE will match a specific ingress port.Format: 1,3,6."
   ::= { gs2326ACLACEEntry 4 }

gs2326ACLACEPortPolicyNumber OBJECT-TYPE
   SYNTAX      Integer32(0..255)
   MAX-ACCESS  read-write
   STATUS      current
   DESCRIPTION
       " policy value.
         range : 0 - 255. "
   ::= { gs2326ACLACEEntry 5 }
   
gs2326ACLACEPortPolicyBitmask OBJECT-TYPE
   SYNTAX      Integer32(0..255)
   MAX-ACCESS  read-write
   STATUS      current
   DESCRIPTION
       " policy bitmask.
         range : 0 - 255(0xff). "
   ::= { gs2326ACLACEEntry 6 }

gs2326ACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2326ACLACEEntry 7 }

gs2326ACLACEAction OBJECT-TYPE
   SYNTAX      INTEGER { deny(0), permit(1) }
   MAX-ACCESS  read-write
   STATUS      current
   DESCRIPTION
       "default: 1,
        0: Deny
        1: Permit"
   ::= { gs2326ACLACEEntry 8 }

gs2326ACLACEDenyPortRedirect OBJECT-TYPE
   SYNTAX      DisplayString
   MAX-ACCESS  read-write
   STATUS      current
   DESCRIPTION
       " Frames that hit the ACE are redirected to the port number specified here.  
         Disabled: indicates that the port redirect operation is disabled. 
         Port Format: 1,3,6."
   ::= { gs2326ACLACEEntry 9 }

gs2326ACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2326ACLACEEntry 10 }

gs2326ACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { gs2326ACLACEEntry 11 }

gs2326ACLACERateLimiter OBJECT-TYPE
   SYNTAX      Integer32(0..12)
   MAX-ACCESS  read-write
   STATUS      current
   DESCRIPTION
       "default: 0,
        0: Disable
        range : 0 - 12 "
   ::= { gs2326ACLACEEntry 12 }

gs2326ACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2326ACLACEEntry 13 }

gs2326ACLACEVLAN8021QTagged OBJECT-TYPE
   SYNTAX      INTEGER { disable(0), enable(1), any(2) }
   MAX-ACCESS  read-write
   STATUS      current
   DESCRIPTION
       "Specify whether frames can hit the action according to the 802.1Q tagged. 
        default: 2,
        0: disable - Untagged frame only.
        1: enable - Tagged frame only.
        2: Any - Any value is allowed. "
   ::= { gs2326ACLACEEntry 14 }

gs2326ACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2326ACLACEEntry 15 }

gs2326ACLACEVLANVID OBJECT-TYPE
   SYNTAX      Integer32(0..4094)
   MAX-ACCESS  read-write
   STATUS      current
   DESCRIPTION
       "Specify the VLAN ID filter for this ACE.
        The vid can't be set when 802.1Q Tagged is disabled. 
        default: 0,
        0: Any - No VLAN ID filter is specified.
        range : 0 - 4094 "
   ::= { gs2326ACLACEEntry 16 }

gs2326ACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2326ACLACEEntry 17 }

gs2326ACLACESMAC OBJECT-TYPE
   SYNTAX      DisplayString
   MAX-ACCESS  read-write
   STATUS      current
   DESCRIPTION
       " Configure source MAC address for this ACE.
         <mac-address>: A frame that hits this ACE matches this source MAC address value. 
         Any: Don't care."
   ::= { gs2326ACLACEEntry 18 }

gs2326ACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { gs2326ACLACEEntry 19 }

gs2326ACLACEDMAC OBJECT-TYPE
   SYNTAX      DisplayString
   MAX-ACCESS  read-write
   STATUS      current
   DESCRIPTION
       " Configure destination MAC address for this ACE. 
         <mac-address>: A frame that hits this ACE matches this destination MAC address value.            
         Any: Don't care.
         Broadcast: Frame must be broadcast.
         Unicast: Frame must be unicast.
         Multicast: Frame must be multicast. "
   ::= { gs2326ACLACEEntry 20 }

gs2326ACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2326ACLACEEntry 21 }

gs2326ACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2326ACLACEEntry 22 }

gs2326ACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2326ACLACEEntry 23 }   

gs2326ACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2326ACLACEEntry 24 }

gs2326ACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2326ACLACEEntry 25 }

gs2326ACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2326ACLACEEntry 26 }

gs2326ACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2326ACLACEEntry 27 }
   
gs2326ACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { gs2326ACLACEEntry 28 }   
   
gs2326ACLACESIPIPAddress OBJECT-TYPE
   SYNTAX      IpAddress
   MAX-ACCESS  read-write
   STATUS      current
   DESCRIPTION
       "A frame that hits this ACE matches this source IP address value."
   ::= { gs2326ACLACEEntry 29 }      
   
gs2326ACLACESIPNetworkPrefix OBJECT-TYPE
   SYNTAX      Integer32(0..32)
   MAX-ACCESS  read-write
   STATUS      current
   DESCRIPTION
       "Network prefix.
        default: 32,
        0: No data.
        range : 1 - 32"
   ::= { gs2326ACLACEEntry 30 }   
   

gs2326ACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2326ACLACEEntry 32 }   
   
gs2326ACLACEDIPIPAddress OBJECT-TYPE
   SYNTAX      IpAddress
   MAX-ACCESS  read-write
   STATUS      current
   DESCRIPTION
       "A frame that hits this ACE matches this destination IP address value."
   ::= { gs2326ACLACEEntry 33 }      
   
gs2326ACLACEDIPNetworkPrefix OBJECT-TYPE
   SYNTAX      Integer32(0..32)
   MAX-ACCESS  read-write
   STATUS      current
   DESCRIPTION
       "Network prefix.
        default: 32,
        0: No data.
        range : 1 - 32"
   ::= { gs2326ACLACEEntry 34 }  
   
   
gs2326ACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { gs2326ACLACEEntry 36 } 

gs2326ACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2326ACLACEEntry 37 }   
   
gs2326ACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2326ACLACEEntry 38 }

gs2326ACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2326ACLACEEntry 39 }

gs2326ACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { gs2326ACLACEEntry 40 }   

gs2326ACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2326ACLACEEntry 41 } 

gs2326ACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2326ACLACEEntry 42 }     
   
gs2326ACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2326ACLACEEntry 43 } 
      
gs2326ACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { gs2326ACLACEEntry 44 }     

gs2326ACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { gs2326ACLACEEntry 45 }

gs2326ACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2326ACLACEEntry 46 }

gs2326ACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2326ACLACEEntry 47 }

gs2326ACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2326ACLACEEntry 48 }

gs2326ACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2326ACLACEEntry 49 }

gs2326ACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2326ACLACEEntry 50 }

gs2326ACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2326ACLACEEntry 51 }

gs2326ACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2326ACLACEEntry 66 }


gs2326ACLACEClear OBJECT-TYPE
   SYNTAX       INTEGER { noAction(0), clear(1) }
   MAX-ACCESS   read-write
   STATUS       current
   DESCRIPTION
       "default: 0
        0 : No action
        1 : Clear all ACL counters."
   ::= { gs2326ACLACE 3 }

gs2326ACLACEMoveACEID OBJECT-TYPE
   SYNTAX       Integer32(0..256)
   MAX-ACCESS   read-write
   STATUS       current
   DESCRIPTION
       "Move ACE,
        default: 0
        ACE ID must be exist.
        range : 1 - 256."
   ::= { gs2326ACLACE 4 }

gs2326ACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2326ACLACE 5 }

gs2326ACLACEStatusTable OBJECT-TYPE
   SYNTAX      SEQUENCE OF GS2326ACLACEStatusEntry
   MAX-ACCESS  not-accessible
   STATUS      current
   DESCRIPTION
       " ACL ACE Status entry. "
   ::= { gs2326ACLACE 6 }

gs2326ACLACEStatusEntry OBJECT-TYPE
   SYNTAX      GS2326ACLACEStatusEntry
   MAX-ACCESS  not-accessible
   STATUS      current
   DESCRIPTION
       ""
   INDEX    { gs2326ACLACEStatusIndex  }
   ::= { gs2326ACLACEStatusTable 1 }

GS2326ACLACEStatusEntry ::= SEQUENCE {
   gs2326ACLACEStatusIndex          Integer32,
   gs2326ACLACEStatusUser           DisplayString,
   gs2326ACLACEStatusID             Integer32,
   gs2326ACLACEStatusIngressPort    DisplayString,
   gs2326ACLACEStatusFrameType      DisplayString,
   gs2326ACLACEStatusAction         DisplayString,
   gs2326ACLACEStatusRateLimiter    DisplayString,
   gs2326ACLACEStatusPortCopy       DisplayString,
   gs2326ACLACEStatusMirror         DisplayString,
   gs2326ACLACEStatusCPU            DisplayString,
   gs2326ACLACEStatusCounter        Counter32,
   gs2326ACLACEStatusConflict       DisplayString
}

gs2326ACLACEStatusIndex OBJECT-TYPE
   SYNTAX      Integer32(1..256)
   MAX-ACCESS  not-accessible
   STATUS      current
   DESCRIPTION
       " "
   ::= { gs2326ACLACEStatusEntry 1 }

gs2326ACLACEStatusUser OBJECT-TYPE
   SYNTAX      DisplayString
   MAX-ACCESS  read-only
   STATUS      current
   DESCRIPTION
       " Indicates the ACL user. 
         S : Static.  
         IPMG : IP Management.  
         IPSG : IP Source Guard.  
         IPMC : IPMC.  
         ARPI : Arp Inspection.  
         UPnP : UPnP.  
         DHCP : DHCP. "
   ::= { gs2326ACLACEStatusEntry 2 }

gs2326ACLACEStatusID OBJECT-TYPE
   SYNTAX      Integer32(1..256)
   MAX-ACCESS  read-only
   STATUS      current
   DESCRIPTION
       " ACE ID.
         range : 1 - 256. "
   ::= { gs2326ACLACEStatusEntry 3 }

gs2326ACLACEStatusIngressPort OBJECT-TYPE
   SYNTAX      DisplayString
   MAX-ACCESS  read-only
   STATUS      current
   DESCRIPTION
       " Indicates the ingress port of the ACE. Possible values are: 
         All: The ACE will match all ingress port. 
         Port: The ACE will match a specific ingress port. "
   ::= { gs2326ACLACEStatusEntry 4 }

gs2326ACLACEStatusFrameType OBJECT-TYPE
   SYNTAX      DisplayString
   MAX-ACCESS  read-only
   STATUS      current
   DESCRIPTION
       " Indicates the frame type of the ACE. "
   ::= { gs2326ACLACEStatusEntry 5 }

gs2326ACLACEStatusAction OBJECT-TYPE
   SYNTAX      DisplayString
   MAX-ACCESS  read-only
   STATUS      current
   DESCRIPTION
       " Indicates the forwarding action of the ACE. "
   ::= { gs2326ACLACEStatusEntry 6 }

gs2326ACLACEStatusRateLimiter OBJECT-TYPE
   SYNTAX      DisplayString
   MAX-ACCESS  read-only
   STATUS      current
   DESCRIPTION
       " Indicates the rate limiter number of the ACE. "
   ::= { gs2326ACLACEStatusEntry 7 }

gs2326ACLACEStatusPortCopy OBJECT-TYPE
   SYNTAX      DisplayString
   MAX-ACCESS  read-only
   STATUS      current
   DESCRIPTION
       " Indicates the port redirect operation of the ACE. Frames matching the ACE are redirected to the port number. "
   ::= { gs2326ACLACEStatusEntry 8 }

gs2326ACLACEStatusMirror OBJECT-TYPE
   SYNTAX      DisplayString
   MAX-ACCESS  read-only
   STATUS      current
   DESCRIPTION
       " Specify the mirror operation of this port. "
   ::= { gs2326ACLACEStatusEntry 9 }

gs2326ACLACEStatusCPU OBJECT-TYPE
   SYNTAX      DisplayString
   MAX-ACCESS  read-only
   STATUS      current
   DESCRIPTION
       " Forward packet that matched the specific ACE to CPU. "
   ::= { gs2326ACLACEStatusEntry 10 }

gs2326ACLACEStatusCounter OBJECT-TYPE
   SYNTAX      Counter32
   MAX-ACCESS  read-only
   STATUS      current
   DESCRIPTION
       " The counter indicates the number of times the ACE was hit by a frame. "
   ::= { gs2326ACLACEStatusEntry 11 }
   
gs2326ACLACEStatusConflict OBJECT-TYPE
   SYNTAX      DisplayString
   MAX-ACCESS  read-only
   STATUS      current
   DESCRIPTION
       " Indicates the hardware status of the specific ACE. The specific ACE is not applied to the hardware due to hardware limitations. "
   ::= { gs2326ACLACEStatusEntry 12 }

gs2326LoopProtection                                                  OBJECT IDENTIFIER ::= { gs2326Configuration 12 }

gs2326LoopProtectionConfig                                            OBJECT IDENTIFIER ::= { gs2326LoopProtection 1 }

gs2326LoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2326LoopProtectionConfig 1 }
   
gs2326LoopProtectionTranmisstionTime OBJECT-TYPE
   SYNTAX      Integer32(1..10)
   MAX-ACCESS  read-write
   STATUS      current
   DESCRIPTION
       "Configure loop protection transmit interval.
        default: 5,
        range: 1-10. "
   ::= { gs2326LoopProtectionConfig 2 }
   
gs2326LoopProtectionShutdownTime OBJECT-TYPE
   SYNTAX      Integer32(0..604800)
   MAX-ACCESS  read-write
   STATUS      current
   DESCRIPTION
       "Configure loop protection shutdown time.
        default: 180,
        range: 0-604800. "
   ::= { gs2326LoopProtectionConfig 3 }

gs2326LoopProtectionConfigurationTable OBJECT-TYPE
   SYNTAX      SEQUENCE OF GS2326LoopProtectionConfigurationEntry
   MAX-ACCESS  not-accessible
   STATUS      current
   DESCRIPTION
       " Show Loop Protection configurations. "
   ::= { gs2326LoopProtectionConfig 4 }

gs2326LoopProtectionConfigurationEntry OBJECT-TYPE
   SYNTAX      GS2326LoopProtectionConfigurationEntry
   MAX-ACCESS  not-accessible
   STATUS      current
   DESCRIPTION
       ""
   INDEX    { gs2326LoopProtectionConfPort  }
   ::= { gs2326LoopProtectionConfigurationTable 1 }

GS2326LoopProtectionConfigurationEntry ::= SEQUENCE {
   gs2326LoopProtectionConfPort	    Integer32,
   gs2326LoopProtectionConfEnable	INTEGER,
   gs2326LoopProtectionConfAction	INTEGER,
   gs2326LoopProtectionConfTxmode	INTEGER
}

gs2326LoopProtectionConfPort OBJECT-TYPE
   SYNTAX      Integer32(1..4095)
   MAX-ACCESS  not-accessible
   STATUS      current
   DESCRIPTION
       " port, range : 1 - port number. "
   ::= { gs2326LoopProtectionConfigurationEntry 1 }

gs2326LoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2326LoopProtectionConfigurationEntry 2 }

gs2326LoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2326LoopProtectionConfigurationEntry 3 }
   
gs2326LoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2326LoopProtectionConfigurationEntry 4 }
   
gs2326LoopProtectionStatusTable OBJECT-TYPE
   SYNTAX      SEQUENCE OF GS2326LoopProtectionStatusEntry
   MAX-ACCESS  not-accessible
   STATUS      current
   DESCRIPTION
       " Show Loop Protection Status. "
   ::= { gs2326LoopProtection 2 }

gs2326LoopProtectionStatusEntry OBJECT-TYPE
   SYNTAX      GS2326LoopProtectionStatusEntry
   MAX-ACCESS  not-accessible
   STATUS      current
   DESCRIPTION
       ""
   INDEX    { gs2326LoopProtectionStatusPort  }
   ::= { gs2326LoopProtectionStatusTable 1 }

GS2326LoopProtectionStatusEntry ::= SEQUENCE {
   gs2326LoopProtectionStatusPort	       Integer32,
   gs2326LoopProtectionStatusAction	       DisplayString,
   gs2326LoopProtectionStatusTransmit	   DisplayString,
   gs2326LoopProtectionStatusLoops	       Integer32,
   gs2326LoopProtectionStatusStatus	       DisplayString,
   gs2326LoopProtectionStatusLoop	       DisplayString,
   gs2326LoopProtectionStatusTimeLastLoop  DisplayString
}

gs2326LoopProtectionStatusPort OBJECT-TYPE
   SYNTAX      Integer32(1..4095)
   MAX-ACCESS  not-accessible
   STATUS      current
   DESCRIPTION
       " port, range : 1 - port number. "
   ::= { gs2326LoopProtectionStatusEntry 1 }
   
gs2326LoopProtectionStatusAction OBJECT-TYPE
   SYNTAX      DisplayString
   MAX-ACCESS  read-only
   STATUS      current
   DESCRIPTION
       " The currently configured port action. "
   ::= { gs2326LoopProtectionStatusEntry 2 }
   
gs2326LoopProtectionStatusTransmit OBJECT-TYPE
   SYNTAX      DisplayString
   MAX-ACCESS  read-only
   STATUS      current
   DESCRIPTION
       " The currently configured port transmit mode. "
   ::= { gs2326LoopProtectionStatusEntry 3 }
   
gs2326LoopProtectionStatusLoops OBJECT-TYPE
   SYNTAX      Integer32(0..1000000)
   MAX-ACCESS  read-only
   STATUS      current
   DESCRIPTION
       " The number of loops detected on this port. "
   ::= { gs2326LoopProtectionStatusEntry 4 }
   
gs2326LoopProtectionStatusStatus OBJECT-TYPE
   SYNTAX      DisplayString
   MAX-ACCESS  read-only
   STATUS      current
   DESCRIPTION
       " The current loop protection status of the port. "
   ::= { gs2326LoopProtectionStatusEntry 5 }
   
gs2326LoopProtectionStatusLoop OBJECT-TYPE
   SYNTAX      DisplayString
   MAX-ACCESS  read-only
   STATUS      current
   DESCRIPTION
       " Whether a loop is currently detected on the port. "
   ::= { gs2326LoopProtectionStatusEntry 6 }

gs2326LoopProtectionStatusTimeLastLoop OBJECT-TYPE
   SYNTAX      DisplayString
   MAX-ACCESS  read-only
   STATUS      current
   DESCRIPTION
       " The time of the last loop event detected. "
   ::= { gs2326LoopProtectionStatusEntry 7 }

gs2326Qos                                                             OBJECT IDENTIFIER ::= { gs2326Configuration 14 }

gs2326QosPortClassification                                           OBJECT IDENTIFIER ::= { gs2326Qos 1 }

gs2326QosPortClassificationTable OBJECT-TYPE
   SYNTAX      SEQUENCE OF GS2326QosPortClassificationEntry
   MAX-ACCESS  not-accessible
   STATUS      current
   DESCRIPTION
       " QoS Ingress Port Classification . "
   ::= { gs2326QosPortClassification  1 }

gs2326QosPortClassificationEntry OBJECT-TYPE
   SYNTAX      GS2326QosPortClassificationEntry
   MAX-ACCESS  not-accessible
   STATUS      current
   DESCRIPTION
       ""
   INDEX    { gs2326QosPortClassificationPort  }
   ::= { gs2326QosPortClassificationTable 1 }

GS2326QosPortClassificationEntry ::= SEQUENCE {
   gs2326QosPortClassificationPort	        Integer32,
   gs2326QosPortClassificationQoSclass       Integer32,
   gs2326QosPortClassificationDPlevel	    Integer32,
   gs2326QosPortClassificationPCP	        Integer32,
   gs2326QosPortClassificationDEI	        INTEGER,
   gs2326QosPortClassificationTagClass	    INTEGER,
   gs2326QosPortClassificationDSCPBased    INTEGER,
   gs2326QosPortClassificationAddressMode  INTEGER
}

gs2326QosPortClassificationPort OBJECT-TYPE
   SYNTAX      Integer32(1..4095)
   MAX-ACCESS  not-accessible
   STATUS      current
   DESCRIPTION
       " port, range : 1 - port number. "
   ::= { gs2326QosPortClassificationEntry 1 }

gs2326QosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2326QosPortClassificationEntry 2 }

gs2326QosPortClassificationDPlevel OBJECT-TYPE
   SYNTAX      Integer32(0|1)
   MAX-ACCESS  read-write
   STATUS      current
   DESCRIPTION
       " DP level for frames not classified in any other way.
         range: 0-1,
         default: 0. "
   ::= { gs2326QosPortClassificationEntry 3 }

gs2326QosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2326QosPortClassificationEntry 4 }

gs2326QosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2326QosPortClassificationEntry 5 }

gs2326QosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2326QosPortClassificationEntry 6 }

gs2326QosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2326QosPortClassificationEntry 7 }

gs2326QosPortClassificationAddressMode OBJECT-TYPE
   SYNTAX      INTEGER { source(0), destination(1) }
   MAX-ACCESS  read-write
   STATUS      current
   DESCRIPTION
      "The IP/MAC address mode specifying whether the QCL classification
       must be based on source (SMAC/SIP) or destination (DMAC/DIP)
       addresses on this port.
        0: source,
        1: destination,
        default: source. "
   ::= { gs2326QosPortClassificationEntry 8 }

gs2326QoSIngressPortTagClassificationTable OBJECT-TYPE
   SYNTAX      SEQUENCE OF GS2326QoSIngressPortTagClassificationEntry
   MAX-ACCESS  not-accessible
   STATUS      current
   DESCRIPTION
       " Show QoS Ingress Port Tag Classification. "
   ::= { gs2326QosPortClassification 2 }

gs2326QoSIngressPortTagClassificationEntry OBJECT-TYPE
   SYNTAX      GS2326QoSIngressPortTagClassificationEntry
   MAX-ACCESS  not-accessible
   STATUS      current
   DESCRIPTION
       ""
   INDEX    { gs2326QoSIngressPortTagClassificationPort, gs2326QoSIngressPortTagPCP, gs2326QoSIngressPortTagDEI  }
   ::= { gs2326QoSIngressPortTagClassificationTable 1 }

GS2326QoSIngressPortTagClassificationEntry ::= SEQUENCE {
   gs2326QoSIngressPortTagClassificationPort	Integer32,
   gs2326QoSIngressPortTagPCP					INTEGER,
   gs2326QoSIngressPortTagDEI					INTEGER,
   gs2326QoSIngressPortTagQosClass				Integer32,
   gs2326QoSIngressPortTagDPLevel				Integer32
}

gs2326QoSIngressPortTagClassificationPort OBJECT-TYPE
   SYNTAX      Integer32(1..4095)
   MAX-ACCESS  not-accessible
   STATUS      current
   DESCRIPTION
       " port, range : 1 - port number. "
   ::= { gs2326QoSIngressPortTagClassificationEntry 1 }

gs2326QoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8, 
         PCP0:1, PCP1:2...  "
   ::= { gs2326QoSIngressPortTagClassificationEntry 2 }

gs2326QoSIngressPortTagDEI OBJECT-TYPE
   SYNTAX      INTEGER { dei0(1), dei1(2) }
   MAX-ACCESS  not-accessible
   STATUS      current
   DESCRIPTION
       " range: 1-2,
         DEI0:1, DEI1:2. "
   ::= { gs2326QoSIngressPortTagClassificationEntry 3 }

gs2326QoSIngressPortTagQosClass OBJECT-TYPE
   SYNTAX      Integer32 (0..7)
   MAX-ACCESS  read-write
   STATUS      current
   DESCRIPTION
       " range: 0-7.  "
   ::= { gs2326QoSIngressPortTagClassificationEntry 4 }
   
gs2326QoSIngressPortTagDPLevel OBJECT-TYPE
   SYNTAX      Integer32 (0|1)
   MAX-ACCESS  read-write
   STATUS      current
   DESCRIPTION
       " range: 0-1.  "
   ::= { gs2326QoSIngressPortTagClassificationEntry 5 }


gs2326QosPortPolicingTable OBJECT-TYPE
   SYNTAX      SEQUENCE OF GS2326QosPortPolicingEntry
   MAX-ACCESS  not-accessible
   STATUS      current
   DESCRIPTION
       "  configure the Policer settings for all switch ports. "
   ::= { gs2326Qos  2 }

gs2326QosPortPolicingEntry OBJECT-TYPE
   SYNTAX      GS2326QosPortPolicingEntry
   MAX-ACCESS  not-accessible
   STATUS      current
   DESCRIPTION
       ""
   INDEX    { gs2326QosPortPolicingPort  }
   ::= { gs2326QosPortPolicingTable 1 }

GS2326QosPortPolicingEntry ::= SEQUENCE {
   gs2326QosPortPolicingPort	        Integer32,
   gs2326QosPortPolicingMode           INTEGER,
   gs2326QosPortPolicingRate	        Integer32,
   gs2326QosPortPolicingUnit	        INTEGER,
   gs2326QosPortPolicingFlowControl	INTEGER
}

gs2326QosPortPolicingPort OBJECT-TYPE
   SYNTAX      Integer32 (1..4095)
   MAX-ACCESS  not-accessible
   STATUS      current
   DESCRIPTION
       " port, range : 1 - port number. "
   ::= { gs2326QosPortPolicingEntry 1 }

gs2326QosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2326QosPortPolicingEntry 2 }

gs2326QosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2326QosPortPolicingEntry 3 }

gs2326QosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2326QosPortPolicingEntry 4 }

gs2326QosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2326QosPortPolicingEntry 5 }

gs2326QosPortScheduler                                           OBJECT IDENTIFIER ::= { gs2326Qos 3 }

gs2326QosPortSchedulerModeTable OBJECT-TYPE
   SYNTAX      SEQUENCE OF GS2326QosPortSchedulerModeEntry
   MAX-ACCESS  not-accessible
   STATUS      current
   DESCRIPTION
       " configure the basic QoS Port Scheduler Mode settings for all switch ports. "
   ::= { gs2326QosPortScheduler  1 }

gs2326QosPortSchedulerModeEntry OBJECT-TYPE
   SYNTAX      GS2326QosPortSchedulerModeEntry
   MAX-ACCESS  not-accessible
   STATUS      current
   DESCRIPTION
       ""
   INDEX    { gs2326QosSchedulerModePort  }
   ::= { gs2326QosPortSchedulerModeTable 1 }

GS2326QosPortSchedulerModeEntry ::= SEQUENCE {
   gs2326QosSchedulerModePort	                Integer32,
   gs2326QosSchedulerMode                        INTEGER,
   gs2326QosSchedulerShaper	                    INTEGER,
   gs2326QosSchedulerShaperRate	                Integer32
}

gs2326QosSchedulerModePort OBJECT-TYPE
   SYNTAX      Integer32 (1..4095)
   MAX-ACCESS  not-accessible
   STATUS      current
   DESCRIPTION
       " port, range : 1 - port number. "
   ::= { gs2326QosPortSchedulerModeEntry 1 }

gs2326QosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2326QosPortSchedulerModeEntry 2 }

gs2326QosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2326QosPortSchedulerModeEntry 3 }

gs2326QosSchedulerShaperRate OBJECT-TYPE
   SYNTAX      Integer32(100..1000000)
   MAX-ACCESS  read-write
   STATUS      current
   DESCRIPTION
       " Controls the rate for the port shaper.
         range: 100-1000000
         default: 500 kbps. "
   ::= { gs2326QosPortSchedulerModeEntry 4 }

gs2326QosPortSchedulerTable OBJECT-TYPE
   SYNTAX      SEQUENCE OF GS2326QosPortSchedulerEntry
   MAX-ACCESS  not-accessible
   STATUS      current
   DESCRIPTION
       " Show Qos Port Scheduler. "
   ::= { gs2326QosPortScheduler 2 }

gs2326QosPortSchedulerEntry OBJECT-TYPE
   SYNTAX      GS2326QosPortSchedulerEntry
   MAX-ACCESS  not-accessible
   STATUS      current
   DESCRIPTION
       ""
   INDEX    { gs2326QosSchedulerPort, gs2326QosSchedulerPortQueue}
   ::= { gs2326QosPortSchedulerTable 1 }

GS2326QosPortSchedulerEntry ::= SEQUENCE {
   gs2326QosSchedulerPort						Integer32,
   gs2326QosSchedulerPortQueue					INTEGER,
   gs2326QosSchedulerPortQueueShaper				INTEGER,
   gs2326QosSchedulerPortQueueShaperRate			Integer32,
   gs2326QosSchedulerPortQueueShaperExcess		INTEGER,
   gs2326QosSchedulerPortQueueSchedulerWeight	Integer32,
   gs2326QosSchedulerPortQueueSchedulerPercent	DisplayString
}

gs2326QosSchedulerPort OBJECT-TYPE
   SYNTAX      Integer32 (1..4095)
   MAX-ACCESS  not-accessible
   STATUS      current
   DESCRIPTION
       " port, range : 1 - port number. "
   ::= { gs2326QosPortSchedulerEntry 1 }

gs2326QosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2326QosPortSchedulerEntry 2 }
   
gs2326QosSchedulerPortQueueShaper OBJECT-TYPE
   SYNTAX      INTEGER { disable(0), enable(1) }
   MAX-ACCESS  read-write
   STATUS      current
   DESCRIPTION
       " 0: disable  1:enable,
         default: 0.  "
   ::= { gs2326QosPortSchedulerEntry 3 }
   
gs2326QosSchedulerPortQueueShaperRate OBJECT-TYPE
   SYNTAX      Integer32(100..1000000)
   MAX-ACCESS  read-write
   STATUS      current
   DESCRIPTION
       " range: 100..1000000 kbps.  "
   ::= { gs2326QosPortSchedulerEntry 4 }
   
gs2326QosSchedulerPortQueueShaperExcess OBJECT-TYPE
   SYNTAX      INTEGER { disable(0), enable(1) }
   MAX-ACCESS  read-write
   STATUS      current
   DESCRIPTION
       " 0: disable  1:enable,
         default: 0.  "
   ::= { gs2326QosPortSchedulerEntry 5 }
   
gs2326QosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2326QosPortSchedulerEntry 6 }
   
gs2326QosSchedulerPortQueueSchedulerPercent OBJECT-TYPE
   SYNTAX      DisplayString
   MAX-ACCESS  read-only
   STATUS      current
   DESCRIPTION
       " Only use in Q0 - Q5. Q6 & Q7 show empty "
   ::= { gs2326QosPortSchedulerEntry 7 }

gs2326QosPortEgressTagRemarking                                           OBJECT IDENTIFIER ::= { gs2326Qos 4 }

gs2326QosPortEgressTagRemarkingTable OBJECT-TYPE
   SYNTAX      SEQUENCE OF GS2326QosPortEgressTagRemarkingEntry
   MAX-ACCESS  not-accessible
   STATUS      current
   DESCRIPTION
       " configure the basic QoS Port Egress Tag Remark Configuration settings for all switch ports. "
   ::= { gs2326QosPortEgressTagRemarking  1 }

gs2326QosPortEgressTagRemarkingEntry OBJECT-TYPE
   SYNTAX      GS2326QosPortEgressTagRemarkingEntry
   MAX-ACCESS  not-accessible
   STATUS      current
   DESCRIPTION
       ""
   INDEX    { gs2326QosEgressTagRemarkingPort  }
   ::= { gs2326QosPortEgressTagRemarkingTable 1 }

GS2326QosPortEgressTagRemarkingEntry ::= SEQUENCE {
   gs2326QosEgressTagRemarkingPort	                Integer32,
   gs2326QosEgressTagRemarkingMode	                INTEGER
}

gs2326QosEgressTagRemarkingPort OBJECT-TYPE
   SYNTAX      Integer32 (1..4095)
   MAX-ACCESS  not-accessible
   STATUS      current
   DESCRIPTION
       " port, range : 1 - port number. "
   ::= { gs2326QosPortEgressTagRemarkingEntry 1 }

gs2326QosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2326QosPortEgressTagRemarkingEntry 2 }


gs2326QosPortEgressTagRemarkingDefTable OBJECT-TYPE
   SYNTAX      SEQUENCE OF GS2326QosPortEgressTagRemarkingDefEntry
   MAX-ACCESS  not-accessible
   STATUS      current
   DESCRIPTION
       " configure the basic QoS Port Egress Tag Remark Configuration settings for all switch ports. "
   ::= { gs2326QosPortEgressTagRemarking  2 }

gs2326QosPortEgressTagRemarkingDefEntry OBJECT-TYPE
   SYNTAX      GS2326QosPortEgressTagRemarkingDefEntry
   MAX-ACCESS  not-accessible
   STATUS      current
   DESCRIPTION
       ""
   INDEX    { gs2326QosEgressTagRemarkingDefPort  }
   ::= { gs2326QosPortEgressTagRemarkingDefTable 1 }

GS2326QosPortEgressTagRemarkingDefEntry ::= SEQUENCE {
   gs2326QosEgressTagRemarkingDefPort	            Integer32,
   gs2326QosEgressTagRemarkingDefPCP	                Integer32,
   gs2326QosEgressTagRemarkingDefDEI	                INTEGER
}

gs2326QosEgressTagRemarkingDefPort OBJECT-TYPE
   SYNTAX      Integer32(1..4095)
   MAX-ACCESS  not-accessible
   STATUS      current
   DESCRIPTION
       " port, range : 1 - port number. "
   ::= { gs2326QosPortEgressTagRemarkingDefEntry 1 }

gs2326QosEgressTagRemarkingDefPCP OBJECT-TYPE
   SYNTAX      Integer32(0..7)
   MAX-ACCESS  read-write
   STATUS      current
   DESCRIPTION
       " Controls the default PCP
       Range : 0-7"
   ::= { gs2326QosPortEgressTagRemarkingDefEntry 2 }

gs2326QosEgressTagRemarkingDefDEI OBJECT-TYPE
   SYNTAX      INTEGER { disable(0), enable(1) }
   MAX-ACCESS  read-write
   STATUS      current
   DESCRIPTION
       " controls the DEI
       Range 0-1"
   ::= { gs2326QosPortEgressTagRemarkingDefEntry 3 }

gs2326QosPortEgressTagRemarkingMapTable OBJECT-TYPE
   SYNTAX      SEQUENCE OF GS2326QosPortEgressTagRemarkingMapEntry
   MAX-ACCESS  not-accessible
   STATUS      current
   DESCRIPTION
       " Show Qos Port Egress Tag Remarking Map. "
   ::= { gs2326QosPortEgressTagRemarking 4 }

gs2326QosPortEgressTagRemarkingMapEntry OBJECT-TYPE
   SYNTAX      GS2326QosPortEgressTagRemarkingMapEntry
   MAX-ACCESS  not-accessible
   STATUS      current
   DESCRIPTION
       ""
   INDEX    { gs2326QosPortEgressTagRemarkingMapPort, gs2326QosTagRemarkingQoSClass, gs2326QosTagRemarkingDPLevel  }
   ::= { gs2326QosPortEgressTagRemarkingMapTable 1 }

GS2326QosPortEgressTagRemarkingMapEntry ::= SEQUENCE {
   gs2326QosPortEgressTagRemarkingMapPort	Integer32,
   gs2326QosTagRemarkingQoSClass			INTEGER,
   gs2326QosTagRemarkingDPLevel				INTEGER,
   gs2326QosTagRemarkingPCP					Integer32,
   gs2326QosTagRemarkingDEI					INTEGER
}

gs2326QosPortEgressTagRemarkingMapPort OBJECT-TYPE
   SYNTAX      Integer32 (1..4095)
   MAX-ACCESS  not-accessible
   STATUS      current
   DESCRIPTION
       " port, range : 1 - port number. "
   ::= { gs2326QosPortEgressTagRemarkingMapEntry 1 }

gs2326QosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8, 
         QoS Class0: 1, QoS Class1: 2...  "
   ::= { gs2326QosPortEgressTagRemarkingMapEntry 2 }

gs2326QosTagRemarkingDPLevel OBJECT-TYPE
   SYNTAX      INTEGER { level0(1), level1(2) }
   MAX-ACCESS  not-accessible
   STATUS      current
   DESCRIPTION
       " range: 1-2,
         DP Level0: 1, DP Level1: 2. "
   ::= { gs2326QosPortEgressTagRemarkingMapEntry 3 }

gs2326QosTagRemarkingPCP OBJECT-TYPE
   SYNTAX      Integer32 (0..7)
   MAX-ACCESS  read-write
   STATUS      current
   DESCRIPTION
       " range: 0-7.  "
   ::= { gs2326QosPortEgressTagRemarkingMapEntry 4 }
   
gs2326QosTagRemarkingDEI OBJECT-TYPE
   SYNTAX      INTEGER (0|1)
   MAX-ACCESS  read-write
   STATUS      current
   DESCRIPTION
       " range: 0-1.  "
   ::= { gs2326QosPortEgressTagRemarkingMapEntry 5 }


gs2326QosPortDSCPTable OBJECT-TYPE
   SYNTAX      SEQUENCE OF GS2326QosPortDSCPEntry
   MAX-ACCESS  not-accessible
   STATUS      current
   DESCRIPTION
       " configure the basic QoS Port DSCP Configuration settings for all switch ports. "
   ::= { gs2326Qos  5 }

gs2326QosPortDSCPEntry OBJECT-TYPE
   SYNTAX      GS2326QosPortDSCPEntry
   MAX-ACCESS  not-accessible
   STATUS      current
   DESCRIPTION
       ""
   INDEX    { gs2326QosPortDSCPPort  }
   ::= { gs2326QosPortDSCPTable 1 }

GS2326QosPortDSCPEntry ::= SEQUENCE {
   gs2326QosPortDSCPPort	                Integer32,
   gs2326QosPortDSCPIngressTranslate       INTEGER,
   gs2326QosPortDSCPIngressClassify	    INTEGER,
   gs2326QosPortDSCPEgressRewrite	        INTEGER
}

gs2326QosPortDSCPPort OBJECT-TYPE
   SYNTAX      Integer32 (1..4095)
   MAX-ACCESS  not-accessible
   STATUS      current
   DESCRIPTION
       " port, range : 1 - port number. "
   ::= { gs2326QosPortDSCPEntry 1 }

gs2326QosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2326QosPortDSCPEntry 2 }

gs2326QosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2326QosPortDSCPEntry 3 }

gs2326QosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { gs2326QosPortDSCPEntry 4 }


gs2326QosDSCPTable OBJECT-TYPE
   SYNTAX      SEQUENCE OF GS2326QosDSCPEntry
   MAX-ACCESS  not-accessible
   STATUS      current
   DESCRIPTION
       " configure the basic QoS DSCP based QoS Ingress Classification settings for all switches. "
   ::= { gs2326Qos  6 }

gs2326QosDSCPEntry OBJECT-TYPE
   SYNTAX      GS2326QosDSCPEntry
   MAX-ACCESS  not-accessible
   STATUS      current
   DESCRIPTION
       ""
   INDEX    { gs2326QosDSCPList  }
   ::= { gs2326QosDSCPTable 1 }

GS2326QosDSCPEntry ::= SEQUENCE {
   gs2326QosDSCPList       Integer32,
   gs2326QosDSCP           DisplayString,
   gs2326QosDSCPTrust      INTEGER,
   gs2326QosDSCPQosClass	  Integer32,
   gs2326QosDSCPDPL	      INTEGER
}

gs2326QosDSCPList OBJECT-TYPE
   SYNTAX      Integer32(1..64)
   MAX-ACCESS  not-accessible
   STATUS      current
   DESCRIPTION
      " DSCP mapping table index(1-64). "
   ::= { gs2326QosDSCPEntry 1 }

gs2326QosDSCP OBJECT-TYPE
   SYNTAX      DisplayString
   MAX-ACCESS  read-only
   STATUS      current
   DESCRIPTION
      "Maximum number of supported DSCP values are 64."
   ::= { gs2326QosDSCPEntry 2 }

gs2326QosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2326QosDSCPEntry 3 }

gs2326QosDSCPQosClass OBJECT-TYPE
   SYNTAX      Integer32(0..7)
   MAX-ACCESS  read-write
   STATUS      current
   DESCRIPTION
      " QoS class.
        range: 0-7,
        default: 0. "
   ::= { gs2326QosDSCPEntry 4 }

gs2326QosDSCPDPL OBJECT-TYPE
   SYNTAX      INTEGER(0|1)
   MAX-ACCESS  read-write
   STATUS      current
   DESCRIPTION
      " Drop Precedence Level.
        range: 0-1,
        default: disable. "
   ::= { gs2326QosDSCPEntry 5 }

gs2326QosDSCPTranslationTable OBJECT-TYPE
   SYNTAX      SEQUENCE OF GS2326QosDSCPTranslationEntry
   MAX-ACCESS  not-accessible
   STATUS      current
   DESCRIPTION
       "  configure the basic QoS DSCP Translation settings for all switches. "
   ::= { gs2326Qos  7 }

gs2326QosDSCPTranslationEntry OBJECT-TYPE
   SYNTAX      GS2326QosDSCPTranslationEntry
   MAX-ACCESS  not-accessible
   STATUS      current
   DESCRIPTION
       ""
   INDEX    { gs2326QosDSCPTranslationList  }
   ::= { gs2326QosDSCPTranslationTable 1 }

GS2326QosDSCPTranslationEntry ::= SEQUENCE {
   gs2326QosDSCPTranslationList                 Integer32,
   gs2326QosDSCPTranslationDSCPBasedId          DisplayString,
   gs2326QosDSCPTranslationIngressTranslate     Integer32,
   gs2326QosDSCPTranslationIngressClassify      INTEGER,
   gs2326QosDSCPTranslationEgressRemapDP0       Integer32,
   gs2326QosDSCPTranslationEgressRemapDP1       Integer32
}

gs2326QosDSCPTranslationList OBJECT-TYPE
   SYNTAX      Integer32(1..64)
   MAX-ACCESS  not-accessible
   STATUS      current
   DESCRIPTION
      " DSCP translation table index(1-64). "
   ::= { gs2326QosDSCPTranslationEntry 1 }

gs2326QosDSCPTranslationDSCPBasedId OBJECT-TYPE
   SYNTAX      DisplayString
   MAX-ACCESS  read-write
   STATUS      current
   DESCRIPTION
      " Configure global ingress DSCP translation table. "
   ::= { gs2326QosDSCPTranslationEntry 2 }

gs2326QosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2326QosDSCPTranslationEntry 3 }

gs2326QosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2326QosDSCPTranslationEntry 4 }

gs2326QosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { gs2326QosDSCPTranslationEntry 5 }

gs2326QosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { gs2326QosDSCPTranslationEntry 6 }


gs2326QosDSCPClassificationTable OBJECT-TYPE
   SYNTAX      SEQUENCE OF GS2326QosDSCPClassificationEntry
   MAX-ACCESS  not-accessible
   STATUS      current
   DESCRIPTION
       "   configure the mapping of QoS class  to DSCP value. "
   ::= { gs2326Qos  8 }

gs2326QosDSCPClassificationEntry OBJECT-TYPE
   SYNTAX      GS2326QosDSCPClassificationEntry
   MAX-ACCESS  not-accessible
   STATUS      current
   DESCRIPTION
       ""
   INDEX    { gs2326QosDSCPClassificationQoSClass, gs2326QosDSCPClassificationDPL }
   ::= { gs2326QosDSCPClassificationTable 1 }

GS2326QosDSCPClassificationEntry ::= SEQUENCE {
   gs2326QosDSCPClassificationQoSClass		INTEGER,
   gs2326QosDSCPClassificationDPL			INTEGER,
   gs2326QosDSCPClassificationDSCP			Integer32
}

gs2326QosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2326QosDSCPClassificationEntry 1 }

gs2326QosDSCPClassificationDPL OBJECT-TYPE
   SYNTAX      INTEGER(1|2)
   MAX-ACCESS  not-accessible
   STATUS      current
   DESCRIPTION
      " DPL. Index 1~2 mean DPL 0~1."
   ::= { gs2326QosDSCPClassificationEntry 2 }

gs2326QosDSCPClassificationDSCP OBJECT-TYPE
   SYNTAX      Integer32(0..63)
   MAX-ACCESS  read-write
   STATUS      current
   DESCRIPTION
      " Select the classified DSCP value.
        range: 0-63,
        default: 0. "
   ::= { gs2326QosDSCPClassificationEntry 3 }

gs2326QosControlList                                         OBJECT IDENTIFIER ::= { gs2326Qos 9 }

gs2326QosQceCreate OBJECT-TYPE
   SYNTAX       INTEGER { none(0), create(1) }
   MAX-ACCESS   read-write
   STATUS       current
   DESCRIPTION
       "default: 0
        0 : None  (read only)
        1 : Create an Qos entry"
   ::= { gs2326QosControlList 1 }

gs2326QosQceTable OBJECT-TYPE
   SYNTAX      SEQUENCE OF GS2326QosQceEntry
   MAX-ACCESS  not-accessible
   STATUS      current
   DESCRIPTION
       " Create Qos QCE entry. "
   ::= { gs2326QosControlList 2 }

gs2326QosQceEntry OBJECT-TYPE
   SYNTAX      GS2326QosQceEntry
   MAX-ACCESS  not-accessible
   STATUS      current
   DESCRIPTION
       ""
   INDEX    { gs2326QosQceIndex  }
   ::= { gs2326QosQceTable 1 }

GS2326QosQceEntry ::= SEQUENCE {
   gs2326QosQceIndex                Integer32,
   gs2326QosQceID                   Integer32,
   gs2326QosQceNextID               Integer32,
   gs2326QosQcePortMembers          DisplayString,
   
   gs2326QosQceTag                  DisplayString,
   gs2326QosQceVID                  DisplayString,
   gs2326QosPCP                     DisplayString,
   gs2326QosDEI                     DisplayString,
   gs2326QosSMAC                    DisplayString,
   gs2326QosDMACType                DisplayString,
   gs2326QosFrameType               INTEGER,
   
   gs2326QosMacEtherType            DisplayString,
   
   gs2326QosLLCSSAPAddr             DisplayString,
   gs2326QosLLCDSAPAddr             DisplayString,
   gs2326QosLLCControl              DisplayString,
   
   gs2326QosSNAPPID                 DisplayString,
   
   gs2326QosIpv4Protocol            DisplayString,
   gs2326QosIpv4ProtocolValue       Integer32,
   gs2326QosIpv4ProtocolUDPSport    DisplayString,
   gs2326QosIpv4ProtocolUDPDport    DisplayString,
   gs2326QosIpv4ProtocolTCPSport    DisplayString,
   gs2326QosIpv4ProtocolTCPDport    DisplayString,
   gs2326QosIpv4Ip                  DisplayString,
   gs2326QosIpv4Mask                DisplayString,
   gs2326QosIpv4IPFragment          INTEGER,
   gs2326QosIpv4DSCP                DisplayString,


   gs2326QosIpv6Protocol            DisplayString,
   gs2326QosIpv6ProtocolValue       Integer32,
   gs2326QosIpv6ProtocolUDPSport    DisplayString,
   gs2326QosIpv6ProtocolUDPDport    DisplayString,
   gs2326QosIpv6ProtocolTCPSport    DisplayString,
   gs2326QosIpv6ProtocolTCPDport    DisplayString,
   gs2326QosIpv6Ip                  DisplayString,
   gs2326QosIpv6Mask                DisplayString,
   gs2326QosIpv6DSCP                DisplayString,
   
   gs2326QosActionClass             Integer32,
   gs2326QosActionDPL               INTEGER,
   gs2326QosActionDSCP              Integer32,
   gs2326QosQceRowStatus            INTEGER
}

gs2326QosQceIndex OBJECT-TYPE
   SYNTAX      Integer32(1..256)
   MAX-ACCESS  not-accessible
   STATUS      current
   DESCRIPTION
       " "
   ::= { gs2326QosQceEntry 1 }

gs2326QosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2326QosQceEntry 2 }

gs2326QosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2326QosQceEntry 3 }

gs2326QosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2326QosQceEntry 4 }

gs2326QosQceTag OBJECT-TYPE
   SYNTAX      DisplayString
   MAX-ACCESS  read-write
   STATUS      current
   DESCRIPTION
       " Value of Tag field can be 'Any', 'Untag' or 'Tag'. "
   ::= { gs2326QosQceEntry 5 }

gs2326QosQceVID OBJECT-TYPE
   SYNTAX      DisplayString
   MAX-ACCESS  read-write
   STATUS      current
   DESCRIPTION
       " Valid value of VLAN ID can be any value in 'Specific 1~4094' or 'range 1-4094' or 'Any'. "
   ::= { gs2326QosQceEntry 6 }

gs2326QosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2326QosQceEntry 7 }

gs2326QosDEI OBJECT-TYPE
   SYNTAX      DisplayString
   MAX-ACCESS  read-write
   STATUS      current
   DESCRIPTION
       " Drop Eligible Indicator: Valid value of DEI can be any of values between 0, 1 or 'Any'. "
   ::= { gs2326QosQceEntry 8 }

gs2326QosSMAC  OBJECT-TYPE
   SYNTAX      DisplayString
   MAX-ACCESS  read-write
   STATUS      current
   DESCRIPTION
       "  Source MAC address: 24 MS bits OUI(00-00-00 ~ FF-FF-FF) or 'Any'. "
   ::= { gs2326QosQceEntry 9 }

gs2326QosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2326QosQceEntry 10 }

gs2326QosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2326QosQceEntry 11 }

gs2326QosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2326QosQceEntry 12 }

gs2326QosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2326QosQceEntry 13 }

gs2326QosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2326QosQceEntry 14 }

gs2326QosLLCControl OBJECT-TYPE
   SYNTAX      DisplayString
   MAX-ACCESS  read-write
   STATUS      current
   DESCRIPTION
       " Valid Control field can vary from 0x00 to 0xFF or 'Any',
         range: 00-FF,
         default: Any. "
   ::= { gs2326QosQceEntry 15 }

gs2326QosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2326QosQceEntry 16 }

gs2326QosIpv4Protocol OBJECT-TYPE
   SYNTAX      DisplayString
   MAX-ACCESS  read-write
   STATUS      current
   DESCRIPTION
       " IP protocol number: (Other, TCP or UDP) or 'Any'. "
   ::= { gs2326QosQceEntry 17 }

gs2326QosIpv4ProtocolValue  OBJECT-TYPE
   SYNTAX      Integer32(0..255)
   MAX-ACCESS  read-write
   STATUS      current
   DESCRIPTION
       " Ipv4 Protocol is Other.
         range: 0-255
         default: 0. "
   ::= { gs2326QosQceEntry 18 }

gs2326QosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2326QosQceEntry 19 }

gs2326QosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2326QosQceEntry 20 }

gs2326QosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2326QosQceEntry 21 }

gs2326QosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2326QosQceEntry 22 }

gs2326QosIpv4Ip OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223.
          If a port is configured to match on DMAC/DIP, this field is the
          Destination IP address."
   ::= { gs2326QosQceEntry 23 }

gs2326QosIpv4Mask OBJECT-TYPE
   SYNTAX      DisplayString
   MAX-ACCESS  read-write
   STATUS      current
   DESCRIPTION
       " Specific IP address in mask format or value 0.0.0.0 is 'Any'. "
   ::= { gs2326QosQceEntry 24 }

gs2326QosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2326QosQceEntry 25 }

gs2326QosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2326QosQceEntry 26 }

gs2326QosIpv6Protocol OBJECT-TYPE
   SYNTAX      DisplayString
   MAX-ACCESS  read-write
   STATUS      current
   DESCRIPTION
       " IP protocol number: (Other, TCP or UDP) or 'Any'. "
   ::= { gs2326QosQceEntry 27 }

gs2326QosIpv6ProtocolValue OBJECT-TYPE
   SYNTAX      Integer32(0..255)
   MAX-ACCESS  read-write
   STATUS      current
   DESCRIPTION
       " when IPv6 protocol is Other ,
         range: 0-255. "
   ::= { gs2326QosQceEntry 28 }

gs2326QosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2326QosQceEntry 29 }

gs2326QosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2326QosQceEntry 30 }

gs2326QosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2326QosQceEntry 31 }


gs2326QosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2326QosQceEntry 32 }

gs2326QosIpv6Ip OBJECT-TYPE
   SYNTAX      DisplayString
   MAX-ACCESS  read-write
   STATUS      current
   DESCRIPTION
       " IPv6 source address: (a.b.c.d) or value 0.0.0.0 is 'Any', 32 LS bits.
         If a port is configured to match on DMAC/DIP, this field is the
         Destination IP address."
   ::= { gs2326QosQceEntry 33 }

gs2326QosIpv6Mask OBJECT-TYPE
   SYNTAX      DisplayString
   MAX-ACCESS  read-write
   STATUS      current
   DESCRIPTION
       " IPv6 mask address: (a.b.c.d) or value 0.0.0.0 is 'Any', 32 LS bits. "
   ::= { gs2326QosQceEntry 34 }

gs2326QosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2326QosQceEntry 35 }

gs2326QosActionClass  OBJECT-TYPE
   SYNTAX      Integer32(0..8)
   MAX-ACCESS  read-write
   STATUS      current
   DESCRIPTION
       " QoS class: (0-7) or 8: Default."
   ::= { gs2326QosQceEntry 36 }

gs2326QosActionDPL OBJECT-TYPE
   SYNTAX      INTEGER (0..4)
   MAX-ACCESS  read-write
   STATUS      current
   DESCRIPTION
       " DP Valid Drop Precedence Level can be (0-3) or 4: Default. "
   ::= { gs2326QosQceEntry 37 }

gs2326QosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2326QosQceEntry 38 }

gs2326QosQceRowStatus OBJECT-TYPE
   SYNTAX      INTEGER { active(1), notInservice(2), destroy(4) }
   MAX-ACCESS  read-write
   STATUS      current
   DESCRIPTION
       "  1: active2: notInservice 4: destroy"
   ::= { gs2326QosQceEntry 39 }

gs2326QosQceMoveID OBJECT-TYPE
   SYNTAX       Integer32(0..256)
   MAX-ACCESS   read-write
   STATUS       current
   DESCRIPTION
       " Move Qos,
         default: 0
         Qos ID must be exist.
         range : 0 - 256."
   ::= { gs2326QosControlList 3 }

gs2326QosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2326QosControlList 4 }


gs2326QosQCLStatusTable OBJECT-TYPE
   SYNTAX      SEQUENCE OF GS2326QosQCLStatusEntry
   MAX-ACCESS  not-accessible
   STATUS      current
   DESCRIPTION
       "  configure the basic QoS DSCP Translation settings for all switches. "
   ::= { gs2326Qos  10 }

gs2326QosQCLStatusEntry OBJECT-TYPE
   SYNTAX      GS2326QosQCLStatusEntry
   MAX-ACCESS  not-accessible
   STATUS      current
   DESCRIPTION
       ""
   INDEX    { gs2326QosQCLStatusList  }
   ::= { gs2326QosQCLStatusTable 1 }

GS2326QosQCLStatusEntry ::= SEQUENCE {
   gs2326QosQCLStatusList               Integer32,
   gs2326QosQCLStatusUser               DisplayString,
   gs2326QosQCLStatusQCEId              DisplayString,
   gs2326QosQCLStatusFrameType          DisplayString,
   gs2326QosQCLStatusPortlist           DisplayString,
   gs2326QosQCLStatusActionClass	       DisplayString,
   gs2326QosQCLStatusActionDPL	       DisplayString,
   gs2326QosQCLStatusActionDSCP	       DisplayString,
   gs2326QosQCLStatusActionConflict     DisplayString
}

gs2326QosQCLStatusList OBJECT-TYPE
   SYNTAX      Integer32(1..4095)
   MAX-ACCESS  not-accessible
   STATUS      current
   DESCRIPTION
       " QCL table index. "
   ::= { gs2326QosQCLStatusEntry 1}
   
gs2326QosQCLStatusUser OBJECT-TYPE
   SYNTAX      DisplayString
   MAX-ACCESS  read-only
   STATUS      current
   DESCRIPTION
       " Indicates the QCL user. "
   ::= { gs2326QosQCLStatusEntry 2 }

gs2326QosQCLStatusQCEId OBJECT-TYPE
   SYNTAX      DisplayString
   MAX-ACCESS  read-only
   STATUS      current
   DESCRIPTION
      " Indicates the index of QCE. "
   ::= { gs2326QosQCLStatusEntry 3}

gs2326QosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2326QosQCLStatusEntry 4}

gs2326QosQCLStatusPortlist OBJECT-TYPE
   SYNTAX      DisplayString
   MAX-ACCESS  read-only
   STATUS      current
   DESCRIPTION
       " Indicates the list of ports configured with the QCE. "
   ::= { gs2326QosQCLStatusEntry 5}

gs2326QosQCLStatusActionClass OBJECT-TYPE
   SYNTAX      DisplayString
   MAX-ACCESS  read-only
   STATUS      current
   DESCRIPTION
       " Classified QoS class; if a frame matches the QCE it will be put in the
       queue. "
   ::= { gs2326QosQCLStatusEntry 6}

gs2326QosQCLStatusActionDPL OBJECT-TYPE
   SYNTAX      DisplayString
   MAX-ACCESS  read-only
   STATUS      current
   DESCRIPTION
       " Drop Precedence Level; if a frame matches the QCE then DP level will
       set to value displayed under DPL column."
   ::= { gs2326QosQCLStatusEntry 7}

gs2326QosQCLStatusActionDSCP OBJECT-TYPE
   SYNTAX      DisplayString
   MAX-ACCESS  read-only
   STATUS      current
   DESCRIPTION
       " If a frame matches the QCE then DSCP will be classified with the value
       displayed under DSCP column."
   ::= { gs2326QosQCLStatusEntry 8}

gs2326QosQCLStatusActionConflict OBJECT-TYPE
   SYNTAX      DisplayString
   MAX-ACCESS  read-only
   STATUS      current
   DESCRIPTION
       " If a frame matches the QCE then DSCP will be classified with the value
        displayed under DSCP column. "
   ::= { gs2326QosQCLStatusEntry 9}


gs2326QosStormControl                                           OBJECT IDENTIFIER ::= { gs2326Qos 11 }

gs2326QoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { gs2326QosStormControl 2 }

gs2326QoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326QosStormControl 3 }

gs2326QoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { gs2326QosStormControl 4 }

gs2326QoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326QosStormControl 5 }

gs2326QoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { gs2326QosStormControl 6 }

gs2326QoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326QosStormControl 7 }


gs2326Vlan                                                           OBJECT IDENTIFIER ::= { gs2326Configuration 15 }

gs2326VlanPorts                                                      OBJECT IDENTIFIER ::= { gs2326Vlan 1 }

gs2326VlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2326VlanPorts 1 }

gs2326VlanPortsTable OBJECT-TYPE
   SYNTAX      SEQUENCE OF GS2326VlanPortsEntry
   MAX-ACCESS  not-accessible
   STATUS      current
   DESCRIPTION
       " Configure Vlan ports Configuration mode. "
   ::= { gs2326VlanPorts 2 }

gs2326VlanPortsEntry OBJECT-TYPE
   SYNTAX      GS2326VlanPortsEntry
   MAX-ACCESS  not-accessible
   STATUS      current
   DESCRIPTION
       ""
   INDEX    { gs2326VlanPortsPort  }
   ::= { gs2326VlanPortsTable 1 }

GS2326VlanPortsEntry ::= SEQUENCE {
   gs2326VlanPortsPort	         Integer32,
   gs2326VlanPortsPVID     Integer32,
   gs2326VlanPortsFrameType      INTEGER,
   gs2326VlanPortsIngressFilter  INTEGER,
   gs2326VlanPortsEgressRule     INTEGER,
   gs2326VlanPortsPortType       INTEGER
}

gs2326VlanPortsPort OBJECT-TYPE
   SYNTAX      Integer32(1..4094)
   MAX-ACCESS  not-accessible
   STATUS      current
   DESCRIPTION
       " port, range : 1 - port number. "
   ::= { gs2326VlanPortsEntry 1 }

gs2326VlanPortsPVID OBJECT-TYPE
   SYNTAX      Integer32(1..4094)
   MAX-ACCESS  read-write
   STATUS      current
   DESCRIPTION
       "Configure PVID.
        range: 1-4094,
        default: 1. "
   ::= { gs2326VlanPortsEntry 2 }

gs2326VlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2326VlanPortsEntry 3 }

gs2326VlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2326VlanPortsEntry 4 }

gs2326VlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2326VlanPortsEntry 5 }

gs2326VlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2326VlanPortsEntry 6 }

gs2326VlanPrivateVLAN                                                              OBJECT IDENTIFIER ::= { gs2326Vlan 2 }

gs2326VlanPrivateVLANMembership                                                    OBJECT IDENTIFIER ::= { gs2326VlanPrivateVLAN 1 }

gs2326VlanPrivateVLANMembershipCreate OBJECT-TYPE
   SYNTAX       Integer32(1..4094)
   MAX-ACCESS   read-write
   STATUS       current
   DESCRIPTION
       "default: 0
        0 : None  (read only)
        1 : Create a pvlan"
   ::= { gs2326VlanPrivateVLANMembership 1 }

gs2326VlanPrivateVLANMembershipTable OBJECT-TYPE
   SYNTAX      SEQUENCE OF Gs2326VlanPrivateVLANMembershipEntry
   MAX-ACCESS  not-accessible
   STATUS      current
   DESCRIPTION
       " Configure Private Vlan Configuration. "
   ::= { gs2326VlanPrivateVLANMembership 2 }

gs2326VlanPrivateVLANMembershipEntry OBJECT-TYPE
   SYNTAX      Gs2326VlanPrivateVLANMembershipEntry
   MAX-ACCESS  not-accessible
   STATUS      current
   DESCRIPTION
       ""
   INDEX    { gs2326VlanPrivateVLANIndex  }
   ::= { gs2326VlanPrivateVLANMembershipTable 1 }

Gs2326VlanPrivateVLANMembershipEntry ::= SEQUENCE {
   gs2326VlanPrivateVLANIndex          Integer32,
   gs2326VlanPrivateVLANID             Integer32,
   gs2326VlanPrivateVLANMemberships    DisplayString,
   gs2326VlanPrivateVLANRowStatus      INTEGER
}

gs2326VlanPrivateVLANIndex OBJECT-TYPE
   SYNTAX      Integer32(1..52)
   MAX-ACCESS  not-accessible
   STATUS      current
   DESCRIPTION
       "private VLAN Index. "
   ::= { gs2326VlanPrivateVLANMembershipEntry 1 }

gs2326VlanPrivateVLANID OBJECT-TYPE
   SYNTAX      Integer32(1..52)
   MAX-ACCESS  read-write
   STATUS      current
   DESCRIPTION
       "Indicates the ID of this particular private VLAN.
       The CreateEntry can be modify, the other entry can't be modify."
   ::= { gs2326VlanPrivateVLANMembershipEntry 2 }

gs2326VlanPrivateVLANMemberships OBJECT-TYPE
   SYNTAX      DisplayString
   MAX-ACCESS  read-write
   STATUS      current
   DESCRIPTION
       "To include the ports in a Private VLAN"
   ::= { gs2326VlanPrivateVLANMembershipEntry 3 }

gs2326VlanPrivateVLANRowStatus OBJECT-TYPE
   SYNTAX      INTEGER { active(1), notInservice(2), destroy(4) }
   MAX-ACCESS  read-write
   STATUS      current
   DESCRIPTION
       "1: active
        2: notInservice
        4: destroy"
   ::= { gs2326VlanPrivateVLANMembershipEntry 4 }

gs2326VlanPortIsolationTable OBJECT-TYPE
   SYNTAX      SEQUENCE OF Gs2326VlanPortIsolationEntry
   MAX-ACCESS  not-accessible
   STATUS      current
   DESCRIPTION
       " Configure Vlan Port Isolation Configuration. "
   ::= { gs2326VlanPrivateVLAN 2 }

gs2326VlanPortIsolationEntry OBJECT-TYPE
   SYNTAX      Gs2326VlanPortIsolationEntry
   MAX-ACCESS  not-accessible
   STATUS      current
   DESCRIPTION
       ""
   INDEX    { gs2326VlanPortIsolationPort  }
   ::= { gs2326VlanPortIsolationTable 1 }

Gs2326VlanPortIsolationEntry ::= SEQUENCE {
   gs2326VlanPortIsolationPort Integer32,
   gs2326VlanPortIsolation     INTEGER
}

gs2326VlanPortIsolationPort OBJECT-TYPE
   SYNTAX      Integer32(1..4094)
   MAX-ACCESS  not-accessible
   STATUS      current
   DESCRIPTION
       " port, range : 1 - port number. "
   ::= { gs2326VlanPortIsolationEntry 1 }

gs2326VlanPortIsolation OBJECT-TYPE
   SYNTAX      INTEGER{ disable(0), enable(1) }
   MAX-ACCESS  read-write
   STATUS      current
   DESCRIPTION
       "default: 0
        0:disable
        1:enable"
   ::= { gs2326VlanPortIsolationEntry 2 }


gs2326MACbasedVLAN                                                      OBJECT IDENTIFIER ::= { gs2326Vlan 3 }

gs2326MACbasedVLANConf                                                      OBJECT IDENTIFIER ::= { gs2326MACbasedVLAN 1 }

gs2326MACbasedVLANConfCreate OBJECT-TYPE
   SYNTAX       Integer32
   MAX-ACCESS   read-write
   STATUS       current
   DESCRIPTION
       "default: 0
       0 : None  (read only) 1 : Create MAC base vlan"
   ::= { gs2326MACbasedVLANConf 1 }

gs2326MACbasedVLANConfTable OBJECT-TYPE
   SYNTAX      SEQUENCE OF Gs2326MACbasedVLANConfEntry
   MAX-ACCESS  not-accessible
   STATUS      current
   DESCRIPTION
       " Configure Vlan Port Isolation Configuration. "
   ::= { gs2326MACbasedVLANConf 2 }

gs2326MACbasedVLANConfEntry OBJECT-TYPE
   SYNTAX      Gs2326MACbasedVLANConfEntry
   MAX-ACCESS  not-accessible
   STATUS      current
   DESCRIPTION
       ""
   INDEX    { gs2326MACbasedVLANIndex  }
   ::= { gs2326MACbasedVLANConfTable 1 }

Gs2326MACbasedVLANConfEntry ::= SEQUENCE {
   gs2326MACbasedVLANIndex         Integer32,
   gs2326MACbasedVLANMACAddress    MacAddress,
   gs2326MACbasedVLANID            Integer32,
   gs2326MACbasedMemberships       DisplayString,
   gs2326MACbaseRowStatus          INTEGER
}

gs2326MACbasedVLANIndex OBJECT-TYPE
   SYNTAX      Integer32(1..256)
   MAX-ACCESS  read-write
   STATUS      current
   DESCRIPTION
       "Indicates the VLAN ID. "
   ::= { gs2326MACbasedVLANConfEntry 1 }

gs2326MACbasedVLANMACAddress OBJECT-TYPE
   SYNTAX      MacAddress
   MAX-ACCESS  read-write
   STATUS      current
   DESCRIPTION
       "Indicates the MAC address.
       The CreateEntry can be modify, the other entry can't be modify."
   ::= { gs2326MACbasedVLANConfEntry 2 }

gs2326MACbasedVLANID OBJECT-TYPE
   SYNTAX      Integer32(1..4094)
   MAX-ACCESS  read-write
   STATUS      current
   DESCRIPTION
       "Indicates the VLAN ID. "
   ::= { gs2326MACbasedVLANConfEntry 3 }

gs2326MACbasedMemberships OBJECT-TYPE
   SYNTAX      DisplayString
   MAX-ACCESS  read-write
   STATUS      current
   DESCRIPTION
       "The ports are displayed for each MAC-based VLAN entry.
        To include the port in a MAC-based VLAN"
   ::= { gs2326MACbasedVLANConfEntry 4 }


gs2326MACbaseRowStatus OBJECT-TYPE
   SYNTAX      INTEGER { active(1), notInservice(2), destroy(4)}
   MAX-ACCESS  read-write
   STATUS      current
   DESCRIPTION
       "1: active
        2: notInservice
        4: destroy"
   ::= { gs2326MACbasedVLANConfEntry 5 }

gs2326IGMPSnooping                                                           OBJECT IDENTIFIER ::= { gs2326Configuration 16 }

gs2326IGMPSnoopingBasic                                                      OBJECT IDENTIFIER ::= { gs2326IGMPSnooping 1 }

gs2326IGMPSnoopingEnable  OBJECT-TYPE
   SYNTAX      INTEGER { disable(0), enable(1) }
   MAX-ACCESS  read-write
   STATUS      current
   DESCRIPTION
       "Enable/Disable the Global IGMP Snooping"
   ::= { gs2326IGMPSnoopingBasic 1 }

gs2326IGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2326IGMPSnoopingBasic 2 }

gs2326IGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2326IGMPSnoopingBasic 3 }
   
gs2326IGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2326IGMPSnoopingBasic 4 }

gs2326IGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2326IGMPSnoopingBasic 5 }

gs2326IGMPSnoopingPortRelatedTable OBJECT-TYPE
   SYNTAX      SEQUENCE OF Gs2326IGMPSnoopingPortRelatedEntry
   MAX-ACCESS  not-accessible
   STATUS      current
   DESCRIPTION
       " Configure IGMP Snooping Port Related Configuration. "
   ::= { gs2326IGMPSnoopingBasic 6 }

gs2326IGMPSnoopingPortRelatedEntry OBJECT-TYPE
   SYNTAX      Gs2326IGMPSnoopingPortRelatedEntry
   MAX-ACCESS  not-accessible
   STATUS      current
   DESCRIPTION
       ""
   INDEX    { ifIndex  }
   ::= { gs2326IGMPSnoopingPortRelatedTable 1 }

Gs2326IGMPSnoopingPortRelatedEntry ::= SEQUENCE {
   gs2326IGMPSnoopingRouterPort	INTEGER,
   gs2326IGMPSnoopingFastLeave  	INTEGER,
   gs2326IGMPSnoopingThrottling    Integer32
}

gs2326IGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2326IGMPSnoopingPortRelatedEntry 1 }

gs2326IGMPSnoopingFastLeave OBJECT-TYPE
   SYNTAX      INTEGER { disable(0), enable(1) }
   MAX-ACCESS  read-write
   STATUS      current
   DESCRIPTION
       "Enable/Disable the fast leave on the port. "
   ::= { gs2326IGMPSnoopingPortRelatedEntry 2 }
   
gs2326IGMPSnoopingThrottling OBJECT-TYPE
   SYNTAX      Integer32(0..10)
   MAX-ACCESS  read-write
   STATUS      current
   DESCRIPTION
       "Enable to limit the number of multicast groups to which a switch port can belong.
       0: unlimited"
   ::= { gs2326IGMPSnoopingPortRelatedEntry 3 }
   
gs2326IGMPSnoopingVLANTable OBJECT-TYPE
   SYNTAX      SEQUENCE OF Gs2326IGMPSnoopingVLANEntry
   MAX-ACCESS  not-accessible
   STATUS      current
   DESCRIPTION
       " Configure IGMP Snooping Vlan Configuration. "
   ::= { gs2326IGMPSnooping 2 }

gs2326IGMPSnoopingVLANEntry OBJECT-TYPE
   SYNTAX      Gs2326IGMPSnoopingVLANEntry
   MAX-ACCESS  not-accessible
   STATUS      current
   DESCRIPTION
       ""
   INDEX    { gs2326IGMPSnoopingVLANID  }
   ::= { gs2326IGMPSnoopingVLANTable 1 }

Gs2326IGMPSnoopingVLANEntry ::= SEQUENCE {
   gs2326IGMPSnoopingVLANID        	Integer32,
   gs2326IGMPSnoopingVLANEnable    	INTEGER,
   gs2326IGMPSnoopingVLANIGMPQuerier   INTEGER,
   gs2326IGMPSnoopingVLANCompatibility INTEGER,
   gs2326IGMPSnoopingVLANRV        	Integer32,
   gs2326IGMPSnoopingVLANQI      	    Integer32,
   gs2326IGMPSnoopingVLANQRI   	    Integer32,
   gs2326IGMPSnoopingVLANLLQI   	    Integer32,
   gs2326IGMPSnoopingVLANURI    	    Integer32
}

gs2326IGMPSnoopingVLANID OBJECT-TYPE
   SYNTAX      Integer32(1..4095)
   MAX-ACCESS  read-write
   STATUS      current
   DESCRIPTION
       "The VLAN ID of the entry"
   ::= { gs2326IGMPSnoopingVLANEntry 1 }

gs2326IGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2326IGMPSnoopingVLANEntry 2 }

gs2326IGMPSnoopingVLANIGMPQuerier OBJECT-TYPE
   SYNTAX      INTEGER { disable(0), enable(1) }
   MAX-ACCESS  read-write
   STATUS      current
   DESCRIPTION
       "Enable/Disable the IGMP Querier in the VLAN. "
   ::= { gs2326IGMPSnoopingVLANEntry 3 }

gs2326IGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2326IGMPSnoopingVLANEntry 4 }
   
gs2326IGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2326IGMPSnoopingVLANEntry 5 }
   
gs2326IGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2326IGMPSnoopingVLANEntry 6 }
   
gs2326IGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2326IGMPSnoopingVLANEntry 7 }
   
gs2326IGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2326IGMPSnoopingVLANEntry 8 }

gs2326IGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2326IGMPSnoopingVLANEntry 9 }

gs2326IGMPSnoopingPortGroupFiltering                                                      OBJECT IDENTIFIER ::= { gs2326IGMPSnooping 3 }

gs2326IGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2326IGMPSnoopingPortGroupFiltering 1 }

gs2326IGMPSnoopingPortGroupFilteringTable OBJECT-TYPE
   SYNTAX      SEQUENCE OF Gs2326IGMPSnoopingPortGroupFilteringEntry
   MAX-ACCESS  not-accessible
   STATUS      current
   DESCRIPTION
       " Configure IGMP Snooping port group filtering. "
   ::= { gs2326IGMPSnoopingPortGroupFiltering 2 }

gs2326IGMPSnoopingPortGroupFilteringEntry OBJECT-TYPE
   SYNTAX      Gs2326IGMPSnoopingPortGroupFilteringEntry
   MAX-ACCESS  not-accessible
   STATUS      current
   DESCRIPTION
       ""
   INDEX    { gs2326IGMPSnoopingPortGroupFilteringIndex  }
   ::= { gs2326IGMPSnoopingPortGroupFilteringTable 1 }

Gs2326IGMPSnoopingPortGroupFilteringEntry ::= SEQUENCE {
   gs2326IGMPSnoopingPortGroupFilteringIndex         Integer32,
   gs2326IGMPSnoopingPortGroupFilteringPort          Integer32,
   gs2326IGMPSnoopingPortGroupFilteringGroups        DisplayString,
   gs2326IGMPSnoopingPortGroupFilteringRowStatus     INTEGER
}

gs2326IGMPSnoopingPortGroupFilteringIndex OBJECT-TYPE
   SYNTAX      Integer32(1..65535)
   MAX-ACCESS  not-accessible
   STATUS      current
   DESCRIPTION
       "IGMP Snooping Port Group Filtering Configuration Index. "
   ::= { gs2326IGMPSnoopingPortGroupFilteringEntry 1 }

gs2326IGMPSnoopingPortGroupFilteringPort OBJECT-TYPE
   SYNTAX      Integer32(1..65535)
   MAX-ACCESS  read-write
   STATUS      current
   DESCRIPTION
       "The logical port for the settings. "
   ::= { gs2326IGMPSnoopingPortGroupFilteringEntry 2 }

gs2326IGMPSnoopingPortGroupFilteringGroups OBJECT-TYPE
   SYNTAX      DisplayString
   MAX-ACCESS  read-write
   STATUS      current
   DESCRIPTION
       "The IP Multicast Group that will be filtered. "
   ::= { gs2326IGMPSnoopingPortGroupFilteringEntry 3 }

gs2326IGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2326IGMPSnoopingPortGroupFilteringEntry 4 }

gs2326IGMPSnoopingStatus                                                      OBJECT IDENTIFIER ::= { gs2326IGMPSnooping 4 }

gs2326IGMPSnoopingstatisticClear OBJECT-TYPE
   SYNTAX      INTEGER { none(0), clear(1)}
   MAX-ACCESS  read-write
   STATUS      current
   DESCRIPTION
       "Clears all Statistics counters."
   ::= { gs2326IGMPSnoopingStatus 1 }


gs2326IGMPSnoopingstatisticTable OBJECT-TYPE
   SYNTAX      SEQUENCE OF Gs2326IGMPSnoopingstatisticEntry
   MAX-ACCESS  not-accessible
   STATUS      current
   DESCRIPTION
       " Configure Vlan Port Isolation Configuration. "
   ::= { gs2326IGMPSnoopingStatus 2 }

gs2326IGMPSnoopingstatisticEntry OBJECT-TYPE
   SYNTAX      Gs2326IGMPSnoopingstatisticEntry
   MAX-ACCESS  not-accessible
   STATUS      current
   DESCRIPTION
       ""
   INDEX    { gs2326IGMPSnoopingstatisticVLANID  }
   ::= { gs2326IGMPSnoopingstatisticTable 1 }

Gs2326IGMPSnoopingstatisticEntry ::= SEQUENCE {
   gs2326IGMPSnoopingstatisticVLANID              Integer32,
   gs2326IGMPSnoopingstatisticQuerierVersion      DisplayString,
   gs2326IGMPSnoopingstatisticHostVersion         DisplayString,
   gs2326IGMPSnoopingstatisticQuerierStatus       DisplayString,
   gs2326IGMPSnoopingstatisticQueriesTransmitted  Counter32,
   gs2326IGMPSnoopingstatisticQueriesReceived     Counter32,
   gs2326IGMPSnoopingstatisticV1ReportsReceived   Counter32,
   gs2326IGMPSnoopingstatisticV2ReportsReceived   Counter32,
   gs2326IGMPSnoopingstatisticV3ReportsReceived   Counter32,
   gs2326IGMPSnoopingstatisticV2LeavesReceived    Counter32
}


gs2326IGMPSnoopingstatisticVLANID OBJECT-TYPE
   SYNTAX      Integer32(1..4095)
   MAX-ACCESS  read-only
   STATUS      current
   DESCRIPTION
       "The VLAN ID of the entry. "
   ::= { gs2326IGMPSnoopingstatisticEntry 1 }

gs2326IGMPSnoopingstatisticQuerierVersion OBJECT-TYPE
   SYNTAX      DisplayString
   MAX-ACCESS  read-only
   STATUS      current
   DESCRIPTION
       "Working Querier Version currently. "
   ::= { gs2326IGMPSnoopingstatisticEntry 2 }
   
gs2326IGMPSnoopingstatisticHostVersion OBJECT-TYPE
   SYNTAX      DisplayString
   MAX-ACCESS  read-only
   STATUS      current
   DESCRIPTION
       "Working Host Version currently. "
   ::= { gs2326IGMPSnoopingstatisticEntry 3 }

gs2326IGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2326IGMPSnoopingstatisticEntry 4 }

gs2326IGMPSnoopingstatisticQueriesTransmitted OBJECT-TYPE
   SYNTAX      Counter32
   MAX-ACCESS  read-only
   STATUS      current
   DESCRIPTION
       "The number of Transmitted Queries. "
   ::= { gs2326IGMPSnoopingstatisticEntry 5 }

gs2326IGMPSnoopingstatisticQueriesReceived OBJECT-TYPE
   SYNTAX      Counter32
   MAX-ACCESS  read-only
   STATUS      current
   DESCRIPTION
       "The number of Received Queries. "
   ::= { gs2326IGMPSnoopingstatisticEntry 6 }

gs2326IGMPSnoopingstatisticV1ReportsReceived OBJECT-TYPE
   SYNTAX      Counter32
   MAX-ACCESS  read-only
   STATUS      current
   DESCRIPTION
       "The number of Received V1 Reports. "
   ::= { gs2326IGMPSnoopingstatisticEntry 7 }

gs2326IGMPSnoopingstatisticV2ReportsReceived OBJECT-TYPE
   SYNTAX      Counter32
   MAX-ACCESS  read-only
   STATUS      current
   DESCRIPTION
       "The number of Received V2 Reports. "
   ::= { gs2326IGMPSnoopingstatisticEntry 8 }

gs2326IGMPSnoopingstatisticV3ReportsReceived OBJECT-TYPE
   SYNTAX      Counter32
   MAX-ACCESS  read-only
   STATUS      current
   DESCRIPTION
       "The number of Received V3 Reports. "
   ::= { gs2326IGMPSnoopingstatisticEntry 9 }

gs2326IGMPSnoopingstatisticV2LeavesReceived OBJECT-TYPE
   SYNTAX      Counter32
   MAX-ACCESS  read-only
   STATUS      current
   DESCRIPTION
       "The number of Received V2 Leaves. "
   ::= { gs2326IGMPSnoopingstatisticEntry 10 }

gs2326IGMPSnoopingRouterPortTable OBJECT-TYPE
   SYNTAX      SEQUENCE OF Gs2326IGMPSnoopingRouterPortEntry
   MAX-ACCESS  not-accessible
   STATUS      current
   DESCRIPTION
       " Configure Vlan Port Isolation Configuration. "
   ::= { gs2326IGMPSnoopingStatus 3 }

gs2326IGMPSnoopingRouterPortEntry OBJECT-TYPE
   SYNTAX      Gs2326IGMPSnoopingRouterPortEntry
   MAX-ACCESS  not-accessible
   STATUS      current
   DESCRIPTION
       ""
   INDEX    { ifIndex  }
   ::= { gs2326IGMPSnoopingRouterPortTable 1 }

Gs2326IGMPSnoopingRouterPortEntry ::= SEQUENCE {
   gs2326IGMPSnoopingRouterPortStatus            DisplayString
}

gs2326IGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2326IGMPSnoopingRouterPortEntry 1 }

gs2326IGMPSnoopingGroupsTable OBJECT-TYPE
   SYNTAX      SEQUENCE OF Gs2326IGMPSnoopingGroupsEntry
   MAX-ACCESS  not-accessible
   STATUS      current
   DESCRIPTION
       "IGMP Snooping Groups Information . "
   ::= { gs2326IGMPSnooping 5 }

gs2326IGMPSnoopingGroupsEntry OBJECT-TYPE
   SYNTAX      Gs2326IGMPSnoopingGroupsEntry
   MAX-ACCESS  not-accessible
   STATUS      current
   DESCRIPTION
       ""
   INDEX    { gs2326IGMPSnoopingGroupsIndex  }
   ::= { gs2326IGMPSnoopingGroupsTable 1 }

Gs2326IGMPSnoopingGroupsEntry ::= SEQUENCE {
   gs2326IGMPSnoopingGroupsIndex          Integer32,
   gs2326IGMPSnoopingGroupsVLANID         Integer32,
   gs2326IGMPSnoopingGroups               InetAddress,
   gs2326IGMPSnoopingGroupsMemberships    DisplayString
}

gs2326IGMPSnoopingGroupsIndex OBJECT-TYPE
   SYNTAX      Integer32(1..65535)
   MAX-ACCESS  not-accessible
   STATUS      current
   DESCRIPTION
       "IGMP Snooping Groups Index"
   ::= { gs2326IGMPSnoopingGroupsEntry 1 }

gs2326IGMPSnoopingGroupsVLANID OBJECT-TYPE
   SYNTAX      Integer32(1..4095)
   MAX-ACCESS  read-only
   STATUS      current
   DESCRIPTION
       "VLAN ID of the group. "
   ::= { gs2326IGMPSnoopingGroupsEntry 2 }

gs2326IGMPSnoopingGroups OBJECT-TYPE
   SYNTAX      DisplayString
   MAX-ACCESS  read-only
   STATUS      current
   DESCRIPTION
       "Group address of the group displayed."
   ::= { gs2326IGMPSnoopingGroupsEntry 3 }

gs2326IGMPSnoopingGroupsMemberships OBJECT-TYPE
   SYNTAX      DisplayString
   MAX-ACCESS  read-only
   STATUS      current
   DESCRIPTION
       "Ports under this group."
   ::= { gs2326IGMPSnoopingGroupsEntry 4 }
   
gs2326IGMPSnoopingSSMTable OBJECT-TYPE
   SYNTAX      SEQUENCE OF Gs2326IGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2326IGMPSnooping 6 }

gs2326IGMPSnoopingSSMEntry OBJECT-TYPE
   SYNTAX      Gs2326IGMPSnoopingSSMEntry
   MAX-ACCESS  not-accessible
   STATUS      current
   DESCRIPTION
       ""
   INDEX    { gs2326IGMPSnoopingSSMIndex  }
   ::= { gs2326IGMPSnoopingSSMTable 1 }

Gs2326IGMPSnoopingSSMEntry ::= SEQUENCE {
   gs2326IGMPSnoopingSSMIndex          Integer32,
   gs2326IGMPSnoopingSSMVLANID         Integer32,
   gs2326IGMPSnoopingSSMGroup          DisplayString,
   gs2326IGMPSnoopingSSMPort           Integer32,
   gs2326IGMPSnoopingSSMMode           DisplayString,
   gs2326IGMPSnoopingSSMSourceAddress  DisplayString,
   gs2326IGMPSnoopingSSMType           DisplayString
}

gs2326IGMPSnoopingSSMIndex OBJECT-TYPE
   SYNTAX      Integer32(1..65535)
   MAX-ACCESS  not-accessible
   STATUS      current
   DESCRIPTION
       "IGMP Snooping SSM Index"
   ::= { gs2326IGMPSnoopingSSMEntry 1 }

gs2326IGMPSnoopingSSMVLANID OBJECT-TYPE
   SYNTAX      Integer32(1..4095)
   MAX-ACCESS  read-only
   STATUS      current
   DESCRIPTION
       "VLAN ID of the group. "
   ::= { gs2326IGMPSnoopingSSMEntry 2 }

gs2326IGMPSnoopingSSMGroup OBJECT-TYPE
   SYNTAX      DisplayString
   MAX-ACCESS  read-only
   STATUS      current
   DESCRIPTION
       "Group address of the group displayed."
   ::= { gs2326IGMPSnoopingSSMEntry 3 }

gs2326IGMPSnoopingSSMPort OBJECT-TYPE
   SYNTAX      Integer32(1..65535)
   MAX-ACCESS  read-only
   STATUS      current
   DESCRIPTION
       "Ports under this group."
   ::= { gs2326IGMPSnoopingSSMEntry 4 }
   
gs2326IGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2326IGMPSnoopingSSMEntry 5 }
   
gs2326IGMPSnoopingSSMSourceAddress OBJECT-TYPE
   SYNTAX      DisplayString
   MAX-ACCESS  read-only
   STATUS      current
   DESCRIPTION
       "IP Address of the source. Currently, system limits the total number of
       IP source addresses for filtering to be 128."
   ::= { gs2326IGMPSnoopingSSMEntry 6 }

gs2326IGMPSnoopingSSMType OBJECT-TYPE
   SYNTAX      DisplayString
   MAX-ACCESS  read-only
   STATUS      current
   DESCRIPTION
       "Indicates the Type. It can be either Allow or Deny."
   ::= { gs2326IGMPSnoopingSSMEntry 7 }   
   
gs2326MLDSnooping                                                           OBJECT IDENTIFIER ::= { gs2326Configuration 17 }

gs2326MLDSnoopingBasic                                                      OBJECT IDENTIFIER ::= { gs2326MLDSnooping 1 }

gs2326MLDSnoopingEnable  OBJECT-TYPE
   SYNTAX      INTEGER { disable(0), enable(1) }
   MAX-ACCESS  read-write
   STATUS      current
   DESCRIPTION
       "Enable/Disable the Global MLD Snooping"
   ::= { gs2326MLDSnoopingBasic 1 }

gs2326MLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2326MLDSnoopingBasic 2 }

gs2326MLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2326MLDSnoopingBasic 3 }
   
gs2326MLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2326MLDSnoopingBasic 4 }

gs2326MLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2326MLDSnoopingBasic 5 }

gs2326MLDSnoopingPortRelatedTable OBJECT-TYPE
   SYNTAX      SEQUENCE OF Gs2326MLDSnoopingPortRelatedEntry
   MAX-ACCESS  not-accessible
   STATUS      current
   DESCRIPTION
       " Configure MLD Snooping Port Related Configuration. "
   ::= { gs2326MLDSnoopingBasic 6 }

gs2326MLDSnoopingPortRelatedEntry OBJECT-TYPE
   SYNTAX      Gs2326MLDSnoopingPortRelatedEntry
   MAX-ACCESS  not-accessible
   STATUS      current
   DESCRIPTION
       ""
   INDEX    { ifIndex  }
   ::= { gs2326MLDSnoopingPortRelatedTable 1 }

Gs2326MLDSnoopingPortRelatedEntry ::= SEQUENCE {
   gs2326MLDSnoopingRouterPort	INTEGER,
   gs2326MLDSnoopingFastLeave  	INTEGER,
   gs2326MLDSnoopingThrottling    Integer32
}

gs2326MLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2326MLDSnoopingPortRelatedEntry 1 }

gs2326MLDSnoopingFastLeave OBJECT-TYPE
   SYNTAX      INTEGER { disable(0), enable(1) }
   MAX-ACCESS  read-write
   STATUS      current
   DESCRIPTION
       "Enable/Disable the fast leave on the port. "
   ::= { gs2326MLDSnoopingPortRelatedEntry 2 }
   
gs2326MLDSnoopingThrottling OBJECT-TYPE
   SYNTAX      Integer32(0..10)
   MAX-ACCESS  read-write
   STATUS      current
   DESCRIPTION
       "Enable to limit the number of multicast groups to which a switch port can belong.
       0: unlimited"
   ::= { gs2326MLDSnoopingPortRelatedEntry 3 }
   
gs2326MLDSnoopingVLANTable OBJECT-TYPE
   SYNTAX      SEQUENCE OF Gs2326MLDSnoopingVLANEntry
   MAX-ACCESS  not-accessible
   STATUS      current
   DESCRIPTION
       " Configure MLD Snooping Vlan Configuration. "
   ::= { gs2326MLDSnooping 2 }

gs2326MLDSnoopingVLANEntry OBJECT-TYPE
   SYNTAX      Gs2326MLDSnoopingVLANEntry
   MAX-ACCESS  not-accessible
   STATUS      current
   DESCRIPTION
       ""
   INDEX    { gs2326MLDSnoopingVLANID  }
   ::= { gs2326MLDSnoopingVLANTable 1 }

Gs2326MLDSnoopingVLANEntry ::= SEQUENCE {
   gs2326MLDSnoopingVLANID        	Integer32,
   gs2326MLDSnoopingVLANEnable    	INTEGER,
   gs2326MLDSnoopingVLANIGMPQuerier   INTEGER,
   gs2326MLDSnoopingVLANCompatibility INTEGER,
   gs2326MLDSnoopingVLANRV        	Integer32,
   gs2326MLDSnoopingVLANQI      	    Integer32,
   gs2326MLDSnoopingVLANQRI   	    Integer32,
   gs2326MLDSnoopingVLANLLQI   	    Integer32,
   gs2326MLDSnoopingVLANURI    	    Integer32
}

gs2326MLDSnoopingVLANID OBJECT-TYPE
   SYNTAX      Integer32(1..4095)
   MAX-ACCESS  read-write
   STATUS      current
   DESCRIPTION
       "The VLAN ID of the entry"
   ::= { gs2326MLDSnoopingVLANEntry 1 }

gs2326MLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2326MLDSnoopingVLANEntry 2 }

gs2326MLDSnoopingVLANIGMPQuerier OBJECT-TYPE
   SYNTAX      INTEGER { disable(0), enable(1) }
   MAX-ACCESS  read-write
   STATUS      current
   DESCRIPTION
       "Enable/Disable the MLD Querier in the VLAN. "
   ::= { gs2326MLDSnoopingVLANEntry 3 }

gs2326MLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2326MLDSnoopingVLANEntry 4 }
   
gs2326MLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2326MLDSnoopingVLANEntry 5 }
   
gs2326MLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2326MLDSnoopingVLANEntry 6 }
   
gs2326MLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2326MLDSnoopingVLANEntry 7 }
   
gs2326MLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2326MLDSnoopingVLANEntry 8 }

gs2326MLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2326MLDSnoopingVLANEntry 9 }

gs2326MLDSnoopingPortGroupFiltering                                                      OBJECT IDENTIFIER ::= { gs2326MLDSnooping 3 }

gs2326MLDSnoopingPortGroupFilteringCreate OBJECT-TYPE
   SYNTAX       Integer32
   MAX-ACCESS   read-write
   STATUS       current
   DESCRIPTION
       "default: 0
       0 : None  (read only) 1 : Create MLD Snooping Port Group Filtering "
   ::= { gs2326MLDSnoopingPortGroupFiltering 1 }

gs2326MLDSnoopingPortGroupFilteringTable OBJECT-TYPE
   SYNTAX      SEQUENCE OF Gs2326MLDSnoopingPortGroupFilteringEntry
   MAX-ACCESS  not-accessible
   STATUS      current
   DESCRIPTION
       " Configure MLD Snooping port group filtering. "
   ::= { gs2326MLDSnoopingPortGroupFiltering 2 }

gs2326MLDSnoopingPortGroupFilteringEntry OBJECT-TYPE
   SYNTAX      Gs2326MLDSnoopingPortGroupFilteringEntry
   MAX-ACCESS  not-accessible
   STATUS      current
   DESCRIPTION
       ""
   INDEX    { gs2326MLDSnoopingPortGroupFilteringIndex  }
   ::= { gs2326MLDSnoopingPortGroupFilteringTable 1 }

Gs2326MLDSnoopingPortGroupFilteringEntry ::= SEQUENCE {
   gs2326MLDSnoopingPortGroupFilteringIndex         Integer32,
   gs2326MLDSnoopingPortGroupFilteringPort          Integer32,
   gs2326MLDSnoopingPortGroupFilteringGroups        DisplayString,
   gs2326MLDSnoopingPortGroupFilteringRowStatus     INTEGER
}

gs2326MLDSnoopingPortGroupFilteringIndex OBJECT-TYPE
   SYNTAX      Integer32(1..65535)
   MAX-ACCESS  not-accessible
   STATUS      current
   DESCRIPTION
       "MLD Snooping Port Group Filtering Configuration Index. "
   ::= { gs2326MLDSnoopingPortGroupFilteringEntry 1 }

gs2326MLDSnoopingPortGroupFilteringPort OBJECT-TYPE
   SYNTAX      Integer32(1..65535)
   MAX-ACCESS  read-write
   STATUS      current
   DESCRIPTION
       "The logical port for the settings. "
   ::= { gs2326MLDSnoopingPortGroupFilteringEntry 2 }

gs2326MLDSnoopingPortGroupFilteringGroups OBJECT-TYPE
   SYNTAX      DisplayString
   MAX-ACCESS  read-write
   STATUS      current
   DESCRIPTION
       "The IP Multicast Group that will be filtered. "
   ::= { gs2326MLDSnoopingPortGroupFilteringEntry 3 }

gs2326MLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2326MLDSnoopingPortGroupFilteringEntry 4 }

gs2326MLDSnoopingStatus                                                      OBJECT IDENTIFIER ::= { gs2326MLDSnooping 4 }

gs2326MLDSnoopingstatisticClear OBJECT-TYPE
   SYNTAX      INTEGER { none(0), clear(1)}
   MAX-ACCESS  read-write
   STATUS      current
   DESCRIPTION
       "Clears all Statistics counters."
   ::= { gs2326MLDSnoopingStatus 1 }


gs2326MLDSnoopingstatisticTable OBJECT-TYPE
   SYNTAX      SEQUENCE OF Gs2326MLDSnoopingstatisticEntry
   MAX-ACCESS  not-accessible
   STATUS      current
   DESCRIPTION
       " Configure Vlan Port Isolation Configuration. "
   ::= { gs2326MLDSnoopingStatus 2 }

gs2326MLDSnoopingstatisticEntry OBJECT-TYPE
   SYNTAX      Gs2326MLDSnoopingstatisticEntry
   MAX-ACCESS  not-accessible
   STATUS      current
   DESCRIPTION
       ""
   INDEX    { gs2326MLDSnoopingstatisticVLANID  }
   ::= { gs2326MLDSnoopingstatisticTable 1 }

Gs2326MLDSnoopingstatisticEntry ::= SEQUENCE {
   gs2326MLDSnoopingstatisticVLANID              Integer32,
   gs2326MLDSnoopingstatisticQuerierVersion      DisplayString,
   gs2326MLDSnoopingstatisticHostVersion         DisplayString,
   gs2326MLDSnoopingstatisticQuerierStatus       DisplayString,
   gs2326MLDSnoopingstatisticQueriesTransmitted  Counter32,
   gs2326MLDSnoopingstatisticQueriesReceived     Counter32,
   gs2326MLDSnoopingstatisticV1ReportsReceived   Counter32,
   gs2326MLDSnoopingstatisticV2ReportsReceived   Counter32,
   gs2326MLDSnoopingstatisticV1LeavesReceived    Counter32
}


gs2326MLDSnoopingstatisticVLANID OBJECT-TYPE
   SYNTAX      Integer32(1..4095)
   MAX-ACCESS  read-only
   STATUS      current
   DESCRIPTION
       "The VLAN ID of the entry. "
   ::= { gs2326MLDSnoopingstatisticEntry 1 }

gs2326MLDSnoopingstatisticQuerierVersion OBJECT-TYPE
   SYNTAX      DisplayString
   MAX-ACCESS  read-only
   STATUS      current
   DESCRIPTION
       "Working Querier Version currently. "
   ::= { gs2326MLDSnoopingstatisticEntry 2 }
   
gs2326MLDSnoopingstatisticHostVersion OBJECT-TYPE
   SYNTAX      DisplayString
   MAX-ACCESS  read-only
   STATUS      current
   DESCRIPTION
       "Working Host Version currently. "
   ::= { gs2326MLDSnoopingstatisticEntry 3 }

gs2326MLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2326MLDSnoopingstatisticEntry 4 }

gs2326MLDSnoopingstatisticQueriesTransmitted OBJECT-TYPE
   SYNTAX      Counter32
   MAX-ACCESS  read-only
   STATUS      current
   DESCRIPTION
       "The number of Transmitted Queries. "
   ::= { gs2326MLDSnoopingstatisticEntry 5 }

gs2326MLDSnoopingstatisticQueriesReceived OBJECT-TYPE
   SYNTAX      Counter32
   MAX-ACCESS  read-only
   STATUS      current
   DESCRIPTION
       "The number of Received Queries. "
   ::= { gs2326MLDSnoopingstatisticEntry 6 }

gs2326MLDSnoopingstatisticV1ReportsReceived OBJECT-TYPE
   SYNTAX      Counter32
   MAX-ACCESS  read-only
   STATUS      current
   DESCRIPTION
       "The number of Received V1 Reports. "
   ::= { gs2326MLDSnoopingstatisticEntry 7 }

gs2326MLDSnoopingstatisticV2ReportsReceived OBJECT-TYPE
   SYNTAX      Counter32
   MAX-ACCESS  read-only
   STATUS      current
   DESCRIPTION
       "The number of Received V2 Reports. "
   ::= { gs2326MLDSnoopingstatisticEntry 8 }

gs2326MLDSnoopingstatisticV1LeavesReceived OBJECT-TYPE
   SYNTAX      Counter32
   MAX-ACCESS  read-only
   STATUS      current
   DESCRIPTION
       "The number of Received V1 Leaves. "
   ::= { gs2326MLDSnoopingstatisticEntry 9 }

gs2326MLDSnoopingRouterPortTable OBJECT-TYPE
   SYNTAX      SEQUENCE OF Gs2326MLDSnoopingRouterPortEntry
   MAX-ACCESS  not-accessible
   STATUS      current
   DESCRIPTION
       " Configure Vlan Port Isolation Configuration. "
   ::= { gs2326MLDSnoopingStatus 3 }

gs2326MLDSnoopingRouterPortEntry OBJECT-TYPE
   SYNTAX      Gs2326MLDSnoopingRouterPortEntry
   MAX-ACCESS  not-accessible
   STATUS      current
   DESCRIPTION
       ""
   INDEX    { ifIndex  }
   ::= { gs2326MLDSnoopingRouterPortTable 1 }

Gs2326MLDSnoopingRouterPortEntry ::= SEQUENCE {
   gs2326MLDSnoopingRouterPortStatus            DisplayString
}

gs2326MLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2326MLDSnoopingRouterPortEntry 1 }

gs2326MLDSnoopingGroupsTable OBJECT-TYPE
   SYNTAX      SEQUENCE OF Gs2326MLDSnoopingGroupsEntry
   MAX-ACCESS  not-accessible
   STATUS      current
   DESCRIPTION
       "MLD Snooping Groups Information . "
   ::= { gs2326MLDSnooping 5 }

gs2326MLDSnoopingGroupsEntry OBJECT-TYPE
   SYNTAX      Gs2326MLDSnoopingGroupsEntry
   MAX-ACCESS  not-accessible
   STATUS      current
   DESCRIPTION
       ""
   INDEX    { gs2326MLDSnoopingGroupsIndex  }
   ::= { gs2326MLDSnoopingGroupsTable 1 }

Gs2326MLDSnoopingGroupsEntry ::= SEQUENCE {
   gs2326MLDSnoopingGroupsIndex          Integer32,
   gs2326MLDSnoopingGroupsVLANID         Integer32,
   gs2326MLDSnoopingGroups               InetAddress,
   gs2326MLDSnoopingGroupsMemberships    DisplayString
}

gs2326MLDSnoopingGroupsIndex OBJECT-TYPE
   SYNTAX      Integer32(1..65535)
   MAX-ACCESS  not-accessible
   STATUS      current
   DESCRIPTION
       "MLD Snooping Groups Index"
   ::= { gs2326MLDSnoopingGroupsEntry 1 }

gs2326MLDSnoopingGroupsVLANID OBJECT-TYPE
   SYNTAX      Integer32(1..4095)
   MAX-ACCESS  read-only
   STATUS      current
   DESCRIPTION
       "VLAN ID of the group. "
   ::= { gs2326MLDSnoopingGroupsEntry 2 }

gs2326MLDSnoopingGroups OBJECT-TYPE
   SYNTAX      DisplayString
   MAX-ACCESS  read-only
   STATUS      current
   DESCRIPTION
       "Group address of the group displayed."
   ::= { gs2326MLDSnoopingGroupsEntry 3 }

gs2326MLDSnoopingGroupsMemberships OBJECT-TYPE
   SYNTAX      DisplayString
   MAX-ACCESS  read-only
   STATUS      current
   DESCRIPTION
       "Ports under this group."
   ::= { gs2326MLDSnoopingGroupsEntry 4 }
   
gs2326MLDSnoopingSSMTable OBJECT-TYPE
   SYNTAX      SEQUENCE OF Gs2326MLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2326MLDSnooping 6 }

gs2326MLDSnoopingSSMEntry OBJECT-TYPE
   SYNTAX      Gs2326MLDSnoopingSSMEntry
   MAX-ACCESS  not-accessible
   STATUS      current
   DESCRIPTION
       ""
   INDEX    { gs2326MLDSnoopingSSMIndex  }
   ::= { gs2326MLDSnoopingSSMTable 1 }

Gs2326MLDSnoopingSSMEntry ::= SEQUENCE {
   gs2326MLDSnoopingSSMIndex          Integer32,
   gs2326MLDSnoopingSSMVLANID         Integer32,
   gs2326MLDSnoopingSSMGroup          DisplayString,
   gs2326MLDSnoopingSSMPort           Integer32,
   gs2326MLDSnoopingSSMMode           DisplayString,
   gs2326MLDSnoopingSSMSourceAddress  DisplayString,
   gs2326MLDSnoopingSSMType           DisplayString
}

gs2326MLDSnoopingSSMIndex OBJECT-TYPE
   SYNTAX      Integer32(1..65535)
   MAX-ACCESS  not-accessible
   STATUS      current
   DESCRIPTION
       "MLD Snooping SSM Index"
   ::= { gs2326MLDSnoopingSSMEntry 1 }

gs2326MLDSnoopingSSMVLANID OBJECT-TYPE
   SYNTAX      Integer32(1..4095)
   MAX-ACCESS  read-only
   STATUS      current
   DESCRIPTION
       "VLAN ID of the group. "
   ::= { gs2326MLDSnoopingSSMEntry 2 }

gs2326MLDSnoopingSSMGroup OBJECT-TYPE
   SYNTAX      DisplayString
   MAX-ACCESS  read-only
   STATUS      current
   DESCRIPTION
       "Group address of the group displayed."
   ::= { gs2326MLDSnoopingSSMEntry 3 }

gs2326MLDSnoopingSSMPort OBJECT-TYPE
   SYNTAX      Integer32(1..65535)
   MAX-ACCESS  read-only
   STATUS      current
   DESCRIPTION
       "Ports under this group."
   ::= { gs2326MLDSnoopingSSMEntry 4 }
   
gs2326MLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2326MLDSnoopingSSMEntry 5 }
   
gs2326MLDSnoopingSSMSourceAddress OBJECT-TYPE
   SYNTAX      DisplayString
   MAX-ACCESS  read-only
   STATUS      current
   DESCRIPTION
       "IP Address of the source. Currently, system limits the total number of
       IP source addresses for filtering to be 128."
   ::= { gs2326MLDSnoopingSSMEntry 6 }

gs2326MLDSnoopingSSMType OBJECT-TYPE
   SYNTAX      DisplayString
   MAX-ACCESS  read-only
   STATUS      current
   DESCRIPTION
       "Indicates the Type. It can be either Allow or Deny."
   ::= { gs2326MLDSnoopingSSMEntry 7 }      
   

gs2326MVR                                                                   OBJECT IDENTIFIER ::= { gs2326Configuration 18 }

gs2326MVRConfiguration                                                      OBJECT IDENTIFIER ::= { gs2326MVR 1 }

gs2326MVRMode  OBJECT-TYPE
   SYNTAX      INTEGER { disable(0), enable(1) }
   MAX-ACCESS  read-write
   STATUS      current
   DESCRIPTION
       "Enable/Disable the Global MVR. "
   ::= { gs2326MVRConfiguration 1 }

gs2326MVRVLANId  OBJECT-TYPE
   SYNTAX      Integer32(1..4094)
   MAX-ACCESS  read-write
   STATUS      current
   DESCRIPTION
       "Specify the Multicast VLAN ID. "
   ::= { gs2326MVRConfiguration 2 }

gs2326MVRPortConfigurationTable OBJECT-TYPE
   SYNTAX      SEQUENCE OF Gs2326MVRPortConfigurationEntry
   MAX-ACCESS  not-accessible
   STATUS      current
   DESCRIPTION
       " Configure MVR Port Configuration. "
   ::= { gs2326MVRConfiguration 3 }

gs2326MVRPortConfigurationEntry OBJECT-TYPE
   SYNTAX      Gs2326MVRPortConfigurationEntry
   MAX-ACCESS  not-accessible
   STATUS      current
   DESCRIPTION
       ""
   INDEX    { ifIndex  }
   ::= { gs2326MVRPortConfigurationTable 1 }

Gs2326MVRPortConfigurationEntry ::= SEQUENCE {
   gs2326MVRPortConfigurationMode	INTEGER,
   gs2326MVRPortConfigurationType  	INTEGER,
   gs2326MVRPortConfigurationImmediateLeave    INTEGER
}

gs2326MVRPortConfigurationMode OBJECT-TYPE
   SYNTAX      INTEGER { disable(0), enable(1) }
   MAX-ACCESS  read-write
   STATUS      current
   DESCRIPTION
       "Enable MVR on the port. "
   ::= { gs2326MVRPortConfigurationEntry 1 }

gs2326MVRPortConfigurationType OBJECT-TYPE
   SYNTAX      INTEGER { receiver(0), source(1) }
   MAX-ACCESS  read-write
   STATUS      current
   DESCRIPTION
       "Specify the MVR port type on the port. "
   ::= { gs2326MVRPortConfigurationEntry 2 }
   
gs2326MVRPortConfigurationImmediateLeave OBJECT-TYPE
   SYNTAX      INTEGER { disable(0), enable(1) }
   MAX-ACCESS  read-write
   STATUS      current
   DESCRIPTION
       "Enable the fast leave on the port. "
   ::= { gs2326MVRPortConfigurationEntry 3 }
      

gs2326MVRPortGroupFiltering                                                      OBJECT IDENTIFIER ::= { gs2326MVR 2 }

gs2326MVRPortGroupFilteringCreate OBJECT-TYPE
   SYNTAX       Integer32
   MAX-ACCESS   read-write
   STATUS       current
   DESCRIPTION
       "default: 0
       0 : None  (read only) 1 : Create MLD Snooping Port Group Filtering "
   ::= { gs2326MVRPortGroupFiltering 1 }

gs2326MVRPortGroupFilteringTable OBJECT-TYPE
   SYNTAX      SEQUENCE OF Gs2326MVRPortGroupFilteringEntry
   MAX-ACCESS  not-accessible
   STATUS      current
   DESCRIPTION
       " Configure MVR port group filtering. "
   ::= { gs2326MVRPortGroupFiltering 2 }

gs2326MVRPortGroupFilteringEntry OBJECT-TYPE
   SYNTAX      Gs2326MVRPortGroupFilteringEntry
   MAX-ACCESS  not-accessible
   STATUS      current
   DESCRIPTION
       ""
   INDEX    { gs2326MVRPortGroupFilteringIndex  }
   ::= { gs2326MVRPortGroupFilteringTable 1 }

Gs2326MVRPortGroupFilteringEntry ::= SEQUENCE {
   gs2326MVRPortGroupFilteringIndex         Integer32,
   gs2326MVRPortGroupFilteringPort          Integer32,
   gs2326MVRPortGroupFilteringStartGroups   DisplayString,
   gs2326MVRPortGroupFilteringEndGroups     DisplayString,
   gs2326MVRPortGroupFilteringRowStatus     INTEGER
}

gs2326MVRPortGroupFilteringIndex OBJECT-TYPE
   SYNTAX      Integer32(1..65535)
   MAX-ACCESS  not-accessible
   STATUS      current
   DESCRIPTION
       "MVR Port Group Filtering Configuration Index. "
   ::= { gs2326MVRPortGroupFilteringEntry 1 }

gs2326MVRPortGroupFilteringPort OBJECT-TYPE
   SYNTAX      Integer32(1..65535)
   MAX-ACCESS  read-write
   STATUS      current
   DESCRIPTION
       "The logical port for the settings. "
   ::= { gs2326MVRPortGroupFilteringEntry 2 }

gs2326MVRPortGroupFilteringStartGroups OBJECT-TYPE
   SYNTAX      DisplayString
   MAX-ACCESS  read-write
   STATUS      current
   DESCRIPTION
       "The IP Multicast Group that will be allowed. "
   ::= { gs2326MVRPortGroupFilteringEntry 3 }

gs2326MVRPortGroupFilteringEndGroups OBJECT-TYPE
   SYNTAX      DisplayString
   MAX-ACCESS  read-write
   STATUS      current
   DESCRIPTION
       "The IP Multicast Group that will be allowed. "
   ::= { gs2326MVRPortGroupFilteringEntry 4 }   

gs2326MVRPortGroupFilteringRowStatus OBJECT-TYPE
   SYNTAX      INTEGER { active(1), notInservice(2), destroy(4)}
   MAX-ACCESS  read-write
   STATUS      current
   DESCRIPTION
       "1: active
        2: notInservice
        4: destroy"
   ::= { gs2326MVRPortGroupFilteringEntry 5 }

gs2326MVRGroupsTable OBJECT-TYPE
   SYNTAX      SEQUENCE OF Gs2326MVRGroupsEntry
   MAX-ACCESS  not-accessible
   STATUS      current
   DESCRIPTION
       "MVR Groups Information . "
   ::= { gs2326MVR 3 }

gs2326MVRGroupsEntry OBJECT-TYPE
   SYNTAX      Gs2326MVRGroupsEntry
   MAX-ACCESS  not-accessible
   STATUS      current
   DESCRIPTION
       ""
   INDEX    { gs2326MVRGroupsIndex  }
   ::= { gs2326MVRGroupsTable 1 }

Gs2326MVRGroupsEntry ::= SEQUENCE {
   gs2326MVRGroupsIndex          Integer32,
   gs2326MVRGroupsVLANID         Integer32,
   gs2326MVRGroups               InetAddress,
   gs2326MVRGroupsMemberships    DisplayString
}

gs2326MVRGroupsIndex OBJECT-TYPE
   SYNTAX      Integer32(1..65535)
   MAX-ACCESS  not-accessible
   STATUS      current
   DESCRIPTION
       "MVR Groups Index"
   ::= { gs2326MVRGroupsEntry 1 }

gs2326MVRGroupsVLANID OBJECT-TYPE
   SYNTAX      Integer32(1..4095)
   MAX-ACCESS  read-only
   STATUS      current
   DESCRIPTION
       "VLAN ID of the group. "
   ::= { gs2326MVRGroupsEntry 2 }

gs2326MVRGroups OBJECT-TYPE
   SYNTAX      DisplayString
   MAX-ACCESS  read-only
   STATUS      current
   DESCRIPTION
       "Group address of the group displayed."
   ::= { gs2326MVRGroupsEntry 3 }

gs2326MVRGroupsMemberships OBJECT-TYPE
   SYNTAX      DisplayString
   MAX-ACCESS  read-only
   STATUS      current
   DESCRIPTION
       "Ports under this group."
   ::= { gs2326MVRGroupsEntry 4 }
            

gs2326MVRStatus                                                      OBJECT IDENTIFIER ::= { gs2326MVR 4 }

gs2326MVRstatisticClear OBJECT-TYPE
   SYNTAX      INTEGER { none(0), clear(1)}
   MAX-ACCESS  read-write
   STATUS      current
   DESCRIPTION
       "Clears all Statistics counters."
   ::= { gs2326MVRStatus 1 }

gs2326MVRstatisticVLANID OBJECT-TYPE
   SYNTAX      Integer32(1..4095)
   MAX-ACCESS  read-only
   STATUS      current
   DESCRIPTION
       "The VLAN ID of the entry. "
   ::= { gs2326MVRStatus 2 }

gs2326MVRstatisticV1ReportsReceived OBJECT-TYPE
   SYNTAX      Counter32
   MAX-ACCESS  read-only
   STATUS      current
   DESCRIPTION
       "The number of Received V1 Reports. "
   ::= { gs2326MVRStatus 3 }

gs2326MVRstatisticV2ReportsReceived OBJECT-TYPE
   SYNTAX      Counter32
   MAX-ACCESS  read-only
   STATUS      current
   DESCRIPTION
       "The number of Received V2 Reports. "
   ::= { gs2326MVRStatus 4 }
   
gs2326MVRstatisticV3ReportsReceived OBJECT-TYPE
   SYNTAX      Counter32
   MAX-ACCESS  read-only
   STATUS      current
   DESCRIPTION
       "The number of Received V3 Reports. "
   ::= { gs2326MVRStatus 5 }

gs2326MVRstatisticV2LeavesReceived OBJECT-TYPE
   SYNTAX      Counter32
   MAX-ACCESS  read-only
   STATUS      current
   DESCRIPTION
       "The number of Received V2 Leaves. "
   ::= { gs2326MVRStatus 6 }
            
gs2326LACP                                                     OBJECT IDENTIFIER ::= { gs2326Configuration 19 }

gs2326LACPConf                                                 OBJECT IDENTIFIER ::= { gs2326LACP 1 }

gs2326LACPPortConfigurationTable OBJECT-TYPE
   SYNTAX      SEQUENCE OF Gs2326LACPPortConfigurationEntry
   MAX-ACCESS  not-accessible
   STATUS      current
   DESCRIPTION
       " "
   ::= { gs2326LACPConf 1 }

gs2326LACPPortConfigurationEntry OBJECT-TYPE
   SYNTAX      Gs2326LACPPortConfigurationEntry
   MAX-ACCESS  not-accessible
   STATUS      current
   DESCRIPTION
       ""
   INDEX    { gs2326LACPPortConfigurationPort  }
   ::= { gs2326LACPPortConfigurationTable 1 }
   
Gs2326LACPPortConfigurationEntry ::= SEQUENCE {
    gs2326LACPPortConfigurationPort         Integer32,
    gs2326LACPPortConfigurationMode         INTEGER,
    gs2326LACPPortConfigurationKey          Integer32,
    gs2326LACPPortConfigurationRole         INTEGER
}

gs2326LACPPortConfigurationPort OBJECT-TYPE
   SYNTAX      Integer32(1..4095)
   MAX-ACCESS  not-accessible
   STATUS      current
   DESCRIPTION
       " "
   ::= { gs2326LACPPortConfigurationEntry 1 }

gs2326LACPPortConfigurationMode OBJECT-TYPE
   SYNTAX      INTEGER { disable(0), enable(1) }
   MAX-ACCESS  read-write
   STATUS      current
   DESCRIPTION
       "Enable/Disable LACP Mode."
   ::= { gs2326LACPPortConfigurationEntry 2 }
   
gs2326LACPPortConfigurationKey OBJECT-TYPE
   SYNTAX      Integer32(0..65535)
   MAX-ACCESS  read-write
   STATUS      current
   DESCRIPTION
       "LACP key : 1-65535. 0 : Auto"
   ::= { gs2326LACPPortConfigurationEntry 3 }
   
gs2326LACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2326LACPPortConfigurationEntry 4 }

gs2326LACPSystemStatusTable OBJECT-TYPE
   SYNTAX      SEQUENCE OF Gs2326LACPSystemStatusEntry
   MAX-ACCESS  not-accessible
   STATUS      current
   DESCRIPTION
       " "
   ::= { gs2326LACP 2 }

gs2326LACPSystemStatusEntry OBJECT-TYPE
   SYNTAX      Gs2326LACPSystemStatusEntry
   MAX-ACCESS  not-accessible
   STATUS      current
   DESCRIPTION
       ""
   INDEX    { gs2326LACPSystemStatusIndex  }
   ::= { gs2326LACPSystemStatusTable 1 }

Gs2326LACPSystemStatusEntry ::= SEQUENCE {
   gs2326LACPSystemStatusIndex             Integer32,
   gs2326LACPSystemStatusAggrID            DisplayString,
   gs2326LACPSystemStatusPartnerSystemID   MacAddress,
   gs2326LACPSystemStatusPartnerKey        DisplayString,
   gs2326LACPSystemStatusLastchanged       DisplayString,
   gs2326LACPSystemStatusLocalPorts        DisplayString
}

gs2326LACPSystemStatusIndex OBJECT-TYPE
   SYNTAX      Integer32(1..12)
   MAX-ACCESS  not-accessible
   STATUS      current
   DESCRIPTION
       " "
   ::= { gs2326LACPSystemStatusEntry 1 }

gs2326LACPSystemStatusAggrID OBJECT-TYPE
   SYNTAX      DisplayString
   MAX-ACCESS  read-only
   STATUS      current
   DESCRIPTION
       "The Aggregation ID associated with this aggregation instance."
   ::= { gs2326LACPSystemStatusEntry 2 }
   
gs2326LACPSystemStatusPartnerSystemID OBJECT-TYPE
   SYNTAX      MacAddress
   MAX-ACCESS  read-only
   STATUS      current
   DESCRIPTION
       "The system ID (MAC address) of the aggregation partner."
   ::= { gs2326LACPSystemStatusEntry 3 }

gs2326LACPSystemStatusPartnerKey OBJECT-TYPE
   SYNTAX      DisplayString
   MAX-ACCESS  read-only
   STATUS      current
   DESCRIPTION
       " The Key that the partner has assigned to this aggregation ID. "
   ::= { gs2326LACPSystemStatusEntry 4 }

gs2326LACPSystemStatusLastchanged OBJECT-TYPE
   SYNTAX      DisplayString
   MAX-ACCESS  read-only
   STATUS      current
   DESCRIPTION
       " The time since this aggregation changed. "
   ::= { gs2326LACPSystemStatusEntry 5 }
   
gs2326LACPSystemStatusLocalPorts OBJECT-TYPE
   SYNTAX      DisplayString
   MAX-ACCESS  read-only
   STATUS      current
   DESCRIPTION
       " Shows which ports are a part of this aggregation for this switch. "
   ::= { gs2326LACPSystemStatusEntry 6 }

gs2326LACPStatusTable OBJECT-TYPE
   SYNTAX      SEQUENCE OF Gs2326LACPStatusEntry
   MAX-ACCESS  not-accessible
   STATUS      current
   DESCRIPTION
       " "
   ::= { gs2326LACP 3 }

gs2326LACPStatusEntry OBJECT-TYPE
   SYNTAX      Gs2326LACPStatusEntry
   MAX-ACCESS  not-accessible
   STATUS      current
   DESCRIPTION
       ""
   INDEX    { gs2326LACPStatusPort  }
   ::= { gs2326LACPStatusTable 1 }

Gs2326LACPStatusEntry ::= SEQUENCE {
   gs2326LACPStatusPort                Integer32,
   gs2326LACPStatusLACP                DisplayString,
   gs2326LACPStatusKey                 DisplayString,
   gs2326LACPStatusAggrID              DisplayString,
   gs2326LACPStatusPartnerSystemID     DisplayString,
   gs2326LACPStatusPartnerPort         DisplayString
}

gs2326LACPStatusPort OBJECT-TYPE
   SYNTAX      Integer32(1..4095)
   MAX-ACCESS  not-accessible
   STATUS      current
   DESCRIPTION
       " "
   ::= { gs2326LACPStatusEntry 1 }

gs2326LACPStatusLACP OBJECT-TYPE
   SYNTAX      DisplayString
   MAX-ACCESS  read-only
   STATUS      current
   DESCRIPTION
       "Enabled means that LACP is enabled and the port link is up. 
        Disabled means that LACP is not enabled or that the port link is down. 
        Backup means that the port could not join the aggregation group but will join if other port leaves. 
        Meanwhile it's LACP status is disabled."
   ::= { gs2326LACPStatusEntry 2 }
   
gs2326LACPStatusKey OBJECT-TYPE
   SYNTAX      DisplayString
   MAX-ACCESS  read-only
   STATUS      current
   DESCRIPTION
       "The key assigned to this port. Only ports with the same key can aggregate together."
   ::= { gs2326LACPStatusEntry 3 }

gs2326LACPStatusAggrID	 OBJECT-TYPE
   SYNTAX      DisplayString
   MAX-ACCESS  read-only
   STATUS      current
   DESCRIPTION
       " The Aggregation ID assigned to this aggregation group. "
   ::= { gs2326LACPStatusEntry 4 }

gs2326LACPStatusPartnerSystemID OBJECT-TYPE
   SYNTAX      DisplayString
   MAX-ACCESS  read-only
   STATUS      current
   DESCRIPTION
       " The partner's System ID. "
   ::= { gs2326LACPStatusEntry 5 }
   
gs2326LACPStatusPartnerPort OBJECT-TYPE
   SYNTAX      DisplayString
   MAX-ACCESS  read-only
   STATUS      current
   DESCRIPTION
       " The partner's port number connected to this port. "
   ::= { gs2326LACPStatusEntry 6 }


gs2326LACPStatisticsTable OBJECT-TYPE
   SYNTAX      SEQUENCE OF Gs2326LACPStatisticsEntry
   MAX-ACCESS  not-accessible
   STATUS      current
   DESCRIPTION
       " "
   ::= { gs2326LACP 4 }

gs2326LACPStatisticsEntry OBJECT-TYPE
   SYNTAX      Gs2326LACPStatisticsEntry
   MAX-ACCESS  not-accessible
   STATUS      current
   DESCRIPTION
       ""
   INDEX    { gs2326LACPStatisticsPort  }
   ::= { gs2326LACPStatisticsTable 1 }

Gs2326LACPStatisticsEntry ::= SEQUENCE {
   gs2326LACPStatisticsPort        Integer32,
   gs2326LACPReceived              Counter32,
   gs2326LACPTransmitted           Counter32,
   gs2326LACPDiscardedUnknown      Counter32,
   gs2326LACPDiscardedIllegal      Counter32
}

gs2326LACPStatisticsPort OBJECT-TYPE
   SYNTAX      Integer32(1..4095)
   MAX-ACCESS  not-accessible
   STATUS      current
   DESCRIPTION
       " "
   ::= { gs2326LACPStatisticsEntry 1 }
   
gs2326LACPReceived OBJECT-TYPE
   SYNTAX      Counter32
   MAX-ACCESS  read-only
   STATUS      current
   DESCRIPTION
       "Shows how many LACP frames have been received at each port. "
   ::= { gs2326LACPStatisticsEntry 2 }

gs2326LACPTransmitted OBJECT-TYPE
   SYNTAX      Counter32
   MAX-ACCESS  read-only
   STATUS      current
   DESCRIPTION
       " Shows how many LACP frames have been sent from each port. "
   ::= { gs2326LACPStatisticsEntry 3 }

gs2326LACPDiscardedUnknown OBJECT-TYPE
   SYNTAX      Counter32
   MAX-ACCESS  read-only
   STATUS      current
   DESCRIPTION
       " Shows how many unknown LACP frames have been discarded at each port. "
   ::= { gs2326LACPStatisticsEntry 4 }
   
gs2326LACPDiscardedIllegal OBJECT-TYPE
   SYNTAX      Counter32
   MAX-ACCESS  read-only
   STATUS      current
   DESCRIPTION
       " Shows how many illegal LACP frames have been discarded at each port. "
   ::= { gs2326LACPStatisticsEntry 5 }
   
gs2326LACPStatisticsClear OBJECT-TYPE
   SYNTAX      INTEGER { none(0), clear(1) }
   MAX-ACCESS  read-write
   STATUS      current
   DESCRIPTION
       "default: 0
       0: none
       1: clear"
   ::= { gs2326LACP 5 }

gs2326STP                                                     OBJECT IDENTIFIER ::= { gs2326Configuration 20 }

gs2326STPBridgeBasicConf                                                 OBJECT IDENTIFIER ::= { gs2326STP 1 }

gs2326STPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2326STPBridgeBasicConf 1 }

gs2326STPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2326STPBridgeBasicConf 2 }
   
gs2326STPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2326STPBridgeBasicConf 3 }
   
gs2326STPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2326STPBridgeBasicConf 4 }
   
gs2326STPBridgeMaximumHopCount OBJECT-TYPE
   SYNTAX      Integer32(6..40)
   MAX-ACCESS  read-write
   STATUS      current
   DESCRIPTION
       " Maximum Hop Count default: 20, range: 6 - 40."
   ::= { gs2326STPBridgeBasicConf 5 }
   
gs2326STPBridgeTransmitHoldCount OBJECT-TYPE
   SYNTAX      Integer32(1..10)
   MAX-ACCESS  read-write
   STATUS      current
   DESCRIPTION
       " Transmit Hold Count default: 6, range: 1 - 10."
   ::= { gs2326STPBridgeBasicConf 6 }
   
gs2326STPBridgeAdvancedConf                                                 OBJECT IDENTIFIER ::= { gs2326STP 2 }

gs2326STPBridgeEdgePortBPDUFiltering OBJECT-TYPE
   SYNTAX      INTEGER { disable(0), enable(1) }
   MAX-ACCESS  read-write
   STATUS      current
   DESCRIPTION
       " default: 0,
        0: disable
        1: enable"
   ::= { gs2326STPBridgeAdvancedConf 1 }
   
gs2326STPBridgeEdgePortBPDUGuard OBJECT-TYPE
   SYNTAX      INTEGER { disable(0), enable(1) }
   MAX-ACCESS  read-write
   STATUS      current
   DESCRIPTION
       " default: 0,
        0: disable
        1: enable"
   ::= { gs2326STPBridgeAdvancedConf 2 }
   
gs2326STPBridgePortErrorRecoveryTimeout OBJECT-TYPE
   SYNTAX      Integer32(0..86400)
   MAX-ACCESS  read-write
   STATUS      current
   DESCRIPTION
       " Port Error Recovery Timeout disable: 0, range: 30 - 86400."
   ::= { gs2326STPBridgeAdvancedConf 3 }
   
gs2326STPMSTIConf                                                 OBJECT IDENTIFIER ::= { gs2326STP 3 }
   
gs2326STPMSTIConfigurationName OBJECT-TYPE
   SYNTAX      DisplayString (SIZE (1..32))
   MAX-ACCESS  read-write
   STATUS      current
   DESCRIPTION
       "A text string up to 32 characters long."
   ::= { gs2326STPMSTIConf 1 }
   
gs2326STPMSTIConfigurationRevision   OBJECT-TYPE
   SYNTAX      Integer32(0..65535)
   MAX-ACCESS  read-write
   STATUS      current
   DESCRIPTION
       " Configuration Revision default: 0, range: 0 - 65535."
   ::= { gs2326STPMSTIConf 2 }
   
gs2326STPMSTIMappingConf                                                 OBJECT IDENTIFIER ::= { gs2326STP 4 }
   
gs2326STPMSTI1VLANsMapped OBJECT-TYPE
   SYNTAX      DisplayString (SIZE (1..4096))
   MAX-ACCESS  read-write
   STATUS      current
   DESCRIPTION
       "The list of VLANs mapped to the MSTI1. 
       The VLANs must be separated with comma or space. 
       An unused MSTI should just be left empty. "
   ::= { gs2326STPMSTIMappingConf 1 }

gs2326STPMSTI2VLANsMapped OBJECT-TYPE
   SYNTAX      DisplayString (SIZE (1..4096))
   MAX-ACCESS  read-write
   STATUS      current
   DESCRIPTION
       "The list of VLANs mapped to the MSTI2. 
       The VLANs must be separated with comma or space. 
       An unused MSTI should just be left empty. "
   ::= { gs2326STPMSTIMappingConf 2 }
   
gs2326STPMSTI3VLANsMapped OBJECT-TYPE
   SYNTAX      DisplayString (SIZE (1..4096))
   MAX-ACCESS  read-write
   STATUS      current
   DESCRIPTION
       "The list of VLANs mapped to the MSTI3. 
       The VLANs must be separated with comma or space. 
       An unused MSTI should just be left empty. "
   ::= { gs2326STPMSTIMappingConf 3 }
   
gs2326STPMSTI4VLANsMapped OBJECT-TYPE
   SYNTAX      DisplayString (SIZE (1..4096))
   MAX-ACCESS  read-write
   STATUS      current
   DESCRIPTION
       "The list of VLANs mapped to the MSTI4. 
       The VLANs must be separated with comma or space. 
       An unused MSTI should just be left empty. "
   ::= { gs2326STPMSTIMappingConf 4 }
   
gs2326STPMSTI5VLANsMapped OBJECT-TYPE
   SYNTAX      DisplayString (SIZE (1..4096))
   MAX-ACCESS  read-write
   STATUS      current
   DESCRIPTION
       "The list of VLANs mapped to the MSTI5. 
       The VLANs must be separated with comma or space. 
       An unused MSTI should just be left empty. "
   ::= { gs2326STPMSTIMappingConf 5 }

gs2326STPMSTI6VLANsMapped OBJECT-TYPE
   SYNTAX      DisplayString (SIZE (1..4096))
   MAX-ACCESS  read-write
   STATUS      current
   DESCRIPTION
       "The list of VLANs mapped to the MSTI6. 
       The VLANs must be separated with comma or space. 
       An unused MSTI should just be left empty. "
   ::= { gs2326STPMSTIMappingConf 6 }
   
gs2326STPMSTI7VLANsMapped OBJECT-TYPE
   SYNTAX      DisplayString (SIZE (1..4096))
   MAX-ACCESS  read-write
   STATUS      current
   DESCRIPTION
       "The list of VLANs mapped to the MSTI7. 
       The VLANs must be separated with comma or space. 
       An unused MSTI should just be left empty. "
   ::= { gs2326STPMSTIMappingConf 7 }
   
gs2326STPMSTIPriority                                                 OBJECT IDENTIFIER ::= { gs2326STP 5 }
   
gs2326STPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326STPMSTIPriority 1 }
   
gs2326STPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326STPMSTIPriority 2 }
   
gs2326STPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326STPMSTIPriority 3 }
   
gs2326STPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326STPMSTIPriority 4 }
   
gs2326STPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326STPMSTIPriority 5 }
   
gs2326STPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326STPMSTIPriority 6 }

gs2326STPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326STPMSTIPriority 7 }  

gs2326STPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326STPMSTIPriority 8 }
   
gs2326STPCISTPort                                                          OBJECT IDENTIFIER ::= { gs2326STP 6 }

gs2326STPCISTAggregatedPort                                                OBJECT IDENTIFIER ::= { gs2326STPCISTPort 1 }
   
gs2326STPCISTAggregatedPortSTPEnabled OBJECT-TYPE
   SYNTAX      INTEGER { disable(0), enable(1) }
   MAX-ACCESS  read-write
   STATUS      current
   DESCRIPTION
       " default: 0,
        0: disable
        1: enable"
   ::= { gs2326STPCISTAggregatedPort 1 }
   
gs2326STPCISTAggregatedPortPathCost OBJECT-TYPE
   SYNTAX      Integer32(0..200000000)
   MAX-ACCESS  read-write
   STATUS      current
   DESCRIPTION
       " Auto: 0,
        Specific Path Cost range: 1 - 200000000."
   ::= { gs2326STPCISTAggregatedPort 2 }
   
gs2326STPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2326STPCISTAggregatedPort 3 }
   
gs2326STPCISTAggregatedPortAdminEdge OBJECT-TYPE
   SYNTAX      INTEGER { non-edge(0), edge(1) }
   MAX-ACCESS  read-write
   STATUS      current
   DESCRIPTION
       " default: 0,
        0: non-edge
        1: edge"
   ::= { gs2326STPCISTAggregatedPort 4 }

gs2326STPCISTAggregatedPortAutoEdge OBJECT-TYPE
   SYNTAX      INTEGER { disable(0), enable(1) }
   MAX-ACCESS  read-write
   STATUS      current
   DESCRIPTION
       " default: 1,
        0: disable
        1: enable"
   ::= { gs2326STPCISTAggregatedPort 5 }
   
gs2326STPCISTAggregatedPortRestrictedRole OBJECT-TYPE
   SYNTAX      INTEGER { disable(0), enable(1) }
   MAX-ACCESS  read-write
   STATUS      current
   DESCRIPTION
       " default: 0,
        0: disable
        1: enable"
   ::= { gs2326STPCISTAggregatedPort 6 }
   
gs2326STPCISTAggregatedPortRestrictedTCN OBJECT-TYPE
   SYNTAX      INTEGER { disable(0), enable(1) }
   MAX-ACCESS  read-write
   STATUS      current
   DESCRIPTION
       " default: 0,
        0: disable
        1: enable"
   ::= { gs2326STPCISTAggregatedPort 7 }
   
gs2326STPCISTAggregatedPortBPDUGuard OBJECT-TYPE
   SYNTAX      INTEGER { disable(0), enable(1) }
   MAX-ACCESS  read-write
   STATUS      current
   DESCRIPTION
       " default: 0,
        0: disable
        1: enable"
   ::= { gs2326STPCISTAggregatedPort 8 }
   
gs2326STPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2326STPCISTAggregatedPort 9 }
   
gs2326STPCISTNormalPortTable OBJECT-TYPE
   SYNTAX      SEQUENCE OF Gs2326STPCISTNormalPortEntry
   MAX-ACCESS  not-accessible
   STATUS      current
   DESCRIPTION
       " Show CIST Normal Port Configurations. "
   ::= { gs2326STPCISTPort 2 }

gs2326STPCISTNormalPortEntry OBJECT-TYPE
   SYNTAX      Gs2326STPCISTNormalPortEntry
   MAX-ACCESS  not-accessible
   STATUS      current
   DESCRIPTION
       ""
   INDEX    { gs2326STPCISTNormalPortConfPort  }
   ::= { gs2326STPCISTNormalPortTable 1 }

Gs2326STPCISTNormalPortEntry ::= SEQUENCE {
   gs2326STPCISTNormalPortConfPort         Integer32,
   gs2326STPCISTNormalPortSTPEnabled       INTEGER,
   gs2326STPCISTNormalPortPathCost         Integer32,
   gs2326STPCISTNormalPortPriority         Integer32,
   gs2326STPCISTNormalPortAdminEdge        INTEGER,
   gs2326STPCISTNormalPortAutoEdge         INTEGER,
   gs2326STPCISTNormalPortRestrictedRole   INTEGER,
   gs2326STPCISTNormalPortRestrictedTCN    INTEGER,
   gs2326STPCISTNormalPortBPDUGuard        INTEGER,
   gs2326STPCISTNormalPortPointtoPoint     INTEGER
}

gs2326STPCISTNormalPortConfPort OBJECT-TYPE
   SYNTAX      Integer32(1..4095)
   MAX-ACCESS  not-accessible
   STATUS      current
   DESCRIPTION
       " port, range : 1 - port number. "
   ::= { gs2326STPCISTNormalPortEntry 1 }
   
gs2326STPCISTNormalPortSTPEnabled OBJECT-TYPE
   SYNTAX      INTEGER { disable(0), enable(1) }
   MAX-ACCESS  read-write
   STATUS      current
   DESCRIPTION
       " default: 0,
        0: disable
        1: enable"
   ::= { gs2326STPCISTNormalPortEntry 2 }
   
gs2326STPCISTNormalPortPathCost OBJECT-TYPE
   SYNTAX      Integer32(0..200000000)
   MAX-ACCESS  read-write
   STATUS      current
   DESCRIPTION
       " Auto: 0,
        Specific Path Cost range: 1 - 200000000."
   ::= { gs2326STPCISTNormalPortEntry 3 }
   
gs2326STPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2326STPCISTNormalPortEntry 4 }
   
gs2326STPCISTNormalPortAdminEdge OBJECT-TYPE
   SYNTAX      INTEGER { non-edge(0), edge(1) }
   MAX-ACCESS  read-write
   STATUS      current
   DESCRIPTION
       " default: 0,
        0: non-edge
        1: edge"
   ::= { gs2326STPCISTNormalPortEntry 5 }
   
gs2326STPCISTNormalPortAutoEdge OBJECT-TYPE
   SYNTAX      INTEGER { disable(0), enable(1) }
   MAX-ACCESS  read-write
   STATUS      current
   DESCRIPTION
       " default: 1,
        0: disable
        1: enable"
   ::= { gs2326STPCISTNormalPortEntry 6 }
   
gs2326STPCISTNormalPortRestrictedRole OBJECT-TYPE
   SYNTAX      INTEGER { disable(0), enable(1) }
   MAX-ACCESS  read-write
   STATUS      current
   DESCRIPTION
       " default: 0,
        0: disable
        1: enable"
   ::= { gs2326STPCISTNormalPortEntry 7 }
   
gs2326STPCISTNormalPortRestrictedTCN OBJECT-TYPE
   SYNTAX      INTEGER { disable(0), enable(1) }
   MAX-ACCESS  read-write
   STATUS      current
   DESCRIPTION
       " default: 0,
        0: disable
        1: enable"
   ::= { gs2326STPCISTNormalPortEntry 8 }
   
gs2326STPCISTNormalPortBPDUGuard OBJECT-TYPE
   SYNTAX      INTEGER { disable(0), enable(1) }
   MAX-ACCESS  read-write
   STATUS      current
   DESCRIPTION
       " default: 0,
        0: disable
        1: enable"
   ::= { gs2326STPCISTNormalPortEntry 9 }
   
gs2326STPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2326STPCISTNormalPortEntry 10 }
   

gs2326STPMSTIPort                                                          OBJECT IDENTIFIER ::= { gs2326STP 7 }

gs2326STPMSTI1Port                                                         OBJECT IDENTIFIER ::= { gs2326STPMSTIPort 1 }

gs2326STPMSTI1AggregatedPort                                                OBJECT IDENTIFIER ::= { gs2326STPMSTI1Port 1 }
      
gs2326STPMSTI1AggregatedPortPathCost OBJECT-TYPE
   SYNTAX      Integer32(0..200000000)
   MAX-ACCESS  read-write
   STATUS      current
   DESCRIPTION
       " Auto: 0,
        Specific Path Cost range: 1 - 200000000."
   ::= { gs2326STPMSTI1AggregatedPort 1 }
   
gs2326STPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI1AggregatedPort 2 }
   
gs2326STPMSTI1NormalPortTable OBJECT-TYPE
   SYNTAX      SEQUENCE OF Gs2326STPMSTI1NormalPortEntry
   MAX-ACCESS  not-accessible
   STATUS      current
   DESCRIPTION
       " Show MSTI1 Normal Port Configurations. "
   ::= { gs2326STPMSTI1Port 2 }

gs2326STPMSTI1NormalPortEntry OBJECT-TYPE
   SYNTAX      Gs2326STPMSTI1NormalPortEntry
   MAX-ACCESS  not-accessible
   STATUS      current
   DESCRIPTION
       ""
   INDEX    { gs2326STPMSTI1NormalPortConfPort  }
   ::= { gs2326STPMSTI1NormalPortTable 1 }

Gs2326STPMSTI1NormalPortEntry ::= SEQUENCE {
   gs2326STPMSTI1NormalPortConfPort         Integer32,
   gs2326STPMSTI1NormalPortPathCost         Integer32,
   gs2326STPMSTI1NormalPortPriority         Integer32
}

gs2326STPMSTI1NormalPortConfPort OBJECT-TYPE
   SYNTAX      Integer32(1..4095)
   MAX-ACCESS  not-accessible
   STATUS      current
   DESCRIPTION
       " port, range : 1 - port number. "
   ::= { gs2326STPMSTI1NormalPortEntry 1 }
   
gs2326STPMSTI1NormalPortPathCost OBJECT-TYPE
   SYNTAX      Integer32(0..200000000)
   MAX-ACCESS  read-write
   STATUS      current
   DESCRIPTION
       " Auto: 0,
        Specific Path Cost range: 1 - 200000000."
   ::= { gs2326STPMSTI1NormalPortEntry 2 }
   
gs2326STPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI1NormalPortEntry 3 }

gs2326STPMSTI2Port                                                          OBJECT IDENTIFIER ::= { gs2326STPMSTIPort 2 }

gs2326STPMSTI2AggregatedPort                                                OBJECT IDENTIFIER ::= { gs2326STPMSTI2Port 1 }
      
gs2326STPMSTI2AggregatedPortPathCost OBJECT-TYPE
   SYNTAX      Integer32(0..200000000)
   MAX-ACCESS  read-write
   STATUS      current
   DESCRIPTION
       " Auto: 0,
        Specific Path Cost range: 1 - 200000000."
   ::= { gs2326STPMSTI2AggregatedPort 1 }
   
gs2326STPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI2AggregatedPort 2 }
   
gs2326STPMSTI2NormalPortTable OBJECT-TYPE
   SYNTAX      SEQUENCE OF Gs2326STPMSTI2NormalPortEntry
   MAX-ACCESS  not-accessible
   STATUS      current
   DESCRIPTION
       " Show MSTI2 Normal Port Configurations. "
   ::= { gs2326STPMSTI2Port 2 }

gs2326STPMSTI2NormalPortEntry OBJECT-TYPE
   SYNTAX      Gs2326STPMSTI2NormalPortEntry
   MAX-ACCESS  not-accessible
   STATUS      current
   DESCRIPTION
       ""
   INDEX    { gs2326STPMSTI2NormalPortConfPort  }
   ::= { gs2326STPMSTI2NormalPortTable 1 }

Gs2326STPMSTI2NormalPortEntry ::= SEQUENCE {
   gs2326STPMSTI2NormalPortConfPort         Integer32,
   gs2326STPMSTI2NormalPortPathCost         Integer32,
   gs2326STPMSTI2NormalPortPriority         Integer32
}

gs2326STPMSTI2NormalPortConfPort OBJECT-TYPE
   SYNTAX      Integer32(1..4095)
   MAX-ACCESS  not-accessible
   STATUS      current
   DESCRIPTION
       " port, range : 1 - port number. "
   ::= { gs2326STPMSTI2NormalPortEntry 1 }
   
gs2326STPMSTI2NormalPortPathCost OBJECT-TYPE
   SYNTAX      Integer32(0..200000000)
   MAX-ACCESS  read-write
   STATUS      current
   DESCRIPTION
       " Auto: 0,
        Specific Path Cost range: 1 - 200000000."
   ::= { gs2326STPMSTI2NormalPortEntry 2 }
   
gs2326STPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI2NormalPortEntry 3 }
   
gs2326STPMSTI3Port                                                          OBJECT IDENTIFIER ::= { gs2326STPMSTIPort 3 }

gs2326STPMSTI3AggregatedPort                                                OBJECT IDENTIFIER ::= { gs2326STPMSTI3Port 1 }
      
gs2326STPMSTI3AggregatedPortPathCost OBJECT-TYPE
   SYNTAX      Integer32(0..200000000)
   MAX-ACCESS  read-write
   STATUS      current
   DESCRIPTION
       " Auto: 0,
        Specific Path Cost range: 1 - 200000000."
   ::= { gs2326STPMSTI3AggregatedPort 1 }
   
gs2326STPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI3AggregatedPort 2 }
   
gs2326STPMSTI3NormalPortTable OBJECT-TYPE
   SYNTAX      SEQUENCE OF Gs2326STPMSTI3NormalPortEntry
   MAX-ACCESS  not-accessible
   STATUS      current
   DESCRIPTION
       " Show MSTI3 Normal Port Configurations. "
   ::= { gs2326STPMSTI3Port 2 }

gs2326STPMSTI3NormalPortEntry OBJECT-TYPE
   SYNTAX      Gs2326STPMSTI3NormalPortEntry
   MAX-ACCESS  not-accessible
   STATUS      current
   DESCRIPTION
       ""
   INDEX    { gs2326STPMSTI3NormalPortConfPort  }
   ::= { gs2326STPMSTI3NormalPortTable 1 }

Gs2326STPMSTI3NormalPortEntry ::= SEQUENCE {
   gs2326STPMSTI3NormalPortConfPort         Integer32,
   gs2326STPMSTI3NormalPortPathCost         Integer32,
   gs2326STPMSTI3NormalPortPriority         Integer32
}

gs2326STPMSTI3NormalPortConfPort OBJECT-TYPE
   SYNTAX      Integer32(1..4095)
   MAX-ACCESS  not-accessible
   STATUS      current
   DESCRIPTION
       " port, range : 1 - port number. "
   ::= { gs2326STPMSTI3NormalPortEntry 1 }
   
gs2326STPMSTI3NormalPortPathCost OBJECT-TYPE
   SYNTAX      Integer32(0..200000000)
   MAX-ACCESS  read-write
   STATUS      current
   DESCRIPTION
       " Auto: 0,
        Specific Path Cost range: 1 - 200000000."
   ::= { gs2326STPMSTI3NormalPortEntry 2 }
   
gs2326STPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI3NormalPortEntry 3 }
   
gs2326STPMSTI4Port                                                          OBJECT IDENTIFIER ::= { gs2326STPMSTIPort 4 }

gs2326STPMSTI4AggregatedPort                                                OBJECT IDENTIFIER ::= { gs2326STPMSTI4Port 1 }
      
gs2326STPMSTI4AggregatedPortPathCost OBJECT-TYPE
   SYNTAX      Integer32(0..200000000)
   MAX-ACCESS  read-write
   STATUS      current
   DESCRIPTION
       " Auto: 0,
        Specific Path Cost range: 1 - 200000000."
   ::= { gs2326STPMSTI4AggregatedPort 1 }
   
gs2326STPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI4AggregatedPort 2 }
   
gs2326STPMSTI4NormalPortTable OBJECT-TYPE
   SYNTAX      SEQUENCE OF Gs2326STPMSTI4NormalPortEntry
   MAX-ACCESS  not-accessible
   STATUS      current
   DESCRIPTION
       " Show MSTI4 Normal Port Configurations. "
   ::= { gs2326STPMSTI4Port 2 }

gs2326STPMSTI4NormalPortEntry OBJECT-TYPE
   SYNTAX      Gs2326STPMSTI4NormalPortEntry
   MAX-ACCESS  not-accessible
   STATUS      current
   DESCRIPTION
       ""
   INDEX    { gs2326STPMSTI4NormalPortConfPort  }
   ::= { gs2326STPMSTI4NormalPortTable 1 }

Gs2326STPMSTI4NormalPortEntry ::= SEQUENCE {
   gs2326STPMSTI4NormalPortConfPort         Integer32,
   gs2326STPMSTI4NormalPortPathCost         Integer32,
   gs2326STPMSTI4NormalPortPriority         Integer32
}

gs2326STPMSTI4NormalPortConfPort OBJECT-TYPE
   SYNTAX      Integer32(1..4095)
   MAX-ACCESS  not-accessible
   STATUS      current
   DESCRIPTION
       " port, range : 1 - port number. "
   ::= { gs2326STPMSTI4NormalPortEntry 1 }
   
gs2326STPMSTI4NormalPortPathCost OBJECT-TYPE
   SYNTAX      Integer32(0..200000000)
   MAX-ACCESS  read-write
   STATUS      current
   DESCRIPTION
       " Auto: 0,
        Specific Path Cost range: 1 - 200000000."
   ::= { gs2326STPMSTI4NormalPortEntry 2 }
   
gs2326STPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI4NormalPortEntry 3 }
   
gs2326STPMSTI5Port                                                          OBJECT IDENTIFIER ::= { gs2326STPMSTIPort 5 }

gs2326STPMSTI5AggregatedPort                                                OBJECT IDENTIFIER ::= { gs2326STPMSTI5Port 1 }
      
gs2326STPMSTI5AggregatedPortPathCost OBJECT-TYPE
   SYNTAX      Integer32(0..200000000)
   MAX-ACCESS  read-write
   STATUS      current
   DESCRIPTION
       " Auto: 0,
        Specific Path Cost range: 1 - 200000000."
   ::= { gs2326STPMSTI5AggregatedPort 1 }
   
gs2326STPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI5AggregatedPort 2 }
   
gs2326STPMSTI5NormalPortTable OBJECT-TYPE
   SYNTAX      SEQUENCE OF Gs2326STPMSTI5NormalPortEntry
   MAX-ACCESS  not-accessible
   STATUS      current
   DESCRIPTION
       " Show MSTI5 Normal Port Configurations. "
   ::= { gs2326STPMSTI5Port 2 }

gs2326STPMSTI5NormalPortEntry OBJECT-TYPE
   SYNTAX      Gs2326STPMSTI5NormalPortEntry
   MAX-ACCESS  not-accessible
   STATUS      current
   DESCRIPTION
       ""
   INDEX    { gs2326STPMSTI5NormalPortConfPort  }
   ::= { gs2326STPMSTI5NormalPortTable 1 }

Gs2326STPMSTI5NormalPortEntry ::= SEQUENCE {
   gs2326STPMSTI5NormalPortConfPort         Integer32,
   gs2326STPMSTI5NormalPortPathCost         Integer32,
   gs2326STPMSTI5NormalPortPriority         Integer32
}

gs2326STPMSTI5NormalPortConfPort OBJECT-TYPE
   SYNTAX      Integer32(1..4095)
   MAX-ACCESS  not-accessible
   STATUS      current
   DESCRIPTION
       " port, range : 1 - port number. "
   ::= { gs2326STPMSTI5NormalPortEntry 1 }
   
gs2326STPMSTI5NormalPortPathCost OBJECT-TYPE
   SYNTAX      Integer32(0..200000000)
   MAX-ACCESS  read-write
   STATUS      current
   DESCRIPTION
       " Auto: 0,
        Specific Path Cost range: 1 - 200000000."
   ::= { gs2326STPMSTI5NormalPortEntry 2 }
   
gs2326STPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI5NormalPortEntry 3 }
   
gs2326STPMSTI6Port                                                          OBJECT IDENTIFIER ::= { gs2326STPMSTIPort 6 }

gs2326STPMSTI6AggregatedPort                                                OBJECT IDENTIFIER ::= { gs2326STPMSTI6Port 1 }
      
gs2326STPMSTI6AggregatedPortPathCost OBJECT-TYPE
   SYNTAX      Integer32(0..200000000)
   MAX-ACCESS  read-write
   STATUS      current
   DESCRIPTION
       " Auto: 0,
        Specific Path Cost range: 1 - 200000000."
   ::= { gs2326STPMSTI6AggregatedPort 1 }
   
gs2326STPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI6AggregatedPort 2 }
   
gs2326STPMSTI6NormalPortTable OBJECT-TYPE
   SYNTAX      SEQUENCE OF Gs2326STPMSTI6NormalPortEntry
   MAX-ACCESS  not-accessible
   STATUS      current
   DESCRIPTION
       " Show MSTI6 Normal Port Configurations. "
   ::= { gs2326STPMSTI6Port 2 }

gs2326STPMSTI6NormalPortEntry OBJECT-TYPE
   SYNTAX      Gs2326STPMSTI6NormalPortEntry
   MAX-ACCESS  not-accessible
   STATUS      current
   DESCRIPTION
       ""
   INDEX    { gs2326STPMSTI6NormalPortConfPort  }
   ::= { gs2326STPMSTI6NormalPortTable 1 }

Gs2326STPMSTI6NormalPortEntry ::= SEQUENCE {
   gs2326STPMSTI6NormalPortConfPort         Integer32,
   gs2326STPMSTI6NormalPortPathCost         Integer32,
   gs2326STPMSTI6NormalPortPriority         Integer32
}

gs2326STPMSTI6NormalPortConfPort OBJECT-TYPE
   SYNTAX      Integer32(1..4095)
   MAX-ACCESS  not-accessible
   STATUS      current
   DESCRIPTION
       " port, range : 1 - port number. "
   ::= { gs2326STPMSTI6NormalPortEntry 1 }
   
gs2326STPMSTI6NormalPortPathCost OBJECT-TYPE
   SYNTAX      Integer32(0..200000000)
   MAX-ACCESS  read-write
   STATUS      current
   DESCRIPTION
       " Auto: 0,
        Specific Path Cost range: 1 - 200000000."
   ::= { gs2326STPMSTI6NormalPortEntry 2 }
   
gs2326STPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI6NormalPortEntry 3 }
   
gs2326STPMSTI7Port                                                          OBJECT IDENTIFIER ::= { gs2326STPMSTIPort 7 }

gs2326STPMSTI7AggregatedPort                                                OBJECT IDENTIFIER ::= { gs2326STPMSTI7Port 1 }
      
gs2326STPMSTI7AggregatedPortPathCost OBJECT-TYPE
   SYNTAX      Integer32(0..200000000)
   MAX-ACCESS  read-write
   STATUS      current
   DESCRIPTION
       " Auto: 0,
        Specific Path Cost range: 1 - 200000000."
   ::= { gs2326STPMSTI7AggregatedPort 1 }
   
gs2326STPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI7AggregatedPort 2 }
   
gs2326STPMSTI7NormalPortTable OBJECT-TYPE
   SYNTAX      SEQUENCE OF Gs2326STPMSTI7NormalPortEntry
   MAX-ACCESS  not-accessible
   STATUS      current
   DESCRIPTION
       " Show MSTI7 Normal Port Configurations. "
   ::= { gs2326STPMSTI7Port 2 }

gs2326STPMSTI7NormalPortEntry OBJECT-TYPE
   SYNTAX      Gs2326STPMSTI7NormalPortEntry
   MAX-ACCESS  not-accessible
   STATUS      current
   DESCRIPTION
       ""
   INDEX    { gs2326STPMSTI7NormalPortConfPort  }
   ::= { gs2326STPMSTI7NormalPortTable 1 }

Gs2326STPMSTI7NormalPortEntry ::= SEQUENCE {
   gs2326STPMSTI7NormalPortConfPort         Integer32,
   gs2326STPMSTI7NormalPortPathCost         Integer32,
   gs2326STPMSTI7NormalPortPriority         Integer32
}

gs2326STPMSTI7NormalPortConfPort OBJECT-TYPE
   SYNTAX      Integer32(1..4095)
   MAX-ACCESS  not-accessible
   STATUS      current
   DESCRIPTION
       " port, range : 1 - port number. "
   ::= { gs2326STPMSTI7NormalPortEntry 1 }
   
gs2326STPMSTI7NormalPortPathCost OBJECT-TYPE
   SYNTAX      Integer32(0..200000000)
   MAX-ACCESS  read-write
   STATUS      current
   DESCRIPTION
       " Auto: 0,
        Specific Path Cost range: 1 - 200000000."
   ::= { gs2326STPMSTI7NormalPortEntry 2 }
   
gs2326STPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326STPMSTI7NormalPortEntry 3 }
   

gs2326STPBridgeStatus                                                      OBJECT IDENTIFIER ::= { gs2326STP 8 }

gs2326CISTBridgeSTP                                                        OBJECT IDENTIFIER ::= { gs2326STPBridgeStatus 1 }

gs2326CISTBridgeSTPStatus                                                  OBJECT IDENTIFIER ::= { gs2326CISTBridgeSTP 1 }
      
gs2326CISTBridgeInstance OBJECT-TYPE
   SYNTAX       DisplayString
   MAX-ACCESS   read-only
   STATUS       current
   DESCRIPTION
       "The Bridge instance - CIST, MST1, ..."
   ::= { gs2326CISTBridgeSTPStatus 1 }
   
gs2326CISTBridgeID OBJECT-TYPE
   SYNTAX       DisplayString
   MAX-ACCESS   read-only
   STATUS       current
   DESCRIPTION
       "The Bridge ID of this Bridge instance."
   ::= { gs2326CISTBridgeSTPStatus 2 }
   
gs2326CISTRootID OBJECT-TYPE
   SYNTAX       DisplayString
   MAX-ACCESS   read-only
   STATUS       current
   DESCRIPTION
       "The Bridge ID of the currently elected root bridge."
   ::= { gs2326CISTBridgeSTPStatus 3 }
   
gs2326CISTRootPort OBJECT-TYPE
   SYNTAX       DisplayString
   MAX-ACCESS   read-only
   STATUS       current
   DESCRIPTION
       "The switch port currently assigned the root port role."
   ::= { gs2326CISTBridgeSTPStatus 4 }

gs2326CISTRootCost OBJECT-TYPE
   SYNTAX       Integer32(0..200000000)
   MAX-ACCESS   read-only
   STATUS       current
   DESCRIPTION
       "Root Path Cost."
   ::= { gs2326CISTBridgeSTPStatus 5 }
   
gs2326CISTRegionalRoot OBJECT-TYPE
   SYNTAX       DisplayString
   MAX-ACCESS   read-only
   STATUS       current
   DESCRIPTION
       "The Bridge ID of the currently elected regional root bridge, inside the MSTP region of this bridge."
   ::= { gs2326CISTBridgeSTPStatus 6 }
   
gs2326CISTInternalRootCost OBJECT-TYPE
   SYNTAX       Integer32(0..200000000)
   MAX-ACCESS   read-only
   STATUS       current
   DESCRIPTION
       "The Regional Root Path Cost."
   ::= { gs2326CISTBridgeSTPStatus 7 }

gs2326CISTTopologyFlag OBJECT-TYPE
   SYNTAX       DisplayString
   MAX-ACCESS   read-only
   STATUS       current
   DESCRIPTION
       "The current state of the Topology Change Flag of this Bridge instance."
   ::= { gs2326CISTBridgeSTPStatus 8 }

gs2326CISTTopologyChangeCount OBJECT-TYPE
   SYNTAX       Counter32
   MAX-ACCESS   read-only
   STATUS       current
   DESCRIPTION
       "The number of times where the topology change flag has been set."
   ::= { gs2326CISTBridgeSTPStatus 9 }
   
gs2326CISTTopologyChangeLast OBJECT-TYPE
   SYNTAX       DisplayString
   MAX-ACCESS   read-only
   STATUS       current
   DESCRIPTION
       "The time passed since the Topology Flag was last set."
   ::= { gs2326CISTBridgeSTPStatus 10 }
   
gs2326CISTPortStateTable OBJECT-TYPE
   SYNTAX      SEQUENCE OF Gs2326CISTPortStateEntry
   MAX-ACCESS  not-accessible
   STATUS      current
   DESCRIPTION
       " Show CIST Ports and Aggregations State Configurations. "
   ::= { gs2326CISTBridgeSTP 2 }

gs2326CISTPortStateEntry OBJECT-TYPE
   SYNTAX      Gs2326CISTPortStateEntry
   MAX-ACCESS  not-accessible
   STATUS      current
   DESCRIPTION
       ""
   INDEX    { gs2326CISTPortStateIndex  }
   ::= { gs2326CISTPortStateTable 1 }

Gs2326CISTPortStateEntry ::= SEQUENCE {
   gs2326CISTPortStateIndex        Integer32,
   gs2326CISTPortStatePort         DisplayString,
   gs2326CISTPortStatePortID       DisplayString,
   gs2326CISTPortStateRole         DisplayString,
   gs2326CISTPortStateState        DisplayString,
   gs2326CISTPortStatePathCost     Integer32,
   gs2326CISTPortStateEdge         DisplayString,
   gs2326CISTPortStatePoint2Point  DisplayString,
   gs2326CISTPortStateUptime       DisplayString
}

gs2326CISTPortStateIndex OBJECT-TYPE
   SYNTAX      Integer32(1..4095)
   MAX-ACCESS  not-accessible
   STATUS      current
   DESCRIPTION
       "table index."
   ::= { gs2326CISTPortStateEntry 1 }
   
gs2326CISTPortStatePort OBJECT-TYPE
   SYNTAX      DisplayString
   MAX-ACCESS  read-only
   STATUS      current
   DESCRIPTION
       "The switch port number of the logical STP port."
   ::= { gs2326CISTPortStateEntry 2 }
   
gs2326CISTPortStatePortID OBJECT-TYPE
   SYNTAX      DisplayString
   MAX-ACCESS  read-only
   STATUS      current
   DESCRIPTION
       "The port id as used by the STP protocol. 
        This is the priority part and the logical port index of the bridge port."
   ::= { gs2326CISTPortStateEntry 3 }
   
gs2326CISTPortStateRole OBJECT-TYPE
   SYNTAX      DisplayString
   MAX-ACCESS  read-only
   STATUS      current
   DESCRIPTION
       "The current STP port role."
   ::= { gs2326CISTPortStateEntry 4 }
   
gs2326CISTPortStateState OBJECT-TYPE
   SYNTAX      DisplayString
   MAX-ACCESS  read-only
   STATUS      current
   DESCRIPTION
       "The current STP port state."
   ::= { gs2326CISTPortStateEntry 5 }
   
gs2326CISTPortStatePathCost OBJECT-TYPE
   SYNTAX      Integer32(0..200000000)
   MAX-ACCESS  read-only
   STATUS      current
   DESCRIPTION
       "The current STP port path cost."
   ::= { gs2326CISTPortStateEntry 6 }
   
gs2326CISTPortStateEdge OBJECT-TYPE
   SYNTAX      DisplayString
   MAX-ACCESS  read-only
   STATUS      current
   DESCRIPTION
       "The current STP port Edge Flag."
   ::= { gs2326CISTPortStateEntry 7 }
   
gs2326CISTPortStatePoint2Point OBJECT-TYPE
   SYNTAX      DisplayString
   MAX-ACCESS  read-only
   STATUS      current
   DESCRIPTION
       "The current STP port point-to-point flag."
   ::= { gs2326CISTPortStateEntry 8 }
   
gs2326CISTPortStateUptime OBJECT-TYPE
   SYNTAX      DisplayString
   MAX-ACCESS  read-only
   STATUS      current
   DESCRIPTION
       "The time since the bridge port was last initialized."
   ::= { gs2326CISTPortStateEntry 9 }
   
gs2326MSTI1BridgeSTP                                                        OBJECT IDENTIFIER ::= { gs2326STPBridgeStatus 2 }

gs2326MSTI1BridgeSTPStatus                                                  OBJECT IDENTIFIER ::= { gs2326MSTI1BridgeSTP 1 }
      
gs2326MSTI1BridgeInstance OBJECT-TYPE
   SYNTAX       DisplayString
   MAX-ACCESS   read-only
   STATUS       current
   DESCRIPTION
       "The Bridge instance - CIST, MST1, ..."
   ::= { gs2326MSTI1BridgeSTPStatus 1 }
   
gs2326MSTI1BridgeID OBJECT-TYPE
   SYNTAX       DisplayString
   MAX-ACCESS   read-only
   STATUS       current
   DESCRIPTION
       "The Bridge ID of this Bridge instance."
   ::= { gs2326MSTI1BridgeSTPStatus 2 }
   
gs2326MSTI1RootID OBJECT-TYPE
   SYNTAX       DisplayString
   MAX-ACCESS   read-only
   STATUS       current
   DESCRIPTION
       "The Bridge ID of the currently elected root bridge."
   ::= { gs2326MSTI1BridgeSTPStatus 3 }
   
gs2326MSTI1RootPort OBJECT-TYPE
   SYNTAX       DisplayString
   MAX-ACCESS   read-only
   STATUS       current
   DESCRIPTION
       "The switch port currently assigned the root port role."
   ::= { gs2326MSTI1BridgeSTPStatus 4 }

gs2326MSTI1RootCost OBJECT-TYPE
   SYNTAX       Integer32(0..200000000)
   MAX-ACCESS   read-only
   STATUS       current
   DESCRIPTION
       "Root Path Cost."
   ::= { gs2326MSTI1BridgeSTPStatus 5 }

gs2326MSTI1TopologyFlag OBJECT-TYPE
   SYNTAX       DisplayString
   MAX-ACCESS   read-only
   STATUS       current
   DESCRIPTION
       "The current state of the Topology Change Flag of this Bridge instance."
   ::= { gs2326MSTI1BridgeSTPStatus 8 }

gs2326MSTI1TopologyChangeCount OBJECT-TYPE
   SYNTAX       Counter32
   MAX-ACCESS   read-only
   STATUS       current
   DESCRIPTION
       "The number of times where the topology change flag has been set."
   ::= { gs2326MSTI1BridgeSTPStatus 9 }
   
gs2326MSTI1TopologyChangeLast OBJECT-TYPE
   SYNTAX       DisplayString
   MAX-ACCESS   read-only
   STATUS       current
   DESCRIPTION
       "The time passed since the Topology Flag was last set."
   ::= { gs2326MSTI1BridgeSTPStatus 10 }
   
gs2326MSTI1PortStateTable OBJECT-TYPE
   SYNTAX      SEQUENCE OF Gs2326MSTI1PortStateEntry
   MAX-ACCESS  not-accessible
   STATUS      current
   DESCRIPTION
       " Show MSTI1 Ports and Aggregations State Configurations. "
   ::= { gs2326MSTI1BridgeSTP 2 }

gs2326MSTI1PortStateEntry OBJECT-TYPE
   SYNTAX      Gs2326MSTI1PortStateEntry
   MAX-ACCESS  not-accessible
   STATUS      current
   DESCRIPTION
       ""
   INDEX    { gs2326MSTI1PortStateIndex  }
   ::= { gs2326MSTI1PortStateTable 1 }

Gs2326MSTI1PortStateEntry ::= SEQUENCE {
   gs2326MSTI1PortStateIndex        Integer32,
   gs2326MSTI1PortStatePort         DisplayString,
   gs2326MSTI1PortStatePortID       DisplayString,
   gs2326MSTI1PortStateRole         DisplayString,
   gs2326MSTI1PortStateState        DisplayString,
   gs2326MSTI1PortStatePathCost     Integer32,
   gs2326MSTI1PortStateEdge         DisplayString,
   gs2326MSTI1PortStatePoint2Point  DisplayString,
   gs2326MSTI1PortStateUptime       DisplayString
}

gs2326MSTI1PortStateIndex OBJECT-TYPE
   SYNTAX      Integer32(1..4095)
   MAX-ACCESS  not-accessible
   STATUS      current
   DESCRIPTION
       "table index."
   ::= { gs2326MSTI1PortStateEntry 1 }
   
gs2326MSTI1PortStatePort OBJECT-TYPE
   SYNTAX      DisplayString
   MAX-ACCESS  read-only
   STATUS      current
   DESCRIPTION
       "The switch port number of the logical STP port."
   ::= { gs2326MSTI1PortStateEntry 2 }
   
gs2326MSTI1PortStatePortID OBJECT-TYPE
   SYNTAX      DisplayString
   MAX-ACCESS  read-only
   STATUS      current
   DESCRIPTION
       "The port id as used by the STP protocol. 
        This is the priority part and the logical port index of the bridge port."
   ::= { gs2326MSTI1PortStateEntry 3 }
   
gs2326MSTI1PortStateRole OBJECT-TYPE
   SYNTAX      DisplayString
   MAX-ACCESS  read-only
   STATUS      current
   DESCRIPTION
       "The current STP port role."
   ::= { gs2326MSTI1PortStateEntry 4 }
   
gs2326MSTI1PortStateState OBJECT-TYPE
   SYNTAX      DisplayString
   MAX-ACCESS  read-only
   STATUS      current
   DESCRIPTION
       "The current STP port state."
   ::= { gs2326MSTI1PortStateEntry 5 }
   
gs2326MSTI1PortStatePathCost OBJECT-TYPE
   SYNTAX      Integer32(0..200000000)
   MAX-ACCESS  read-only
   STATUS      current
   DESCRIPTION
       "The current STP port path cost."
   ::= { gs2326MSTI1PortStateEntry 6 }
   
gs2326MSTI1PortStateEdge OBJECT-TYPE
   SYNTAX      DisplayString
   MAX-ACCESS  read-only
   STATUS      current
   DESCRIPTION
       "The current STP port Edge Flag."
   ::= { gs2326MSTI1PortStateEntry 7 }
   
gs2326MSTI1PortStatePoint2Point OBJECT-TYPE
   SYNTAX      DisplayString
   MAX-ACCESS  read-only
   STATUS      current
   DESCRIPTION
       "The current STP port point-to-point flag."
   ::= { gs2326MSTI1PortStateEntry 8 }
   
gs2326MSTI1PortStateUptime OBJECT-TYPE
   SYNTAX      DisplayString
   MAX-ACCESS  read-only
   STATUS      current
   DESCRIPTION
       "The time since the bridge port was last initialized."
   ::= { gs2326MSTI1PortStateEntry 9 }
   
gs2326MSTI2BridgeSTP                                                        OBJECT IDENTIFIER ::= { gs2326STPBridgeStatus 3 }

gs2326MSTI2BridgeSTPStatus                                                  OBJECT IDENTIFIER ::= { gs2326MSTI2BridgeSTP 1 }
      
gs2326MSTI2BridgeInstance OBJECT-TYPE
   SYNTAX       DisplayString
   MAX-ACCESS   read-only
   STATUS       current
   DESCRIPTION
       "The Bridge instance - CIST, MST1, ..."
   ::= { gs2326MSTI2BridgeSTPStatus 1 }
   
gs2326MSTI2BridgeID OBJECT-TYPE
   SYNTAX       DisplayString
   MAX-ACCESS   read-only
   STATUS       current
   DESCRIPTION
       "The Bridge ID of this Bridge instance."
   ::= { gs2326MSTI2BridgeSTPStatus 2 }
   
gs2326MSTI2RootID OBJECT-TYPE
   SYNTAX       DisplayString
   MAX-ACCESS   read-only
   STATUS       current
   DESCRIPTION
       "The Bridge ID of the currently elected root bridge."
   ::= { gs2326MSTI2BridgeSTPStatus 3 }
   
gs2326MSTI2RootPort OBJECT-TYPE
   SYNTAX       DisplayString
   MAX-ACCESS   read-only
   STATUS       current
   DESCRIPTION
       "The switch port currently assigned the root port role."
   ::= { gs2326MSTI2BridgeSTPStatus 4 }

gs2326MSTI2RootCost OBJECT-TYPE
   SYNTAX       Integer32(0..200000000)
   MAX-ACCESS   read-only
   STATUS       current
   DESCRIPTION
       "Root Path Cost."
   ::= { gs2326MSTI2BridgeSTPStatus 5 }

gs2326MSTI2TopologyFlag OBJECT-TYPE
   SYNTAX       DisplayString
   MAX-ACCESS   read-only
   STATUS       current
   DESCRIPTION
       "The current state of the Topology Change Flag of this Bridge instance."
   ::= { gs2326MSTI2BridgeSTPStatus 8 }

gs2326MSTI2TopologyChangeCount OBJECT-TYPE
   SYNTAX       Counter32
   MAX-ACCESS   read-only
   STATUS       current
   DESCRIPTION
       "The number of times where the topology change flag has been set."
   ::= { gs2326MSTI2BridgeSTPStatus 9 }
   
gs2326MSTI2TopologyChangeLast OBJECT-TYPE
   SYNTAX       DisplayString
   MAX-ACCESS   read-only
   STATUS       current
   DESCRIPTION
       "The time passed since the Topology Flag was last set."
   ::= { gs2326MSTI2BridgeSTPStatus 10 }
   
gs2326MSTI2PortStateTable OBJECT-TYPE
   SYNTAX      SEQUENCE OF Gs2326MSTI2PortStateEntry
   MAX-ACCESS  not-accessible
   STATUS      current
   DESCRIPTION
       " Show MSTI2 Ports and Aggregations State Configurations. "
   ::= { gs2326MSTI2BridgeSTP 2 }

gs2326MSTI2PortStateEntry OBJECT-TYPE
   SYNTAX      Gs2326MSTI2PortStateEntry
   MAX-ACCESS  not-accessible
   STATUS      current
   DESCRIPTION
       ""
   INDEX    { gs2326MSTI2PortStateIndex  }
   ::= { gs2326MSTI2PortStateTable 1 }

Gs2326MSTI2PortStateEntry ::= SEQUENCE {
   gs2326MSTI2PortStateIndex        Integer32,
   gs2326MSTI2PortStatePort         DisplayString,
   gs2326MSTI2PortStatePortID       DisplayString,
   gs2326MSTI2PortStateRole         DisplayString,
   gs2326MSTI2PortStateState        DisplayString,
   gs2326MSTI2PortStatePathCost     Integer32,
   gs2326MSTI2PortStateEdge         DisplayString,
   gs2326MSTI2PortStatePoint2Point  DisplayString,
   gs2326MSTI2PortStateUptime       DisplayString
}

gs2326MSTI2PortStateIndex OBJECT-TYPE
   SYNTAX      Integer32(1..4095)
   MAX-ACCESS  not-accessible
   STATUS      current
   DESCRIPTION
       "table index."
   ::= { gs2326MSTI2PortStateEntry 1 }
   
gs2326MSTI2PortStatePort OBJECT-TYPE
   SYNTAX      DisplayString
   MAX-ACCESS  read-only
   STATUS      current
   DESCRIPTION
       "The switch port number of the logical STP port."
   ::= { gs2326MSTI2PortStateEntry 2 }
   
gs2326MSTI2PortStatePortID OBJECT-TYPE
   SYNTAX      DisplayString
   MAX-ACCESS  read-only
   STATUS      current
   DESCRIPTION
       "The port id as used by the STP protocol. 
        This is the priority part and the logical port index of the bridge port."
   ::= { gs2326MSTI2PortStateEntry 3 }
   
gs2326MSTI2PortStateRole OBJECT-TYPE
   SYNTAX      DisplayString
   MAX-ACCESS  read-only
   STATUS      current
   DESCRIPTION
       "The current STP port role."
   ::= { gs2326MSTI2PortStateEntry 4 }
   
gs2326MSTI2PortStateState OBJECT-TYPE
   SYNTAX      DisplayString
   MAX-ACCESS  read-only
   STATUS      current
   DESCRIPTION
       "The current STP port state."
   ::= { gs2326MSTI2PortStateEntry 5 }
   
gs2326MSTI2PortStatePathCost OBJECT-TYPE
   SYNTAX      Integer32(0..200000000)
   MAX-ACCESS  read-only
   STATUS      current
   DESCRIPTION
       "The current STP port path cost."
   ::= { gs2326MSTI2PortStateEntry 6 }
   
gs2326MSTI2PortStateEdge OBJECT-TYPE
   SYNTAX      DisplayString
   MAX-ACCESS  read-only
   STATUS      current
   DESCRIPTION
       "The current STP port Edge Flag."
   ::= { gs2326MSTI2PortStateEntry 7 }
   
gs2326MSTI2PortStatePoint2Point OBJECT-TYPE
   SYNTAX      DisplayString
   MAX-ACCESS  read-only
   STATUS      current
   DESCRIPTION
       "The current STP port point-to-point flag."
   ::= { gs2326MSTI2PortStateEntry 8 }
   
gs2326MSTI2PortStateUptime OBJECT-TYPE
   SYNTAX      DisplayString
   MAX-ACCESS  read-only
   STATUS      current
   DESCRIPTION
       "The time since the bridge port was last initialized."
   ::= { gs2326MSTI2PortStateEntry 9 }

gs2326MSTI3BridgeSTP                                                        OBJECT IDENTIFIER ::= { gs2326STPBridgeStatus 4 }

gs2326MSTI3BridgeSTPStatus                                                  OBJECT IDENTIFIER ::= { gs2326MSTI3BridgeSTP 1 }
      
gs2326MSTI3BridgeInstance OBJECT-TYPE
   SYNTAX       DisplayString
   MAX-ACCESS   read-only
   STATUS       current
   DESCRIPTION
       "The Bridge instance - CIST, MST1, ..."
   ::= { gs2326MSTI3BridgeSTPStatus 1 }
   
gs2326MSTI3BridgeID OBJECT-TYPE
   SYNTAX       DisplayString
   MAX-ACCESS   read-only
   STATUS       current
   DESCRIPTION
       "The Bridge ID of this Bridge instance."
   ::= { gs2326MSTI3BridgeSTPStatus 2 }
   
gs2326MSTI3RootID OBJECT-TYPE
   SYNTAX       DisplayString
   MAX-ACCESS   read-only
   STATUS       current
   DESCRIPTION
       "The Bridge ID of the currently elected root bridge."
   ::= { gs2326MSTI3BridgeSTPStatus 3 }
   
gs2326MSTI3RootPort OBJECT-TYPE
   SYNTAX       DisplayString
   MAX-ACCESS   read-only
   STATUS       current
   DESCRIPTION
       "The switch port currently assigned the root port role."
   ::= { gs2326MSTI3BridgeSTPStatus 4 }

gs2326MSTI3RootCost OBJECT-TYPE
   SYNTAX       Integer32(0..200000000)
   MAX-ACCESS   read-only
   STATUS       current
   DESCRIPTION
       "Root Path Cost."
   ::= { gs2326MSTI3BridgeSTPStatus 5 }

gs2326MSTI3TopologyFlag OBJECT-TYPE
   SYNTAX       DisplayString
   MAX-ACCESS   read-only
   STATUS       current
   DESCRIPTION
       "The current state of the Topology Change Flag of this Bridge instance."
   ::= { gs2326MSTI3BridgeSTPStatus 8 }

gs2326MSTI3TopologyChangeCount OBJECT-TYPE
   SYNTAX       Counter32
   MAX-ACCESS   read-only
   STATUS       current
   DESCRIPTION
       "The number of times where the topology change flag has been set."
   ::= { gs2326MSTI3BridgeSTPStatus 9 }
   
gs2326MSTI3TopologyChangeLast OBJECT-TYPE
   SYNTAX       DisplayString
   MAX-ACCESS   read-only
   STATUS       current
   DESCRIPTION
       "The time passed since the Topology Flag was last set."
   ::= { gs2326MSTI3BridgeSTPStatus 10 }
   
gs2326MSTI3PortStateTable OBJECT-TYPE
   SYNTAX      SEQUENCE OF Gs2326MSTI3PortStateEntry
   MAX-ACCESS  not-accessible
   STATUS      current
   DESCRIPTION
       " Show MSTI3 Ports and Aggregations State Configurations. "
   ::= { gs2326MSTI3BridgeSTP 2 }

gs2326MSTI3PortStateEntry OBJECT-TYPE
   SYNTAX      Gs2326MSTI3PortStateEntry
   MAX-ACCESS  not-accessible
   STATUS      current
   DESCRIPTION
       ""
   INDEX    { gs2326MSTI3PortStateIndex  }
   ::= { gs2326MSTI3PortStateTable 1 }

Gs2326MSTI3PortStateEntry ::= SEQUENCE {
   gs2326MSTI3PortStateIndex        Integer32,
   gs2326MSTI3PortStatePort         DisplayString,
   gs2326MSTI3PortStatePortID       DisplayString,
   gs2326MSTI3PortStateRole         DisplayString,
   gs2326MSTI3PortStateState        DisplayString,
   gs2326MSTI3PortStatePathCost     Integer32,
   gs2326MSTI3PortStateEdge         DisplayString,
   gs2326MSTI3PortStatePoint2Point  DisplayString,
   gs2326MSTI3PortStateUptime       DisplayString
}

gs2326MSTI3PortStateIndex OBJECT-TYPE
   SYNTAX      Integer32(1..4095)
   MAX-ACCESS  not-accessible
   STATUS      current
   DESCRIPTION
       "table index."
   ::= { gs2326MSTI3PortStateEntry 1 }
   
gs2326MSTI3PortStatePort OBJECT-TYPE
   SYNTAX      DisplayString
   MAX-ACCESS  read-only
   STATUS      current
   DESCRIPTION
       "The switch port number of the logical STP port."
   ::= { gs2326MSTI3PortStateEntry 2 }
   
gs2326MSTI3PortStatePortID OBJECT-TYPE
   SYNTAX      DisplayString
   MAX-ACCESS  read-only
   STATUS      current
   DESCRIPTION
       "The port id as used by the STP protocol. 
        This is the priority part and the logical port index of the bridge port."
   ::= { gs2326MSTI3PortStateEntry 3 }
   
gs2326MSTI3PortStateRole OBJECT-TYPE
   SYNTAX      DisplayString
   MAX-ACCESS  read-only
   STATUS      current
   DESCRIPTION
       "The current STP port role."
   ::= { gs2326MSTI3PortStateEntry 4 }
   
gs2326MSTI3PortStateState OBJECT-TYPE
   SYNTAX      DisplayString
   MAX-ACCESS  read-only
   STATUS      current
   DESCRIPTION
       "The current STP port state."
   ::= { gs2326MSTI3PortStateEntry 5 }
   
gs2326MSTI3PortStatePathCost OBJECT-TYPE
   SYNTAX      Integer32(0..200000000)
   MAX-ACCESS  read-only
   STATUS      current
   DESCRIPTION
       "The current STP port path cost."
   ::= { gs2326MSTI3PortStateEntry 6 }
   
gs2326MSTI3PortStateEdge OBJECT-TYPE
   SYNTAX      DisplayString
   MAX-ACCESS  read-only
   STATUS      current
   DESCRIPTION
       "The current STP port Edge Flag."
   ::= { gs2326MSTI3PortStateEntry 7 }
   
gs2326MSTI3PortStatePoint2Point OBJECT-TYPE
   SYNTAX      DisplayString
   MAX-ACCESS  read-only
   STATUS      current
   DESCRIPTION
       "The current STP port point-to-point flag."
   ::= { gs2326MSTI3PortStateEntry 8 }
   
gs2326MSTI3PortStateUptime OBJECT-TYPE
   SYNTAX      DisplayString
   MAX-ACCESS  read-only
   STATUS      current
   DESCRIPTION
       "The time since the bridge port was last initialized."
   ::= { gs2326MSTI3PortStateEntry 9 }
   
gs2326MSTI4BridgeSTP                                                        OBJECT IDENTIFIER ::= { gs2326STPBridgeStatus 5 }

gs2326MSTI4BridgeSTPStatus                                                  OBJECT IDENTIFIER ::= { gs2326MSTI4BridgeSTP 1 }
      
gs2326MSTI4BridgeInstance OBJECT-TYPE
   SYNTAX       DisplayString
   MAX-ACCESS   read-only
   STATUS       current
   DESCRIPTION
       "The Bridge instance - CIST, MST1, ..."
   ::= { gs2326MSTI4BridgeSTPStatus 1 }
   
gs2326MSTI4BridgeID OBJECT-TYPE
   SYNTAX       DisplayString
   MAX-ACCESS   read-only
   STATUS       current
   DESCRIPTION
       "The Bridge ID of this Bridge instance."
   ::= { gs2326MSTI4BridgeSTPStatus 2 }
   
gs2326MSTI4RootID OBJECT-TYPE
   SYNTAX       DisplayString
   MAX-ACCESS   read-only
   STATUS       current
   DESCRIPTION
       "The Bridge ID of the currently elected root bridge."
   ::= { gs2326MSTI4BridgeSTPStatus 3 }
   
gs2326MSTI4RootPort OBJECT-TYPE
   SYNTAX       DisplayString
   MAX-ACCESS   read-only
   STATUS       current
   DESCRIPTION
       "The switch port currently assigned the root port role."
   ::= { gs2326MSTI4BridgeSTPStatus 4 }

gs2326MSTI4RootCost OBJECT-TYPE
   SYNTAX       Integer32(0..200000000)
   MAX-ACCESS   read-only
   STATUS       current
   DESCRIPTION
       "Root Path Cost."
   ::= { gs2326MSTI4BridgeSTPStatus 5 }

gs2326MSTI4TopologyFlag OBJECT-TYPE
   SYNTAX       DisplayString
   MAX-ACCESS   read-only
   STATUS       current
   DESCRIPTION
       "The current state of the Topology Change Flag of this Bridge instance."
   ::= { gs2326MSTI4BridgeSTPStatus 8 }

gs2326MSTI4TopologyChangeCount OBJECT-TYPE
   SYNTAX       Counter32
   MAX-ACCESS   read-only
   STATUS       current
   DESCRIPTION
       "The number of times where the topology change flag has been set."
   ::= { gs2326MSTI4BridgeSTPStatus 9 }
   
gs2326MSTI4TopologyChangeLast OBJECT-TYPE
   SYNTAX       DisplayString
   MAX-ACCESS   read-only
   STATUS       current
   DESCRIPTION
       "The time passed since the Topology Flag was last set."
   ::= { gs2326MSTI4BridgeSTPStatus 10 }
   
gs2326MSTI4PortStateTable OBJECT-TYPE
   SYNTAX      SEQUENCE OF Gs2326MSTI4PortStateEntry
   MAX-ACCESS  not-accessible
   STATUS      current
   DESCRIPTION
       " Show MSTI4 Ports and Aggregations State Configurations. "
   ::= { gs2326MSTI4BridgeSTP 2 }

gs2326MSTI4PortStateEntry OBJECT-TYPE
   SYNTAX      Gs2326MSTI4PortStateEntry
   MAX-ACCESS  not-accessible
   STATUS      current
   DESCRIPTION
       ""
   INDEX    { gs2326MSTI4PortStateIndex  }
   ::= { gs2326MSTI4PortStateTable 1 }

Gs2326MSTI4PortStateEntry ::= SEQUENCE {
   gs2326MSTI4PortStateIndex        Integer32,
   gs2326MSTI4PortStatePort         DisplayString,
   gs2326MSTI4PortStatePortID       DisplayString,
   gs2326MSTI4PortStateRole         DisplayString,
   gs2326MSTI4PortStateState        DisplayString,
   gs2326MSTI4PortStatePathCost     Integer32,
   gs2326MSTI4PortStateEdge         DisplayString,
   gs2326MSTI4PortStatePoint2Point  DisplayString,
   gs2326MSTI4PortStateUptime       DisplayString
}

gs2326MSTI4PortStateIndex OBJECT-TYPE
   SYNTAX      Integer32(1..4095)
   MAX-ACCESS  not-accessible
   STATUS      current
   DESCRIPTION
       "table index."
   ::= { gs2326MSTI4PortStateEntry 1 }
   
gs2326MSTI4PortStatePort OBJECT-TYPE
   SYNTAX      DisplayString
   MAX-ACCESS  read-only
   STATUS      current
   DESCRIPTION
       "The switch port number of the logical STP port."
   ::= { gs2326MSTI4PortStateEntry 2 }
   
gs2326MSTI4PortStatePortID OBJECT-TYPE
   SYNTAX      DisplayString
   MAX-ACCESS  read-only
   STATUS      current
   DESCRIPTION
       "The port id as used by the STP protocol. 
        This is the priority part and the logical port index of the bridge port."
   ::= { gs2326MSTI4PortStateEntry 3 }
   
gs2326MSTI4PortStateRole OBJECT-TYPE
   SYNTAX      DisplayString
   MAX-ACCESS  read-only
   STATUS      current
   DESCRIPTION
       "The current STP port role."
   ::= { gs2326MSTI4PortStateEntry 4 }
   
gs2326MSTI4PortStateState OBJECT-TYPE
   SYNTAX      DisplayString
   MAX-ACCESS  read-only
   STATUS      current
   DESCRIPTION
       "The current STP port state."
   ::= { gs2326MSTI4PortStateEntry 5 }
   
gs2326MSTI4PortStatePathCost OBJECT-TYPE
   SYNTAX      Integer32(0..200000000)
   MAX-ACCESS  read-only
   STATUS      current
   DESCRIPTION
       "The current STP port path cost."
   ::= { gs2326MSTI4PortStateEntry 6 }
   
gs2326MSTI4PortStateEdge OBJECT-TYPE
   SYNTAX      DisplayString
   MAX-ACCESS  read-only
   STATUS      current
   DESCRIPTION
       "The current STP port Edge Flag."
   ::= { gs2326MSTI4PortStateEntry 7 }
   
gs2326MSTI4PortStatePoint2Point OBJECT-TYPE
   SYNTAX      DisplayString
   MAX-ACCESS  read-only
   STATUS      current
   DESCRIPTION
       "The current STP port point-to-point flag."
   ::= { gs2326MSTI4PortStateEntry 8 }
   
gs2326MSTI4PortStateUptime OBJECT-TYPE
   SYNTAX      DisplayString
   MAX-ACCESS  read-only
   STATUS      current
   DESCRIPTION
       "The time since the bridge port was last initialized."
   ::= { gs2326MSTI4PortStateEntry 9 }
   
gs2326MSTI5BridgeSTP                                                        OBJECT IDENTIFIER ::= { gs2326STPBridgeStatus 6 }

gs2326MSTI5BridgeSTPStatus                                                  OBJECT IDENTIFIER ::= { gs2326MSTI5BridgeSTP 1 }
      
gs2326MSTI5BridgeInstance OBJECT-TYPE
   SYNTAX       DisplayString
   MAX-ACCESS   read-only
   STATUS       current
   DESCRIPTION
       "The Bridge instance - CIST, MST1, ..."
   ::= { gs2326MSTI5BridgeSTPStatus 1 }
   
gs2326MSTI5BridgeID OBJECT-TYPE
   SYNTAX       DisplayString
   MAX-ACCESS   read-only
   STATUS       current
   DESCRIPTION
       "The Bridge ID of this Bridge instance."
   ::= { gs2326MSTI5BridgeSTPStatus 2 }
   
gs2326MSTI5RootID OBJECT-TYPE
   SYNTAX       DisplayString
   MAX-ACCESS   read-only
   STATUS       current
   DESCRIPTION
       "The Bridge ID of the currently elected root bridge."
   ::= { gs2326MSTI5BridgeSTPStatus 3 }
   
gs2326MSTI5RootPort OBJECT-TYPE
   SYNTAX       DisplayString
   MAX-ACCESS   read-only
   STATUS       current
   DESCRIPTION
       "The switch port currently assigned the root port role."
   ::= { gs2326MSTI5BridgeSTPStatus 4 }

gs2326MSTI5RootCost OBJECT-TYPE
   SYNTAX       Integer32(0..200000000)
   MAX-ACCESS   read-only
   STATUS       current
   DESCRIPTION
       "Root Path Cost."
   ::= { gs2326MSTI5BridgeSTPStatus 5 }

gs2326MSTI5TopologyFlag OBJECT-TYPE
   SYNTAX       DisplayString
   MAX-ACCESS   read-only
   STATUS       current
   DESCRIPTION
       "The current state of the Topology Change Flag of this Bridge instance."
   ::= { gs2326MSTI5BridgeSTPStatus 8 }

gs2326MSTI5TopologyChangeCount OBJECT-TYPE
   SYNTAX       Counter32
   MAX-ACCESS   read-only
   STATUS       current
   DESCRIPTION
       "The number of times where the topology change flag has been set."
   ::= { gs2326MSTI5BridgeSTPStatus 9 }
   
gs2326MSTI5TopologyChangeLast OBJECT-TYPE
   SYNTAX       DisplayString
   MAX-ACCESS   read-only
   STATUS       current
   DESCRIPTION
       "The time passed since the Topology Flag was last set."
   ::= { gs2326MSTI5BridgeSTPStatus 10 }
   
gs2326MSTI5PortStateTable OBJECT-TYPE
   SYNTAX      SEQUENCE OF Gs2326MSTI5PortStateEntry
   MAX-ACCESS  not-accessible
   STATUS      current
   DESCRIPTION
       " Show MSTI5 Ports and Aggregations State Configurations. "
   ::= { gs2326MSTI5BridgeSTP 2 }

gs2326MSTI5PortStateEntry OBJECT-TYPE
   SYNTAX      Gs2326MSTI5PortStateEntry
   MAX-ACCESS  not-accessible
   STATUS      current
   DESCRIPTION
       ""
   INDEX    { gs2326MSTI5PortStateIndex  }
   ::= { gs2326MSTI5PortStateTable 1 }

Gs2326MSTI5PortStateEntry ::= SEQUENCE {
   gs2326MSTI5PortStateIndex        Integer32,
   gs2326MSTI5PortStatePort         DisplayString,
   gs2326MSTI5PortStatePortID       DisplayString,
   gs2326MSTI5PortStateRole         DisplayString,
   gs2326MSTI5PortStateState        DisplayString,
   gs2326MSTI5PortStatePathCost     Integer32,
   gs2326MSTI5PortStateEdge         DisplayString,
   gs2326MSTI5PortStatePoint2Point  DisplayString,
   gs2326MSTI5PortStateUptime       DisplayString
}

gs2326MSTI5PortStateIndex OBJECT-TYPE
   SYNTAX      Integer32(1..4095)
   MAX-ACCESS  not-accessible
   STATUS      current
   DESCRIPTION
       "table index."
   ::= { gs2326MSTI5PortStateEntry 1 }
   
gs2326MSTI5PortStatePort OBJECT-TYPE
   SYNTAX      DisplayString
   MAX-ACCESS  read-only
   STATUS      current
   DESCRIPTION
       "The switch port number of the logical STP port."
   ::= { gs2326MSTI5PortStateEntry 2 }
   
gs2326MSTI5PortStatePortID OBJECT-TYPE
   SYNTAX      DisplayString
   MAX-ACCESS  read-only
   STATUS      current
   DESCRIPTION
       "The port id as used by the STP protocol. 
        This is the priority part and the logical port index of the bridge port."
   ::= { gs2326MSTI5PortStateEntry 3 }
   
gs2326MSTI5PortStateRole OBJECT-TYPE
   SYNTAX      DisplayString
   MAX-ACCESS  read-only
   STATUS      current
   DESCRIPTION
       "The current STP port role."
   ::= { gs2326MSTI5PortStateEntry 4 }
   
gs2326MSTI5PortStateState OBJECT-TYPE
   SYNTAX      DisplayString
   MAX-ACCESS  read-only
   STATUS      current
   DESCRIPTION
       "The current STP port state."
   ::= { gs2326MSTI5PortStateEntry 5 }
   
gs2326MSTI5PortStatePathCost OBJECT-TYPE
   SYNTAX      Integer32(0..200000000)
   MAX-ACCESS  read-only
   STATUS      current
   DESCRIPTION
       "The current STP port path cost."
   ::= { gs2326MSTI5PortStateEntry 6 }
   
gs2326MSTI5PortStateEdge OBJECT-TYPE
   SYNTAX      DisplayString
   MAX-ACCESS  read-only
   STATUS      current
   DESCRIPTION
       "The current STP port Edge Flag."
   ::= { gs2326MSTI5PortStateEntry 7 }
   
gs2326MSTI5PortStatePoint2Point OBJECT-TYPE
   SYNTAX      DisplayString
   MAX-ACCESS  read-only
   STATUS      current
   DESCRIPTION
       "The current STP port point-to-point flag."
   ::= { gs2326MSTI5PortStateEntry 8 }
   
gs2326MSTI5PortStateUptime OBJECT-TYPE
   SYNTAX      DisplayString
   MAX-ACCESS  read-only
   STATUS      current
   DESCRIPTION
       "The time since the bridge port was last initialized."
   ::= { gs2326MSTI5PortStateEntry 9 }
   
gs2326MSTI6BridgeSTP                                                        OBJECT IDENTIFIER ::= { gs2326STPBridgeStatus 7 }

gs2326MSTI6BridgeSTPStatus                                                  OBJECT IDENTIFIER ::= { gs2326MSTI6BridgeSTP 1 }
      
gs2326MSTI6BridgeInstance OBJECT-TYPE
   SYNTAX       DisplayString
   MAX-ACCESS   read-only
   STATUS       current
   DESCRIPTION
       "The Bridge instance - CIST, MST1, ..."
   ::= { gs2326MSTI6BridgeSTPStatus 1 }
   
gs2326MSTI6BridgeID OBJECT-TYPE
   SYNTAX       DisplayString
   MAX-ACCESS   read-only
   STATUS       current
   DESCRIPTION
       "The Bridge ID of this Bridge instance."
   ::= { gs2326MSTI6BridgeSTPStatus 2 }
   
gs2326MSTI6RootID OBJECT-TYPE
   SYNTAX       DisplayString
   MAX-ACCESS   read-only
   STATUS       current
   DESCRIPTION
       "The Bridge ID of the currently elected root bridge."
   ::= { gs2326MSTI6BridgeSTPStatus 3 }
   
gs2326MSTI6RootPort OBJECT-TYPE
   SYNTAX       DisplayString
   MAX-ACCESS   read-only
   STATUS       current
   DESCRIPTION
       "The switch port currently assigned the root port role."
   ::= { gs2326MSTI6BridgeSTPStatus 4 }

gs2326MSTI6RootCost OBJECT-TYPE
   SYNTAX       Integer32(0..200000000)
   MAX-ACCESS   read-only
   STATUS       current
   DESCRIPTION
       "Root Path Cost."
   ::= { gs2326MSTI6BridgeSTPStatus 5 }

gs2326MSTI6TopologyFlag OBJECT-TYPE
   SYNTAX       DisplayString
   MAX-ACCESS   read-only
   STATUS       current
   DESCRIPTION
       "The current state of the Topology Change Flag of this Bridge instance."
   ::= { gs2326MSTI6BridgeSTPStatus 8 }

gs2326MSTI6TopologyChangeCount OBJECT-TYPE
   SYNTAX       Counter32
   MAX-ACCESS   read-only
   STATUS       current
   DESCRIPTION
       "The number of times where the topology change flag has been set."
   ::= { gs2326MSTI6BridgeSTPStatus 9 }
   
gs2326MSTI6TopologyChangeLast OBJECT-TYPE
   SYNTAX       DisplayString
   MAX-ACCESS   read-only
   STATUS       current
   DESCRIPTION
       "The time passed since the Topology Flag was last set."
   ::= { gs2326MSTI6BridgeSTPStatus 10 }
   
gs2326MSTI6PortStateTable OBJECT-TYPE
   SYNTAX      SEQUENCE OF Gs2326MSTI6PortStateEntry
   MAX-ACCESS  not-accessible
   STATUS      current
   DESCRIPTION
       " Show MSTI6 Ports and Aggregations State Configurations. "
   ::= { gs2326MSTI6BridgeSTP 2 }

gs2326MSTI6PortStateEntry OBJECT-TYPE
   SYNTAX      Gs2326MSTI6PortStateEntry
   MAX-ACCESS  not-accessible
   STATUS      current
   DESCRIPTION
       ""
   INDEX    { gs2326MSTI6PortStateIndex  }
   ::= { gs2326MSTI6PortStateTable 1 }

Gs2326MSTI6PortStateEntry ::= SEQUENCE {
   gs2326MSTI6PortStateIndex        Integer32,
   gs2326MSTI6PortStatePort         DisplayString,
   gs2326MSTI6PortStatePortID       DisplayString,
   gs2326MSTI6PortStateRole         DisplayString,
   gs2326MSTI6PortStateState        DisplayString,
   gs2326MSTI6PortStatePathCost     Integer32,
   gs2326MSTI6PortStateEdge         DisplayString,
   gs2326MSTI6PortStatePoint2Point  DisplayString,
   gs2326MSTI6PortStateUptime       DisplayString
}

gs2326MSTI6PortStateIndex OBJECT-TYPE
   SYNTAX      Integer32(1..4095)
   MAX-ACCESS  not-accessible
   STATUS      current
   DESCRIPTION
       "table index."
   ::= { gs2326MSTI6PortStateEntry 1 }
   
gs2326MSTI6PortStatePort OBJECT-TYPE
   SYNTAX      DisplayString
   MAX-ACCESS  read-only
   STATUS      current
   DESCRIPTION
       "The switch port number of the logical STP port."
   ::= { gs2326MSTI6PortStateEntry 2 }
   
gs2326MSTI6PortStatePortID OBJECT-TYPE
   SYNTAX      DisplayString
   MAX-ACCESS  read-only
   STATUS      current
   DESCRIPTION
       "The port id as used by the STP protocol. 
        This is the priority part and the logical port index of the bridge port."
   ::= { gs2326MSTI6PortStateEntry 3 }
   
gs2326MSTI6PortStateRole OBJECT-TYPE
   SYNTAX      DisplayString
   MAX-ACCESS  read-only
   STATUS      current
   DESCRIPTION
       "The current STP port role."
   ::= { gs2326MSTI6PortStateEntry 4 }
   
gs2326MSTI6PortStateState OBJECT-TYPE
   SYNTAX      DisplayString
   MAX-ACCESS  read-only
   STATUS      current
   DESCRIPTION
       "The current STP port state."
   ::= { gs2326MSTI6PortStateEntry 5 }
   
gs2326MSTI6PortStatePathCost OBJECT-TYPE
   SYNTAX      Integer32(0..200000000)
   MAX-ACCESS  read-only
   STATUS      current
   DESCRIPTION
       "The current STP port path cost."
   ::= { gs2326MSTI6PortStateEntry 6 }
   
gs2326MSTI6PortStateEdge OBJECT-TYPE
   SYNTAX      DisplayString
   MAX-ACCESS  read-only
   STATUS      current
   DESCRIPTION
       "The current STP port Edge Flag."
   ::= { gs2326MSTI6PortStateEntry 7 }
   
gs2326MSTI6PortStatePoint2Point OBJECT-TYPE
   SYNTAX      DisplayString
   MAX-ACCESS  read-only
   STATUS      current
   DESCRIPTION
       "The current STP port point-to-point flag."
   ::= { gs2326MSTI6PortStateEntry 8 }
   
gs2326MSTI6PortStateUptime OBJECT-TYPE
   SYNTAX      DisplayString
   MAX-ACCESS  read-only
   STATUS      current
   DESCRIPTION
       "The time since the bridge port was last initialized."
   ::= { gs2326MSTI6PortStateEntry 9 }
   
gs2326MSTI7BridgeSTP                                                        OBJECT IDENTIFIER ::= { gs2326STPBridgeStatus 8 }

gs2326MSTI7BridgeSTPStatus                                                  OBJECT IDENTIFIER ::= { gs2326MSTI7BridgeSTP 1 }
      
gs2326MSTI7BridgeInstance OBJECT-TYPE
   SYNTAX       DisplayString
   MAX-ACCESS   read-only
   STATUS       current
   DESCRIPTION
       "The Bridge instance - CIST, MST1, ..."
   ::= { gs2326MSTI7BridgeSTPStatus 1 }
   
gs2326MSTI7BridgeID OBJECT-TYPE
   SYNTAX       DisplayString
   MAX-ACCESS   read-only
   STATUS       current
   DESCRIPTION
       "The Bridge ID of this Bridge instance."
   ::= { gs2326MSTI7BridgeSTPStatus 2 }
   
gs2326MSTI7RootID OBJECT-TYPE
   SYNTAX       DisplayString
   MAX-ACCESS   read-only
   STATUS       current
   DESCRIPTION
       "The Bridge ID of the currently elected root bridge."
   ::= { gs2326MSTI7BridgeSTPStatus 3 }
   
gs2326MSTI7RootPort OBJECT-TYPE
   SYNTAX       DisplayString
   MAX-ACCESS   read-only
   STATUS       current
   DESCRIPTION
       "The switch port currently assigned the root port role."
   ::= { gs2326MSTI7BridgeSTPStatus 4 }

gs2326MSTI7RootCost OBJECT-TYPE
   SYNTAX       Integer32(0..200000000)
   MAX-ACCESS   read-only
   STATUS       current
   DESCRIPTION
       "Root Path Cost."
   ::= { gs2326MSTI7BridgeSTPStatus 5 }

gs2326MSTI7TopologyFlag OBJECT-TYPE
   SYNTAX       DisplayString
   MAX-ACCESS   read-only
   STATUS       current
   DESCRIPTION
       "The current state of the Topology Change Flag of this Bridge instance."
   ::= { gs2326MSTI7BridgeSTPStatus 8 }

gs2326MSTI7TopologyChangeCount OBJECT-TYPE
   SYNTAX       Counter32
   MAX-ACCESS   read-only
   STATUS       current
   DESCRIPTION
       "The number of times where the topology change flag has been set."
   ::= { gs2326MSTI7BridgeSTPStatus 9 }
   
gs2326MSTI7TopologyChangeLast OBJECT-TYPE
   SYNTAX       DisplayString
   MAX-ACCESS   read-only
   STATUS       current
   DESCRIPTION
       "The time passed since the Topology Flag was last set."
   ::= { gs2326MSTI7BridgeSTPStatus 10 }
   
gs2326MSTI7PortStateTable OBJECT-TYPE
   SYNTAX      SEQUENCE OF Gs2326MSTI7PortStateEntry
   MAX-ACCESS  not-accessible
   STATUS      current
   DESCRIPTION
       " Show MSTI7 Ports and Aggregations State Configurations. "
   ::= { gs2326MSTI7BridgeSTP 2 }

gs2326MSTI7PortStateEntry OBJECT-TYPE
   SYNTAX      Gs2326MSTI7PortStateEntry
   MAX-ACCESS  not-accessible
   STATUS      current
   DESCRIPTION
       ""
   INDEX    { gs2326MSTI7PortStateIndex  }
   ::= { gs2326MSTI7PortStateTable 1 }

Gs2326MSTI7PortStateEntry ::= SEQUENCE {
   gs2326MSTI7PortStateIndex        Integer32,
   gs2326MSTI7PortStatePort         DisplayString,
   gs2326MSTI7PortStatePortID       DisplayString,
   gs2326MSTI7PortStateRole         DisplayString,
   gs2326MSTI7PortStateState        DisplayString,
   gs2326MSTI7PortStatePathCost     Integer32,
   gs2326MSTI7PortStateEdge         DisplayString,
   gs2326MSTI7PortStatePoint2Point  DisplayString,
   gs2326MSTI7PortStateUptime       DisplayString
}

gs2326MSTI7PortStateIndex OBJECT-TYPE
   SYNTAX      Integer32(1..4095)
   MAX-ACCESS  not-accessible
   STATUS      current
   DESCRIPTION
       "table index."
   ::= { gs2326MSTI7PortStateEntry 1 }
   
gs2326MSTI7PortStatePort OBJECT-TYPE
   SYNTAX      DisplayString
   MAX-ACCESS  read-only
   STATUS      current
   DESCRIPTION
       "The switch port number of the logical STP port."
   ::= { gs2326MSTI7PortStateEntry 2 }
   
gs2326MSTI7PortStatePortID OBJECT-TYPE
   SYNTAX      DisplayString
   MAX-ACCESS  read-only
   STATUS      current
   DESCRIPTION
       "The port id as used by the STP protocol. 
        This is the priority part and the logical port index of the bridge port."
   ::= { gs2326MSTI7PortStateEntry 3 }
   
gs2326MSTI7PortStateRole OBJECT-TYPE
   SYNTAX      DisplayString
   MAX-ACCESS  read-only
   STATUS      current
   DESCRIPTION
       "The current STP port role."
   ::= { gs2326MSTI7PortStateEntry 4 }
   
gs2326MSTI7PortStateState OBJECT-TYPE
   SYNTAX      DisplayString
   MAX-ACCESS  read-only
   STATUS      current
   DESCRIPTION
       "The current STP port state."
   ::= { gs2326MSTI7PortStateEntry 5 }
   
gs2326MSTI7PortStatePathCost OBJECT-TYPE
   SYNTAX      Integer32(0..200000000)
   MAX-ACCESS  read-only
   STATUS      current
   DESCRIPTION
       "The current STP port path cost."
   ::= { gs2326MSTI7PortStateEntry 6 }
   
gs2326MSTI7PortStateEdge OBJECT-TYPE
   SYNTAX      DisplayString
   MAX-ACCESS  read-only
   STATUS      current
   DESCRIPTION
       "The current STP port Edge Flag."
   ::= { gs2326MSTI7PortStateEntry 7 }
   
gs2326MSTI7PortStatePoint2Point OBJECT-TYPE
   SYNTAX      DisplayString
   MAX-ACCESS  read-only
   STATUS      current
   DESCRIPTION
       "The current STP port point-to-point flag."
   ::= { gs2326MSTI7PortStateEntry 8 }
   
gs2326MSTI7PortStateUptime OBJECT-TYPE
   SYNTAX      DisplayString
   MAX-ACCESS  read-only
   STATUS      current
   DESCRIPTION
       "The time since the bridge port was last initialized."
   ::= { gs2326MSTI7PortStateEntry 9 }
   
gs2326STPPortStatusTable OBJECT-TYPE
   SYNTAX      SEQUENCE OF Gs2326STPPortStatusEntry
   MAX-ACCESS  not-accessible
   STATUS      current
   DESCRIPTION
       " Show STP Port Status."
   ::= { gs2326STP 9 }

gs2326STPPortStatusEntry OBJECT-TYPE
   SYNTAX      Gs2326STPPortStatusEntry
   MAX-ACCESS  not-accessible
   STATUS      current
   DESCRIPTION
       ""
   INDEX    { gs2326STPPortStatusPort  }
   ::= { gs2326STPPortStatusTable 1 }

Gs2326STPPortStatusEntry ::= SEQUENCE {
   gs2326STPPortStatusPort         Integer32,
   gs2326STPPortStatusCISTRole     DisplayString,
   gs2326STPPortStatusCISTState    DisplayString,
   gs2326STPPortStatusUptime       DisplayString
}

gs2326STPPortStatusPort OBJECT-TYPE
   SYNTAX      Integer32(1..4095)
   MAX-ACCESS  not-accessible
   STATUS      current
   DESCRIPTION
       " port, range : 1 - port number. "
   ::= { gs2326STPPortStatusEntry 1 }

gs2326STPPortStatusCISTRole OBJECT-TYPE
   SYNTAX      DisplayString
   MAX-ACCESS  read-only
   STATUS      current
   DESCRIPTION
       " The current STP port role of the CIST port. "
   ::= { gs2326STPPortStatusEntry 2 }

gs2326STPPortStatusCISTState OBJECT-TYPE
   SYNTAX      DisplayString
   MAX-ACCESS  read-only
   STATUS      current
   DESCRIPTION
       " The current STP port state of the CIST port. "
   ::= { gs2326STPPortStatusEntry 3 }

gs2326STPPortStatusUptime OBJECT-TYPE
   SYNTAX      DisplayString
   MAX-ACCESS  read-only
   STATUS      current
   DESCRIPTION
       " The time since the bridge port was last initialized. "
   ::= { gs2326STPPortStatusEntry 4 }
   
gs2326STPPortStatisticsTable OBJECT-TYPE
   SYNTAX      SEQUENCE OF Gs2326STPPortStatisticsEntry
   MAX-ACCESS  not-accessible
   STATUS      current
   DESCRIPTION
       " Show STP Port Statistics."
   ::= { gs2326STP 10 }

gs2326STPPortStatisticsEntry OBJECT-TYPE
   SYNTAX      Gs2326STPPortStatisticsEntry
   MAX-ACCESS  not-accessible
   STATUS      current
   DESCRIPTION
       ""
   INDEX    { gs2326STPStatisticsIndex  }
   ::= { gs2326STPPortStatisticsTable 1 }

Gs2326STPPortStatisticsEntry ::= SEQUENCE {
   gs2326STPStatisticsIndex            Integer32,
   gs2326STPStatisticsPort             DisplayString,
   gs2326STPStatisticsTxMSTP           Counter32,
   gs2326STPStatisticsTxRSTP           Counter32,
   gs2326STPStatisticsTxSTP            Counter32,
   gs2326STPStatisticsTxTCN            Counter32,
   gs2326STPStatisticsRxMSTP           Counter32,
   gs2326STPStatisticsRxRSTP           Counter32,
   gs2326STPStatisticsRxSTP            Counter32,
   gs2326STPStatisticsRxTCN            Counter32,
   gs2326STPStatisticsDiscardedUnknown Counter32,
   gs2326STPStatisticsDiscardedIllegal Counter32
}

gs2326STPStatisticsIndex OBJECT-TYPE
   SYNTAX      Integer32(1..4095)
   MAX-ACCESS  not-accessible
   STATUS      current
   DESCRIPTION
       "table index."
   ::= { gs2326STPPortStatisticsEntry 1 }
   
gs2326STPStatisticsPort OBJECT-TYPE
   SYNTAX      DisplayString
   MAX-ACCESS  not-accessible
   STATUS      current
   DESCRIPTION
       " port, range : 1 - port number. "
   ::= { gs2326STPPortStatisticsEntry 2 }

gs2326STPStatisticsTxMSTP OBJECT-TYPE
   SYNTAX      Counter32
   MAX-ACCESS  read-only
   STATUS      current
   DESCRIPTION
       " The number of MSTP Configuration BPDU's received/transmitted on the port."
   ::= { gs2326STPPortStatisticsEntry 3 }

gs2326STPStatisticsTxRSTP OBJECT-TYPE
   SYNTAX      Counter32
   MAX-ACCESS  read-only
   STATUS      current
   DESCRIPTION
       " The number of RSTP Configuration BPDU's received/transmitted on the port. "
   ::= { gs2326STPPortStatisticsEntry 4 }

gs2326STPStatisticsTxSTP OBJECT-TYPE
   SYNTAX      Counter32
   MAX-ACCESS  read-only
   STATUS      current
   DESCRIPTION
       " The number of legacy STP Configuration BPDU's received/transmitted on the port. "
   ::= { gs2326STPPortStatisticsEntry 5 }

gs2326STPStatisticsTxTCN OBJECT-TYPE
   SYNTAX      Counter32
   MAX-ACCESS  read-only
   STATUS      current
   DESCRIPTION
       " The number of Topology Change Notification BPDU's received/transmitted on the port. "
   ::= { gs2326STPPortStatisticsEntry 6 }
   
gs2326STPStatisticsRxMSTP OBJECT-TYPE
   SYNTAX      Counter32
   MAX-ACCESS  read-only
   STATUS      current
   DESCRIPTION
       " The number of MSTP Configuration BPDU's received/transmitted on the port."
   ::= { gs2326STPPortStatisticsEntry 7 }

gs2326STPStatisticsRxRSTP OBJECT-TYPE
   SYNTAX      Counter32
   MAX-ACCESS  read-only
   STATUS      current
   DESCRIPTION
       " The number of RSTP Configuration BPDU's received/transmitted on the port. "
   ::= { gs2326STPPortStatisticsEntry 8 }

gs2326STPStatisticsRxSTP OBJECT-TYPE
   SYNTAX      Counter32
   MAX-ACCESS  read-only
   STATUS      current
   DESCRIPTION
       " The number of legacy STP Configuration BPDU's received/transmitted on the port. "
   ::= { gs2326STPPortStatisticsEntry 9 }

gs2326STPStatisticsRxTCN OBJECT-TYPE
   SYNTAX      Counter32
   MAX-ACCESS  read-only
   STATUS      current
   DESCRIPTION
       " The number of Topology Change Notification BPDU's received/transmitted on the port. "
   ::= { gs2326STPPortStatisticsEntry 10 }

gs2326STPStatisticsDiscardedUnknown OBJECT-TYPE
   SYNTAX      Counter32
   MAX-ACCESS  read-only
   STATUS      current
   DESCRIPTION
       " The number of unknown Spanning Tree BPDU's received and discarded on the port. "
   ::= { gs2326STPPortStatisticsEntry 11 }
   
gs2326STPStatisticsDiscardedIllegal OBJECT-TYPE
   SYNTAX      Counter32
   MAX-ACCESS  read-only
   STATUS      current
   DESCRIPTION
       " The number of illegal Spanning Tree BPDU's received and discarded on the port. "
   ::= { gs2326STPPortStatisticsEntry 12 }


gs2326FilteringDataBase                                                  OBJECT IDENTIFIER ::= { gs2326Configuration 21 }

gs2326FilteringDataBaseConfig                                            OBJECT IDENTIFIER ::= { gs2326FilteringDataBase 1 }

gs2326FilteringDataBaseAgingTime OBJECT-TYPE
   SYNTAX      Integer32(0..1000000)
   MAX-ACCESS  read-write
   STATUS      current
   DESCRIPTION
       "Configure aging time by entering a value here in seconds.
        default: 300,
        range: 10-1000000. 
        Disable automatic aging : 0."
   ::= { gs2326FilteringDataBaseConfig 1 }

gs2326FilteringDataBaseConfigTable OBJECT-TYPE
   SYNTAX      SEQUENCE OF GS2326FilteringDataBaseConfigEntry
   MAX-ACCESS  not-accessible
   STATUS      current
   DESCRIPTION
       " "
   ::= { gs2326FilteringDataBaseConfig 2 }

gs2326FilteringDataBaseConfigEntry OBJECT-TYPE
   SYNTAX      GS2326FilteringDataBaseConfigEntry
   MAX-ACCESS  not-accessible
   STATUS      current
   DESCRIPTION
       ""
   INDEX    { gs2326FilteringDataBaseConfigPort  }
   ::= { gs2326FilteringDataBaseConfigTable 1 }
   
GS2326FilteringDataBaseConfigEntry ::= SEQUENCE {
   gs2326FilteringDataBaseConfigPort        Integer32,
   gs2326FilteringDataBaseConfigLearning    INTEGER
}

gs2326FilteringDataBaseConfigPort OBJECT-TYPE
   SYNTAX      Integer32(1..4095)
   MAX-ACCESS  not-accessible
   STATUS      current
   DESCRIPTION
       " "
   ::= { gs2326FilteringDataBaseConfigEntry 1 }

gs2326FilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2326FilteringDataBaseConfigEntry 2 }


gs2326FilteringDataBaseStaticMAC                                OBJECT IDENTIFIER ::= { gs2326FilteringDataBaseConfig 3 }

gs2326FilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2326FilteringDataBaseStaticMAC 1 }

gs2326FilteringDataBaseStaticMACTable OBJECT-TYPE
   SYNTAX      SEQUENCE OF GS2326FilteringDataBaseStaticMACEntry
   MAX-ACCESS  not-accessible
   STATUS      current
   DESCRIPTION
       " "
   ::= { gs2326FilteringDataBaseStaticMAC 2 }

gs2326FilteringDataBaseStaticMACEntry OBJECT-TYPE
   SYNTAX      GS2326FilteringDataBaseStaticMACEntry
   MAX-ACCESS  not-accessible
   STATUS      current
   DESCRIPTION
       ""
   INDEX    { gs2326FilteringDataBaseStaticMACIndex  }
   ::= { gs2326FilteringDataBaseStaticMACTable 1 }

GS2326FilteringDataBaseStaticMACEntry ::= SEQUENCE {
   gs2326FilteringDataBaseStaticMACIndex	    Integer32,
   gs2326FilteringDataBaseStaticMACVLANId	    Integer32,
   gs2326FilteringDataBaseStaticMACAddress      MacAddress,
   gs2326FilteringDataBaseStaticMACPortMembers  DisplayString,
   gs2326FilteringDataBaseStaticMACRowStatus	INTEGER
}

gs2326FilteringDataBaseStaticMACIndex OBJECT-TYPE
   SYNTAX      Integer32(1..4095)
   MAX-ACCESS  not-accessible
   STATUS      current
   DESCRIPTION
       " "
   ::= { gs2326FilteringDataBaseStaticMACEntry 1 }

gs2326FilteringDataBaseStaticMACVLANId OBJECT-TYPE
   SYNTAX      Integer32(1..4094)
   MAX-ACCESS  read-write
   STATUS      current
   DESCRIPTION
       " VLAN ID, range: 1 - 4094. "
   ::= { gs2326FilteringDataBaseStaticMACEntry 2 }

gs2326FilteringDataBaseStaticMACAddress OBJECT-TYPE
   SYNTAX      MacAddress
   MAX-ACCESS  read-write
   STATUS      current
   DESCRIPTION
       " MAC address, format 0a 1b 2c 3d 4e 5f "
   ::= { gs2326FilteringDataBaseStaticMACEntry 3 }

gs2326FilteringDataBaseStaticMACPortMembers OBJECT-TYPE
   SYNTAX      DisplayString
   MAX-ACCESS  read-write
   STATUS      current
   DESCRIPTION
       "To include the ports in a Static MAC Table"
   ::= { gs2326FilteringDataBaseStaticMACEntry 4 }

gs2326FilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2326FilteringDataBaseStaticMACEntry 5 }
   

gs2326FilteringDataBaseDynamicMACTable OBJECT-TYPE
   SYNTAX      SEQUENCE OF GS2326FilteringDataBaseDynamicMACEntry
   MAX-ACCESS  not-accessible
   STATUS      current
   DESCRIPTION
       " "
   ::= { gs2326FilteringDataBaseConfig 4 }

gs2326FilteringDataBaseDynamicMACEntry OBJECT-TYPE
   SYNTAX      GS2326FilteringDataBaseDynamicMACEntry
   MAX-ACCESS  not-accessible
   STATUS      current
   DESCRIPTION
       ""
   INDEX    { gs2326FilteringDataBaseDynamicMACIndex  }
   ::= { gs2326FilteringDataBaseDynamicMACTable 1 }
   
GS2326FilteringDataBaseDynamicMACEntry ::= SEQUENCE {
   gs2326FilteringDataBaseDynamicMACIndex	    Integer32,
   gs2326FilteringDataBaseDynamicMACType	    INTEGER,
   gs2326FilteringDataBaseDynamicMACVLAN	    Integer32,
   gs2326FilteringDataBaseDynamicMACAddress     MacAddress,
   gs2326FilteringDataBaseDynamicPortMembers    DisplayString
}

gs2326FilteringDataBaseDynamicMACIndex OBJECT-TYPE
   SYNTAX      Integer32(1..4095)
   MAX-ACCESS  not-accessible
   STATUS      current
   DESCRIPTION
       " "
   ::= { gs2326FilteringDataBaseDynamicMACEntry 1 }

gs2326FilteringDataBaseDynamicMACType OBJECT-TYPE
   SYNTAX      INTEGER { dynamic(0), static(1) }
   MAX-ACCESS  read-only
   STATUS      current
   DESCRIPTION
       "Indicates whether the entry is a static or a dynamic entry."
   ::= { gs2326FilteringDataBaseDynamicMACEntry 2 }

gs2326FilteringDataBaseDynamicMACVLAN OBJECT-TYPE
   SYNTAX      Integer32(1..4094)
   MAX-ACCESS  read-only
   STATUS      current
   DESCRIPTION
       "The VLAN ID of the entry."
   ::= { gs2326FilteringDataBaseDynamicMACEntry 3 }

gs2326FilteringDataBaseDynamicMACAddress OBJECT-TYPE
   SYNTAX      MacAddress
   MAX-ACCESS  read-only
   STATUS      current
   DESCRIPTION
       "The MAC address of the entry."
   ::= { gs2326FilteringDataBaseDynamicMACEntry 4 }
   
gs2326FilteringDataBaseDynamicPortMembers OBJECT-TYPE
   SYNTAX      DisplayString
   MAX-ACCESS  read-only
   STATUS      current
   DESCRIPTION
       "The ports that are members of the entry."
   ::= { gs2326FilteringDataBaseDynamicMACEntry 5 } 
   
                  
gs2326SFlowAgent                                                  OBJECT IDENTIFIER ::= { gs2326Configuration 22 }

gs2326SFlowAgentCollector                                            OBJECT IDENTIFIER ::= { gs2326SFlowAgent 1 }

gs2326SFlowAgentReceiverMode OBJECT-TYPE
   SYNTAX      INTEGER { disable(0), enable(1) }
   MAX-ACCESS  read-write
   STATUS      current
   DESCRIPTION
       "default: 0
       0: disable
       1: enable "
   ::= { gs2326SFlowAgentCollector 1 }


gs2326LMC                                                   OBJECT IDENTIFIER ::= { gs2326Configuration 1500 }

gs2326LMCOperating OBJECT-TYPE
   SYNTAX      INTEGER { disabled(0), enabled(1), try(2) }
   MAX-ACCESS  read-write
   STATUS      current
   DESCRIPTION
       "0: disabled
        1: enabled
        2: try"
   ::= { gs2326LMC 1 }

gs2326LMCConfigViaDhcp OBJECT-TYPE
   SYNTAX      INTEGER { disabled(0), enabled(1) }
   MAX-ACCESS  read-write
   STATUS      current
   DESCRIPTION
       "0: disabled
        1: enabled"
   ::= { gs2326LMC 2 }

gs2326LMCDomain OBJECT-TYPE
   SYNTAX      DisplayString(SIZE(0..255))
   MAX-ACCESS  read-write
   STATUS      current
   DESCRIPTION
       "0: disabled
        1: enabled"
   ::= { gs2326LMC 3 }

gs2326LMCDhcpClientAutoRenew OBJECT-TYPE
   SYNTAX      INTEGER { disabled(0), enabled(1) }
   MAX-ACCESS  read-write
   STATUS      current
   DESCRIPTION
       "0: disabled
        1: enabled"
   ::= { gs2326LMC 4 }


gs2326LMCZeroTouchSupport OBJECT-TYPE
   SYNTAX      INTEGER { No(0), Yes(1) }
   MAX-ACCESS  read-only
   STATUS      current
   DESCRIPTION
       "0: No
        1: Yes"
   ::= { gs2326LMC 50 }   
   
gs2326LMCPairingTokenPresent OBJECT-TYPE
   SYNTAX      INTEGER { No(0), Yes(1) }
   MAX-ACCESS  read-only
   STATUS      current
   DESCRIPTION
       "0: No
        1: Yes"
   ::= { gs2326LMC 51 }
   
gs2326LMCClientStatus OBJECT-TYPE
   SYNTAX      DisplayString
   MAX-ACCESS  read-only
   STATUS      current
   DESCRIPTION
           ""
   ::= { gs2326LMC  52 }
   
   
gs2326LMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2326LMC  53 }
   
gs2326LMCControlStatus OBJECT-TYPE
   SYNTAX      INTEGER {Disabled(2), Operating(4)}
   MAX-ACCESS  read-only
   STATUS      current
   DESCRIPTION
           "2: Disabled
            4: Operating"
   ::= { gs2326LMC  54 }          
   
gs2326LMCMonitoringStatus OBJECT-TYPE
   SYNTAX      INTEGER {Disabled(2), Operating(4)}
   MAX-ACCESS  read-only
   STATUS      current
   DESCRIPTION
           "2: Disabled
            4: Operating"
   ::= { gs2326LMC  55 }
   
gs2326LMCConfigurationSource OBJECT-TYPE
   SYNTAX      DisplayString
   MAX-ACCESS  read-only
   STATUS      current
   DESCRIPTION
           ""
   ::= { gs2326LMC  56 }
   
gs2326LMCConfigModified OBJECT-TYPE
   SYNTAX      INTEGER { No(0), Yes(1) }
   MAX-ACCESS  read-only
   STATUS      current
   DESCRIPTION
       "0: No
        1: Yes"
   ::= { gs2326LMC 57 }
   
gs2326LMCDeviceID OBJECT-TYPE
   SYNTAX      DisplayString
   MAX-ACCESS  read-only
   STATUS      current
   DESCRIPTION
           ""
   ::= { gs2326LMC  58 }
   
gs2326LMCRoundTripTime OBJECT-TYPE
   SYNTAX      INTEGER
   MAX-ACCESS  read-only
   STATUS      current
   DESCRIPTION
           ""
   ::= { gs2326LMC  100 }
----------------------------------------------------------------------------------------------------------------------------
gs2326Security                                              OBJECT IDENTIFIER ::= { lancomGS2326  3 }

gs2326IPSourceGuard                                         OBJECT IDENTIFIER ::= { gs2326Security 1 }

gs2326IPSourceGuardConf                                     OBJECT IDENTIFIER ::= { gs2326IPSourceGuard 1 }

gs2326IPSourceGuardMode OBJECT-TYPE
   SYNTAX      INTEGER { disable(0), enable(1) }
   MAX-ACCESS  read-write
   STATUS      current
   DESCRIPTION
       " default:  0
        0: disable
        1: enable"
   ::= { gs2326IPSourceGuardConf 1 }

gs2326IPSourceGuardPortConfigTable OBJECT-TYPE
   SYNTAX      SEQUENCE OF GS2326IPSourceGuardPortConfigEntry
   MAX-ACCESS  not-accessible
   STATUS      current
   DESCRIPTION
       " "
   ::= { gs2326IPSourceGuardConf 2 }

gs2326IPSourceGuardPortConfigEntry OBJECT-TYPE
   SYNTAX      GS2326IPSourceGuardPortConfigEntry
   MAX-ACCESS  not-accessible
   STATUS      current
   DESCRIPTION
       ""
   INDEX    { gs2326IPSourceGuardPortConfigPort  }
   ::= { gs2326IPSourceGuardPortConfigTable 1 }

GS2326IPSourceGuardPortConfigEntry ::= SEQUENCE {
   gs2326IPSourceGuardPortConfigPort               Integer32,
   gs2326IPSourceGuardPortConfigMode               INTEGER,
   gs2326IPSourceGuardPortMaxDynamicClients        Integer32
}

gs2326IPSourceGuardPortConfigPort OBJECT-TYPE
   SYNTAX      Integer32(1..4095)
   MAX-ACCESS  not-accessible
   STATUS      current
   DESCRIPTION
       " "
   ::= { gs2326IPSourceGuardPortConfigEntry 1 }

gs2326IPSourceGuardPortConfigMode OBJECT-TYPE
   SYNTAX      INTEGER { disable(0), enable(1) }
   MAX-ACCESS  read-write
   STATUS      current
   DESCRIPTION
       "default: 0
       0:disable
       1:enable "
   ::= { gs2326IPSourceGuardPortConfigEntry 2 }

gs2326IPSourceGuardPortMaxDynamicClients OBJECT-TYPE
   SYNTAX      Integer32(0..2|99)
   MAX-ACCESS  read-write
   STATUS      current
   DESCRIPTION
       "default: 99
       0~2: Max Dynamic clients
       99:Unlimited "
   ::= { gs2326IPSourceGuardPortConfigEntry 3 }


gs2326IPSourceGuardStatic                                OBJECT IDENTIFIER ::= { gs2326IPSourceGuard 2 }

gs2326IPSourceGuardStaticCreate OBJECT-TYPE
   SYNTAX       INTEGER { none(0), create(1) }
   MAX-ACCESS   read-write
   STATUS       current
   DESCRIPTION
       "default: 0
        0 : None  (read only)
        1 : Create a IP Source Guard"
   ::= { gs2326IPSourceGuardStatic 1 }

gs2326IPSourceGuardStaticTable OBJECT-TYPE
   SYNTAX      SEQUENCE OF GS2326IPSourceGuardStaticEntry
   MAX-ACCESS  not-accessible
   STATUS      current
   DESCRIPTION
       " "
   ::= { gs2326IPSourceGuardStatic 2 }

gs2326IPSourceGuardStaticEntry OBJECT-TYPE
   SYNTAX      GS2326IPSourceGuardStaticEntry
   MAX-ACCESS  not-accessible
   STATUS      current
   DESCRIPTION
       ""
   INDEX    { gs2326IPSourceGuardStaticIndex  }
   ::= { gs2326IPSourceGuardStaticTable 1 }

GS2326IPSourceGuardStaticEntry ::= SEQUENCE {
   gs2326IPSourceGuardStaticIndex         Integer32,
   gs2326IPSourceGuardStaticPort          Integer32,
   gs2326IPSourceGuardStaticVLANId        Integer32,
   gs2326IPSourceGuardStaticIPAddress     IpAddress,
   gs2326IPSourceGuardStaticMACAddress    MacAddress,
   gs2326IPSourceGuardStaticRowStatus     INTEGER
}

gs2326IPSourceGuardStaticIndex OBJECT-TYPE
   SYNTAX      Integer32(1..28)
   MAX-ACCESS  not-accessible
   STATUS      current
   DESCRIPTION
       " "
   ::= { gs2326IPSourceGuardStaticEntry 1 }

gs2326IPSourceGuardStaticPort OBJECT-TYPE
   SYNTAX      Integer32(1..4095)
   MAX-ACCESS  read-write
   STATUS      current
   DESCRIPTION
       " Port, range: 1 - port number. "
   ::= { gs2326IPSourceGuardStaticEntry 2 }

gs2326IPSourceGuardStaticVLANId OBJECT-TYPE
   SYNTAX      Integer32(1..4094)
   MAX-ACCESS  read-write
   STATUS      current
   DESCRIPTION
       " VLAN ID, range: 1 - 4094. "
   ::= { gs2326IPSourceGuardStaticEntry 3 }

gs2326IPSourceGuardStaticIPAddress OBJECT-TYPE
   SYNTAX      IpAddress
   MAX-ACCESS  read-write
   STATUS      current
   DESCRIPTION
       " IP address allowed for doing IP source guard. "
   ::= { gs2326IPSourceGuardStaticEntry 4 }

gs2326IPSourceGuardStaticMACAddress OBJECT-TYPE
   SYNTAX      MacAddress
   MAX-ACCESS  read-write
   STATUS      current
   DESCRIPTION
       " Allowed Source MAC address, format 0a 1b 2c 3d 4e 5f "
   ::= { gs2326IPSourceGuardStaticEntry 5 }

gs2326IPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2326IPSourceGuardStaticEntry 6 }

gs2326IPSourceGuardDynamicTable OBJECT-TYPE
   SYNTAX      SEQUENCE OF GS2326IPSourceGuardDynamicEntry
   MAX-ACCESS  not-accessible
   STATUS      current
   DESCRIPTION
       " "
   ::= { gs2326IPSourceGuard 3 }

gs2326IPSourceGuardDynamicEntry OBJECT-TYPE
   SYNTAX      GS2326IPSourceGuardDynamicEntry
   MAX-ACCESS  not-accessible
   STATUS      current
   DESCRIPTION
       ""
   INDEX    { gs2326IPSourceGuardDynamicIndex  }
   ::= { gs2326IPSourceGuardDynamicTable 1 }

GS2326IPSourceGuardDynamicEntry ::= SEQUENCE {
   gs2326IPSourceGuardDynamicIndex          Integer32,
   gs2326IPSourceGuardDynamicPort           Integer32,
   gs2326IPSourceGuardDynamicVLANId         Integer32,
   gs2326IPSourceGuardDynamicIPAddress      IpAddress,
   gs2326IPSourceGuardDynamicMACAddress     MacAddress
}

gs2326IPSourceGuardDynamicIndex OBJECT-TYPE
   SYNTAX      Integer32(1..4095)
   MAX-ACCESS  not-accessible
   STATUS      current
   DESCRIPTION
       " "
   ::= { gs2326IPSourceGuardDynamicEntry 1 }

gs2326IPSourceGuardDynamicPort OBJECT-TYPE
   SYNTAX      Integer32(1..10)
   MAX-ACCESS  read-only
   STATUS      current
   DESCRIPTION
       " "
   ::= { gs2326IPSourceGuardDynamicEntry 2 }

gs2326IPSourceGuardDynamicVLANId OBJECT-TYPE
   SYNTAX      Integer32(1..4094)
   MAX-ACCESS  read-only
   STATUS      current
   DESCRIPTION
       " "
   ::= { gs2326IPSourceGuardDynamicEntry 3 }

gs2326IPSourceGuardDynamicIPAddress OBJECT-TYPE
   SYNTAX      IpAddress
   MAX-ACCESS  read-only
   STATUS      current
   DESCRIPTION
       " "
   ::= { gs2326IPSourceGuardDynamicEntry 4 }

gs2326IPSourceGuardDynamicMACAddress OBJECT-TYPE
   SYNTAX      MacAddress
   MAX-ACCESS  read-only
   STATUS      current
   DESCRIPTION
       " "
   ::= { gs2326IPSourceGuardDynamicEntry 5 }

gs2326ARPInspection                                         OBJECT IDENTIFIER ::= { gs2326Security 2 }

gs2326ARPInspectionConf                                     OBJECT IDENTIFIER ::= { gs2326ARPInspection 1 }

gs2326ARPInspectionConfMode OBJECT-TYPE
   SYNTAX      INTEGER { disable(0), enable(1) }
   MAX-ACCESS  read-write
   STATUS      current
   DESCRIPTION
       "default: 0
        0: disable
        1: enable"
   ::= { gs2326ARPInspectionConf 1 }

gs2326ARPInspectionConfTable OBJECT-TYPE
   SYNTAX      SEQUENCE OF GS2326ARPInspectionConfEntry
   MAX-ACCESS  not-accessible
   STATUS      current
   DESCRIPTION
       " "
   ::= { gs2326ARPInspectionConf 2 }

gs2326ARPInspectionConfEntry OBJECT-TYPE
   SYNTAX      GS2326ARPInspectionConfEntry
   MAX-ACCESS  not-accessible
   STATUS      current
   DESCRIPTION
       ""
   INDEX    { gs2326ARPInspectionConfPortIndex  }
   ::= { gs2326ARPInspectionConfTable 1 }

GS2326ARPInspectionConfEntry ::= SEQUENCE {
   gs2326ARPInspectionConfPortIndex	Integer32,
   gs2326ARPInspectionConfPortMode	INTEGER
}

gs2326ARPInspectionConfPortIndex OBJECT-TYPE
   SYNTAX      Integer32(1..4095)
   MAX-ACCESS  not-accessible
   STATUS      current
   DESCRIPTION
       " "
   ::= { gs2326ARPInspectionConfEntry 1 }

gs2326ARPInspectionConfPortMode OBJECT-TYPE
   SYNTAX      INTEGER { disable(0), enable(1) }
   MAX-ACCESS  read-write
   STATUS      current
   DESCRIPTION
       "default: 0
        0: disable
        1: enable"
   ::= { gs2326ARPInspectionConfEntry 2 }


gs2326ARPInspectionStatic                                OBJECT IDENTIFIER ::= { gs2326ARPInspection 2 }

gs2326ARPInspectionStaticCreate OBJECT-TYPE
   SYNTAX      INTEGER { none(0), create(1) }
   MAX-ACCESS  read-write
   STATUS      current
   DESCRIPTION
       "default: 0
        0: none
        1: create"
   ::= { gs2326ARPInspectionStatic 1 }

gs2326ARPInspectionStaticTable OBJECT-TYPE
   SYNTAX      SEQUENCE OF GS2326ARPInspectionStaticEntry
   MAX-ACCESS  not-accessible
   STATUS      current
   DESCRIPTION
       " "
   ::= { gs2326ARPInspectionStatic 2 }

gs2326ARPInspectionStaticEntry OBJECT-TYPE
   SYNTAX      GS2326ARPInspectionStaticEntry
   MAX-ACCESS  not-accessible
   STATUS      current
   DESCRIPTION
       ""
   INDEX    { gs2326ARPInspectionStaticIndex  }
   ::= { gs2326ARPInspectionStaticTable 1 }

GS2326ARPInspectionStaticEntry ::= SEQUENCE {
   gs2326ARPInspectionStaticIndex       Integer32,
   gs2326ARPInspectionStaticPort        Integer32,
   gs2326ARPInspectionStaticVLANId      Integer32,
   gs2326ARPInspectionStaticIPAddress   IpAddress,
   gs2326ARPInspectionStaticMACAddress  MacAddress,
   gs2326ARPInspectionStaticRowStatus   INTEGER
}

gs2326ARPInspectionStaticIndex OBJECT-TYPE
   SYNTAX      Integer32(1..4095)
   MAX-ACCESS  not-accessible
   STATUS      current
   DESCRIPTION
       ""
   ::= { gs2326ARPInspectionStaticEntry 1 }

gs2326ARPInspectionStaticPort OBJECT-TYPE
   SYNTAX      Integer32(1..4095)
   MAX-ACCESS  read-write
   STATUS      current
   DESCRIPTION
       " Port, range: 1 - port number. "
   ::= { gs2326ARPInspectionStaticEntry 2 }

gs2326ARPInspectionStaticVLANId OBJECT-TYPE
   SYNTAX      Integer32(1..4094)
   MAX-ACCESS  read-write
   STATUS      current
   DESCRIPTION
       " VLAN ID, range: 1 - 4094. "
   ::= { gs2326ARPInspectionStaticEntry 3 }

gs2326ARPInspectionStaticIPAddress OBJECT-TYPE
   SYNTAX      IpAddress
   MAX-ACCESS  read-write
   STATUS      current
   DESCRIPTION
       " IP address allowed for doing ARP request. "
   ::= { gs2326ARPInspectionStaticEntry 4 }

gs2326ARPInspectionStaticMACAddress OBJECT-TYPE
   SYNTAX      MacAddress
   MAX-ACCESS  read-write
   STATUS      current
   DESCRIPTION
       " Allowed Source MAC address in ARP request packets, format 0a 1b 2c 3d 4e 5f "
   ::= { gs2326ARPInspectionStaticEntry 5 }

gs2326ARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2326ARPInspectionStaticEntry 6 }

gs2326ARPInspectionDynamicTable OBJECT-TYPE
   SYNTAX      SEQUENCE OF GS2326ARPInspectionDynamicEntry
   MAX-ACCESS  not-accessible
   STATUS      current
   DESCRIPTION
       " "
   ::= { gs2326ARPInspection 3 }

gs2326ARPInspectionDynamicEntry OBJECT-TYPE
   SYNTAX      GS2326ARPInspectionDynamicEntry
   MAX-ACCESS  not-accessible
   STATUS      current
   DESCRIPTION
       ""
   INDEX    { gs2326ARPInspectionDynamicIndex  }
   ::= { gs2326ARPInspectionDynamicTable 1 }

GS2326ARPInspectionDynamicEntry ::= SEQUENCE {
   gs2326ARPInspectionDynamicIndex          Integer32,
   gs2326ARPInspectionDynamicPort           Integer32,
   gs2326ARPInspectionDynamicVLANId         Integer32,
   gs2326ARPInspectionDynamicIPAddress      IpAddress,
   gs2326ARPInspectionDynamicMACAddress     MacAddress
}

gs2326ARPInspectionDynamicIndex OBJECT-TYPE
   SYNTAX      Integer32(1..4095)
   MAX-ACCESS  not-accessible
   STATUS      current
   DESCRIPTION
       " "
   ::= { gs2326ARPInspectionDynamicEntry 1 }

gs2326ARPInspectionDynamicPort OBJECT-TYPE
   SYNTAX      Integer32(1..4095)
   MAX-ACCESS  read-only
   STATUS      current
   DESCRIPTION
       ""
   ::= { gs2326ARPInspectionDynamicEntry 2 }

gs2326ARPInspectionDynamicVLANId OBJECT-TYPE
   SYNTAX      Integer32(1..4094)
   MAX-ACCESS  read-only
   STATUS      current
   DESCRIPTION
       ""
   ::= { gs2326ARPInspectionDynamicEntry 3 }

gs2326ARPInspectionDynamicIPAddress OBJECT-TYPE
   SYNTAX      IpAddress
   MAX-ACCESS  read-only
   STATUS      current
   DESCRIPTION
       ""
   ::= { gs2326ARPInspectionDynamicEntry 4 }

gs2326ARPInspectionDynamicMACAddress OBJECT-TYPE
   SYNTAX      MacAddress
   MAX-ACCESS  read-only
   STATUS      current
   DESCRIPTION
       ""
   ::= { gs2326ARPInspectionDynamicEntry 5 }

gs2326ARPStaticGatewayCtrl	                                OBJECT IDENTIFIER ::= { gs2326ARPInspection 6 }

gs2326ARPStaticGatewayCtrlSystemConf                                      OBJECT IDENTIFIER ::= { gs2326ARPStaticGatewayCtrl 1 }

gs2326ARPStaticGatewayCtrlMode OBJECT-TYPE
   SYNTAX      INTEGER { disable(0), enable(1) }
   MAX-ACCESS  read-write
   STATUS      current
   DESCRIPTION
       "default: 0
       0: disable
       1: enable "
   ::= { gs2326ARPStaticGatewayCtrlSystemConf 1 }

gs2326ARPStaticGatewayCtrlCreate OBJECT-TYPE
   SYNTAX      INTEGER { none(0), create(1) }
   MAX-ACCESS  read-write
   STATUS      current
   DESCRIPTION
       "default: 0
        0: none
        1: create"
   ::= { gs2326ARPStaticGatewayCtrl 2 }

gs2326ARPStaticGatewayCtrlTable OBJECT-TYPE
   SYNTAX      SEQUENCE OF GS2326ARPStaticGatewayCtrlEntry
   MAX-ACCESS  not-accessible
   STATUS      current
   DESCRIPTION
       " "
   ::= { gs2326ARPStaticGatewayCtrl 3 }

gs2326ARPStaticGatewayCtrlEntry OBJECT-TYPE
   SYNTAX      GS2326ARPStaticGatewayCtrlEntry
   MAX-ACCESS  not-accessible
   STATUS      current
   DESCRIPTION
       ""
   INDEX    { gs2326ARPStaticGatewayCtrlIndex  }
   ::= { gs2326ARPStaticGatewayCtrlTable 1 }

GS2326ARPStaticGatewayCtrlEntry ::= SEQUENCE {
   gs2326ARPStaticGatewayCtrlIndex       Integer32,
   gs2326ARPStaticGatewayCtrlIPAddress   IpAddress,
   gs2326ARPStaticGatewayCtrlMACAddress  MacAddress,
   gs2326ARPStaticGatewayCtrlPort        Integer32,
   gs2326ARPStaticGatewayCtrlAction      INTEGER,
   gs2326ARPStaticGatewayCtrlState       DisplayString,
   gs2326ARPStaticGatewayCtrlReOpen      INTEGER,
   gs2326ARPStaticGatewayCtrlRowStatus   INTEGER
}

gs2326ARPStaticGatewayCtrlIndex OBJECT-TYPE
   SYNTAX      Integer32(1..4)
   MAX-ACCESS  not-accessible
   STATUS      current
   DESCRIPTION
       ""
   ::= { gs2326ARPStaticGatewayCtrlEntry 1 }

gs2326ARPStaticGatewayCtrlIPAddress OBJECT-TYPE
   SYNTAX      IpAddress
   MAX-ACCESS  read-write
   STATUS      current
   DESCRIPTION
       " Source IP address. "
   ::= { gs2326ARPStaticGatewayCtrlEntry 2 }

gs2326ARPStaticGatewayCtrlMACAddress OBJECT-TYPE
   SYNTAX      MacAddress
   MAX-ACCESS  read-write
   STATUS      current
   DESCRIPTION
       " Source MAC address , format 0a 1b 2c 3d 4e 5f "
   ::= { gs2326ARPStaticGatewayCtrlEntry 3 }

gs2326ARPStaticGatewayCtrlPort OBJECT-TYPE
   SYNTAX      Integer32(1..4095)
   MAX-ACCESS  read-write
   STATUS      current
   DESCRIPTION
       " Port, range: 1 - port number. "
   ::= { gs2326ARPStaticGatewayCtrlEntry 4 }

gs2326ARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2326ARPStaticGatewayCtrlEntry 5 }

gs2326ARPStaticGatewayCtrlState OBJECT-TYPE
   SYNTAX      DisplayString
   MAX-ACCESS  read-only
   STATUS      current
   DESCRIPTION
       ""
   ::= { gs2326ARPStaticGatewayCtrlEntry 6 }

gs2326ARPStaticGatewayCtrlReOpen OBJECT-TYPE
   SYNTAX      INTEGER { none(0), reopen(1) }
   MAX-ACCESS  read-write
   STATUS      current
   DESCRIPTION
       "default: 0
       0: none
       1: reopen"
   ::= { gs2326ARPStaticGatewayCtrlEntry 7 }  
   
gs2326ARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2326ARPStaticGatewayCtrlEntry 8 }

gs2326ARPSpoofingPrevention	                                OBJECT IDENTIFIER ::= { gs2326ARPInspection 7 }

gs2326ARPSpoofingPreventionSystemConf                                      OBJECT IDENTIFIER ::= { gs2326ARPSpoofingPrevention 1 }

gs2326ARPSpoofingPreventionMode OBJECT-TYPE
   SYNTAX      INTEGER { disable(0), enable(1) }
   MAX-ACCESS  read-write
   STATUS      current
   DESCRIPTION
       "default: 0
       0: disable
       1: enable "
   ::= { gs2326ARPSpoofingPreventionSystemConf 1 }

gs2326ARPSpoofingPreventionTable OBJECT-TYPE
   SYNTAX      SEQUENCE OF GS2326ARPSpoofingPreventionEntry
   MAX-ACCESS  not-accessible
   STATUS      current
   DESCRIPTION
       " "
   ::= { gs2326ARPSpoofingPrevention 2 }

gs2326ARPSpoofingPreventionEntry OBJECT-TYPE
   SYNTAX      GS2326ARPSpoofingPreventionEntry
   MAX-ACCESS  not-accessible
   STATUS      current
   DESCRIPTION
       ""
   INDEX    { gs2326ARPSpoofingPreventionPort  }
   ::= { gs2326ARPSpoofingPreventionTable 1 }

GS2326ARPSpoofingPreventionEntry ::= SEQUENCE {
   gs2326ARPSpoofingPreventionPort           Integer32,
   gs2326ARPSpoofingPreventionPortMode       INTEGER,
   gs2326ARPSpoofingPreventionPortLimit      Integer32,
   gs2326ARPSpoofingPreventionPortAction     INTEGER,
   gs2326ARPSpoofingPreventionPortState      DisplayString,
   gs2326ARPSpoofingPreventionPortReOpen     INTEGER
}

gs2326ARPSpoofingPreventionPort OBJECT-TYPE
   SYNTAX      Integer32(1..4095)
   MAX-ACCESS  not-accessible
   STATUS      current
   DESCRIPTION
       " "
   ::= { gs2326ARPSpoofingPreventionEntry 1 }

gs2326ARPSpoofingPreventionPortMode OBJECT-TYPE
   SYNTAX      INTEGER { disable(0), enable(1) }
   MAX-ACCESS  read-write
   STATUS      current
   DESCRIPTION
       "default: 0
       0: disable
       1: enable"
   ::= { gs2326ARPSpoofingPreventionEntry 2 }

gs2326ARPSpoofingPreventionPortLimit OBJECT-TYPE
   SYNTAX      Integer32(1..100)
   MAX-ACCESS  read-write
   STATUS      current
   DESCRIPTION
       "default: 1, range: 1-100"
   ::= { gs2326ARPSpoofingPreventionEntry 3 }

gs2326ARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2326ARPSpoofingPreventionEntry 4 }

gs2326ARPSpoofingPreventionPortState OBJECT-TYPE
   SYNTAX      DisplayString
   MAX-ACCESS  read-only
   STATUS      current
   DESCRIPTION
       ""
   ::= { gs2326ARPSpoofingPreventionEntry 5 }

gs2326ARPSpoofingPreventionPortReOpen OBJECT-TYPE
   SYNTAX      INTEGER { none(0), reopen(1) }
   MAX-ACCESS  read-write
   STATUS      current
   DESCRIPTION
       "default: 0
       0: none
       1: reopen"
   ::= { gs2326ARPSpoofingPreventionEntry 6 }  

gs2326ARPIPDoSPrevention	                                OBJECT IDENTIFIER ::= { gs2326ARPInspection 8 }

gs2326ARPIPDoSPreventionTCPMode OBJECT-TYPE
   SYNTAX      INTEGER { disable(0), enable(1) }
   MAX-ACCESS  read-write
   STATUS      current
   DESCRIPTION
       "default: 0
       0: disable
       1: enable "
   ::= { gs2326ARPIPDoSPrevention 1 }

gs2326ARPIPDoSPreventionUDPMode OBJECT-TYPE
   SYNTAX      INTEGER { disable(0), enable(1) }
   MAX-ACCESS  read-write
   STATUS      current
   DESCRIPTION
       "default: 0
       0: disable
       1: enable "
   ::= { gs2326ARPIPDoSPrevention 2 }
   
gs2326ARPIPDoSPreventionICMPMode OBJECT-TYPE
   SYNTAX      INTEGER { disable(0), enable(1) }
   MAX-ACCESS  read-write
   STATUS      current
   DESCRIPTION
       "default: 0
       0: disable
       1: enable "
   ::= { gs2326ARPIPDoSPrevention 3 }   

gs2326ARPIPDoSPreventionServerPort1 OBJECT-TYPE
   SYNTAX      Integer32(0..4094)
   MAX-ACCESS  read-write
   STATUS      current
   DESCRIPTION
       " Port, range: 0 - port number. 0: none. "
   ::= { gs2326ARPIPDoSPrevention 4 }  

gs2326ARPIPDoSPreventionServerPort2 OBJECT-TYPE
   SYNTAX      Integer32(0..4094)
   MAX-ACCESS  read-write
   STATUS      current
   DESCRIPTION
       " Port, range: 0 - port number. 0: none. "
   ::= { gs2326ARPIPDoSPrevention 5 }  
   
gs2326ARPIPDoSPreventionServerPort3 OBJECT-TYPE
   SYNTAX      Integer32(0..4094)
   MAX-ACCESS  read-write
   STATUS      current
   DESCRIPTION
       " Port, range: 0 - port number. 0: none. "
   ::= { gs2326ARPIPDoSPrevention 6 }  
   
gs2326ARPIPDoSPreventionServerPort4 OBJECT-TYPE
   SYNTAX      Integer32(0..4094)
   MAX-ACCESS  read-write
   STATUS      current
   DESCRIPTION
       " Port, range: 0 - port number. 0: none. "
   ::= { gs2326ARPIPDoSPrevention 7 }        

gs2326DHCPSnooping                                          OBJECT IDENTIFIER ::= { gs2326Security 3 }

gs2326DHCPSnoopingConf                                          OBJECT IDENTIFIER ::= { gs2326DHCPSnooping 1 }

gs2326DHCPSnoopingMode OBJECT-TYPE
   SYNTAX      INTEGER { disable(0), enable(1) }
   MAX-ACCESS  read-write
   STATUS      current
   DESCRIPTION
       "default: 0
       0: disable
       1: enable"
   ::= { gs2326DHCPSnoopingConf 1 }

gs2326DHCPSnoopingPortModeConfigurationTable OBJECT-TYPE
   SYNTAX      SEQUENCE OF GS2326DHCPSnoopingPortModeConfigurationEntry
   MAX-ACCESS  not-accessible
   STATUS      current
   DESCRIPTION
       " "
   ::= { gs2326DHCPSnoopingConf 2 }

gs2326DHCPSnoopingPortModeConfigurationEntry OBJECT-TYPE
   SYNTAX      GS2326DHCPSnoopingPortModeConfigurationEntry
   MAX-ACCESS  not-accessible
   STATUS      current
   DESCRIPTION
       ""
   INDEX    { gs2326DHCPSnoopingPortModeConfigurationPort  }
   ::= { gs2326DHCPSnoopingPortModeConfigurationTable 1 }
   
GS2326DHCPSnoopingPortModeConfigurationEntry ::= SEQUENCE {
   gs2326DHCPSnoopingPortModeConfigurationPort	Integer32,
   gs2326DHCPSnoopingPortModeConfigurationMode	INTEGER
}

gs2326DHCPSnoopingPortModeConfigurationPort OBJECT-TYPE
   SYNTAX      Integer32(1..4095)
   MAX-ACCESS  not-accessible
   STATUS      current
   DESCRIPTION
       " "
   ::= { gs2326DHCPSnoopingPortModeConfigurationEntry 1 }

gs2326DHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2326DHCPSnoopingPortModeConfigurationEntry 2 }

gs2326DHCPSnoopingStatisticsTable OBJECT-TYPE
   SYNTAX      SEQUENCE OF GS2326DHCPSnoopingStatisticsEntry
   MAX-ACCESS  not-accessible
   STATUS      current
   DESCRIPTION
       " "
   ::= { gs2326DHCPSnooping 2 }

gs2326DHCPSnoopingStatisticsEntry OBJECT-TYPE
   SYNTAX      GS2326DHCPSnoopingStatisticsEntry
   MAX-ACCESS  not-accessible
   STATUS      current
   DESCRIPTION
       ""
   INDEX    { gs2326DHCPSnoopingStatisticsPort  }
   ::= { gs2326DHCPSnoopingStatisticsTable 1 }

GS2326DHCPSnoopingStatisticsEntry ::= SEQUENCE {
   gs2326DHCPSnoopingStatisticsPort         Integer32,
   gs2326DHCPSnoopingStatisticsClear        INTEGER,
   gs2326DHCPSnoopingRxDiscover             Counter32,
   gs2326DHCPSnoopingRxOffer                Counter32,
   gs2326DHCPSnoopingRxRequest              Counter32,
   gs2326DHCPSnoopingRxDecline              Counter32,
   gs2326DHCPSnoopingRxACK                  Counter32,
   gs2326DHCPSnoopingRxNAK                  Counter32,
   gs2326DHCPSnoopingRxRelease              Counter32,
   gs2326DHCPSnoopingRxInform               Counter32,
   gs2326DHCPSnoopingRxLeaseQuery           Counter32,
   gs2326DHCPSnoopingRxLeaseUnassigned      Counter32,
   gs2326DHCPSnoopingRxLeaseUnknown         Counter32,
   gs2326DHCPSnoopingRxLeaseActive          Counter32,
   gs2326DHCPSnoopingTxDiscover             Counter32,
   gs2326DHCPSnoopingTxOffer                Counter32,
   gs2326DHCPSnoopingTxRequest              Counter32,
   gs2326DHCPSnoopingTxDecline              Counter32,
   gs2326DHCPSnoopingTxACK                  Counter32,
   gs2326DHCPSnoopingTxNAK                  Counter32,
   gs2326DHCPSnoopingTxRelease              Counter32,
   gs2326DHCPSnoopingTxInform               Counter32,
   gs2326DHCPSnoopingTxLeaseQuery           Counter32,
   gs2326DHCPSnoopingTxLeaseUnassigned      Counter32,
   gs2326DHCPSnoopingTxLeaseUnknown         Counter32,
   gs2326DHCPSnoopingTxLeaseActive          Counter32
}

gs2326DHCPSnoopingStatisticsPort OBJECT-TYPE
   SYNTAX      Integer32(1..4095)
   MAX-ACCESS  not-accessible
   STATUS      current
   DESCRIPTION
       " "
   ::= { gs2326DHCPSnoopingStatisticsEntry 1 }

gs2326DHCPSnoopingStatisticsClear OBJECT-TYPE
   SYNTAX      INTEGER { none(0), clear(1) }
   MAX-ACCESS  read-write
   STATUS      current
   DESCRIPTION
       "default: 0
       0: none
       1: clear"
   ::= { gs2326DHCPSnoopingStatisticsEntry 2 }
   
gs2326DHCPSnoopingRxDiscover OBJECT-TYPE
   SYNTAX      Counter32
   MAX-ACCESS  read-only
   STATUS      current
   DESCRIPTION
       " "
   ::= { gs2326DHCPSnoopingStatisticsEntry 3 }

gs2326DHCPSnoopingRxOffer OBJECT-TYPE
   SYNTAX      Counter32
   MAX-ACCESS  read-only
   STATUS      current
   DESCRIPTION
       " "
   ::= { gs2326DHCPSnoopingStatisticsEntry 4 }

gs2326DHCPSnoopingRxRequest OBJECT-TYPE
   SYNTAX      Counter32
   MAX-ACCESS  read-only
   STATUS      current
   DESCRIPTION
       " "
   ::= { gs2326DHCPSnoopingStatisticsEntry 5 }

gs2326DHCPSnoopingRxDecline OBJECT-TYPE
   SYNTAX      Counter32
   MAX-ACCESS  read-only
   STATUS      current
   DESCRIPTION
       " "
   ::= { gs2326DHCPSnoopingStatisticsEntry 6 }

gs2326DHCPSnoopingRxACK OBJECT-TYPE
   SYNTAX      Counter32
   MAX-ACCESS  read-only
   STATUS      current
   DESCRIPTION
       " "
   ::= { gs2326DHCPSnoopingStatisticsEntry 7 }

gs2326DHCPSnoopingRxNAK OBJECT-TYPE
   SYNTAX      Counter32
   MAX-ACCESS  read-only
   STATUS      current
   DESCRIPTION
       " "
   ::= { gs2326DHCPSnoopingStatisticsEntry 8 }   

gs2326DHCPSnoopingRxRelease OBJECT-TYPE
   SYNTAX      Counter32
   MAX-ACCESS  read-only
   STATUS      current
   DESCRIPTION
       " "
   ::= { gs2326DHCPSnoopingStatisticsEntry 9 }

gs2326DHCPSnoopingRxInform OBJECT-TYPE
   SYNTAX      Counter32
   MAX-ACCESS  read-only
   STATUS      current
   DESCRIPTION
       " "
   ::= { gs2326DHCPSnoopingStatisticsEntry 10 }

gs2326DHCPSnoopingRxLeaseQuery OBJECT-TYPE
   SYNTAX      Counter32
   MAX-ACCESS  read-only
   STATUS      current
   DESCRIPTION
       " "
   ::= { gs2326DHCPSnoopingStatisticsEntry 11 }

gs2326DHCPSnoopingRxLeaseUnassigned OBJECT-TYPE
   SYNTAX      Counter32
   MAX-ACCESS  read-only
   STATUS      current
   DESCRIPTION
       " "
   ::= { gs2326DHCPSnoopingStatisticsEntry 12 }

gs2326DHCPSnoopingRxLeaseUnknown OBJECT-TYPE
   SYNTAX      Counter32
   MAX-ACCESS  read-only
   STATUS      current
   DESCRIPTION
       " "
   ::= { gs2326DHCPSnoopingStatisticsEntry 13 }

gs2326DHCPSnoopingRxLeaseActive OBJECT-TYPE
   SYNTAX      Counter32
   MAX-ACCESS  read-only
   STATUS      current
   DESCRIPTION
       " "
   ::= { gs2326DHCPSnoopingStatisticsEntry 14 }

gs2326DHCPSnoopingTxDiscover OBJECT-TYPE
   SYNTAX      Counter32
   MAX-ACCESS  read-only
   STATUS      current
   DESCRIPTION
       " "
   ::= { gs2326DHCPSnoopingStatisticsEntry 15 }

gs2326DHCPSnoopingTxOffer OBJECT-TYPE
   SYNTAX      Counter32
   MAX-ACCESS  read-only
   STATUS      current
   DESCRIPTION
       " "
   ::= { gs2326DHCPSnoopingStatisticsEntry 16 }

gs2326DHCPSnoopingTxRequest OBJECT-TYPE
   SYNTAX      Counter32
   MAX-ACCESS  read-only
   STATUS      current
   DESCRIPTION
       " "
   ::= { gs2326DHCPSnoopingStatisticsEntry 17 }

gs2326DHCPSnoopingTxDecline OBJECT-TYPE
   SYNTAX      Counter32
   MAX-ACCESS  read-only
   STATUS      current
   DESCRIPTION
       " "
   ::= { gs2326DHCPSnoopingStatisticsEntry 18 }

gs2326DHCPSnoopingTxACK OBJECT-TYPE
   SYNTAX      Counter32
   MAX-ACCESS  read-only
   STATUS      current
   DESCRIPTION
       " "
   ::= { gs2326DHCPSnoopingStatisticsEntry 19 }

gs2326DHCPSnoopingTxNAK OBJECT-TYPE
   SYNTAX      Counter32
   MAX-ACCESS  read-only
   STATUS      current
   DESCRIPTION
       " "
   ::= { gs2326DHCPSnoopingStatisticsEntry 20 }   

gs2326DHCPSnoopingTxRelease OBJECT-TYPE
   SYNTAX      Counter32
   MAX-ACCESS  read-only
   STATUS      current
   DESCRIPTION
       " "
   ::= { gs2326DHCPSnoopingStatisticsEntry 21 }

gs2326DHCPSnoopingTxInform OBJECT-TYPE
   SYNTAX      Counter32
   MAX-ACCESS  read-only
   STATUS      current
   DESCRIPTION
       " "
   ::= { gs2326DHCPSnoopingStatisticsEntry 22 }

gs2326DHCPSnoopingTxLeaseQuery OBJECT-TYPE
   SYNTAX      Counter32
   MAX-ACCESS  read-only
   STATUS      current
   DESCRIPTION
       " "
   ::= { gs2326DHCPSnoopingStatisticsEntry 23 }

gs2326DHCPSnoopingTxLeaseUnassigned OBJECT-TYPE
   SYNTAX      Counter32
   MAX-ACCESS  read-only
   STATUS      current
   DESCRIPTION
       " "
   ::= { gs2326DHCPSnoopingStatisticsEntry 24 }

gs2326DHCPSnoopingTxLeaseUnknown OBJECT-TYPE
   SYNTAX      Counter32
   MAX-ACCESS  read-only
   STATUS      current
   DESCRIPTION
       " "
   ::= { gs2326DHCPSnoopingStatisticsEntry 25 }

gs2326DHCPSnoopingTxLeaseActive OBJECT-TYPE
   SYNTAX      Counter32
   MAX-ACCESS  read-only
   STATUS      current
   DESCRIPTION
       " "
   ::= { gs2326DHCPSnoopingStatisticsEntry 26 }


gs2326DHCPRelay                                             OBJECT IDENTIFIER ::= { gs2326Security 4 }

gs2326DHCPRelayConfiguration                                         OBJECT IDENTIFIER ::= { gs2326DHCPRelay 1 }

gs2326DHCPRelayMode OBJECT-TYPE
   SYNTAX      INTEGER { disable(0), enable(1) }
   MAX-ACCESS  read-write
   STATUS      current
   DESCRIPTION
       "default: 0
       0: disable
       1: enable 
       We need at least one server"
   ::= { gs2326DHCPRelayConfiguration 1 }

gs2326DHCPRelayServer OBJECT-TYPE
   SYNTAX      IpAddress
   MAX-ACCESS  read-write
   STATUS      current
   DESCRIPTION
       " "
   ::= { gs2326DHCPRelayConfiguration 2 }

gs2326DHCPRelayInformationMode OBJECT-TYPE
   SYNTAX      INTEGER { disable(0), enable(1) }
   MAX-ACCESS  read-write
   STATUS      current
   DESCRIPTION
       "default: 0
       0: disable
       1: enable "
   ::= { gs2326DHCPRelayConfiguration 3 }

gs2326DHCPRelayInformationPolicy OBJECT-TYPE
   SYNTAX      INTEGER { replace(0), keep(1), drop(2) }
   MAX-ACCESS  read-write
   STATUS      current
   DESCRIPTION
       "default: 0
       0: replace
       1: keep
       2: drop "
   ::= { gs2326DHCPRelayConfiguration 4 }

gs2326DHCPRelayInformationCustom OBJECT-TYPE
   SYNTAX      DisplayString(SIZE(0..32))
   MAX-ACCESS  read-write
   STATUS      current
   DESCRIPTION
       "DHCP Option 82 Circuit ID custom information"
   ::= { gs2326DHCPRelayConfiguration 1500 }

gs2326DHCPRelayConfigurationGateways                                          OBJECT IDENTIFIER ::= { gs2326DHCPRelayConfiguration 5 }

gs2326DHCPRelayConfigurationGatewaysCreate OBJECT-TYPE
   SYNTAX       INTEGER { none(0), create(1) }
   MAX-ACCESS   read-write
   STATUS       current
   DESCRIPTION
       "default: 0
        0 : None  (read only)
        1 : Create entry"
   ::= { gs2326DHCPRelayConfigurationGateways 1 }

gs2326DHCPRelayConfigurationGatewaysTable OBJECT-TYPE
   SYNTAX      SEQUENCE OF Gs2326DHCPRelayConfigurationGatewaysEntry
   MAX-ACCESS  not-accessible
   STATUS      current
   DESCRIPTION
       " Create DHCP Relay Gateway IP address entry."
   ::= { gs2326DHCPRelayConfigurationGateways 2 }

gs2326DHCPRelayConfigurationGatewaysEntry OBJECT-TYPE
   SYNTAX      Gs2326DHCPRelayConfigurationGatewaysEntry
   MAX-ACCESS  not-accessible
   STATUS      current
   DESCRIPTION
       ""
   INDEX    { gs2326DHCPRelayConfigurationGatewaysIndex  }
   ::= { gs2326DHCPRelayConfigurationGatewaysTable 1 }

Gs2326DHCPRelayConfigurationGatewaysEntry ::= SEQUENCE {
   gs2326DHCPRelayConfigurationGatewaysIndex           Integer32,
   gs2326DHCPRelayConfigurationGatewaysVLANId          Integer32,
   gs2326DHCPRelayConfigurationGatewaysIP              IpAddress,
   gs2326DHCPRelayConfigurationGatewaysRowStatus       INTEGER
}

gs2326DHCPRelayConfigurationGatewaysIndex OBJECT-TYPE
   SYNTAX      Integer32(1..6)
   MAX-ACCESS  not-accessible
   STATUS      current
   DESCRIPTION
       " "
   ::= { gs2326DHCPRelayConfigurationGatewaysEntry 1 }

gs2326DHCPRelayConfigurationGatewaysVLANId OBJECT-TYPE
   SYNTAX      Integer32(1..4094)
   MAX-ACCESS  read-write
   STATUS      current
   DESCRIPTION
       " VLAN ID "
   ::= { gs2326DHCPRelayConfigurationGatewaysEntry 2 }

gs2326DHCPRelayConfigurationGatewaysIP OBJECT-TYPE
   SYNTAX      IpAddress
   MAX-ACCESS  read-write
   STATUS      current
   DESCRIPTION
       "DHCP GIADDR address."
   ::= { gs2326DHCPRelayConfigurationGatewaysEntry 3 }
   
gs2326DHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2326DHCPRelayConfigurationGatewaysEntry 4 }

gs2326DHCPRelayStatistics                                   OBJECT IDENTIFIER ::= { gs2326DHCPRelay 2 }

gs2326DHCPRelayServerStatistics                                   OBJECT IDENTIFIER ::= { gs2326DHCPRelayStatistics 1 }

gs2326ServerStatTransmitToServer OBJECT-TYPE
   SYNTAX      Counter32
   MAX-ACCESS  read-only
   STATUS      current
   DESCRIPTION
       " "
   ::= { gs2326DHCPRelayServerStatistics 1 }

gs2326ServerStatTransmitError OBJECT-TYPE
   SYNTAX      Counter32
   MAX-ACCESS  read-only
   STATUS      current
   DESCRIPTION
       " "
   ::= { gs2326DHCPRelayServerStatistics 2 }

gs2326ServerStatReceiveFromServer OBJECT-TYPE
   SYNTAX      Counter32
   MAX-ACCESS  read-only
   STATUS      current
   DESCRIPTION
       " "
   ::= { gs2326DHCPRelayServerStatistics 3 }

gs2326ServerStatReceiveMissingAgentOption OBJECT-TYPE
   SYNTAX      Counter32
   MAX-ACCESS  read-only
   STATUS      current
   DESCRIPTION
       " "
   ::= { gs2326DHCPRelayServerStatistics 4 }

gs2326ServerStatReceiveMissingCircuitID OBJECT-TYPE
   SYNTAX      Counter32
   MAX-ACCESS  read-only
   STATUS      current
   DESCRIPTION
       " "
   ::= { gs2326DHCPRelayServerStatistics 5 }

gs2326ServerStatReceiveMissingRemoteID OBJECT-TYPE
   SYNTAX      Counter32
   MAX-ACCESS  read-only
   STATUS      current
   DESCRIPTION
       " "
   ::= { gs2326DHCPRelayServerStatistics 6 }

gs2326ServerStatReceiveBadCircuitID OBJECT-TYPE
   SYNTAX      Counter32
   MAX-ACCESS  read-only
   STATUS      current
   DESCRIPTION
       " "
   ::= { gs2326DHCPRelayServerStatistics 7 }

gs2326ServerStatReceiveBadRemoteID OBJECT-TYPE
   SYNTAX      Counter32
   MAX-ACCESS  read-only
   STATUS      current
   DESCRIPTION
       " "
   ::= { gs2326DHCPRelayServerStatistics 8 }

gs2326DHCPRelayClientStatistics                                   OBJECT IDENTIFIER ::= { gs2326DHCPRelayStatistics 2 }

gs2326ClientStatTransmitToClient OBJECT-TYPE
   SYNTAX      Counter32
   MAX-ACCESS  read-only
   STATUS      current
   DESCRIPTION
       " "
   ::= { gs2326DHCPRelayClientStatistics 1 }

gs2326ClientStatTransmitError OBJECT-TYPE
   SYNTAX      Counter32
   MAX-ACCESS  read-only
   STATUS      current
   DESCRIPTION
       " "
   ::= { gs2326DHCPRelayClientStatistics 2 }

gs2326ClientStatReceivefromClient OBJECT-TYPE
   SYNTAX      Counter32
   MAX-ACCESS  read-only
   STATUS      current
   DESCRIPTION
       " "
   ::= { gs2326DHCPRelayClientStatistics 3 }

gs2326ClientStatReceiveAgentOption OBJECT-TYPE
   SYNTAX      Counter32
   MAX-ACCESS  read-only
   STATUS      current
   DESCRIPTION
       " "
   ::= { gs2326DHCPRelayClientStatistics 4 }

gs2326ClientStatReplaceAgentOption OBJECT-TYPE
   SYNTAX      Counter32
   MAX-ACCESS  read-only
   STATUS      current
   DESCRIPTION
       " "
   ::= { gs2326DHCPRelayClientStatistics 5 }

gs2326ClientStatKeepAgentOption OBJECT-TYPE
   SYNTAX      Counter32
   MAX-ACCESS  read-only
   STATUS      current
   DESCRIPTION
       " "
   ::= { gs2326DHCPRelayClientStatistics 6 }

gs2326ClientStatDropAgentOption OBJECT-TYPE
   SYNTAX      Counter32
   MAX-ACCESS  read-only
   STATUS      current
   DESCRIPTION
       " "
   ::= { gs2326DHCPRelayClientStatistics 7 }

gs2326PortSecurity                                          OBJECT IDENTIFIER ::= { gs2326Security 5 }

gs2326PortSecLimitCtrl                                      OBJECT IDENTIFIER ::= { gs2326PortSecurity 1 }

gs2326PortSecLimitCtrlSystemConf                                      OBJECT IDENTIFIER ::= { gs2326PortSecLimitCtrl 1 }

gs2326PortSecurityMode OBJECT-TYPE
   SYNTAX      INTEGER { disable(0), enable(1) }
   MAX-ACCESS  read-write
   STATUS      current
   DESCRIPTION
       "default: 0
       0: disable
       1: enable "
   ::= { gs2326PortSecLimitCtrlSystemConf 1 }

gs2326PortSecurityAging OBJECT-TYPE
   SYNTAX      INTEGER { disable(0), enable(1) }
   MAX-ACCESS  read-write
   STATUS      current
   DESCRIPTION
       "default: 0
       0: disable
       1: enable "
   ::= { gs2326PortSecLimitCtrlSystemConf 2 }

gs2326PortSecurityAgingPeriod OBJECT-TYPE
   SYNTAX      INTEGER(10..10000000)
   MAX-ACCESS  read-write
   STATUS      current
   DESCRIPTION
       "default: 3600, range: 10-10000000 "
   ::= { gs2326PortSecLimitCtrlSystemConf 3 }

gs2326PortSecLimitCtrlTable OBJECT-TYPE
   SYNTAX      SEQUENCE OF GS2326PortSecLimitCtrlEntry
   MAX-ACCESS  not-accessible
   STATUS      current
   DESCRIPTION
       " "
   ::= { gs2326PortSecLimitCtrl 2 }

gs2326PortSecLimitCtrlEntry OBJECT-TYPE
   SYNTAX      GS2326PortSecLimitCtrlEntry
   MAX-ACCESS  not-accessible
   STATUS      current
   DESCRIPTION
       ""
   INDEX    { gs2326PortSecLimitCtrlPort  }
   ::= { gs2326PortSecLimitCtrlTable 1 }

GS2326PortSecLimitCtrlEntry ::= SEQUENCE {
   gs2326PortSecLimitCtrlPort           Integer32,
   gs2326PortSecLimitCtrlPortMode       INTEGER,
   gs2326PortSecLimitCtrlPortLimit      Integer32,
   gs2326PortSecLimitCtrlPortAction     INTEGER,
   gs2326PortSecLimitCtrlPortState      DisplayString,
   gs2326PortSecLimitCtrlPortReOpen     INTEGER
}

gs2326PortSecLimitCtrlPort OBJECT-TYPE
   SYNTAX      Integer32(1..4095)
   MAX-ACCESS  not-accessible
   STATUS      current
   DESCRIPTION
       " "
   ::= { gs2326PortSecLimitCtrlEntry 1 }

gs2326PortSecLimitCtrlPortMode OBJECT-TYPE
   SYNTAX      INTEGER { disable(0), enable(1) }
   MAX-ACCESS  read-write
   STATUS      current
   DESCRIPTION
       "default: 0
       0: disable
       1: enable"
   ::= { gs2326PortSecLimitCtrlEntry 2 }

gs2326PortSecLimitCtrlPortLimit OBJECT-TYPE
   SYNTAX      Integer32(1..1024)
   MAX-ACCESS  read-write
   STATUS      current
   DESCRIPTION
       "default: 4, range: 1-1024"
   ::= { gs2326PortSecLimitCtrlEntry 3 }

gs2326PortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2326PortSecLimitCtrlEntry 4 }

gs2326PortSecLimitCtrlPortState OBJECT-TYPE
   SYNTAX      DisplayString
   MAX-ACCESS  read-only
   STATUS      current
   DESCRIPTION
       ""
   ::= { gs2326PortSecLimitCtrlEntry 5 }

gs2326PortSecLimitCtrlPortReOpen OBJECT-TYPE
   SYNTAX      INTEGER { none(0), reopen(1) }
   MAX-ACCESS  read-write
   STATUS      current
   DESCRIPTION
       "default: 0
       0: none
       1: reopen"
   ::= { gs2326PortSecLimitCtrlEntry 6 }

gs2326PortSecSwitchStatusTable OBJECT-TYPE
   SYNTAX      SEQUENCE OF GS2326PortSecSwitchStatusEntry
   MAX-ACCESS  not-accessible
   STATUS      current
   DESCRIPTION
       " "
   ::= { gs2326PortSecurity 2 }

gs2326PortSecSwitchStatusEntry OBJECT-TYPE
   SYNTAX      GS2326PortSecSwitchStatusEntry
   MAX-ACCESS  not-accessible
   STATUS      current
   DESCRIPTION
       ""
   INDEX    { gs2326PortSecSwitchStatusPort  }
   ::= { gs2326PortSecSwitchStatusTable 1 }

GS2326PortSecSwitchStatusEntry ::= SEQUENCE {
   gs2326PortSecSwitchStatusPort                Integer32,
   gs2326PortSecSwitchStatusUsers               DisplayString,
   gs2326PortSecSwitchStatusState               DisplayString,
   gs2326PortSecSwitchStatusMACCountCurrent     Integer32,
   gs2326PortSecSwitchStatusMACCountLimit       Integer32
}

gs2326PortSecSwitchStatusPort OBJECT-TYPE
   SYNTAX      Integer32(1..4095)
   MAX-ACCESS  not-accessible
   STATUS      current
   DESCRIPTION
       " "
   ::= { gs2326PortSecSwitchStatusEntry 1 }

gs2326PortSecSwitchStatusUsers OBJECT-TYPE
   SYNTAX      DisplayString
   MAX-ACCESS  read-only
   STATUS      current
   DESCRIPTION
       " Users Abbr: L = Limit Control, 8 = 802.1X, D = DHCP Snooping, V = Voice VLAN, 
         '-' means that the corresponding user module is not enabled. "
   ::= { gs2326PortSecSwitchStatusEntry 2 }

gs2326PortSecSwitchStatusState OBJECT-TYPE
   SYNTAX      DisplayString
   MAX-ACCESS  read-only
   STATUS      current
   DESCRIPTION
       " Shows the current state of the port : Disabled, Ready, Limit Reached, Shutdown. "
   ::= { gs2326PortSecSwitchStatusEntry 3 }

gs2326PortSecSwitchStatusMACCountCurrent OBJECT-TYPE
   SYNTAX      Integer32(1..4095)
   MAX-ACCESS  read-only
   STATUS      current
   DESCRIPTION
       ""
   ::= { gs2326PortSecSwitchStatusEntry 4 }

gs2326PortSecSwitchStatusMACCountLimit OBJECT-TYPE
   SYNTAX      Integer32(1..4095)
   MAX-ACCESS  read-only
   STATUS      current
   DESCRIPTION
       ""
   ::= { gs2326PortSecSwitchStatusEntry 5 }

gs2326PortSecPortStatus                                      OBJECT IDENTIFIER ::= { gs2326PortSecurity 3 }

gs2326PortSecPortStatusPort OBJECT-TYPE
   SYNTAX       Integer32(1..4095)
   MAX-ACCESS   read-write
   STATUS       current
   DESCRIPTION
       "port number
        default: 1
        range: 1 - port number."
   ::= { gs2326PortSecPortStatus 1 }

gs2326PortSecPortStatusTable OBJECT-TYPE
   SYNTAX      SEQUENCE OF GS2326PortSecPortStatusEntry
   MAX-ACCESS  not-accessible
   STATUS      current
   DESCRIPTION
      " "
   ::= { gs2326PortSecPortStatus 2 }
       
gs2326PortSecPortStatusEntry OBJECT-TYPE
   SYNTAX      GS2326PortSecPortStatusEntry
   MAX-ACCESS  not-accessible
   STATUS      current
   DESCRIPTION
       ""
   INDEX    { gs2326PortSecPortStatusIndex  }
   ::= { gs2326PortSecPortStatusTable 1 }       

GS2326PortSecPortStatusEntry ::= SEQUENCE {
   gs2326PortSecPortStatusIndex              Integer32,
   gs2326PortSecPortStatusMACAddress         MacAddress,
   gs2326PortSecPortStatusVLANId             Integer32,
   gs2326PortSecPortStatusState              DisplayString,
   gs2326PortSecPortStatusTimeOfAddition     DisplayString,
   gs2326PortSecPortStatusAgeAndHold         DisplayString
}

gs2326PortSecPortStatusIndex OBJECT-TYPE
   SYNTAX      Integer32(1..4095)
   MAX-ACCESS  not-accessible
   STATUS      current
   DESCRIPTION
       " "
   ::= { gs2326PortSecPortStatusEntry 1 }

gs2326PortSecPortStatusMACAddress OBJECT-TYPE
   SYNTAX      MacAddress
   MAX-ACCESS  read-only
   STATUS      current
   DESCRIPTION
       " "
   ::= { gs2326PortSecPortStatusEntry 2 }

gs2326PortSecPortStatusVLANId OBJECT-TYPE
   SYNTAX      Integer32(1..4094)
   MAX-ACCESS  read-only
   STATUS      current
   DESCRIPTION
       " "
   ::= { gs2326PortSecPortStatusEntry 3 }

gs2326PortSecPortStatusState OBJECT-TYPE
   SYNTAX      DisplayString
   MAX-ACCESS  read-only
   STATUS      current
   DESCRIPTION
       "Blocked / Forwarding "
   ::= { gs2326PortSecPortStatusEntry 4 }

gs2326PortSecPortStatusTimeOfAddition OBJECT-TYPE
   SYNTAX      DisplayString
   MAX-ACCESS  read-only
   STATUS      current
   DESCRIPTION
       " "
   ::= { gs2326PortSecPortStatusEntry 5 }

gs2326PortSecPortStatusAgeAndHold OBJECT-TYPE
   SYNTAX      DisplayString
   MAX-ACCESS  read-only
   STATUS      current
   DESCRIPTION
       " "
   ::= { gs2326PortSecPortStatusEntry 6 }       
       

gs2326AccessManagement                                      OBJECT IDENTIFIER ::= { gs2326Security 6 }

gs2326AccessMgtConf                                         OBJECT IDENTIFIER ::= { gs2326AccessManagement 1 }

gs2326AccessMgtConfMode OBJECT-TYPE
   SYNTAX      INTEGER { disable(0), enable(1) }
   MAX-ACCESS  read-write
   STATUS      current
   DESCRIPTION
       "default: 0
       0: disable
       1: enable "
   ::= { gs2326AccessMgtConf 1 }

gs2326AccessMgtConfCreate OBJECT-TYPE
   SYNTAX      INTEGER { none(0), create(1) }
   MAX-ACCESS  read-write
   STATUS      current
   DESCRIPTION
       "default: 0
       0: none
       1: create "
   ::= { gs2326AccessMgtConf 2 }

gs2326AccessMgtConfTable OBJECT-TYPE
   SYNTAX      SEQUENCE OF GS2326AccessMgtConfEntry
   MAX-ACCESS  not-accessible
   STATUS      current
   DESCRIPTION
       " "
   ::= { gs2326AccessMgtConf 3 }

gs2326AccessMgtConfEntry OBJECT-TYPE
   SYNTAX      GS2326AccessMgtConfEntry
   MAX-ACCESS  not-accessible
   STATUS      current
   DESCRIPTION
       ""
   INDEX    { gs2326AccessMgtIndex  }
   ::= { gs2326AccessMgtConfTable 1 }
   
GS2326AccessMgtConfEntry ::= SEQUENCE {
   gs2326AccessMgtIndex             Integer32,
   gs2326AccessMgtAddresstype       INTEGER,
   gs2326AccessMgtStartIpAddress    DisplayString,
   gs2326AccessMgtEndIpAddress      DisplayString,
   gs2326AccessMgtHttpHttps         INTEGER,
   gs2326AccessMgtSNMP              INTEGER,
   gs2326AccessMgtTelnetSSH         INTEGER,
   gs2326AccessMgtRowStatus         INTEGER
}

gs2326AccessMgtIndex OBJECT-TYPE
   SYNTAX      Integer32(1..16)
   MAX-ACCESS  read-write
   STATUS      current
   DESCRIPTION
       "Set Access Management config index
        range : 1-16."
   ::= { gs2326AccessMgtConfEntry 1 }

gs2326AccessMgtAddresstype OBJECT-TYPE
   SYNTAX      INTEGER { ipv4(0), ipv6(1) }
   MAX-ACCESS  read-write
   STATUS      current
   DESCRIPTION
       "0: ipv4
        1: ipv6 "
   ::= { gs2326AccessMgtConfEntry 2 }
   
gs2326AccessMgtStartIpAddress OBJECT-TYPE
   SYNTAX      DisplayString
   MAX-ACCESS  read-write
   STATUS      current
   DESCRIPTION
       " Start IP address. 
         IP address doesn't allowed all zero or all 'ff'H."
   ::= { gs2326AccessMgtConfEntry 3 }
   
gs2326AccessMgtEndIpAddress OBJECT-TYPE
   SYNTAX      DisplayString
   MAX-ACCESS  read-write
   STATUS      current
   DESCRIPTION
       " End IP address. 
         IP address doesn't allowed all zero or all 'ff'H.
         End ip address is not less than start ip address."
   ::= { gs2326AccessMgtConfEntry 4 }

gs2326AccessMgtHttpHttps OBJECT-TYPE
   SYNTAX      INTEGER { disable(0), enable(1) }
   MAX-ACCESS  read-write
   STATUS      current
   DESCRIPTION
       "default: 0
       0: disable
       1: enable "
   ::= { gs2326AccessMgtConfEntry 5 }

gs2326AccessMgtSNMP OBJECT-TYPE
   SYNTAX      INTEGER { disable(0), enable(1) }
   MAX-ACCESS  read-write
   STATUS      current
   DESCRIPTION
       "default: 0
       0: disable
       1: enable "
   ::= { gs2326AccessMgtConfEntry 6 }

gs2326AccessMgtTelnetSSH OBJECT-TYPE
   SYNTAX      INTEGER { disable(0), enable(1) }
   MAX-ACCESS  read-write
   STATUS      current
   DESCRIPTION
       "default: 0
       0: disable
       1: enable "
   ::= { gs2326AccessMgtConfEntry 7 }

gs2326AccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2326AccessMgtConfEntry 8 }

gs2326AccessMgtStatistics                                   OBJECT IDENTIFIER ::= { gs2326AccessManagement 2 }

gs2326HttpReceivedPkts OBJECT-TYPE
   SYNTAX      Counter32
   MAX-ACCESS  read-only
   STATUS      current
   DESCRIPTION
       " "
   ::= { gs2326AccessMgtStatistics 1 }

gs2326HttpAllowedPkts OBJECT-TYPE
   SYNTAX      Counter32
   MAX-ACCESS  read-only
   STATUS      current
   DESCRIPTION
       " "
   ::= { gs2326AccessMgtStatistics 2 }

gs2326HttpDiscardedPkts OBJECT-TYPE
   SYNTAX      Counter32
   MAX-ACCESS  read-only
   STATUS      current
   DESCRIPTION
       " "
   ::= { gs2326AccessMgtStatistics 3 }

gs2326HttpsReceivedPkts OBJECT-TYPE
   SYNTAX      Counter32
   MAX-ACCESS  read-only
   STATUS      current
   DESCRIPTION
       " "
   ::= { gs2326AccessMgtStatistics 4 }

gs2326HttpsAllowedPkts OBJECT-TYPE
   SYNTAX      Counter32
   MAX-ACCESS  read-only
   STATUS      current
   DESCRIPTION
       " "
   ::= { gs2326AccessMgtStatistics 5 }

gs2326HttpsDiscardedPkts OBJECT-TYPE
   SYNTAX      Counter32
   MAX-ACCESS  read-only
   STATUS      current
   DESCRIPTION
       " "
   ::= { gs2326AccessMgtStatistics 6 }

gs2326SnmpReceivedPkts OBJECT-TYPE
   SYNTAX      Counter32
   MAX-ACCESS  read-only
   STATUS      current
   DESCRIPTION
       " "
   ::= { gs2326AccessMgtStatistics 7 }

gs2326SnmpAllowedPkts OBJECT-TYPE
   SYNTAX      Counter32
   MAX-ACCESS  read-only
   STATUS      current
   DESCRIPTION
       " "
   ::= { gs2326AccessMgtStatistics 8 }

gs2326SnmpDiscardedPkts OBJECT-TYPE
   SYNTAX      Counter32
   MAX-ACCESS  read-only
   STATUS      current
   DESCRIPTION
       " "
   ::= { gs2326AccessMgtStatistics 9 }

gs2326TelnetReceivedPkts OBJECT-TYPE
   SYNTAX      Counter32
   MAX-ACCESS  read-only
   STATUS      current
   DESCRIPTION
       " "
   ::= { gs2326AccessMgtStatistics 10 }

gs2326TelnetAllowedPkts OBJECT-TYPE
   SYNTAX      Counter32
   MAX-ACCESS  read-only
   STATUS      current
   DESCRIPTION
       " "
   ::= { gs2326AccessMgtStatistics 11 }

gs2326TelnetDiscardedPkts OBJECT-TYPE
   SYNTAX      Counter32
   MAX-ACCESS  read-only
   STATUS      current
   DESCRIPTION
       " "
   ::= { gs2326AccessMgtStatistics 12 }

gs2326SSHReceivedPkts OBJECT-TYPE
   SYNTAX      Counter32
   MAX-ACCESS  read-only
   STATUS      current
   DESCRIPTION
       " "
   ::= { gs2326AccessMgtStatistics 13 }

gs2326SSHAllowedPkts OBJECT-TYPE
   SYNTAX      Counter32
   MAX-ACCESS  read-only
   STATUS      current
   DESCRIPTION
       " "
   ::= { gs2326AccessMgtStatistics 14 }

gs2326SSHDiscardedPkts OBJECT-TYPE
   SYNTAX      Counter32
   MAX-ACCESS  read-only
   STATUS      current
   DESCRIPTION
       " "
   ::= { gs2326AccessMgtStatistics 15 }

gs2326AccessMgtStatisticsClearAll OBJECT-TYPE
   SYNTAX      INTEGER { none(0), clear(1) }
   MAX-ACCESS  read-write
   STATUS      current
   DESCRIPTION
       "0: none
        1: clear"
   ::= { gs2326AccessMgtStatistics 16 }

gs2326SSH                                                   OBJECT IDENTIFIER ::= { gs2326Security 7 }

gs2326SSHMode OBJECT-TYPE
   SYNTAX      INTEGER { disable(0), enable(1) }
   MAX-ACCESS  read-write
   STATUS      current
   DESCRIPTION
       "default: 1
        0: disable
        1: enable"
   ::= { gs2326SSH 1 }

gs2326HTTPS                                                 OBJECT IDENTIFIER ::= { gs2326Security 8 }

gs2326HTTPSMode OBJECT-TYPE
   SYNTAX      INTEGER { disable(0), enable(1) }
   MAX-ACCESS  read-write
   STATUS      current
   DESCRIPTION
       "default: 1
        0: disable
        1: enable"
   ::= { gs2326HTTPS 1 }

gs2326HTTPSAutoRedirect OBJECT-TYPE
   SYNTAX      INTEGER { disable(0), enable(1) }
   MAX-ACCESS  read-write
   STATUS      current
   DESCRIPTION
       "default: 0
        0: disable
        1: enable"
   ::= { gs2326HTTPS 2 }

gs2326HTTPSCertRenew OBJECT-TYPE
   SYNTAX      INTEGER { doNothing(0), renew(1) }
   MAX-ACCESS  read-write
   STATUS      current
   DESCRIPTION
       "default: 0 ,
        0: doNothing
        1: renew"
   ::= { gs2326HTTPS 3 }

gs2326HTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2326HTTPS 4 }

gs2326HTTPMode OBJECT-TYPE
   SYNTAX      INTEGER { disable(0), enable(1) }
   MAX-ACCESS  read-write
   STATUS      current
   DESCRIPTION
       "default: 1
        0: disable
        1: enable"
   ::= { gs2326HTTPS 5 }

gs2326AuthMethod                                            OBJECT IDENTIFIER ::= { gs2326Security 9 }

gs2326ConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326AuthMethod 1 }

gs2326ConsoleFallback OBJECT-TYPE
   SYNTAX      INTEGER { disable(0), enable(1) }
   MAX-ACCESS  read-write
   STATUS      current
   DESCRIPTION
       "default: 0
        0:disable
        1:enable"
   ::= { gs2326AuthMethod 2 }

gs2326TelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326AuthMethod 3 }

gs2326TelnetFallback OBJECT-TYPE
   SYNTAX      INTEGER { disable(0), enable(1) }
   MAX-ACCESS  read-write
   STATUS      current
   DESCRIPTION
       "default: 0
        0:disable
        1:enable"
   ::= { gs2326AuthMethod 4 }

gs2326SshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326AuthMethod 5 }

gs2326SshFallback OBJECT-TYPE
   SYNTAX      INTEGER { disable(0), enable(1) }
   MAX-ACCESS  read-write
   STATUS      current
   DESCRIPTION
       "default: 0
        0:disable
        1:enable"
   ::= { gs2326AuthMethod 6 }

gs2326TftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326AuthMethod 9 }

gs2326TftpFallback OBJECT-TYPE
   SYNTAX      INTEGER { disable(0), enable(1) }
   MAX-ACCESS  read-write
   STATUS      current
   DESCRIPTION
       "default: 0
        0:disable
        1:enable"
   ::= { gs2326AuthMethod 10 }
   
gs2326LoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2326AuthMethod 11 }

gs2326LockMinutes OBJECT-TYPE
   SYNTAX      Integer32(1..99)
   MAX-ACCESS  read-write
   STATUS      current
   DESCRIPTION
       "Lock time to login failures trigger.
        range: 1-99.
        default: 5."
   ::= { gs2326AuthMethod 12 }

gs2326HttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326AuthMethod 13 }

gs2326HttpFallback OBJECT-TYPE
   SYNTAX      INTEGER { disable(0), enable(1) }
   MAX-ACCESS  read-write
   STATUS      current
   DESCRIPTION
       "default: 0
        0:disable
        1:enable"
   ::= { gs2326AuthMethod 14 }

gs2326HttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326AuthMethod 15 }

gs2326HttpsFallback OBJECT-TYPE
   SYNTAX      INTEGER { disable(0), enable(1) }
   MAX-ACCESS  read-write
   STATUS      current
   DESCRIPTION
       "default: 0
        0:disable
        1:enable"
   ::= { gs2326AuthMethod 16 }


gs2326AAA                                              OBJECT IDENTIFIER ::= { gs2326Security 10 }

gs2326AAACommonServer                                  OBJECT IDENTIFIER ::= { gs2326AAA 1 }

gs2326AAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2326AAACommonServer 1 }

gs2326AAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2326AAACommonServer 2 }

gs2326AAATACACSPlusAuthAndAccounting                  OBJECT IDENTIFIER ::= { gs2326AAA 2 }

gs2326AAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2326AAATACACSPlusAuthAndAccounting 1 }

gs2326AAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2326AAATACACSPlusAuthAndAccounting 2 }

gs2326AAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2326AAATACACSPlusAuthAndAccounting 3 }

gs2326RADIUSAuthenticationServerTable OBJECT-TYPE
   SYNTAX      SEQUENCE OF Gs2326RADIUSAuthenticationServerEntry
   MAX-ACCESS  not-accessible
   STATUS      current
   DESCRIPTION
       " "
   ::= { gs2326AAA 3 }

gs2326RADIUSAuthenticationServerEntry OBJECT-TYPE
   SYNTAX      Gs2326RADIUSAuthenticationServerEntry
   MAX-ACCESS  not-accessible
   STATUS      current
   DESCRIPTION
       ""
   INDEX    { gs2326RADIUSAuthenticationServerIndex  }
   ::= { gs2326RADIUSAuthenticationServerTable 1 }

Gs2326RADIUSAuthenticationServerEntry ::= SEQUENCE {
   gs2326RADIUSAuthenticationServerIndex     Integer32,
   gs2326RADIUSAuthenticationServerEnable    INTEGER,
   gs2326RADIUSAuthenticationServerIP        DisplayString,
   gs2326RADIUSAuthenticationServerPort      Integer32,
   gs2326RADIUSAuthenticationServerSecret    DisplayString
}

gs2326RADIUSAuthenticationServerIndex OBJECT-TYPE
   SYNTAX      Integer32(1..5)
   MAX-ACCESS  not-accessible
   STATUS      current
   DESCRIPTION
       "RADIUS Authentication Server index
        range : 1-5."
   ::= { gs2326RADIUSAuthenticationServerEntry 1 }

gs2326RADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2326RADIUSAuthenticationServerEntry 2 }

gs2326RADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2326RADIUSAuthenticationServerEntry 3 }

gs2326RADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2326RADIUSAuthenticationServerEntry 4 }

gs2326RADIUSAuthenticationServerSecret OBJECT-TYPE
   SYNTAX      DisplayString
   MAX-ACCESS  read-write
   STATUS      current
   DESCRIPTION
       "The secret - up to 64 characters long - shared between the RADIUS Authentication Server and the switch. "
   ::= { gs2326RADIUSAuthenticationServerEntry 5 }
   

gs2326RADIUSAccountingServerTable OBJECT-TYPE
   SYNTAX      SEQUENCE OF Gs2326RADIUSAccountingServerEntry
   MAX-ACCESS  not-accessible
   STATUS      current
   DESCRIPTION
       " "
   ::= { gs2326AAA 4 }

gs2326RADIUSAccountingServerEntry OBJECT-TYPE
   SYNTAX      Gs2326RADIUSAccountingServerEntry
   MAX-ACCESS  not-accessible
   STATUS      current
   DESCRIPTION
       ""
   INDEX    { gs2326RADIUSAccountingServerIndex  }
   ::= { gs2326RADIUSAccountingServerTable 1 }

Gs2326RADIUSAccountingServerEntry ::= SEQUENCE {
   gs2326RADIUSAccountingServerIndex     Integer32,
   gs2326RADIUSAccountingServerEnable    INTEGER,
   gs2326RADIUSAccountingServerIP        DisplayString,
   gs2326RADIUSAccountingServerPort      Integer32,
   gs2326RADIUSAccountingServerSecret    DisplayString
}

gs2326RADIUSAccountingServerIndex OBJECT-TYPE
   SYNTAX      Integer32(1..5)
   MAX-ACCESS  not-accessible
   STATUS      current
   DESCRIPTION
       "RADIUS Accounting Server index
        range : 1-5."
   ::= { gs2326RADIUSAccountingServerEntry 1 }

gs2326RADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2326RADIUSAccountingServerEntry 2 }

gs2326RADIUSAccountingServerIP OBJECT-TYPE
   SYNTAX      DisplayString
   MAX-ACCESS  read-write
   STATUS      current
   DESCRIPTION
       "The IP address or hostname of the RADIUS Accounting Server.
       IP address is expressed in  dotted decimal notation. "
   ::= { gs2326RADIUSAccountingServerEntry 3 }

gs2326RADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2326RADIUSAccountingServerEntry 4 }

gs2326RADIUSAccountingServerSecret OBJECT-TYPE
   SYNTAX      DisplayString
   MAX-ACCESS  read-write
   STATUS      current
   DESCRIPTION
       "The secret - up to 64 characters long - shared between the RADIUS Accounting Server and the switch. "
   ::= { gs2326RADIUSAccountingServerEntry 5 }

gs2326TACACSPlusAuthenticationServerTable OBJECT-TYPE
   SYNTAX      SEQUENCE OF Gs2326TACACSPlusAuthenticationServerEntry
   MAX-ACCESS  not-accessible
   STATUS      current
   DESCRIPTION
       " "
   ::= { gs2326AAA 5 }

gs2326TACACSPlusAuthenticationServerEntry OBJECT-TYPE
   SYNTAX      Gs2326TACACSPlusAuthenticationServerEntry
   MAX-ACCESS  not-accessible
   STATUS      current
   DESCRIPTION
       ""
   INDEX    { gs2326TACACSPlusAuthenticationServerIndex  }
   ::= { gs2326TACACSPlusAuthenticationServerTable 1 }

Gs2326TACACSPlusAuthenticationServerEntry ::= SEQUENCE {
   gs2326TACACSPlusAuthenticationServerIndex     Integer32,
   gs2326TACACSPlusAuthenticationServerEnable    INTEGER,
   gs2326TACACSPlusAuthenticationServerIP        DisplayString,
   gs2326TACACSPlusAuthenticationServerPort      Integer32,
   gs2326TACACSPlusAuthenticationServerSecret    DisplayString
}

gs2326TACACSPlusAuthenticationServerIndex OBJECT-TYPE
   SYNTAX      Integer32(1..5)
   MAX-ACCESS  not-accessible
   STATUS      current
   DESCRIPTION
       "TACACSPlus Authentication Server index
        range : 1-5."
   ::= { gs2326TACACSPlusAuthenticationServerEntry 1 }

gs2326TACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2326TACACSPlusAuthenticationServerEntry 2 }

gs2326TACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2326TACACSPlusAuthenticationServerEntry 3 }

gs2326TACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2326TACACSPlusAuthenticationServerEntry 4 }

gs2326TACACSPlusAuthenticationServerSecret OBJECT-TYPE
   SYNTAX      DisplayString
   MAX-ACCESS  read-write
   STATUS      current
   DESCRIPTION
       "The secret - up to 64 characters long - shared between the TACACSPlus Authentication Server and the switch. "
   ::= { gs2326TACACSPlusAuthenticationServerEntry 5 }


gs2326RADIUSStatisticsTable OBJECT-TYPE
   SYNTAX      SEQUENCE OF Gs2326RADIUSStatisticsEntry
   MAX-ACCESS  not-accessible
   STATUS      current
   DESCRIPTION
       " "
   ::= { gs2326AAA 6 }

gs2326RADIUSStatisticsEntry OBJECT-TYPE
   SYNTAX      Gs2326RADIUSStatisticsEntry
   MAX-ACCESS  not-accessible
   STATUS      current
   DESCRIPTION
       ""
   INDEX    { gs2326RADIUSAuthStatisticsServerIndex  }
   ::= { gs2326RADIUSStatisticsTable 1 }

Gs2326RADIUSStatisticsEntry ::= SEQUENCE {
   gs2326RADIUSAuthStatisticsServerIndex                           Integer32,
   gs2326RADIUSAuthStatisticsRecPktAccessAccepts                   Counter32,
   gs2326RADIUSAuthStatisticsRecPktAccessRejects                   Counter32,
   gs2326RADIUSAuthStatisticsRecPktAccessChallenges                Counter32,
   gs2326RADIUSAuthStatisticsRecPktMalformedAccResponses           Counter32,
   gs2326RADIUSAuthStatisticsRecPktBadAuthenticators               Counter32,
   gs2326RADIUSAuthStatisticsRecPktUnknownTypes                    Counter32,
   gs2326RADIUSAuthStatisticsRecPktDropped                         Counter32,
   gs2326RADIUSAuthStatisticsTransmitPktAccessRequests             Counter32,
   gs2326RADIUSAuthStatisticsTransmitPktAccessRetransmissions      Counter32,
   gs2326RADIUSAuthStatisticsTransmitPktPendingRequests            Counter32,
   gs2326RADIUSAuthStatisticsTransmitPktTimeouts                   Counter32,
   gs2326RADIUSAuthIP                                              DisplayString,
   gs2326RADIUSAuthState                                           DisplayString,
   gs2326RADIUSAuthRoundTripTime                                   DisplayString,

   gs2326RADIUSAccountingStatisticsRecPktResponses                 Counter32,
   gs2326RADIUSAccountingStatisticsRecPktMalformedResponses        Counter32,
   gs2326RADIUSAccountingStatisticsRecPktBadAuthenticators         Counter32,
   gs2326RADIUSAccountingStatisticsRecPktUnknownTypes              Counter32,
   gs2326RADIUSAccountingStatisticsRecPktDropped                   Counter32,
   gs2326RADIUSAccountingStatisticsTransmitPktRequests             Counter32,
   gs2326RADIUSAccountingStatisticsTransmitPktRetransmissions      Counter32,
   gs2326RADIUSAccountingStatisticsTransmitPktPendingRequests      Counter32,
   gs2326RADIUSAccountingStatisticsTransmitPktTimeouts             Counter32,
   gs2326RADIUSAccountingIP                                        DisplayString,
   gs2326RADIUSAccountingState                                     DisplayString,
   gs2326RADIUSAccountingRoundTripTime                             DisplayString,
   gs2326RADIUSStatisticsClear                                     INTEGER
}

gs2326RADIUSAuthStatisticsServerIndex OBJECT-TYPE
   SYNTAX      Integer32(1..5)
   MAX-ACCESS  not-accessible
   STATUS      current
   DESCRIPTION
       "RADIUS Authentication Server index
        range : 1-5."
   ::= { gs2326RADIUSStatisticsEntry 1 }

gs2326RADIUSAuthStatisticsRecPktAccessAccepts OBJECT-TYPE
   SYNTAX      Counter32
   MAX-ACCESS  read-only
   STATUS      current
   DESCRIPTION
       "The number of RADIUS Access-Accept packets (valid or invalid) received from the server."
   ::= { gs2326RADIUSStatisticsEntry 2 }

gs2326RADIUSAuthStatisticsRecPktAccessRejects OBJECT-TYPE
   SYNTAX      Counter32
   MAX-ACCESS  read-only
   STATUS      current
   DESCRIPTION
       "The number of RADIUS Access-Reject packets (valid or invalid) received from the server."
   ::= { gs2326RADIUSStatisticsEntry 3 }

gs2326RADIUSAuthStatisticsRecPktAccessChallenges OBJECT-TYPE
   SYNTAX      Counter32
   MAX-ACCESS  read-only
   STATUS      current
   DESCRIPTION
       "The number of RADIUS Access-Challenge packets (valid or invalid) received from the server. "
   ::= { gs2326RADIUSStatisticsEntry 4 }

gs2326RADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2326RADIUSStatisticsEntry 5 }

gs2326RADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2326RADIUSStatisticsEntry 6 }

gs2326RADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2326RADIUSStatisticsEntry 7 }

gs2326RADIUSAuthStatisticsRecPktDropped OBJECT-TYPE
   SYNTAX      Counter32
   MAX-ACCESS  read-only
   STATUS      current
   DESCRIPTION
       "The number of RADIUS packets that were received from the server on the
       authentication port and dropped for some other reason."
   ::= { gs2326RADIUSStatisticsEntry 8 }

gs2326RADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2326RADIUSStatisticsEntry 9 }

gs2326RADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2326RADIUSStatisticsEntry 10 }

gs2326RADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2326RADIUSStatisticsEntry 11 }

gs2326RADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2326RADIUSStatisticsEntry 12 }

gs2326RADIUSAuthIP OBJECT-TYPE
   SYNTAX      DisplayString
   MAX-ACCESS  read-only
   STATUS      current
   DESCRIPTION
       "IP address and UDP port for the authentication server in question."
   ::= { gs2326RADIUSStatisticsEntry 13 }

gs2326RADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2326RADIUSStatisticsEntry 14 }

gs2326RADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2326RADIUSStatisticsEntry 15 }

gs2326RADIUSAccountingStatisticsRecPktResponses OBJECT-TYPE
   SYNTAX      Counter32
   MAX-ACCESS  read-only
   STATUS      current
   DESCRIPTION
       "The number of RADIUS packets (valid or invalid) received from the server."
   ::= { gs2326RADIUSStatisticsEntry 16 }

gs2326RADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2326RADIUSStatisticsEntry 17 }

gs2326RADIUSAccountingStatisticsRecPktBadAuthenticators OBJECT-TYPE
   SYNTAX      Counter32
   MAX-ACCESS  read-only
   STATUS      current
   DESCRIPTION
       "The number of RADIUS packets containing invalid authenticators received
       from the server."
   ::= { gs2326RADIUSStatisticsEntry 18 }

gs2326RADIUSAccountingStatisticsRecPktUnknownTypes OBJECT-TYPE
   SYNTAX      Counter32
   MAX-ACCESS  read-only
   STATUS      current
   DESCRIPTION
       "The number of RADIUS packets of unknown types that were received from
       the server on the accounting port."
   ::= { gs2326RADIUSStatisticsEntry 19 }

gs2326RADIUSAccountingStatisticsRecPktDropped OBJECT-TYPE
   SYNTAX      Counter32
   MAX-ACCESS  read-only
   STATUS      current
   DESCRIPTION
       "The number of RADIUS packets that were received from the server on the
       accounting port and dropped for some other reason."
   ::= { gs2326RADIUSStatisticsEntry 20 }

gs2326RADIUSAccountingStatisticsTransmitPktRequests OBJECT-TYPE
   SYNTAX      Counter32
   MAX-ACCESS  read-only
   STATUS      current
   DESCRIPTION
       "The number of RADIUS packets sent to the server. This does not include
       retransmissions."
   ::= { gs2326RADIUSStatisticsEntry 21 }

gs2326RADIUSAccountingStatisticsTransmitPktRetransmissions OBJECT-TYPE
   SYNTAX      Counter32
   MAX-ACCESS  read-only
   STATUS      current
   DESCRIPTION
       "The number of RADIUS packets retransmitted to the RADIUS accounting server."
   ::= { gs2326RADIUSStatisticsEntry 22 }

gs2326RADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2326RADIUSStatisticsEntry 23 }

gs2326RADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2326RADIUSStatisticsEntry 24 }

gs2326RADIUSAccountingIP OBJECT-TYPE
   SYNTAX      DisplayString
   MAX-ACCESS  read-only
   STATUS      current
   DESCRIPTION
       "IP address and UDP port for the accounting server in question."
   ::= { gs2326RADIUSStatisticsEntry 25 }

gs2326RADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2326RADIUSStatisticsEntry 26 }
   
gs2326RADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2326RADIUSStatisticsEntry 27 }

gs2326RADIUSStatisticsClear OBJECT-TYPE
   SYNTAX      INTEGER(0|1)
   MAX-ACCESS  read-write
   STATUS      current
   DESCRIPTION
       "Clears the counters for the server.
       read: always 0
       clear: set 1"
   ::= { gs2326RADIUSStatisticsEntry 28 }

gs2326NAS                                              OBJECT IDENTIFIER ::= { gs2326Security 11 }

gs2326NASConfiguration                                 OBJECT IDENTIFIER ::= { gs2326NAS 1 }

gs2326NASConfigMode OBJECT-TYPE
   SYNTAX      INTEGER { disable(0), enable(1) }
   MAX-ACCESS  read-write
   STATUS      current
   DESCRIPTION
       "Indicates if NAS is globally enabled or disabled on the switch. 
	    If globally disabled, all ports are allowed forwarding of frames."
   ::= { gs2326NASConfiguration 1 }

gs2326NASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication 
		Period. Reauthentication for 802.1X-enabled ports can be used to 
		detect if a new device is plugged into a switch port or if a 
		supplicant is no longer attached. 
		For MAC-based ports, reauthentication is only useful if the RADIUS 
		server configuration has changed. It does not involve communication 
		between the switch and the client, and therefore doesn't imply that 
		a client is still present on a port."
   ::= { gs2326NASConfiguration 2 }

gs2326NASConfigReauthPeriod OBJECT-TYPE
   SYNTAX      Integer32(1..3600)
   MAX-ACCESS  read-write
   STATUS      current
   DESCRIPTION
       "Determines the period, in seconds, after which a connected client must 
	    be reauthenticated. This is only active if the Reauthentication Enabled 
		checkbox is checked. 
		range: 1 - 3600 seconds."
   ::= { gs2326NASConfiguration 3 }

gs2326NASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2326NASConfiguration 4 }
   
gs2326NASConfigAgingPeriod OBJECT-TYPE
   SYNTAX      Integer32(10..1000000)
   MAX-ACCESS  read-write
   STATUS      current
   DESCRIPTION
       "When the NAS module uses the Port Security module to secure MAC addresses, 
	    the Port Security module needs to check for activity on the MAC address 
		in question at regular intervals and free resources if no activity 
		is seen within a given period of time.
		Admin State supported : Single, Multi and MAC-Based Auth. 802.1X.
		range: 10 - 1000000 seconds."
   ::= { gs2326NASConfiguration 5 }   
   
gs2326NASConfigHoldTime OBJECT-TYPE
   SYNTAX      Integer32(10..1000000)
   MAX-ACCESS  read-write
   STATUS      current
   DESCRIPTION
       "If a client is denied access - either because the RADIUS server denies
	    the client access or because the RADIUS server request times out 
		- the client is put on hold in the Unauthorized state. The hold timer 
		does not count during an on-going authentication. In MAC-based Auth. 
		mode, the switch will ignore new frames coming from the client during 
		the hold time.
		Admin State supported : Single, Multi and MAC-Based Auth. 802.1X.
		range: 10 - 1000000 seconds."
   ::= { gs2326NASConfiguration 6 }  

gs2326NASConfigRADIUSAssignedQoSEnabled OBJECT-TYPE
   SYNTAX      INTEGER { disable(0), enable(1) }
   MAX-ACCESS  read-write
   STATUS      current
   DESCRIPTION
       "RADIUS-assigned QoS provides a means to centrally control the 
	    traffic class to which traffic coming from a successfully authenticated 
		supplicant is assigned on the switch. The RADIUS server must be configured 
		to transmit special RADIUS attributes to take advantage of this feature."
   ::= { gs2326NASConfiguration 7 }  
 
gs2326NASConfigRADIUSAssignedVLANEnabled OBJECT-TYPE
   SYNTAX      INTEGER { disable(0), enable(1) }
   MAX-ACCESS  read-write
   STATUS      current
   DESCRIPTION
       "RADIUS-assigned VLAN provides a means to centrally control the VLAN on 
	    which a successfully authenticated supplicant is placed on the switch. 
	    Incoming traffic will be classified to and switched on the RADIUS-assigned 
		VLAN. The RADIUS server must be configured to transmit special RADIUS 
		attributes to take advantage of this feature.When enable, the individual 
		ports' ditto setting determine whether RADIUS-assigned VLAN is enabled 
		on that port. When disable, RADIUS-server assigned VLAN is disabled on 
		all ports. "
   ::= { gs2326NASConfiguration 8 }    
   
gs2326NASConfigGuestVLANEnabled OBJECT-TYPE
   SYNTAX      INTEGER { disable(0), enable(1) }
   MAX-ACCESS  read-write
   STATUS      current
   DESCRIPTION
       "A Guest VLAN is a special VLAN - typically with limited network access - 
	   on which 802.1X-unaware clients are placed after a network administrator-defined 
	   timeout. The switch follows a set of rules for entering and leaving the Guest 
	   VLAN as listed below.When enable, the individual ports' ditto setting determines 
	   whether the port can be moved into Guest VLAN. When disable, the ability to 
	   move to the Guest VLAN is disabled on all ports. "
   ::= { gs2326NASConfiguration 9 } 
   
gs2326NASConfigGuestVLANID OBJECT-TYPE
   SYNTAX      Integer32(1..4094)
   MAX-ACCESS  read-write
   STATUS      current
   DESCRIPTION
       "This is the value that a port's Port VLAN ID is set to if a port is moved into 
	   the Guest VLAN. It is only changeable if the Guest VLAN option is globally enabled.
	   range: 1 - 4094."
   ::= { gs2326NASConfiguration 10 }

gs2326NASConfigMaxReauthCount OBJECT-TYPE
   SYNTAX      Integer32(1..255)
   MAX-ACCESS  read-write
   STATUS      current
   DESCRIPTION
       "The number of times the switch transmits an EAPOL Request Identity frame without 
	   response before considering entering the Guest VLAN is adjusted with this setting. 
	   The value can only be changed if the Guest VLAN option is globally enabled.
	   range: 1 - 255."
   ::= { gs2326NASConfiguration 11 }

gs2326NASConfigAllowGuestVLANEAPOLSeen OBJECT-TYPE
   SYNTAX      INTEGER { disable(0), enable(1) }
   MAX-ACCESS  read-write
   STATUS      current
   DESCRIPTION
       "The switch remembers if an EAPOL frame has been received on the port for the 
	   life-time of the port. Once the switch considers whether to enter the Guest VLAN, 
	   it will first check if this option is enabled or disabled. If disabled, the switch 
	   will only enter the Guest VLAN if an EAPOL frame has not been received on the port 
	   for the life-time of the port. If enabled (checked), the switch will consider 
	   entering the Guest VLAN even if an EAPOL frame has been received on the port for 
	   the life-time of the port.The value can only be changed if the Guest VLAN option 
	   is globally enabled."
   ::= { gs2326NASConfiguration 12 }

gs2326NASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2326NASConfiguration 101 }

gs2326NASPortConfigTable OBJECT-TYPE
   SYNTAX      SEQUENCE OF Gs2326NASPortConfigEntry
   MAX-ACCESS  not-accessible
   STATUS      current
   DESCRIPTION
       ""
   ::= { gs2326NASConfiguration 13 }

gs2326NASPortConfigEntry OBJECT-TYPE
   SYNTAX      Gs2326NASPortConfigEntry
   MAX-ACCESS  not-accessible
   STATUS      current
   DESCRIPTION
       ""
   INDEX    { gs2326NASPortConfigPort }
   ::= { gs2326NASPortConfigTable 1 }

Gs2326NASPortConfigEntry ::= SEQUENCE {
   gs2326NASPortConfigPort                       Integer32,
   gs2326NASPortConfigAdminState                 INTEGER,
   gs2326NASPortConfigRADIUSAssignedQoSEnabled	  INTEGER,
   gs2326NASPortConfigRADIUSAssignedVLANEnabled  INTEGER,
   gs2326NASPortConfigGuestVLANEnabled           INTEGER,   
   gs2326NASPortConfigFallbackEnabled            INTEGER,   
   gs2326NASPortConfigPortState                  DisplayString,
   gs2326NASPortConfigReauthenticate             INTEGER,
   gs2326NASPortConfigReinitialize               INTEGER
}
  
gs2326NASPortConfigPort OBJECT-TYPE
   SYNTAX      Integer32(1..255)
   MAX-ACCESS  not-accessible
   STATUS      current
   DESCRIPTION
       " port, range : 1 - port number. "
   ::= { gs2326NASPortConfigEntry 1 }   
   
gs2326NASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2326NASPortConfigEntry 2 }   
   
gs2326NASPortConfigRADIUSAssignedQoSEnabled OBJECT-TYPE
   SYNTAX      INTEGER { disable(0), enable(1) }
   MAX-ACCESS  read-write
   STATUS      current
   DESCRIPTION
       "When RADIUS-Assigned QoS is both globally enabled and enabled (checked) 
	    on a given port, the switch reacts to QoS Class information carried in 
		the RADIUS Access-Accept packet transmitted by the RADIUS server when a 
		supplicant is successfully authenticated. If present and valid, traffic 
		received on the supplicant's port will be classified to the given QoS Class.
		Admin State supported : Port-based and Single 802.1X and MAC-based Single Auth."
   ::= { gs2326NASPortConfigEntry 3 }    
   
gs2326NASPortConfigRADIUSAssignedVLANEnabled OBJECT-TYPE
   SYNTAX      INTEGER { disable(0), enable(1) }
   MAX-ACCESS  read-write
   STATUS      current
   DESCRIPTION
       "When RADIUS-Assigned VLAN is both globally enabled and enabled (checked) 
	   for a given port, the switch reacts to VLAN ID information carried in the 
	   RADIUS Access-Accept packet transmitted by the RADIUS server when a supplicant 
	   is successfully authenticated. If present and valid, the port's Port VLAN ID 
	   will be changed to this VLAN ID, the port will be set to be a member of that 
	   VLAN ID, and the port will be forced into VLAN unaware mode. Once assigned, 
	   all traffic arriving on the port will be classified and switched on the 
	   RADIUS-assigned VLAN ID.
	   Admin State supported : Port-based and Single 802.1X and MAC-based Single Auth."
   ::= { gs2326NASPortConfigEntry 4 }    
   
gs2326NASPortConfigGuestVLANEnabled OBJECT-TYPE
   SYNTAX      INTEGER { disable(0), enable(1) }
   MAX-ACCESS  read-write
   STATUS      current
   DESCRIPTION
       "When Guest VLAN is both globally enabled and enabled (checked) for a given port, 
	   the switch considers moving the port into the Guest VLAN according to the rules
	   outlined below.
	   Admin State supported : Port-based , Single and Multi 802.1X."
   ::= { gs2326NASPortConfigEntry 5 }    
   
gs2326NASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode 
		and the supplicant is authorized.
		Unauthorized: The port is in Force Unauthorized or a single-supplicant 
		mode and the supplicant is not successfully authorized by the RADIUS server.
		X Auth/Y Unauth: The port is in a multi-supplicant mode. Currently X clients 
		are authorized and Y are unauthorized."
   ::= { gs2326NASPortConfigEntry 6 }    
   
gs2326NASPortConfigReauthenticate OBJECT-TYPE
   SYNTAX      INTEGER { doNothing(0), do(1) }
   MAX-ACCESS  read-write
   STATUS      current
   DESCRIPTION
       "Schedules a reauthentication whenever the quiet-period of the port runs out 
	   (EAPOL-based authentication). For MAC-based authentication, reauthentication 
	   will be attempted immediately.The button only has effect for successfully 
	   authenticated clients on the port and will not cause the clients to get 
	   temporarily unauthorized."
   ::= { gs2326NASPortConfigEntry 7 }    

gs2326NASPortConfigReinitialize OBJECT-TYPE
   SYNTAX      INTEGER { doNothing(0), do(1) }
   MAX-ACCESS  read-write
   STATUS      current
   DESCRIPTION
       "Forces a reinitialization of the clients on the port and thereby a reauthentication 
	   immediately. The clients will transfer to the unauthorized state while the 
	   reauthentication is in progress."
   ::= { gs2326NASPortConfigEntry 8 }    

gs2326NASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2326NASPortConfigEntry 101 }

gs2326NASSwitchStatusTable OBJECT-TYPE
   SYNTAX      SEQUENCE OF Gs2326NASSwitchStatusEntry
   MAX-ACCESS  not-accessible
   STATUS      current
   DESCRIPTION
       ""
   ::= { gs2326NAS 2 }

gs2326NASSwitchStatusEntry OBJECT-TYPE
   SYNTAX      Gs2326NASSwitchStatusEntry
   MAX-ACCESS  not-accessible
   STATUS      current
   DESCRIPTION
       ""
   INDEX    { gs2326NASPortConfigPort }
   ::= { gs2326NASSwitchStatusTable 1 }

Gs2326NASSwitchStatusEntry ::= SEQUENCE {
   gs2326NASSwitchStatusAdminState 	DisplayString,
   gs2326NASSwitchStatusPortState		DisplayString,
   gs2326NASSwitchStatusLastSource		DisplayString,
   gs2326NASSwitchStatusLastID			DisplayString,
   gs2326NASSwitchStatusQoSClass		DisplayString,
   gs2326NASSwitchStatusPortVlanID		DisplayString
}
   
gs2326NASSwitchStatusAdminState OBJECT-TYPE
   SYNTAX      DisplayString
   MAX-ACCESS  read-only
   STATUS      current
   DESCRIPTION
       "The port's current administrative state. Refer to NAS Admin State for a description of possible values."
   ::= { gs2326NASSwitchStatusEntry 2 }   
   
gs2326NASSwitchStatusPortState OBJECT-TYPE
   SYNTAX      DisplayString
   MAX-ACCESS  read-only
   STATUS      current
   DESCRIPTION
       "The current state of the port. Refer to NAS Port State for a description of the individual states."
   ::= { gs2326NASSwitchStatusEntry 3 }      
   
gs2326NASSwitchStatusLastSource OBJECT-TYPE
   SYNTAX      DisplayString
   MAX-ACCESS  read-only
   STATUS      current
   DESCRIPTION
       "The source MAC address carried in the most recently received EAPOL frame for EAPOL-based authentication, 
	   and the most recently received frame from a new client for MAC-based authentication."
   ::= { gs2326NASSwitchStatusEntry 4 }      

gs2326NASSwitchStatusLastID OBJECT-TYPE
   SYNTAX      DisplayString
   MAX-ACCESS  read-only
   STATUS      current
   DESCRIPTION
       "The user name (supplicant identity) carried in the most recently received Response Identity EAPOL frame 
	   for EAPOL-based authentication, and the source MAC address from the most recently received frame from a 
	   new client for MAC-based authentication."
   ::= { gs2326NASSwitchStatusEntry 5 }      

gs2326NASSwitchStatusQoSClass OBJECT-TYPE
   SYNTAX      DisplayString
   MAX-ACCESS  read-only
   STATUS      current
   DESCRIPTION
       "QoS Class assigned to the port by the RADIUS server if enabled."
   ::= { gs2326NASSwitchStatusEntry 6 } 
   
gs2326NASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2326NASSwitchStatusEntry 7 } 

gs2326NASPortStatus                                 OBJECT IDENTIFIER ::= { gs2326NAS 3 }
   
gs2326NASPortStatusCountersTable OBJECT-TYPE
   SYNTAX      SEQUENCE OF Gs2326NASPortStatusCountersEntry
   MAX-ACCESS  not-accessible
   STATUS      current
   DESCRIPTION
       ""
   ::= { gs2326NASPortStatus 1 }

gs2326NASPortStatusCountersEntry OBJECT-TYPE
   SYNTAX      Gs2326NASPortStatusCountersEntry
   MAX-ACCESS  not-accessible
   STATUS      current
   DESCRIPTION
       ""
   INDEX    { gs2326NASPortConfigPort }
   ::= { gs2326NASPortStatusCountersTable 1 }

Gs2326NASPortStatusCountersEntry ::= SEQUENCE {
   gs2326NASRxCountersEAPOLTotal  	                  Counter32,
   gs2326NASRxCountersEAPOLResponseID	              Counter32,
   gs2326NASRxCountersEAPOLResponses	              Counter32,
   gs2326NASRxCountersEAPOLStart	                  Counter32,
   gs2326NASRxCountersEAPOLLogoff                    Counter32,
   gs2326NASRxCountersEAPOLInvalidType               Counter32,
   gs2326NASRxCountersEAPOLInvalidLength             Counter32,
   gs2326NASTxCountersEAPOLTotal                     Counter32,
   gs2326NASTxCountersEAPOLRequestID                 Counter32,
   gs2326NASTxCountersEAPOLRequests                  Counter32,
   gs2326NASRxBackendServerCountersAccessChallenges  Counter32,
   gs2326NASRxBackendServerCountersOtherRequests     Counter32,
   gs2326NASRxBackendServerCountersAuthSuccesses     Counter32,
   gs2326NASRxBackendServerCountersAuthFailures      Counter32,
   gs2326NASTxBackendServerCountersResponses         Counter32,
   gs2326NASLastSupplicantInfoMACAddress             DisplayString,
   gs2326NASLastSupplicantInfoVlanID                 Integer32,
   gs2326NASLastSupplicantInfoVersion                Integer32,
   gs2326NASLastSupplicantInfoIdentity               DisplayString,
   gs2326NASCountersDoClear                          INTEGER
}

gs2326NASRxCountersEAPOLTotal OBJECT-TYPE
   SYNTAX      Counter32
   MAX-ACCESS  read-only
   STATUS      current
   DESCRIPTION
       "The number of valid EAPOL frames of any type that have been received by the switch."
   ::= { gs2326NASPortStatusCountersEntry 2 }   

gs2326NASRxCountersEAPOLResponseID OBJECT-TYPE
   SYNTAX      Counter32
   MAX-ACCESS  read-only
   STATUS      current
   DESCRIPTION
       "The number of valid EAPOL Response Identity frames that have been received by the switch."
   ::= { gs2326NASPortStatusCountersEntry 3 }   

gs2326NASRxCountersEAPOLResponses OBJECT-TYPE
   SYNTAX      Counter32
   MAX-ACCESS  read-only
   STATUS      current
   DESCRIPTION
       "The number of valid EAPOL response frames (other than Response Identity frames) 
	   that have been received by the switch."
   ::= { gs2326NASPortStatusCountersEntry 4 }   

gs2326NASRxCountersEAPOLStart OBJECT-TYPE
   SYNTAX      Counter32
   MAX-ACCESS  read-only
   STATUS      current
   DESCRIPTION
       "The number of EAPOL Start frames that have been received by the switch."
   ::= { gs2326NASPortStatusCountersEntry 5 }   

gs2326NASRxCountersEAPOLLogoff OBJECT-TYPE
   SYNTAX      Counter32
   MAX-ACCESS  read-only
   STATUS      current
   DESCRIPTION
       "The number of valid EAPOL Logoff frames that have been received by the switch."
   ::= { gs2326NASPortStatusCountersEntry 6 }   

gs2326NASRxCountersEAPOLInvalidType OBJECT-TYPE
   SYNTAX      Counter32
   MAX-ACCESS  read-only
   STATUS      current
   DESCRIPTION
       "The number of EAPOL frames that have been received by the switch in which 
	   the frame type is not recognized."
   ::= { gs2326NASPortStatusCountersEntry 7 }   
   
gs2326NASRxCountersEAPOLInvalidLength OBJECT-TYPE
   SYNTAX      Counter32
   MAX-ACCESS  read-only
   STATUS      current
   DESCRIPTION
       "The number of EAPOL frames that have been received by the switch in which the 
	   Packet Body Length field is invalid."
   ::= { gs2326NASPortStatusCountersEntry 8 }   
   
gs2326NASTxCountersEAPOLTotal OBJECT-TYPE
   SYNTAX      Counter32
   MAX-ACCESS  read-only
   STATUS      current
   DESCRIPTION
       "The number of EAPOL frames of any type that have been transmitted by the switch."
   ::= { gs2326NASPortStatusCountersEntry 9 }   
   
gs2326NASTxCountersEAPOLRequestID OBJECT-TYPE
   SYNTAX      Counter32
   MAX-ACCESS  read-only
   STATUS      current
   DESCRIPTION
       "The number of EAPOL Request Identity frames that have been transmitted by the switch."
   ::= { gs2326NASPortStatusCountersEntry 10 }      

gs2326NASTxCountersEAPOLRequests OBJECT-TYPE
   SYNTAX      Counter32
   MAX-ACCESS  read-only
   STATUS      current
   DESCRIPTION
       "The number of valid EAPOL Request frames (other than Request Identity frames) 
	   that have been transmitted by the switch."
   ::= { gs2326NASPortStatusCountersEntry 11 }      
   
gs2326NASRxBackendServerCountersAccessChallenges OBJECT-TYPE
   SYNTAX      Counter32
   MAX-ACCESS  read-only
   STATUS      current
   DESCRIPTION
       "802.1X-based: Counts the number of times that the switch receives the first request 
	   from the backend server following the first response from the supplicant.
	   MAC-based: Counts all Access Challenges received from the backend server for this 
	   port or client."
   ::= { gs2326NASPortStatusCountersEntry 12 }      

gs2326NASRxBackendServerCountersOtherRequests OBJECT-TYPE
   SYNTAX      Counter32
   MAX-ACCESS  read-only
   STATUS      current
   DESCRIPTION
       "802.1X-based: Counts the number of times that the switch sends an EAP Request 
	   packet following the first to the supplicant.
	   MAC-based: Not applicable."
   ::= { gs2326NASPortStatusCountersEntry 13 }      
   
gs2326NASRxBackendServerCountersAuthSuccesses OBJECT-TYPE
   SYNTAX      Counter32
   MAX-ACCESS  read-only
   STATUS      current
   DESCRIPTION
       "Counts the number of times that the switch receives a success indication. 
	   Indicates that the supplicant/client has successfully authenticated to the 
	   backend server."
   ::= { gs2326NASPortStatusCountersEntry 14 }      
   
gs2326NASRxBackendServerCountersAuthFailures OBJECT-TYPE
   SYNTAX      Counter32
   MAX-ACCESS  read-only
   STATUS      current
   DESCRIPTION
       "Counts the number of times that the switch receives a failure message. 
	   This indicates that the supplicant/client has not authenticated to the 
	   backend server. "
   ::= { gs2326NASPortStatusCountersEntry 15 }      
   
gs2326NASTxBackendServerCountersResponses OBJECT-TYPE
   SYNTAX      Counter32
   MAX-ACCESS  read-only
   STATUS      current
   DESCRIPTION
       "802.1X-based: Counts the number of times that the switch attempts to 
	   send a supplicant's first response packet to the backend server. Indicates 
	   the switch attempted communication with the backend server. Possible 
	   retransmissions are not counted. 
	   MAC-based: Counts all the backend server packets sent from the switch 
	   towards the backend server for a given port or client. Possible 
	   retransmissions are not counted."
   ::= { gs2326NASPortStatusCountersEntry 16 }  

gs2326NASLastSupplicantInfoMACAddress OBJECT-TYPE
   SYNTAX      DisplayString
   MAX-ACCESS  read-only
   STATUS      current
   DESCRIPTION
       "The MAC address of the last supplicant/client."
   ::= { gs2326NASPortStatusCountersEntry 17 }  

gs2326NASLastSupplicantInfoVlanID OBJECT-TYPE
   SYNTAX      Integer32
   MAX-ACCESS  read-only
   STATUS      current
   DESCRIPTION
       "The VLAN ID on which the last frame from the last supplicant/client was received."
   ::= { gs2326NASPortStatusCountersEntry 18 }  
   
gs2326NASLastSupplicantInfoVersion OBJECT-TYPE
   SYNTAX      Integer32
   MAX-ACCESS  read-only
   STATUS      current
   DESCRIPTION
       "802.1X-based: The protocol version number carried in the most recently 
	   received EAPOL frame. 
	   MAC-based: Not applicable."
   ::= { gs2326NASPortStatusCountersEntry 19 }  

gs2326NASLastSupplicantInfoIdentity OBJECT-TYPE
   SYNTAX      DisplayString
   MAX-ACCESS  read-only
   STATUS      current
   DESCRIPTION
       "802.1X-based: The user name (supplicant identity) carried in the most recently received 
	   Response Identity EAPOL frame. 
	   MAC-based: Not applicable."
   ::= { gs2326NASPortStatusCountersEntry 20 }  

gs2326NASCountersDoClear OBJECT-TYPE
   SYNTAX      INTEGER { doNothing(0), do(1) }
   MAX-ACCESS  read-write
   STATUS      current
   DESCRIPTION
       "Clear the counters for the selected port."
   ::= { gs2326NASPortStatusCountersEntry 21 }    

gs2326NASPortStatusClientsTable OBJECT-TYPE
   SYNTAX      SEQUENCE OF Gs2326NASPortStatusClientsEntry
   MAX-ACCESS  not-accessible
   STATUS      current
   DESCRIPTION
       ""
   ::= { gs2326NASPortStatus 2 }

gs2326NASPortStatusClientsEntry OBJECT-TYPE
   SYNTAX      Gs2326NASPortStatusClientsEntry
   MAX-ACCESS  not-accessible
   STATUS      current
   DESCRIPTION
       ""
   INDEX    { gs2326NASPortConfigPort,
		gs2326NASClientsIndex}
   ::= { gs2326NASPortStatusClientsTable 1 }

Gs2326NASPortStatusClientsEntry ::= SEQUENCE {
   gs2326NASClientsIndex  	                  		    Integer32,
   gs2326NASClientsIdentity							DisplayString,
   gs2326NASClientsMACAddress  	                  	DisplayString,
   gs2326NASClientsVlanID		              			Integer32,
   gs2326NASClientsState	              				DisplayString,
   gs2326NASClientsLastAuth	                  		DisplayString,
   gs2326NASRxClientsEAPOLTotal  	                  	Counter32,
   gs2326NASRxClientsEAPOLResponseID	              	Counter32,
   gs2326NASRxClientsEAPOLResponses	              	Counter32,
   gs2326NASRxClientsEAPOLStart	                  	Counter32,
   gs2326NASRxClientsEAPOLLogoff                    	Counter32,
   gs2326NASRxClientsEAPOLInvalidType               	Counter32,
   gs2326NASRxClientsEAPOLInvalidLength             	Counter32,
   gs2326NASTxClientsEAPOLTotal                     	Counter32,
   gs2326NASTxClientsEAPOLRequestID                 	Counter32,
   gs2326NASTxClientsEAPOLRequests                  	Counter32,
   gs2326NASRxBackendServerClientsAccessChallenges  	Counter32,
   gs2326NASRxBackendServerClientsOtherRequests     	Counter32,
   gs2326NASRxBackendServerClientsAuthSuccesses     	Counter32,
   gs2326NASRxBackendServerClientsAuthFailures      	Counter32,
   gs2326NASTxBackendServerClientsResponses         	Counter32
}

gs2326NASClientsIndex OBJECT-TYPE
   SYNTAX      Integer32(1..255)
   MAX-ACCESS  not-accessible
   STATUS      current
   DESCRIPTION
       "Entry of client table in the port."
   ::= { gs2326NASPortStatusClientsEntry 1 } 
   
gs2326NASClientsIdentity OBJECT-TYPE
   SYNTAX      DisplayString
   MAX-ACCESS  read-only
   STATUS      current
   DESCRIPTION
       "Shows the identity of the supplicant, as received in the Response Identity 
	   EAPOL frame.This isn't available for MAC-based Auth."
   ::= { gs2326NASPortStatusClientsEntry 2 }
   
gs2326NASClientsMACAddress OBJECT-TYPE
   SYNTAX      DisplayString
   MAX-ACCESS  read-only
   STATUS      current
   DESCRIPTION
       "Multi 802.1X, this column holds the MAC address of the attached supplicant. 
	   MAC-based Auth., this column holds the MAC address of the attached client."
   ::= { gs2326NASPortStatusClientsEntry 3 }  

gs2326NASClientsVlanID OBJECT-TYPE
   SYNTAX      Integer32(1..4095)
   MAX-ACCESS  read-only
   STATUS      current
   DESCRIPTION
       "This column holds the VLAN ID that the corresponding client is currently 
	   secured through the Port Security module."
   ::= { gs2326NASPortStatusClientsEntry 4 }  
   
gs2326NASClientsState OBJECT-TYPE
   SYNTAX      DisplayString
   MAX-ACCESS  read-only
   STATUS      current
   DESCRIPTION
       "The client can either be authenticated or unauthenticated. In the authenticated 
	   state, it is allowed to forward frames on the port, and in the unauthenticated 
	   state, it is blocked."
   ::= { gs2326NASPortStatusClientsEntry 5 }  

gs2326NASClientsLastAuth OBJECT-TYPE
   SYNTAX      DisplayString
   MAX-ACCESS  read-only
   STATUS      current
   DESCRIPTION
       "Shows the date and time of the last authentication of the client."
   ::= { gs2326NASPortStatusClientsEntry 6 }  
   
gs2326NASRxClientsEAPOLTotal OBJECT-TYPE
   SYNTAX      Counter32
   MAX-ACCESS  read-only
   STATUS      current
   DESCRIPTION
       "The number of valid EAPOL frames of any type that have been received by the switch."
   ::= { gs2326NASPortStatusClientsEntry 7 }  

gs2326NASRxClientsEAPOLResponseID OBJECT-TYPE
   SYNTAX      Counter32
   MAX-ACCESS  read-only
   STATUS      current
   DESCRIPTION
       "The number of valid EAPOL Response Identity frames that have been received by the switch."
   ::= { gs2326NASPortStatusClientsEntry 8 }   

gs2326NASRxClientsEAPOLResponses OBJECT-TYPE
   SYNTAX      Counter32
   MAX-ACCESS  read-only
   STATUS      current
   DESCRIPTION
       "The number of valid EAPOL response frames (other than Response Identity frames) 
	   that have been received by the switch."
   ::= { gs2326NASPortStatusClientsEntry 9 }   

gs2326NASRxClientsEAPOLStart OBJECT-TYPE
   SYNTAX      Counter32
   MAX-ACCESS  read-only
   STATUS      current
   DESCRIPTION
       "The number of EAPOL Start frames that have been received by the switch."
   ::= { gs2326NASPortStatusClientsEntry 10 }   

gs2326NASRxClientsEAPOLLogoff OBJECT-TYPE
   SYNTAX      Counter32
   MAX-ACCESS  read-only
   STATUS      current
   DESCRIPTION
       "The number of valid EAPOL Logoff frames that have been received by the switch."
   ::= { gs2326NASPortStatusClientsEntry 11 }   

gs2326NASRxClientsEAPOLInvalidType OBJECT-TYPE
   SYNTAX      Counter32
   MAX-ACCESS  read-only
   STATUS      current
   DESCRIPTION
       "The number of EAPOL frames that have been received by the switch in which 
	   the frame type is not recognized."
   ::= { gs2326NASPortStatusClientsEntry 12 }   
   
gs2326NASRxClientsEAPOLInvalidLength OBJECT-TYPE
   SYNTAX      Counter32
   MAX-ACCESS  read-only
   STATUS      current
   DESCRIPTION
       "The number of EAPOL frames that have been received by the switch in which the 
	   Packet Body Length field is invalid."
   ::= { gs2326NASPortStatusClientsEntry 13 }

gs2326NASTxClientsEAPOLTotal OBJECT-TYPE
   SYNTAX      Counter32
   MAX-ACCESS  read-only
   STATUS      current
   DESCRIPTION
       "The number of EAPOL frames of any type that have been transmitted by the switch."
   ::= { gs2326NASPortStatusClientsEntry 14 }   
   
gs2326NASTxClientsEAPOLRequestID OBJECT-TYPE
   SYNTAX      Counter32
   MAX-ACCESS  read-only
   STATUS      current
   DESCRIPTION
       "The number of EAPOL Request Identity frames that have been transmitted by the switch."
   ::= { gs2326NASPortStatusClientsEntry 15 }      

gs2326NASTxClientsEAPOLRequests OBJECT-TYPE
   SYNTAX      Counter32
   MAX-ACCESS  read-only
   STATUS      current
   DESCRIPTION
       "The number of valid EAPOL Request frames (other than Request Identity frames) 
	   that have been transmitted by the switch."
   ::= { gs2326NASPortStatusClientsEntry 16 }        

gs2326NASRxBackendServerClientsAccessChallenges OBJECT-TYPE
   SYNTAX      Counter32
   MAX-ACCESS  read-only
   STATUS      current
   DESCRIPTION
       "802.1X-based: Counts the number of times that the switch receives the first request 
	   from the backend server following the first response from the supplicant.
	   MAC-based: Counts all Access Challenges received from the backend server for this 
	   port or client."
   ::= { gs2326NASPortStatusClientsEntry 17 }      

gs2326NASRxBackendServerClientsOtherRequests OBJECT-TYPE
   SYNTAX      Counter32
   MAX-ACCESS  read-only
   STATUS      current
   DESCRIPTION
       "802.1X-based: Counts the number of times that the switch sends an EAP Request 
	   packet following the first to the supplicant.
	   MAC-based: Not applicable."
   ::= { gs2326NASPortStatusClientsEntry 18 }      
   
gs2326NASRxBackendServerClientsAuthSuccesses OBJECT-TYPE
   SYNTAX      Counter32
   MAX-ACCESS  read-only
   STATUS      current
   DESCRIPTION
       "Counts the number of times that the switch receives a success indication. 
	   Indicates that the supplicant/client has successfully authenticated to the 
	   backend server."
   ::= { gs2326NASPortStatusClientsEntry 19 }      
   
gs2326NASRxBackendServerClientsAuthFailures OBJECT-TYPE
   SYNTAX      Counter32
   MAX-ACCESS  read-only
   STATUS      current
   DESCRIPTION
       "Counts the number of times that the switch receives a failure message. 
	   This indicates that the supplicant/client has not authenticated to the 
	   backend server. "
   ::= { gs2326NASPortStatusClientsEntry 20 }      
   
gs2326NASTxBackendServerClientsResponses OBJECT-TYPE
   SYNTAX      Counter32
   MAX-ACCESS  read-only
   STATUS      current
   DESCRIPTION
       "802.1X-based: Counts the number of times that the switch attempts to 
	   send a supplicant's first response packet to the backend server. Indicates 
	   the switch attempted communication with the backend server. Possible 
	   retransmissions are not counted. 
	   MAC-based: Counts all the backend server packets sent from the switch 
	   towards the backend server for a given port or client. Possible 
	   retransmissions are not counted."
   ::= { gs2326NASPortStatusClientsEntry 21 }  
   

gs2326Maintenance                                           OBJECT IDENTIFIER ::= { lancomGS2326  4 }

gs2326RestartDevice OBJECT-TYPE
   SYNTAX      INTEGER { disable(0), enable(1) }
   MAX-ACCESS  read-write
   STATUS      current
   DESCRIPTION
       "default: 0
        0:none
        1:yes"
   ::= { gs2326Maintenance 1 }

gs2326ColdRestartDevice OBJECT-TYPE
   SYNTAX      INTEGER { disable(0), enable(1) }
   MAX-ACCESS  read-write
   STATUS      current
   DESCRIPTION
       "default: 0
        0:none
        1:yes"
   ::= { gs2326Maintenance 1500 }

gs2326Firmware                                         OBJECT IDENTIFIER ::= { gs2326Maintenance 2 }

gs2326FirmwareIpAddress OBJECT-TYPE
   SYNTAX       IpAddress
   MAX-ACCESS   read-write
   STATUS       current
   DESCRIPTION
        "Get/Set the firmware tftp server."
   ::= { gs2326Firmware 1 }

gs2326FirmwareFileName OBJECT-TYPE
   SYNTAX       DisplayString
   MAX-ACCESS   read-write
   STATUS       current
   DESCRIPTION
        "Get/Set the path and filename for firmware upgrading."
   ::= { gs2326Firmware 2 }

gs2326DoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2326Firmware 3 }

gs2326SaveOrRestore                                         OBJECT IDENTIFIER ::= { gs2326Maintenance 3 }

gs2326FactoryDefaults OBJECT-TYPE
   SYNTAX      INTEGER { none(0), yes(1) }
   MAX-ACCESS  read-write
   STATUS      current
   DESCRIPTION
       "default: 0
        0:none
        1:yes"
   ::= { gs2326SaveOrRestore 1 }

gs2326SaveStart OBJECT-TYPE
   SYNTAX      INTEGER { none(0), yes(1) }
   MAX-ACCESS  read-write
   STATUS      current
   DESCRIPTION
       "default: 0
        0:none
        1:yes"
   ::= { gs2326SaveOrRestore 2 }

gs2326SaveUser OBJECT-TYPE
   SYNTAX      INTEGER { none(0), yes(1) }
   MAX-ACCESS  read-write
   STATUS      current
   DESCRIPTION
       "default: 0
        0:none
        1:yes"
   ::= { gs2326SaveOrRestore 3 }

gs2326RestoreUser OBJECT-TYPE
   SYNTAX      INTEGER { none(0), yes(1) }
   MAX-ACCESS  read-write
   STATUS      current
   DESCRIPTION
       "default: 0
        0:none
        1:yes"
   ::= { gs2326SaveOrRestore 4 }


gs2326ExportOrImport                                        OBJECT IDENTIFIER ::= { gs2326Maintenance 4 }

gs2326ExportIpAddress OBJECT-TYPE
   SYNTAX       IpAddress
   MAX-ACCESS   read-write
   STATUS       current
   DESCRIPTION
        "Get/Set the export tftp server."
   ::= { gs2326ExportOrImport 1 }

gs2326ExportConfigName OBJECT-TYPE
   SYNTAX       DisplayString
   MAX-ACCESS   read-write
   STATUS       current
   DESCRIPTION
       "Get/Set the export file path and name."
   ::= { gs2326ExportOrImport 2 }

gs2326DoExportConfig OBJECT-TYPE
   SYNTAX       INTEGER{ doNothing(0), do(1) }
   MAX-ACCESS   read-write
   STATUS       current
   DESCRIPTION
        "Do export-config.
         Get this OID always return zero.
         1 - export."
   ::= { gs2326ExportOrImport 3 }

gs2326ImportIpAddress OBJECT-TYPE
   SYNTAX       IpAddress
   MAX-ACCESS   read-write
   STATUS       current
   DESCRIPTION
        "Get/Set the import tftp server."
   ::= { gs2326ExportOrImport 4 }

gs2326ImportConfigName OBJECT-TYPE
   SYNTAX      DisplayString
   MAX-ACCESS  read-write
   STATUS      current
   DESCRIPTION
       "Get/Set the import file path and name."
   ::= { gs2326ExportOrImport 5 }

gs2326DoImportConfig OBJECT-TYPE
   SYNTAX       INTEGER{ doNothing(0), do(1) }
   MAX-ACCESS   read-write
   STATUS       current
   DESCRIPTION
        "Do export-config.
         Get this OID always return zero.
         1 - import."
   ::= { gs2326ExportOrImport 6 }

gs2326Diagnostics                                           OBJECT IDENTIFIER ::= { gs2326Maintenance 5 }

gs2326PingIpAddress OBJECT-TYPE
   SYNTAX      IpAddress
   MAX-ACCESS  read-write
   STATUS      current
   DESCRIPTION
       " The destination IP Address. "
   ::= { gs2326Diagnostics 1 }
   
gs2326PingSize OBJECT-TYPE
   SYNTAX      Integer32(60..1400)
   MAX-ACCESS  read-write
   STATUS      current
   DESCRIPTION
       " Size of ICMP echo packet.
         range : 60-1400, default : 64. "
   ::= { gs2326Diagnostics 2 }   

gs2326DoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2326Diagnostics 3 }

gs2326PingResult OBJECT-TYPE
   SYNTAX      DisplayString
   MAX-ACCESS  read-only
   STATUS      current
   DESCRIPTION
       " Show ping result. "
   ::= { gs2326Diagnostics 4 }

gs2326Ping6IpAddress OBJECT-TYPE
   SYNTAX      DisplayString
   MAX-ACCESS  read-write
   STATUS      current
   DESCRIPTION
       " The destination IPv6 Address. "
   ::= { gs2326Diagnostics 5 }
   
gs2326Ping6Size OBJECT-TYPE
   SYNTAX      Integer32(60..1400)
   MAX-ACCESS  read-write
   STATUS      current
   DESCRIPTION
       " Size of ICMP echo packet.
         range : 60-1400. "
   ::= { gs2326Diagnostics 6 }   

gs2326DoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2326Diagnostics 7 }

gs2326Ping6Result OBJECT-TYPE
   SYNTAX      DisplayString
   MAX-ACCESS  read-only
   STATUS      current
   DESCRIPTION
       " Show ping result. "
   ::= { gs2326Diagnostics 8 }


gs2326VeriPHY                                           OBJECT IDENTIFIER ::= { gs2326Diagnostics 9 }

gs2326VeriPHYTest OBJECT-TYPE
   SYNTAX      Integer32(1..4095)
   MAX-ACCESS  read-write
   STATUS      current
   DESCRIPTION
       "Run VeriPHY Cable Diagnostics.
        port, range : 0 - port number.
        0 : ALL "
   ::= { gs2326VeriPHY 1 }

gs2326VeriPHYTable OBJECT-TYPE
   SYNTAX      SEQUENCE OF GS2326VeriPHYEntry
   MAX-ACCESS  not-accessible
   STATUS      current
   DESCRIPTION
       " "
   ::= { gs2326VeriPHY 2 }

gs2326VeriPHYEntry OBJECT-TYPE
   SYNTAX      GS2326VeriPHYEntry
   MAX-ACCESS  not-accessible
   STATUS      current
   DESCRIPTION
       ""
   INDEX    { gs2326VeriPHYPort  }
   ::= { gs2326VeriPHYTable 1 }

GS2326VeriPHYEntry ::= SEQUENCE {
   gs2326VeriPHYPort        Integer32,
   gs2326VeriPHYPairA       DisplayString,
   gs2326VeriPHYLengthA     DisplayString,
   gs2326VeriPHYPairB       DisplayString,
   gs2326VeriPHYLengthB     DisplayString,
   gs2326VeriPHYPairC       DisplayString,
   gs2326VeriPHYLengthC     DisplayString,
   gs2326VeriPHYPairD       DisplayString,
   gs2326VeriPHYLengthD     DisplayString
}

gs2326VeriPHYPort OBJECT-TYPE
   SYNTAX      Integer32(1..4095)
   MAX-ACCESS  not-accessible
   STATUS      current
   DESCRIPTION
       " The length (in meters) of the cable pair. "
   ::= { gs2326VeriPHYEntry 1 }

gs2326VeriPHYPairA OBJECT-TYPE
   SYNTAX      DisplayString
   MAX-ACCESS  read-only
   STATUS      current
   DESCRIPTION
       " The status of the cable pair. "
   ::= { gs2326VeriPHYEntry 2 }

gs2326VeriPHYLengthA OBJECT-TYPE
   SYNTAX      DisplayString
   MAX-ACCESS  read-only
   STATUS      current
   DESCRIPTION
       " The length (in meters) of the cable pair. "
   ::= { gs2326VeriPHYEntry 3 }

gs2326VeriPHYPairB OBJECT-TYPE
   SYNTAX      DisplayString
   MAX-ACCESS  read-only
   STATUS      current
   DESCRIPTION
       " The status of the cable pair. "
   ::= { gs2326VeriPHYEntry 4 }

gs2326VeriPHYLengthB OBJECT-TYPE
   SYNTAX      DisplayString
   MAX-ACCESS  read-only
   STATUS      current
   DESCRIPTION
       " The length (in meters) of the cable pair. "
   ::= { gs2326VeriPHYEntry 5 }

gs2326VeriPHYPairC OBJECT-TYPE
   SYNTAX      DisplayString
   MAX-ACCESS  read-only
   STATUS      current
   DESCRIPTION
       " The status of the cable pair. "
   ::= { gs2326VeriPHYEntry 6 }

gs2326VeriPHYLengthC OBJECT-TYPE
   SYNTAX      DisplayString
   MAX-ACCESS  read-only
   STATUS      current
   DESCRIPTION
       " The length (in meters) of the cable pair. "
   ::= { gs2326VeriPHYEntry 7 }

gs2326VeriPHYPairD OBJECT-TYPE
   SYNTAX      DisplayString
   MAX-ACCESS  read-only
   STATUS      current
   DESCRIPTION
       " The status of the cable pair. "
   ::= { gs2326VeriPHYEntry 8 }

gs2326VeriPHYLengthD OBJECT-TYPE
   SYNTAX      DisplayString
   MAX-ACCESS  read-only
   STATUS      current
   DESCRIPTION
       " The length (in meters) of the cable pair. "
   ::= { gs2326VeriPHYEntry 9 }


------------------------------------------------------------------------------------------------------------------
gs2326Trap                                                  OBJECT IDENTIFIER ::= { lancomGS2326  5 }

gs2326TrapEvent                                             OBJECT IDENTIFIER ::= { gs2326Trap 1 }

gs2326Emergency NOTIFICATION-TYPE
  OBJECTS   { gs2326Information }
  STATUS        current
    DESCRIPTION
        "The severity level is Emergency. The system is unusable."
    ::= { gs2326TrapEvent 1 }

gs2326Alert NOTIFICATION-TYPE
  OBJECTS   { gs2326Information }
  STATUS        current
    DESCRIPTION
        "The severity level is Alert. The action must be taken immediately."
    ::= { gs2326TrapEvent 2 }

gs2326Critical NOTIFICATION-TYPE
  OBJECTS   { gs2326Information }
  STATUS        current
    DESCRIPTION
        "The severity level is Critical. Critical conditions."
    ::= { gs2326TrapEvent 3 }

gs2326Error NOTIFICATION-TYPE
  OBJECTS   { gs2326Information }
  STATUS        current
    DESCRIPTION
        "The severity level is Error. Error conditions."
    ::= { gs2326TrapEvent 4 }

gs2326Warning NOTIFICATION-TYPE
  OBJECTS   { gs2326Information }
  STATUS        current
    DESCRIPTION
        "The severity level is Warning. Warning conditions."
    ::= { gs2326TrapEvent 5 }

gs2326Notice NOTIFICATION-TYPE
  OBJECTS   { gs2326Information }
  STATUS        current
    DESCRIPTION
        "The severity level is Notice. Normal but significant condition."
    ::= { gs2326TrapEvent 6 }

gs2326Informational NOTIFICATION-TYPE
  OBJECTS   { gs2326Information }
  STATUS        current
    DESCRIPTION
        "The severity level is Informational. Informational messages."
    ::= { gs2326TrapEvent 7 }

gs2326Debug NOTIFICATION-TYPE
  OBJECTS   { gs2326Information }
  STATUS        current
    DESCRIPTION
        "The severity level is Debug. debug-level messages."
    ::= { gs2326TrapEvent 8 }

gs2326TrapVariable                                          OBJECT IDENTIFIER ::= { gs2326Trap 2 }

gs2326Information OBJECT-TYPE
    SYNTAX      DisplayString
    MAX-ACCESS  read-only
    STATUS      current
    DESCRIPTION
        "Trap information."
    ::= { gs2326TrapVariable 1 }


END

LANCOM-GS-2328-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2328                                                OBJECT IDENTIFIER ::= { gigabitEthernetSwitches 2330 }

gs2328System                                                OBJECT IDENTIFIER ::= { lancomGS2328  1 }

gs2328SystemInformation                                     OBJECT IDENTIFIER ::= { gs2328System 1 }

gs2328ModelName OBJECT-TYPE
   SYNTAX       DisplayString
   MAX-ACCESS   read-only
   STATUS       current
   DESCRIPTION
       ""
 ::= { gs2328SystemInformation 1 }

gs2328BIOSVersion OBJECT-TYPE
   SYNTAX       DisplayString
   MAX-ACCESS   read-only
   STATUS       current
   DESCRIPTION
       ""
   ::= { gs2328SystemInformation 2 }

gs2328FirmwareVersion OBJECT-TYPE
   SYNTAX       DisplayString
   MAX-ACCESS   read-only
   STATUS       current
   DESCRIPTION
       ""
   ::= { gs2328SystemInformation 3 }

gs2328HardwareMechanicalVersion OBJECT-TYPE
   SYNTAX       DisplayString
   MAX-ACCESS   read-only
   STATUS       current
   DESCRIPTION
       ""
   ::= { gs2328SystemInformation 4 }

gs2328SerialNumber OBJECT-TYPE
   SYNTAX       DisplayString
   MAX-ACCESS   read-only
   STATUS       current
   DESCRIPTION
       ""
   ::= { gs2328SystemInformation 5 }

gs2328HostMACAddress OBJECT-TYPE
   SYNTAX       MacAddress
   MAX-ACCESS   read-only
   STATUS       current
   DESCRIPTION
       ""
   ::= { gs2328SystemInformation 6 }

gs2328ConsoleBaudrate OBJECT-TYPE
   SYNTAX       DisplayString
   MAX-ACCESS   read-only
   STATUS       current
   DESCRIPTION
       ""
   ::= { gs2328SystemInformation 7 }

gs2328RAMSize OBJECT-TYPE
   SYNTAX       DisplayString
   MAX-ACCESS   read-only
   STATUS       current
   DESCRIPTION
       ""
   ::= { gs2328SystemInformation 8 }

gs2328FlashSize OBJECT-TYPE
   SYNTAX       DisplayString
   MAX-ACCESS   read-only
   STATUS       current
   DESCRIPTION
       ""
   ::= { gs2328SystemInformation 9 }

gs2328BridgeFDBSize OBJECT-TYPE
   SYNTAX       DisplayString
   MAX-ACCESS   read-only
   STATUS       current
   DESCRIPTION
       ""
   ::= { gs2328SystemInformation 10 }

gs2328TransmitQueue OBJECT-TYPE
   SYNTAX       DisplayString
   MAX-ACCESS   read-only
   STATUS       current
   DESCRIPTION
       ""
   ::= { gs2328SystemInformation 11 }

gs2328MaximumFrameSize OBJECT-TYPE
   SYNTAX       DisplayString
   MAX-ACCESS   read-only
   STATUS       current
   DESCRIPTION
       ""
   ::= { gs2328SystemInformation 12 }

gs2328CPULoad OBJECT-TYPE
   SYNTAX       DisplayString
   MAX-ACCESS   read-only
   STATUS       current
   DESCRIPTION
       ""
   ::= { gs2328SystemInformation 13 }

gs2328FanSpeed OBJECT-TYPE
   SYNTAX       DisplayString
   MAX-ACCESS   read-only
   STATUS       current
   DESCRIPTION
       ""
   ::= { gs2328SystemInformation 17 }
   
gs2328Temperature OBJECT-TYPE
   SYNTAX       DisplayString
   MAX-ACCESS   read-only
   STATUS       current
   DESCRIPTION
       ""
   ::= { gs2328SystemInformation 19 }

gs2328SystemDescription OBJECT-TYPE
   SYNTAX       DisplayString
   MAX-ACCESS   read-only
   STATUS       current
   DESCRIPTION
       ""
   ::= { gs2328SystemInformation 21 }
   
gs2328Location OBJECT-TYPE
   SYNTAX       DisplayString
   MAX-ACCESS   read-only
   STATUS       current
   DESCRIPTION
       ""
   ::= { gs2328SystemInformation 22 }
   
gs2328Contact OBJECT-TYPE
   SYNTAX       DisplayString
   MAX-ACCESS   read-only
   STATUS       current
   DESCRIPTION
       ""
   ::= { gs2328SystemInformation 23 }
   
gs2328DeviceName OBJECT-TYPE
   SYNTAX       DisplayString
   MAX-ACCESS   read-only
   STATUS       current
   DESCRIPTION
       ""
   ::= { gs2328SystemInformation 24 }
   
gs2328SystemDate OBJECT-TYPE
   SYNTAX       DisplayString
   MAX-ACCESS   read-only
   STATUS       current
   DESCRIPTION
       ""
   ::= { gs2328SystemInformation 25 }
   
gs2328SystemUptime OBJECT-TYPE
   SYNTAX       DisplayString
   MAX-ACCESS   read-only
   STATUS       current
   DESCRIPTION
       ""
   ::= { gs2328SystemInformation 26 }
   
gs2328SystemIPv4Address OBJECT-TYPE
   SYNTAX       DisplayString
   MAX-ACCESS   read-only
   STATUS       current
   DESCRIPTION
       ""
   ::= { gs2328SystemInformation 27 }

gs2328SystemIPv4SubnetMask OBJECT-TYPE
   SYNTAX       DisplayString
   MAX-ACCESS   read-only
   STATUS       current
   DESCRIPTION
       ""
   ::= { gs2328SystemInformation 28 }
   
gs2328SystemIPv4Gateway OBJECT-TYPE
   SYNTAX       DisplayString
   MAX-ACCESS   read-only
   STATUS       current
   DESCRIPTION
       ""
   ::= { gs2328SystemInformation 29 }

gs2328IPv6LinkLocalAddress OBJECT-TYPE
   SYNTAX       DisplayString
   MAX-ACCESS   read-only
   STATUS       current
   DESCRIPTION
       ""
   ::= { gs2328SystemInformation 30 }

gs2328IPv6Address OBJECT-TYPE
   SYNTAX       DisplayString
   MAX-ACCESS   read-only
   STATUS       current
   DESCRIPTION
       ""
   ::= { gs2328SystemInformation 31 }

gs2328IPv6Prefix OBJECT-TYPE
   SYNTAX       DisplayString
   MAX-ACCESS   read-only
   STATUS       current
   DESCRIPTION
       ""
   ::= { gs2328SystemInformation 32 }
   
gs2328IPv6Gateway OBJECT-TYPE
   SYNTAX       DisplayString
   MAX-ACCESS   read-only
   STATUS       current
   DESCRIPTION
       ""
   ::= { gs2328SystemInformation 33 }
   
gs2328LargestFreeMemBlock OBJECT-TYPE
   SYNTAX       Integer32
   MAX-ACCESS   read-only
   STATUS       current
   DESCRIPTION
       "Largest free memory block in Kb"
   ::= { gs2328SystemInformation 1500 }   
   
gs2328MemFree  OBJECT-TYPE
   SYNTAX       Integer32
   MAX-ACCESS   read-only
   STATUS       current
   DESCRIPTION
       "Free memory in Kb"
   ::= { gs2328SystemInformation 1501 }

gs2328SystemTime                                            OBJECT IDENTIFIER ::= { gs2328System 2 }

gs2328SystemTimeManual                                      OBJECT IDENTIFIER ::= { gs2328SystemTime 1 }

gs2328SystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2328SystemTimeManual 1 }
   
gs2328SystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2328SystemTimeManual 2 }

gs2328SystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2328SystemTimeManual 3 }
   
gs2328SystemTimeManualDaylightSavings OBJECT-TYPE
   SYNTAX       INTEGER { disable(0), enable(1) }
   MAX-ACCESS   read-write
   STATUS       current
   DESCRIPTION
       "default: 0,
        0 : Disable,
        1 : Enable."
   ::= { gs2328SystemTimeManual 4 }
   
gs2328SystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2328SystemTimeManual 5 }
   
gs2328SystemTimeManualDaylightSavingsType OBJECT-TYPE
   SYNTAX       INTEGER { byDates(0), recurring(1) }
   MAX-ACCESS   read-write
   STATUS       current
   DESCRIPTION
       "default: 0,
        0 : By dates,
        1 : Recurring."
   ::= { gs2328SystemTimeManual 6 }
   
gs2328SystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2328SystemTimeManual 7 }
   
gs2328SystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2328SystemTimeManual 8 }

gs2328SystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2328SystemTimeManual 9 }

gs2328SystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2328SystemTimeManual 10 }
   
gs2328SystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2328SystemTimeManual 11 }

gs2328SystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2328SystemTimeManual 12 }
   
gs2328SystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2328SystemTimeManual 13 }

gs2328SystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2328SystemTimeManual 14 }
   
gs2328SystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2328SystemTimeManual 15 }

gs2328SystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2328SystemTimeManual 16 }

gs2328SystemTimeNTP                                     OBJECT IDENTIFIER ::= { gs2328SystemTime 2 }

gs2328SystemTimeNTPTable OBJECT-TYPE
   SYNTAX      SEQUENCE OF GS2328SystemTimeNTPEntry
   MAX-ACCESS  not-accessible
   STATUS      current
   DESCRIPTION
       " "
   ::= { gs2328SystemTimeNTP 1 }

gs2328SystemTimeNTPEntry OBJECT-TYPE
   SYNTAX      GS2328SystemTimeNTPEntry
   MAX-ACCESS  not-accessible
   STATUS      current
   DESCRIPTION
       ""
   INDEX    { gs2328SystemTimeNTPIndex  }
   ::= { gs2328SystemTimeNTPTable 1 }

GS2328SystemTimeNTPEntry ::= SEQUENCE {
   gs2328SystemTimeNTPIndex             Integer32,
   gs2328SystemTimeNTPServerIPType      INTEGER,
   gs2328SystemTimeNTPServer            DisplayString,
   gs2328SystemTimeNTPCurrentMode       INTEGER
}

gs2328SystemTimeNTPIndex OBJECT-TYPE
   SYNTAX      Integer32(1..5)
   MAX-ACCESS  not-accessible
   STATUS      current
   DESCRIPTION
       " The index of the ntp entry. "
   ::= { gs2328SystemTimeNTPEntry 1 }

gs2328SystemTimeNTPServerIPType OBJECT-TYPE
   SYNTAX       INTEGER { ipv4(0), ipv6(1) }
   MAX-ACCESS   read-write
   STATUS       current
   DESCRIPTION
       "Default: 0,
        0 : IPv4,
        1 : IPv6."
   ::= { gs2328SystemTimeNTPEntry 2 }

gs2328SystemTimeNTPServer OBJECT-TYPE
   SYNTAX       DisplayString
   MAX-ACCESS   read-write
   STATUS       current
   DESCRIPTION
       "Get/Set the NTP Time Server1. You can use the IP address or domain name."
   ::= { gs2328SystemTimeNTPEntry 3 }

gs2328SystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2328SystemTimeNTPEntry 4 }

gs2328SystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2328SystemTimeNTP 2 }
   
gs2328SystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2328SystemTimeNTP 3 }
    

gs2328SystemAccount                                         OBJECT IDENTIFIER ::= { gs2328System 3 }

gs2328SystemAccountUsers                                    OBJECT IDENTIFIER ::= { gs2328SystemAccount 1 }

gs2328SystemAccountUserCreate OBJECT-TYPE
   SYNTAX       INTEGER { none(0), create(1) }
   MAX-ACCESS   read-write
   STATUS       current
   DESCRIPTION
       "default: 0
        0 : None  (read only)
        1 : Create a user account"
   ::= { gs2328SystemAccountUsers 1 }

gs2328SystemAccountUsersTable OBJECT-TYPE
   SYNTAX      SEQUENCE OF GS2328SystemAccountUsersEntry
   MAX-ACCESS  not-accessible
   STATUS      current
   DESCRIPTION
       " "
   ::= { gs2328SystemAccountUsers 2 }

gs2328SystemAccountUsersEntry OBJECT-TYPE
   SYNTAX      GS2328SystemAccountUsersEntry
   MAX-ACCESS  not-accessible
   STATUS      current
   DESCRIPTION
       ""
   INDEX    { gs2328UserIndex  }
   ::= { gs2328SystemAccountUsersTable 1 }


GS2328SystemAccountUsersEntry ::= SEQUENCE {
   gs2328UserIndex              Integer32 ,
   gs2328UserName               DisplayString,
   gs2328Password               DisplayString,
   gs2328UserPrivilegeLevel     Integer32 ,
   gs2328AccountUserRowStatus   INTEGER
}


gs2328UserIndex OBJECT-TYPE
   SYNTAX      Integer32 (1..20)
   MAX-ACCESS  not-accessible
   STATUS      current
   DESCRIPTION
       " "
   ::= { gs2328SystemAccountUsersEntry 1 }

gs2328UserName OBJECT-TYPE
   SYNTAX      DisplayString (SIZE (1..32))
   MAX-ACCESS  read-write
   STATUS      current
   DESCRIPTION
       "Please use a combination of letters, numbers and underscores"
   ::= { gs2328SystemAccountUsersEntry 2 }

gs2328Password OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2328SystemAccountUsersEntry 3 }

gs2328UserPrivilegeLevel OBJECT-TYPE
   SYNTAX      Integer32 (1..15)
   MAX-ACCESS  read-write
   STATUS      current
   DESCRIPTION
       "default:1 
        User privilege level range : 1 - 15"
   ::= { gs2328SystemAccountUsersEntry 4 }

gs2328AccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2328SystemAccountUsersEntry 5 }

gs2328SystemAccountUsersSuperUserPassword OBJECT-TYPE
   SYNTAX      OCTET STRING (SIZE (0..32))
   MAX-ACCESS read-write
   STATUS      current
   DESCRIPTION
        "Super-User Password"
   ::= { gs2328SystemAccountUsers 1500 }

gs2328SystemAccountEnforcePasswordRules OBJECT-TYPE
   SYNTAX       INTEGER { yes(0), no(1) }
   MAX-ACCESS   read-write
   STATUS       current
   DESCRIPTION
       "default: 0
        0 : Do not enforce rules
        1 : enforce rules"
   ::= { gs2328SystemAccountUsers 1501 }

gs2328SystemAccountPrivilegeLevel                           OBJECT IDENTIFIER ::= { gs2328SystemAccount 2 }

gs2328AccountPrivilegeLevel OBJECT-TYPE
   SYNTAX      Integer32 (1..15)
   MAX-ACCESS  read-write
   STATUS      current
   DESCRIPTION
       "Default:15, Range : 1-15. "
   ::= { gs2328SystemAccountPrivilegeLevel 1 }

gs2328AggregationPrivilegeLevel OBJECT-TYPE
   SYNTAX      Integer32 (1..15)
   MAX-ACCESS  read-write
   STATUS      current
   DESCRIPTION
       "Default:15, Range : 1-15. "
   ::= { gs2328SystemAccountPrivilegeLevel 2 }

gs2328DiagnosticsPrivilegeLevel OBJECT-TYPE
   SYNTAX      Integer32 (1..15)
   MAX-ACCESS  read-write
   STATUS      current
   DESCRIPTION
       "Default:15, Range : 1-15. "
   ::= { gs2328SystemAccountPrivilegeLevel 3 }

gs2328EEEPrivilegeLevel OBJECT-TYPE
   SYNTAX      Integer32 (1..15)
   MAX-ACCESS  read-write
   STATUS      current
   DESCRIPTION
       "Default:15, Range : 1-15. "
   ::= { gs2328SystemAccountPrivilegeLevel 4 }

gs2328EasyportPrivilegeLevel OBJECT-TYPE
   SYNTAX      Integer32 (1..15)
   MAX-ACCESS  read-write
   STATUS      current
   DESCRIPTION
       "Default:15, Range : 1-15. "
   ::= { gs2328SystemAccountPrivilegeLevel 9 }

gs2328GARPPrivilegeLevel OBJECT-TYPE
   SYNTAX      Integer32 (1..15)
   MAX-ACCESS  read-write
   STATUS      current
   DESCRIPTION
       "Default:15, Range : 1-15. "
   ::= { gs2328SystemAccountPrivilegeLevel 10 }

gs2328GVRPPrivilegeLevel OBJECT-TYPE
   SYNTAX      Integer32 (1..15)
   MAX-ACCESS  read-write
   STATUS      current
   DESCRIPTION
       "Default:15, Range : 1-15. "
   ::= { gs2328SystemAccountPrivilegeLevel 11 }

gs2328IPPrivilegeLevel OBJECT-TYPE
   SYNTAX      Integer32 (1..15)
   MAX-ACCESS  read-write
   STATUS      current
   DESCRIPTION
       "Default:15, Range : 1-15. "
   ::= { gs2328SystemAccountPrivilegeLevel 12 }

gs2328IPMCSnoopingPrivilegeLevel OBJECT-TYPE
   SYNTAX      Integer32 (1..15)
   MAX-ACCESS  read-write
   STATUS      current
   DESCRIPTION
       "Default:15, Range : 1-15. "
   ::= { gs2328SystemAccountPrivilegeLevel 13 }

gs2328LACPPrivilegeLevel OBJECT-TYPE
   SYNTAX      Integer32 (1..15)
   MAX-ACCESS  read-write
   STATUS      current
   DESCRIPTION
       "Default:15, Range : 1-15. "
   ::= { gs2328SystemAccountPrivilegeLevel 14 }

gs2328LLDPPrivilegeLevel OBJECT-TYPE
   SYNTAX      Integer32 (1..15)
   MAX-ACCESS  read-write
   STATUS      current
   DESCRIPTION
       "Default:15, Range : 1-15. "
   ::= { gs2328SystemAccountPrivilegeLevel 15 }

gs2328LLDPMEDPrivilegeLevel OBJECT-TYPE
   SYNTAX      Integer32 (1..15)
   MAX-ACCESS  read-write
   STATUS      current
   DESCRIPTION
       "Default:15, Range : 1-15. "
   ::= { gs2328SystemAccountPrivilegeLevel 16 }

gs2328LoopProtectPrivilegeLevel OBJECT-TYPE
   SYNTAX      Integer32 (1..15)
   MAX-ACCESS  read-write
   STATUS      current
   DESCRIPTION
       "Default:15, Range : 1-15. "
   ::= { gs2328SystemAccountPrivilegeLevel 17 }

gs2328MACTablePrivilegeLevel OBJECT-TYPE
   SYNTAX      Integer32 (1..15)
   MAX-ACCESS  read-write
   STATUS      current
   DESCRIPTION
       "Default:15, Range : 1-15. "
   ::= { gs2328SystemAccountPrivilegeLevel 18 }

gs2328MVRPrivilegeLevel OBJECT-TYPE
   SYNTAX      Integer32 (1..15)
   MAX-ACCESS  read-write
   STATUS      current
   DESCRIPTION
       "Default:15, Range : 1-15. "
   ::= { gs2328SystemAccountPrivilegeLevel 22 }

gs2328MaintenancePrivilegeLevel OBJECT-TYPE
   SYNTAX      Integer32 (1..15)
   MAX-ACCESS  read-write
   STATUS      current
   DESCRIPTION
       "Default:15, Range : 1-15. "
   ::= { gs2328SystemAccountPrivilegeLevel 24 }

gs2328MirroringPrivilegeLevel OBJECT-TYPE
   SYNTAX      Integer32 (1..15)
   MAX-ACCESS  read-write
   STATUS      current
   DESCRIPTION
       "Default:15, Range : 1-15. "
   ::= { gs2328SystemAccountPrivilegeLevel 25 }

gs2328PortsPrivilegeLevel OBJECT-TYPE
   SYNTAX      Integer32 (1..15)
   MAX-ACCESS  read-write
   STATUS      current
   DESCRIPTION
       "Default:15, Range : 1-15. "
   ::= { gs2328SystemAccountPrivilegeLevel 27 }

gs2328PrivateVLANsPrivilegeLevel OBJECT-TYPE
   SYNTAX      Integer32 (1..15)
   MAX-ACCESS  read-write
   STATUS      current
   DESCRIPTION
       "Default:15, Range : 1-15. "
   ::= { gs2328SystemAccountPrivilegeLevel 28 }

gs2328QoSPrivilegeLevel OBJECT-TYPE
   SYNTAX      Integer32 (1..15)
   MAX-ACCESS  read-write
   STATUS      current
   DESCRIPTION
       "Default:15, Range : 1-15. "
   ::= { gs2328SystemAccountPrivilegeLevel 29 }

gs2328SFlowPrivilegeLevel OBJECT-TYPE
   SYNTAX      Integer32 (1..15)
   MAX-ACCESS  read-write
   STATUS      current
   DESCRIPTION
       "Default:15, Range : 1-15. "
   ::= { gs2328SystemAccountPrivilegeLevel 30 }

gs2328SMTPPrivilegeLevel OBJECT-TYPE
   SYNTAX      Integer32 (1..15)
   MAX-ACCESS  read-write
   STATUS      current
   DESCRIPTION
       "Default:15, Range : 1-15. "
   ::= { gs2328SystemAccountPrivilegeLevel 31 }

gs2328SNMPPrivilegeLevel OBJECT-TYPE
   SYNTAX      Integer32 (1..15)
   MAX-ACCESS  read-write
   STATUS      current
   DESCRIPTION
       "Default:15, Range : 1-15. "
   ::= { gs2328SystemAccountPrivilegeLevel 32 }

gs2328SecurityPrivilegeLevel OBJECT-TYPE
   SYNTAX      Integer32 (1..15)
   MAX-ACCESS  read-write
   STATUS      current
   DESCRIPTION
       "Default:15, Range : 1-15. "
   ::= { gs2328SystemAccountPrivilegeLevel 33 }

gs2328SingleIPPrivilegeLevel OBJECT-TYPE
   SYNTAX      Integer32 (1..15)
   MAX-ACCESS  read-write
   STATUS      current
   DESCRIPTION
       "Default:15, Range : 1-15. "
   ::= { gs2328SystemAccountPrivilegeLevel 34 }

gs2328SpanningTreePrivilegeLevel OBJECT-TYPE
   SYNTAX      Integer32 (1..15)
   MAX-ACCESS  read-write
   STATUS      current
   DESCRIPTION
       "Default:15, Range : 1-15. "
   ::= { gs2328SystemAccountPrivilegeLevel 35 }

gs2328SystemPrivilegeLevel OBJECT-TYPE
   SYNTAX      Integer32 (1..15)
   MAX-ACCESS  read-write
   STATUS      current
   DESCRIPTION
       "Default:15, Range : 1-15. "
   ::= { gs2328SystemAccountPrivilegeLevel 36 }

gs2328TrapEventPrivilegeLevel OBJECT-TYPE
   SYNTAX      Integer32 (1..15)
   MAX-ACCESS  read-write
   STATUS      current
   DESCRIPTION
       "Default:15, Range : 1-15. "
   ::= { gs2328SystemAccountPrivilegeLevel 37 }

gs2328UPnPPrivilegeLevel OBJECT-TYPE
   SYNTAX      Integer32 (1..15)
   MAX-ACCESS  read-write
   STATUS      current
   DESCRIPTION
       "Default:15, Range : 1-15. "
   ::= { gs2328SystemAccountPrivilegeLevel 38 }

gs2328VCLPrivilegeLevel OBJECT-TYPE
   SYNTAX      Integer32 (1..15)
   MAX-ACCESS  read-write
   STATUS      current
   DESCRIPTION
       "Default:15, Range : 1-15. "
   ::= { gs2328SystemAccountPrivilegeLevel 39 }

gs2328VLANsPrivilegeLevel OBJECT-TYPE
   SYNTAX      Integer32 (1..15)
   MAX-ACCESS  read-write
   STATUS      current
   DESCRIPTION
       "Default:15, Range : 1-15. "
   ::= { gs2328SystemAccountPrivilegeLevel 41 }

gs2328VoiceVLANPrivilegeLevel OBJECT-TYPE
   SYNTAX      Integer32 (1..15)
   MAX-ACCESS  read-write
   STATUS      current
   DESCRIPTION
       "Default:15, Range : 1-15. "
   ::= { gs2328SystemAccountPrivilegeLevel 42 }

gs2328IP                                                    OBJECT IDENTIFIER ::= { gs2328System 4 }

gs2328IPv4                                                  OBJECT IDENTIFIER ::= { gs2328IP 1 }

gs2328IPv4Configured                                                  OBJECT IDENTIFIER ::= { gs2328IPv4 1 }

gs2328Ipv4DHCPClient OBJECT-TYPE
   SYNTAX      INTEGER { disable(0), enable(1) }
   MAX-ACCESS  read-write
   STATUS      current
   DESCRIPTION
       "default:0
       0: disable
       1: enable"
   ::= { gs2328IPv4Configured 1 }

gs2328IPv4Address OBJECT-TYPE
   SYNTAX      IpAddress
   MAX-ACCESS  read-write
   STATUS      current
   DESCRIPTION
       ""
   ::= { gs2328IPv4Configured 2 }

gs2328IPv4Mask OBJECT-TYPE
   SYNTAX      IpAddress
   MAX-ACCESS  read-write
   STATUS      current
   DESCRIPTION
       ""
   ::= { gs2328IPv4Configured 3 }

gs2328IPv4Gateway OBJECT-TYPE
   SYNTAX      IpAddress
   MAX-ACCESS  read-write
   STATUS      current
   DESCRIPTION
       ""
   ::= { gs2328IPv4Configured 4 }

gs2328IPv4VLANId OBJECT-TYPE
   SYNTAX      Integer32(1..4094)
   MAX-ACCESS  read-write
   STATUS      current
   DESCRIPTION
       "default:1"
   ::= { gs2328IPv4Configured 5 }

gs2328IPv4DNSServer OBJECT-TYPE
   SYNTAX      IpAddress
   MAX-ACCESS  read-write
   STATUS      current
   DESCRIPTION
       ""
   ::= { gs2328IPv4Configured 6 }

gs2328IPv4DNSProxy OBJECT-TYPE
   SYNTAX      INTEGER { disable(0), enable(1) }
   MAX-ACCESS  read-write
   STATUS      current
   DESCRIPTION
       "0:disable, 1:enable "
   ::= { gs2328IPv4Configured 7 }

gs2328IPv4Current                                                  OBJECT IDENTIFIER ::= { gs2328IPv4 2 }

gs2328Ipv4CurrentDHCPClient OBJECT-TYPE
   SYNTAX      INTEGER { none(0), renew(1) }
   MAX-ACCESS  read-write
   STATUS      current
   DESCRIPTION
       "default:0
       0: none (for read)
       1: renew"
   ::= { gs2328IPv4Current 1 }

gs2328IPv4CurrentAddress OBJECT-TYPE
   SYNTAX      IpAddress
   MAX-ACCESS  read-only
   STATUS      current
   DESCRIPTION
       ""
   ::= { gs2328IPv4Current 2 }

gs2328IPv4CurrentMask OBJECT-TYPE
   SYNTAX      IpAddress
   MAX-ACCESS  read-only
   STATUS      current
   DESCRIPTION
       ""
   ::= { gs2328IPv4Current 3 }

gs2328IPv4CurrentGateway OBJECT-TYPE
   SYNTAX      IpAddress
   MAX-ACCESS  read-only
   STATUS      current
   DESCRIPTION
       ""
   ::= { gs2328IPv4Current 4 }

gs2328IPv4CurrentVLANId OBJECT-TYPE
   SYNTAX      Integer32(1..4094)
   MAX-ACCESS  read-only
   STATUS      current
   DESCRIPTION
       "default:1"
   ::= { gs2328IPv4Current 5 }

gs2328IPv4CurrentDNSServer OBJECT-TYPE
   SYNTAX      IpAddress
   MAX-ACCESS  read-only
   STATUS      current
   DESCRIPTION
       ""
   ::= { gs2328IPv4Current 6 }


gs2328IPv6                                                  OBJECT IDENTIFIER ::= { gs2328IP 2 }

gs2328IPv6Configured                                                  OBJECT IDENTIFIER ::= { gs2328IPv6 1 }

gs2328Ipv6AutoConfiguration OBJECT-TYPE
   SYNTAX      INTEGER { disable(0), enable(1) }
   MAX-ACCESS  read-write
   STATUS      current
   DESCRIPTION
       "default:0
       0: disable
       1: enable"
   ::= { gs2328IPv6Configured 1 }

gs2328Ipv6Address OBJECT-TYPE
   SYNTAX      DisplayString (SIZE (0..30))
   MAX-ACCESS  read-write
   STATUS      current
   DESCRIPTION
       ""
   ::= { gs2328IPv6Configured 2 }

gs2328Ipv6Prefix OBJECT-TYPE
   SYNTAX      Integer32 (1..128)
   MAX-ACCESS  read-write
   STATUS      current
   DESCRIPTION
       "default: 96"
   ::= { gs2328IPv6Configured 3 }

gs2328Ipv6Gateway OBJECT-TYPE
   SYNTAX      DisplayString (SIZE (0..30))
   MAX-ACCESS  read-write
   STATUS      current
   DESCRIPTION
       " "
   ::= { gs2328IPv6Configured 4 }

gs2328IPv6Current                                                  OBJECT IDENTIFIER ::= { gs2328IPv6 2 }

gs2328Ipv6CurrentAutoConfiguration OBJECT-TYPE
   SYNTAX      INTEGER { disable(0), enable(1) }
   MAX-ACCESS  read-only
   STATUS      current
   DESCRIPTION
       "default:0
       0: disable
       1: enable"
   ::= { gs2328IPv6Current 1 }

gs2328Ipv6CurrentAddress OBJECT-TYPE
   SYNTAX      DisplayString (SIZE (0..30))
   MAX-ACCESS  read-only
   STATUS      current
   DESCRIPTION
       ""
   ::= { gs2328IPv6Current 2 }


gs2328Ipv6CurrentLinkLocalAddress OBJECT-TYPE
   SYNTAX      DisplayString(SIZE (0..30))
   MAX-ACCESS  read-only
   STATUS      current
   DESCRIPTION
       ""
   ::= { gs2328IPv6Current 3 }


gs2328Ipv6CurrentPrefix OBJECT-TYPE
   SYNTAX      DisplayString(SIZE (0..64))
   MAX-ACCESS  read-only
   STATUS      current
   DESCRIPTION
       ""
   ::= { gs2328IPv6Current 4 }

gs2328Ipv6CurrentGateway OBJECT-TYPE
   SYNTAX      DisplayString (SIZE (0..30))
   MAX-ACCESS  read-only
   STATUS      current
   DESCRIPTION
       " "
   ::= { gs2328IPv6Current 5 }

gs2328Syslog                                                OBJECT IDENTIFIER ::= { gs2328System 5 }

gs2328SyslogConf                                            OBJECT IDENTIFIER ::= { gs2328Syslog 1 }

gs2328ServerMode OBJECT-TYPE
   SYNTAX      INTEGER { disable(0), enable(1) }
   MAX-ACCESS  read-write
   STATUS      current
   DESCRIPTION
       "default: 0
       0: disable
       1: enable "
   ::= { gs2328SyslogConf 1 }

gs2328ServerAddress1 OBJECT-TYPE
   SYNTAX      IpAddress
   MAX-ACCESS  read-write
   STATUS      current
   DESCRIPTION
       " "
   ::= { gs2328SyslogConf 2 }

gs2328ServerAddress2 OBJECT-TYPE
   SYNTAX      IpAddress
   MAX-ACCESS  read-write
   STATUS      current
   DESCRIPTION
       " "
   ::= { gs2328SyslogConf 3 }

gs2328SyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2328SyslogConf 4 }

gs2328SyslogDetailedInfo                                    OBJECT IDENTIFIER ::= { gs2328Syslog 2 }

gs2328SyslogDetailedInfoClear OBJECT-TYPE
   SYNTAX      INTEGER { none(0), clear(1) }
   MAX-ACCESS  read-write
   STATUS      current
   DESCRIPTION
      "default: 0
       0 : None  (read only)
       1 : Clear Syslog"
   ::= { gs2328SyslogDetailedInfo 1 }

gs2328SyslogDetailedInfoTable OBJECT-TYPE
  SYNTAX      SEQUENCE OF GS2328SyslogDetailedInfoEntry
  MAX-ACCESS  not-accessible
  STATUS      current
  DESCRIPTION
           " "
       ::= { gs2328SyslogDetailedInfo 2 }

gs2328SyslogDetailedInfoEntry OBJECT-TYPE
   SYNTAX      GS2328SyslogDetailedInfoEntry
   MAX-ACCESS  not-accessible
   STATUS      current
   DESCRIPTION
           ""
   INDEX    { gs2328SyslogDetailedInfoIndex  }
   ::= { gs2328SyslogDetailedInfoTable 1 }

GS2328SyslogDetailedInfoEntry ::= SEQUENCE {
   gs2328SyslogDetailedInfoIndex       Integer32,
   gs2328SyslogDetailedInfoLevel       DisplayString,
   gs2328SyslogDetailedInfoTime        DisplayString,
   gs2328SyslogDetailedInfoMessage     DisplayString
}

gs2328SyslogDetailedInfoIndex OBJECT-TYPE
   SYNTAX      Integer32(1..1024)
   MAX-ACCESS  not-accessible
   STATUS      current
   DESCRIPTION
       " "
   ::= { gs2328SyslogDetailedInfoEntry 1 }
   
gs2328SyslogDetailedInfoLevel OBJECT-TYPE
   SYNTAX      DisplayString
   MAX-ACCESS  read-only
   STATUS      current
   DESCRIPTION
       " "
   ::= { gs2328SyslogDetailedInfoEntry 2 }

gs2328SyslogDetailedInfoTime OBJECT-TYPE
   SYNTAX      DisplayString(SIZE (0..20))
   MAX-ACCESS  read-only
   STATUS      current
   DESCRIPTION
       " "
   ::= { gs2328SyslogDetailedInfoEntry 3 }

gs2328SyslogDetailedInfoMessage OBJECT-TYPE
   SYNTAX      DisplayString
   MAX-ACCESS  read-only
   STATUS      current
   DESCRIPTION
       " "
   ::= { gs2328SyslogDetailedInfoEntry 4 }


gs2328Snmp                                                OBJECT IDENTIFIER ::= { gs2328System 6 }

gs2328SnmpConf                                            OBJECT IDENTIFIER ::= { gs2328Snmp 1 }

gs2328GetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2328SnmpConf 1 }

gs2328GetCommunity OBJECT-TYPE
   SYNTAX       DisplayString
   MAX-ACCESS   read-write
   STATUS       current
   DESCRIPTION
       "Get/Set the get-community of the SNMP."
   ::= { gs2328SnmpConf 2 }

gs2328SetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2328SnmpConf 3 }

gs2328SetCommunity OBJECT-TYPE
   SYNTAX       DisplayString
   MAX-ACCESS   read-write
   STATUS       current
   DESCRIPTION
       "Get/Set the set-community of the SNMP."
   ::= { gs2328SnmpConf 4 }

gs2328GetCommunityConfTable OBJECT-TYPE
   SYNTAX      SEQUENCE OF GS2328GetCommunityConfEntry
   MAX-ACCESS  not-accessible
   STATUS      current
   DESCRIPTION
       " Show get-community of the SNMP. "
   ::= { gs2328SnmpConf 5 }

gs2328GetCommunityConfEntry OBJECT-TYPE
   SYNTAX      GS2328GetCommunityConfEntry
   MAX-ACCESS  not-accessible
   STATUS      current
   DESCRIPTION
       ""
   INDEX    { gs2328CommunityConfIndex  }
   ::= { gs2328GetCommunityConfTable 1 }

GS2328GetCommunityConfEntry ::= SEQUENCE {
   gs2328CommunityConfIndex				Integer32,
   gs2328CommunityConfGetCommunity			DisplayString
}

gs2328CommunityConfIndex OBJECT-TYPE
   SYNTAX      Integer32(1..4095)
   MAX-ACCESS  not-accessible
   STATUS      current
   DESCRIPTION
       " index, range : 1 - 5. "
   ::= { gs2328GetCommunityConfEntry 1 }
   
gs2328CommunityConfGetCommunity OBJECT-TYPE
   SYNTAX      DisplayString
   MAX-ACCESS  read-write
   STATUS      current
   DESCRIPTION
       " Get/Set the get-community of the SNMP."
   ::= { gs2328GetCommunityConfEntry 2 }

gs2328TrapHostConfTable OBJECT-TYPE
   SYNTAX      SEQUENCE OF GS2328TrapHostConfEntry
   MAX-ACCESS  not-accessible
   STATUS      current
   DESCRIPTION
       "A list of trap host entry. The numbers of entries are given by the value of gs2328TrapHostConfNumber."
   ::= { gs2328SnmpConf 6 }
   
gs2328TrapHostConfEntry OBJECT-TYPE
   SYNTAX      GS2328TrapHostConfEntry
   MAX-ACCESS  not-accessible
   STATUS      current
   DESCRIPTION
       "This is the entry information for trap host."
   INDEX    { gs2328TrapHostConfIndex  }
   ::= { gs2328TrapHostConfTable 1 }

GS2328TrapHostConfEntry ::= SEQUENCE {
    gs2328TrapHostConfIndex             Integer32,
    gs2328TrapHostConfVersion           INTEGER,
    gs2328TrapHostConfIPType            INTEGER,
    gs2328TrapHostConfIP                DisplayString,
    gs2328TrapHostConfPort              Integer32,
    gs2328TrapHostConfCommunity         DisplayString,
    gs2328TrapHostConfSeverityLevel     INTEGER,
    gs2328TrapHostConfSecurityLevel     INTEGER,
    gs2328TrapHostConfAuthPtc           INTEGER,
    gs2328TrapHostConfAuthPassword      DisplayString,
    gs2328TrapHostConfPrivPtc           INTEGER,
    gs2328TrapHostConfPrivPassword      DisplayString,
    gs2328TrapHostConfCurrentMode       INTEGER
}
   
gs2328TrapHostConfIndex OBJECT-TYPE
   SYNTAX      Integer32(1..6)
   MAX-ACCESS  not-accessible
   STATUS      current
   DESCRIPTION
       " The index of the trap host entry. "
   ::= { gs2328TrapHostConfEntry 1 }

gs2328TrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2328TrapHostConfEntry 2 }

gs2328TrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2328TrapHostConfEntry 3 }

gs2328TrapHostConfIP OBJECT-TYPE
   SYNTAX       DisplayString
   MAX-ACCESS   read-write
   STATUS       current
   DESCRIPTION
       "This is the IP of the trap host."
   ::= { gs2328TrapHostConfEntry 4 }

gs2328TrapHostConfPort OBJECT-TYPE
   SYNTAX       Integer32(1..65535)
   MAX-ACCESS   read-write
   STATUS       current
   DESCRIPTION
       "This is the receiving-port number of the trap host.
        range : 1 - 65535."
   ::= { gs2328TrapHostConfEntry 5 }

gs2328TrapHostConfCommunity OBJECT-TYPE
   SYNTAX       DisplayString (SIZE (1..32))
   MAX-ACCESS   read-write
   STATUS       current
   DESCRIPTION
       "The community/security name for the trap PDU."
   ::= { gs2328TrapHostConfEntry 6 }

gs2328TrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2328TrapHostConfEntry 7 }

gs2328TrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2328TrapHostConfEntry 8 }

gs2328TrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2328TrapHostConfEntry 9 }

gs2328TrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2328TrapHostConfEntry 10 }

gs2328TrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2328TrapHostConfEntry 11 }

gs2328TrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2328TrapHostConfEntry 12 }

gs2328TrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2328TrapHostConfEntry 13 }


gs2328SnmpSystem                                          OBJECT IDENTIFIER ::= { gs2328Snmp 2 }

gs2328SnmpState OBJECT-TYPE
   SYNTAX       INTEGER { disable(0), enable(1) }
   MAX-ACCESS   read-write
   STATUS       current
   DESCRIPTION
       "Get/Set the state of the SNMP.
        default : 1, 0: disable, 1: enable. "
   ::= { gs2328SnmpSystem 1 }

gs2328SnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2328SnmpSystem 2 }

gs2328SnmpCommunities                                          OBJECT IDENTIFIER ::= { gs2328Snmp 3 }

gs2328SnmpCommunitiesCreate OBJECT-TYPE
   SYNTAX       INTEGER { none(0), create(1) }
   MAX-ACCESS   read-write
   STATUS       current
   DESCRIPTION
       "default: 0
        0 : None  (read only)
        1 : Create entry"
   ::= { gs2328SnmpCommunities 1 }

gs2328SnmpCommunitiesTable OBJECT-TYPE
   SYNTAX      SEQUENCE OF GS2328SnmpCommunitiesEntry
   MAX-ACCESS  not-accessible
   STATUS      current
   DESCRIPTION
       " Create SNMPv1/v2 Communities entry."
   ::= { gs2328SnmpCommunities 2 }

gs2328SnmpCommunitiesEntry OBJECT-TYPE
   SYNTAX      GS2328SnmpCommunitiesEntry
   MAX-ACCESS  not-accessible
   STATUS      current
   DESCRIPTION
       ""
   INDEX    { gs2328SnmpCommunitiesIndex  }
   ::= { gs2328SnmpCommunitiesTable 1 }

GS2328SnmpCommunitiesEntry ::= SEQUENCE {
   gs2328SnmpCommunitiesIndex          Integer32,
   gs2328SnmpCommunitiesCommunity      DisplayString,
   gs2328SnmpCommunitiesUserName       DisplayString,
   gs2328SnmpCommunitiesSourceIP       IpAddress,
   gs2328SnmpCommunitiesSourceMask     IpAddress,
   gs2328SnmpCommunitiesRowStatus      INTEGER
}

gs2328SnmpCommunitiesIndex OBJECT-TYPE
   SYNTAX      Integer32(1..4)
   MAX-ACCESS  not-accessible
   STATUS      current
   DESCRIPTION
       " "
   ::= { gs2328SnmpCommunitiesEntry 1 }

gs2328SnmpCommunitiesCommunity OBJECT-TYPE
   SYNTAX      DisplayString (SIZE (1..32))
   MAX-ACCESS  read-write
   STATUS      current
   DESCRIPTION
       "Up to 32 characters describing Community."
   ::= { gs2328SnmpCommunitiesEntry 2 }

gs2328SnmpCommunitiesUserName OBJECT-TYPE
   SYNTAX      DisplayString (SIZE (1..32))
   MAX-ACCESS  read-write
   STATUS      current
   DESCRIPTION
       " Up to 32 characters describing User Name. "
   ::= { gs2328SnmpCommunitiesEntry 3 }

gs2328SnmpCommunitiesSourceIP OBJECT-TYPE
   SYNTAX      IpAddress
   MAX-ACCESS  read-write
   STATUS      current
   DESCRIPTION
       " SNMP access source ip. "
   ::= { gs2328SnmpCommunitiesEntry 4 }

gs2328SnmpCommunitiesSourceMask OBJECT-TYPE
   SYNTAX      IpAddress
   MAX-ACCESS  read-write
   STATUS      current
   DESCRIPTION
       " SNMP access source address mask. "
   ::= { gs2328SnmpCommunitiesEntry 5 }

gs2328SnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2328SnmpCommunitiesEntry 6 }


gs2328SnmpUsers                                          OBJECT IDENTIFIER ::= { gs2328Snmp 4 }

gs2328SnmpUsersCreate OBJECT-TYPE
   SYNTAX       INTEGER { none(0), create(1) }
   MAX-ACCESS   read-write
   STATUS       current
   DESCRIPTION
       "default: 0
        0 : None  (read only)
        1 : Create entry"
   ::= { gs2328SnmpUsers 1 }

gs2328SnmpUsersTable OBJECT-TYPE
   SYNTAX      SEQUENCE OF GS2328SnmpUsersEntry
   MAX-ACCESS  not-accessible
   STATUS      current
   DESCRIPTION
       " Create SNMPv3 users entry."
   ::= { gs2328SnmpUsers 2 }

gs2328SnmpUsersEntry OBJECT-TYPE
   SYNTAX      GS2328SnmpUsersEntry
   MAX-ACCESS  not-accessible
   STATUS      current
   DESCRIPTION
       ""
   INDEX    { gs2328SnmpUsersIndex  }
   ::= { gs2328SnmpUsersTable 1 }

GS2328SnmpUsersEntry ::= SEQUENCE {
   gs2328SnmpUsersIndex                    Integer32,
   gs2328SnmpUsersUserName                 DisplayString,
   gs2328SnmpUsersSecurityLevel            INTEGER,
   gs2328SnmpUsersAuthenticationProtocol   INTEGER,
   gs2328SnmpUsersAuthenticationPassword   DisplayString,
   gs2328SnmpUsersPrivacyProtocol          INTEGER,
   gs2328SnmpUsersPrivacyPassword          DisplayString,
   gs2328SnmpUsersRowStatus                INTEGER
}

gs2328SnmpUsersIndex OBJECT-TYPE
   SYNTAX      Integer32(1..10)
   MAX-ACCESS  not-accessible
   STATUS      current
   DESCRIPTION
       " "
   ::= { gs2328SnmpUsersEntry 1 }

gs2328SnmpUsersUserName OBJECT-TYPE
   SYNTAX      DisplayString (SIZE (1..32))
   MAX-ACCESS  read-write
   STATUS      current
   DESCRIPTION
       "Up to 32 characters describing User Name."
   ::= { gs2328SnmpUsersEntry 2 }

gs2328SnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy. 
         3: Authentication and privacy. "
   ::= { gs2328SnmpUsersEntry 3 }

gs2328SnmpUsersAuthenticationProtocol OBJECT-TYPE
   SYNTAX      INTEGER { none(0), md5(1), sha(2) }
   MAX-ACCESS  read-write
   STATUS      current
   DESCRIPTION
       " 0: None.
         1: MD5.
         2: SHA "
   ::= { gs2328SnmpUsersEntry 4 }

gs2328SnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2328SnmpUsersEntry 5 }
   
gs2328SnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2328SnmpUsersEntry 6 }

gs2328SnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2328SnmpUsersEntry 7 }
   
gs2328SnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2328SnmpUsersEntry 8 }


gs2328SnmpGroups                                          OBJECT IDENTIFIER ::= { gs2328Snmp 5 }

gs2328SnmpGroupsCreate OBJECT-TYPE
   SYNTAX       INTEGER { none(0), create(1) }
   MAX-ACCESS   read-write
   STATUS       current
   DESCRIPTION
       "default: 0
        0 : None  (read only)
        1 : Create entry"
   ::= { gs2328SnmpGroups 1 }

gs2328SnmpGroupsTable OBJECT-TYPE
   SYNTAX      SEQUENCE OF GS2328SnmpGroupsEntry
   MAX-ACCESS  not-accessible
   STATUS      current
   DESCRIPTION
       " Create SNMPv3 groups entry."
   ::= { gs2328SnmpGroups 2 }

gs2328SnmpGroupsEntry OBJECT-TYPE
   SYNTAX      GS2328SnmpGroupsEntry
   MAX-ACCESS  not-accessible
   STATUS      current
   DESCRIPTION
       ""
   INDEX    { gs2328SnmpGroupsIndex  }
   ::= { gs2328SnmpGroupsTable 1 }

GS2328SnmpGroupsEntry ::= SEQUENCE {
   gs2328SnmpGroupsIndex           Integer32,
   gs2328SnmpGroupsSecurityModel   INTEGER,
   gs2328SnmpGroupsSecurityName    DisplayString,
   gs2328SnmpGroupsGroupName       DisplayString,
   gs2328SnmpGroupsRowStatus       INTEGER
}

gs2328SnmpGroupsIndex OBJECT-TYPE
   SYNTAX      Integer32(1..14)
   MAX-ACCESS  not-accessible
   STATUS      current
   DESCRIPTION
       " "
   ::= { gs2328SnmpGroupsEntry 1 }

gs2328SnmpGroupsSecurityModel OBJECT-TYPE
   SYNTAX      INTEGER { v1(1), v2c(2), usm(3) }
   MAX-ACCESS  read-write
   STATUS      current
   DESCRIPTION
       " 1: v1.
         2: v2c. 
         3: usm."
   ::= { gs2328SnmpGroupsEntry 2 }

gs2328SnmpGroupsSecurityName OBJECT-TYPE
   SYNTAX      DisplayString (SIZE (1..32))
   MAX-ACCESS  read-write
   STATUS      current
   DESCRIPTION
       "Up to 32 characters describing User Name."
   ::= { gs2328SnmpGroupsEntry 3 }

gs2328SnmpGroupsGroupName OBJECT-TYPE
   SYNTAX      DisplayString (SIZE (1..32))
   MAX-ACCESS  read-write
   STATUS      current
   DESCRIPTION
       "Up to 32 characters describing Group Name."
   ::= { gs2328SnmpGroupsEntry 4 }
   
gs2328SnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2328SnmpGroupsEntry 5 }

gs2328SnmpViews                                              OBJECT IDENTIFIER ::= { gs2328Snmp 6 }

gs2328SnmpViewsCreate OBJECT-TYPE
   SYNTAX       INTEGER { none(0), create(1) }
   MAX-ACCESS   read-write
   STATUS       current
   DESCRIPTION
       "default: 0
        0 : None  (read only)
        1 : Create entry"
   ::= { gs2328SnmpViews 1 }

gs2328SnmpViewsTable OBJECT-TYPE
   SYNTAX      SEQUENCE OF GS2328SnmpViewsEntry
   MAX-ACCESS  not-accessible
   STATUS      current
   DESCRIPTION
       " Create SNMPv1/v2 Views entry."
   ::= { gs2328SnmpViews 2 }

gs2328SnmpViewsEntry OBJECT-TYPE
   SYNTAX      GS2328SnmpViewsEntry
   MAX-ACCESS  not-accessible
   STATUS      current
   DESCRIPTION
       ""
   INDEX    { gs2328SnmpViewsIndex  }
   ::= { gs2328SnmpViewsTable 1 }

GS2328SnmpViewsEntry ::= SEQUENCE {
   gs2328SnmpViewsIndex        Integer32,
   gs2328SnmpViewsName         DisplayString,
   gs2328SnmpViewsType         INTEGER,
   gs2328SnmpViewsOIDSubtree   DisplayString,
   gs2328SnmpViewsRowStatus    INTEGER
}
   
gs2328SnmpViewsIndex OBJECT-TYPE
   SYNTAX      Integer32(1..4)
   MAX-ACCESS  not-accessible
   STATUS      current
   DESCRIPTION
       " "
   ::= { gs2328SnmpViewsEntry 1 }

gs2328SnmpViewsName OBJECT-TYPE
   SYNTAX      DisplayString (SIZE (1..32))
   MAX-ACCESS  read-write
   STATUS      current
   DESCRIPTION
       "Up to 32 characters describing view Name."
   ::= { gs2328SnmpViewsEntry 2 }   

gs2328SnmpViewsType OBJECT-TYPE
   SYNTAX      INTEGER { included(1), excluded(2) }
   MAX-ACCESS  read-write
   STATUS      current
   DESCRIPTION
       "1: included, An optional flag to indicate that this view subtree should be included. 
	   2: excluded, An optional flag to indicate that this view subtree should be excluded."
   ::= { gs2328SnmpViewsEntry 3 } 
   
gs2328SnmpViewsOIDSubtree OBJECT-TYPE
   SYNTAX      DisplayString (SIZE (1..128))
   MAX-ACCESS  read-write
   STATUS      current
   DESCRIPTION
       "The OID defining the root of the subtree to add to the named view."
   ::= { gs2328SnmpViewsEntry 4 } 

gs2328SnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2328SnmpViewsEntry 5 }   


gs2328SnmpAccess                                          OBJECT IDENTIFIER ::= { gs2328Snmp 7 }

gs2328SnmpAccessCreate OBJECT-TYPE
   SYNTAX       INTEGER { none(0), create(1) }
   MAX-ACCESS   read-write
   STATUS       current
   DESCRIPTION
       "default: 0
        0 : None  (read only)
        1 : Create entry"
   ::= { gs2328SnmpAccess 1 }

gs2328SnmpAccessTable OBJECT-TYPE
   SYNTAX      SEQUENCE OF GS2328SnmpAccessEntry
   MAX-ACCESS  not-accessible
   STATUS      current
   DESCRIPTION
       " Create SNMPv3 Access entry."
   ::= { gs2328SnmpAccess 2 }

gs2328SnmpAccessEntry OBJECT-TYPE
   SYNTAX      GS2328SnmpAccessEntry
   MAX-ACCESS  not-accessible
   STATUS      current
   DESCRIPTION
       ""
   INDEX    { gs2328SnmpAccessIndex  }
   ::= { gs2328SnmpAccessTable 1 }

GS2328SnmpAccessEntry ::= SEQUENCE {
   gs2328SnmpAccessIndex             Integer32,
   gs2328SnmpAccessGroupName         DisplayString,
   gs2328SnmpAccessSecurityModel     INTEGER,
   gs2328SnmpAccessSecurityLevel     INTEGER,
   gs2328SnmpAccessReadViewName      DisplayString,
   gs2328SnmpAccessWriteViewName     DisplayString,  
   gs2328SnmpAccessRowStatus         INTEGER
}

gs2328SnmpAccessIndex OBJECT-TYPE
   SYNTAX      Integer32(1..14)
   MAX-ACCESS  not-accessible
   STATUS      current
   DESCRIPTION
       " "
   ::= { gs2328SnmpAccessEntry 1 }

gs2328SnmpAccessGroupName OBJECT-TYPE
   SYNTAX      DisplayString (SIZE (1..32))
   MAX-ACCESS  read-write
   STATUS      current
   DESCRIPTION
       "Up to 32 characters describing Group Name."
   ::= { gs2328SnmpAccessEntry 2 }

gs2328SnmpAccessSecurityModel OBJECT-TYPE
   SYNTAX      INTEGER { any(0), v1(1), v2c(2), usm(3) }
   MAX-ACCESS  read-write
   STATUS      current
   DESCRIPTION
       " 0: any.
         1: v1.
         2: v2c. 
         3: usm."
   ::= { gs2328SnmpAccessEntry 3 }

gs2328SnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy. 
         3: Authentication and privacy. "
   ::= { gs2328SnmpAccessEntry 4 }

gs2328SnmpAccessReadViewName OBJECT-TYPE
   SYNTAX      DisplayString (SIZE (1..32))
   MAX-ACCESS  read-write
   STATUS      current
   DESCRIPTION
       "Up to 32 characters describing Read View Name.
        None is reserved for Empty."
   ::= { gs2328SnmpAccessEntry 5 }
   
gs2328SnmpAccessWriteViewName OBJECT-TYPE
   SYNTAX      DisplayString (SIZE (1..32))
   MAX-ACCESS  read-write
   STATUS      current
   DESCRIPTION
       "Up to 32 characters describing Write View Name.
        None is reserved for Empty."
   ::= { gs2328SnmpAccessEntry 6 }
   
gs2328SnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2328SnmpAccessEntry 7 }


----------------------------------------------------------------------------------------------------

gs2328Configuration                                         OBJECT IDENTIFIER ::= { lancomGS2328  2 }

gs2328Port                                                  OBJECT IDENTIFIER ::= { gs2328Configuration 1 }

gs2328PortConfigurationTable OBJECT-TYPE
   SYNTAX      SEQUENCE OF GS2328PortConfigurationEntry
   MAX-ACCESS  not-accessible
   STATUS      current
   DESCRIPTION
       " Show port configurations. "
   ::= { gs2328Port 1 }

gs2328PortConfigurationEntry OBJECT-TYPE
   SYNTAX      GS2328PortConfigurationEntry
   MAX-ACCESS  not-accessible
   STATUS      current
   DESCRIPTION
       ""
   INDEX    { gs2328PortConfPort  }
   ::= { gs2328PortConfigurationTable 1 }

GS2328PortConfigurationEntry ::= SEQUENCE {
   gs2328PortConfPort                     Integer32,
   gs2328PortConfPortMedia                DisplayString,
   gs2328PortConfLink                     DisplayString,
   gs2328PortConfCurrentSpeed             DisplayString,
   gs2328PortConfSpeed                    INTEGER,
   gs2328PortConfCurrentFlowControlRx     INTEGER,
   gs2328PortConfCurrentFlowControlTx     INTEGER,
   gs2328PortConfFlowControl              INTEGER,
   gs2328PortConfMaxFrameSize             Integer32,
   gs2328PortConfExcessiveCollisionMode   INTEGER,
   gs2328PortConfPowerControl             INTEGER,
   gs2328PortConfDescription              DisplayString
}

gs2328PortConfPort OBJECT-TYPE
   SYNTAX      Integer32(1..4095)
   MAX-ACCESS  not-accessible
   STATUS      current
   DESCRIPTION
       " port, range : 1 - port number. "
   ::= { gs2328PortConfigurationEntry 1 }

gs2328PortConfPortMedia OBJECT-TYPE
   SYNTAX      DisplayString(SIZE (1..4))
   MAX-ACCESS  read-only
   STATUS      current
   DESCRIPTION
       " Show port media. "
   ::= { gs2328PortConfigurationEntry 2 }

gs2328PortConfLink OBJECT-TYPE
   SYNTAX      DisplayString(SIZE (2..4))
   MAX-ACCESS  read-only
   STATUS      current
   DESCRIPTION
       " The current link state. "
   ::= { gs2328PortConfigurationEntry 3 }

gs2328PortConfCurrentSpeed OBJECT-TYPE
   SYNTAX      DisplayString(SIZE (6..12))
   MAX-ACCESS  read-only
   STATUS      current
   DESCRIPTION
       " The current link speed of the port. "
   ::= { gs2328PortConfigurationEntry 4 }

gs2328PortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11),
                    speed10GFull(12)
                }
   MAX-ACCESS  read-write
   STATUS      current
   DESCRIPTION
       "default: 1,
        0: disable state, 
        1: auto, 
        2: 10 Half, 
        3: 10 Full, 
        4: 100 Half, 
        5: 100 Full, 
        6: 1G full, 
        only 'Dual Media' port have 7-11 option. 
        Dual Media port default: 7,  
        7: SFP_Auto_AMS, 
        8: 100FX_AMS, 
        9: 1000X_AMS, 
        10: 100FX, 
        11: 1000X,
        12: 10G Full. "
   ::= { gs2328PortConfigurationEntry 5 }

gs2328PortConfCurrentFlowControlRx OBJECT-TYPE
   SYNTAX      INTEGER { disable(0), enable(1), noSupport(2) }
   MAX-ACCESS  read-only
   STATUS      current
   DESCRIPTION
       "0: disable
        1: enable
        2: no support.  "
   ::= { gs2328PortConfigurationEntry 6 }

gs2328PortConfCurrentFlowControlTx OBJECT-TYPE
   SYNTAX      INTEGER { disable(0), enable(1), noSupport(2) }
   MAX-ACCESS  read-only
   STATUS      current
   DESCRIPTION
       "0: disable
        1: enable
        2: no support.  "
   ::= { gs2328PortConfigurationEntry 7 }

gs2328PortConfFlowControl OBJECT-TYPE
   SYNTAX      INTEGER { disable(0), enable(1), noSupport(2) }
   MAX-ACCESS  read-write
   STATUS      current
   DESCRIPTION
       "default: 0,
        0: disable
        1: enable
        2: no support. "
   ::= { gs2328PortConfigurationEntry 8 }

gs2328PortConfMaxFrameSize OBJECT-TYPE
   SYNTAX      Integer32 (1518..9600)
   MAX-ACCESS  read-write
   STATUS      current
   DESCRIPTION
       "default: 9600 , range : 1518 - 9600 "
   ::= { gs2328PortConfigurationEntry 9 }

gs2328PortConfExcessiveCollisionMode OBJECT-TYPE
   SYNTAX      INTEGER { discard(0), restart(1), noSupport(2) }
   MAX-ACCESS  read-write
   STATUS      current
   DESCRIPTION
       "default: 0,
        Excessive Collision Mode : 
        0: Discard,
        1: Restart, 
        2: no support.
       "
   ::= { gs2328PortConfigurationEntry 10 }

gs2328PortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy, 
        2: Dynamic (perfectReach),
        3: Enable,
        4: no support.
       "
   ::= { gs2328PortConfigurationEntry 11 }

gs2328PortConfDescription OBJECT-TYPE
   SYNTAX      DisplayString
   MAX-ACCESS  read-write
   STATUS      current
   DESCRIPTION
       " Interface specific description.
         Up to 47 characters describing this interface. "
   ::= { gs2328PortConfigurationEntry 12 }


gs2328PortTrafficStatisticsTable OBJECT-TYPE
   SYNTAX      SEQUENCE OF GS2328PortTrafficStatisticsEntry
   MAX-ACCESS  not-accessible
   STATUS      current
   DESCRIPTION
       " "
   ::= { gs2328Port 2 }

gs2328PortTrafficStatisticsEntry OBJECT-TYPE
   SYNTAX      GS2328PortTrafficStatisticsEntry
   MAX-ACCESS  not-accessible
   STATUS      current
   DESCRIPTION
       ""
   INDEX    { gs2328PortTrafficStatisticsPort  }
   ::= { gs2328PortTrafficStatisticsTable 1 }

GS2328PortTrafficStatisticsEntry ::= SEQUENCE {
   gs2328PortTrafficStatisticsPort          Integer32,
   gs2328PortTrafficStatisticsClear         INTEGER,
   gs2328PortTrafficRxPackets               Counter64,
   gs2328PortTrafficRxOctets                Counter64,
   gs2328PortTrafficRxUnicast               Counter64,
   gs2328PortTrafficRxMulticast             Counter64,
   gs2328PortTrafficRxBroadcast             Counter64,
   gs2328PortTrafficRxPause                 Counter64,
   gs2328PortTrafficRx64Bytes               Counter64,
   gs2328PortTrafficRx65to127Bytes          Counter64,
   gs2328PortTrafficRx128to255Bytes         Counter64,
   gs2328PortTrafficRx256to511Bytes         Counter64,
   gs2328PortTrafficRx512to1023Bytes        Counter64,
   gs2328PortTrafficRx1024to1526Bytes       Counter64,
   gs2328PortTrafficRxExceecd1527Bytes      Counter64,
   gs2328PortTrafficRxQ0                    Counter64,
   gs2328PortTrafficRxQ1                    Counter64,
   gs2328PortTrafficRxQ2                    Counter64,
   gs2328PortTrafficRxQ3                    Counter64,
   gs2328PortTrafficRxQ4                    Counter64,
   gs2328PortTrafficRxQ5                    Counter64,
   gs2328PortTrafficRxQ6                    Counter64,
   gs2328PortTrafficRxQ7                    Counter64,
   gs2328PortTrafficRxDrops                 Counter64,
   gs2328PortTrafficRxCRCorAlignment        Counter64,
   gs2328PortTrafficRxUndersize             Counter64,
   gs2328PortTrafficRxOversize              Counter64,
   gs2328PortTrafficRxFragments             Counter64,
   gs2328PortTrafficRxJabber                Counter64,
   gs2328PortTrafficRxFiltered              Counter64,
   gs2328PortTrafficTxPackets               Counter64,
   gs2328PortTrafficTxOctets                Counter64,
   gs2328PortTrafficTxUnicast               Counter64,
   gs2328PortTrafficTxMulticast             Counter64,
   gs2328PortTrafficTxBroadcast             Counter64,
   gs2328PortTrafficTxPause                 Counter64,
   gs2328PortTrafficTx64Bytes               Counter64,
   gs2328PortTrafficTx65to127Bytes          Counter64,
   gs2328PortTrafficTx128to255Bytes         Counter64,
   gs2328PortTrafficTx256to511Bytes         Counter64,
   gs2328PortTrafficTx512to1023Bytes        Counter64,
   gs2328PortTrafficTx1024to1526Bytes       Counter64,
   gs2328PortTrafficTxExceecd1527Bytes      Counter64,
   gs2328PortTrafficTxQ0                    Counter64,
   gs2328PortTrafficTxQ1                    Counter64,
   gs2328PortTrafficTxQ2                    Counter64,
   gs2328PortTrafficTxQ3                    Counter64,
   gs2328PortTrafficTxQ4                    Counter64,
   gs2328PortTrafficTxQ5                    Counter64,
   gs2328PortTrafficTxQ6                    Counter64,
   gs2328PortTrafficTxQ7                    Counter64,
   gs2328PortTrafficTxDrops                 Counter64,
   gs2328PortTrafficTxLateOrExcColl         Counter64
}

gs2328PortTrafficStatisticsPort OBJECT-TYPE
   SYNTAX      Integer32 (1..4095)
   MAX-ACCESS  not-accessible
   STATUS      current
   DESCRIPTION
       " "
   ::= { gs2328PortTrafficStatisticsEntry 1 }

gs2328PortTrafficStatisticsClear OBJECT-TYPE
   SYNTAX      INTEGER { disable(0), enable(1) }
   MAX-ACCESS  read-write
   STATUS      current
   DESCRIPTION
       " "
   ::= { gs2328PortTrafficStatisticsEntry 2 }

gs2328PortTrafficRxPackets OBJECT-TYPE
   SYNTAX      Counter64
   MAX-ACCESS  read-only
   STATUS      current
   DESCRIPTION
       " "
   ::= { gs2328PortTrafficStatisticsEntry 3 }

gs2328PortTrafficRxOctets OBJECT-TYPE
   SYNTAX      Counter64
   MAX-ACCESS  read-only
   STATUS      current
   DESCRIPTION
       " "
   ::= { gs2328PortTrafficStatisticsEntry 4 }

gs2328PortTrafficRxUnicast OBJECT-TYPE
   SYNTAX      Counter64
   MAX-ACCESS  read-only
   STATUS      current
   DESCRIPTION
       " "
   ::= { gs2328PortTrafficStatisticsEntry 5 }

gs2328PortTrafficRxMulticast OBJECT-TYPE
   SYNTAX      Counter64
   MAX-ACCESS  read-only
   STATUS      current
   DESCRIPTION
       " "
   ::= { gs2328PortTrafficStatisticsEntry 6 }

gs2328PortTrafficRxBroadcast OBJECT-TYPE
   SYNTAX      Counter64
   MAX-ACCESS  read-only
   STATUS      current
   DESCRIPTION
       " "
   ::= { gs2328PortTrafficStatisticsEntry 7 }

gs2328PortTrafficRxPause OBJECT-TYPE
   SYNTAX      Counter64
   MAX-ACCESS  read-only
   STATUS      current
   DESCRIPTION
       " "
   ::= { gs2328PortTrafficStatisticsEntry 8 }

gs2328PortTrafficRx64Bytes OBJECT-TYPE
   SYNTAX      Counter64
   MAX-ACCESS  read-only
   STATUS      current
   DESCRIPTION
       " "
   ::= { gs2328PortTrafficStatisticsEntry 9 }

gs2328PortTrafficRx65to127Bytes OBJECT-TYPE
   SYNTAX      Counter64
   MAX-ACCESS  read-only
   STATUS      current
   DESCRIPTION
       " "
   ::= { gs2328PortTrafficStatisticsEntry 10 }

gs2328PortTrafficRx128to255Bytes OBJECT-TYPE
   SYNTAX      Counter64
   MAX-ACCESS  read-only
   STATUS      current
   DESCRIPTION
       " "
   ::= { gs2328PortTrafficStatisticsEntry 11 }

gs2328PortTrafficRx256to511Bytes OBJECT-TYPE
   SYNTAX      Counter64
   MAX-ACCESS  read-only
   STATUS      current
   DESCRIPTION
       " "
   ::= { gs2328PortTrafficStatisticsEntry 12 }

gs2328PortTrafficRx512to1023Bytes OBJECT-TYPE
   SYNTAX      Counter64
   MAX-ACCESS  read-only
   STATUS      current
   DESCRIPTION
       " "
   ::= { gs2328PortTrafficStatisticsEntry 13 }

gs2328PortTrafficRx1024to1526Bytes OBJECT-TYPE
   SYNTAX      Counter64
   MAX-ACCESS  read-only
   STATUS      current
   DESCRIPTION
       " "
   ::= { gs2328PortTrafficStatisticsEntry 14 }

gs2328PortTrafficRxExceecd1527Bytes OBJECT-TYPE
   SYNTAX      Counter64
   MAX-ACCESS  read-only
   STATUS      current
   DESCRIPTION
       " "
   ::= { gs2328PortTrafficStatisticsEntry 15 }

gs2328PortTrafficRxQ0 OBJECT-TYPE
   SYNTAX      Counter64
   MAX-ACCESS  read-only
   STATUS      current
   DESCRIPTION
       " "
   ::= { gs2328PortTrafficStatisticsEntry 16 }

gs2328PortTrafficRxQ1 OBJECT-TYPE
   SYNTAX      Counter64
   MAX-ACCESS  read-only
   STATUS      current
   DESCRIPTION
       " "
   ::= { gs2328PortTrafficStatisticsEntry 17 }

gs2328PortTrafficRxQ2 OBJECT-TYPE
   SYNTAX      Counter64
   MAX-ACCESS  read-only
   STATUS      current
   DESCRIPTION
       " "
   ::= { gs2328PortTrafficStatisticsEntry 18 }

gs2328PortTrafficRxQ3 OBJECT-TYPE
   SYNTAX      Counter64
   MAX-ACCESS  read-only
   STATUS      current
   DESCRIPTION
       " "
   ::= { gs2328PortTrafficStatisticsEntry 19 }

gs2328PortTrafficRxQ4 OBJECT-TYPE
   SYNTAX      Counter64
   MAX-ACCESS  read-only
   STATUS      current
   DESCRIPTION
       " "
   ::= { gs2328PortTrafficStatisticsEntry 20 }

gs2328PortTrafficRxQ5 OBJECT-TYPE
   SYNTAX      Counter64
   MAX-ACCESS  read-only
   STATUS      current
   DESCRIPTION
       " "
   ::= { gs2328PortTrafficStatisticsEntry 21 }

gs2328PortTrafficRxQ6 OBJECT-TYPE
   SYNTAX      Counter64
   MAX-ACCESS  read-only
   STATUS      current
   DESCRIPTION
       " "
   ::= { gs2328PortTrafficStatisticsEntry 22 }

gs2328PortTrafficRxQ7 OBJECT-TYPE
   SYNTAX      Counter64
   MAX-ACCESS  read-only
   STATUS      current
   DESCRIPTION
       " "
   ::= { gs2328PortTrafficStatisticsEntry 23 }

gs2328PortTrafficRxDrops OBJECT-TYPE
   SYNTAX      Counter64
   MAX-ACCESS  read-only
   STATUS      current
   DESCRIPTION
       " "
   ::= { gs2328PortTrafficStatisticsEntry 24 }

gs2328PortTrafficRxCRCorAlignment OBJECT-TYPE
   SYNTAX      Counter64
   MAX-ACCESS  read-only
   STATUS      current
   DESCRIPTION
       " "
   ::= { gs2328PortTrafficStatisticsEntry 25 }

gs2328PortTrafficRxUndersize OBJECT-TYPE
   SYNTAX      Counter64
   MAX-ACCESS  read-only
   STATUS      current
   DESCRIPTION
       " "
   ::= { gs2328PortTrafficStatisticsEntry 26 }

gs2328PortTrafficRxOversize OBJECT-TYPE
   SYNTAX      Counter64
   MAX-ACCESS  read-only
   STATUS      current
   DESCRIPTION
       " "
   ::= { gs2328PortTrafficStatisticsEntry 27 }

gs2328PortTrafficRxFragments OBJECT-TYPE
   SYNTAX      Counter64
   MAX-ACCESS  read-only
   STATUS      current
   DESCRIPTION
       " "
   ::= { gs2328PortTrafficStatisticsEntry 28 }

gs2328PortTrafficRxJabber OBJECT-TYPE
   SYNTAX      Counter64
   MAX-ACCESS  read-only
   STATUS      current
   DESCRIPTION
       " "
   ::= { gs2328PortTrafficStatisticsEntry 29 }

gs2328PortTrafficRxFiltered OBJECT-TYPE
   SYNTAX      Counter64
   MAX-ACCESS  read-only
   STATUS      current
   DESCRIPTION
       " "
   ::= { gs2328PortTrafficStatisticsEntry 30 }

gs2328PortTrafficTxPackets OBJECT-TYPE
   SYNTAX      Counter64
   MAX-ACCESS  read-only
   STATUS      current
   DESCRIPTION
       " "
   ::= { gs2328PortTrafficStatisticsEntry 31 }

gs2328PortTrafficTxOctets OBJECT-TYPE
   SYNTAX      Counter64
   MAX-ACCESS  read-only
   STATUS      current
   DESCRIPTION
       " "
   ::= { gs2328PortTrafficStatisticsEntry 32 }

gs2328PortTrafficTxUnicast OBJECT-TYPE
   SYNTAX      Counter64
   MAX-ACCESS  read-only
   STATUS      current
   DESCRIPTION
       " "
   ::= { gs2328PortTrafficStatisticsEntry 33 }

gs2328PortTrafficTxMulticast OBJECT-TYPE
   SYNTAX      Counter64
   MAX-ACCESS  read-only
   STATUS      current
   DESCRIPTION
       " "
   ::= { gs2328PortTrafficStatisticsEntry 34 }

gs2328PortTrafficTxBroadcast OBJECT-TYPE
   SYNTAX      Counter64
   MAX-ACCESS  read-only
   STATUS      current
   DESCRIPTION
       " "
   ::= { gs2328PortTrafficStatisticsEntry 35 }

gs2328PortTrafficTxPause OBJECT-TYPE
   SYNTAX      Counter64
   MAX-ACCESS  read-only
   STATUS      current
   DESCRIPTION
       " "
   ::= { gs2328PortTrafficStatisticsEntry 36 }

gs2328PortTrafficTx64Bytes OBJECT-TYPE
   SYNTAX      Counter64
   MAX-ACCESS  read-only
   STATUS      current
   DESCRIPTION
       " "
   ::= { gs2328PortTrafficStatisticsEntry 37 }

gs2328PortTrafficTx65to127Bytes OBJECT-TYPE
   SYNTAX      Counter64
   MAX-ACCESS  read-only
   STATUS      current
   DESCRIPTION
       " "
   ::= { gs2328PortTrafficStatisticsEntry 38 }

gs2328PortTrafficTx128to255Bytes OBJECT-TYPE
   SYNTAX      Counter64
   MAX-ACCESS  read-only
   STATUS      current
   DESCRIPTION
       " "
   ::= { gs2328PortTrafficStatisticsEntry 39 }

gs2328PortTrafficTx256to511Bytes OBJECT-TYPE
   SYNTAX      Counter64
   MAX-ACCESS  read-only
   STATUS      current
   DESCRIPTION
       " "
   ::= { gs2328PortTrafficStatisticsEntry 40 }

gs2328PortTrafficTx512to1023Bytes OBJECT-TYPE
   SYNTAX      Counter64
   MAX-ACCESS  read-only
   STATUS      current
   DESCRIPTION
       " "
   ::= { gs2328PortTrafficStatisticsEntry 41 }

gs2328PortTrafficTx1024to1526Bytes OBJECT-TYPE
   SYNTAX      Counter64
   MAX-ACCESS  read-only
   STATUS      current
   DESCRIPTION
       " "
   ::= { gs2328PortTrafficStatisticsEntry 42 }

gs2328PortTrafficTxExceecd1527Bytes OBJECT-TYPE
   SYNTAX      Counter64
   MAX-ACCESS  read-only
   STATUS      current
   DESCRIPTION
       " "
   ::= { gs2328PortTrafficStatisticsEntry 43 }

gs2328PortTrafficTxQ0 OBJECT-TYPE
   SYNTAX      Counter64
   MAX-ACCESS  read-only
   STATUS      current
   DESCRIPTION
       " "
   ::= { gs2328PortTrafficStatisticsEntry 44 }

gs2328PortTrafficTxQ1 OBJECT-TYPE
   SYNTAX      Counter64
   MAX-ACCESS  read-only
   STATUS      current
   DESCRIPTION
       " "
   ::= { gs2328PortTrafficStatisticsEntry 45 }

gs2328PortTrafficTxQ2 OBJECT-TYPE
   SYNTAX      Counter64
   MAX-ACCESS  read-only
   STATUS      current
   DESCRIPTION
       " "
   ::= { gs2328PortTrafficStatisticsEntry 46 }

gs2328PortTrafficTxQ3 OBJECT-TYPE
   SYNTAX      Counter64
   MAX-ACCESS  read-only
   STATUS      current
   DESCRIPTION
       " "
   ::= { gs2328PortTrafficStatisticsEntry 47 }

gs2328PortTrafficTxQ4 OBJECT-TYPE
   SYNTAX      Counter64
   MAX-ACCESS  read-only
   STATUS      current
   DESCRIPTION
       " "
   ::= { gs2328PortTrafficStatisticsEntry 48 }

gs2328PortTrafficTxQ5 OBJECT-TYPE
   SYNTAX      Counter64
   MAX-ACCESS  read-only
   STATUS      current
   DESCRIPTION
       " "
   ::= { gs2328PortTrafficStatisticsEntry 49 }

gs2328PortTrafficTxQ6 OBJECT-TYPE
   SYNTAX      Counter64
   MAX-ACCESS  read-only
   STATUS      current
   DESCRIPTION
       " "
   ::= { gs2328PortTrafficStatisticsEntry 50 }


gs2328PortTrafficTxQ7 OBJECT-TYPE
   SYNTAX      Counter64
   MAX-ACCESS  read-only
   STATUS      current
   DESCRIPTION
       " "
   ::= { gs2328PortTrafficStatisticsEntry 51 }

gs2328PortTrafficTxDrops OBJECT-TYPE
   SYNTAX      Counter64
   MAX-ACCESS  read-only
   STATUS      current
   DESCRIPTION
       " "
   ::= { gs2328PortTrafficStatisticsEntry 52 }

gs2328PortTrafficTxLateOrExcColl OBJECT-TYPE
   SYNTAX      Counter64
   MAX-ACCESS  read-only
   STATUS      current
   DESCRIPTION
       " "
   ::= { gs2328PortTrafficStatisticsEntry 53 }


gs2328PortQoSStatistics                                     OBJECT IDENTIFIER ::= { gs2328Port 3 }

gs2328PortQoSStatisticsClear OBJECT-TYPE
   SYNTAX      INTEGER { none(0), clear(1) }
   MAX-ACCESS  read-only
   STATUS      current
   DESCRIPTION
       "default: 0
       0: none
       1: clear "
   ::= { gs2328PortQoSStatistics 1 }

gs2328PortQoSStatisticsTable OBJECT-TYPE
   SYNTAX      SEQUENCE OF GS2328PortQoSStatisticsEntry
   MAX-ACCESS  not-accessible
   STATUS      current
   DESCRIPTION
       " "
   ::= { gs2328PortQoSStatistics 2 }

gs2328PortQoSStatisticsEntry OBJECT-TYPE
   SYNTAX      GS2328PortQoSStatisticsEntry
   MAX-ACCESS  not-accessible
   STATUS      current
   DESCRIPTION
       ""
   INDEX    { gs2328PortQoSStatisticsPort  }
   ::= { gs2328PortQoSStatisticsTable 1 }

GS2328PortQoSStatisticsEntry ::= SEQUENCE {
   gs2328PortQoSStatisticsPort      Integer32,
   gs2328PortQoSQ0Rx                Counter64,
   gs2328PortQoSQ0Tx                Counter64,
   gs2328PortQoSQ1Rx                Counter64,
   gs2328PortQoSQ1Tx                Counter64,
   gs2328PortQoSQ2Rx                Counter64,
   gs2328PortQoSQ2Tx                Counter64,
   gs2328PortQoSQ3Rx                Counter64,
   gs2328PortQoSQ3Tx                Counter64,
   gs2328PortQoSQ4Rx                Counter64,
   gs2328PortQoSQ4Tx                Counter64,
   gs2328PortQoSQ5Rx                Counter64,
   gs2328PortQoSQ5Tx                Counter64,
   gs2328PortQoSQ6Rx                Counter64,
   gs2328PortQoSQ6Tx                Counter64,
   gs2328PortQoSQ7Rx                Counter64,
   gs2328PortQoSQ7Tx                Counter64
}

gs2328PortQoSStatisticsPort OBJECT-TYPE
   SYNTAX      Integer32(1..4095)
   MAX-ACCESS  not-accessible
   STATUS      current
   DESCRIPTION
       " "
   ::= { gs2328PortQoSStatisticsEntry 1 }

gs2328PortQoSQ0Rx OBJECT-TYPE
   SYNTAX      Counter64
   MAX-ACCESS  read-only
   STATUS      current
   DESCRIPTION
       " "
   ::= { gs2328PortQoSStatisticsEntry 2 }

gs2328PortQoSQ0Tx OBJECT-TYPE
   SYNTAX      Counter64
   MAX-ACCESS  read-only
   STATUS      current
   DESCRIPTION
       " "
   ::= { gs2328PortQoSStatisticsEntry 3 }

gs2328PortQoSQ1Rx OBJECT-TYPE
   SYNTAX      Counter64
   MAX-ACCESS  read-only
   STATUS      current
   DESCRIPTION
       " "
   ::= { gs2328PortQoSStatisticsEntry 4 }

gs2328PortQoSQ1Tx OBJECT-TYPE
   SYNTAX      Counter64
   MAX-ACCESS  read-only
   STATUS      current
   DESCRIPTION
       " "
   ::= { gs2328PortQoSStatisticsEntry 5 }

gs2328PortQoSQ2Rx OBJECT-TYPE
   SYNTAX      Counter64
   MAX-ACCESS  read-only
   STATUS      current
   DESCRIPTION
       " "
   ::= { gs2328PortQoSStatisticsEntry 6 }

gs2328PortQoSQ2Tx OBJECT-TYPE
   SYNTAX      Counter64
   MAX-ACCESS  read-only
   STATUS      current
   DESCRIPTION
       " "
   ::= { gs2328PortQoSStatisticsEntry 7 }

gs2328PortQoSQ3Rx OBJECT-TYPE
   SYNTAX      Counter64
   MAX-ACCESS  read-only
   STATUS      current
   DESCRIPTION
       " "
   ::= { gs2328PortQoSStatisticsEntry 8 }

gs2328PortQoSQ3Tx OBJECT-TYPE
   SYNTAX      Counter64
   MAX-ACCESS  read-only
   STATUS      current
   DESCRIPTION
       " "
   ::= { gs2328PortQoSStatisticsEntry 9 }

gs2328PortQoSQ4Rx OBJECT-TYPE
   SYNTAX      Counter64
   MAX-ACCESS  read-only
   STATUS      current
   DESCRIPTION
       " "
   ::= { gs2328PortQoSStatisticsEntry 10 }

gs2328PortQoSQ4Tx OBJECT-TYPE
   SYNTAX      Counter64
   MAX-ACCESS  read-only
   STATUS      current
   DESCRIPTION
       " "
   ::= { gs2328PortQoSStatisticsEntry 11 }

gs2328PortQoSQ5Rx OBJECT-TYPE
   SYNTAX      Counter64
   MAX-ACCESS  read-only
   STATUS      current
   DESCRIPTION
       " "
   ::= { gs2328PortQoSStatisticsEntry 12 }

gs2328PortQoSQ5Tx OBJECT-TYPE
   SYNTAX      Counter64
   MAX-ACCESS  read-only
   STATUS      current
   DESCRIPTION
       " "
   ::= { gs2328PortQoSStatisticsEntry 13 }

gs2328PortQoSQ6Rx OBJECT-TYPE
   SYNTAX      Counter64
   MAX-ACCESS  read-only
   STATUS      current
   DESCRIPTION
       " "
   ::= { gs2328PortQoSStatisticsEntry 14 }

gs2328PortQoSQ6Tx OBJECT-TYPE
   SYNTAX      Counter64
   MAX-ACCESS  read-only
   STATUS      current
   DESCRIPTION
       " "
   ::= { gs2328PortQoSStatisticsEntry 15 }

gs2328PortQoSQ7Rx OBJECT-TYPE
   SYNTAX      Counter64
   MAX-ACCESS  read-only
   STATUS      current
   DESCRIPTION
       " "
   ::= { gs2328PortQoSStatisticsEntry 16 }

gs2328PortQoSQ7Tx OBJECT-TYPE
   SYNTAX      Counter64
   MAX-ACCESS  read-only
   STATUS      current
   DESCRIPTION
       " "
   ::= { gs2328PortQoSStatisticsEntry 17 }

gs2328SFPInfoTable OBJECT-TYPE
   SYNTAX      SEQUENCE OF GS2328SFPInfoEntry
   MAX-ACCESS  not-accessible
   STATUS      current
   DESCRIPTION
       " "
   ::= { gs2328Port 4 }

gs2328SFPInfoEntry OBJECT-TYPE
   SYNTAX      GS2328SFPInfoEntry
   MAX-ACCESS  not-accessible
   STATUS      current
   DESCRIPTION
       ""
   INDEX    { gs2328SFPInfoIndex }
   ::= { gs2328SFPInfoTable 1 }

GS2328SFPInfoEntry ::= SEQUENCE {
   gs2328SFPInfoIndex               Integer32,
   gs2328SFPInfoPort                DisplayString,
   gs2328SFPConnectorType           DisplayString,
   gs2328SFPFiberType               DisplayString,
   gs2328SFPTxCentralWavelength     DisplayString,
   gs2328SFPBaudRate                DisplayString,
   gs2328SFPVendorOUI               DisplayString,
   gs2328SFPVendorName              DisplayString,
   gs2328SFPVendorPN                DisplayString,
   gs2328SFPVendorRev               DisplayString,
   gs2328SFPVendorSN                DisplayString,
   gs2328SFPDateCode                DisplayString,
   gs2328SFPTemperature             DisplayString,
   gs2328SFPVcc                     DisplayString,
   gs2328SFPMon1Bias                DisplayString,
   gs2328SFPMon2TxPWR               DisplayString,
   gs2328SFPMon3RxPWR               DisplayString
}

gs2328SFPInfoIndex OBJECT-TYPE
   SYNTAX      Integer32(1..4095)
   MAX-ACCESS  not-accessible
   STATUS      current
   DESCRIPTION
       " "
   ::= { gs2328SFPInfoEntry 1 }

gs2328SFPInfoPort OBJECT-TYPE
   SYNTAX      DisplayString
   MAX-ACCESS  read-only
   STATUS      current
   DESCRIPTION
       " "
   ::= { gs2328SFPInfoEntry 2 }

gs2328SFPConnectorType OBJECT-TYPE
   SYNTAX      DisplayString
   MAX-ACCESS  read-only
   STATUS      current
   DESCRIPTION
       " "
   ::= { gs2328SFPInfoEntry 3 }

gs2328SFPFiberType OBJECT-TYPE
   SYNTAX      DisplayString
   MAX-ACCESS  read-only
   STATUS      current
   DESCRIPTION
       " "
   ::= { gs2328SFPInfoEntry 4 }

gs2328SFPTxCentralWavelength OBJECT-TYPE
   SYNTAX      DisplayString
   MAX-ACCESS  read-only
   STATUS      current
   DESCRIPTION
       " "
   ::= { gs2328SFPInfoEntry 5 }

gs2328SFPBaudRate OBJECT-TYPE
   SYNTAX      DisplayString
   MAX-ACCESS  read-only
   STATUS      current
   DESCRIPTION
       " "
   ::= { gs2328SFPInfoEntry 6 }

gs2328SFPVendorOUI OBJECT-TYPE
   SYNTAX      DisplayString
   MAX-ACCESS  read-only
   STATUS      current
   DESCRIPTION
       " "
   ::= { gs2328SFPInfoEntry 7 }

gs2328SFPVendorName OBJECT-TYPE
   SYNTAX      DisplayString
   MAX-ACCESS  read-only
   STATUS      current
   DESCRIPTION
       " "
   ::= { gs2328SFPInfoEntry 8 }

gs2328SFPVendorPN OBJECT-TYPE
   SYNTAX      DisplayString
   MAX-ACCESS  read-only
   STATUS      current
   DESCRIPTION
       " "
   ::= { gs2328SFPInfoEntry 9 }

gs2328SFPVendorRev OBJECT-TYPE
   SYNTAX      DisplayString
   MAX-ACCESS  read-only
   STATUS      current
   DESCRIPTION
       " "
   ::= { gs2328SFPInfoEntry 10 }

gs2328SFPVendorSN OBJECT-TYPE
   SYNTAX      DisplayString
   MAX-ACCESS  read-only
   STATUS      current
   DESCRIPTION
       " "
   ::= { gs2328SFPInfoEntry 11 }

gs2328SFPDateCode OBJECT-TYPE
   SYNTAX      DisplayString
   MAX-ACCESS  read-only
   STATUS      current
   DESCRIPTION
       " "
   ::= { gs2328SFPInfoEntry 12 }

gs2328SFPTemperature OBJECT-TYPE
   SYNTAX      DisplayString
   MAX-ACCESS  read-only
   STATUS      current
   DESCRIPTION
       " "
   ::= { gs2328SFPInfoEntry 13 }

gs2328SFPVcc OBJECT-TYPE
   SYNTAX      DisplayString
   MAX-ACCESS  read-only
   STATUS      current
   DESCRIPTION
       " "
   ::= { gs2328SFPInfoEntry 14 }
   
gs2328SFPMon1Bias OBJECT-TYPE
   SYNTAX      DisplayString
   MAX-ACCESS  read-only
   STATUS      current
   DESCRIPTION
       " "
   ::= { gs2328SFPInfoEntry 15 }
   
gs2328SFPMon2TxPWR OBJECT-TYPE
   SYNTAX      DisplayString
   MAX-ACCESS  read-only
   STATUS      current
   DESCRIPTION
       " "
   ::= { gs2328SFPInfoEntry 16 }

gs2328SFPMon3RxPWR OBJECT-TYPE
   SYNTAX      DisplayString
   MAX-ACCESS  read-only
   STATUS      current
   DESCRIPTION
       " "
   ::= { gs2328SFPInfoEntry 17 }


gs2328VoiceVLAN                                             OBJECT IDENTIFIER ::= { gs2328Configuration 2 }

gs2328VoiceVLANConf                                         OBJECT IDENTIFIER ::= { gs2328VoiceVLAN 1 }

gs2328VoiceVLANMode OBJECT-TYPE
   SYNTAX      INTEGER { disable(0), enable(1) }
   MAX-ACCESS  read-write
   STATUS      current
   DESCRIPTION
       " Voice VLAN mode operation.
       default: 0,
       0: disable
       1: enable"
   ::= { gs2328VoiceVLANConf 1 }

gs2328VoiceVLANVLANId OBJECT-TYPE
   SYNTAX      Integer32(1..4094)
   MAX-ACCESS  read-write
   STATUS      current
   DESCRIPTION
       "Voice VLAN ID.
        default: 1000,
        range : 1-4094. "
   ::= { gs2328VoiceVLANConf 2 }

gs2328VoiceVLANAgingTime OBJECT-TYPE
   SYNTAX      Integer32(10..1000000)
   MAX-ACCESS  read-write
   STATUS      current
   DESCRIPTION
       " Voice VLAN secure learning aging time. 
         default: 86400,
         range : 10 - 10000000. "
   ::= { gs2328VoiceVLANConf 3 }

gs2328VoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2328VoiceVLANConf 4 }


gs2328VoiceVLANPortTable OBJECT-TYPE
   SYNTAX      SEQUENCE OF GS2328VoiceVLANPortEntry
   MAX-ACCESS  not-accessible
   STATUS      current
   DESCRIPTION
       " Show Voice Vlan configuration. "
   ::= { gs2328VoiceVLANConf 5 }

gs2328VoiceVLANPortEntry OBJECT-TYPE
   SYNTAX      GS2328VoiceVLANPortEntry
   MAX-ACCESS  not-accessible
   STATUS      current
   DESCRIPTION
       ""
   INDEX    { gs2328VoiceVLANPort  }
   ::= { gs2328VoiceVLANPortTable 1 }

GS2328VoiceVLANPortEntry ::= SEQUENCE {
   gs2328VoiceVLANPort                    Integer32,
   gs2328VoiceVLANPortMode                INTEGER,
   gs2328VoiceVLANPortSecurity            INTEGER,
   gs2328VoiceVLANPortDiscoveryProtocol   INTEGER
}

gs2328VoiceVLANPort OBJECT-TYPE
   SYNTAX      Integer32(1..4095)
   MAX-ACCESS  not-accessible
   STATUS      current
   DESCRIPTION
       " port, range : 1 - port number. "
   ::= { gs2328VoiceVLANPortEntry 1 }

gs2328VoiceVLANPortMode OBJECT-TYPE
   SYNTAX      INTEGER { disable(0), auto(1), forced(2) }
   MAX-ACCESS  read-write
   STATUS      current
   DESCRIPTION
       " Voice VLAN port mode.  
         default: 0,
         0: Disable (Disjoin from Voice VLAN.)
         1: Auto (Enable auto detect mode. It detects whether there is VoIP phone attached to the specific port and configures the Voice VLAN members automatically.)
         2: Forced (Force join to Voice VLAN.)"
   ::= { gs2328VoiceVLANPortEntry 2 }

gs2328VoiceVLANPortSecurity OBJECT-TYPE
   SYNTAX      INTEGER { disable(0), enable(1) }
   MAX-ACCESS  read-write
   STATUS      current
   DESCRIPTION
       " Voice VLAN port security mode. 
         default: 0,
         0: Disable (Disjoin from Voice VLAN.)
         1: enable ( Enable Voice VLAN security mode. When the function is
                     enabled, all non-telephone MAC address in Voice VLAN
                     will be blocked 10 seconds.)"
   ::= { gs2328VoiceVLANPortEntry 3 }

gs2328VoiceVLANPortDiscoveryProtocol OBJECT-TYPE
   SYNTAX      INTEGER { oui(0), lldp(1), both(2) }
   MAX-ACCESS  read-write
   STATUS      current
   DESCRIPTION
       " Voice VLAN port discovery protocol.  
         default: 0
         0: OUI (Detect telephony device by OUI address.)
         1: LLDP (Detect telephony device by LLDP.)
         2: Both (Both OUI and LLDP.) "
   ::= { gs2328VoiceVLANPortEntry 4 }

gs2328VoiceVLANSkipNAS OBJECT-TYPE
   SYNTAX      INTEGER { disable(0), enable(1) }
   MAX-ACCESS  read-write
   STATUS      current
   DESCRIPTION
       " Voice VLAN skip NAS mode. 
         default: 0,
         0: Disable (Do not skip NAS on Voice VLAN.)
         1: enable (Enable skipping of NAS on Voice VLAN. When the function is
                    enabled, authentication through the NAS module is not
                    applied to the Voice VLAN, but clients are allowed without
                    authentication.)"
   ::= { gs2328VoiceVLANPortEntry 5 }


gs2328VoiceVLANOUI                                          OBJECT IDENTIFIER ::= { gs2328VoiceVLAN 2 }

gs2328VoiceVLANOUICreate OBJECT-TYPE
   SYNTAX       INTEGER { none(0), create(1) }
   MAX-ACCESS   read-write
   STATUS       current
   DESCRIPTION
       "default: 0
        0 : None  (read only)
        1 : Create an OUI entry"
   ::= { gs2328VoiceVLANOUI 1 }

gs2328VoiceVLANOUITable OBJECT-TYPE
   SYNTAX      SEQUENCE OF GS2328VoiceVLANOUIEntry
   MAX-ACCESS  not-accessible
   STATUS      current
   DESCRIPTION
       " Create Voice VLAN OUI entry. Modify OUI table will
         restart auto detect OUI process. "
   ::= { gs2328VoiceVLANOUI 2 }

gs2328VoiceVLANOUIEntry OBJECT-TYPE
   SYNTAX      GS2328VoiceVLANOUIEntry
   MAX-ACCESS  not-accessible
   STATUS      current
   DESCRIPTION
       ""
   INDEX    { gs2328VoiceVLANOUIIndex  }
   ::= { gs2328VoiceVLANOUITable 1 }

GS2328VoiceVLANOUIEntry ::= SEQUENCE {
   gs2328VoiceVLANOUIIndex         Integer32,
   gs2328VoiceVLANTelephonyOUI     OCTET STRING,
   gs2328VoiceVLANDescription      DisplayString,
   gs2328VoiceVLANOUIRowStatus     INTEGER
}

gs2328VoiceVLANOUIIndex OBJECT-TYPE
   SYNTAX      Integer32(1..16)
   MAX-ACCESS  not-accessible
   STATUS      current
   DESCRIPTION
       " "
   ::= { gs2328VoiceVLANOUIEntry 1 }

gs2328VoiceVLANTelephonyOUI OBJECT-TYPE
   SYNTAX      OCTET STRING (SIZE (1..32))
   MAX-ACCESS  read-write
   STATUS      current
   DESCRIPTION
       "OUI address, format : 0a 1b 2c "
   ::= { gs2328VoiceVLANOUIEntry 2 }

gs2328VoiceVLANDescription OBJECT-TYPE
   SYNTAX      DisplayString (SIZE (1..32))
   MAX-ACCESS  read-write
   STATUS      current
   DESCRIPTION
       " Up to 32 characters describing OUI address. "
   ::= { gs2328VoiceVLANOUIEntry 3 }

gs2328VoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2328VoiceVLANOUIEntry 4 }

gs2328GARP                                                   OBJECT IDENTIFIER ::= { gs2328Configuration 3 }

gs2328GARPConfTable OBJECT-TYPE
   SYNTAX      SEQUENCE OF GS2328GARPConfEntry
   MAX-ACCESS  not-accessible
   STATUS      current
   DESCRIPTION
       " "
   ::= { gs2328GARP 1 }

gs2328GARPConfEntry OBJECT-TYPE
   SYNTAX      GS2328GARPConfEntry
   MAX-ACCESS  not-accessible
   STATUS      current
   DESCRIPTION
       ""
   INDEX    { gs2328GARPConfPort  }
   ::= { gs2328GARPConfTable 1 }

GS2328GARPConfEntry ::= SEQUENCE {
   gs2328GARPConfPort           Integer32,
   gs2328GARPJoinTimer          Integer32,
   gs2328GARPLeaveTimer         Integer32,
   gs2328GARPLeaveAllTimer      Integer32,
   gs2328GARPApplicantion       INTEGER,
   gs2328GARPAttributeType      INTEGER,
   gs2328GARPApplicant          INTEGER
}

gs2328GARPConfPort OBJECT-TYPE
   SYNTAX      Integer32(1..4095)
   MAX-ACCESS  not-accessible
   STATUS      current
   DESCRIPTION
       " "
   ::= { gs2328GARPConfEntry 1 }

gs2328GARPJoinTimer OBJECT-TYPE
   SYNTAX      Integer32(200..1000)
   MAX-ACCESS  read-write
   STATUS      current
   DESCRIPTION
       "default: 200, range : 200 - 1000 "
   ::= { gs2328GARPConfEntry 2 }

gs2328GARPLeaveTimer OBJECT-TYPE
   SYNTAX      Integer32(600..3000)
   MAX-ACCESS  read-write
   STATUS      current
   DESCRIPTION
       "default: 600 , range : 600 - 3000"
   ::= { gs2328GARPConfEntry 3 }

gs2328GARPLeaveAllTimer OBJECT-TYPE
   SYNTAX      Integer32(10000..50000)
   MAX-ACCESS  read-write
   STATUS      current
   DESCRIPTION
       "default: 10000, range : 10000 - 50000 "
   ::= { gs2328GARPConfEntry 4 }

gs2328GARPApplicantion OBJECT-TYPE
   SYNTAX      INTEGER { gvrp(1)}
   MAX-ACCESS  read-write
   STATUS      current
   DESCRIPTION
       "default: 1
       1: GVRP"
   ::= { gs2328GARPConfEntry 5 }

gs2328GARPAttributeType OBJECT-TYPE
   SYNTAX      INTEGER { vlan(1)}
   MAX-ACCESS  read-write
   STATUS      current
   DESCRIPTION
       "default: 1
       1: VLAN"
   ::= { gs2328GARPConfEntry 6 }

gs2328GARPApplicant OBJECT-TYPE
   SYNTAX      INTEGER { participant(0), nonParticipant(1) }
   MAX-ACCESS  read-write
   STATUS      current
   DESCRIPTION
       "default: 0
       0: normal-participant
       1: non-participant"
   ::= { gs2328GARPConfEntry 7 }

gs2328GARPStatisticsTable OBJECT-TYPE
   SYNTAX      SEQUENCE OF GS2328GARPStatisticsEntry
   MAX-ACCESS  not-accessible
   STATUS      current
   DESCRIPTION
       " Show the basic GARP port statistics. "
   ::= { gs2328GARP 2 }

gs2328GARPStatisticsEntry OBJECT-TYPE
   SYNTAX      GS2328GARPStatisticsEntry
   MAX-ACCESS  not-accessible
   STATUS      current
   DESCRIPTION
       ""
   INDEX    { gs2328GARPStatisticsPort  }
   ::= { gs2328GARPStatisticsTable 1 }

GS2328GARPStatisticsEntry ::= SEQUENCE {
   gs2328GARPStatisticsPort             Integer32,
   gs2328GARPStatisticsPeerMAC          DisplayString,
   gs2328GARPStatisticsFailedCount      Counter32
}

gs2328GARPStatisticsPort OBJECT-TYPE
   SYNTAX      Integer32(1..4095)
   MAX-ACCESS  not-accessible
   STATUS      current
   DESCRIPTION
       " port, range : 1 - port number. "
   ::= { gs2328GARPStatisticsEntry 1 }

gs2328GARPStatisticsPeerMAC OBJECT-TYPE
   SYNTAX      DisplayString
   MAX-ACCESS  read-only
   STATUS      current
   DESCRIPTION
       " Peer MAC is MAC address of the neighbour Switch from with GARP frame is received.  "
   ::= { gs2328GARPStatisticsEntry 2 }

gs2328GARPStatisticsFailedCount OBJECT-TYPE
   SYNTAX      Counter32
   MAX-ACCESS  read-only
   STATUS      current
   DESCRIPTION
       " explain Failed count here. "
   ::= { gs2328GARPStatisticsEntry 3 }

gs2328GVRP                                                   OBJECT IDENTIFIER ::= { gs2328Configuration 4 }

gs2328GVRPConf                                                   OBJECT IDENTIFIER ::= { gs2328GVRP 1 }

gs2328GVRPMode OBJECT-TYPE
   SYNTAX      INTEGER { disable(0), enable(1) }
   MAX-ACCESS  read-write
   STATUS      current
   DESCRIPTION
       "default: 0,
        0: disable, 
        1: enable. "
   ::= { gs2328GVRPConf 1 }

gs2328GVRPConfTable OBJECT-TYPE
   SYNTAX      SEQUENCE OF GS2328GVRPConfEntry
   MAX-ACCESS  not-accessible
   STATUS      current
   DESCRIPTION
       " "
   ::= { gs2328GVRPConf 2 }

gs2328GVRPConfEntry OBJECT-TYPE
   SYNTAX      GS2328GVRPConfEntry
   MAX-ACCESS  not-accessible
   STATUS      current
   DESCRIPTION
       ""
   INDEX    { gs2328GVRPConfPort  }
   ::= { gs2328GVRPConfTable 1 }

GS2328GVRPConfEntry ::= SEQUENCE {
   gs2328GVRPConfPort           Integer32,
   gs2328GVRPConfPortMode       INTEGER,
   gs2328GVRPConfPortRRole      INTEGER
}

gs2328GVRPConfPort OBJECT-TYPE
   SYNTAX      Integer32(1..4095)
   MAX-ACCESS  not-accessible
   STATUS      current
   DESCRIPTION
       " "
   ::= { gs2328GVRPConfEntry 1 }

gs2328GVRPConfPortMode OBJECT-TYPE
   SYNTAX      INTEGER { disable(0), enable(1) }
   MAX-ACCESS  read-write
   STATUS      current
   DESCRIPTION
       "default: 0
       1: enable
       0: disable"
   ::= { gs2328GVRPConfEntry 2 }

gs2328GVRPConfPortRRole OBJECT-TYPE
   SYNTAX      INTEGER { disable(0), enable(1) }
   MAX-ACCESS  read-write
   STATUS      current
   DESCRIPTION
       "default: 0
       1: enable
       0: disable"
   ::= { gs2328GVRPConfEntry 3 }

gs2328GVRPStatisticsTable OBJECT-TYPE
   SYNTAX      SEQUENCE OF GS2328GVRPStatisticsEntry
   MAX-ACCESS  not-accessible
   STATUS      current
   DESCRIPTION
       " "
   ::= { gs2328GVRP 2 }

gs2328GVRPStatisticsEntry OBJECT-TYPE
   SYNTAX      GS2328GVRPStatisticsEntry
   MAX-ACCESS  not-accessible
   STATUS      current
   DESCRIPTION
       ""
   INDEX    { gs2328GVRPStatisticsPort  }
   ::= { gs2328GVRPStatisticsTable 1 }

GS2328GVRPStatisticsEntry ::= SEQUENCE {
   gs2328GVRPStatisticsPort         Integer32,
   gs2328GVRPStatisticsJoinTxCnt    Counter32,
   gs2328GVRPStatisticsLeaveTxCnt   Counter32
}

gs2328GVRPStatisticsPort OBJECT-TYPE
   SYNTAX      Integer32(1..4095)
   MAX-ACCESS  not-accessible
   STATUS      current
   DESCRIPTION
       " "
   ::= { gs2328GVRPStatisticsEntry 1 }

gs2328GVRPStatisticsJoinTxCnt OBJECT-TYPE
   SYNTAX      Counter32
   MAX-ACCESS  read-only
   STATUS      current
   DESCRIPTION
       ""
   ::= { gs2328GVRPStatisticsEntry 2 }

gs2328GVRPStatisticsLeaveTxCnt OBJECT-TYPE
   SYNTAX      Counter32
   MAX-ACCESS  read-only
   STATUS      current
   DESCRIPTION
       ""
   ::= { gs2328GVRPStatisticsEntry 3 }


gs2328Mirroring                                             OBJECT IDENTIFIER ::= { gs2328Configuration 6 }

gs2328PortToMirrorOn OBJECT-TYPE
   SYNTAX      Integer32(0..10)
   MAX-ACCESS  read-write
   STATUS      current
   DESCRIPTION
       "default: 0 
        0: disable,
        range : 1 - port number. "
   ::= { gs2328Mirroring 1 }

gs2328MirrorTable OBJECT-TYPE
   SYNTAX      SEQUENCE OF GS2328MirrorEntry
   MAX-ACCESS  not-accessible
   STATUS      current
   DESCRIPTION
       " "
   ::= { gs2328Mirroring 2 }

gs2328MirrorEntry OBJECT-TYPE
   SYNTAX      GS2328MirrorEntry
   MAX-ACCESS  not-accessible
   STATUS      current
   DESCRIPTION
       ""
   INDEX    { gs2328MirrorPort  }
   ::= { gs2328MirrorTable 1 }

GS2328MirrorEntry ::= SEQUENCE {
   gs2328MirrorPort		Integer32,
   gs2328MirrorMode		INTEGER
}

gs2328MirrorPort OBJECT-TYPE
   SYNTAX      Integer32(1..4095)
   MAX-ACCESS  not-accessible
   STATUS      current
   DESCRIPTION
       " "
   ::= { gs2328MirrorEntry 1 }

gs2328MirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2328MirrorEntry 2 }

gs2328TrapEventSeverity                                             OBJECT IDENTIFIER ::= { gs2328Configuration 7 }

gs2328TrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 1 }

gs2328TrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2328TrapEventSeverity 2 }

gs2328TrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 3 }

gs2328TrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328TrapEventSeverity 4 }

gs2328TrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328TrapEventSeverity 5 }

gs2328TrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 6 }

gs2328TrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 7 }

gs2328TrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 8 }

gs2328TrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 9 }

gs2328TrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328TrapEventSeverity 10 }

gs2328TrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 11 }

gs2328TrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 12 }

gs2328TrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 13 }

gs2328TrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 14 }

gs2328TrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2328TrapEventSeverity 15 }

gs2328TrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 16 }

gs2328TrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 17 }

gs2328TrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 18 }

gs2328TrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328TrapEventSeverity 20 }

gs2328TrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328TrapEventSeverity 21 }



gs2328TrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328TrapEventSeverity 25 }

gs2328TrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328TrapEventSeverity 27 }
   
gs2328TrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328TrapEventSeverity 28 }

gs2328SMTP                                             OBJECT IDENTIFIER ::= { gs2328Configuration 8 }

gs2328SMTPMailServer OBJECT-TYPE
   SYNTAX      DisplayString
   MAX-ACCESS  read-write
   STATUS      current
   DESCRIPTION
       " Up to 47 characters describing email server. "
   ::= { gs2328SMTP 1 }

gs2328SMTPUserName OBJECT-TYPE
   SYNTAX      DisplayString
   MAX-ACCESS  read-write
   STATUS      current
   DESCRIPTION
       " Up to 47 characters describing user name. "
   ::= { gs2328SMTP 2 }

gs2328SMTPPassword OBJECT-TYPE
   SYNTAX      DisplayString
   MAX-ACCESS  read-write
   STATUS      current
   DESCRIPTION
       " Up to 47 characters describing password. "
   ::= { gs2328SMTP 3 }

gs2328SMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2328SMTP 4 }

gs2328SMTPSender OBJECT-TYPE
   SYNTAX      DisplayString
   MAX-ACCESS  read-write
   STATUS      current
   DESCRIPTION
       " Up to 47 characters describing sender. "
   ::= { gs2328SMTP 5 }

gs2328SMTPReturnPath OBJECT-TYPE
   SYNTAX      DisplayString
   MAX-ACCESS  read-write
   STATUS      current
   DESCRIPTION
       " Up to 47 characters describing return path. "
   ::= { gs2328SMTP 6 }

gs2328SMTPEmailAddress1 OBJECT-TYPE
   SYNTAX      DisplayString
   MAX-ACCESS  read-write
   STATUS      current
   DESCRIPTION
       " Up to 47 characters describing mail address. "
   ::= { gs2328SMTP 7 }

gs2328SMTPEmailAddress2 OBJECT-TYPE
   SYNTAX      DisplayString
   MAX-ACCESS  read-write
   STATUS      current
   DESCRIPTION
       " Up to 47 characters describing mail address. "
   ::= { gs2328SMTP 8 }

gs2328SMTPEmailAddress3 OBJECT-TYPE
   SYNTAX      DisplayString
   MAX-ACCESS  read-write
   STATUS      current
   DESCRIPTION
       " Up to 47 characters describing mail address. "
   ::= { gs2328SMTP 9 }

gs2328SMTPEmailAddress4 OBJECT-TYPE
   SYNTAX      DisplayString
   MAX-ACCESS  read-write
   STATUS      current
   DESCRIPTION
       " Up to 47 characters describing mail address. "
   ::= { gs2328SMTP 10 }

gs2328SMTPEmailAddress5 OBJECT-TYPE
   SYNTAX      DisplayString
   MAX-ACCESS  read-write
   STATUS      current
   DESCRIPTION
       " Up to 47 characters describing mail address. "
   ::= { gs2328SMTP 11 }

gs2328SMTPEmailAddress6 OBJECT-TYPE
   SYNTAX      DisplayString
   MAX-ACCESS  read-write
   STATUS      current
   DESCRIPTION
       " Up to 47 characters describing mail address. "
   ::= { gs2328SMTP 12 }


gs2328ACL                                                   OBJECT IDENTIFIER ::= { gs2328Configuration 9 }

gs2328ACLPortsConfTable OBJECT-TYPE
   SYNTAX      SEQUENCE OF GS2328ACLPortsConfEntry
   MAX-ACCESS  not-accessible
   STATUS      current
   DESCRIPTION
       " "
   ::= { gs2328ACL 1 }

gs2328ACLPortsConfEntry OBJECT-TYPE
   SYNTAX      GS2328ACLPortsConfEntry
   MAX-ACCESS  not-accessible
   STATUS      current
   DESCRIPTION
       ""
   INDEX    { gs2328ACLPortsConfPort  }
   ::= { gs2328ACLPortsConfTable 1 }

GS2328ACLPortsConfEntry ::= SEQUENCE {
   gs2328ACLPortsConfPort               Integer32,
   gs2328ACLPortsConfPolicyID           Integer32,
   gs2328ACLPortsConfAction             INTEGER,
   gs2328ACLPortsConfRateLimiterID      Integer32,
   gs2328ACLPortsConfPortRedirect       Integer32,
   gs2328ACLPortsConfMirror             INTEGER,
   gs2328ACLPortsConfLogging            INTEGER,
   gs2328ACLPortsConfShutdown           INTEGER,
   gs2328ACLPortsConfState              INTEGER,
   gs2328ACLPortsConfCounter            Counter32
}

gs2328ACLPortsConfPort OBJECT-TYPE
   SYNTAX      Integer32 (1..4095)
   MAX-ACCESS  not-accessible
   STATUS      current
   DESCRIPTION
       " "
   ::= { gs2328ACLPortsConfEntry 1 }

gs2328ACLPortsConfPolicyID OBJECT-TYPE
   SYNTAX      Integer32 (0..255)
   MAX-ACCESS  read-write
   STATUS      current
   DESCRIPTION
       "default: 0, range : 0 - 255 "
   ::= { gs2328ACLPortsConfEntry 2 }

gs2328ACLPortsConfAction OBJECT-TYPE
   SYNTAX      INTEGER { deny(0), permit(1) }
   MAX-ACCESS  read-write
   STATUS      current
   DESCRIPTION
       "default: 1,
        0: Deny
        1: Permit"
   ::= { gs2328ACLPortsConfEntry 3 }

gs2328ACLPortsConfRateLimiterID OBJECT-TYPE
   SYNTAX      Integer32 (0..12)
   MAX-ACCESS  read-write
   STATUS      current
   DESCRIPTION
       "default: 0,
        0: Disable
        range : 0 - 12 "
   ::= { gs2328ACLPortsConfEntry 4 }

gs2328ACLPortsConfPortRedirect OBJECT-TYPE
   SYNTAX      Integer32 (0..4095)
   MAX-ACCESS  read-write
   STATUS      current
   DESCRIPTION
       "default: 0
        0: Disable
        range : 0 - end port number "
   ::= { gs2328ACLPortsConfEntry 5 }

gs2328ACLPortsConfMirror OBJECT-TYPE
   SYNTAX      INTEGER { disable(0), enable(1) }
   MAX-ACCESS  read-write
   STATUS      current
   DESCRIPTION
       "default: 0
        0: Disable
        1: Enable "
   ::= { gs2328ACLPortsConfEntry 6 }

gs2328ACLPortsConfLogging OBJECT-TYPE
   SYNTAX      INTEGER { disable(0), enable(1) }
   MAX-ACCESS  read-write
   STATUS      current
   DESCRIPTION
       "default: 0
        0: Disable
        1: Enable "
   ::= { gs2328ACLPortsConfEntry 7 }

gs2328ACLPortsConfShutdown OBJECT-TYPE
   SYNTAX      INTEGER { disable(0), enable(1) }
   MAX-ACCESS  read-write
   STATUS      current
   DESCRIPTION
       "default: 0
        0: Disable
        1: Enable "
   ::= { gs2328ACLPortsConfEntry 8 }
   
gs2328ACLPortsConfState OBJECT-TYPE
   SYNTAX      INTEGER { disable(0), enable(1) }
   MAX-ACCESS  read-write
   STATUS      current
   DESCRIPTION
       "default: 1
        0: Disable
        1: Enable "
   ::= { gs2328ACLPortsConfEntry 9 }

gs2328ACLPortsConfCounter OBJECT-TYPE
   SYNTAX      Counter32
   MAX-ACCESS  read-only
   STATUS      current
   DESCRIPTION
       "Counts the number of frames that match this ACE. "
   ::= { gs2328ACLPortsConfEntry 10 }


gs2328ACLRateLimiterTable OBJECT-TYPE
   SYNTAX      SEQUENCE OF GS2328ACLRateLimiterEntry
   MAX-ACCESS  not-accessible
   STATUS      current
   DESCRIPTION
       " "
   ::= { gs2328ACL 2 }

gs2328ACLRateLimiterEntry OBJECT-TYPE
   SYNTAX      GS2328ACLRateLimiterEntry
   MAX-ACCESS  not-accessible
   STATUS      current
   DESCRIPTION
       ""
   INDEX    { gs2328ACLRateLimiterID  }
   ::= { gs2328ACLRateLimiterTable 1 }

GS2328ACLRateLimiterEntry ::= SEQUENCE {
   gs2328ACLRateLimiterID       Integer32,
   gs2328ACLRateLimiterUnit     INTEGER,
   gs2328ACLRateLimiterRate     Integer32
}

gs2328ACLRateLimiterID OBJECT-TYPE
   SYNTAX      Integer32 (1..12)
   MAX-ACCESS  not-accessible
   STATUS      current
   DESCRIPTION
       " Rate Limiter ID.
         range : 1-12 "
   ::= { gs2328ACLRateLimiterEntry 1 }

gs2328ACLRateLimiterUnit OBJECT-TYPE
   SYNTAX      INTEGER { pps(0), kbps(1) }
   MAX-ACCESS  read-write
   STATUS      current
   DESCRIPTION
       "default: 0, 
        0: pps
        1: kbps"
   ::= { gs2328ACLRateLimiterEntry 2 }

gs2328ACLRateLimiterRate OBJECT-TYPE
   SYNTAX      Integer32(0..3276700)
   MAX-ACCESS  read-write
   STATUS      current
   DESCRIPTION
       "default: 1, 
        range : <0-3276700> pps
                <0-10000> kbps"
   ::= { gs2328ACLRateLimiterEntry 3 }


gs2328ACLACE                                          OBJECT IDENTIFIER ::= { gs2328ACL 3 }

gs2328ACLACECreate OBJECT-TYPE
   SYNTAX       INTEGER { none(0), create(1) }
   MAX-ACCESS   read-write
   STATUS       current
   DESCRIPTION
       "default: 0
        0 : None  (read only)
        1 : Create an ACE entry"
   ::= { gs2328ACLACE 1 }

gs2328ACLACETable OBJECT-TYPE
   SYNTAX      SEQUENCE OF GS2328ACLACEEntry
   MAX-ACCESS  not-accessible
   STATUS      current
   DESCRIPTION
       " Create ACL ACE entry. "
   ::= { gs2328ACLACE 2 }

gs2328ACLACEEntry OBJECT-TYPE
   SYNTAX      GS2328ACLACEEntry
   MAX-ACCESS  not-accessible
   STATUS      current
   DESCRIPTION
       ""
   INDEX    { gs2328ACLACEIndex  }
   ::= { gs2328ACLACETable 1 }

GS2328ACLACEEntry ::= SEQUENCE {
   gs2328ACLACEIndex                Integer32,
   gs2328ACLACEID                   Integer32,
   gs2328ACLACENextID               Integer32,
   gs2328ACLACEIngressPort          DisplayString,
   gs2328ACLACEPortPolicyNumber     Integer32,
   
   gs2328ACLACEPortPolicyBitmask    Integer32,
   gs2328ACLACEFrameType            INTEGER,
   gs2328ACLACEAction               INTEGER,
   gs2328ACLACEDenyPortRedirect     DisplayString,
   gs2328ACLACELogging              INTEGER,
   
   gs2328ACLACEMirror               INTEGER,
   gs2328ACLACERateLimiter          Integer32,
   gs2328ACLACEShutdown             INTEGER,
   gs2328ACLACEVLAN8021QTagged      INTEGER,
   gs2328ACLACEVLANTagPriority      Integer32,
   
   gs2328ACLACEVLANVID              Integer32,
   gs2328ACLACEEtherType            Integer32,
   gs2328ACLACESMAC                 DisplayString,
   gs2328ACLACEDMACType             INTEGER,
   gs2328ACLACEDMAC                 DisplayString,
   
   gs2328ACLACEArpOpcode            INTEGER,
   gs2328ACLACEArpFlagsRequestReply INTEGER,
   gs2328ACLACEArpFlagsArpSmac      INTEGER,
   gs2328ACLACEArpFlagsRarpDmac     INTEGER,
   gs2328ACLACEArpFlagsLength       INTEGER,
   
   gs2328ACLACEArpFlagsIp           INTEGER,
   gs2328ACLACEArpFlagsEthernet     INTEGER,
   gs2328ACLACESIPType              INTEGER,
   gs2328ACLACESIPIPAddress         IpAddress,                      
   gs2328ACLACESIPNetworkPrefix     Integer32,
   
   gs2328ACLACEDIPType              INTEGER,
   gs2328ACLACEDIPIPAddress         IpAddress,                      
   gs2328ACLACEDIPNetworkPrefix     Integer32,
   
   gs2328ACLACEIPProtocol           Integer32,
   gs2328ACLACEIPFlagsTTL           INTEGER,
   gs2328ACLACEIPFlagsOptions       INTEGER,
   gs2328ACLACEIPFlagsFragment      INTEGER,
   gs2328ACLACEICMPType             Integer32,
   
   gs2328ACLACEICMPCode             Integer32,
   gs2328ACLACESourcePortMin        Integer32,
   gs2328ACLACESourcePortMax        Integer32,
   gs2328ACLACEDestPortMin          Integer32,
   gs2328ACLACEDestPortMax          Integer32,
   
   gs2328ACLACETCPFlagsFin          INTEGER,
   gs2328ACLACETCPFlagsSyn          INTEGER,
   gs2328ACLACETCPFlagsRst          INTEGER,
   gs2328ACLACETCPFlagsPsh          INTEGER,
   gs2328ACLACETCPFlagsAck          INTEGER,
   
   gs2328ACLACETCPFlagsUrg          INTEGER,
   
   gs2328ACLACERowStatus            INTEGER
}

gs2328ACLACEIndex OBJECT-TYPE
   SYNTAX      Integer32(1..256)
   MAX-ACCESS  not-accessible
   STATUS      current
   DESCRIPTION
       " "
   ::= { gs2328ACLACEEntry 1 }

gs2328ACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2328ACLACEEntry 2 }

gs2328ACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2328ACLACEEntry 3 }

gs2328ACLACEIngressPort OBJECT-TYPE
   SYNTAX      DisplayString
   MAX-ACCESS  read-write
   STATUS      current
   DESCRIPTION
       " Indicates the ingress port of the ACE. Possible values are: 
         All: The ACE will match all ingress port. 
         Port: The ACE will match a specific ingress port.Format: 1,3,6."
   ::= { gs2328ACLACEEntry 4 }

gs2328ACLACEPortPolicyNumber OBJECT-TYPE
   SYNTAX      Integer32(0..255)
   MAX-ACCESS  read-write
   STATUS      current
   DESCRIPTION
       " policy value.
         range : 0 - 255. "
   ::= { gs2328ACLACEEntry 5 }
   
gs2328ACLACEPortPolicyBitmask OBJECT-TYPE
   SYNTAX      Integer32(0..255)
   MAX-ACCESS  read-write
   STATUS      current
   DESCRIPTION
       " policy bitmask.
         range : 0 - 255(0xff). "
   ::= { gs2328ACLACEEntry 6 }

gs2328ACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2328ACLACEEntry 7 }

gs2328ACLACEAction OBJECT-TYPE
   SYNTAX      INTEGER { deny(0), permit(1) }
   MAX-ACCESS  read-write
   STATUS      current
   DESCRIPTION
       "default: 1,
        0: Deny
        1: Permit"
   ::= { gs2328ACLACEEntry 8 }

gs2328ACLACEDenyPortRedirect OBJECT-TYPE
   SYNTAX      DisplayString
   MAX-ACCESS  read-write
   STATUS      current
   DESCRIPTION
       " Frames that hit the ACE are redirected to the port number specified here.  
         Disabled: indicates that the port redirect operation is disabled. 
         Port Format: 1,3,6."
   ::= { gs2328ACLACEEntry 9 }

gs2328ACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2328ACLACEEntry 10 }

gs2328ACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { gs2328ACLACEEntry 11 }

gs2328ACLACERateLimiter OBJECT-TYPE
   SYNTAX      Integer32(0..12)
   MAX-ACCESS  read-write
   STATUS      current
   DESCRIPTION
       "default: 0,
        0: Disable
        range : 0 - 12 "
   ::= { gs2328ACLACEEntry 12 }

gs2328ACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2328ACLACEEntry 13 }

gs2328ACLACEVLAN8021QTagged OBJECT-TYPE
   SYNTAX      INTEGER { disable(0), enable(1), any(2) }
   MAX-ACCESS  read-write
   STATUS      current
   DESCRIPTION
       "Specify whether frames can hit the action according to the 802.1Q tagged. 
        default: 2,
        0: disable - Untagged frame only.
        1: enable - Tagged frame only.
        2: Any - Any value is allowed. "
   ::= { gs2328ACLACEEntry 14 }

gs2328ACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2328ACLACEEntry 15 }

gs2328ACLACEVLANVID OBJECT-TYPE
   SYNTAX      Integer32(0..4094)
   MAX-ACCESS  read-write
   STATUS      current
   DESCRIPTION
       "Specify the VLAN ID filter for this ACE.
        The vid can't be set when 802.1Q Tagged is disabled. 
        default: 0,
        0: Any - No VLAN ID filter is specified.
        range : 0 - 4094 "
   ::= { gs2328ACLACEEntry 16 }

gs2328ACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2328ACLACEEntry 17 }

gs2328ACLACESMAC OBJECT-TYPE
   SYNTAX      DisplayString
   MAX-ACCESS  read-write
   STATUS      current
   DESCRIPTION
       " Configure source MAC address for this ACE.
         <mac-address>: A frame that hits this ACE matches this source MAC address value. 
         Any: Don't care."
   ::= { gs2328ACLACEEntry 18 }

gs2328ACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { gs2328ACLACEEntry 19 }

gs2328ACLACEDMAC OBJECT-TYPE
   SYNTAX      DisplayString
   MAX-ACCESS  read-write
   STATUS      current
   DESCRIPTION
       " Configure destination MAC address for this ACE. 
         <mac-address>: A frame that hits this ACE matches this destination MAC address value.            
         Any: Don't care.
         Broadcast: Frame must be broadcast.
         Unicast: Frame must be unicast.
         Multicast: Frame must be multicast. "
   ::= { gs2328ACLACEEntry 20 }

gs2328ACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2328ACLACEEntry 21 }

gs2328ACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2328ACLACEEntry 22 }

gs2328ACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2328ACLACEEntry 23 }   

gs2328ACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2328ACLACEEntry 24 }

gs2328ACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2328ACLACEEntry 25 }

gs2328ACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2328ACLACEEntry 26 }

gs2328ACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2328ACLACEEntry 27 }
   
gs2328ACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { gs2328ACLACEEntry 28 }   
   
gs2328ACLACESIPIPAddress OBJECT-TYPE
   SYNTAX      IpAddress
   MAX-ACCESS  read-write
   STATUS      current
   DESCRIPTION
       "A frame that hits this ACE matches this source IP address value."
   ::= { gs2328ACLACEEntry 29 }      
   
gs2328ACLACESIPNetworkPrefix OBJECT-TYPE
   SYNTAX      Integer32(0..32)
   MAX-ACCESS  read-write
   STATUS      current
   DESCRIPTION
       "Network prefix.
        default: 32,
        0: No data.
        range : 1 - 32"
   ::= { gs2328ACLACEEntry 30 }   
   

gs2328ACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2328ACLACEEntry 32 }   
   
gs2328ACLACEDIPIPAddress OBJECT-TYPE
   SYNTAX      IpAddress
   MAX-ACCESS  read-write
   STATUS      current
   DESCRIPTION
       "A frame that hits this ACE matches this destination IP address value."
   ::= { gs2328ACLACEEntry 33 }      
   
gs2328ACLACEDIPNetworkPrefix OBJECT-TYPE
   SYNTAX      Integer32(0..32)
   MAX-ACCESS  read-write
   STATUS      current
   DESCRIPTION
       "Network prefix.
        default: 32,
        0: No data.
        range : 1 - 32"
   ::= { gs2328ACLACEEntry 34 }  
   
   
gs2328ACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { gs2328ACLACEEntry 36 } 

gs2328ACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2328ACLACEEntry 37 }   
   
gs2328ACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2328ACLACEEntry 38 }

gs2328ACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2328ACLACEEntry 39 }

gs2328ACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { gs2328ACLACEEntry 40 }   

gs2328ACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2328ACLACEEntry 41 } 

gs2328ACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2328ACLACEEntry 42 }     
   
gs2328ACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2328ACLACEEntry 43 } 
      
gs2328ACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { gs2328ACLACEEntry 44 }     

gs2328ACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { gs2328ACLACEEntry 45 }

gs2328ACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2328ACLACEEntry 46 }

gs2328ACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2328ACLACEEntry 47 }

gs2328ACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2328ACLACEEntry 48 }

gs2328ACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2328ACLACEEntry 49 }

gs2328ACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2328ACLACEEntry 50 }

gs2328ACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2328ACLACEEntry 51 }

gs2328ACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2328ACLACEEntry 66 }


gs2328ACLACEClear OBJECT-TYPE
   SYNTAX       INTEGER { noAction(0), clear(1) }
   MAX-ACCESS   read-write
   STATUS       current
   DESCRIPTION
       "default: 0
        0 : No action
        1 : Clear all ACL counters."
   ::= { gs2328ACLACE 3 }

gs2328ACLACEMoveACEID OBJECT-TYPE
   SYNTAX       Integer32(0..256)
   MAX-ACCESS   read-write
   STATUS       current
   DESCRIPTION
       "Move ACE,
        default: 0
        ACE ID must be exist.
        range : 1 - 256."
   ::= { gs2328ACLACE 4 }

gs2328ACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2328ACLACE 5 }

gs2328ACLACEStatusTable OBJECT-TYPE
   SYNTAX      SEQUENCE OF GS2328ACLACEStatusEntry
   MAX-ACCESS  not-accessible
   STATUS      current
   DESCRIPTION
       " ACL ACE Status entry. "
   ::= { gs2328ACLACE 6 }

gs2328ACLACEStatusEntry OBJECT-TYPE
   SYNTAX      GS2328ACLACEStatusEntry
   MAX-ACCESS  not-accessible
   STATUS      current
   DESCRIPTION
       ""
   INDEX    { gs2328ACLACEStatusIndex  }
   ::= { gs2328ACLACEStatusTable 1 }

GS2328ACLACEStatusEntry ::= SEQUENCE {
   gs2328ACLACEStatusIndex          Integer32,
   gs2328ACLACEStatusUser           DisplayString,
   gs2328ACLACEStatusID             Integer32,
   gs2328ACLACEStatusIngressPort    DisplayString,
   gs2328ACLACEStatusFrameType      DisplayString,
   gs2328ACLACEStatusAction         DisplayString,
   gs2328ACLACEStatusRateLimiter    DisplayString,
   gs2328ACLACEStatusPortCopy       DisplayString,
   gs2328ACLACEStatusMirror         DisplayString,
   gs2328ACLACEStatusCPU            DisplayString,
   gs2328ACLACEStatusCounter        Counter32,
   gs2328ACLACEStatusConflict       DisplayString
}

gs2328ACLACEStatusIndex OBJECT-TYPE
   SYNTAX      Integer32(1..256)
   MAX-ACCESS  not-accessible
   STATUS      current
   DESCRIPTION
       " "
   ::= { gs2328ACLACEStatusEntry 1 }

gs2328ACLACEStatusUser OBJECT-TYPE
   SYNTAX      DisplayString
   MAX-ACCESS  read-only
   STATUS      current
   DESCRIPTION
       " Indicates the ACL user. 
         S : Static.  
         IPMG : IP Management.  
         IPSG : IP Source Guard.  
         IPMC : IPMC.  
         ARPI : Arp Inspection.  
         UPnP : UPnP.  
         DHCP : DHCP. "
   ::= { gs2328ACLACEStatusEntry 2 }

gs2328ACLACEStatusID OBJECT-TYPE
   SYNTAX      Integer32(1..256)
   MAX-ACCESS  read-only
   STATUS      current
   DESCRIPTION
       " ACE ID.
         range : 1 - 256. "
   ::= { gs2328ACLACEStatusEntry 3 }

gs2328ACLACEStatusIngressPort OBJECT-TYPE
   SYNTAX      DisplayString
   MAX-ACCESS  read-only
   STATUS      current
   DESCRIPTION
       " Indicates the ingress port of the ACE. Possible values are: 
         All: The ACE will match all ingress port. 
         Port: The ACE will match a specific ingress port. "
   ::= { gs2328ACLACEStatusEntry 4 }

gs2328ACLACEStatusFrameType OBJECT-TYPE
   SYNTAX      DisplayString
   MAX-ACCESS  read-only
   STATUS      current
   DESCRIPTION
       " Indicates the frame type of the ACE. "
   ::= { gs2328ACLACEStatusEntry 5 }

gs2328ACLACEStatusAction OBJECT-TYPE
   SYNTAX      DisplayString
   MAX-ACCESS  read-only
   STATUS      current
   DESCRIPTION
       " Indicates the forwarding action of the ACE. "
   ::= { gs2328ACLACEStatusEntry 6 }

gs2328ACLACEStatusRateLimiter OBJECT-TYPE
   SYNTAX      DisplayString
   MAX-ACCESS  read-only
   STATUS      current
   DESCRIPTION
       " Indicates the rate limiter number of the ACE. "
   ::= { gs2328ACLACEStatusEntry 7 }

gs2328ACLACEStatusPortCopy OBJECT-TYPE
   SYNTAX      DisplayString
   MAX-ACCESS  read-only
   STATUS      current
   DESCRIPTION
       " Indicates the port redirect operation of the ACE. Frames matching the ACE are redirected to the port number. "
   ::= { gs2328ACLACEStatusEntry 8 }

gs2328ACLACEStatusMirror OBJECT-TYPE
   SYNTAX      DisplayString
   MAX-ACCESS  read-only
   STATUS      current
   DESCRIPTION
       " Specify the mirror operation of this port. "
   ::= { gs2328ACLACEStatusEntry 9 }

gs2328ACLACEStatusCPU OBJECT-TYPE
   SYNTAX      DisplayString
   MAX-ACCESS  read-only
   STATUS      current
   DESCRIPTION
       " Forward packet that matched the specific ACE to CPU. "
   ::= { gs2328ACLACEStatusEntry 10 }

gs2328ACLACEStatusCounter OBJECT-TYPE
   SYNTAX      Counter32
   MAX-ACCESS  read-only
   STATUS      current
   DESCRIPTION
       " The counter indicates the number of times the ACE was hit by a frame. "
   ::= { gs2328ACLACEStatusEntry 11 }
   
gs2328ACLACEStatusConflict OBJECT-TYPE
   SYNTAX      DisplayString
   MAX-ACCESS  read-only
   STATUS      current
   DESCRIPTION
       " Indicates the hardware status of the specific ACE. The specific ACE is not applied to the hardware due to hardware limitations. "
   ::= { gs2328ACLACEStatusEntry 12 }

gs2328LoopProtection                                                  OBJECT IDENTIFIER ::= { gs2328Configuration 12 }

gs2328LoopProtectionConfig                                            OBJECT IDENTIFIER ::= { gs2328LoopProtection 1 }

gs2328LoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2328LoopProtectionConfig 1 }
   
gs2328LoopProtectionTranmisstionTime OBJECT-TYPE
   SYNTAX      Integer32(1..10)
   MAX-ACCESS  read-write
   STATUS      current
   DESCRIPTION
       "Configure loop protection transmit interval.
        default: 5,
        range: 1-10. "
   ::= { gs2328LoopProtectionConfig 2 }
   
gs2328LoopProtectionShutdownTime OBJECT-TYPE
   SYNTAX      Integer32(0..604800)
   MAX-ACCESS  read-write
   STATUS      current
   DESCRIPTION
       "Configure loop protection shutdown time.
        default: 180,
        range: 0-604800. "
   ::= { gs2328LoopProtectionConfig 3 }

gs2328LoopProtectionConfigurationTable OBJECT-TYPE
   SYNTAX      SEQUENCE OF GS2328LoopProtectionConfigurationEntry
   MAX-ACCESS  not-accessible
   STATUS      current
   DESCRIPTION
       " Show Loop Protection configurations. "
   ::= { gs2328LoopProtectionConfig 4 }

gs2328LoopProtectionConfigurationEntry OBJECT-TYPE
   SYNTAX      GS2328LoopProtectionConfigurationEntry
   MAX-ACCESS  not-accessible
   STATUS      current
   DESCRIPTION
       ""
   INDEX    { gs2328LoopProtectionConfPort  }
   ::= { gs2328LoopProtectionConfigurationTable 1 }

GS2328LoopProtectionConfigurationEntry ::= SEQUENCE {
   gs2328LoopProtectionConfPort	    Integer32,
   gs2328LoopProtectionConfEnable	INTEGER,
   gs2328LoopProtectionConfAction	INTEGER,
   gs2328LoopProtectionConfTxmode	INTEGER
}

gs2328LoopProtectionConfPort OBJECT-TYPE
   SYNTAX      Integer32(1..4095)
   MAX-ACCESS  not-accessible
   STATUS      current
   DESCRIPTION
       " port, range : 1 - port number. "
   ::= { gs2328LoopProtectionConfigurationEntry 1 }

gs2328LoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2328LoopProtectionConfigurationEntry 2 }

gs2328LoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2328LoopProtectionConfigurationEntry 3 }
   
gs2328LoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2328LoopProtectionConfigurationEntry 4 }
   
gs2328LoopProtectionStatusTable OBJECT-TYPE
   SYNTAX      SEQUENCE OF GS2328LoopProtectionStatusEntry
   MAX-ACCESS  not-accessible
   STATUS      current
   DESCRIPTION
       " Show Loop Protection Status. "
   ::= { gs2328LoopProtection 2 }

gs2328LoopProtectionStatusEntry OBJECT-TYPE
   SYNTAX      GS2328LoopProtectionStatusEntry
   MAX-ACCESS  not-accessible
   STATUS      current
   DESCRIPTION
       ""
   INDEX    { gs2328LoopProtectionStatusPort  }
   ::= { gs2328LoopProtectionStatusTable 1 }

GS2328LoopProtectionStatusEntry ::= SEQUENCE {
   gs2328LoopProtectionStatusPort	       Integer32,
   gs2328LoopProtectionStatusAction	       DisplayString,
   gs2328LoopProtectionStatusTransmit	   DisplayString,
   gs2328LoopProtectionStatusLoops	       Integer32,
   gs2328LoopProtectionStatusStatus	       DisplayString,
   gs2328LoopProtectionStatusLoop	       DisplayString,
   gs2328LoopProtectionStatusTimeLastLoop  DisplayString
}

gs2328LoopProtectionStatusPort OBJECT-TYPE
   SYNTAX      Integer32(1..4095)
   MAX-ACCESS  not-accessible
   STATUS      current
   DESCRIPTION
       " port, range : 1 - port number. "
   ::= { gs2328LoopProtectionStatusEntry 1 }
   
gs2328LoopProtectionStatusAction OBJECT-TYPE
   SYNTAX      DisplayString
   MAX-ACCESS  read-only
   STATUS      current
   DESCRIPTION
       " The currently configured port action. "
   ::= { gs2328LoopProtectionStatusEntry 2 }
   
gs2328LoopProtectionStatusTransmit OBJECT-TYPE
   SYNTAX      DisplayString
   MAX-ACCESS  read-only
   STATUS      current
   DESCRIPTION
       " The currently configured port transmit mode. "
   ::= { gs2328LoopProtectionStatusEntry 3 }
   
gs2328LoopProtectionStatusLoops OBJECT-TYPE
   SYNTAX      Integer32(0..1000000)
   MAX-ACCESS  read-only
   STATUS      current
   DESCRIPTION
       " The number of loops detected on this port. "
   ::= { gs2328LoopProtectionStatusEntry 4 }
   
gs2328LoopProtectionStatusStatus OBJECT-TYPE
   SYNTAX      DisplayString
   MAX-ACCESS  read-only
   STATUS      current
   DESCRIPTION
       " The current loop protection status of the port. "
   ::= { gs2328LoopProtectionStatusEntry 5 }
   
gs2328LoopProtectionStatusLoop OBJECT-TYPE
   SYNTAX      DisplayString
   MAX-ACCESS  read-only
   STATUS      current
   DESCRIPTION
       " Whether a loop is currently detected on the port. "
   ::= { gs2328LoopProtectionStatusEntry 6 }

gs2328LoopProtectionStatusTimeLastLoop OBJECT-TYPE
   SYNTAX      DisplayString
   MAX-ACCESS  read-only
   STATUS      current
   DESCRIPTION
       " The time of the last loop event detected. "
   ::= { gs2328LoopProtectionStatusEntry 7 }

gs2328Qos                                                             OBJECT IDENTIFIER ::= { gs2328Configuration 14 }

gs2328QosPortClassification                                           OBJECT IDENTIFIER ::= { gs2328Qos 1 }

gs2328QosPortClassificationTable OBJECT-TYPE
   SYNTAX      SEQUENCE OF GS2328QosPortClassificationEntry
   MAX-ACCESS  not-accessible
   STATUS      current
   DESCRIPTION
       " QoS Ingress Port Classification . "
   ::= { gs2328QosPortClassification  1 }

gs2328QosPortClassificationEntry OBJECT-TYPE
   SYNTAX      GS2328QosPortClassificationEntry
   MAX-ACCESS  not-accessible
   STATUS      current
   DESCRIPTION
       ""
   INDEX    { gs2328QosPortClassificationPort  }
   ::= { gs2328QosPortClassificationTable 1 }

GS2328QosPortClassificationEntry ::= SEQUENCE {
   gs2328QosPortClassificationPort	        Integer32,
   gs2328QosPortClassificationQoSclass       Integer32,
   gs2328QosPortClassificationDPlevel	    Integer32,
   gs2328QosPortClassificationPCP	        Integer32,
   gs2328QosPortClassificationDEI	        INTEGER,
   gs2328QosPortClassificationTagClass	    INTEGER,
   gs2328QosPortClassificationDSCPBased    INTEGER,
   gs2328QosPortClassificationAddressMode  INTEGER
}

gs2328QosPortClassificationPort OBJECT-TYPE
   SYNTAX      Integer32(1..4095)
   MAX-ACCESS  not-accessible
   STATUS      current
   DESCRIPTION
       " port, range : 1 - port number. "
   ::= { gs2328QosPortClassificationEntry 1 }

gs2328QosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2328QosPortClassificationEntry 2 }

gs2328QosPortClassificationDPlevel OBJECT-TYPE
   SYNTAX      Integer32(0|1)
   MAX-ACCESS  read-write
   STATUS      current
   DESCRIPTION
       " DP level for frames not classified in any other way.
         range: 0-1,
         default: 0. "
   ::= { gs2328QosPortClassificationEntry 3 }

gs2328QosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2328QosPortClassificationEntry 4 }

gs2328QosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2328QosPortClassificationEntry 5 }

gs2328QosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2328QosPortClassificationEntry 6 }

gs2328QosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2328QosPortClassificationEntry 7 }

gs2328QosPortClassificationAddressMode OBJECT-TYPE
   SYNTAX      INTEGER { source(0), destination(1) }
   MAX-ACCESS  read-write
   STATUS      current
   DESCRIPTION
      "The IP/MAC address mode specifying whether the QCL classification
       must be based on source (SMAC/SIP) or destination (DMAC/DIP)
       addresses on this port.
        0: source,
        1: destination,
        default: source. "
   ::= { gs2328QosPortClassificationEntry 8 }

gs2328QoSIngressPortTagClassificationTable OBJECT-TYPE
   SYNTAX      SEQUENCE OF GS2328QoSIngressPortTagClassificationEntry
   MAX-ACCESS  not-accessible
   STATUS      current
   DESCRIPTION
       " Show QoS Ingress Port Tag Classification. "
   ::= { gs2328QosPortClassification 2 }

gs2328QoSIngressPortTagClassificationEntry OBJECT-TYPE
   SYNTAX      GS2328QoSIngressPortTagClassificationEntry
   MAX-ACCESS  not-accessible
   STATUS      current
   DESCRIPTION
       ""
   INDEX    { gs2328QoSIngressPortTagClassificationPort, gs2328QoSIngressPortTagPCP, gs2328QoSIngressPortTagDEI  }
   ::= { gs2328QoSIngressPortTagClassificationTable 1 }

GS2328QoSIngressPortTagClassificationEntry ::= SEQUENCE {
   gs2328QoSIngressPortTagClassificationPort	Integer32,
   gs2328QoSIngressPortTagPCP					INTEGER,
   gs2328QoSIngressPortTagDEI					INTEGER,
   gs2328QoSIngressPortTagQosClass				Integer32,
   gs2328QoSIngressPortTagDPLevel				Integer32
}

gs2328QoSIngressPortTagClassificationPort OBJECT-TYPE
   SYNTAX      Integer32(1..4095)
   MAX-ACCESS  not-accessible
   STATUS      current
   DESCRIPTION
       " port, range : 1 - port number. "
   ::= { gs2328QoSIngressPortTagClassificationEntry 1 }

gs2328QoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8, 
         PCP0:1, PCP1:2...  "
   ::= { gs2328QoSIngressPortTagClassificationEntry 2 }

gs2328QoSIngressPortTagDEI OBJECT-TYPE
   SYNTAX      INTEGER { dei0(1), dei1(2) }
   MAX-ACCESS  not-accessible
   STATUS      current
   DESCRIPTION
       " range: 1-2,
         DEI0:1, DEI1:2. "
   ::= { gs2328QoSIngressPortTagClassificationEntry 3 }

gs2328QoSIngressPortTagQosClass OBJECT-TYPE
   SYNTAX      Integer32 (0..7)
   MAX-ACCESS  read-write
   STATUS      current
   DESCRIPTION
       " range: 0-7.  "
   ::= { gs2328QoSIngressPortTagClassificationEntry 4 }
   
gs2328QoSIngressPortTagDPLevel OBJECT-TYPE
   SYNTAX      Integer32 (0|1)
   MAX-ACCESS  read-write
   STATUS      current
   DESCRIPTION
       " range: 0-1.  "
   ::= { gs2328QoSIngressPortTagClassificationEntry 5 }


gs2328QosPortPolicingTable OBJECT-TYPE
   SYNTAX      SEQUENCE OF GS2328QosPortPolicingEntry
   MAX-ACCESS  not-accessible
   STATUS      current
   DESCRIPTION
       "  configure the Policer settings for all switch ports. "
   ::= { gs2328Qos  2 }

gs2328QosPortPolicingEntry OBJECT-TYPE
   SYNTAX      GS2328QosPortPolicingEntry
   MAX-ACCESS  not-accessible
   STATUS      current
   DESCRIPTION
       ""
   INDEX    { gs2328QosPortPolicingPort  }
   ::= { gs2328QosPortPolicingTable 1 }

GS2328QosPortPolicingEntry ::= SEQUENCE {
   gs2328QosPortPolicingPort	        Integer32,
   gs2328QosPortPolicingMode           INTEGER,
   gs2328QosPortPolicingRate	        Integer32,
   gs2328QosPortPolicingUnit	        INTEGER,
   gs2328QosPortPolicingFlowControl	INTEGER
}

gs2328QosPortPolicingPort OBJECT-TYPE
   SYNTAX      Integer32 (1..4095)
   MAX-ACCESS  not-accessible
   STATUS      current
   DESCRIPTION
       " port, range : 1 - port number. "
   ::= { gs2328QosPortPolicingEntry 1 }

gs2328QosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2328QosPortPolicingEntry 2 }

gs2328QosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2328QosPortPolicingEntry 3 }

gs2328QosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2328QosPortPolicingEntry 4 }

gs2328QosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2328QosPortPolicingEntry 5 }

gs2328QosPortScheduler                                           OBJECT IDENTIFIER ::= { gs2328Qos 3 }

gs2328QosPortSchedulerModeTable OBJECT-TYPE
   SYNTAX      SEQUENCE OF GS2328QosPortSchedulerModeEntry
   MAX-ACCESS  not-accessible
   STATUS      current
   DESCRIPTION
       " configure the basic QoS Port Scheduler Mode settings for all switch ports. "
   ::= { gs2328QosPortScheduler  1 }

gs2328QosPortSchedulerModeEntry OBJECT-TYPE
   SYNTAX      GS2328QosPortSchedulerModeEntry
   MAX-ACCESS  not-accessible
   STATUS      current
   DESCRIPTION
       ""
   INDEX    { gs2328QosSchedulerModePort  }
   ::= { gs2328QosPortSchedulerModeTable 1 }

GS2328QosPortSchedulerModeEntry ::= SEQUENCE {
   gs2328QosSchedulerModePort	                Integer32,
   gs2328QosSchedulerMode                        INTEGER,
   gs2328QosSchedulerShaper	                    INTEGER,
   gs2328QosSchedulerShaperRate	                Integer32
}

gs2328QosSchedulerModePort OBJECT-TYPE
   SYNTAX      Integer32 (1..4095)
   MAX-ACCESS  not-accessible
   STATUS      current
   DESCRIPTION
       " port, range : 1 - port number. "
   ::= { gs2328QosPortSchedulerModeEntry 1 }

gs2328QosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2328QosPortSchedulerModeEntry 2 }

gs2328QosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2328QosPortSchedulerModeEntry 3 }

gs2328QosSchedulerShaperRate OBJECT-TYPE
   SYNTAX      Integer32(100..1000000)
   MAX-ACCESS  read-write
   STATUS      current
   DESCRIPTION
       " Controls the rate for the port shaper.
         range: 100-1000000
         default: 500 kbps. "
   ::= { gs2328QosPortSchedulerModeEntry 4 }

gs2328QosPortSchedulerTable OBJECT-TYPE
   SYNTAX      SEQUENCE OF GS2328QosPortSchedulerEntry
   MAX-ACCESS  not-accessible
   STATUS      current
   DESCRIPTION
       " Show Qos Port Scheduler. "
   ::= { gs2328QosPortScheduler 2 }

gs2328QosPortSchedulerEntry OBJECT-TYPE
   SYNTAX      GS2328QosPortSchedulerEntry
   MAX-ACCESS  not-accessible
   STATUS      current
   DESCRIPTION
       ""
   INDEX    { gs2328QosSchedulerPort, gs2328QosSchedulerPortQueue}
   ::= { gs2328QosPortSchedulerTable 1 }

GS2328QosPortSchedulerEntry ::= SEQUENCE {
   gs2328QosSchedulerPort						Integer32,
   gs2328QosSchedulerPortQueue					INTEGER,
   gs2328QosSchedulerPortQueueShaper				INTEGER,
   gs2328QosSchedulerPortQueueShaperRate			Integer32,
   gs2328QosSchedulerPortQueueShaperExcess		INTEGER,
   gs2328QosSchedulerPortQueueSchedulerWeight	Integer32,
   gs2328QosSchedulerPortQueueSchedulerPercent	DisplayString
}

gs2328QosSchedulerPort OBJECT-TYPE
   SYNTAX      Integer32 (1..4095)
   MAX-ACCESS  not-accessible
   STATUS      current
   DESCRIPTION
       " port, range : 1 - port number. "
   ::= { gs2328QosPortSchedulerEntry 1 }

gs2328QosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2328QosPortSchedulerEntry 2 }
   
gs2328QosSchedulerPortQueueShaper OBJECT-TYPE
   SYNTAX      INTEGER { disable(0), enable(1) }
   MAX-ACCESS  read-write
   STATUS      current
   DESCRIPTION
       " 0: disable  1:enable,
         default: 0.  "
   ::= { gs2328QosPortSchedulerEntry 3 }
   
gs2328QosSchedulerPortQueueShaperRate OBJECT-TYPE
   SYNTAX      Integer32(100..1000000)
   MAX-ACCESS  read-write
   STATUS      current
   DESCRIPTION
       " range: 100..1000000 kbps.  "
   ::= { gs2328QosPortSchedulerEntry 4 }
   
gs2328QosSchedulerPortQueueShaperExcess OBJECT-TYPE
   SYNTAX      INTEGER { disable(0), enable(1) }
   MAX-ACCESS  read-write
   STATUS      current
   DESCRIPTION
       " 0: disable  1:enable,
         default: 0.  "
   ::= { gs2328QosPortSchedulerEntry 5 }
   
gs2328QosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2328QosPortSchedulerEntry 6 }
   
gs2328QosSchedulerPortQueueSchedulerPercent OBJECT-TYPE
   SYNTAX      DisplayString
   MAX-ACCESS  read-only
   STATUS      current
   DESCRIPTION
       " Only use in Q0 - Q5. Q6 & Q7 show empty "
   ::= { gs2328QosPortSchedulerEntry 7 }

gs2328QosPortEgressTagRemarking                                           OBJECT IDENTIFIER ::= { gs2328Qos 4 }

gs2328QosPortEgressTagRemarkingTable OBJECT-TYPE
   SYNTAX      SEQUENCE OF GS2328QosPortEgressTagRemarkingEntry
   MAX-ACCESS  not-accessible
   STATUS      current
   DESCRIPTION
       " configure the basic QoS Port Egress Tag Remark Configuration settings for all switch ports. "
   ::= { gs2328QosPortEgressTagRemarking  1 }

gs2328QosPortEgressTagRemarkingEntry OBJECT-TYPE
   SYNTAX      GS2328QosPortEgressTagRemarkingEntry
   MAX-ACCESS  not-accessible
   STATUS      current
   DESCRIPTION
       ""
   INDEX    { gs2328QosEgressTagRemarkingPort  }
   ::= { gs2328QosPortEgressTagRemarkingTable 1 }

GS2328QosPortEgressTagRemarkingEntry ::= SEQUENCE {
   gs2328QosEgressTagRemarkingPort	                Integer32,
   gs2328QosEgressTagRemarkingMode	                INTEGER
}

gs2328QosEgressTagRemarkingPort OBJECT-TYPE
   SYNTAX      Integer32 (1..4095)
   MAX-ACCESS  not-accessible
   STATUS      current
   DESCRIPTION
       " port, range : 1 - port number. "
   ::= { gs2328QosPortEgressTagRemarkingEntry 1 }

gs2328QosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2328QosPortEgressTagRemarkingEntry 2 }


gs2328QosPortEgressTagRemarkingDefTable OBJECT-TYPE
   SYNTAX      SEQUENCE OF GS2328QosPortEgressTagRemarkingDefEntry
   MAX-ACCESS  not-accessible
   STATUS      current
   DESCRIPTION
       " configure the basic QoS Port Egress Tag Remark Configuration settings for all switch ports. "
   ::= { gs2328QosPortEgressTagRemarking  2 }

gs2328QosPortEgressTagRemarkingDefEntry OBJECT-TYPE
   SYNTAX      GS2328QosPortEgressTagRemarkingDefEntry
   MAX-ACCESS  not-accessible
   STATUS      current
   DESCRIPTION
       ""
   INDEX    { gs2328QosEgressTagRemarkingDefPort  }
   ::= { gs2328QosPortEgressTagRemarkingDefTable 1 }

GS2328QosPortEgressTagRemarkingDefEntry ::= SEQUENCE {
   gs2328QosEgressTagRemarkingDefPort	            Integer32,
   gs2328QosEgressTagRemarkingDefPCP	                Integer32,
   gs2328QosEgressTagRemarkingDefDEI	                INTEGER
}

gs2328QosEgressTagRemarkingDefPort OBJECT-TYPE
   SYNTAX      Integer32(1..4095)
   MAX-ACCESS  not-accessible
   STATUS      current
   DESCRIPTION
       " port, range : 1 - port number. "
   ::= { gs2328QosPortEgressTagRemarkingDefEntry 1 }

gs2328QosEgressTagRemarkingDefPCP OBJECT-TYPE
   SYNTAX      Integer32(0..7)
   MAX-ACCESS  read-write
   STATUS      current
   DESCRIPTION
       " Controls the default PCP
       Range : 0-7"
   ::= { gs2328QosPortEgressTagRemarkingDefEntry 2 }

gs2328QosEgressTagRemarkingDefDEI OBJECT-TYPE
   SYNTAX      INTEGER { disable(0), enable(1) }
   MAX-ACCESS  read-write
   STATUS      current
   DESCRIPTION
       " controls the DEI
       Range 0-1"
   ::= { gs2328QosPortEgressTagRemarkingDefEntry 3 }

gs2328QosPortEgressTagRemarkingMapTable OBJECT-TYPE
   SYNTAX      SEQUENCE OF GS2328QosPortEgressTagRemarkingMapEntry
   MAX-ACCESS  not-accessible
   STATUS      current
   DESCRIPTION
       " Show Qos Port Egress Tag Remarking Map. "
   ::= { gs2328QosPortEgressTagRemarking 4 }

gs2328QosPortEgressTagRemarkingMapEntry OBJECT-TYPE
   SYNTAX      GS2328QosPortEgressTagRemarkingMapEntry
   MAX-ACCESS  not-accessible
   STATUS      current
   DESCRIPTION
       ""
   INDEX    { gs2328QosPortEgressTagRemarkingMapPort, gs2328QosTagRemarkingQoSClass, gs2328QosTagRemarkingDPLevel  }
   ::= { gs2328QosPortEgressTagRemarkingMapTable 1 }

GS2328QosPortEgressTagRemarkingMapEntry ::= SEQUENCE {
   gs2328QosPortEgressTagRemarkingMapPort	Integer32,
   gs2328QosTagRemarkingQoSClass			INTEGER,
   gs2328QosTagRemarkingDPLevel				INTEGER,
   gs2328QosTagRemarkingPCP					Integer32,
   gs2328QosTagRemarkingDEI					INTEGER
}

gs2328QosPortEgressTagRemarkingMapPort OBJECT-TYPE
   SYNTAX      Integer32 (1..4095)
   MAX-ACCESS  not-accessible
   STATUS      current
   DESCRIPTION
       " port, range : 1 - port number. "
   ::= { gs2328QosPortEgressTagRemarkingMapEntry 1 }

gs2328QosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8, 
         QoS Class0: 1, QoS Class1: 2...  "
   ::= { gs2328QosPortEgressTagRemarkingMapEntry 2 }

gs2328QosTagRemarkingDPLevel OBJECT-TYPE
   SYNTAX      INTEGER { level0(1), level1(2) }
   MAX-ACCESS  not-accessible
   STATUS      current
   DESCRIPTION
       " range: 1-2,
         DP Level0: 1, DP Level1: 2. "
   ::= { gs2328QosPortEgressTagRemarkingMapEntry 3 }

gs2328QosTagRemarkingPCP OBJECT-TYPE
   SYNTAX      Integer32 (0..7)
   MAX-ACCESS  read-write
   STATUS      current
   DESCRIPTION
       " range: 0-7.  "
   ::= { gs2328QosPortEgressTagRemarkingMapEntry 4 }
   
gs2328QosTagRemarkingDEI OBJECT-TYPE
   SYNTAX      INTEGER (0|1)
   MAX-ACCESS  read-write
   STATUS      current
   DESCRIPTION
       " range: 0-1.  "
   ::= { gs2328QosPortEgressTagRemarkingMapEntry 5 }


gs2328QosPortDSCPTable OBJECT-TYPE
   SYNTAX      SEQUENCE OF GS2328QosPortDSCPEntry
   MAX-ACCESS  not-accessible
   STATUS      current
   DESCRIPTION
       " configure the basic QoS Port DSCP Configuration settings for all switch ports. "
   ::= { gs2328Qos  5 }

gs2328QosPortDSCPEntry OBJECT-TYPE
   SYNTAX      GS2328QosPortDSCPEntry
   MAX-ACCESS  not-accessible
   STATUS      current
   DESCRIPTION
       ""
   INDEX    { gs2328QosPortDSCPPort  }
   ::= { gs2328QosPortDSCPTable 1 }

GS2328QosPortDSCPEntry ::= SEQUENCE {
   gs2328QosPortDSCPPort	                Integer32,
   gs2328QosPortDSCPIngressTranslate       INTEGER,
   gs2328QosPortDSCPIngressClassify	    INTEGER,
   gs2328QosPortDSCPEgressRewrite	        INTEGER
}

gs2328QosPortDSCPPort OBJECT-TYPE
   SYNTAX      Integer32 (1..4095)
   MAX-ACCESS  not-accessible
   STATUS      current
   DESCRIPTION
       " port, range : 1 - port number. "
   ::= { gs2328QosPortDSCPEntry 1 }

gs2328QosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2328QosPortDSCPEntry 2 }

gs2328QosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2328QosPortDSCPEntry 3 }

gs2328QosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { gs2328QosPortDSCPEntry 4 }


gs2328QosDSCPTable OBJECT-TYPE
   SYNTAX      SEQUENCE OF GS2328QosDSCPEntry
   MAX-ACCESS  not-accessible
   STATUS      current
   DESCRIPTION
       " configure the basic QoS DSCP based QoS Ingress Classification settings for all switches. "
   ::= { gs2328Qos  6 }

gs2328QosDSCPEntry OBJECT-TYPE
   SYNTAX      GS2328QosDSCPEntry
   MAX-ACCESS  not-accessible
   STATUS      current
   DESCRIPTION
       ""
   INDEX    { gs2328QosDSCPList  }
   ::= { gs2328QosDSCPTable 1 }

GS2328QosDSCPEntry ::= SEQUENCE {
   gs2328QosDSCPList       Integer32,
   gs2328QosDSCP           DisplayString,
   gs2328QosDSCPTrust      INTEGER,
   gs2328QosDSCPQosClass	  Integer32,
   gs2328QosDSCPDPL	      INTEGER
}

gs2328QosDSCPList OBJECT-TYPE
   SYNTAX      Integer32(1..64)
   MAX-ACCESS  not-accessible
   STATUS      current
   DESCRIPTION
      " DSCP mapping table index(1-64). "
   ::= { gs2328QosDSCPEntry 1 }

gs2328QosDSCP OBJECT-TYPE
   SYNTAX      DisplayString
   MAX-ACCESS  read-only
   STATUS      current
   DESCRIPTION
      "Maximum number of supported DSCP values are 64."
   ::= { gs2328QosDSCPEntry 2 }

gs2328QosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2328QosDSCPEntry 3 }

gs2328QosDSCPQosClass OBJECT-TYPE
   SYNTAX      Integer32(0..7)
   MAX-ACCESS  read-write
   STATUS      current
   DESCRIPTION
      " QoS class.
        range: 0-7,
        default: 0. "
   ::= { gs2328QosDSCPEntry 4 }

gs2328QosDSCPDPL OBJECT-TYPE
   SYNTAX      INTEGER(0|1)
   MAX-ACCESS  read-write
   STATUS      current
   DESCRIPTION
      " Drop Precedence Level.
        range: 0-1,
        default: disable. "
   ::= { gs2328QosDSCPEntry 5 }

gs2328QosDSCPTranslationTable OBJECT-TYPE
   SYNTAX      SEQUENCE OF GS2328QosDSCPTranslationEntry
   MAX-ACCESS  not-accessible
   STATUS      current
   DESCRIPTION
       "  configure the basic QoS DSCP Translation settings for all switches. "
   ::= { gs2328Qos  7 }

gs2328QosDSCPTranslationEntry OBJECT-TYPE
   SYNTAX      GS2328QosDSCPTranslationEntry
   MAX-ACCESS  not-accessible
   STATUS      current
   DESCRIPTION
       ""
   INDEX    { gs2328QosDSCPTranslationList  }
   ::= { gs2328QosDSCPTranslationTable 1 }

GS2328QosDSCPTranslationEntry ::= SEQUENCE {
   gs2328QosDSCPTranslationList                 Integer32,
   gs2328QosDSCPTranslationDSCPBasedId          DisplayString,
   gs2328QosDSCPTranslationIngressTranslate     Integer32,
   gs2328QosDSCPTranslationIngressClassify      INTEGER,
   gs2328QosDSCPTranslationEgressRemapDP0       Integer32,
   gs2328QosDSCPTranslationEgressRemapDP1       Integer32
}

gs2328QosDSCPTranslationList OBJECT-TYPE
   SYNTAX      Integer32(1..64)
   MAX-ACCESS  not-accessible
   STATUS      current
   DESCRIPTION
      " DSCP translation table index(1-64). "
   ::= { gs2328QosDSCPTranslationEntry 1 }

gs2328QosDSCPTranslationDSCPBasedId OBJECT-TYPE
   SYNTAX      DisplayString
   MAX-ACCESS  read-write
   STATUS      current
   DESCRIPTION
      " Configure global ingress DSCP translation table. "
   ::= { gs2328QosDSCPTranslationEntry 2 }

gs2328QosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2328QosDSCPTranslationEntry 3 }

gs2328QosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2328QosDSCPTranslationEntry 4 }

gs2328QosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { gs2328QosDSCPTranslationEntry 5 }

gs2328QosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { gs2328QosDSCPTranslationEntry 6 }


gs2328QosDSCPClassificationTable OBJECT-TYPE
   SYNTAX      SEQUENCE OF GS2328QosDSCPClassificationEntry
   MAX-ACCESS  not-accessible
   STATUS      current
   DESCRIPTION
       "   configure the mapping of QoS class  to DSCP value. "
   ::= { gs2328Qos  8 }

gs2328QosDSCPClassificationEntry OBJECT-TYPE
   SYNTAX      GS2328QosDSCPClassificationEntry
   MAX-ACCESS  not-accessible
   STATUS      current
   DESCRIPTION
       ""
   INDEX    { gs2328QosDSCPClassificationQoSClass, gs2328QosDSCPClassificationDPL }
   ::= { gs2328QosDSCPClassificationTable 1 }

GS2328QosDSCPClassificationEntry ::= SEQUENCE {
   gs2328QosDSCPClassificationQoSClass		INTEGER,
   gs2328QosDSCPClassificationDPL			INTEGER,
   gs2328QosDSCPClassificationDSCP			Integer32
}

gs2328QosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2328QosDSCPClassificationEntry 1 }

gs2328QosDSCPClassificationDPL OBJECT-TYPE
   SYNTAX      INTEGER(1|2)
   MAX-ACCESS  not-accessible
   STATUS      current
   DESCRIPTION
      " DPL. Index 1~2 mean DPL 0~1."
   ::= { gs2328QosDSCPClassificationEntry 2 }

gs2328QosDSCPClassificationDSCP OBJECT-TYPE
   SYNTAX      Integer32(0..63)
   MAX-ACCESS  read-write
   STATUS      current
   DESCRIPTION
      " Select the classified DSCP value.
        range: 0-63,
        default: 0. "
   ::= { gs2328QosDSCPClassificationEntry 3 }

gs2328QosControlList                                         OBJECT IDENTIFIER ::= { gs2328Qos 9 }

gs2328QosQceCreate OBJECT-TYPE
   SYNTAX       INTEGER { none(0), create(1) }
   MAX-ACCESS   read-write
   STATUS       current
   DESCRIPTION
       "default: 0
        0 : None  (read only)
        1 : Create an Qos entry"
   ::= { gs2328QosControlList 1 }

gs2328QosQceTable OBJECT-TYPE
   SYNTAX      SEQUENCE OF GS2328QosQceEntry
   MAX-ACCESS  not-accessible
   STATUS      current
   DESCRIPTION
       " Create Qos QCE entry. "
   ::= { gs2328QosControlList 2 }

gs2328QosQceEntry OBJECT-TYPE
   SYNTAX      GS2328QosQceEntry
   MAX-ACCESS  not-accessible
   STATUS      current
   DESCRIPTION
       ""
   INDEX    { gs2328QosQceIndex  }
   ::= { gs2328QosQceTable 1 }

GS2328QosQceEntry ::= SEQUENCE {
   gs2328QosQceIndex                Integer32,
   gs2328QosQceID                   Integer32,
   gs2328QosQceNextID               Integer32,
   gs2328QosQcePortMembers          DisplayString,
   
   gs2328QosQceTag                  DisplayString,
   gs2328QosQceVID                  DisplayString,
   gs2328QosPCP                     DisplayString,
   gs2328QosDEI                     DisplayString,
   gs2328QosSMAC                    DisplayString,
   gs2328QosDMACType                DisplayString,
   gs2328QosFrameType               INTEGER,
   
   gs2328QosMacEtherType            DisplayString,
   
   gs2328QosLLCSSAPAddr             DisplayString,
   gs2328QosLLCDSAPAddr             DisplayString,
   gs2328QosLLCControl              DisplayString,
   
   gs2328QosSNAPPID                 DisplayString,
   
   gs2328QosIpv4Protocol            DisplayString,
   gs2328QosIpv4ProtocolValue       Integer32,
   gs2328QosIpv4ProtocolUDPSport    DisplayString,
   gs2328QosIpv4ProtocolUDPDport    DisplayString,
   gs2328QosIpv4ProtocolTCPSport    DisplayString,
   gs2328QosIpv4ProtocolTCPDport    DisplayString,
   gs2328QosIpv4Ip                  DisplayString,
   gs2328QosIpv4Mask                DisplayString,
   gs2328QosIpv4IPFragment          INTEGER,
   gs2328QosIpv4DSCP                DisplayString,


   gs2328QosIpv6Protocol            DisplayString,
   gs2328QosIpv6ProtocolValue       Integer32,
   gs2328QosIpv6ProtocolUDPSport    DisplayString,
   gs2328QosIpv6ProtocolUDPDport    DisplayString,
   gs2328QosIpv6ProtocolTCPSport    DisplayString,
   gs2328QosIpv6ProtocolTCPDport    DisplayString,
   gs2328QosIpv6Ip                  DisplayString,
   gs2328QosIpv6Mask                DisplayString,
   gs2328QosIpv6DSCP                DisplayString,
   
   gs2328QosActionClass             Integer32,
   gs2328QosActionDPL               INTEGER,
   gs2328QosActionDSCP              Integer32,
   gs2328QosQceRowStatus            INTEGER
}

gs2328QosQceIndex OBJECT-TYPE
   SYNTAX      Integer32(1..256)
   MAX-ACCESS  not-accessible
   STATUS      current
   DESCRIPTION
       " "
   ::= { gs2328QosQceEntry 1 }

gs2328QosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2328QosQceEntry 2 }

gs2328QosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2328QosQceEntry 3 }

gs2328QosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2328QosQceEntry 4 }

gs2328QosQceTag OBJECT-TYPE
   SYNTAX      DisplayString
   MAX-ACCESS  read-write
   STATUS      current
   DESCRIPTION
       " Value of Tag field can be 'Any', 'Untag' or 'Tag'. "
   ::= { gs2328QosQceEntry 5 }

gs2328QosQceVID OBJECT-TYPE
   SYNTAX      DisplayString
   MAX-ACCESS  read-write
   STATUS      current
   DESCRIPTION
       " Valid value of VLAN ID can be any value in 'Specific 1~4094' or 'range 1-4094' or 'Any'. "
   ::= { gs2328QosQceEntry 6 }

gs2328QosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2328QosQceEntry 7 }

gs2328QosDEI OBJECT-TYPE
   SYNTAX      DisplayString
   MAX-ACCESS  read-write
   STATUS      current
   DESCRIPTION
       " Drop Eligible Indicator: Valid value of DEI can be any of values between 0, 1 or 'Any'. "
   ::= { gs2328QosQceEntry 8 }

gs2328QosSMAC  OBJECT-TYPE
   SYNTAX      DisplayString
   MAX-ACCESS  read-write
   STATUS      current
   DESCRIPTION
       "  Source MAC address: 24 MS bits OUI(00-00-00 ~ FF-FF-FF) or 'Any'. "
   ::= { gs2328QosQceEntry 9 }

gs2328QosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2328QosQceEntry 10 }

gs2328QosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2328QosQceEntry 11 }

gs2328QosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2328QosQceEntry 12 }

gs2328QosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2328QosQceEntry 13 }

gs2328QosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2328QosQceEntry 14 }

gs2328QosLLCControl OBJECT-TYPE
   SYNTAX      DisplayString
   MAX-ACCESS  read-write
   STATUS      current
   DESCRIPTION
       " Valid Control field can vary from 0x00 to 0xFF or 'Any',
         range: 00-FF,
         default: Any. "
   ::= { gs2328QosQceEntry 15 }

gs2328QosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2328QosQceEntry 16 }

gs2328QosIpv4Protocol OBJECT-TYPE
   SYNTAX      DisplayString
   MAX-ACCESS  read-write
   STATUS      current
   DESCRIPTION
       " IP protocol number: (Other, TCP or UDP) or 'Any'. "
   ::= { gs2328QosQceEntry 17 }

gs2328QosIpv4ProtocolValue  OBJECT-TYPE
   SYNTAX      Integer32(0..255)
   MAX-ACCESS  read-write
   STATUS      current
   DESCRIPTION
       " Ipv4 Protocol is Other.
         range: 0-255
         default: 0. "
   ::= { gs2328QosQceEntry 18 }

gs2328QosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2328QosQceEntry 19 }

gs2328QosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2328QosQceEntry 20 }

gs2328QosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2328QosQceEntry 21 }

gs2328QosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2328QosQceEntry 22 }

gs2328QosIpv4Ip OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223.
          If a port is configured to match on DMAC/DIP, this field is the
          Destination IP address."
   ::= { gs2328QosQceEntry 23 }

gs2328QosIpv4Mask OBJECT-TYPE
   SYNTAX      DisplayString
   MAX-ACCESS  read-write
   STATUS      current
   DESCRIPTION
       " Specific IP address in mask format or value 0.0.0.0 is 'Any'. "
   ::= { gs2328QosQceEntry 24 }

gs2328QosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2328QosQceEntry 25 }

gs2328QosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2328QosQceEntry 26 }

gs2328QosIpv6Protocol OBJECT-TYPE
   SYNTAX      DisplayString
   MAX-ACCESS  read-write
   STATUS      current
   DESCRIPTION
       " IP protocol number: (Other, TCP or UDP) or 'Any'. "
   ::= { gs2328QosQceEntry 27 }

gs2328QosIpv6ProtocolValue OBJECT-TYPE
   SYNTAX      Integer32(0..255)
   MAX-ACCESS  read-write
   STATUS      current
   DESCRIPTION
       " when IPv6 protocol is Other ,
         range: 0-255. "
   ::= { gs2328QosQceEntry 28 }

gs2328QosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2328QosQceEntry 29 }

gs2328QosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2328QosQceEntry 30 }

gs2328QosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2328QosQceEntry 31 }


gs2328QosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2328QosQceEntry 32 }

gs2328QosIpv6Ip OBJECT-TYPE
   SYNTAX      DisplayString
   MAX-ACCESS  read-write
   STATUS      current
   DESCRIPTION
       " IPv6 source address: (a.b.c.d) or value 0.0.0.0 is 'Any', 32 LS bits.
         If a port is configured to match on DMAC/DIP, this field is the
         Destination IP address."
   ::= { gs2328QosQceEntry 33 }

gs2328QosIpv6Mask OBJECT-TYPE
   SYNTAX      DisplayString
   MAX-ACCESS  read-write
   STATUS      current
   DESCRIPTION
       " IPv6 mask address: (a.b.c.d) or value 0.0.0.0 is 'Any', 32 LS bits. "
   ::= { gs2328QosQceEntry 34 }

gs2328QosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2328QosQceEntry 35 }

gs2328QosActionClass  OBJECT-TYPE
   SYNTAX      Integer32(0..8)
   MAX-ACCESS  read-write
   STATUS      current
   DESCRIPTION
       " QoS class: (0-7) or 8: Default."
   ::= { gs2328QosQceEntry 36 }

gs2328QosActionDPL OBJECT-TYPE
   SYNTAX      INTEGER (0..4)
   MAX-ACCESS  read-write
   STATUS      current
   DESCRIPTION
       " DP Valid Drop Precedence Level can be (0-3) or 4: Default. "
   ::= { gs2328QosQceEntry 37 }

gs2328QosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2328QosQceEntry 38 }

gs2328QosQceRowStatus OBJECT-TYPE
   SYNTAX      INTEGER { active(1), notInservice(2), destroy(4) }
   MAX-ACCESS  read-write
   STATUS      current
   DESCRIPTION
       "  1: active2: notInservice 4: destroy"
   ::= { gs2328QosQceEntry 39 }

gs2328QosQceMoveID OBJECT-TYPE
   SYNTAX       Integer32(0..256)
   MAX-ACCESS   read-write
   STATUS       current
   DESCRIPTION
       " Move Qos,
         default: 0
         Qos ID must be exist.
         range : 0 - 256."
   ::= { gs2328QosControlList 3 }

gs2328QosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2328QosControlList 4 }


gs2328QosQCLStatusTable OBJECT-TYPE
   SYNTAX      SEQUENCE OF GS2328QosQCLStatusEntry
   MAX-ACCESS  not-accessible
   STATUS      current
   DESCRIPTION
       "  configure the basic QoS DSCP Translation settings for all switches. "
   ::= { gs2328Qos  10 }

gs2328QosQCLStatusEntry OBJECT-TYPE
   SYNTAX      GS2328QosQCLStatusEntry
   MAX-ACCESS  not-accessible
   STATUS      current
   DESCRIPTION
       ""
   INDEX    { gs2328QosQCLStatusList  }
   ::= { gs2328QosQCLStatusTable 1 }

GS2328QosQCLStatusEntry ::= SEQUENCE {
   gs2328QosQCLStatusList               Integer32,
   gs2328QosQCLStatusUser               DisplayString,
   gs2328QosQCLStatusQCEId              DisplayString,
   gs2328QosQCLStatusFrameType          DisplayString,
   gs2328QosQCLStatusPortlist           DisplayString,
   gs2328QosQCLStatusActionClass	       DisplayString,
   gs2328QosQCLStatusActionDPL	       DisplayString,
   gs2328QosQCLStatusActionDSCP	       DisplayString,
   gs2328QosQCLStatusActionConflict     DisplayString
}

gs2328QosQCLStatusList OBJECT-TYPE
   SYNTAX      Integer32(1..4095)
   MAX-ACCESS  not-accessible
   STATUS      current
   DESCRIPTION
       " QCL table index. "
   ::= { gs2328QosQCLStatusEntry 1}
   
gs2328QosQCLStatusUser OBJECT-TYPE
   SYNTAX      DisplayString
   MAX-ACCESS  read-only
   STATUS      current
   DESCRIPTION
       " Indicates the QCL user. "
   ::= { gs2328QosQCLStatusEntry 2 }

gs2328QosQCLStatusQCEId OBJECT-TYPE
   SYNTAX      DisplayString
   MAX-ACCESS  read-only
   STATUS      current
   DESCRIPTION
      " Indicates the index of QCE. "
   ::= { gs2328QosQCLStatusEntry 3}

gs2328QosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2328QosQCLStatusEntry 4}

gs2328QosQCLStatusPortlist OBJECT-TYPE
   SYNTAX      DisplayString
   MAX-ACCESS  read-only
   STATUS      current
   DESCRIPTION
       " Indicates the list of ports configured with the QCE. "
   ::= { gs2328QosQCLStatusEntry 5}

gs2328QosQCLStatusActionClass OBJECT-TYPE
   SYNTAX      DisplayString
   MAX-ACCESS  read-only
   STATUS      current
   DESCRIPTION
       " Classified QoS class; if a frame matches the QCE it will be put in the
       queue. "
   ::= { gs2328QosQCLStatusEntry 6}

gs2328QosQCLStatusActionDPL OBJECT-TYPE
   SYNTAX      DisplayString
   MAX-ACCESS  read-only
   STATUS      current
   DESCRIPTION
       " Drop Precedence Level; if a frame matches the QCE then DP level will
       set to value displayed under DPL column."
   ::= { gs2328QosQCLStatusEntry 7}

gs2328QosQCLStatusActionDSCP OBJECT-TYPE
   SYNTAX      DisplayString
   MAX-ACCESS  read-only
   STATUS      current
   DESCRIPTION
       " If a frame matches the QCE then DSCP will be classified with the value
       displayed under DSCP column."
   ::= { gs2328QosQCLStatusEntry 8}

gs2328QosQCLStatusActionConflict OBJECT-TYPE
   SYNTAX      DisplayString
   MAX-ACCESS  read-only
   STATUS      current
   DESCRIPTION
       " If a frame matches the QCE then DSCP will be classified with the value
        displayed under DSCP column. "
   ::= { gs2328QosQCLStatusEntry 9}


gs2328QosStormControl                                           OBJECT IDENTIFIER ::= { gs2328Qos 11 }

gs2328QoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { gs2328QosStormControl 2 }

gs2328QoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2328QosStormControl 3 }

gs2328QoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { gs2328QosStormControl 4 }

gs2328QoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2328QosStormControl 5 }

gs2328QoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { gs2328QosStormControl 6 }

gs2328QoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2328QosStormControl 7 }


gs2328Vlan                                                           OBJECT IDENTIFIER ::= { gs2328Configuration 15 }

gs2328VlanPorts                                                      OBJECT IDENTIFIER ::= { gs2328Vlan 1 }

gs2328VlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2328VlanPorts 1 }

gs2328VlanPortsTable OBJECT-TYPE
   SYNTAX      SEQUENCE OF GS2328VlanPortsEntry
   MAX-ACCESS  not-accessible
   STATUS      current
   DESCRIPTION
       " Configure Vlan ports Configuration mode. "
   ::= { gs2328VlanPorts 2 }

gs2328VlanPortsEntry OBJECT-TYPE
   SYNTAX      GS2328VlanPortsEntry
   MAX-ACCESS  not-accessible
   STATUS      current
   DESCRIPTION
       ""
   INDEX    { gs2328VlanPortsPort  }
   ::= { gs2328VlanPortsTable 1 }

GS2328VlanPortsEntry ::= SEQUENCE {
   gs2328VlanPortsPort	         Integer32,
   gs2328VlanPortsPVID     Integer32,
   gs2328VlanPortsFrameType      INTEGER,
   gs2328VlanPortsIngressFilter  INTEGER,
   gs2328VlanPortsEgressRule     INTEGER,
   gs2328VlanPortsPortType       INTEGER
}

gs2328VlanPortsPort OBJECT-TYPE
   SYNTAX      Integer32(1..4094)
   MAX-ACCESS  not-accessible
   STATUS      current
   DESCRIPTION
       " port, range : 1 - port number. "
   ::= { gs2328VlanPortsEntry 1 }

gs2328VlanPortsPVID OBJECT-TYPE
   SYNTAX      Integer32(1..4094)
   MAX-ACCESS  read-write
   STATUS      current
   DESCRIPTION
       "Configure PVID.
        range: 1-4094,
        default: 1. "
   ::= { gs2328VlanPortsEntry 2 }

gs2328VlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2328VlanPortsEntry 3 }

gs2328VlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2328VlanPortsEntry 4 }

gs2328VlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2328VlanPortsEntry 5 }

gs2328VlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2328VlanPortsEntry 6 }

gs2328VlanPrivateVLAN                                                              OBJECT IDENTIFIER ::= { gs2328Vlan 2 }

gs2328VlanPrivateVLANMembership                                                    OBJECT IDENTIFIER ::= { gs2328VlanPrivateVLAN 1 }

gs2328VlanPrivateVLANMembershipCreate OBJECT-TYPE
   SYNTAX       Integer32(1..4094)
   MAX-ACCESS   read-write
   STATUS       current
   DESCRIPTION
       "default: 0
        0 : None  (read only)
        1 : Create a pvlan"
   ::= { gs2328VlanPrivateVLANMembership 1 }

gs2328VlanPrivateVLANMembershipTable OBJECT-TYPE
   SYNTAX      SEQUENCE OF Gs2328VlanPrivateVLANMembershipEntry
   MAX-ACCESS  not-accessible
   STATUS      current
   DESCRIPTION
       " Configure Private Vlan Configuration. "
   ::= { gs2328VlanPrivateVLANMembership 2 }

gs2328VlanPrivateVLANMembershipEntry OBJECT-TYPE
   SYNTAX      Gs2328VlanPrivateVLANMembershipEntry
   MAX-ACCESS  not-accessible
   STATUS      current
   DESCRIPTION
       ""
   INDEX    { gs2328VlanPrivateVLANIndex  }
   ::= { gs2328VlanPrivateVLANMembershipTable 1 }

Gs2328VlanPrivateVLANMembershipEntry ::= SEQUENCE {
   gs2328VlanPrivateVLANIndex          Integer32,
   gs2328VlanPrivateVLANID             Integer32,
   gs2328VlanPrivateVLANMemberships    DisplayString,
   gs2328VlanPrivateVLANRowStatus      INTEGER
}

gs2328VlanPrivateVLANIndex OBJECT-TYPE
   SYNTAX      Integer32(1..52)
   MAX-ACCESS  not-accessible
   STATUS      current
   DESCRIPTION
       "private VLAN Index. "
   ::= { gs2328VlanPrivateVLANMembershipEntry 1 }

gs2328VlanPrivateVLANID OBJECT-TYPE
   SYNTAX      Integer32(1..52)
   MAX-ACCESS  read-write
   STATUS      current
   DESCRIPTION
       "Indicates the ID of this particular private VLAN.
       The CreateEntry can be modify, the other entry can't be modify."
   ::= { gs2328VlanPrivateVLANMembershipEntry 2 }

gs2328VlanPrivateVLANMemberships OBJECT-TYPE
   SYNTAX      DisplayString
   MAX-ACCESS  read-write
   STATUS      current
   DESCRIPTION
       "To include the ports in a Private VLAN"
   ::= { gs2328VlanPrivateVLANMembershipEntry 3 }

gs2328VlanPrivateVLANRowStatus OBJECT-TYPE
   SYNTAX      INTEGER { active(1), notInservice(2), destroy(4) }
   MAX-ACCESS  read-write
   STATUS      current
   DESCRIPTION
       "1: active
        2: notInservice
        4: destroy"
   ::= { gs2328VlanPrivateVLANMembershipEntry 4 }

gs2328VlanPortIsolationTable OBJECT-TYPE
   SYNTAX      SEQUENCE OF Gs2328VlanPortIsolationEntry
   MAX-ACCESS  not-accessible
   STATUS      current
   DESCRIPTION
       " Configure Vlan Port Isolation Configuration. "
   ::= { gs2328VlanPrivateVLAN 2 }

gs2328VlanPortIsolationEntry OBJECT-TYPE
   SYNTAX      Gs2328VlanPortIsolationEntry
   MAX-ACCESS  not-accessible
   STATUS      current
   DESCRIPTION
       ""
   INDEX    { gs2328VlanPortIsolationPort  }
   ::= { gs2328VlanPortIsolationTable 1 }

Gs2328VlanPortIsolationEntry ::= SEQUENCE {
   gs2328VlanPortIsolationPort Integer32,
   gs2328VlanPortIsolation     INTEGER
}

gs2328VlanPortIsolationPort OBJECT-TYPE
   SYNTAX      Integer32(1..4094)
   MAX-ACCESS  not-accessible
   STATUS      current
   DESCRIPTION
       " port, range : 1 - port number. "
   ::= { gs2328VlanPortIsolationEntry 1 }

gs2328VlanPortIsolation OBJECT-TYPE
   SYNTAX      INTEGER{ disable(0), enable(1) }
   MAX-ACCESS  read-write
   STATUS      current
   DESCRIPTION
       "default: 0
        0:disable
        1:enable"
   ::= { gs2328VlanPortIsolationEntry 2 }


gs2328MACbasedVLAN                                                      OBJECT IDENTIFIER ::= { gs2328Vlan 3 }

gs2328MACbasedVLANConf                                                      OBJECT IDENTIFIER ::= { gs2328MACbasedVLAN 1 }

gs2328MACbasedVLANConfCreate OBJECT-TYPE
   SYNTAX       Integer32
   MAX-ACCESS   read-write
   STATUS       current
   DESCRIPTION
       "default: 0
       0 : None  (read only) 1 : Create MAC base vlan"
   ::= { gs2328MACbasedVLANConf 1 }

gs2328MACbasedVLANConfTable OBJECT-TYPE
   SYNTAX      SEQUENCE OF Gs2328MACbasedVLANConfEntry
   MAX-ACCESS  not-accessible
   STATUS      current
   DESCRIPTION
       " Configure Vlan Port Isolation Configuration. "
   ::= { gs2328MACbasedVLANConf 2 }

gs2328MACbasedVLANConfEntry OBJECT-TYPE
   SYNTAX      Gs2328MACbasedVLANConfEntry
   MAX-ACCESS  not-accessible
   STATUS      current
   DESCRIPTION
       ""
   INDEX    { gs2328MACbasedVLANIndex  }
   ::= { gs2328MACbasedVLANConfTable 1 }

Gs2328MACbasedVLANConfEntry ::= SEQUENCE {
   gs2328MACbasedVLANIndex         Integer32,
   gs2328MACbasedVLANMACAddress    MacAddress,
   gs2328MACbasedVLANID            Integer32,
   gs2328MACbasedMemberships       DisplayString,
   gs2328MACbaseRowStatus          INTEGER
}

gs2328MACbasedVLANIndex OBJECT-TYPE
   SYNTAX      Integer32(1..256)
   MAX-ACCESS  read-write
   STATUS      current
   DESCRIPTION
       "Indicates the VLAN ID. "
   ::= { gs2328MACbasedVLANConfEntry 1 }

gs2328MACbasedVLANMACAddress OBJECT-TYPE
   SYNTAX      MacAddress
   MAX-ACCESS  read-write
   STATUS      current
   DESCRIPTION
       "Indicates the MAC address.
       The CreateEntry can be modify, the other entry can't be modify."
   ::= { gs2328MACbasedVLANConfEntry 2 }

gs2328MACbasedVLANID OBJECT-TYPE
   SYNTAX      Integer32(1..4094)
   MAX-ACCESS  read-write
   STATUS      current
   DESCRIPTION
       "Indicates the VLAN ID. "
   ::= { gs2328MACbasedVLANConfEntry 3 }

gs2328MACbasedMemberships OBJECT-TYPE
   SYNTAX      DisplayString
   MAX-ACCESS  read-write
   STATUS      current
   DESCRIPTION
       "The ports are displayed for each MAC-based VLAN entry.
        To include the port in a MAC-based VLAN"
   ::= { gs2328MACbasedVLANConfEntry 4 }


gs2328MACbaseRowStatus OBJECT-TYPE
   SYNTAX      INTEGER { active(1), notInservice(2), destroy(4)}
   MAX-ACCESS  read-write
   STATUS      current
   DESCRIPTION
       "1: active
        2: notInservice
        4: destroy"
   ::= { gs2328MACbasedVLANConfEntry 5 }

gs2328IGMPSnooping                                                           OBJECT IDENTIFIER ::= { gs2328Configuration 16 }

gs2328IGMPSnoopingBasic                                                      OBJECT IDENTIFIER ::= { gs2328IGMPSnooping 1 }

gs2328IGMPSnoopingEnable  OBJECT-TYPE
   SYNTAX      INTEGER { disable(0), enable(1) }
   MAX-ACCESS  read-write
   STATUS      current
   DESCRIPTION
       "Enable/Disable the Global IGMP Snooping"
   ::= { gs2328IGMPSnoopingBasic 1 }

gs2328IGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2328IGMPSnoopingBasic 2 }

gs2328IGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2328IGMPSnoopingBasic 3 }
   
gs2328IGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2328IGMPSnoopingBasic 4 }

gs2328IGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2328IGMPSnoopingBasic 5 }

gs2328IGMPSnoopingPortRelatedTable OBJECT-TYPE
   SYNTAX      SEQUENCE OF Gs2328IGMPSnoopingPortRelatedEntry
   MAX-ACCESS  not-accessible
   STATUS      current
   DESCRIPTION
       " Configure IGMP Snooping Port Related Configuration. "
   ::= { gs2328IGMPSnoopingBasic 6 }

gs2328IGMPSnoopingPortRelatedEntry OBJECT-TYPE
   SYNTAX      Gs2328IGMPSnoopingPortRelatedEntry
   MAX-ACCESS  not-accessible
   STATUS      current
   DESCRIPTION
       ""
   INDEX    { ifIndex  }
   ::= { gs2328IGMPSnoopingPortRelatedTable 1 }

Gs2328IGMPSnoopingPortRelatedEntry ::= SEQUENCE {
   gs2328IGMPSnoopingRouterPort	INTEGER,
   gs2328IGMPSnoopingFastLeave  	INTEGER,
   gs2328IGMPSnoopingThrottling    Integer32
}

gs2328IGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2328IGMPSnoopingPortRelatedEntry 1 }

gs2328IGMPSnoopingFastLeave OBJECT-TYPE
   SYNTAX      INTEGER { disable(0), enable(1) }
   MAX-ACCESS  read-write
   STATUS      current
   DESCRIPTION
       "Enable/Disable the fast leave on the port. "
   ::= { gs2328IGMPSnoopingPortRelatedEntry 2 }
   
gs2328IGMPSnoopingThrottling OBJECT-TYPE
   SYNTAX      Integer32(0..10)
   MAX-ACCESS  read-write
   STATUS      current
   DESCRIPTION
       "Enable to limit the number of multicast groups to which a switch port can belong.
       0: unlimited"
   ::= { gs2328IGMPSnoopingPortRelatedEntry 3 }
   
gs2328IGMPSnoopingVLANTable OBJECT-TYPE
   SYNTAX      SEQUENCE OF Gs2328IGMPSnoopingVLANEntry
   MAX-ACCESS  not-accessible
   STATUS      current
   DESCRIPTION
       " Configure IGMP Snooping Vlan Configuration. "
   ::= { gs2328IGMPSnooping 2 }

gs2328IGMPSnoopingVLANEntry OBJECT-TYPE
   SYNTAX      Gs2328IGMPSnoopingVLANEntry
   MAX-ACCESS  not-accessible
   STATUS      current
   DESCRIPTION
       ""
   INDEX    { gs2328IGMPSnoopingVLANID  }
   ::= { gs2328IGMPSnoopingVLANTable 1 }

Gs2328IGMPSnoopingVLANEntry ::= SEQUENCE {
   gs2328IGMPSnoopingVLANID        	Integer32,
   gs2328IGMPSnoopingVLANEnable    	INTEGER,
   gs2328IGMPSnoopingVLANIGMPQuerier   INTEGER,
   gs2328IGMPSnoopingVLANCompatibility INTEGER,
   gs2328IGMPSnoopingVLANRV        	Integer32,
   gs2328IGMPSnoopingVLANQI      	    Integer32,
   gs2328IGMPSnoopingVLANQRI   	    Integer32,
   gs2328IGMPSnoopingVLANLLQI   	    Integer32,
   gs2328IGMPSnoopingVLANURI    	    Integer32
}

gs2328IGMPSnoopingVLANID OBJECT-TYPE
   SYNTAX      Integer32(1..4095)
   MAX-ACCESS  read-write
   STATUS      current
   DESCRIPTION
       "The VLAN ID of the entry"
   ::= { gs2328IGMPSnoopingVLANEntry 1 }

gs2328IGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2328IGMPSnoopingVLANEntry 2 }

gs2328IGMPSnoopingVLANIGMPQuerier OBJECT-TYPE
   SYNTAX      INTEGER { disable(0), enable(1) }
   MAX-ACCESS  read-write
   STATUS      current
   DESCRIPTION
       "Enable/Disable the IGMP Querier in the VLAN. "
   ::= { gs2328IGMPSnoopingVLANEntry 3 }

gs2328IGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2328IGMPSnoopingVLANEntry 4 }
   
gs2328IGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2328IGMPSnoopingVLANEntry 5 }
   
gs2328IGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2328IGMPSnoopingVLANEntry 6 }
   
gs2328IGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2328IGMPSnoopingVLANEntry 7 }
   
gs2328IGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2328IGMPSnoopingVLANEntry 8 }

gs2328IGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2328IGMPSnoopingVLANEntry 9 }

gs2328IGMPSnoopingPortGroupFiltering                                                      OBJECT IDENTIFIER ::= { gs2328IGMPSnooping 3 }

gs2328IGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2328IGMPSnoopingPortGroupFiltering 1 }

gs2328IGMPSnoopingPortGroupFilteringTable OBJECT-TYPE
   SYNTAX      SEQUENCE OF Gs2328IGMPSnoopingPortGroupFilteringEntry
   MAX-ACCESS  not-accessible
   STATUS      current
   DESCRIPTION
       " Configure IGMP Snooping port group filtering. "
   ::= { gs2328IGMPSnoopingPortGroupFiltering 2 }

gs2328IGMPSnoopingPortGroupFilteringEntry OBJECT-TYPE
   SYNTAX      Gs2328IGMPSnoopingPortGroupFilteringEntry
   MAX-ACCESS  not-accessible
   STATUS      current
   DESCRIPTION
       ""
   INDEX    { gs2328IGMPSnoopingPortGroupFilteringIndex  }
   ::= { gs2328IGMPSnoopingPortGroupFilteringTable 1 }

Gs2328IGMPSnoopingPortGroupFilteringEntry ::= SEQUENCE {
   gs2328IGMPSnoopingPortGroupFilteringIndex         Integer32,
   gs2328IGMPSnoopingPortGroupFilteringPort          Integer32,
   gs2328IGMPSnoopingPortGroupFilteringGroups        DisplayString,
   gs2328IGMPSnoopingPortGroupFilteringRowStatus     INTEGER
}

gs2328IGMPSnoopingPortGroupFilteringIndex OBJECT-TYPE
   SYNTAX      Integer32(1..65535)
   MAX-ACCESS  not-accessible
   STATUS      current
   DESCRIPTION
       "IGMP Snooping Port Group Filtering Configuration Index. "
   ::= { gs2328IGMPSnoopingPortGroupFilteringEntry 1 }

gs2328IGMPSnoopingPortGroupFilteringPort OBJECT-TYPE
   SYNTAX      Integer32(1..65535)
   MAX-ACCESS  read-write
   STATUS      current
   DESCRIPTION
       "The logical port for the settings. "
   ::= { gs2328IGMPSnoopingPortGroupFilteringEntry 2 }

gs2328IGMPSnoopingPortGroupFilteringGroups OBJECT-TYPE
   SYNTAX      DisplayString
   MAX-ACCESS  read-write
   STATUS      current
   DESCRIPTION
       "The IP Multicast Group that will be filtered. "
   ::= { gs2328IGMPSnoopingPortGroupFilteringEntry 3 }

gs2328IGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2328IGMPSnoopingPortGroupFilteringEntry 4 }

gs2328IGMPSnoopingStatus                                                      OBJECT IDENTIFIER ::= { gs2328IGMPSnooping 4 }

gs2328IGMPSnoopingstatisticClear OBJECT-TYPE
   SYNTAX      INTEGER { none(0), clear(1)}
   MAX-ACCESS  read-write
   STATUS      current
   DESCRIPTION
       "Clears all Statistics counters."
   ::= { gs2328IGMPSnoopingStatus 1 }


gs2328IGMPSnoopingstatisticTable OBJECT-TYPE
   SYNTAX      SEQUENCE OF Gs2328IGMPSnoopingstatisticEntry
   MAX-ACCESS  not-accessible
   STATUS      current
   DESCRIPTION
       " Configure Vlan Port Isolation Configuration. "
   ::= { gs2328IGMPSnoopingStatus 2 }

gs2328IGMPSnoopingstatisticEntry OBJECT-TYPE
   SYNTAX      Gs2328IGMPSnoopingstatisticEntry
   MAX-ACCESS  not-accessible
   STATUS      current
   DESCRIPTION
       ""
   INDEX    { gs2328IGMPSnoopingstatisticVLANID  }
   ::= { gs2328IGMPSnoopingstatisticTable 1 }

Gs2328IGMPSnoopingstatisticEntry ::= SEQUENCE {
   gs2328IGMPSnoopingstatisticVLANID              Integer32,
   gs2328IGMPSnoopingstatisticQuerierVersion      DisplayString,
   gs2328IGMPSnoopingstatisticHostVersion         DisplayString,
   gs2328IGMPSnoopingstatisticQuerierStatus       DisplayString,
   gs2328IGMPSnoopingstatisticQueriesTransmitted  Counter32,
   gs2328IGMPSnoopingstatisticQueriesReceived     Counter32,
   gs2328IGMPSnoopingstatisticV1ReportsReceived   Counter32,
   gs2328IGMPSnoopingstatisticV2ReportsReceived   Counter32,
   gs2328IGMPSnoopingstatisticV3ReportsReceived   Counter32,
   gs2328IGMPSnoopingstatisticV2LeavesReceived    Counter32
}


gs2328IGMPSnoopingstatisticVLANID OBJECT-TYPE
   SYNTAX      Integer32(1..4095)
   MAX-ACCESS  read-only
   STATUS      current
   DESCRIPTION
       "The VLAN ID of the entry. "
   ::= { gs2328IGMPSnoopingstatisticEntry 1 }

gs2328IGMPSnoopingstatisticQuerierVersion OBJECT-TYPE
   SYNTAX      DisplayString
   MAX-ACCESS  read-only
   STATUS      current
   DESCRIPTION
       "Working Querier Version currently. "
   ::= { gs2328IGMPSnoopingstatisticEntry 2 }
   
gs2328IGMPSnoopingstatisticHostVersion OBJECT-TYPE
   SYNTAX      DisplayString
   MAX-ACCESS  read-only
   STATUS      current
   DESCRIPTION
       "Working Host Version currently. "
   ::= { gs2328IGMPSnoopingstatisticEntry 3 }

gs2328IGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2328IGMPSnoopingstatisticEntry 4 }

gs2328IGMPSnoopingstatisticQueriesTransmitted OBJECT-TYPE
   SYNTAX      Counter32
   MAX-ACCESS  read-only
   STATUS      current
   DESCRIPTION
       "The number of Transmitted Queries. "
   ::= { gs2328IGMPSnoopingstatisticEntry 5 }

gs2328IGMPSnoopingstatisticQueriesReceived OBJECT-TYPE
   SYNTAX      Counter32
   MAX-ACCESS  read-only
   STATUS      current
   DESCRIPTION
       "The number of Received Queries. "
   ::= { gs2328IGMPSnoopingstatisticEntry 6 }

gs2328IGMPSnoopingstatisticV1ReportsReceived OBJECT-TYPE
   SYNTAX      Counter32
   MAX-ACCESS  read-only
   STATUS      current
   DESCRIPTION
       "The number of Received V1 Reports. "
   ::= { gs2328IGMPSnoopingstatisticEntry 7 }

gs2328IGMPSnoopingstatisticV2ReportsReceived OBJECT-TYPE
   SYNTAX      Counter32
   MAX-ACCESS  read-only
   STATUS      current
   DESCRIPTION
       "The number of Received V2 Reports. "
   ::= { gs2328IGMPSnoopingstatisticEntry 8 }

gs2328IGMPSnoopingstatisticV3ReportsReceived OBJECT-TYPE
   SYNTAX      Counter32
   MAX-ACCESS  read-only
   STATUS      current
   DESCRIPTION
       "The number of Received V3 Reports. "
   ::= { gs2328IGMPSnoopingstatisticEntry 9 }

gs2328IGMPSnoopingstatisticV2LeavesReceived OBJECT-TYPE
   SYNTAX      Counter32
   MAX-ACCESS  read-only
   STATUS      current
   DESCRIPTION
       "The number of Received V2 Leaves. "
   ::= { gs2328IGMPSnoopingstatisticEntry 10 }

gs2328IGMPSnoopingRouterPortTable OBJECT-TYPE
   SYNTAX      SEQUENCE OF Gs2328IGMPSnoopingRouterPortEntry
   MAX-ACCESS  not-accessible
   STATUS      current
   DESCRIPTION
       " Configure Vlan Port Isolation Configuration. "
   ::= { gs2328IGMPSnoopingStatus 3 }

gs2328IGMPSnoopingRouterPortEntry OBJECT-TYPE
   SYNTAX      Gs2328IGMPSnoopingRouterPortEntry
   MAX-ACCESS  not-accessible
   STATUS      current
   DESCRIPTION
       ""
   INDEX    { ifIndex  }
   ::= { gs2328IGMPSnoopingRouterPortTable 1 }

Gs2328IGMPSnoopingRouterPortEntry ::= SEQUENCE {
   gs2328IGMPSnoopingRouterPortStatus            DisplayString
}

gs2328IGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2328IGMPSnoopingRouterPortEntry 1 }

gs2328IGMPSnoopingGroupsTable OBJECT-TYPE
   SYNTAX      SEQUENCE OF Gs2328IGMPSnoopingGroupsEntry
   MAX-ACCESS  not-accessible
   STATUS      current
   DESCRIPTION
       "IGMP Snooping Groups Information . "
   ::= { gs2328IGMPSnooping 5 }

gs2328IGMPSnoopingGroupsEntry OBJECT-TYPE
   SYNTAX      Gs2328IGMPSnoopingGroupsEntry
   MAX-ACCESS  not-accessible
   STATUS      current
   DESCRIPTION
       ""
   INDEX    { gs2328IGMPSnoopingGroupsIndex  }
   ::= { gs2328IGMPSnoopingGroupsTable 1 }

Gs2328IGMPSnoopingGroupsEntry ::= SEQUENCE {
   gs2328IGMPSnoopingGroupsIndex          Integer32,
   gs2328IGMPSnoopingGroupsVLANID         Integer32,
   gs2328IGMPSnoopingGroups               InetAddress,
   gs2328IGMPSnoopingGroupsMemberships    DisplayString
}

gs2328IGMPSnoopingGroupsIndex OBJECT-TYPE
   SYNTAX      Integer32(1..65535)
   MAX-ACCESS  not-accessible
   STATUS      current
   DESCRIPTION
       "IGMP Snooping Groups Index"
   ::= { gs2328IGMPSnoopingGroupsEntry 1 }

gs2328IGMPSnoopingGroupsVLANID OBJECT-TYPE
   SYNTAX      Integer32(1..4095)
   MAX-ACCESS  read-only
   STATUS      current
   DESCRIPTION
       "VLAN ID of the group. "
   ::= { gs2328IGMPSnoopingGroupsEntry 2 }

gs2328IGMPSnoopingGroups OBJECT-TYPE
   SYNTAX      DisplayString
   MAX-ACCESS  read-only
   STATUS      current
   DESCRIPTION
       "Group address of the group displayed."
   ::= { gs2328IGMPSnoopingGroupsEntry 3 }

gs2328IGMPSnoopingGroupsMemberships OBJECT-TYPE
   SYNTAX      DisplayString
   MAX-ACCESS  read-only
   STATUS      current
   DESCRIPTION
       "Ports under this group."
   ::= { gs2328IGMPSnoopingGroupsEntry 4 }
   
gs2328IGMPSnoopingSSMTable OBJECT-TYPE
   SYNTAX      SEQUENCE OF Gs2328IGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2328IGMPSnooping 6 }

gs2328IGMPSnoopingSSMEntry OBJECT-TYPE
   SYNTAX      Gs2328IGMPSnoopingSSMEntry
   MAX-ACCESS  not-accessible
   STATUS      current
   DESCRIPTION
       ""
   INDEX    { gs2328IGMPSnoopingSSMIndex  }
   ::= { gs2328IGMPSnoopingSSMTable 1 }

Gs2328IGMPSnoopingSSMEntry ::= SEQUENCE {
   gs2328IGMPSnoopingSSMIndex          Integer32,
   gs2328IGMPSnoopingSSMVLANID         Integer32,
   gs2328IGMPSnoopingSSMGroup          DisplayString,
   gs2328IGMPSnoopingSSMPort           Integer32,
   gs2328IGMPSnoopingSSMMode           DisplayString,
   gs2328IGMPSnoopingSSMSourceAddress  DisplayString,
   gs2328IGMPSnoopingSSMType           DisplayString
}

gs2328IGMPSnoopingSSMIndex OBJECT-TYPE
   SYNTAX      Integer32(1..65535)
   MAX-ACCESS  not-accessible
   STATUS      current
   DESCRIPTION
       "IGMP Snooping SSM Index"
   ::= { gs2328IGMPSnoopingSSMEntry 1 }

gs2328IGMPSnoopingSSMVLANID OBJECT-TYPE
   SYNTAX      Integer32(1..4095)
   MAX-ACCESS  read-only
   STATUS      current
   DESCRIPTION
       "VLAN ID of the group. "
   ::= { gs2328IGMPSnoopingSSMEntry 2 }

gs2328IGMPSnoopingSSMGroup OBJECT-TYPE
   SYNTAX      DisplayString
   MAX-ACCESS  read-only
   STATUS      current
   DESCRIPTION
       "Group address of the group displayed."
   ::= { gs2328IGMPSnoopingSSMEntry 3 }

gs2328IGMPSnoopingSSMPort OBJECT-TYPE
   SYNTAX      Integer32(1..65535)
   MAX-ACCESS  read-only
   STATUS      current
   DESCRIPTION
       "Ports under this group."
   ::= { gs2328IGMPSnoopingSSMEntry 4 }
   
gs2328IGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2328IGMPSnoopingSSMEntry 5 }
   
gs2328IGMPSnoopingSSMSourceAddress OBJECT-TYPE
   SYNTAX      DisplayString
   MAX-ACCESS  read-only
   STATUS      current
   DESCRIPTION
       "IP Address of the source. Currently, system limits the total number of
       IP source addresses for filtering to be 128."
   ::= { gs2328IGMPSnoopingSSMEntry 6 }

gs2328IGMPSnoopingSSMType OBJECT-TYPE
   SYNTAX      DisplayString
   MAX-ACCESS  read-only
   STATUS      current
   DESCRIPTION
       "Indicates the Type. It can be either Allow or Deny."
   ::= { gs2328IGMPSnoopingSSMEntry 7 }   

gs2328MLDSnooping                                                           OBJECT IDENTIFIER ::= { gs2328Configuration 17 }

gs2328MLDSnoopingBasic                                                      OBJECT IDENTIFIER ::= { gs2328MLDSnooping 1 }

gs2328MLDSnoopingEnable  OBJECT-TYPE
   SYNTAX      INTEGER { disable(0), enable(1) }
   MAX-ACCESS  read-write
   STATUS      current
   DESCRIPTION
       "Enable/Disable the Global MLD Snooping"
   ::= { gs2328MLDSnoopingBasic 1 }

gs2328MLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2328MLDSnoopingBasic 2 }

gs2328MLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2328MLDSnoopingBasic 3 }
   
gs2328MLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2328MLDSnoopingBasic 4 }

gs2328MLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2328MLDSnoopingBasic 5 }

gs2328MLDSnoopingPortRelatedTable OBJECT-TYPE
   SYNTAX      SEQUENCE OF Gs2328MLDSnoopingPortRelatedEntry
   MAX-ACCESS  not-accessible
   STATUS      current
   DESCRIPTION
       " Configure MLD Snooping Port Related Configuration. "
   ::= { gs2328MLDSnoopingBasic 6 }

gs2328MLDSnoopingPortRelatedEntry OBJECT-TYPE
   SYNTAX      Gs2328MLDSnoopingPortRelatedEntry
   MAX-ACCESS  not-accessible
   STATUS      current
   DESCRIPTION
       ""
   INDEX    { ifIndex  }
   ::= { gs2328MLDSnoopingPortRelatedTable 1 }

Gs2328MLDSnoopingPortRelatedEntry ::= SEQUENCE {
   gs2328MLDSnoopingRouterPort	INTEGER,
   gs2328MLDSnoopingFastLeave  	INTEGER,
   gs2328MLDSnoopingThrottling    Integer32
}

gs2328MLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2328MLDSnoopingPortRelatedEntry 1 }

gs2328MLDSnoopingFastLeave OBJECT-TYPE
   SYNTAX      INTEGER { disable(0), enable(1) }
   MAX-ACCESS  read-write
   STATUS      current
   DESCRIPTION
       "Enable/Disable the fast leave on the port. "
   ::= { gs2328MLDSnoopingPortRelatedEntry 2 }
   
gs2328MLDSnoopingThrottling OBJECT-TYPE
   SYNTAX      Integer32(0..10)
   MAX-ACCESS  read-write
   STATUS      current
   DESCRIPTION
       "Enable to limit the number of multicast groups to which a switch port can belong.
       0: unlimited"
   ::= { gs2328MLDSnoopingPortRelatedEntry 3 }
   
gs2328MLDSnoopingVLANTable OBJECT-TYPE
   SYNTAX      SEQUENCE OF Gs2328MLDSnoopingVLANEntry
   MAX-ACCESS  not-accessible
   STATUS      current
   DESCRIPTION
       " Configure MLD Snooping Vlan Configuration. "
   ::= { gs2328MLDSnooping 2 }

gs2328MLDSnoopingVLANEntry OBJECT-TYPE
   SYNTAX      Gs2328MLDSnoopingVLANEntry
   MAX-ACCESS  not-accessible
   STATUS      current
   DESCRIPTION
       ""
   INDEX    { gs2328MLDSnoopingVLANID  }
   ::= { gs2328MLDSnoopingVLANTable 1 }

Gs2328MLDSnoopingVLANEntry ::= SEQUENCE {
   gs2328MLDSnoopingVLANID        	Integer32,
   gs2328MLDSnoopingVLANEnable    	INTEGER,
   gs2328MLDSnoopingVLANIGMPQuerier   INTEGER,
   gs2328MLDSnoopingVLANCompatibility INTEGER,
   gs2328MLDSnoopingVLANRV        	Integer32,
   gs2328MLDSnoopingVLANQI      	    Integer32,
   gs2328MLDSnoopingVLANQRI   	    Integer32,
   gs2328MLDSnoopingVLANLLQI   	    Integer32,
   gs2328MLDSnoopingVLANURI    	    Integer32
}

gs2328MLDSnoopingVLANID OBJECT-TYPE
   SYNTAX      Integer32(1..4095)
   MAX-ACCESS  read-write
   STATUS      current
   DESCRIPTION
       "The VLAN ID of the entry"
   ::= { gs2328MLDSnoopingVLANEntry 1 }

gs2328MLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2328MLDSnoopingVLANEntry 2 }

gs2328MLDSnoopingVLANIGMPQuerier OBJECT-TYPE
   SYNTAX      INTEGER { disable(0), enable(1) }
   MAX-ACCESS  read-write
   STATUS      current
   DESCRIPTION
       "Enable/Disable the MLD Querier in the VLAN. "
   ::= { gs2328MLDSnoopingVLANEntry 3 }

gs2328MLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2328MLDSnoopingVLANEntry 4 }
   
gs2328MLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2328MLDSnoopingVLANEntry 5 }
   
gs2328MLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2328MLDSnoopingVLANEntry 6 }
   
gs2328MLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2328MLDSnoopingVLANEntry 7 }
   
gs2328MLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2328MLDSnoopingVLANEntry 8 }

gs2328MLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2328MLDSnoopingVLANEntry 9 }

gs2328MLDSnoopingPortGroupFiltering                                                      OBJECT IDENTIFIER ::= { gs2328MLDSnooping 3 }

gs2328MLDSnoopingPortGroupFilteringCreate OBJECT-TYPE
   SYNTAX       Integer32
   MAX-ACCESS   read-write
   STATUS       current
   DESCRIPTION
       "default: 0
       0 : None  (read only) 1 : Create MLD Snooping Port Group Filtering "
   ::= { gs2328MLDSnoopingPortGroupFiltering 1 }

gs2328MLDSnoopingPortGroupFilteringTable OBJECT-TYPE
   SYNTAX      SEQUENCE OF Gs2328MLDSnoopingPortGroupFilteringEntry
   MAX-ACCESS  not-accessible
   STATUS      current
   DESCRIPTION
       " Configure MLD Snooping port group filtering. "
   ::= { gs2328MLDSnoopingPortGroupFiltering 2 }

gs2328MLDSnoopingPortGroupFilteringEntry OBJECT-TYPE
   SYNTAX      Gs2328MLDSnoopingPortGroupFilteringEntry
   MAX-ACCESS  not-accessible
   STATUS      current
   DESCRIPTION
       ""
   INDEX    { gs2328MLDSnoopingPortGroupFilteringIndex  }
   ::= { gs2328MLDSnoopingPortGroupFilteringTable 1 }

Gs2328MLDSnoopingPortGroupFilteringEntry ::= SEQUENCE {
   gs2328MLDSnoopingPortGroupFilteringIndex         Integer32,
   gs2328MLDSnoopingPortGroupFilteringPort          Integer32,
   gs2328MLDSnoopingPortGroupFilteringGroups        DisplayString,
   gs2328MLDSnoopingPortGroupFilteringRowStatus     INTEGER
}

gs2328MLDSnoopingPortGroupFilteringIndex OBJECT-TYPE
   SYNTAX      Integer32(1..65535)
   MAX-ACCESS  not-accessible
   STATUS      current
   DESCRIPTION
       "MLD Snooping Port Group Filtering Configuration Index. "
   ::= { gs2328MLDSnoopingPortGroupFilteringEntry 1 }

gs2328MLDSnoopingPortGroupFilteringPort OBJECT-TYPE
   SYNTAX      Integer32(1..65535)
   MAX-ACCESS  read-write
   STATUS      current
   DESCRIPTION
       "The logical port for the settings. "
   ::= { gs2328MLDSnoopingPortGroupFilteringEntry 2 }

gs2328MLDSnoopingPortGroupFilteringGroups OBJECT-TYPE
   SYNTAX      DisplayString
   MAX-ACCESS  read-write
   STATUS      current
   DESCRIPTION
       "The IP Multicast Group that will be filtered. "
   ::= { gs2328MLDSnoopingPortGroupFilteringEntry 3 }

gs2328MLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2328MLDSnoopingPortGroupFilteringEntry 4 }

gs2328MLDSnoopingStatus                                                      OBJECT IDENTIFIER ::= { gs2328MLDSnooping 4 }

gs2328MLDSnoopingstatisticClear OBJECT-TYPE
   SYNTAX      INTEGER { none(0), clear(1)}
   MAX-ACCESS  read-write
   STATUS      current
   DESCRIPTION
       "Clears all Statistics counters."
   ::= { gs2328MLDSnoopingStatus 1 }


gs2328MLDSnoopingstatisticTable OBJECT-TYPE
   SYNTAX      SEQUENCE OF Gs2328MLDSnoopingstatisticEntry
   MAX-ACCESS  not-accessible
   STATUS      current
   DESCRIPTION
       " Configure Vlan Port Isolation Configuration. "
   ::= { gs2328MLDSnoopingStatus 2 }

gs2328MLDSnoopingstatisticEntry OBJECT-TYPE
   SYNTAX      Gs2328MLDSnoopingstatisticEntry
   MAX-ACCESS  not-accessible
   STATUS      current
   DESCRIPTION
       ""
   INDEX    { gs2328MLDSnoopingstatisticVLANID  }
   ::= { gs2328MLDSnoopingstatisticTable 1 }

Gs2328MLDSnoopingstatisticEntry ::= SEQUENCE {
   gs2328MLDSnoopingstatisticVLANID              Integer32,
   gs2328MLDSnoopingstatisticQuerierVersion      DisplayString,
   gs2328MLDSnoopingstatisticHostVersion         DisplayString,
   gs2328MLDSnoopingstatisticQuerierStatus       DisplayString,
   gs2328MLDSnoopingstatisticQueriesTransmitted  Counter32,
   gs2328MLDSnoopingstatisticQueriesReceived     Counter32,
   gs2328MLDSnoopingstatisticV1ReportsReceived   Counter32,
   gs2328MLDSnoopingstatisticV2ReportsReceived   Counter32,
   gs2328MLDSnoopingstatisticV1LeavesReceived    Counter32
}


gs2328MLDSnoopingstatisticVLANID OBJECT-TYPE
   SYNTAX      Integer32(1..4095)
   MAX-ACCESS  read-only
   STATUS      current
   DESCRIPTION
       "The VLAN ID of the entry. "
   ::= { gs2328MLDSnoopingstatisticEntry 1 }

gs2328MLDSnoopingstatisticQuerierVersion OBJECT-TYPE
   SYNTAX      DisplayString
   MAX-ACCESS  read-only
   STATUS      current
   DESCRIPTION
       "Working Querier Version currently. "
   ::= { gs2328MLDSnoopingstatisticEntry 2 }
   
gs2328MLDSnoopingstatisticHostVersion OBJECT-TYPE
   SYNTAX      DisplayString
   MAX-ACCESS  read-only
   STATUS      current
   DESCRIPTION
       "Working Host Version currently. "
   ::= { gs2328MLDSnoopingstatisticEntry 3 }

gs2328MLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2328MLDSnoopingstatisticEntry 4 }

gs2328MLDSnoopingstatisticQueriesTransmitted OBJECT-TYPE
   SYNTAX      Counter32
   MAX-ACCESS  read-only
   STATUS      current
   DESCRIPTION
       "The number of Transmitted Queries. "
   ::= { gs2328MLDSnoopingstatisticEntry 5 }

gs2328MLDSnoopingstatisticQueriesReceived OBJECT-TYPE
   SYNTAX      Counter32
   MAX-ACCESS  read-only
   STATUS      current
   DESCRIPTION
       "The number of Received Queries. "
   ::= { gs2328MLDSnoopingstatisticEntry 6 }

gs2328MLDSnoopingstatisticV1ReportsReceived OBJECT-TYPE
   SYNTAX      Counter32
   MAX-ACCESS  read-only
   STATUS      current
   DESCRIPTION
       "The number of Received V1 Reports. "
   ::= { gs2328MLDSnoopingstatisticEntry 7 }

gs2328MLDSnoopingstatisticV2ReportsReceived OBJECT-TYPE
   SYNTAX      Counter32
   MAX-ACCESS  read-only
   STATUS      current
   DESCRIPTION
       "The number of Received V2 Reports. "
   ::= { gs2328MLDSnoopingstatisticEntry 8 }

gs2328MLDSnoopingstatisticV1LeavesReceived OBJECT-TYPE
   SYNTAX      Counter32
   MAX-ACCESS  read-only
   STATUS      current
   DESCRIPTION
       "The number of Received V1 Leaves. "
   ::= { gs2328MLDSnoopingstatisticEntry 9 }

gs2328MLDSnoopingRouterPortTable OBJECT-TYPE
   SYNTAX      SEQUENCE OF Gs2328MLDSnoopingRouterPortEntry
   MAX-ACCESS  not-accessible
   STATUS      current
   DESCRIPTION
       " Configure Vlan Port Isolation Configuration. "
   ::= { gs2328MLDSnoopingStatus 3 }

gs2328MLDSnoopingRouterPortEntry OBJECT-TYPE
   SYNTAX      Gs2328MLDSnoopingRouterPortEntry
   MAX-ACCESS  not-accessible
   STATUS      current
   DESCRIPTION
       ""
   INDEX    { ifIndex  }
   ::= { gs2328MLDSnoopingRouterPortTable 1 }

Gs2328MLDSnoopingRouterPortEntry ::= SEQUENCE {
   gs2328MLDSnoopingRouterPortStatus            DisplayString
}

gs2328MLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2328MLDSnoopingRouterPortEntry 1 }

gs2328MLDSnoopingGroupsTable OBJECT-TYPE
   SYNTAX      SEQUENCE OF Gs2328MLDSnoopingGroupsEntry
   MAX-ACCESS  not-accessible
   STATUS      current
   DESCRIPTION
       "MLD Snooping Groups Information . "
   ::= { gs2328MLDSnooping 5 }

gs2328MLDSnoopingGroupsEntry OBJECT-TYPE
   SYNTAX      Gs2328MLDSnoopingGroupsEntry
   MAX-ACCESS  not-accessible
   STATUS      current
   DESCRIPTION
       ""
   INDEX    { gs2328MLDSnoopingGroupsIndex  }
   ::= { gs2328MLDSnoopingGroupsTable 1 }

Gs2328MLDSnoopingGroupsEntry ::= SEQUENCE {
   gs2328MLDSnoopingGroupsIndex          Integer32,
   gs2328MLDSnoopingGroupsVLANID         Integer32,
   gs2328MLDSnoopingGroups               InetAddress,
   gs2328MLDSnoopingGroupsMemberships    DisplayString
}

gs2328MLDSnoopingGroupsIndex OBJECT-TYPE
   SYNTAX      Integer32(1..65535)
   MAX-ACCESS  not-accessible
   STATUS      current
   DESCRIPTION
       "MLD Snooping Groups Index"
   ::= { gs2328MLDSnoopingGroupsEntry 1 }

gs2328MLDSnoopingGroupsVLANID OBJECT-TYPE
   SYNTAX      Integer32(1..4095)
   MAX-ACCESS  read-only
   STATUS      current
   DESCRIPTION
       "VLAN ID of the group. "
   ::= { gs2328MLDSnoopingGroupsEntry 2 }

gs2328MLDSnoopingGroups OBJECT-TYPE
   SYNTAX      DisplayString
   MAX-ACCESS  read-only
   STATUS      current
   DESCRIPTION
       "Group address of the group displayed."
   ::= { gs2328MLDSnoopingGroupsEntry 3 }

gs2328MLDSnoopingGroupsMemberships OBJECT-TYPE
   SYNTAX      DisplayString
   MAX-ACCESS  read-only
   STATUS      current
   DESCRIPTION
       "Ports under this group."
   ::= { gs2328MLDSnoopingGroupsEntry 4 }
   
gs2328MLDSnoopingSSMTable OBJECT-TYPE
   SYNTAX      SEQUENCE OF Gs2328MLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2328MLDSnooping 6 }

gs2328MLDSnoopingSSMEntry OBJECT-TYPE
   SYNTAX      Gs2328MLDSnoopingSSMEntry
   MAX-ACCESS  not-accessible
   STATUS      current
   DESCRIPTION
       ""
   INDEX    { gs2328MLDSnoopingSSMIndex  }
   ::= { gs2328MLDSnoopingSSMTable 1 }

Gs2328MLDSnoopingSSMEntry ::= SEQUENCE {
   gs2328MLDSnoopingSSMIndex          Integer32,
   gs2328MLDSnoopingSSMVLANID         Integer32,
   gs2328MLDSnoopingSSMGroup          DisplayString,
   gs2328MLDSnoopingSSMPort           Integer32,
   gs2328MLDSnoopingSSMMode           DisplayString,
   gs2328MLDSnoopingSSMSourceAddress  DisplayString,
   gs2328MLDSnoopingSSMType           DisplayString
}

gs2328MLDSnoopingSSMIndex OBJECT-TYPE
   SYNTAX      Integer32(1..65535)
   MAX-ACCESS  not-accessible
   STATUS      current
   DESCRIPTION
       "MLD Snooping SSM Index"
   ::= { gs2328MLDSnoopingSSMEntry 1 }

gs2328MLDSnoopingSSMVLANID OBJECT-TYPE
   SYNTAX      Integer32(1..4095)
   MAX-ACCESS  read-only
   STATUS      current
   DESCRIPTION
       "VLAN ID of the group. "
   ::= { gs2328MLDSnoopingSSMEntry 2 }

gs2328MLDSnoopingSSMGroup OBJECT-TYPE
   SYNTAX      DisplayString
   MAX-ACCESS  read-only
   STATUS      current
   DESCRIPTION
       "Group address of the group displayed."
   ::= { gs2328MLDSnoopingSSMEntry 3 }

gs2328MLDSnoopingSSMPort OBJECT-TYPE
   SYNTAX      Integer32(1..65535)
   MAX-ACCESS  read-only
   STATUS      current
   DESCRIPTION
       "Ports under this group."
   ::= { gs2328MLDSnoopingSSMEntry 4 }
   
gs2328MLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2328MLDSnoopingSSMEntry 5 }
   
gs2328MLDSnoopingSSMSourceAddress OBJECT-TYPE
   SYNTAX      DisplayString
   MAX-ACCESS  read-only
   STATUS      current
   DESCRIPTION
       "IP Address of the source. Currently, system limits the total number of
       IP source addresses for filtering to be 128."
   ::= { gs2328MLDSnoopingSSMEntry 6 }

gs2328MLDSnoopingSSMType OBJECT-TYPE
   SYNTAX      DisplayString
   MAX-ACCESS  read-only
   STATUS      current
   DESCRIPTION
       "Indicates the Type. It can be either Allow or Deny."
   ::= { gs2328MLDSnoopingSSMEntry 7 }      
   

gs2328MVR                                                                   OBJECT IDENTIFIER ::= { gs2328Configuration 18 }

gs2328MVRConfiguration                                                      OBJECT IDENTIFIER ::= { gs2328MVR 1 }

gs2328MVRMode  OBJECT-TYPE
   SYNTAX      INTEGER { disable(0), enable(1) }
   MAX-ACCESS  read-write
   STATUS      current
   DESCRIPTION
       "Enable/Disable the Global MVR. "
   ::= { gs2328MVRConfiguration 1 }

gs2328MVRVLANId  OBJECT-TYPE
   SYNTAX      Integer32(1..4094)
   MAX-ACCESS  read-write
   STATUS      current
   DESCRIPTION
       "Specify the Multicast VLAN ID. "
   ::= { gs2328MVRConfiguration 2 }

gs2328MVRPortConfigurationTable OBJECT-TYPE
   SYNTAX      SEQUENCE OF Gs2328MVRPortConfigurationEntry
   MAX-ACCESS  not-accessible
   STATUS      current
   DESCRIPTION
       " Configure MVR Port Configuration. "
   ::= { gs2328MVRConfiguration 3 }

gs2328MVRPortConfigurationEntry OBJECT-TYPE
   SYNTAX      Gs2328MVRPortConfigurationEntry
   MAX-ACCESS  not-accessible
   STATUS      current
   DESCRIPTION
       ""
   INDEX    { ifIndex  }
   ::= { gs2328MVRPortConfigurationTable 1 }

Gs2328MVRPortConfigurationEntry ::= SEQUENCE {
   gs2328MVRPortConfigurationMode	INTEGER,
   gs2328MVRPortConfigurationType  	INTEGER,
   gs2328MVRPortConfigurationImmediateLeave    INTEGER
}

gs2328MVRPortConfigurationMode OBJECT-TYPE
   SYNTAX      INTEGER { disable(0), enable(1) }
   MAX-ACCESS  read-write
   STATUS      current
   DESCRIPTION
       "Enable MVR on the port. "
   ::= { gs2328MVRPortConfigurationEntry 1 }

gs2328MVRPortConfigurationType OBJECT-TYPE
   SYNTAX      INTEGER { receiver(0), source(1) }
   MAX-ACCESS  read-write
   STATUS      current
   DESCRIPTION
       "Specify the MVR port type on the port. "
   ::= { gs2328MVRPortConfigurationEntry 2 }
   
gs2328MVRPortConfigurationImmediateLeave OBJECT-TYPE
   SYNTAX      INTEGER { disable(0), enable(1) }
   MAX-ACCESS  read-write
   STATUS      current
   DESCRIPTION
       "Enable the fast leave on the port. "
   ::= { gs2328MVRPortConfigurationEntry 3 }
      

gs2328MVRPortGroupFiltering                                                      OBJECT IDENTIFIER ::= { gs2328MVR 2 }

gs2328MVRPortGroupFilteringCreate OBJECT-TYPE
   SYNTAX       Integer32
   MAX-ACCESS   read-write
   STATUS       current
   DESCRIPTION
       "default: 0
       0 : None  (read only) 1 : Create MLD Snooping Port Group Filtering "
   ::= { gs2328MVRPortGroupFiltering 1 }

gs2328MVRPortGroupFilteringTable OBJECT-TYPE
   SYNTAX      SEQUENCE OF Gs2328MVRPortGroupFilteringEntry
   MAX-ACCESS  not-accessible
   STATUS      current
   DESCRIPTION
       " Configure MVR port group filtering. "
   ::= { gs2328MVRPortGroupFiltering 2 }

gs2328MVRPortGroupFilteringEntry OBJECT-TYPE
   SYNTAX      Gs2328MVRPortGroupFilteringEntry
   MAX-ACCESS  not-accessible
   STATUS      current
   DESCRIPTION
       ""
   INDEX    { gs2328MVRPortGroupFilteringIndex  }
   ::= { gs2328MVRPortGroupFilteringTable 1 }

Gs2328MVRPortGroupFilteringEntry ::= SEQUENCE {
   gs2328MVRPortGroupFilteringIndex         Integer32,
   gs2328MVRPortGroupFilteringPort          Integer32,
   gs2328MVRPortGroupFilteringStartGroups   DisplayString,
   gs2328MVRPortGroupFilteringEndGroups     DisplayString,
   gs2328MVRPortGroupFilteringRowStatus     INTEGER
}

gs2328MVRPortGroupFilteringIndex OBJECT-TYPE
   SYNTAX      Integer32(1..65535)
   MAX-ACCESS  not-accessible
   STATUS      current
   DESCRIPTION
       "MVR Port Group Filtering Configuration Index. "
   ::= { gs2328MVRPortGroupFilteringEntry 1 }

gs2328MVRPortGroupFilteringPort OBJECT-TYPE
   SYNTAX      Integer32(1..65535)
   MAX-ACCESS  read-write
   STATUS      current
   DESCRIPTION
       "The logical port for the settings. "
   ::= { gs2328MVRPortGroupFilteringEntry 2 }

gs2328MVRPortGroupFilteringStartGroups OBJECT-TYPE
   SYNTAX      DisplayString
   MAX-ACCESS  read-write
   STATUS      current
   DESCRIPTION
       "The IP Multicast Group that will be allowed. "
   ::= { gs2328MVRPortGroupFilteringEntry 3 }

gs2328MVRPortGroupFilteringEndGroups OBJECT-TYPE
   SYNTAX      DisplayString
   MAX-ACCESS  read-write
   STATUS      current
   DESCRIPTION
       "The IP Multicast Group that will be allowed. "
   ::= { gs2328MVRPortGroupFilteringEntry 4 }   

gs2328MVRPortGroupFilteringRowStatus OBJECT-TYPE
   SYNTAX      INTEGER { active(1), notInservice(2), destroy(4)}
   MAX-ACCESS  read-write
   STATUS      current
   DESCRIPTION
       "1: active
        2: notInservice
        4: destroy"
   ::= { gs2328MVRPortGroupFilteringEntry 5 }

gs2328MVRGroupsTable OBJECT-TYPE
   SYNTAX      SEQUENCE OF Gs2328MVRGroupsEntry
   MAX-ACCESS  not-accessible
   STATUS      current
   DESCRIPTION
       "MVR Groups Information . "
   ::= { gs2328MVR 3 }

gs2328MVRGroupsEntry OBJECT-TYPE
   SYNTAX      Gs2328MVRGroupsEntry
   MAX-ACCESS  not-accessible
   STATUS      current
   DESCRIPTION
       ""
   INDEX    { gs2328MVRGroupsIndex  }
   ::= { gs2328MVRGroupsTable 1 }

Gs2328MVRGroupsEntry ::= SEQUENCE {
   gs2328MVRGroupsIndex          Integer32,
   gs2328MVRGroupsVLANID         Integer32,
   gs2328MVRGroups               InetAddress,
   gs2328MVRGroupsMemberships    DisplayString
}

gs2328MVRGroupsIndex OBJECT-TYPE
   SYNTAX      Integer32(1..65535)
   MAX-ACCESS  not-accessible
   STATUS      current
   DESCRIPTION
       "MVR Groups Index"
   ::= { gs2328MVRGroupsEntry 1 }

gs2328MVRGroupsVLANID OBJECT-TYPE
   SYNTAX      Integer32(1..4095)
   MAX-ACCESS  read-only
   STATUS      current
   DESCRIPTION
       "VLAN ID of the group. "
   ::= { gs2328MVRGroupsEntry 2 }

gs2328MVRGroups OBJECT-TYPE
   SYNTAX      DisplayString
   MAX-ACCESS  read-only
   STATUS      current
   DESCRIPTION
       "Group address of the group displayed."
   ::= { gs2328MVRGroupsEntry 3 }

gs2328MVRGroupsMemberships OBJECT-TYPE
   SYNTAX      DisplayString
   MAX-ACCESS  read-only
   STATUS      current
   DESCRIPTION
       "Ports under this group."
   ::= { gs2328MVRGroupsEntry 4 }
            

gs2328MVRStatus                                                      OBJECT IDENTIFIER ::= { gs2328MVR 4 }

gs2328MVRstatisticClear OBJECT-TYPE
   SYNTAX      INTEGER { none(0), clear(1)}
   MAX-ACCESS  read-write
   STATUS      current
   DESCRIPTION
       "Clears all Statistics counters."
   ::= { gs2328MVRStatus 1 }

gs2328MVRstatisticVLANID OBJECT-TYPE
   SYNTAX      Integer32(1..4095)
   MAX-ACCESS  read-only
   STATUS      current
   DESCRIPTION
       "The VLAN ID of the entry. "
   ::= { gs2328MVRStatus 2 }

gs2328MVRstatisticV1ReportsReceived OBJECT-TYPE
   SYNTAX      Counter32
   MAX-ACCESS  read-only
   STATUS      current
   DESCRIPTION
       "The number of Received V1 Reports. "
   ::= { gs2328MVRStatus 3 }

gs2328MVRstatisticV2ReportsReceived OBJECT-TYPE
   SYNTAX      Counter32
   MAX-ACCESS  read-only
   STATUS      current
   DESCRIPTION
       "The number of Received V2 Reports. "
   ::= { gs2328MVRStatus 4 }
   
gs2328MVRstatisticV3ReportsReceived OBJECT-TYPE
   SYNTAX      Counter32
   MAX-ACCESS  read-only
   STATUS      current
   DESCRIPTION
       "The number of Received V3 Reports. "
   ::= { gs2328MVRStatus 5 }

gs2328MVRstatisticV2LeavesReceived OBJECT-TYPE
   SYNTAX      Counter32
   MAX-ACCESS  read-only
   STATUS      current
   DESCRIPTION
       "The number of Received V2 Leaves. "
   ::= { gs2328MVRStatus 6 }

gs2328LACP                                                     OBJECT IDENTIFIER ::= { gs2328Configuration 19 }

gs2328LACPConf                                                 OBJECT IDENTIFIER ::= { gs2328LACP 1 }

gs2328LACPPortConfigurationTable OBJECT-TYPE
   SYNTAX      SEQUENCE OF Gs2328LACPPortConfigurationEntry
   MAX-ACCESS  not-accessible
   STATUS      current
   DESCRIPTION
       " "
   ::= { gs2328LACPConf 1 }

gs2328LACPPortConfigurationEntry OBJECT-TYPE
   SYNTAX      Gs2328LACPPortConfigurationEntry
   MAX-ACCESS  not-accessible
   STATUS      current
   DESCRIPTION
       ""
   INDEX    { gs2328LACPPortConfigurationPort  }
   ::= { gs2328LACPPortConfigurationTable 1 }
   
Gs2328LACPPortConfigurationEntry ::= SEQUENCE {
    gs2328LACPPortConfigurationPort         Integer32,
    gs2328LACPPortConfigurationMode         INTEGER,
    gs2328LACPPortConfigurationKey          Integer32,
    gs2328LACPPortConfigurationRole         INTEGER
}

gs2328LACPPortConfigurationPort OBJECT-TYPE
   SYNTAX      Integer32(1..4095)
   MAX-ACCESS  not-accessible
   STATUS      current
   DESCRIPTION
       " "
   ::= { gs2328LACPPortConfigurationEntry 1 }

gs2328LACPPortConfigurationMode OBJECT-TYPE
   SYNTAX      INTEGER { disable(0), enable(1) }
   MAX-ACCESS  read-write
   STATUS      current
   DESCRIPTION
       "Enable/Disable LACP Mode."
   ::= { gs2328LACPPortConfigurationEntry 2 }
   
gs2328LACPPortConfigurationKey OBJECT-TYPE
   SYNTAX      Integer32(0..65535)
   MAX-ACCESS  read-write
   STATUS      current
   DESCRIPTION
       "LACP key : 1-65535. 0 : Auto"
   ::= { gs2328LACPPortConfigurationEntry 3 }
   
gs2328LACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2328LACPPortConfigurationEntry 4 }

gs2328LACPSystemStatusTable OBJECT-TYPE
   SYNTAX      SEQUENCE OF Gs2328LACPSystemStatusEntry
   MAX-ACCESS  not-accessible
   STATUS      current
   DESCRIPTION
       " "
   ::= { gs2328LACP 2 }

gs2328LACPSystemStatusEntry OBJECT-TYPE
   SYNTAX      Gs2328LACPSystemStatusEntry
   MAX-ACCESS  not-accessible
   STATUS      current
   DESCRIPTION
       ""
   INDEX    { gs2328LACPSystemStatusIndex  }
   ::= { gs2328LACPSystemStatusTable 1 }

Gs2328LACPSystemStatusEntry ::= SEQUENCE {
   gs2328LACPSystemStatusIndex             Integer32,
   gs2328LACPSystemStatusAggrID            DisplayString,
   gs2328LACPSystemStatusPartnerSystemID   MacAddress,
   gs2328LACPSystemStatusPartnerKey        DisplayString,
   gs2328LACPSystemStatusLastchanged       DisplayString,
   gs2328LACPSystemStatusLocalPorts        DisplayString
}

gs2328LACPSystemStatusIndex OBJECT-TYPE
   SYNTAX      Integer32(1..12)
   MAX-ACCESS  not-accessible
   STATUS      current
   DESCRIPTION
       " "
   ::= { gs2328LACPSystemStatusEntry 1 }

gs2328LACPSystemStatusAggrID OBJECT-TYPE
   SYNTAX      DisplayString
   MAX-ACCESS  read-only
   STATUS      current
   DESCRIPTION
       "The Aggregation ID associated with this aggregation instance."
   ::= { gs2328LACPSystemStatusEntry 2 }
   
gs2328LACPSystemStatusPartnerSystemID OBJECT-TYPE
   SYNTAX      MacAddress
   MAX-ACCESS  read-only
   STATUS      current
   DESCRIPTION
       "The system ID (MAC address) of the aggregation partner."
   ::= { gs2328LACPSystemStatusEntry 3 }

gs2328LACPSystemStatusPartnerKey OBJECT-TYPE
   SYNTAX      DisplayString
   MAX-ACCESS  read-only
   STATUS      current
   DESCRIPTION
       " The Key that the partner has assigned to this aggregation ID. "
   ::= { gs2328LACPSystemStatusEntry 4 }

gs2328LACPSystemStatusLastchanged OBJECT-TYPE
   SYNTAX      DisplayString
   MAX-ACCESS  read-only
   STATUS      current
   DESCRIPTION
       " The time since this aggregation changed. "
   ::= { gs2328LACPSystemStatusEntry 5 }
   
gs2328LACPSystemStatusLocalPorts OBJECT-TYPE
   SYNTAX      DisplayString
   MAX-ACCESS  read-only
   STATUS      current
   DESCRIPTION
       " Shows which ports are a part of this aggregation for this switch. "
   ::= { gs2328LACPSystemStatusEntry 6 }

gs2328LACPStatusTable OBJECT-TYPE
   SYNTAX      SEQUENCE OF Gs2328LACPStatusEntry
   MAX-ACCESS  not-accessible
   STATUS      current
   DESCRIPTION
       " "
   ::= { gs2328LACP 3 }

gs2328LACPStatusEntry OBJECT-TYPE
   SYNTAX      Gs2328LACPStatusEntry
   MAX-ACCESS  not-accessible
   STATUS      current
   DESCRIPTION
       ""
   INDEX    { gs2328LACPStatusPort  }
   ::= { gs2328LACPStatusTable 1 }

Gs2328LACPStatusEntry ::= SEQUENCE {
   gs2328LACPStatusPort                Integer32,
   gs2328LACPStatusLACP                DisplayString,
   gs2328LACPStatusKey                 DisplayString,
   gs2328LACPStatusAggrID              DisplayString,
   gs2328LACPStatusPartnerSystemID     DisplayString,
   gs2328LACPStatusPartnerPort         DisplayString
}

gs2328LACPStatusPort OBJECT-TYPE
   SYNTAX      Integer32(1..4095)
   MAX-ACCESS  not-accessible
   STATUS      current
   DESCRIPTION
       " "
   ::= { gs2328LACPStatusEntry 1 }

gs2328LACPStatusLACP OBJECT-TYPE
   SYNTAX      DisplayString
   MAX-ACCESS  read-only
   STATUS      current
   DESCRIPTION
       "Enabled means that LACP is enabled and the port link is up. 
        Disabled means that LACP is not enabled or that the port link is down. 
        Backup means that the port could not join the aggregation group but will join if other port leaves. 
        Meanwhile it's LACP status is disabled."
   ::= { gs2328LACPStatusEntry 2 }
   
gs2328LACPStatusKey OBJECT-TYPE
   SYNTAX      DisplayString
   MAX-ACCESS  read-only
   STATUS      current
   DESCRIPTION
       "The key assigned to this port. Only ports with the same key can aggregate together."
   ::= { gs2328LACPStatusEntry 3 }

gs2328LACPStatusAggrID	 OBJECT-TYPE
   SYNTAX      DisplayString
   MAX-ACCESS  read-only
   STATUS      current
   DESCRIPTION
       " The Aggregation ID assigned to this aggregation group. "
   ::= { gs2328LACPStatusEntry 4 }

gs2328LACPStatusPartnerSystemID OBJECT-TYPE
   SYNTAX      DisplayString
   MAX-ACCESS  read-only
   STATUS      current
   DESCRIPTION
       " The partner's System ID. "
   ::= { gs2328LACPStatusEntry 5 }
   
gs2328LACPStatusPartnerPort OBJECT-TYPE
   SYNTAX      DisplayString
   MAX-ACCESS  read-only
   STATUS      current
   DESCRIPTION
       " The partner's port number connected to this port. "
   ::= { gs2328LACPStatusEntry 6 }


gs2328LACPStatisticsTable OBJECT-TYPE
   SYNTAX      SEQUENCE OF Gs2328LACPStatisticsEntry
   MAX-ACCESS  not-accessible
   STATUS      current
   DESCRIPTION
       " "
   ::= { gs2328LACP 4 }

gs2328LACPStatisticsEntry OBJECT-TYPE
   SYNTAX      Gs2328LACPStatisticsEntry
   MAX-ACCESS  not-accessible
   STATUS      current
   DESCRIPTION
       ""
   INDEX    { gs2328LACPStatisticsPort  }
   ::= { gs2328LACPStatisticsTable 1 }

Gs2328LACPStatisticsEntry ::= SEQUENCE {
   gs2328LACPStatisticsPort        Integer32,
   gs2328LACPReceived              Counter32,
   gs2328LACPTransmitted           Counter32,
   gs2328LACPDiscardedUnknown      Counter32,
   gs2328LACPDiscardedIllegal      Counter32
}

gs2328LACPStatisticsPort OBJECT-TYPE
   SYNTAX      Integer32(1..4095)
   MAX-ACCESS  not-accessible
   STATUS      current
   DESCRIPTION
       " "
   ::= { gs2328LACPStatisticsEntry 1 }
   
gs2328LACPReceived OBJECT-TYPE
   SYNTAX      Counter32
   MAX-ACCESS  read-only
   STATUS      current
   DESCRIPTION
       "Shows how many LACP frames have been received at each port. "
   ::= { gs2328LACPStatisticsEntry 2 }

gs2328LACPTransmitted OBJECT-TYPE
   SYNTAX      Counter32
   MAX-ACCESS  read-only
   STATUS      current
   DESCRIPTION
       " Shows how many LACP frames have been sent from each port. "
   ::= { gs2328LACPStatisticsEntry 3 }

gs2328LACPDiscardedUnknown OBJECT-TYPE
   SYNTAX      Counter32
   MAX-ACCESS  read-only
   STATUS      current
   DESCRIPTION
       " Shows how many unknown LACP frames have been discarded at each port. "
   ::= { gs2328LACPStatisticsEntry 4 }
   
gs2328LACPDiscardedIllegal OBJECT-TYPE
   SYNTAX      Counter32
   MAX-ACCESS  read-only
   STATUS      current
   DESCRIPTION
       " Shows how many illegal LACP frames have been discarded at each port. "
   ::= { gs2328LACPStatisticsEntry 5 }
   
gs2328LACPStatisticsClear OBJECT-TYPE
   SYNTAX      INTEGER { none(0), clear(1) }
   MAX-ACCESS  read-write
   STATUS      current
   DESCRIPTION
       "default: 0
       0: none
       1: clear"
   ::= { gs2328LACP 5 }
   
gs2328STP                                                     OBJECT IDENTIFIER ::= { gs2328Configuration 20 }

gs2328STPBridgeBasicConf                                                 OBJECT IDENTIFIER ::= { gs2328STP 1 }

gs2328STPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2328STPBridgeBasicConf 1 }

gs2328STPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2328STPBridgeBasicConf 2 }
   
gs2328STPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2328STPBridgeBasicConf 3 }
   
gs2328STPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2328STPBridgeBasicConf 4 }
   
gs2328STPBridgeMaximumHopCount OBJECT-TYPE
   SYNTAX      Integer32(6..40)
   MAX-ACCESS  read-write
   STATUS      current
   DESCRIPTION
       " Maximum Hop Count default: 20, range: 6 - 40."
   ::= { gs2328STPBridgeBasicConf 5 }
   
gs2328STPBridgeTransmitHoldCount OBJECT-TYPE
   SYNTAX      Integer32(1..10)
   MAX-ACCESS  read-write
   STATUS      current
   DESCRIPTION
       " Transmit Hold Count default: 6, range: 1 - 10."
   ::= { gs2328STPBridgeBasicConf 6 }
   
gs2328STPBridgeAdvancedConf                                                 OBJECT IDENTIFIER ::= { gs2328STP 2 }

gs2328STPBridgeEdgePortBPDUFiltering OBJECT-TYPE
   SYNTAX      INTEGER { disable(0), enable(1) }
   MAX-ACCESS  read-write
   STATUS      current
   DESCRIPTION
       " default: 0,
        0: disable
        1: enable"
   ::= { gs2328STPBridgeAdvancedConf 1 }
   
gs2328STPBridgeEdgePortBPDUGuard OBJECT-TYPE
   SYNTAX      INTEGER { disable(0), enable(1) }
   MAX-ACCESS  read-write
   STATUS      current
   DESCRIPTION
       " default: 0,
        0: disable
        1: enable"
   ::= { gs2328STPBridgeAdvancedConf 2 }
   
gs2328STPBridgePortErrorRecoveryTimeout OBJECT-TYPE
   SYNTAX      Integer32(0..86400)
   MAX-ACCESS  read-write
   STATUS      current
   DESCRIPTION
       " Port Error Recovery Timeout disable: 0, range: 30 - 86400."
   ::= { gs2328STPBridgeAdvancedConf 3 }
   
gs2328STPMSTIConf                                                 OBJECT IDENTIFIER ::= { gs2328STP 3 }
   
gs2328STPMSTIConfigurationName OBJECT-TYPE
   SYNTAX      DisplayString (SIZE (1..32))
   MAX-ACCESS  read-write
   STATUS      current
   DESCRIPTION
       "A text string up to 32 characters long."
   ::= { gs2328STPMSTIConf 1 }
   
gs2328STPMSTIConfigurationRevision   OBJECT-TYPE
   SYNTAX      Integer32(0..65535)
   MAX-ACCESS  read-write
   STATUS      current
   DESCRIPTION
       " Configuration Revision default: 0, range: 0 - 65535."
   ::= { gs2328STPMSTIConf 2 }
   
gs2328STPMSTIMappingConf                                                 OBJECT IDENTIFIER ::= { gs2328STP 4 }
   
gs2328STPMSTI1VLANsMapped OBJECT-TYPE
   SYNTAX      DisplayString (SIZE (1..4096))
   MAX-ACCESS  read-write
   STATUS      current
   DESCRIPTION
       "The list of VLANs mapped to the MSTI1. 
       The VLANs must be separated with comma or space. 
       An unused MSTI should just be left empty. "
   ::= { gs2328STPMSTIMappingConf 1 }

gs2328STPMSTI2VLANsMapped OBJECT-TYPE
   SYNTAX      DisplayString (SIZE (1..4096))
   MAX-ACCESS  read-write
   STATUS      current
   DESCRIPTION
       "The list of VLANs mapped to the MSTI2. 
       The VLANs must be separated with comma or space. 
       An unused MSTI should just be left empty. "
   ::= { gs2328STPMSTIMappingConf 2 }
   
gs2328STPMSTI3VLANsMapped OBJECT-TYPE
   SYNTAX      DisplayString (SIZE (1..4096))
   MAX-ACCESS  read-write
   STATUS      current
   DESCRIPTION
       "The list of VLANs mapped to the MSTI3. 
       The VLANs must be separated with comma or space. 
       An unused MSTI should just be left empty. "
   ::= { gs2328STPMSTIMappingConf 3 }
   
gs2328STPMSTI4VLANsMapped OBJECT-TYPE
   SYNTAX      DisplayString (SIZE (1..4096))
   MAX-ACCESS  read-write
   STATUS      current
   DESCRIPTION
       "The list of VLANs mapped to the MSTI4. 
       The VLANs must be separated with comma or space. 
       An unused MSTI should just be left empty. "
   ::= { gs2328STPMSTIMappingConf 4 }
   
gs2328STPMSTI5VLANsMapped OBJECT-TYPE
   SYNTAX      DisplayString (SIZE (1..4096))
   MAX-ACCESS  read-write
   STATUS      current
   DESCRIPTION
       "The list of VLANs mapped to the MSTI5. 
       The VLANs must be separated with comma or space. 
       An unused MSTI should just be left empty. "
   ::= { gs2328STPMSTIMappingConf 5 }

gs2328STPMSTI6VLANsMapped OBJECT-TYPE
   SYNTAX      DisplayString (SIZE (1..4096))
   MAX-ACCESS  read-write
   STATUS      current
   DESCRIPTION
       "The list of VLANs mapped to the MSTI6. 
       The VLANs must be separated with comma or space. 
       An unused MSTI should just be left empty. "
   ::= { gs2328STPMSTIMappingConf 6 }
   
gs2328STPMSTI7VLANsMapped OBJECT-TYPE
   SYNTAX      DisplayString (SIZE (1..4096))
   MAX-ACCESS  read-write
   STATUS      current
   DESCRIPTION
       "The list of VLANs mapped to the MSTI7. 
       The VLANs must be separated with comma or space. 
       An unused MSTI should just be left empty. "
   ::= { gs2328STPMSTIMappingConf 7 }
   
gs2328STPMSTIPriority                                                 OBJECT IDENTIFIER ::= { gs2328STP 5 }
   
gs2328STPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328STPMSTIPriority 1 }
   
gs2328STPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328STPMSTIPriority 2 }
   
gs2328STPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328STPMSTIPriority 3 }
   
gs2328STPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328STPMSTIPriority 4 }
   
gs2328STPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328STPMSTIPriority 5 }
   
gs2328STPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328STPMSTIPriority 6 }

gs2328STPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328STPMSTIPriority 7 }  

gs2328STPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328STPMSTIPriority 8 }
   
gs2328STPCISTPort                                                          OBJECT IDENTIFIER ::= { gs2328STP 6 }

gs2328STPCISTAggregatedPort                                                OBJECT IDENTIFIER ::= { gs2328STPCISTPort 1 }
   
gs2328STPCISTAggregatedPortSTPEnabled OBJECT-TYPE
   SYNTAX      INTEGER { disable(0), enable(1) }
   MAX-ACCESS  read-write
   STATUS      current
   DESCRIPTION
       " default: 0,
        0: disable
        1: enable"
   ::= { gs2328STPCISTAggregatedPort 1 }
   
gs2328STPCISTAggregatedPortPathCost OBJECT-TYPE
   SYNTAX      Integer32(0..200000000)
   MAX-ACCESS  read-write
   STATUS      current
   DESCRIPTION
       " Auto: 0,
        Specific Path Cost range: 1 - 200000000."
   ::= { gs2328STPCISTAggregatedPort 2 }
   
gs2328STPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2328STPCISTAggregatedPort 3 }
   
gs2328STPCISTAggregatedPortAdminEdge OBJECT-TYPE
   SYNTAX      INTEGER { non-edge(0), edge(1) }
   MAX-ACCESS  read-write
   STATUS      current
   DESCRIPTION
       " default: 0,
        0: non-edge
        1: edge"
   ::= { gs2328STPCISTAggregatedPort 4 }

gs2328STPCISTAggregatedPortAutoEdge OBJECT-TYPE
   SYNTAX      INTEGER { disable(0), enable(1) }
   MAX-ACCESS  read-write
   STATUS      current
   DESCRIPTION
       " default: 1,
        0: disable
        1: enable"
   ::= { gs2328STPCISTAggregatedPort 5 }
   
gs2328STPCISTAggregatedPortRestrictedRole OBJECT-TYPE
   SYNTAX      INTEGER { disable(0), enable(1) }
   MAX-ACCESS  read-write
   STATUS      current
   DESCRIPTION
       " default: 0,
        0: disable
        1: enable"
   ::= { gs2328STPCISTAggregatedPort 6 }
   
gs2328STPCISTAggregatedPortRestrictedTCN OBJECT-TYPE
   SYNTAX      INTEGER { disable(0), enable(1) }
   MAX-ACCESS  read-write
   STATUS      current
   DESCRIPTION
       " default: 0,
        0: disable
        1: enable"
   ::= { gs2328STPCISTAggregatedPort 7 }
   
gs2328STPCISTAggregatedPortBPDUGuard OBJECT-TYPE
   SYNTAX      INTEGER { disable(0), enable(1) }
   MAX-ACCESS  read-write
   STATUS      current
   DESCRIPTION
       " default: 0,
        0: disable
        1: enable"
   ::= { gs2328STPCISTAggregatedPort 8 }
   
gs2328STPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2328STPCISTAggregatedPort 9 }
   
gs2328STPCISTNormalPortTable OBJECT-TYPE
   SYNTAX      SEQUENCE OF Gs2328STPCISTNormalPortEntry
   MAX-ACCESS  not-accessible
   STATUS      current
   DESCRIPTION
       " Show CIST Normal Port Configurations. "
   ::= { gs2328STPCISTPort 2 }

gs2328STPCISTNormalPortEntry OBJECT-TYPE
   SYNTAX      Gs2328STPCISTNormalPortEntry
   MAX-ACCESS  not-accessible
   STATUS      current
   DESCRIPTION
       ""
   INDEX    { gs2328STPCISTNormalPortConfPort  }
   ::= { gs2328STPCISTNormalPortTable 1 }

Gs2328STPCISTNormalPortEntry ::= SEQUENCE {
   gs2328STPCISTNormalPortConfPort         Integer32,
   gs2328STPCISTNormalPortSTPEnabled       INTEGER,
   gs2328STPCISTNormalPortPathCost         Integer32,
   gs2328STPCISTNormalPortPriority         Integer32,
   gs2328STPCISTNormalPortAdminEdge        INTEGER,
   gs2328STPCISTNormalPortAutoEdge         INTEGER,
   gs2328STPCISTNormalPortRestrictedRole   INTEGER,
   gs2328STPCISTNormalPortRestrictedTCN    INTEGER,
   gs2328STPCISTNormalPortBPDUGuard        INTEGER,
   gs2328STPCISTNormalPortPointtoPoint     INTEGER
}

gs2328STPCISTNormalPortConfPort OBJECT-TYPE
   SYNTAX      Integer32(1..4095)
   MAX-ACCESS  not-accessible
   STATUS      current
   DESCRIPTION
       " port, range : 1 - port number. "
   ::= { gs2328STPCISTNormalPortEntry 1 }
   
gs2328STPCISTNormalPortSTPEnabled OBJECT-TYPE
   SYNTAX      INTEGER { disable(0), enable(1) }
   MAX-ACCESS  read-write
   STATUS      current
   DESCRIPTION
       " default: 0,
        0: disable
        1: enable"
   ::= { gs2328STPCISTNormalPortEntry 2 }
   
gs2328STPCISTNormalPortPathCost OBJECT-TYPE
   SYNTAX      Integer32(0..200000000)
   MAX-ACCESS  read-write
   STATUS      current
   DESCRIPTION
       " Auto: 0,
        Specific Path Cost range: 1 - 200000000."
   ::= { gs2328STPCISTNormalPortEntry 3 }
   
gs2328STPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2328STPCISTNormalPortEntry 4 }
   
gs2328STPCISTNormalPortAdminEdge OBJECT-TYPE
   SYNTAX      INTEGER { non-edge(0), edge(1) }
   MAX-ACCESS  read-write
   STATUS      current
   DESCRIPTION
       " default: 0,
        0: non-edge
        1: edge"
   ::= { gs2328STPCISTNormalPortEntry 5 }
   
gs2328STPCISTNormalPortAutoEdge OBJECT-TYPE
   SYNTAX      INTEGER { disable(0), enable(1) }
   MAX-ACCESS  read-write
   STATUS      current
   DESCRIPTION
       " default: 1,
        0: disable
        1: enable"
   ::= { gs2328STPCISTNormalPortEntry 6 }
   
gs2328STPCISTNormalPortRestrictedRole OBJECT-TYPE
   SYNTAX      INTEGER { disable(0), enable(1) }
   MAX-ACCESS  read-write
   STATUS      current
   DESCRIPTION
       " default: 0,
        0: disable
        1: enable"
   ::= { gs2328STPCISTNormalPortEntry 7 }
   
gs2328STPCISTNormalPortRestrictedTCN OBJECT-TYPE
   SYNTAX      INTEGER { disable(0), enable(1) }
   MAX-ACCESS  read-write
   STATUS      current
   DESCRIPTION
       " default: 0,
        0: disable
        1: enable"
   ::= { gs2328STPCISTNormalPortEntry 8 }
   
gs2328STPCISTNormalPortBPDUGuard OBJECT-TYPE
   SYNTAX      INTEGER { disable(0), enable(1) }
   MAX-ACCESS  read-write
   STATUS      current
   DESCRIPTION
       " default: 0,
        0: disable
        1: enable"
   ::= { gs2328STPCISTNormalPortEntry 9 }
   
gs2328STPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2328STPCISTNormalPortEntry 10 }
   

gs2328STPMSTIPort                                                          OBJECT IDENTIFIER ::= { gs2328STP 7 }

gs2328STPMSTI1Port                                                         OBJECT IDENTIFIER ::= { gs2328STPMSTIPort 1 }

gs2328STPMSTI1AggregatedPort                                                OBJECT IDENTIFIER ::= { gs2328STPMSTI1Port 1 }
      
gs2328STPMSTI1AggregatedPortPathCost OBJECT-TYPE
   SYNTAX      Integer32(0..200000000)
   MAX-ACCESS  read-write
   STATUS      current
   DESCRIPTION
       " Auto: 0,
        Specific Path Cost range: 1 - 200000000."
   ::= { gs2328STPMSTI1AggregatedPort 1 }
   
gs2328STPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI1AggregatedPort 2 }
   
gs2328STPMSTI1NormalPortTable OBJECT-TYPE
   SYNTAX      SEQUENCE OF Gs2328STPMSTI1NormalPortEntry
   MAX-ACCESS  not-accessible
   STATUS      current
   DESCRIPTION
       " Show MSTI1 Normal Port Configurations. "
   ::= { gs2328STPMSTI1Port 2 }

gs2328STPMSTI1NormalPortEntry OBJECT-TYPE
   SYNTAX      Gs2328STPMSTI1NormalPortEntry
   MAX-ACCESS  not-accessible
   STATUS      current
   DESCRIPTION
       ""
   INDEX    { gs2328STPMSTI1NormalPortConfPort  }
   ::= { gs2328STPMSTI1NormalPortTable 1 }

Gs2328STPMSTI1NormalPortEntry ::= SEQUENCE {
   gs2328STPMSTI1NormalPortConfPort         Integer32,
   gs2328STPMSTI1NormalPortPathCost         Integer32,
   gs2328STPMSTI1NormalPortPriority         Integer32
}

gs2328STPMSTI1NormalPortConfPort OBJECT-TYPE
   SYNTAX      Integer32(1..4095)
   MAX-ACCESS  not-accessible
   STATUS      current
   DESCRIPTION
       " port, range : 1 - port number. "
   ::= { gs2328STPMSTI1NormalPortEntry 1 }
   
gs2328STPMSTI1NormalPortPathCost OBJECT-TYPE
   SYNTAX      Integer32(0..200000000)
   MAX-ACCESS  read-write
   STATUS      current
   DESCRIPTION
       " Auto: 0,
        Specific Path Cost range: 1 - 200000000."
   ::= { gs2328STPMSTI1NormalPortEntry 2 }
   
gs2328STPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI1NormalPortEntry 3 }

gs2328STPMSTI2Port                                                          OBJECT IDENTIFIER ::= { gs2328STPMSTIPort 2 }

gs2328STPMSTI2AggregatedPort                                                OBJECT IDENTIFIER ::= { gs2328STPMSTI2Port 1 }
      
gs2328STPMSTI2AggregatedPortPathCost OBJECT-TYPE
   SYNTAX      Integer32(0..200000000)
   MAX-ACCESS  read-write
   STATUS      current
   DESCRIPTION
       " Auto: 0,
        Specific Path Cost range: 1 - 200000000."
   ::= { gs2328STPMSTI2AggregatedPort 1 }
   
gs2328STPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI2AggregatedPort 2 }
   
gs2328STPMSTI2NormalPortTable OBJECT-TYPE
   SYNTAX      SEQUENCE OF Gs2328STPMSTI2NormalPortEntry
   MAX-ACCESS  not-accessible
   STATUS      current
   DESCRIPTION
       " Show MSTI2 Normal Port Configurations. "
   ::= { gs2328STPMSTI2Port 2 }

gs2328STPMSTI2NormalPortEntry OBJECT-TYPE
   SYNTAX      Gs2328STPMSTI2NormalPortEntry
   MAX-ACCESS  not-accessible
   STATUS      current
   DESCRIPTION
       ""
   INDEX    { gs2328STPMSTI2NormalPortConfPort  }
   ::= { gs2328STPMSTI2NormalPortTable 1 }

Gs2328STPMSTI2NormalPortEntry ::= SEQUENCE {
   gs2328STPMSTI2NormalPortConfPort         Integer32,
   gs2328STPMSTI2NormalPortPathCost         Integer32,
   gs2328STPMSTI2NormalPortPriority         Integer32
}

gs2328STPMSTI2NormalPortConfPort OBJECT-TYPE
   SYNTAX      Integer32(1..4095)
   MAX-ACCESS  not-accessible
   STATUS      current
   DESCRIPTION
       " port, range : 1 - port number. "
   ::= { gs2328STPMSTI2NormalPortEntry 1 }
   
gs2328STPMSTI2NormalPortPathCost OBJECT-TYPE
   SYNTAX      Integer32(0..200000000)
   MAX-ACCESS  read-write
   STATUS      current
   DESCRIPTION
       " Auto: 0,
        Specific Path Cost range: 1 - 200000000."
   ::= { gs2328STPMSTI2NormalPortEntry 2 }
   
gs2328STPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI2NormalPortEntry 3 }
   
gs2328STPMSTI3Port                                                          OBJECT IDENTIFIER ::= { gs2328STPMSTIPort 3 }

gs2328STPMSTI3AggregatedPort                                                OBJECT IDENTIFIER ::= { gs2328STPMSTI3Port 1 }
      
gs2328STPMSTI3AggregatedPortPathCost OBJECT-TYPE
   SYNTAX      Integer32(0..200000000)
   MAX-ACCESS  read-write
   STATUS      current
   DESCRIPTION
       " Auto: 0,
        Specific Path Cost range: 1 - 200000000."
   ::= { gs2328STPMSTI3AggregatedPort 1 }
   
gs2328STPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI3AggregatedPort 2 }
   
gs2328STPMSTI3NormalPortTable OBJECT-TYPE
   SYNTAX      SEQUENCE OF Gs2328STPMSTI3NormalPortEntry
   MAX-ACCESS  not-accessible
   STATUS      current
   DESCRIPTION
       " Show MSTI3 Normal Port Configurations. "
   ::= { gs2328STPMSTI3Port 2 }

gs2328STPMSTI3NormalPortEntry OBJECT-TYPE
   SYNTAX      Gs2328STPMSTI3NormalPortEntry
   MAX-ACCESS  not-accessible
   STATUS      current
   DESCRIPTION
       ""
   INDEX    { gs2328STPMSTI3NormalPortConfPort  }
   ::= { gs2328STPMSTI3NormalPortTable 1 }

Gs2328STPMSTI3NormalPortEntry ::= SEQUENCE {
   gs2328STPMSTI3NormalPortConfPort         Integer32,
   gs2328STPMSTI3NormalPortPathCost         Integer32,
   gs2328STPMSTI3NormalPortPriority         Integer32
}

gs2328STPMSTI3NormalPortConfPort OBJECT-TYPE
   SYNTAX      Integer32(1..4095)
   MAX-ACCESS  not-accessible
   STATUS      current
   DESCRIPTION
       " port, range : 1 - port number. "
   ::= { gs2328STPMSTI3NormalPortEntry 1 }
   
gs2328STPMSTI3NormalPortPathCost OBJECT-TYPE
   SYNTAX      Integer32(0..200000000)
   MAX-ACCESS  read-write
   STATUS      current
   DESCRIPTION
       " Auto: 0,
        Specific Path Cost range: 1 - 200000000."
   ::= { gs2328STPMSTI3NormalPortEntry 2 }
   
gs2328STPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI3NormalPortEntry 3 }
   
gs2328STPMSTI4Port                                                          OBJECT IDENTIFIER ::= { gs2328STPMSTIPort 4 }

gs2328STPMSTI4AggregatedPort                                                OBJECT IDENTIFIER ::= { gs2328STPMSTI4Port 1 }
      
gs2328STPMSTI4AggregatedPortPathCost OBJECT-TYPE
   SYNTAX      Integer32(0..200000000)
   MAX-ACCESS  read-write
   STATUS      current
   DESCRIPTION
       " Auto: 0,
        Specific Path Cost range: 1 - 200000000."
   ::= { gs2328STPMSTI4AggregatedPort 1 }
   
gs2328STPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI4AggregatedPort 2 }
   
gs2328STPMSTI4NormalPortTable OBJECT-TYPE
   SYNTAX      SEQUENCE OF Gs2328STPMSTI4NormalPortEntry
   MAX-ACCESS  not-accessible
   STATUS      current
   DESCRIPTION
       " Show MSTI4 Normal Port Configurations. "
   ::= { gs2328STPMSTI4Port 2 }

gs2328STPMSTI4NormalPortEntry OBJECT-TYPE
   SYNTAX      Gs2328STPMSTI4NormalPortEntry
   MAX-ACCESS  not-accessible
   STATUS      current
   DESCRIPTION
       ""
   INDEX    { gs2328STPMSTI4NormalPortConfPort  }
   ::= { gs2328STPMSTI4NormalPortTable 1 }

Gs2328STPMSTI4NormalPortEntry ::= SEQUENCE {
   gs2328STPMSTI4NormalPortConfPort         Integer32,
   gs2328STPMSTI4NormalPortPathCost         Integer32,
   gs2328STPMSTI4NormalPortPriority         Integer32
}

gs2328STPMSTI4NormalPortConfPort OBJECT-TYPE
   SYNTAX      Integer32(1..4095)
   MAX-ACCESS  not-accessible
   STATUS      current
   DESCRIPTION
       " port, range : 1 - port number. "
   ::= { gs2328STPMSTI4NormalPortEntry 1 }
   
gs2328STPMSTI4NormalPortPathCost OBJECT-TYPE
   SYNTAX      Integer32(0..200000000)
   MAX-ACCESS  read-write
   STATUS      current
   DESCRIPTION
       " Auto: 0,
        Specific Path Cost range: 1 - 200000000."
   ::= { gs2328STPMSTI4NormalPortEntry 2 }
   
gs2328STPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI4NormalPortEntry 3 }
   
gs2328STPMSTI5Port                                                          OBJECT IDENTIFIER ::= { gs2328STPMSTIPort 5 }

gs2328STPMSTI5AggregatedPort                                                OBJECT IDENTIFIER ::= { gs2328STPMSTI5Port 1 }
      
gs2328STPMSTI5AggregatedPortPathCost OBJECT-TYPE
   SYNTAX      Integer32(0..200000000)
   MAX-ACCESS  read-write
   STATUS      current
   DESCRIPTION
       " Auto: 0,
        Specific Path Cost range: 1 - 200000000."
   ::= { gs2328STPMSTI5AggregatedPort 1 }
   
gs2328STPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI5AggregatedPort 2 }
   
gs2328STPMSTI5NormalPortTable OBJECT-TYPE
   SYNTAX      SEQUENCE OF Gs2328STPMSTI5NormalPortEntry
   MAX-ACCESS  not-accessible
   STATUS      current
   DESCRIPTION
       " Show MSTI5 Normal Port Configurations. "
   ::= { gs2328STPMSTI5Port 2 }

gs2328STPMSTI5NormalPortEntry OBJECT-TYPE
   SYNTAX      Gs2328STPMSTI5NormalPortEntry
   MAX-ACCESS  not-accessible
   STATUS      current
   DESCRIPTION
       ""
   INDEX    { gs2328STPMSTI5NormalPortConfPort  }
   ::= { gs2328STPMSTI5NormalPortTable 1 }

Gs2328STPMSTI5NormalPortEntry ::= SEQUENCE {
   gs2328STPMSTI5NormalPortConfPort         Integer32,
   gs2328STPMSTI5NormalPortPathCost         Integer32,
   gs2328STPMSTI5NormalPortPriority         Integer32
}

gs2328STPMSTI5NormalPortConfPort OBJECT-TYPE
   SYNTAX      Integer32(1..4095)
   MAX-ACCESS  not-accessible
   STATUS      current
   DESCRIPTION
       " port, range : 1 - port number. "
   ::= { gs2328STPMSTI5NormalPortEntry 1 }
   
gs2328STPMSTI5NormalPortPathCost OBJECT-TYPE
   SYNTAX      Integer32(0..200000000)
   MAX-ACCESS  read-write
   STATUS      current
   DESCRIPTION
       " Auto: 0,
        Specific Path Cost range: 1 - 200000000."
   ::= { gs2328STPMSTI5NormalPortEntry 2 }
   
gs2328STPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI5NormalPortEntry 3 }
   
gs2328STPMSTI6Port                                                          OBJECT IDENTIFIER ::= { gs2328STPMSTIPort 6 }

gs2328STPMSTI6AggregatedPort                                                OBJECT IDENTIFIER ::= { gs2328STPMSTI6Port 1 }
      
gs2328STPMSTI6AggregatedPortPathCost OBJECT-TYPE
   SYNTAX      Integer32(0..200000000)
   MAX-ACCESS  read-write
   STATUS      current
   DESCRIPTION
       " Auto: 0,
        Specific Path Cost range: 1 - 200000000."
   ::= { gs2328STPMSTI6AggregatedPort 1 }
   
gs2328STPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI6AggregatedPort 2 }
   
gs2328STPMSTI6NormalPortTable OBJECT-TYPE
   SYNTAX      SEQUENCE OF Gs2328STPMSTI6NormalPortEntry
   MAX-ACCESS  not-accessible
   STATUS      current
   DESCRIPTION
       " Show MSTI6 Normal Port Configurations. "
   ::= { gs2328STPMSTI6Port 2 }

gs2328STPMSTI6NormalPortEntry OBJECT-TYPE
   SYNTAX      Gs2328STPMSTI6NormalPortEntry
   MAX-ACCESS  not-accessible
   STATUS      current
   DESCRIPTION
       ""
   INDEX    { gs2328STPMSTI6NormalPortConfPort  }
   ::= { gs2328STPMSTI6NormalPortTable 1 }

Gs2328STPMSTI6NormalPortEntry ::= SEQUENCE {
   gs2328STPMSTI6NormalPortConfPort         Integer32,
   gs2328STPMSTI6NormalPortPathCost         Integer32,
   gs2328STPMSTI6NormalPortPriority         Integer32
}

gs2328STPMSTI6NormalPortConfPort OBJECT-TYPE
   SYNTAX      Integer32(1..4095)
   MAX-ACCESS  not-accessible
   STATUS      current
   DESCRIPTION
       " port, range : 1 - port number. "
   ::= { gs2328STPMSTI6NormalPortEntry 1 }
   
gs2328STPMSTI6NormalPortPathCost OBJECT-TYPE
   SYNTAX      Integer32(0..200000000)
   MAX-ACCESS  read-write
   STATUS      current
   DESCRIPTION
       " Auto: 0,
        Specific Path Cost range: 1 - 200000000."
   ::= { gs2328STPMSTI6NormalPortEntry 2 }
   
gs2328STPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI6NormalPortEntry 3 }
   
gs2328STPMSTI7Port                                                          OBJECT IDENTIFIER ::= { gs2328STPMSTIPort 7 }

gs2328STPMSTI7AggregatedPort                                                OBJECT IDENTIFIER ::= { gs2328STPMSTI7Port 1 }
      
gs2328STPMSTI7AggregatedPortPathCost OBJECT-TYPE
   SYNTAX      Integer32(0..200000000)
   MAX-ACCESS  read-write
   STATUS      current
   DESCRIPTION
       " Auto: 0,
        Specific Path Cost range: 1 - 200000000."
   ::= { gs2328STPMSTI7AggregatedPort 1 }
   
gs2328STPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI7AggregatedPort 2 }
   
gs2328STPMSTI7NormalPortTable OBJECT-TYPE
   SYNTAX      SEQUENCE OF Gs2328STPMSTI7NormalPortEntry
   MAX-ACCESS  not-accessible
   STATUS      current
   DESCRIPTION
       " Show MSTI7 Normal Port Configurations. "
   ::= { gs2328STPMSTI7Port 2 }

gs2328STPMSTI7NormalPortEntry OBJECT-TYPE
   SYNTAX      Gs2328STPMSTI7NormalPortEntry
   MAX-ACCESS  not-accessible
   STATUS      current
   DESCRIPTION
       ""
   INDEX    { gs2328STPMSTI7NormalPortConfPort  }
   ::= { gs2328STPMSTI7NormalPortTable 1 }

Gs2328STPMSTI7NormalPortEntry ::= SEQUENCE {
   gs2328STPMSTI7NormalPortConfPort         Integer32,
   gs2328STPMSTI7NormalPortPathCost         Integer32,
   gs2328STPMSTI7NormalPortPriority         Integer32
}

gs2328STPMSTI7NormalPortConfPort OBJECT-TYPE
   SYNTAX      Integer32(1..4095)
   MAX-ACCESS  not-accessible
   STATUS      current
   DESCRIPTION
       " port, range : 1 - port number. "
   ::= { gs2328STPMSTI7NormalPortEntry 1 }
   
gs2328STPMSTI7NormalPortPathCost OBJECT-TYPE
   SYNTAX      Integer32(0..200000000)
   MAX-ACCESS  read-write
   STATUS      current
   DESCRIPTION
       " Auto: 0,
        Specific Path Cost range: 1 - 200000000."
   ::= { gs2328STPMSTI7NormalPortEntry 2 }
   
gs2328STPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328STPMSTI7NormalPortEntry 3 }
   

gs2328STPBridgeStatus                                                      OBJECT IDENTIFIER ::= { gs2328STP 8 }

gs2328CISTBridgeSTP                                                        OBJECT IDENTIFIER ::= { gs2328STPBridgeStatus 1 }

gs2328CISTBridgeSTPStatus                                                  OBJECT IDENTIFIER ::= { gs2328CISTBridgeSTP 1 }
      
gs2328CISTBridgeInstance OBJECT-TYPE
   SYNTAX       DisplayString
   MAX-ACCESS   read-only
   STATUS       current
   DESCRIPTION
       "The Bridge instance - CIST, MST1, ..."
   ::= { gs2328CISTBridgeSTPStatus 1 }
   
gs2328CISTBridgeID OBJECT-TYPE
   SYNTAX       DisplayString
   MAX-ACCESS   read-only
   STATUS       current
   DESCRIPTION
       "The Bridge ID of this Bridge instance."
   ::= { gs2328CISTBridgeSTPStatus 2 }
   
gs2328CISTRootID OBJECT-TYPE
   SYNTAX       DisplayString
   MAX-ACCESS   read-only
   STATUS       current
   DESCRIPTION
       "The Bridge ID of the currently elected root bridge."
   ::= { gs2328CISTBridgeSTPStatus 3 }
   
gs2328CISTRootPort OBJECT-TYPE
   SYNTAX       DisplayString
   MAX-ACCESS   read-only
   STATUS       current
   DESCRIPTION
       "The switch port currently assigned the root port role."
   ::= { gs2328CISTBridgeSTPStatus 4 }

gs2328CISTRootCost OBJECT-TYPE
   SYNTAX       Integer32(0..200000000)
   MAX-ACCESS   read-only
   STATUS       current
   DESCRIPTION
       "Root Path Cost."
   ::= { gs2328CISTBridgeSTPStatus 5 }
   
gs2328CISTRegionalRoot OBJECT-TYPE
   SYNTAX       DisplayString
   MAX-ACCESS   read-only
   STATUS       current
   DESCRIPTION
       "The Bridge ID of the currently elected regional root bridge, inside the MSTP region of this bridge."
   ::= { gs2328CISTBridgeSTPStatus 6 }
   
gs2328CISTInternalRootCost OBJECT-TYPE
   SYNTAX       Integer32(0..200000000)
   MAX-ACCESS   read-only
   STATUS       current
   DESCRIPTION
       "The Regional Root Path Cost."
   ::= { gs2328CISTBridgeSTPStatus 7 }

gs2328CISTTopologyFlag OBJECT-TYPE
   SYNTAX       DisplayString
   MAX-ACCESS   read-only
   STATUS       current
   DESCRIPTION
       "The current state of the Topology Change Flag of this Bridge instance."
   ::= { gs2328CISTBridgeSTPStatus 8 }

gs2328CISTTopologyChangeCount OBJECT-TYPE
   SYNTAX       Counter32
   MAX-ACCESS   read-only
   STATUS       current
   DESCRIPTION
       "The number of times where the topology change flag has been set."
   ::= { gs2328CISTBridgeSTPStatus 9 }
   
gs2328CISTTopologyChangeLast OBJECT-TYPE
   SYNTAX       DisplayString
   MAX-ACCESS   read-only
   STATUS       current
   DESCRIPTION
       "The time passed since the Topology Flag was last set."
   ::= { gs2328CISTBridgeSTPStatus 10 }
   
gs2328CISTPortStateTable OBJECT-TYPE
   SYNTAX      SEQUENCE OF Gs2328CISTPortStateEntry
   MAX-ACCESS  not-accessible
   STATUS      current
   DESCRIPTION
       " Show CIST Ports and Aggregations State Configurations. "
   ::= { gs2328CISTBridgeSTP 2 }

gs2328CISTPortStateEntry OBJECT-TYPE
   SYNTAX      Gs2328CISTPortStateEntry
   MAX-ACCESS  not-accessible
   STATUS      current
   DESCRIPTION
       ""
   INDEX    { gs2328CISTPortStateIndex  }
   ::= { gs2328CISTPortStateTable 1 }

Gs2328CISTPortStateEntry ::= SEQUENCE {
   gs2328CISTPortStateIndex        Integer32,
   gs2328CISTPortStatePort         DisplayString,
   gs2328CISTPortStatePortID       DisplayString,
   gs2328CISTPortStateRole         DisplayString,
   gs2328CISTPortStateState        DisplayString,
   gs2328CISTPortStatePathCost     Integer32,
   gs2328CISTPortStateEdge         DisplayString,
   gs2328CISTPortStatePoint2Point  DisplayString,
   gs2328CISTPortStateUptime       DisplayString
}

gs2328CISTPortStateIndex OBJECT-TYPE
   SYNTAX      Integer32(1..4095)
   MAX-ACCESS  not-accessible
   STATUS      current
   DESCRIPTION
       "table index."
   ::= { gs2328CISTPortStateEntry 1 }
   
gs2328CISTPortStatePort OBJECT-TYPE
   SYNTAX      DisplayString
   MAX-ACCESS  read-only
   STATUS      current
   DESCRIPTION
       "The switch port number of the logical STP port."
   ::= { gs2328CISTPortStateEntry 2 }
   
gs2328CISTPortStatePortID OBJECT-TYPE
   SYNTAX      DisplayString
   MAX-ACCESS  read-only
   STATUS      current
   DESCRIPTION
       "The port id as used by the STP protocol. 
        This is the priority part and the logical port index of the bridge port."
   ::= { gs2328CISTPortStateEntry 3 }
   
gs2328CISTPortStateRole OBJECT-TYPE
   SYNTAX      DisplayString
   MAX-ACCESS  read-only
   STATUS      current
   DESCRIPTION
       "The current STP port role."
   ::= { gs2328CISTPortStateEntry 4 }
   
gs2328CISTPortStateState OBJECT-TYPE
   SYNTAX      DisplayString
   MAX-ACCESS  read-only
   STATUS      current
   DESCRIPTION
       "The current STP port state."
   ::= { gs2328CISTPortStateEntry 5 }
   
gs2328CISTPortStatePathCost OBJECT-TYPE
   SYNTAX      Integer32(0..200000000)
   MAX-ACCESS  read-only
   STATUS      current
   DESCRIPTION
       "The current STP port path cost."
   ::= { gs2328CISTPortStateEntry 6 }
   
gs2328CISTPortStateEdge OBJECT-TYPE
   SYNTAX      DisplayString
   MAX-ACCESS  read-only
   STATUS      current
   DESCRIPTION
       "The current STP port Edge Flag."
   ::= { gs2328CISTPortStateEntry 7 }
   
gs2328CISTPortStatePoint2Point OBJECT-TYPE
   SYNTAX      DisplayString
   MAX-ACCESS  read-only
   STATUS      current
   DESCRIPTION
       "The current STP port point-to-point flag."
   ::= { gs2328CISTPortStateEntry 8 }
   
gs2328CISTPortStateUptime OBJECT-TYPE
   SYNTAX      DisplayString
   MAX-ACCESS  read-only
   STATUS      current
   DESCRIPTION
       "The time since the bridge port was last initialized."
   ::= { gs2328CISTPortStateEntry 9 }
   
gs2328MSTI1BridgeSTP                                                        OBJECT IDENTIFIER ::= { gs2328STPBridgeStatus 2 }

gs2328MSTI1BridgeSTPStatus                                                  OBJECT IDENTIFIER ::= { gs2328MSTI1BridgeSTP 1 }
      
gs2328MSTI1BridgeInstance OBJECT-TYPE
   SYNTAX       DisplayString
   MAX-ACCESS   read-only
   STATUS       current
   DESCRIPTION
       "The Bridge instance - CIST, MST1, ..."
   ::= { gs2328MSTI1BridgeSTPStatus 1 }
   
gs2328MSTI1BridgeID OBJECT-TYPE
   SYNTAX       DisplayString
   MAX-ACCESS   read-only
   STATUS       current
   DESCRIPTION
       "The Bridge ID of this Bridge instance."
   ::= { gs2328MSTI1BridgeSTPStatus 2 }
   
gs2328MSTI1RootID OBJECT-TYPE
   SYNTAX       DisplayString
   MAX-ACCESS   read-only
   STATUS       current
   DESCRIPTION
       "The Bridge ID of the currently elected root bridge."
   ::= { gs2328MSTI1BridgeSTPStatus 3 }
   
gs2328MSTI1RootPort OBJECT-TYPE
   SYNTAX       DisplayString
   MAX-ACCESS   read-only
   STATUS       current
   DESCRIPTION
       "The switch port currently assigned the root port role."
   ::= { gs2328MSTI1BridgeSTPStatus 4 }

gs2328MSTI1RootCost OBJECT-TYPE
   SYNTAX       Integer32(0..200000000)
   MAX-ACCESS   read-only
   STATUS       current
   DESCRIPTION
       "Root Path Cost."
   ::= { gs2328MSTI1BridgeSTPStatus 5 }

gs2328MSTI1TopologyFlag OBJECT-TYPE
   SYNTAX       DisplayString
   MAX-ACCESS   read-only
   STATUS       current
   DESCRIPTION
       "The current state of the Topology Change Flag of this Bridge instance."
   ::= { gs2328MSTI1BridgeSTPStatus 8 }

gs2328MSTI1TopologyChangeCount OBJECT-TYPE
   SYNTAX       Counter32
   MAX-ACCESS   read-only
   STATUS       current
   DESCRIPTION
       "The number of times where the topology change flag has been set."
   ::= { gs2328MSTI1BridgeSTPStatus 9 }
   
gs2328MSTI1TopologyChangeLast OBJECT-TYPE
   SYNTAX       DisplayString
   MAX-ACCESS   read-only
   STATUS       current
   DESCRIPTION
       "The time passed since the Topology Flag was last set."
   ::= { gs2328MSTI1BridgeSTPStatus 10 }
   
gs2328MSTI1PortStateTable OBJECT-TYPE
   SYNTAX      SEQUENCE OF Gs2328MSTI1PortStateEntry
   MAX-ACCESS  not-accessible
   STATUS      current
   DESCRIPTION
       " Show MSTI1 Ports and Aggregations State Configurations. "
   ::= { gs2328MSTI1BridgeSTP 2 }

gs2328MSTI1PortStateEntry OBJECT-TYPE
   SYNTAX      Gs2328MSTI1PortStateEntry
   MAX-ACCESS  not-accessible
   STATUS      current
   DESCRIPTION
       ""
   INDEX    { gs2328MSTI1PortStateIndex  }
   ::= { gs2328MSTI1PortStateTable 1 }

Gs2328MSTI1PortStateEntry ::= SEQUENCE {
   gs2328MSTI1PortStateIndex        Integer32,
   gs2328MSTI1PortStatePort         DisplayString,
   gs2328MSTI1PortStatePortID       DisplayString,
   gs2328MSTI1PortStateRole         DisplayString,
   gs2328MSTI1PortStateState        DisplayString,
   gs2328MSTI1PortStatePathCost     Integer32,
   gs2328MSTI1PortStateEdge         DisplayString,
   gs2328MSTI1PortStatePoint2Point  DisplayString,
   gs2328MSTI1PortStateUptime       DisplayString
}

gs2328MSTI1PortStateIndex OBJECT-TYPE
   SYNTAX      Integer32(1..4095)
   MAX-ACCESS  not-accessible
   STATUS      current
   DESCRIPTION
       "table index."
   ::= { gs2328MSTI1PortStateEntry 1 }
   
gs2328MSTI1PortStatePort OBJECT-TYPE
   SYNTAX      DisplayString
   MAX-ACCESS  read-only
   STATUS      current
   DESCRIPTION
       "The switch port number of the logical STP port."
   ::= { gs2328MSTI1PortStateEntry 2 }
   
gs2328MSTI1PortStatePortID OBJECT-TYPE
   SYNTAX      DisplayString
   MAX-ACCESS  read-only
   STATUS      current
   DESCRIPTION
       "The port id as used by the STP protocol. 
        This is the priority part and the logical port index of the bridge port."
   ::= { gs2328MSTI1PortStateEntry 3 }
   
gs2328MSTI1PortStateRole OBJECT-TYPE
   SYNTAX      DisplayString
   MAX-ACCESS  read-only
   STATUS      current
   DESCRIPTION
       "The current STP port role."
   ::= { gs2328MSTI1PortStateEntry 4 }
   
gs2328MSTI1PortStateState OBJECT-TYPE
   SYNTAX      DisplayString
   MAX-ACCESS  read-only
   STATUS      current
   DESCRIPTION
       "The current STP port state."
   ::= { gs2328MSTI1PortStateEntry 5 }
   
gs2328MSTI1PortStatePathCost OBJECT-TYPE
   SYNTAX      Integer32(0..200000000)
   MAX-ACCESS  read-only
   STATUS      current
   DESCRIPTION
       "The current STP port path cost."
   ::= { gs2328MSTI1PortStateEntry 6 }
   
gs2328MSTI1PortStateEdge OBJECT-TYPE
   SYNTAX      DisplayString
   MAX-ACCESS  read-only
   STATUS      current
   DESCRIPTION
       "The current STP port Edge Flag."
   ::= { gs2328MSTI1PortStateEntry 7 }
   
gs2328MSTI1PortStatePoint2Point OBJECT-TYPE
   SYNTAX      DisplayString
   MAX-ACCESS  read-only
   STATUS      current
   DESCRIPTION
       "The current STP port point-to-point flag."
   ::= { gs2328MSTI1PortStateEntry 8 }
   
gs2328MSTI1PortStateUptime OBJECT-TYPE
   SYNTAX      DisplayString
   MAX-ACCESS  read-only
   STATUS      current
   DESCRIPTION
       "The time since the bridge port was last initialized."
   ::= { gs2328MSTI1PortStateEntry 9 }
   
gs2328MSTI2BridgeSTP                                                        OBJECT IDENTIFIER ::= { gs2328STPBridgeStatus 3 }

gs2328MSTI2BridgeSTPStatus                                                  OBJECT IDENTIFIER ::= { gs2328MSTI2BridgeSTP 1 }
      
gs2328MSTI2BridgeInstance OBJECT-TYPE
   SYNTAX       DisplayString
   MAX-ACCESS   read-only
   STATUS       current
   DESCRIPTION
       "The Bridge instance - CIST, MST1, ..."
   ::= { gs2328MSTI2BridgeSTPStatus 1 }
   
gs2328MSTI2BridgeID OBJECT-TYPE
   SYNTAX       DisplayString
   MAX-ACCESS   read-only
   STATUS       current
   DESCRIPTION
       "The Bridge ID of this Bridge instance."
   ::= { gs2328MSTI2BridgeSTPStatus 2 }
   
gs2328MSTI2RootID OBJECT-TYPE
   SYNTAX       DisplayString
   MAX-ACCESS   read-only
   STATUS       current
   DESCRIPTION
       "The Bridge ID of the currently elected root bridge."
   ::= { gs2328MSTI2BridgeSTPStatus 3 }
   
gs2328MSTI2RootPort OBJECT-TYPE
   SYNTAX       DisplayString
   MAX-ACCESS   read-only
   STATUS       current
   DESCRIPTION
       "The switch port currently assigned the root port role."
   ::= { gs2328MSTI2BridgeSTPStatus 4 }

gs2328MSTI2RootCost OBJECT-TYPE
   SYNTAX       Integer32(0..200000000)
   MAX-ACCESS   read-only
   STATUS       current
   DESCRIPTION
       "Root Path Cost."
   ::= { gs2328MSTI2BridgeSTPStatus 5 }

gs2328MSTI2TopologyFlag OBJECT-TYPE
   SYNTAX       DisplayString
   MAX-ACCESS   read-only
   STATUS       current
   DESCRIPTION
       "The current state of the Topology Change Flag of this Bridge instance."
   ::= { gs2328MSTI2BridgeSTPStatus 8 }

gs2328MSTI2TopologyChangeCount OBJECT-TYPE
   SYNTAX       Counter32
   MAX-ACCESS   read-only
   STATUS       current
   DESCRIPTION
       "The number of times where the topology change flag has been set."
   ::= { gs2328MSTI2BridgeSTPStatus 9 }
   
gs2328MSTI2TopologyChangeLast OBJECT-TYPE
   SYNTAX       DisplayString
   MAX-ACCESS   read-only
   STATUS       current
   DESCRIPTION
       "The time passed since the Topology Flag was last set."
   ::= { gs2328MSTI2BridgeSTPStatus 10 }
   
gs2328MSTI2PortStateTable OBJECT-TYPE
   SYNTAX      SEQUENCE OF Gs2328MSTI2PortStateEntry
   MAX-ACCESS  not-accessible
   STATUS      current
   DESCRIPTION
       " Show MSTI2 Ports and Aggregations State Configurations. "
   ::= { gs2328MSTI2BridgeSTP 2 }

gs2328MSTI2PortStateEntry OBJECT-TYPE
   SYNTAX      Gs2328MSTI2PortStateEntry
   MAX-ACCESS  not-accessible
   STATUS      current
   DESCRIPTION
       ""
   INDEX    { gs2328MSTI2PortStateIndex  }
   ::= { gs2328MSTI2PortStateTable 1 }

Gs2328MSTI2PortStateEntry ::= SEQUENCE {
   gs2328MSTI2PortStateIndex        Integer32,
   gs2328MSTI2PortStatePort         DisplayString,
   gs2328MSTI2PortStatePortID       DisplayString,
   gs2328MSTI2PortStateRole         DisplayString,
   gs2328MSTI2PortStateState        DisplayString,
   gs2328MSTI2PortStatePathCost     Integer32,
   gs2328MSTI2PortStateEdge         DisplayString,
   gs2328MSTI2PortStatePoint2Point  DisplayString,
   gs2328MSTI2PortStateUptime       DisplayString
}

gs2328MSTI2PortStateIndex OBJECT-TYPE
   SYNTAX      Integer32(1..4095)
   MAX-ACCESS  not-accessible
   STATUS      current
   DESCRIPTION
       "table index."
   ::= { gs2328MSTI2PortStateEntry 1 }
   
gs2328MSTI2PortStatePort OBJECT-TYPE
   SYNTAX      DisplayString
   MAX-ACCESS  read-only
   STATUS      current
   DESCRIPTION
       "The switch port number of the logical STP port."
   ::= { gs2328MSTI2PortStateEntry 2 }
   
gs2328MSTI2PortStatePortID OBJECT-TYPE
   SYNTAX      DisplayString
   MAX-ACCESS  read-only
   STATUS      current
   DESCRIPTION
       "The port id as used by the STP protocol. 
        This is the priority part and the logical port index of the bridge port."
   ::= { gs2328MSTI2PortStateEntry 3 }
   
gs2328MSTI2PortStateRole OBJECT-TYPE
   SYNTAX      DisplayString
   MAX-ACCESS  read-only
   STATUS      current
   DESCRIPTION
       "The current STP port role."
   ::= { gs2328MSTI2PortStateEntry 4 }
   
gs2328MSTI2PortStateState OBJECT-TYPE
   SYNTAX      DisplayString
   MAX-ACCESS  read-only
   STATUS      current
   DESCRIPTION
       "The current STP port state."
   ::= { gs2328MSTI2PortStateEntry 5 }
   
gs2328MSTI2PortStatePathCost OBJECT-TYPE
   SYNTAX      Integer32(0..200000000)
   MAX-ACCESS  read-only
   STATUS      current
   DESCRIPTION
       "The current STP port path cost."
   ::= { gs2328MSTI2PortStateEntry 6 }
   
gs2328MSTI2PortStateEdge OBJECT-TYPE
   SYNTAX      DisplayString
   MAX-ACCESS  read-only
   STATUS      current
   DESCRIPTION
       "The current STP port Edge Flag."
   ::= { gs2328MSTI2PortStateEntry 7 }
   
gs2328MSTI2PortStatePoint2Point OBJECT-TYPE
   SYNTAX      DisplayString
   MAX-ACCESS  read-only
   STATUS      current
   DESCRIPTION
       "The current STP port point-to-point flag."
   ::= { gs2328MSTI2PortStateEntry 8 }
   
gs2328MSTI2PortStateUptime OBJECT-TYPE
   SYNTAX      DisplayString
   MAX-ACCESS  read-only
   STATUS      current
   DESCRIPTION
       "The time since the bridge port was last initialized."
   ::= { gs2328MSTI2PortStateEntry 9 }

gs2328MSTI3BridgeSTP                                                        OBJECT IDENTIFIER ::= { gs2328STPBridgeStatus 4 }

gs2328MSTI3BridgeSTPStatus                                                  OBJECT IDENTIFIER ::= { gs2328MSTI3BridgeSTP 1 }
      
gs2328MSTI3BridgeInstance OBJECT-TYPE
   SYNTAX       DisplayString
   MAX-ACCESS   read-only
   STATUS       current
   DESCRIPTION
       "The Bridge instance - CIST, MST1, ..."
   ::= { gs2328MSTI3BridgeSTPStatus 1 }
   
gs2328MSTI3BridgeID OBJECT-TYPE
   SYNTAX       DisplayString
   MAX-ACCESS   read-only
   STATUS       current
   DESCRIPTION
       "The Bridge ID of this Bridge instance."
   ::= { gs2328MSTI3BridgeSTPStatus 2 }
   
gs2328MSTI3RootID OBJECT-TYPE
   SYNTAX       DisplayString
   MAX-ACCESS   read-only
   STATUS       current
   DESCRIPTION
       "The Bridge ID of the currently elected root bridge."
   ::= { gs2328MSTI3BridgeSTPStatus 3 }
   
gs2328MSTI3RootPort OBJECT-TYPE
   SYNTAX       DisplayString
   MAX-ACCESS   read-only
   STATUS       current
   DESCRIPTION
       "The switch port currently assigned the root port role."
   ::= { gs2328MSTI3BridgeSTPStatus 4 }

gs2328MSTI3RootCost OBJECT-TYPE
   SYNTAX       Integer32(0..200000000)
   MAX-ACCESS   read-only
   STATUS       current
   DESCRIPTION
       "Root Path Cost."
   ::= { gs2328MSTI3BridgeSTPStatus 5 }

gs2328MSTI3TopologyFlag OBJECT-TYPE
   SYNTAX       DisplayString
   MAX-ACCESS   read-only
   STATUS       current
   DESCRIPTION
       "The current state of the Topology Change Flag of this Bridge instance."
   ::= { gs2328MSTI3BridgeSTPStatus 8 }

gs2328MSTI3TopologyChangeCount OBJECT-TYPE
   SYNTAX       Counter32
   MAX-ACCESS   read-only
   STATUS       current
   DESCRIPTION
       "The number of times where the topology change flag has been set."
   ::= { gs2328MSTI3BridgeSTPStatus 9 }
   
gs2328MSTI3TopologyChangeLast OBJECT-TYPE
   SYNTAX       DisplayString
   MAX-ACCESS   read-only
   STATUS       current
   DESCRIPTION
       "The time passed since the Topology Flag was last set."
   ::= { gs2328MSTI3BridgeSTPStatus 10 }
   
gs2328MSTI3PortStateTable OBJECT-TYPE
   SYNTAX      SEQUENCE OF Gs2328MSTI3PortStateEntry
   MAX-ACCESS  not-accessible
   STATUS      current
   DESCRIPTION
       " Show MSTI3 Ports and Aggregations State Configurations. "
   ::= { gs2328MSTI3BridgeSTP 2 }

gs2328MSTI3PortStateEntry OBJECT-TYPE
   SYNTAX      Gs2328MSTI3PortStateEntry
   MAX-ACCESS  not-accessible
   STATUS      current
   DESCRIPTION
       ""
   INDEX    { gs2328MSTI3PortStateIndex  }
   ::= { gs2328MSTI3PortStateTable 1 }

Gs2328MSTI3PortStateEntry ::= SEQUENCE {
   gs2328MSTI3PortStateIndex        Integer32,
   gs2328MSTI3PortStatePort         DisplayString,
   gs2328MSTI3PortStatePortID       DisplayString,
   gs2328MSTI3PortStateRole         DisplayString,
   gs2328MSTI3PortStateState        DisplayString,
   gs2328MSTI3PortStatePathCost     Integer32,
   gs2328MSTI3PortStateEdge         DisplayString,
   gs2328MSTI3PortStatePoint2Point  DisplayString,
   gs2328MSTI3PortStateUptime       DisplayString
}

gs2328MSTI3PortStateIndex OBJECT-TYPE
   SYNTAX      Integer32(1..4095)
   MAX-ACCESS  not-accessible
   STATUS      current
   DESCRIPTION
       "table index."
   ::= { gs2328MSTI3PortStateEntry 1 }
   
gs2328MSTI3PortStatePort OBJECT-TYPE
   SYNTAX      DisplayString
   MAX-ACCESS  read-only
   STATUS      current
   DESCRIPTION
       "The switch port number of the logical STP port."
   ::= { gs2328MSTI3PortStateEntry 2 }
   
gs2328MSTI3PortStatePortID OBJECT-TYPE
   SYNTAX      DisplayString
   MAX-ACCESS  read-only
   STATUS      current
   DESCRIPTION
       "The port id as used by the STP protocol. 
        This is the priority part and the logical port index of the bridge port."
   ::= { gs2328MSTI3PortStateEntry 3 }
   
gs2328MSTI3PortStateRole OBJECT-TYPE
   SYNTAX      DisplayString
   MAX-ACCESS  read-only
   STATUS      current
   DESCRIPTION
       "The current STP port role."
   ::= { gs2328MSTI3PortStateEntry 4 }
   
gs2328MSTI3PortStateState OBJECT-TYPE
   SYNTAX      DisplayString
   MAX-ACCESS  read-only
   STATUS      current
   DESCRIPTION
       "The current STP port state."
   ::= { gs2328MSTI3PortStateEntry 5 }
   
gs2328MSTI3PortStatePathCost OBJECT-TYPE
   SYNTAX      Integer32(0..200000000)
   MAX-ACCESS  read-only
   STATUS      current
   DESCRIPTION
       "The current STP port path cost."
   ::= { gs2328MSTI3PortStateEntry 6 }
   
gs2328MSTI3PortStateEdge OBJECT-TYPE
   SYNTAX      DisplayString
   MAX-ACCESS  read-only
   STATUS      current
   DESCRIPTION
       "The current STP port Edge Flag."
   ::= { gs2328MSTI3PortStateEntry 7 }
   
gs2328MSTI3PortStatePoint2Point OBJECT-TYPE
   SYNTAX      DisplayString
   MAX-ACCESS  read-only
   STATUS      current
   DESCRIPTION
       "The current STP port point-to-point flag."
   ::= { gs2328MSTI3PortStateEntry 8 }
   
gs2328MSTI3PortStateUptime OBJECT-TYPE
   SYNTAX      DisplayString
   MAX-ACCESS  read-only
   STATUS      current
   DESCRIPTION
       "The time since the bridge port was last initialized."
   ::= { gs2328MSTI3PortStateEntry 9 }
   
gs2328MSTI4BridgeSTP                                                        OBJECT IDENTIFIER ::= { gs2328STPBridgeStatus 5 }

gs2328MSTI4BridgeSTPStatus                                                  OBJECT IDENTIFIER ::= { gs2328MSTI4BridgeSTP 1 }
      
gs2328MSTI4BridgeInstance OBJECT-TYPE
   SYNTAX       DisplayString
   MAX-ACCESS   read-only
   STATUS       current
   DESCRIPTION
       "The Bridge instance - CIST, MST1, ..."
   ::= { gs2328MSTI4BridgeSTPStatus 1 }
   
gs2328MSTI4BridgeID OBJECT-TYPE
   SYNTAX       DisplayString
   MAX-ACCESS   read-only
   STATUS       current
   DESCRIPTION
       "The Bridge ID of this Bridge instance."
   ::= { gs2328MSTI4BridgeSTPStatus 2 }
   
gs2328MSTI4RootID OBJECT-TYPE
   SYNTAX       DisplayString
   MAX-ACCESS   read-only
   STATUS       current
   DESCRIPTION
       "The Bridge ID of the currently elected root bridge."
   ::= { gs2328MSTI4BridgeSTPStatus 3 }
   
gs2328MSTI4RootPort OBJECT-TYPE
   SYNTAX       DisplayString
   MAX-ACCESS   read-only
   STATUS       current
   DESCRIPTION
       "The switch port currently assigned the root port role."
   ::= { gs2328MSTI4BridgeSTPStatus 4 }

gs2328MSTI4RootCost OBJECT-TYPE
   SYNTAX       Integer32(0..200000000)
   MAX-ACCESS   read-only
   STATUS       current
   DESCRIPTION
       "Root Path Cost."
   ::= { gs2328MSTI4BridgeSTPStatus 5 }

gs2328MSTI4TopologyFlag OBJECT-TYPE
   SYNTAX       DisplayString
   MAX-ACCESS   read-only
   STATUS       current
   DESCRIPTION
       "The current state of the Topology Change Flag of this Bridge instance."
   ::= { gs2328MSTI4BridgeSTPStatus 8 }

gs2328MSTI4TopologyChangeCount OBJECT-TYPE
   SYNTAX       Counter32
   MAX-ACCESS   read-only
   STATUS       current
   DESCRIPTION
       "The number of times where the topology change flag has been set."
   ::= { gs2328MSTI4BridgeSTPStatus 9 }
   
gs2328MSTI4TopologyChangeLast OBJECT-TYPE
   SYNTAX       DisplayString
   MAX-ACCESS   read-only
   STATUS       current
   DESCRIPTION
       "The time passed since the Topology Flag was last set."
   ::= { gs2328MSTI4BridgeSTPStatus 10 }
   
gs2328MSTI4PortStateTable OBJECT-TYPE
   SYNTAX      SEQUENCE OF Gs2328MSTI4PortStateEntry
   MAX-ACCESS  not-accessible
   STATUS      current
   DESCRIPTION
       " Show MSTI4 Ports and Aggregations State Configurations. "
   ::= { gs2328MSTI4BridgeSTP 2 }

gs2328MSTI4PortStateEntry OBJECT-TYPE
   SYNTAX      Gs2328MSTI4PortStateEntry
   MAX-ACCESS  not-accessible
   STATUS      current
   DESCRIPTION
       ""
   INDEX    { gs2328MSTI4PortStateIndex  }
   ::= { gs2328MSTI4PortStateTable 1 }

Gs2328MSTI4PortStateEntry ::= SEQUENCE {
   gs2328MSTI4PortStateIndex        Integer32,
   gs2328MSTI4PortStatePort         DisplayString,
   gs2328MSTI4PortStatePortID       DisplayString,
   gs2328MSTI4PortStateRole         DisplayString,
   gs2328MSTI4PortStateState        DisplayString,
   gs2328MSTI4PortStatePathCost     Integer32,
   gs2328MSTI4PortStateEdge         DisplayString,
   gs2328MSTI4PortStatePoint2Point  DisplayString,
   gs2328MSTI4PortStateUptime       DisplayString
}

gs2328MSTI4PortStateIndex OBJECT-TYPE
   SYNTAX      Integer32(1..4095)
   MAX-ACCESS  not-accessible
   STATUS      current
   DESCRIPTION
       "table index."
   ::= { gs2328MSTI4PortStateEntry 1 }
   
gs2328MSTI4PortStatePort OBJECT-TYPE
   SYNTAX      DisplayString
   MAX-ACCESS  read-only
   STATUS      current
   DESCRIPTION
       "The switch port number of the logical STP port."
   ::= { gs2328MSTI4PortStateEntry 2 }
   
gs2328MSTI4PortStatePortID OBJECT-TYPE
   SYNTAX      DisplayString
   MAX-ACCESS  read-only
   STATUS      current
   DESCRIPTION
       "The port id as used by the STP protocol. 
        This is the priority part and the logical port index of the bridge port."
   ::= { gs2328MSTI4PortStateEntry 3 }
   
gs2328MSTI4PortStateRole OBJECT-TYPE
   SYNTAX      DisplayString
   MAX-ACCESS  read-only
   STATUS      current
   DESCRIPTION
       "The current STP port role."
   ::= { gs2328MSTI4PortStateEntry 4 }
   
gs2328MSTI4PortStateState OBJECT-TYPE
   SYNTAX      DisplayString
   MAX-ACCESS  read-only
   STATUS      current
   DESCRIPTION
       "The current STP port state."
   ::= { gs2328MSTI4PortStateEntry 5 }
   
gs2328MSTI4PortStatePathCost OBJECT-TYPE
   SYNTAX      Integer32(0..200000000)
   MAX-ACCESS  read-only
   STATUS      current
   DESCRIPTION
       "The current STP port path cost."
   ::= { gs2328MSTI4PortStateEntry 6 }
   
gs2328MSTI4PortStateEdge OBJECT-TYPE
   SYNTAX      DisplayString
   MAX-ACCESS  read-only
   STATUS      current
   DESCRIPTION
       "The current STP port Edge Flag."
   ::= { gs2328MSTI4PortStateEntry 7 }
   
gs2328MSTI4PortStatePoint2Point OBJECT-TYPE
   SYNTAX      DisplayString
   MAX-ACCESS  read-only
   STATUS      current
   DESCRIPTION
       "The current STP port point-to-point flag."
   ::= { gs2328MSTI4PortStateEntry 8 }
   
gs2328MSTI4PortStateUptime OBJECT-TYPE
   SYNTAX      DisplayString
   MAX-ACCESS  read-only
   STATUS      current
   DESCRIPTION
       "The time since the bridge port was last initialized."
   ::= { gs2328MSTI4PortStateEntry 9 }
   
gs2328MSTI5BridgeSTP                                                        OBJECT IDENTIFIER ::= { gs2328STPBridgeStatus 6 }

gs2328MSTI5BridgeSTPStatus                                                  OBJECT IDENTIFIER ::= { gs2328MSTI5BridgeSTP 1 }
      
gs2328MSTI5BridgeInstance OBJECT-TYPE
   SYNTAX       DisplayString
   MAX-ACCESS   read-only
   STATUS       current
   DESCRIPTION
       "The Bridge instance - CIST, MST1, ..."
   ::= { gs2328MSTI5BridgeSTPStatus 1 }
   
gs2328MSTI5BridgeID OBJECT-TYPE
   SYNTAX       DisplayString
   MAX-ACCESS   read-only
   STATUS       current
   DESCRIPTION
       "The Bridge ID of this Bridge instance."
   ::= { gs2328MSTI5BridgeSTPStatus 2 }
   
gs2328MSTI5RootID OBJECT-TYPE
   SYNTAX       DisplayString
   MAX-ACCESS   read-only
   STATUS       current
   DESCRIPTION
       "The Bridge ID of the currently elected root bridge."
   ::= { gs2328MSTI5BridgeSTPStatus 3 }
   
gs2328MSTI5RootPort OBJECT-TYPE
   SYNTAX       DisplayString
   MAX-ACCESS   read-only
   STATUS       current
   DESCRIPTION
       "The switch port currently assigned the root port role."
   ::= { gs2328MSTI5BridgeSTPStatus 4 }

gs2328MSTI5RootCost OBJECT-TYPE
   SYNTAX       Integer32(0..200000000)
   MAX-ACCESS   read-only
   STATUS       current
   DESCRIPTION
       "Root Path Cost."
   ::= { gs2328MSTI5BridgeSTPStatus 5 }

gs2328MSTI5TopologyFlag OBJECT-TYPE
   SYNTAX       DisplayString
   MAX-ACCESS   read-only
   STATUS       current
   DESCRIPTION
       "The current state of the Topology Change Flag of this Bridge instance."
   ::= { gs2328MSTI5BridgeSTPStatus 8 }

gs2328MSTI5TopologyChangeCount OBJECT-TYPE
   SYNTAX       Counter32
   MAX-ACCESS   read-only
   STATUS       current
   DESCRIPTION
       "The number of times where the topology change flag has been set."
   ::= { gs2328MSTI5BridgeSTPStatus 9 }
   
gs2328MSTI5TopologyChangeLast OBJECT-TYPE
   SYNTAX       DisplayString
   MAX-ACCESS   read-only
   STATUS       current
   DESCRIPTION
       "The time passed since the Topology Flag was last set."
   ::= { gs2328MSTI5BridgeSTPStatus 10 }
   
gs2328MSTI5PortStateTable OBJECT-TYPE
   SYNTAX      SEQUENCE OF Gs2328MSTI5PortStateEntry
   MAX-ACCESS  not-accessible
   STATUS      current
   DESCRIPTION
       " Show MSTI5 Ports and Aggregations State Configurations. "
   ::= { gs2328MSTI5BridgeSTP 2 }

gs2328MSTI5PortStateEntry OBJECT-TYPE
   SYNTAX      Gs2328MSTI5PortStateEntry
   MAX-ACCESS  not-accessible
   STATUS      current
   DESCRIPTION
       ""
   INDEX    { gs2328MSTI5PortStateIndex  }
   ::= { gs2328MSTI5PortStateTable 1 }

Gs2328MSTI5PortStateEntry ::= SEQUENCE {
   gs2328MSTI5PortStateIndex        Integer32,
   gs2328MSTI5PortStatePort         DisplayString,
   gs2328MSTI5PortStatePortID       DisplayString,
   gs2328MSTI5PortStateRole         DisplayString,
   gs2328MSTI5PortStateState        DisplayString,
   gs2328MSTI5PortStatePathCost     Integer32,
   gs2328MSTI5PortStateEdge         DisplayString,
   gs2328MSTI5PortStatePoint2Point  DisplayString,
   gs2328MSTI5PortStateUptime       DisplayString
}

gs2328MSTI5PortStateIndex OBJECT-TYPE
   SYNTAX      Integer32(1..4095)
   MAX-ACCESS  not-accessible
   STATUS      current
   DESCRIPTION
       "table index."
   ::= { gs2328MSTI5PortStateEntry 1 }
   
gs2328MSTI5PortStatePort OBJECT-TYPE
   SYNTAX      DisplayString
   MAX-ACCESS  read-only
   STATUS      current
   DESCRIPTION
       "The switch port number of the logical STP port."
   ::= { gs2328MSTI5PortStateEntry 2 }
   
gs2328MSTI5PortStatePortID OBJECT-TYPE
   SYNTAX      DisplayString
   MAX-ACCESS  read-only
   STATUS      current
   DESCRIPTION
       "The port id as used by the STP protocol. 
        This is the priority part and the logical port index of the bridge port."
   ::= { gs2328MSTI5PortStateEntry 3 }
   
gs2328MSTI5PortStateRole OBJECT-TYPE
   SYNTAX      DisplayString
   MAX-ACCESS  read-only
   STATUS      current
   DESCRIPTION
       "The current STP port role."
   ::= { gs2328MSTI5PortStateEntry 4 }
   
gs2328MSTI5PortStateState OBJECT-TYPE
   SYNTAX      DisplayString
   MAX-ACCESS  read-only
   STATUS      current
   DESCRIPTION
       "The current STP port state."
   ::= { gs2328MSTI5PortStateEntry 5 }
   
gs2328MSTI5PortStatePathCost OBJECT-TYPE
   SYNTAX      Integer32(0..200000000)
   MAX-ACCESS  read-only
   STATUS      current
   DESCRIPTION
       "The current STP port path cost."
   ::= { gs2328MSTI5PortStateEntry 6 }
   
gs2328MSTI5PortStateEdge OBJECT-TYPE
   SYNTAX      DisplayString
   MAX-ACCESS  read-only
   STATUS      current
   DESCRIPTION
       "The current STP port Edge Flag."
   ::= { gs2328MSTI5PortStateEntry 7 }
   
gs2328MSTI5PortStatePoint2Point OBJECT-TYPE
   SYNTAX      DisplayString
   MAX-ACCESS  read-only
   STATUS      current
   DESCRIPTION
       "The current STP port point-to-point flag."
   ::= { gs2328MSTI5PortStateEntry 8 }
   
gs2328MSTI5PortStateUptime OBJECT-TYPE
   SYNTAX      DisplayString
   MAX-ACCESS  read-only
   STATUS      current
   DESCRIPTION
       "The time since the bridge port was last initialized."
   ::= { gs2328MSTI5PortStateEntry 9 }
   
gs2328MSTI6BridgeSTP                                                        OBJECT IDENTIFIER ::= { gs2328STPBridgeStatus 7 }

gs2328MSTI6BridgeSTPStatus                                                  OBJECT IDENTIFIER ::= { gs2328MSTI6BridgeSTP 1 }
      
gs2328MSTI6BridgeInstance OBJECT-TYPE
   SYNTAX       DisplayString
   MAX-ACCESS   read-only
   STATUS       current
   DESCRIPTION
       "The Bridge instance - CIST, MST1, ..."
   ::= { gs2328MSTI6BridgeSTPStatus 1 }
   
gs2328MSTI6BridgeID OBJECT-TYPE
   SYNTAX       DisplayString
   MAX-ACCESS   read-only
   STATUS       current
   DESCRIPTION
       "The Bridge ID of this Bridge instance."
   ::= { gs2328MSTI6BridgeSTPStatus 2 }
   
gs2328MSTI6RootID OBJECT-TYPE
   SYNTAX       DisplayString
   MAX-ACCESS   read-only
   STATUS       current
   DESCRIPTION
       "The Bridge ID of the currently elected root bridge."
   ::= { gs2328MSTI6BridgeSTPStatus 3 }
   
gs2328MSTI6RootPort OBJECT-TYPE
   SYNTAX       DisplayString
   MAX-ACCESS   read-only
   STATUS       current
   DESCRIPTION
       "The switch port currently assigned the root port role."
   ::= { gs2328MSTI6BridgeSTPStatus 4 }

gs2328MSTI6RootCost OBJECT-TYPE
   SYNTAX       Integer32(0..200000000)
   MAX-ACCESS   read-only
   STATUS       current
   DESCRIPTION
       "Root Path Cost."
   ::= { gs2328MSTI6BridgeSTPStatus 5 }

gs2328MSTI6TopologyFlag OBJECT-TYPE
   SYNTAX       DisplayString
   MAX-ACCESS   read-only
   STATUS       current
   DESCRIPTION
       "The current state of the Topology Change Flag of this Bridge instance."
   ::= { gs2328MSTI6BridgeSTPStatus 8 }

gs2328MSTI6TopologyChangeCount OBJECT-TYPE
   SYNTAX       Counter32
   MAX-ACCESS   read-only
   STATUS       current
   DESCRIPTION
       "The number of times where the topology change flag has been set."
   ::= { gs2328MSTI6BridgeSTPStatus 9 }
   
gs2328MSTI6TopologyChangeLast OBJECT-TYPE
   SYNTAX       DisplayString
   MAX-ACCESS   read-only
   STATUS       current
   DESCRIPTION
       "The time passed since the Topology Flag was last set."
   ::= { gs2328MSTI6BridgeSTPStatus 10 }
   
gs2328MSTI6PortStateTable OBJECT-TYPE
   SYNTAX      SEQUENCE OF Gs2328MSTI6PortStateEntry
   MAX-ACCESS  not-accessible
   STATUS      current
   DESCRIPTION
       " Show MSTI6 Ports and Aggregations State Configurations. "
   ::= { gs2328MSTI6BridgeSTP 2 }

gs2328MSTI6PortStateEntry OBJECT-TYPE
   SYNTAX      Gs2328MSTI6PortStateEntry
   MAX-ACCESS  not-accessible
   STATUS      current
   DESCRIPTION
       ""
   INDEX    { gs2328MSTI6PortStateIndex  }
   ::= { gs2328MSTI6PortStateTable 1 }

Gs2328MSTI6PortStateEntry ::= SEQUENCE {
   gs2328MSTI6PortStateIndex        Integer32,
   gs2328MSTI6PortStatePort         DisplayString,
   gs2328MSTI6PortStatePortID       DisplayString,
   gs2328MSTI6PortStateRole         DisplayString,
   gs2328MSTI6PortStateState        DisplayString,
   gs2328MSTI6PortStatePathCost     Integer32,
   gs2328MSTI6PortStateEdge         DisplayString,
   gs2328MSTI6PortStatePoint2Point  DisplayString,
   gs2328MSTI6PortStateUptime       DisplayString
}

gs2328MSTI6PortStateIndex OBJECT-TYPE
   SYNTAX      Integer32(1..4095)
   MAX-ACCESS  not-accessible
   STATUS      current
   DESCRIPTION
       "table index."
   ::= { gs2328MSTI6PortStateEntry 1 }
   
gs2328MSTI6PortStatePort OBJECT-TYPE
   SYNTAX      DisplayString
   MAX-ACCESS  read-only
   STATUS      current
   DESCRIPTION
       "The switch port number of the logical STP port."
   ::= { gs2328MSTI6PortStateEntry 2 }
   
gs2328MSTI6PortStatePortID OBJECT-TYPE
   SYNTAX      DisplayString
   MAX-ACCESS  read-only
   STATUS      current
   DESCRIPTION
       "The port id as used by the STP protocol. 
        This is the priority part and the logical port index of the bridge port."
   ::= { gs2328MSTI6PortStateEntry 3 }
   
gs2328MSTI6PortStateRole OBJECT-TYPE
   SYNTAX      DisplayString
   MAX-ACCESS  read-only
   STATUS      current
   DESCRIPTION
       "The current STP port role."
   ::= { gs2328MSTI6PortStateEntry 4 }
   
gs2328MSTI6PortStateState OBJECT-TYPE
   SYNTAX      DisplayString
   MAX-ACCESS  read-only
   STATUS      current
   DESCRIPTION
       "The current STP port state."
   ::= { gs2328MSTI6PortStateEntry 5 }
   
gs2328MSTI6PortStatePathCost OBJECT-TYPE
   SYNTAX      Integer32(0..200000000)
   MAX-ACCESS  read-only
   STATUS      current
   DESCRIPTION
       "The current STP port path cost."
   ::= { gs2328MSTI6PortStateEntry 6 }
   
gs2328MSTI6PortStateEdge OBJECT-TYPE
   SYNTAX      DisplayString
   MAX-ACCESS  read-only
   STATUS      current
   DESCRIPTION
       "The current STP port Edge Flag."
   ::= { gs2328MSTI6PortStateEntry 7 }
   
gs2328MSTI6PortStatePoint2Point OBJECT-TYPE
   SYNTAX      DisplayString
   MAX-ACCESS  read-only
   STATUS      current
   DESCRIPTION
       "The current STP port point-to-point flag."
   ::= { gs2328MSTI6PortStateEntry 8 }
   
gs2328MSTI6PortStateUptime OBJECT-TYPE
   SYNTAX      DisplayString
   MAX-ACCESS  read-only
   STATUS      current
   DESCRIPTION
       "The time since the bridge port was last initialized."
   ::= { gs2328MSTI6PortStateEntry 9 }
   
gs2328MSTI7BridgeSTP                                                        OBJECT IDENTIFIER ::= { gs2328STPBridgeStatus 8 }

gs2328MSTI7BridgeSTPStatus                                                  OBJECT IDENTIFIER ::= { gs2328MSTI7BridgeSTP 1 }
      
gs2328MSTI7BridgeInstance OBJECT-TYPE
   SYNTAX       DisplayString
   MAX-ACCESS   read-only
   STATUS       current
   DESCRIPTION
       "The Bridge instance - CIST, MST1, ..."
   ::= { gs2328MSTI7BridgeSTPStatus 1 }
   
gs2328MSTI7BridgeID OBJECT-TYPE
   SYNTAX       DisplayString
   MAX-ACCESS   read-only
   STATUS       current
   DESCRIPTION
       "The Bridge ID of this Bridge instance."
   ::= { gs2328MSTI7BridgeSTPStatus 2 }
   
gs2328MSTI7RootID OBJECT-TYPE
   SYNTAX       DisplayString
   MAX-ACCESS   read-only
   STATUS       current
   DESCRIPTION
       "The Bridge ID of the currently elected root bridge."
   ::= { gs2328MSTI7BridgeSTPStatus 3 }
   
gs2328MSTI7RootPort OBJECT-TYPE
   SYNTAX       DisplayString
   MAX-ACCESS   read-only
   STATUS       current
   DESCRIPTION
       "The switch port currently assigned the root port role."
   ::= { gs2328MSTI7BridgeSTPStatus 4 }

gs2328MSTI7RootCost OBJECT-TYPE
   SYNTAX       Integer32(0..200000000)
   MAX-ACCESS   read-only
   STATUS       current
   DESCRIPTION
       "Root Path Cost."
   ::= { gs2328MSTI7BridgeSTPStatus 5 }

gs2328MSTI7TopologyFlag OBJECT-TYPE
   SYNTAX       DisplayString
   MAX-ACCESS   read-only
   STATUS       current
   DESCRIPTION
       "The current state of the Topology Change Flag of this Bridge instance."
   ::= { gs2328MSTI7BridgeSTPStatus 8 }

gs2328MSTI7TopologyChangeCount OBJECT-TYPE
   SYNTAX       Counter32
   MAX-ACCESS   read-only
   STATUS       current
   DESCRIPTION
       "The number of times where the topology change flag has been set."
   ::= { gs2328MSTI7BridgeSTPStatus 9 }
   
gs2328MSTI7TopologyChangeLast OBJECT-TYPE
   SYNTAX       DisplayString
   MAX-ACCESS   read-only
   STATUS       current
   DESCRIPTION
       "The time passed since the Topology Flag was last set."
   ::= { gs2328MSTI7BridgeSTPStatus 10 }
   
gs2328MSTI7PortStateTable OBJECT-TYPE
   SYNTAX      SEQUENCE OF Gs2328MSTI7PortStateEntry
   MAX-ACCESS  not-accessible
   STATUS      current
   DESCRIPTION
       " Show MSTI7 Ports and Aggregations State Configurations. "
   ::= { gs2328MSTI7BridgeSTP 2 }

gs2328MSTI7PortStateEntry OBJECT-TYPE
   SYNTAX      Gs2328MSTI7PortStateEntry
   MAX-ACCESS  not-accessible
   STATUS      current
   DESCRIPTION
       ""
   INDEX    { gs2328MSTI7PortStateIndex  }
   ::= { gs2328MSTI7PortStateTable 1 }

Gs2328MSTI7PortStateEntry ::= SEQUENCE {
   gs2328MSTI7PortStateIndex        Integer32,
   gs2328MSTI7PortStatePort         DisplayString,
   gs2328MSTI7PortStatePortID       DisplayString,
   gs2328MSTI7PortStateRole         DisplayString,
   gs2328MSTI7PortStateState        DisplayString,
   gs2328MSTI7PortStatePathCost     Integer32,
   gs2328MSTI7PortStateEdge         DisplayString,
   gs2328MSTI7PortStatePoint2Point  DisplayString,
   gs2328MSTI7PortStateUptime       DisplayString
}

gs2328MSTI7PortStateIndex OBJECT-TYPE
   SYNTAX      Integer32(1..4095)
   MAX-ACCESS  not-accessible
   STATUS      current
   DESCRIPTION
       "table index."
   ::= { gs2328MSTI7PortStateEntry 1 }
   
gs2328MSTI7PortStatePort OBJECT-TYPE
   SYNTAX      DisplayString
   MAX-ACCESS  read-only
   STATUS      current
   DESCRIPTION
       "The switch port number of the logical STP port."
   ::= { gs2328MSTI7PortStateEntry 2 }
   
gs2328MSTI7PortStatePortID OBJECT-TYPE
   SYNTAX      DisplayString
   MAX-ACCESS  read-only
   STATUS      current
   DESCRIPTION
       "The port id as used by the STP protocol. 
        This is the priority part and the logical port index of the bridge port."
   ::= { gs2328MSTI7PortStateEntry 3 }
   
gs2328MSTI7PortStateRole OBJECT-TYPE
   SYNTAX      DisplayString
   MAX-ACCESS  read-only
   STATUS      current
   DESCRIPTION
       "The current STP port role."
   ::= { gs2328MSTI7PortStateEntry 4 }
   
gs2328MSTI7PortStateState OBJECT-TYPE
   SYNTAX      DisplayString
   MAX-ACCESS  read-only
   STATUS      current
   DESCRIPTION
       "The current STP port state."
   ::= { gs2328MSTI7PortStateEntry 5 }
   
gs2328MSTI7PortStatePathCost OBJECT-TYPE
   SYNTAX      Integer32(0..200000000)
   MAX-ACCESS  read-only
   STATUS      current
   DESCRIPTION
       "The current STP port path cost."
   ::= { gs2328MSTI7PortStateEntry 6 }
   
gs2328MSTI7PortStateEdge OBJECT-TYPE
   SYNTAX      DisplayString
   MAX-ACCESS  read-only
   STATUS      current
   DESCRIPTION
       "The current STP port Edge Flag."
   ::= { gs2328MSTI7PortStateEntry 7 }
   
gs2328MSTI7PortStatePoint2Point OBJECT-TYPE
   SYNTAX      DisplayString
   MAX-ACCESS  read-only
   STATUS      current
   DESCRIPTION
       "The current STP port point-to-point flag."
   ::= { gs2328MSTI7PortStateEntry 8 }
   
gs2328MSTI7PortStateUptime OBJECT-TYPE
   SYNTAX      DisplayString
   MAX-ACCESS  read-only
   STATUS      current
   DESCRIPTION
       "The time since the bridge port was last initialized."
   ::= { gs2328MSTI7PortStateEntry 9 }
   
gs2328STPPortStatusTable OBJECT-TYPE
   SYNTAX      SEQUENCE OF Gs2328STPPortStatusEntry
   MAX-ACCESS  not-accessible
   STATUS      current
   DESCRIPTION
       " Show STP Port Status."
   ::= { gs2328STP 9 }

gs2328STPPortStatusEntry OBJECT-TYPE
   SYNTAX      Gs2328STPPortStatusEntry
   MAX-ACCESS  not-accessible
   STATUS      current
   DESCRIPTION
       ""
   INDEX    { gs2328STPPortStatusPort  }
   ::= { gs2328STPPortStatusTable 1 }

Gs2328STPPortStatusEntry ::= SEQUENCE {
   gs2328STPPortStatusPort         Integer32,
   gs2328STPPortStatusCISTRole     DisplayString,
   gs2328STPPortStatusCISTState    DisplayString,
   gs2328STPPortStatusUptime       DisplayString
}

gs2328STPPortStatusPort OBJECT-TYPE
   SYNTAX      Integer32(1..4095)
   MAX-ACCESS  not-accessible
   STATUS      current
   DESCRIPTION
       " port, range : 1 - port number. "
   ::= { gs2328STPPortStatusEntry 1 }

gs2328STPPortStatusCISTRole OBJECT-TYPE
   SYNTAX      DisplayString
   MAX-ACCESS  read-only
   STATUS      current
   DESCRIPTION
       " The current STP port role of the CIST port. "
   ::= { gs2328STPPortStatusEntry 2 }

gs2328STPPortStatusCISTState OBJECT-TYPE
   SYNTAX      DisplayString
   MAX-ACCESS  read-only
   STATUS      current
   DESCRIPTION
       " The current STP port state of the CIST port. "
   ::= { gs2328STPPortStatusEntry 3 }

gs2328STPPortStatusUptime OBJECT-TYPE
   SYNTAX      DisplayString
   MAX-ACCESS  read-only
   STATUS      current
   DESCRIPTION
       " The time since the bridge port was last initialized. "
   ::= { gs2328STPPortStatusEntry 4 }
   
gs2328STPPortStatisticsTable OBJECT-TYPE
   SYNTAX      SEQUENCE OF Gs2328STPPortStatisticsEntry
   MAX-ACCESS  not-accessible
   STATUS      current
   DESCRIPTION
       " Show STP Port Statistics."
   ::= { gs2328STP 10 }

gs2328STPPortStatisticsEntry OBJECT-TYPE
   SYNTAX      Gs2328STPPortStatisticsEntry
   MAX-ACCESS  not-accessible
   STATUS      current
   DESCRIPTION
       ""
   INDEX    { gs2328STPStatisticsIndex  }
   ::= { gs2328STPPortStatisticsTable 1 }

Gs2328STPPortStatisticsEntry ::= SEQUENCE {
   gs2328STPStatisticsIndex            Integer32,
   gs2328STPStatisticsPort             DisplayString,
   gs2328STPStatisticsTxMSTP           Counter32,
   gs2328STPStatisticsTxRSTP           Counter32,
   gs2328STPStatisticsTxSTP            Counter32,
   gs2328STPStatisticsTxTCN            Counter32,
   gs2328STPStatisticsRxMSTP           Counter32,
   gs2328STPStatisticsRxRSTP           Counter32,
   gs2328STPStatisticsRxSTP            Counter32,
   gs2328STPStatisticsRxTCN            Counter32,
   gs2328STPStatisticsDiscardedUnknown Counter32,
   gs2328STPStatisticsDiscardedIllegal Counter32
}

gs2328STPStatisticsIndex OBJECT-TYPE
   SYNTAX      Integer32(1..4095)
   MAX-ACCESS  not-accessible
   STATUS      current
   DESCRIPTION
       "table index."
   ::= { gs2328STPPortStatisticsEntry 1 }
   
gs2328STPStatisticsPort OBJECT-TYPE
   SYNTAX      DisplayString
   MAX-ACCESS  not-accessible
   STATUS      current
   DESCRIPTION
       " port, range : 1 - port number. "
   ::= { gs2328STPPortStatisticsEntry 2 }

gs2328STPStatisticsTxMSTP OBJECT-TYPE
   SYNTAX      Counter32
   MAX-ACCESS  read-only
   STATUS      current
   DESCRIPTION
       " The number of MSTP Configuration BPDU's received/transmitted on the port."
   ::= { gs2328STPPortStatisticsEntry 3 }

gs2328STPStatisticsTxRSTP OBJECT-TYPE
   SYNTAX      Counter32
   MAX-ACCESS  read-only
   STATUS      current
   DESCRIPTION
       " The number of RSTP Configuration BPDU's received/transmitted on the port. "
   ::= { gs2328STPPortStatisticsEntry 4 }

gs2328STPStatisticsTxSTP OBJECT-TYPE
   SYNTAX      Counter32
   MAX-ACCESS  read-only
   STATUS      current
   DESCRIPTION
       " The number of legacy STP Configuration BPDU's received/transmitted on the port. "
   ::= { gs2328STPPortStatisticsEntry 5 }

gs2328STPStatisticsTxTCN OBJECT-TYPE
   SYNTAX      Counter32
   MAX-ACCESS  read-only
   STATUS      current
   DESCRIPTION
       " The number of Topology Change Notification BPDU's received/transmitted on the port. "
   ::= { gs2328STPPortStatisticsEntry 6 }
   
gs2328STPStatisticsRxMSTP OBJECT-TYPE
   SYNTAX      Counter32
   MAX-ACCESS  read-only
   STATUS      current
   DESCRIPTION
       " The number of MSTP Configuration BPDU's received/transmitted on the port."
   ::= { gs2328STPPortStatisticsEntry 7 }

gs2328STPStatisticsRxRSTP OBJECT-TYPE
   SYNTAX      Counter32
   MAX-ACCESS  read-only
   STATUS      current
   DESCRIPTION
       " The number of RSTP Configuration BPDU's received/transmitted on the port. "
   ::= { gs2328STPPortStatisticsEntry 8 }

gs2328STPStatisticsRxSTP OBJECT-TYPE
   SYNTAX      Counter32
   MAX-ACCESS  read-only
   STATUS      current
   DESCRIPTION
       " The number of legacy STP Configuration BPDU's received/transmitted on the port. "
   ::= { gs2328STPPortStatisticsEntry 9 }

gs2328STPStatisticsRxTCN OBJECT-TYPE
   SYNTAX      Counter32
   MAX-ACCESS  read-only
   STATUS      current
   DESCRIPTION
       " The number of Topology Change Notification BPDU's received/transmitted on the port. "
   ::= { gs2328STPPortStatisticsEntry 10 }

gs2328STPStatisticsDiscardedUnknown OBJECT-TYPE
   SYNTAX      Counter32
   MAX-ACCESS  read-only
   STATUS      current
   DESCRIPTION
       " The number of unknown Spanning Tree BPDU's received and discarded on the port. "
   ::= { gs2328STPPortStatisticsEntry 11 }
   
gs2328STPStatisticsDiscardedIllegal OBJECT-TYPE
   SYNTAX      Counter32
   MAX-ACCESS  read-only
   STATUS      current
   DESCRIPTION
       " The number of illegal Spanning Tree BPDU's received and discarded on the port. "
   ::= { gs2328STPPortStatisticsEntry 12 }   


gs2328FilteringDataBase                                                  OBJECT IDENTIFIER ::= { gs2328Configuration 21 }

gs2328FilteringDataBaseConfig                                            OBJECT IDENTIFIER ::= { gs2328FilteringDataBase 1 }

gs2328FilteringDataBaseAgingTime OBJECT-TYPE
   SYNTAX      Integer32(0..1000000)
   MAX-ACCESS  read-write
   STATUS      current
   DESCRIPTION
       "Configure aging time by entering a value here in seconds.
        default: 300,
        range: 10-1000000. 
        Disable automatic aging : 0."
   ::= { gs2328FilteringDataBaseConfig 1 }

gs2328FilteringDataBaseConfigTable OBJECT-TYPE
   SYNTAX      SEQUENCE OF GS2328FilteringDataBaseConfigEntry
   MAX-ACCESS  not-accessible
   STATUS      current
   DESCRIPTION
       " "
   ::= { gs2328FilteringDataBaseConfig 2 }

gs2328FilteringDataBaseConfigEntry OBJECT-TYPE
   SYNTAX      GS2328FilteringDataBaseConfigEntry
   MAX-ACCESS  not-accessible
   STATUS      current
   DESCRIPTION
       ""
   INDEX    { gs2328FilteringDataBaseConfigPort  }
   ::= { gs2328FilteringDataBaseConfigTable 1 }
   
GS2328FilteringDataBaseConfigEntry ::= SEQUENCE {
   gs2328FilteringDataBaseConfigPort        Integer32,
   gs2328FilteringDataBaseConfigLearning    INTEGER
}

gs2328FilteringDataBaseConfigPort OBJECT-TYPE
   SYNTAX      Integer32(1..4095)
   MAX-ACCESS  not-accessible
   STATUS      current
   DESCRIPTION
       " "
   ::= { gs2328FilteringDataBaseConfigEntry 1 }

gs2328FilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2328FilteringDataBaseConfigEntry 2 }


gs2328FilteringDataBaseStaticMAC                                OBJECT IDENTIFIER ::= { gs2328FilteringDataBaseConfig 3 }

gs2328FilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2328FilteringDataBaseStaticMAC 1 }

gs2328FilteringDataBaseStaticMACTable OBJECT-TYPE
   SYNTAX      SEQUENCE OF GS2328FilteringDataBaseStaticMACEntry
   MAX-ACCESS  not-accessible
   STATUS      current
   DESCRIPTION
       " "
   ::= { gs2328FilteringDataBaseStaticMAC 2 }

gs2328FilteringDataBaseStaticMACEntry OBJECT-TYPE
   SYNTAX      GS2328FilteringDataBaseStaticMACEntry
   MAX-ACCESS  not-accessible
   STATUS      current
   DESCRIPTION
       ""
   INDEX    { gs2328FilteringDataBaseStaticMACIndex  }
   ::= { gs2328FilteringDataBaseStaticMACTable 1 }

GS2328FilteringDataBaseStaticMACEntry ::= SEQUENCE {
   gs2328FilteringDataBaseStaticMACIndex	    Integer32,
   gs2328FilteringDataBaseStaticMACVLANId	    Integer32,
   gs2328FilteringDataBaseStaticMACAddress      MacAddress,
   gs2328FilteringDataBaseStaticMACPortMembers  DisplayString,
   gs2328FilteringDataBaseStaticMACRowStatus	INTEGER
}

gs2328FilteringDataBaseStaticMACIndex OBJECT-TYPE
   SYNTAX      Integer32(1..4095)
   MAX-ACCESS  not-accessible
   STATUS      current
   DESCRIPTION
       " "
   ::= { gs2328FilteringDataBaseStaticMACEntry 1 }

gs2328FilteringDataBaseStaticMACVLANId OBJECT-TYPE
   SYNTAX      Integer32(1..4094)
   MAX-ACCESS  read-write
   STATUS      current
   DESCRIPTION
       " VLAN ID, range: 1 - 4094. "
   ::= { gs2328FilteringDataBaseStaticMACEntry 2 }

gs2328FilteringDataBaseStaticMACAddress OBJECT-TYPE
   SYNTAX      MacAddress
   MAX-ACCESS  read-write
   STATUS      current
   DESCRIPTION
       " MAC address, format 0a 1b 2c 3d 4e 5f "
   ::= { gs2328FilteringDataBaseStaticMACEntry 3 }

gs2328FilteringDataBaseStaticMACPortMembers OBJECT-TYPE
   SYNTAX      DisplayString
   MAX-ACCESS  read-write
   STATUS      current
   DESCRIPTION
       "To include the ports in a Static MAC Table"
   ::= { gs2328FilteringDataBaseStaticMACEntry 4 }

gs2328FilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2328FilteringDataBaseStaticMACEntry 5 }
   

gs2328FilteringDataBaseDynamicMACTable OBJECT-TYPE
   SYNTAX      SEQUENCE OF GS2328FilteringDataBaseDynamicMACEntry
   MAX-ACCESS  not-accessible
   STATUS      current
   DESCRIPTION
       " "
   ::= { gs2328FilteringDataBaseConfig 4 }

gs2328FilteringDataBaseDynamicMACEntry OBJECT-TYPE
   SYNTAX      GS2328FilteringDataBaseDynamicMACEntry
   MAX-ACCESS  not-accessible
   STATUS      current
   DESCRIPTION
       ""
   INDEX    { gs2328FilteringDataBaseDynamicMACIndex  }
   ::= { gs2328FilteringDataBaseDynamicMACTable 1 }
   
GS2328FilteringDataBaseDynamicMACEntry ::= SEQUENCE {
   gs2328FilteringDataBaseDynamicMACIndex	    Integer32,
   gs2328FilteringDataBaseDynamicMACType	    INTEGER,
   gs2328FilteringDataBaseDynamicMACVLAN	    Integer32,
   gs2328FilteringDataBaseDynamicMACAddress     MacAddress,
   gs2328FilteringDataBaseDynamicPortMembers    DisplayString
}

gs2328FilteringDataBaseDynamicMACIndex OBJECT-TYPE
   SYNTAX      Integer32(1..4095)
   MAX-ACCESS  not-accessible
   STATUS      current
   DESCRIPTION
       " "
   ::= { gs2328FilteringDataBaseDynamicMACEntry 1 }

gs2328FilteringDataBaseDynamicMACType OBJECT-TYPE
   SYNTAX      INTEGER { dynamic(0), static(1) }
   MAX-ACCESS  read-only
   STATUS      current
   DESCRIPTION
       "Indicates whether the entry is a static or a dynamic entry."
   ::= { gs2328FilteringDataBaseDynamicMACEntry 2 }

gs2328FilteringDataBaseDynamicMACVLAN OBJECT-TYPE
   SYNTAX      Integer32(1..4094)
   MAX-ACCESS  read-only
   STATUS      current
   DESCRIPTION
       "The VLAN ID of the entry."
   ::= { gs2328FilteringDataBaseDynamicMACEntry 3 }

gs2328FilteringDataBaseDynamicMACAddress OBJECT-TYPE
   SYNTAX      MacAddress
   MAX-ACCESS  read-only
   STATUS      current
   DESCRIPTION
       "The MAC address of the entry."
   ::= { gs2328FilteringDataBaseDynamicMACEntry 4 }
   
gs2328FilteringDataBaseDynamicPortMembers OBJECT-TYPE
   SYNTAX      DisplayString
   MAX-ACCESS  read-only
   STATUS      current
   DESCRIPTION
       "The ports that are members of the entry."
   ::= { gs2328FilteringDataBaseDynamicMACEntry 5 } 


gs2328SFlowAgent                                                  OBJECT IDENTIFIER ::= { gs2328Configuration 22 }

gs2328SFlowAgentCollector                                            OBJECT IDENTIFIER ::= { gs2328SFlowAgent 1 }

gs2328SFlowAgentReceiverMode OBJECT-TYPE
   SYNTAX      INTEGER { disable(0), enable(1) }
   MAX-ACCESS  read-write
   STATUS      current
   DESCRIPTION
       "default: 0
       0: disable
       1: enable "
   ::= { gs2328SFlowAgentCollector 1 }


gs2328LMC                                                   OBJECT IDENTIFIER ::= { gs2328Configuration 1500 }

gs2328LMCOperating OBJECT-TYPE
   SYNTAX      INTEGER { disabled(0), enabled(1), try(2) }
   MAX-ACCESS  read-write
   STATUS      current
   DESCRIPTION
       "0: disabled
        1: enabled
        2: try"
   ::= { gs2328LMC 1 }

gs2328LMCConfigViaDhcp OBJECT-TYPE
   SYNTAX      INTEGER { disabled(0), enabled(1) }
   MAX-ACCESS  read-write
   STATUS      current
   DESCRIPTION
       "0: disabled
        1: enabled"
   ::= { gs2328LMC 2 }

gs2328LMCDomain OBJECT-TYPE
   SYNTAX      DisplayString(SIZE(0..255))
   MAX-ACCESS  read-write
   STATUS      current
   DESCRIPTION
       "0: disabled
        1: enabled"
   ::= { gs2328LMC 3 }

gs2328LMChcpClientAutoRenew OBJECT-TYPE
   SYNTAX      INTEGER { disabled(0), enabled(1) }
   MAX-ACCESS  read-write
   STATUS      current
   DESCRIPTION
       "0: disabled
        1: enabled"
   ::= { gs2328LMC 4 }
   

   
gs2328LMCZeroTouchSupport OBJECT-TYPE
   SYNTAX      INTEGER { No(0), Yes(1) }
   MAX-ACCESS  read-only
   STATUS      current
   DESCRIPTION
       "0: No
        1: Yes"
   ::= { gs2328LMC 50 }   
   
gs2328LMCPairingTokenPresent OBJECT-TYPE
   SYNTAX      INTEGER { No(0), Yes(1) }
   MAX-ACCESS  read-only
   STATUS      current
   DESCRIPTION
       "0: No
        1: Yes"
   ::= { gs2328LMC 51 }
   
gs2328LMCClientStatus OBJECT-TYPE
   SYNTAX      DisplayString
   MAX-ACCESS  read-only
   STATUS      current
   DESCRIPTION
           ""
   ::= { gs2328LMC  52 }
   
   
gs2328LMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2328LMC  53 }
   
gs2328LMCControlStatus OBJECT-TYPE
   SYNTAX      INTEGER {Disabled(2), Operating(4)}
   MAX-ACCESS  read-only
   STATUS      current
   DESCRIPTION
           "2: Disabled
            4: Operating"
   ::= { gs2328LMC  54 }          
   
gs2328LMCMonitoringStatus OBJECT-TYPE
   SYNTAX      INTEGER {Disabled(2), Operating(4)}
   MAX-ACCESS  read-only
   STATUS      current
   DESCRIPTION
           "2: Disabled
            4: Operating"
   ::= { gs2328LMC  55 }
   
gs2328LMCConfigurationSource OBJECT-TYPE
   SYNTAX      DisplayString
   MAX-ACCESS  read-only
   STATUS      current
   DESCRIPTION
           ""
   ::= { gs2328LMC  56 }
   
gs2328LMCConfigModified OBJECT-TYPE
   SYNTAX      INTEGER { No(0), Yes(1) }
   MAX-ACCESS  read-only
   STATUS      current
   DESCRIPTION
       "0: No
        1: Yes"
   ::= { gs2328LMC 57 }
   
gs2328LMCDeviceID OBJECT-TYPE
   SYNTAX      DisplayString
   MAX-ACCESS  read-only
   STATUS      current
   DESCRIPTION
           ""
   ::= { gs2328LMC  58 }
   
gs2328LMCRoundTripTime OBJECT-TYPE
   SYNTAX      INTEGER
   MAX-ACCESS  read-only
   STATUS      current
   DESCRIPTION
           ""
   ::= { gs2328LMC  100 }
----------------------------------------------------------------------------------------------------------------------------
gs2328Security                                              OBJECT IDENTIFIER ::= { lancomGS2328  3 }

gs2328IPSourceGuard                                         OBJECT IDENTIFIER ::= { gs2328Security 1 }

gs2328IPSourceGuardConf                                     OBJECT IDENTIFIER ::= { gs2328IPSourceGuard 1 }

gs2328IPSourceGuardMode OBJECT-TYPE
   SYNTAX      INTEGER { disable(0), enable(1) }
   MAX-ACCESS  read-write
   STATUS      current
   DESCRIPTION
       " default:  0
        0: disable
        1: enable"
   ::= { gs2328IPSourceGuardConf 1 }

gs2328IPSourceGuardPortConfigTable OBJECT-TYPE
   SYNTAX      SEQUENCE OF GS2328IPSourceGuardPortConfigEntry
   MAX-ACCESS  not-accessible
   STATUS      current
   DESCRIPTION
       " "
   ::= { gs2328IPSourceGuardConf 2 }

gs2328IPSourceGuardPortConfigEntry OBJECT-TYPE
   SYNTAX      GS2328IPSourceGuardPortConfigEntry
   MAX-ACCESS  not-accessible
   STATUS      current
   DESCRIPTION
       ""
   INDEX    { gs2328IPSourceGuardPortConfigPort  }
   ::= { gs2328IPSourceGuardPortConfigTable 1 }

GS2328IPSourceGuardPortConfigEntry ::= SEQUENCE {
   gs2328IPSourceGuardPortConfigPort               Integer32,
   gs2328IPSourceGuardPortConfigMode               INTEGER,
   gs2328IPSourceGuardPortMaxDynamicClients        Integer32
}

gs2328IPSourceGuardPortConfigPort OBJECT-TYPE
   SYNTAX      Integer32(1..4095)
   MAX-ACCESS  not-accessible
   STATUS      current
   DESCRIPTION
       " "
   ::= { gs2328IPSourceGuardPortConfigEntry 1 }

gs2328IPSourceGuardPortConfigMode OBJECT-TYPE
   SYNTAX      INTEGER { disable(0), enable(1) }
   MAX-ACCESS  read-write
   STATUS      current
   DESCRIPTION
       "default: 0
       0:disable
       1:enable "
   ::= { gs2328IPSourceGuardPortConfigEntry 2 }

gs2328IPSourceGuardPortMaxDynamicClients OBJECT-TYPE
   SYNTAX      Integer32(0..2|99)
   MAX-ACCESS  read-write
   STATUS      current
   DESCRIPTION
       "default: 99
       0~2: Max Dynamic clients
       99:Unlimited "
   ::= { gs2328IPSourceGuardPortConfigEntry 3 }


gs2328IPSourceGuardStatic                                OBJECT IDENTIFIER ::= { gs2328IPSourceGuard 2 }

gs2328IPSourceGuardStaticCreate OBJECT-TYPE
   SYNTAX       INTEGER { none(0), create(1) }
   MAX-ACCESS   read-write
   STATUS       current
   DESCRIPTION
       "default: 0
        0 : None  (read only)
        1 : Create a IP Source Guard"
   ::= { gs2328IPSourceGuardStatic 1 }

gs2328IPSourceGuardStaticTable OBJECT-TYPE
   SYNTAX      SEQUENCE OF GS2328IPSourceGuardStaticEntry
   MAX-ACCESS  not-accessible
   STATUS      current
   DESCRIPTION
       " "
   ::= { gs2328IPSourceGuardStatic 2 }

gs2328IPSourceGuardStaticEntry OBJECT-TYPE
   SYNTAX      GS2328IPSourceGuardStaticEntry
   MAX-ACCESS  not-accessible
   STATUS      current
   DESCRIPTION
       ""
   INDEX    { gs2328IPSourceGuardStaticIndex  }
   ::= { gs2328IPSourceGuardStaticTable 1 }

GS2328IPSourceGuardStaticEntry ::= SEQUENCE {
   gs2328IPSourceGuardStaticIndex         Integer32,
   gs2328IPSourceGuardStaticPort          Integer32,
   gs2328IPSourceGuardStaticVLANId        Integer32,
   gs2328IPSourceGuardStaticIPAddress     IpAddress,
   gs2328IPSourceGuardStaticMACAddress    MacAddress,
   gs2328IPSourceGuardStaticRowStatus     INTEGER
}

gs2328IPSourceGuardStaticIndex OBJECT-TYPE
   SYNTAX      Integer32(1..28)
   MAX-ACCESS  not-accessible
   STATUS      current
   DESCRIPTION
       " "
   ::= { gs2328IPSourceGuardStaticEntry 1 }

gs2328IPSourceGuardStaticPort OBJECT-TYPE
   SYNTAX      Integer32(1..4095)
   MAX-ACCESS  read-write
   STATUS      current
   DESCRIPTION
       " Port, range: 1 - port number. "
   ::= { gs2328IPSourceGuardStaticEntry 2 }

gs2328IPSourceGuardStaticVLANId OBJECT-TYPE
   SYNTAX      Integer32(1..4094)
   MAX-ACCESS  read-write
   STATUS      current
   DESCRIPTION
       " VLAN ID, range: 1 - 4094. "
   ::= { gs2328IPSourceGuardStaticEntry 3 }

gs2328IPSourceGuardStaticIPAddress OBJECT-TYPE
   SYNTAX      IpAddress
   MAX-ACCESS  read-write
   STATUS      current
   DESCRIPTION
       " IP address allowed for doing IP source guard. "
   ::= { gs2328IPSourceGuardStaticEntry 4 }

gs2328IPSourceGuardStaticMACAddress OBJECT-TYPE
   SYNTAX      MacAddress
   MAX-ACCESS  read-write
   STATUS      current
   DESCRIPTION
       " Allowed Source MAC address, format 0a 1b 2c 3d 4e 5f "
   ::= { gs2328IPSourceGuardStaticEntry 5 }

gs2328IPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2328IPSourceGuardStaticEntry 6 }

gs2328IPSourceGuardDynamicTable OBJECT-TYPE
   SYNTAX      SEQUENCE OF GS2328IPSourceGuardDynamicEntry
   MAX-ACCESS  not-accessible
   STATUS      current
   DESCRIPTION
       " "
   ::= { gs2328IPSourceGuard 3 }

gs2328IPSourceGuardDynamicEntry OBJECT-TYPE
   SYNTAX      GS2328IPSourceGuardDynamicEntry
   MAX-ACCESS  not-accessible
   STATUS      current
   DESCRIPTION
       ""
   INDEX    { gs2328IPSourceGuardDynamicIndex  }
   ::= { gs2328IPSourceGuardDynamicTable 1 }

GS2328IPSourceGuardDynamicEntry ::= SEQUENCE {
   gs2328IPSourceGuardDynamicIndex          Integer32,
   gs2328IPSourceGuardDynamicPort           Integer32,
   gs2328IPSourceGuardDynamicVLANId         Integer32,
   gs2328IPSourceGuardDynamicIPAddress      IpAddress,
   gs2328IPSourceGuardDynamicMACAddress     MacAddress
}

gs2328IPSourceGuardDynamicIndex OBJECT-TYPE
   SYNTAX      Integer32(1..4095)
   MAX-ACCESS  not-accessible
   STATUS      current
   DESCRIPTION
       " "
   ::= { gs2328IPSourceGuardDynamicEntry 1 }

gs2328IPSourceGuardDynamicPort OBJECT-TYPE
   SYNTAX      Integer32(1..10)
   MAX-ACCESS  read-only
   STATUS      current
   DESCRIPTION
       " "
   ::= { gs2328IPSourceGuardDynamicEntry 2 }

gs2328IPSourceGuardDynamicVLANId OBJECT-TYPE
   SYNTAX      Integer32(1..4094)
   MAX-ACCESS  read-only
   STATUS      current
   DESCRIPTION
       " "
   ::= { gs2328IPSourceGuardDynamicEntry 3 }

gs2328IPSourceGuardDynamicIPAddress OBJECT-TYPE
   SYNTAX      IpAddress
   MAX-ACCESS  read-only
   STATUS      current
   DESCRIPTION
       " "
   ::= { gs2328IPSourceGuardDynamicEntry 4 }

gs2328IPSourceGuardDynamicMACAddress OBJECT-TYPE
   SYNTAX      MacAddress
   MAX-ACCESS  read-only
   STATUS      current
   DESCRIPTION
       " "
   ::= { gs2328IPSourceGuardDynamicEntry 5 }

gs2328ARPInspection                                         OBJECT IDENTIFIER ::= { gs2328Security 2 }

gs2328ARPInspectionConf                                     OBJECT IDENTIFIER ::= { gs2328ARPInspection 1 }

gs2328ARPInspectionConfMode OBJECT-TYPE
   SYNTAX      INTEGER { disable(0), enable(1) }
   MAX-ACCESS  read-write
   STATUS      current
   DESCRIPTION
       "default: 0
        0: disable
        1: enable"
   ::= { gs2328ARPInspectionConf 1 }

gs2328ARPInspectionConfTable OBJECT-TYPE
   SYNTAX      SEQUENCE OF GS2328ARPInspectionConfEntry
   MAX-ACCESS  not-accessible
   STATUS      current
   DESCRIPTION
       " "
   ::= { gs2328ARPInspectionConf 2 }

gs2328ARPInspectionConfEntry OBJECT-TYPE
   SYNTAX      GS2328ARPInspectionConfEntry
   MAX-ACCESS  not-accessible
   STATUS      current
   DESCRIPTION
       ""
   INDEX    { gs2328ARPInspectionConfPortIndex  }
   ::= { gs2328ARPInspectionConfTable 1 }

GS2328ARPInspectionConfEntry ::= SEQUENCE {
   gs2328ARPInspectionConfPortIndex	Integer32,
   gs2328ARPInspectionConfPortMode	INTEGER
}

gs2328ARPInspectionConfPortIndex OBJECT-TYPE
   SYNTAX      Integer32(1..4095)
   MAX-ACCESS  not-accessible
   STATUS      current
   DESCRIPTION
       " "
   ::= { gs2328ARPInspectionConfEntry 1 }

gs2328ARPInspectionConfPortMode OBJECT-TYPE
   SYNTAX      INTEGER { disable(0), enable(1) }
   MAX-ACCESS  read-write
   STATUS      current
   DESCRIPTION
       "default: 0
        0: disable
        1: enable"
   ::= { gs2328ARPInspectionConfEntry 2 }


gs2328ARPInspectionStatic                                OBJECT IDENTIFIER ::= { gs2328ARPInspection 2 }

gs2328ARPInspectionStaticCreate OBJECT-TYPE
   SYNTAX      INTEGER { none(0), create(1) }
   MAX-ACCESS  read-write
   STATUS      current
   DESCRIPTION
       "default: 0
        0: none
        1: create"
   ::= { gs2328ARPInspectionStatic 1 }

gs2328ARPInspectionStaticTable OBJECT-TYPE
   SYNTAX      SEQUENCE OF GS2328ARPInspectionStaticEntry
   MAX-ACCESS  not-accessible
   STATUS      current
   DESCRIPTION
       " "
   ::= { gs2328ARPInspectionStatic 2 }

gs2328ARPInspectionStaticEntry OBJECT-TYPE
   SYNTAX      GS2328ARPInspectionStaticEntry
   MAX-ACCESS  not-accessible
   STATUS      current
   DESCRIPTION
       ""
   INDEX    { gs2328ARPInspectionStaticIndex  }
   ::= { gs2328ARPInspectionStaticTable 1 }

GS2328ARPInspectionStaticEntry ::= SEQUENCE {
   gs2328ARPInspectionStaticIndex       Integer32,
   gs2328ARPInspectionStaticPort        Integer32,
   gs2328ARPInspectionStaticVLANId      Integer32,
   gs2328ARPInspectionStaticIPAddress   IpAddress,
   gs2328ARPInspectionStaticMACAddress  MacAddress,
   gs2328ARPInspectionStaticRowStatus   INTEGER
}

gs2328ARPInspectionStaticIndex OBJECT-TYPE
   SYNTAX      Integer32(1..4095)
   MAX-ACCESS  not-accessible
   STATUS      current
   DESCRIPTION
       ""
   ::= { gs2328ARPInspectionStaticEntry 1 }

gs2328ARPInspectionStaticPort OBJECT-TYPE
   SYNTAX      Integer32(1..4095)
   MAX-ACCESS  read-write
   STATUS      current
   DESCRIPTION
       " Port, range: 1 - port number. "
   ::= { gs2328ARPInspectionStaticEntry 2 }

gs2328ARPInspectionStaticVLANId OBJECT-TYPE
   SYNTAX      Integer32(1..4094)
   MAX-ACCESS  read-write
   STATUS      current
   DESCRIPTION
       " VLAN ID, range: 1 - 4094. "
   ::= { gs2328ARPInspectionStaticEntry 3 }

gs2328ARPInspectionStaticIPAddress OBJECT-TYPE
   SYNTAX      IpAddress
   MAX-ACCESS  read-write
   STATUS      current
   DESCRIPTION
       " IP address allowed for doing ARP request. "
   ::= { gs2328ARPInspectionStaticEntry 4 }

gs2328ARPInspectionStaticMACAddress OBJECT-TYPE
   SYNTAX      MacAddress
   MAX-ACCESS  read-write
   STATUS      current
   DESCRIPTION
       " Allowed Source MAC address in ARP request packets, format 0a 1b 2c 3d 4e 5f "
   ::= { gs2328ARPInspectionStaticEntry 5 }

gs2328ARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2328ARPInspectionStaticEntry 6 }

gs2328ARPInspectionDynamicTable OBJECT-TYPE
   SYNTAX      SEQUENCE OF GS2328ARPInspectionDynamicEntry
   MAX-ACCESS  not-accessible
   STATUS      current
   DESCRIPTION
       " "
   ::= { gs2328ARPInspection 3 }

gs2328ARPInspectionDynamicEntry OBJECT-TYPE
   SYNTAX      GS2328ARPInspectionDynamicEntry
   MAX-ACCESS  not-accessible
   STATUS      current
   DESCRIPTION
       ""
   INDEX    { gs2328ARPInspectionDynamicIndex  }
   ::= { gs2328ARPInspectionDynamicTable 1 }

GS2328ARPInspectionDynamicEntry ::= SEQUENCE {
   gs2328ARPInspectionDynamicIndex          Integer32,
   gs2328ARPInspectionDynamicPort           Integer32,
   gs2328ARPInspectionDynamicVLANId         Integer32,
   gs2328ARPInspectionDynamicIPAddress      IpAddress,
   gs2328ARPInspectionDynamicMACAddress     MacAddress
}

gs2328ARPInspectionDynamicIndex OBJECT-TYPE
   SYNTAX      Integer32(1..4095)
   MAX-ACCESS  not-accessible
   STATUS      current
   DESCRIPTION
       " "
   ::= { gs2328ARPInspectionDynamicEntry 1 }

gs2328ARPInspectionDynamicPort OBJECT-TYPE
   SYNTAX      Integer32(1..4095)
   MAX-ACCESS  read-only
   STATUS      current
   DESCRIPTION
       ""
   ::= { gs2328ARPInspectionDynamicEntry 2 }

gs2328ARPInspectionDynamicVLANId OBJECT-TYPE
   SYNTAX      Integer32(1..4094)
   MAX-ACCESS  read-only
   STATUS      current
   DESCRIPTION
       ""
   ::= { gs2328ARPInspectionDynamicEntry 3 }

gs2328ARPInspectionDynamicIPAddress OBJECT-TYPE
   SYNTAX      IpAddress
   MAX-ACCESS  read-only
   STATUS      current
   DESCRIPTION
       ""
   ::= { gs2328ARPInspectionDynamicEntry 4 }

gs2328ARPInspectionDynamicMACAddress OBJECT-TYPE
   SYNTAX      MacAddress
   MAX-ACCESS  read-only
   STATUS      current
   DESCRIPTION
       ""
   ::= { gs2328ARPInspectionDynamicEntry 5 }

gs2328ARPStaticGatewayCtrl	                                OBJECT IDENTIFIER ::= { gs2328ARPInspection 6 }

gs2328ARPStaticGatewayCtrlSystemConf                                      OBJECT IDENTIFIER ::= { gs2328ARPStaticGatewayCtrl 1 }

gs2328ARPStaticGatewayCtrlMode OBJECT-TYPE
   SYNTAX      INTEGER { disable(0), enable(1) }
   MAX-ACCESS  read-write
   STATUS      current
   DESCRIPTION
       "default: 0
       0: disable
       1: enable "
   ::= { gs2328ARPStaticGatewayCtrlSystemConf 1 }

gs2328ARPStaticGatewayCtrlCreate OBJECT-TYPE
   SYNTAX      INTEGER { none(0), create(1) }
   MAX-ACCESS  read-write
   STATUS      current
   DESCRIPTION
       "default: 0
        0: none
        1: create"
   ::= { gs2328ARPStaticGatewayCtrl 2 }

gs2328ARPStaticGatewayCtrlTable OBJECT-TYPE
   SYNTAX      SEQUENCE OF GS2328ARPStaticGatewayCtrlEntry
   MAX-ACCESS  not-accessible
   STATUS      current
   DESCRIPTION
       " "
   ::= { gs2328ARPStaticGatewayCtrl 3 }

gs2328ARPStaticGatewayCtrlEntry OBJECT-TYPE
   SYNTAX      GS2328ARPStaticGatewayCtrlEntry
   MAX-ACCESS  not-accessible
   STATUS      current
   DESCRIPTION
       ""
   INDEX    { gs2328ARPStaticGatewayCtrlIndex  }
   ::= { gs2328ARPStaticGatewayCtrlTable 1 }

GS2328ARPStaticGatewayCtrlEntry ::= SEQUENCE {
   gs2328ARPStaticGatewayCtrlIndex       Integer32,
   gs2328ARPStaticGatewayCtrlIPAddress   IpAddress,
   gs2328ARPStaticGatewayCtrlMACAddress  MacAddress,
   gs2328ARPStaticGatewayCtrlPort        Integer32,
   gs2328ARPStaticGatewayCtrlAction      INTEGER,
   gs2328ARPStaticGatewayCtrlState       DisplayString,
   gs2328ARPStaticGatewayCtrlReOpen      INTEGER,
   gs2328ARPStaticGatewayCtrlRowStatus   INTEGER
}

gs2328ARPStaticGatewayCtrlIndex OBJECT-TYPE
   SYNTAX      Integer32(1..4)
   MAX-ACCESS  not-accessible
   STATUS      current
   DESCRIPTION
       ""
   ::= { gs2328ARPStaticGatewayCtrlEntry 1 }

gs2328ARPStaticGatewayCtrlIPAddress OBJECT-TYPE
   SYNTAX      IpAddress
   MAX-ACCESS  read-write
   STATUS      current
   DESCRIPTION
       " Source IP address. "
   ::= { gs2328ARPStaticGatewayCtrlEntry 2 }

gs2328ARPStaticGatewayCtrlMACAddress OBJECT-TYPE
   SYNTAX      MacAddress
   MAX-ACCESS  read-write
   STATUS      current
   DESCRIPTION
       " Source MAC address , format 0a 1b 2c 3d 4e 5f "
   ::= { gs2328ARPStaticGatewayCtrlEntry 3 }

gs2328ARPStaticGatewayCtrlPort OBJECT-TYPE
   SYNTAX      Integer32(1..4095)
   MAX-ACCESS  read-write
   STATUS      current
   DESCRIPTION
       " Port, range: 1 - port number. "
   ::= { gs2328ARPStaticGatewayCtrlEntry 4 }

gs2328ARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2328ARPStaticGatewayCtrlEntry 5 }

gs2328ARPStaticGatewayCtrlState OBJECT-TYPE
   SYNTAX      DisplayString
   MAX-ACCESS  read-only
   STATUS      current
   DESCRIPTION
       ""
   ::= { gs2328ARPStaticGatewayCtrlEntry 6 }

gs2328ARPStaticGatewayCtrlReOpen OBJECT-TYPE
   SYNTAX      INTEGER { none(0), reopen(1) }
   MAX-ACCESS  read-write
   STATUS      current
   DESCRIPTION
       "default: 0
       0: none
       1: reopen"
   ::= { gs2328ARPStaticGatewayCtrlEntry 7 }  
   
gs2328ARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2328ARPStaticGatewayCtrlEntry 8 }

gs2328ARPSpoofingPrevention	                                OBJECT IDENTIFIER ::= { gs2328ARPInspection 7 }

gs2328ARPSpoofingPreventionSystemConf                                      OBJECT IDENTIFIER ::= { gs2328ARPSpoofingPrevention 1 }

gs2328ARPSpoofingPreventionMode OBJECT-TYPE
   SYNTAX      INTEGER { disable(0), enable(1) }
   MAX-ACCESS  read-write
   STATUS      current
   DESCRIPTION
       "default: 0
       0: disable
       1: enable "
   ::= { gs2328ARPSpoofingPreventionSystemConf 1 }

gs2328ARPSpoofingPreventionTable OBJECT-TYPE
   SYNTAX      SEQUENCE OF GS2328ARPSpoofingPreventionEntry
   MAX-ACCESS  not-accessible
   STATUS      current
   DESCRIPTION
       " "
   ::= { gs2328ARPSpoofingPrevention 2 }

gs2328ARPSpoofingPreventionEntry OBJECT-TYPE
   SYNTAX      GS2328ARPSpoofingPreventionEntry
   MAX-ACCESS  not-accessible
   STATUS      current
   DESCRIPTION
       ""
   INDEX    { gs2328ARPSpoofingPreventionPort  }
   ::= { gs2328ARPSpoofingPreventionTable 1 }

GS2328ARPSpoofingPreventionEntry ::= SEQUENCE {
   gs2328ARPSpoofingPreventionPort           Integer32,
   gs2328ARPSpoofingPreventionPortMode       INTEGER,
   gs2328ARPSpoofingPreventionPortLimit      Integer32,
   gs2328ARPSpoofingPreventionPortAction     INTEGER,
   gs2328ARPSpoofingPreventionPortState      DisplayString,
   gs2328ARPSpoofingPreventionPortReOpen     INTEGER
}

gs2328ARPSpoofingPreventionPort OBJECT-TYPE
   SYNTAX      Integer32(1..4095)
   MAX-ACCESS  not-accessible
   STATUS      current
   DESCRIPTION
       " "
   ::= { gs2328ARPSpoofingPreventionEntry 1 }

gs2328ARPSpoofingPreventionPortMode OBJECT-TYPE
   SYNTAX      INTEGER { disable(0), enable(1) }
   MAX-ACCESS  read-write
   STATUS      current
   DESCRIPTION
       "default: 0
       0: disable
       1: enable"
   ::= { gs2328ARPSpoofingPreventionEntry 2 }

gs2328ARPSpoofingPreventionPortLimit OBJECT-TYPE
   SYNTAX      Integer32(1..100)
   MAX-ACCESS  read-write
   STATUS      current
   DESCRIPTION
       "default: 1, range: 1-100"
   ::= { gs2328ARPSpoofingPreventionEntry 3 }

gs2328ARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2328ARPSpoofingPreventionEntry 4 }

gs2328ARPSpoofingPreventionPortState OBJECT-TYPE
   SYNTAX      DisplayString
   MAX-ACCESS  read-only
   STATUS      current
   DESCRIPTION
       ""
   ::= { gs2328ARPSpoofingPreventionEntry 5 }

gs2328ARPSpoofingPreventionPortReOpen OBJECT-TYPE
   SYNTAX      INTEGER { none(0), reopen(1) }
   MAX-ACCESS  read-write
   STATUS      current
   DESCRIPTION
       "default: 0
       0: none
       1: reopen"
   ::= { gs2328ARPSpoofingPreventionEntry 6 }  

gs2328ARPIPDoSPrevention	                                OBJECT IDENTIFIER ::= { gs2328ARPInspection 8 }

gs2328ARPIPDoSPreventionTCPMode OBJECT-TYPE
   SYNTAX      INTEGER { disable(0), enable(1) }
   MAX-ACCESS  read-write
   STATUS      current
   DESCRIPTION
       "default: 0
       0: disable
       1: enable "
   ::= { gs2328ARPIPDoSPrevention 1 }

gs2328ARPIPDoSPreventionUDPMode OBJECT-TYPE
   SYNTAX      INTEGER { disable(0), enable(1) }
   MAX-ACCESS  read-write
   STATUS      current
   DESCRIPTION
       "default: 0
       0: disable
       1: enable "
   ::= { gs2328ARPIPDoSPrevention 2 }
   
gs2328ARPIPDoSPreventionICMPMode OBJECT-TYPE
   SYNTAX      INTEGER { disable(0), enable(1) }
   MAX-ACCESS  read-write
   STATUS      current
   DESCRIPTION
       "default: 0
       0: disable
       1: enable "
   ::= { gs2328ARPIPDoSPrevention 3 }   

gs2328ARPIPDoSPreventionServerPort1 OBJECT-TYPE
   SYNTAX      Integer32(0..4094)
   MAX-ACCESS  read-write
   STATUS      current
   DESCRIPTION
       " Port, range: 0 - port number. 0: none. "
   ::= { gs2328ARPIPDoSPrevention 4 }  

gs2328ARPIPDoSPreventionServerPort2 OBJECT-TYPE
   SYNTAX      Integer32(0..4094)
   MAX-ACCESS  read-write
   STATUS      current
   DESCRIPTION
       " Port, range: 0 - port number. 0: none. "
   ::= { gs2328ARPIPDoSPrevention 5 }  
   
gs2328ARPIPDoSPreventionServerPort3 OBJECT-TYPE
   SYNTAX      Integer32(0..4094)
   MAX-ACCESS  read-write
   STATUS      current
   DESCRIPTION
       " Port, range: 0 - port number. 0: none. "
   ::= { gs2328ARPIPDoSPrevention 6 }  
   
gs2328ARPIPDoSPreventionServerPort4 OBJECT-TYPE
   SYNTAX      Integer32(0..4094)
   MAX-ACCESS  read-write
   STATUS      current
   DESCRIPTION
       " Port, range: 0 - port number. 0: none. "
   ::= { gs2328ARPIPDoSPrevention 7 }        

gs2328DHCPSnooping                                          OBJECT IDENTIFIER ::= { gs2328Security 3 }

gs2328DHCPSnoopingConf                                          OBJECT IDENTIFIER ::= { gs2328DHCPSnooping 1 }

gs2328DHCPSnoopingMode OBJECT-TYPE
   SYNTAX      INTEGER { disable(0), enable(1) }
   MAX-ACCESS  read-write
   STATUS      current
   DESCRIPTION
       "default: 0
       0: disable
       1: enable"
   ::= { gs2328DHCPSnoopingConf 1 }

gs2328DHCPSnoopingPortModeConfigurationTable OBJECT-TYPE
   SYNTAX      SEQUENCE OF GS2328DHCPSnoopingPortModeConfigurationEntry
   MAX-ACCESS  not-accessible
   STATUS      current
   DESCRIPTION
       " "
   ::= { gs2328DHCPSnoopingConf 2 }

gs2328DHCPSnoopingPortModeConfigurationEntry OBJECT-TYPE
   SYNTAX      GS2328DHCPSnoopingPortModeConfigurationEntry
   MAX-ACCESS  not-accessible
   STATUS      current
   DESCRIPTION
       ""
   INDEX    { gs2328DHCPSnoopingPortModeConfigurationPort  }
   ::= { gs2328DHCPSnoopingPortModeConfigurationTable 1 }
   
GS2328DHCPSnoopingPortModeConfigurationEntry ::= SEQUENCE {
   gs2328DHCPSnoopingPortModeConfigurationPort	Integer32,
   gs2328DHCPSnoopingPortModeConfigurationMode	INTEGER
}

gs2328DHCPSnoopingPortModeConfigurationPort OBJECT-TYPE
   SYNTAX      Integer32(1..4095)
   MAX-ACCESS  not-accessible
   STATUS      current
   DESCRIPTION
       " "
   ::= { gs2328DHCPSnoopingPortModeConfigurationEntry 1 }

gs2328DHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2328DHCPSnoopingPortModeConfigurationEntry 2 }

gs2328DHCPSnoopingStatisticsTable OBJECT-TYPE
   SYNTAX      SEQUENCE OF GS2328DHCPSnoopingStatisticsEntry
   MAX-ACCESS  not-accessible
   STATUS      current
   DESCRIPTION
       " "
   ::= { gs2328DHCPSnooping 2 }

gs2328DHCPSnoopingStatisticsEntry OBJECT-TYPE
   SYNTAX      GS2328DHCPSnoopingStatisticsEntry
   MAX-ACCESS  not-accessible
   STATUS      current
   DESCRIPTION
       ""
   INDEX    { gs2328DHCPSnoopingStatisticsPort  }
   ::= { gs2328DHCPSnoopingStatisticsTable 1 }

GS2328DHCPSnoopingStatisticsEntry ::= SEQUENCE {
   gs2328DHCPSnoopingStatisticsPort         Integer32,
   gs2328DHCPSnoopingStatisticsClear        INTEGER,
   gs2328DHCPSnoopingRxDiscover             Counter32,
   gs2328DHCPSnoopingRxOffer                Counter32,
   gs2328DHCPSnoopingRxRequest              Counter32,
   gs2328DHCPSnoopingRxDecline              Counter32,
   gs2328DHCPSnoopingRxACK                  Counter32,
   gs2328DHCPSnoopingRxNAK                  Counter32,
   gs2328DHCPSnoopingRxRelease              Counter32,
   gs2328DHCPSnoopingRxInform               Counter32,
   gs2328DHCPSnoopingRxLeaseQuery           Counter32,
   gs2328DHCPSnoopingRxLeaseUnassigned      Counter32,
   gs2328DHCPSnoopingRxLeaseUnknown         Counter32,
   gs2328DHCPSnoopingRxLeaseActive          Counter32,
   gs2328DHCPSnoopingTxDiscover             Counter32,
   gs2328DHCPSnoopingTxOffer                Counter32,
   gs2328DHCPSnoopingTxRequest              Counter32,
   gs2328DHCPSnoopingTxDecline              Counter32,
   gs2328DHCPSnoopingTxACK                  Counter32,
   gs2328DHCPSnoopingTxNAK                  Counter32,
   gs2328DHCPSnoopingTxRelease              Counter32,
   gs2328DHCPSnoopingTxInform               Counter32,
   gs2328DHCPSnoopingTxLeaseQuery           Counter32,
   gs2328DHCPSnoopingTxLeaseUnassigned      Counter32,
   gs2328DHCPSnoopingTxLeaseUnknown         Counter32,
   gs2328DHCPSnoopingTxLeaseActive          Counter32
}

gs2328DHCPSnoopingStatisticsPort OBJECT-TYPE
   SYNTAX      Integer32(1..4095)
   MAX-ACCESS  not-accessible
   STATUS      current
   DESCRIPTION
       " "
   ::= { gs2328DHCPSnoopingStatisticsEntry 1 }

gs2328DHCPSnoopingStatisticsClear OBJECT-TYPE
   SYNTAX      INTEGER { none(0), clear(1) }
   MAX-ACCESS  read-write
   STATUS      current
   DESCRIPTION
       "default: 0
       0: none
       1: clear"
   ::= { gs2328DHCPSnoopingStatisticsEntry 2 }
   
gs2328DHCPSnoopingRxDiscover OBJECT-TYPE
   SYNTAX      Counter32
   MAX-ACCESS  read-only
   STATUS      current
   DESCRIPTION
       " "
   ::= { gs2328DHCPSnoopingStatisticsEntry 3 }

gs2328DHCPSnoopingRxOffer OBJECT-TYPE
   SYNTAX      Counter32
   MAX-ACCESS  read-only
   STATUS      current
   DESCRIPTION
       " "
   ::= { gs2328DHCPSnoopingStatisticsEntry 4 }

gs2328DHCPSnoopingRxRequest OBJECT-TYPE
   SYNTAX      Counter32
   MAX-ACCESS  read-only
   STATUS      current
   DESCRIPTION
       " "
   ::= { gs2328DHCPSnoopingStatisticsEntry 5 }

gs2328DHCPSnoopingRxDecline OBJECT-TYPE
   SYNTAX      Counter32
   MAX-ACCESS  read-only
   STATUS      current
   DESCRIPTION
       " "
   ::= { gs2328DHCPSnoopingStatisticsEntry 6 }

gs2328DHCPSnoopingRxACK OBJECT-TYPE
   SYNTAX      Counter32
   MAX-ACCESS  read-only
   STATUS      current
   DESCRIPTION
       " "
   ::= { gs2328DHCPSnoopingStatisticsEntry 7 }

gs2328DHCPSnoopingRxNAK OBJECT-TYPE
   SYNTAX      Counter32
   MAX-ACCESS  read-only
   STATUS      current
   DESCRIPTION
       " "
   ::= { gs2328DHCPSnoopingStatisticsEntry 8 }   

gs2328DHCPSnoopingRxRelease OBJECT-TYPE
   SYNTAX      Counter32
   MAX-ACCESS  read-only
   STATUS      current
   DESCRIPTION
       " "
   ::= { gs2328DHCPSnoopingStatisticsEntry 9 }

gs2328DHCPSnoopingRxInform OBJECT-TYPE
   SYNTAX      Counter32
   MAX-ACCESS  read-only
   STATUS      current
   DESCRIPTION
       " "
   ::= { gs2328DHCPSnoopingStatisticsEntry 10 }

gs2328DHCPSnoopingRxLeaseQuery OBJECT-TYPE
   SYNTAX      Counter32
   MAX-ACCESS  read-only
   STATUS      current
   DESCRIPTION
       " "
   ::= { gs2328DHCPSnoopingStatisticsEntry 11 }

gs2328DHCPSnoopingRxLeaseUnassigned OBJECT-TYPE
   SYNTAX      Counter32
   MAX-ACCESS  read-only
   STATUS      current
   DESCRIPTION
       " "
   ::= { gs2328DHCPSnoopingStatisticsEntry 12 }

gs2328DHCPSnoopingRxLeaseUnknown OBJECT-TYPE
   SYNTAX      Counter32
   MAX-ACCESS  read-only
   STATUS      current
   DESCRIPTION
       " "
   ::= { gs2328DHCPSnoopingStatisticsEntry 13 }

gs2328DHCPSnoopingRxLeaseActive OBJECT-TYPE
   SYNTAX      Counter32
   MAX-ACCESS  read-only
   STATUS      current
   DESCRIPTION
       " "
   ::= { gs2328DHCPSnoopingStatisticsEntry 14 }

gs2328DHCPSnoopingTxDiscover OBJECT-TYPE
   SYNTAX      Counter32
   MAX-ACCESS  read-only
   STATUS      current
   DESCRIPTION
       " "
   ::= { gs2328DHCPSnoopingStatisticsEntry 15 }

gs2328DHCPSnoopingTxOffer OBJECT-TYPE
   SYNTAX      Counter32
   MAX-ACCESS  read-only
   STATUS      current
   DESCRIPTION
       " "
   ::= { gs2328DHCPSnoopingStatisticsEntry 16 }

gs2328DHCPSnoopingTxRequest OBJECT-TYPE
   SYNTAX      Counter32
   MAX-ACCESS  read-only
   STATUS      current
   DESCRIPTION
       " "
   ::= { gs2328DHCPSnoopingStatisticsEntry 17 }

gs2328DHCPSnoopingTxDecline OBJECT-TYPE
   SYNTAX      Counter32
   MAX-ACCESS  read-only
   STATUS      current
   DESCRIPTION
       " "
   ::= { gs2328DHCPSnoopingStatisticsEntry 18 }

gs2328DHCPSnoopingTxACK OBJECT-TYPE
   SYNTAX      Counter32
   MAX-ACCESS  read-only
   STATUS      current
   DESCRIPTION
       " "
   ::= { gs2328DHCPSnoopingStatisticsEntry 19 }

gs2328DHCPSnoopingTxNAK OBJECT-TYPE
   SYNTAX      Counter32
   MAX-ACCESS  read-only
   STATUS      current
   DESCRIPTION
       " "
   ::= { gs2328DHCPSnoopingStatisticsEntry 20 }   

gs2328DHCPSnoopingTxRelease OBJECT-TYPE
   SYNTAX      Counter32
   MAX-ACCESS  read-only
   STATUS      current
   DESCRIPTION
       " "
   ::= { gs2328DHCPSnoopingStatisticsEntry 21 }

gs2328DHCPSnoopingTxInform OBJECT-TYPE
   SYNTAX      Counter32
   MAX-ACCESS  read-only
   STATUS      current
   DESCRIPTION
       " "
   ::= { gs2328DHCPSnoopingStatisticsEntry 22 }

gs2328DHCPSnoopingTxLeaseQuery OBJECT-TYPE
   SYNTAX      Counter32
   MAX-ACCESS  read-only
   STATUS      current
   DESCRIPTION
       " "
   ::= { gs2328DHCPSnoopingStatisticsEntry 23 }

gs2328DHCPSnoopingTxLeaseUnassigned OBJECT-TYPE
   SYNTAX      Counter32
   MAX-ACCESS  read-only
   STATUS      current
   DESCRIPTION
       " "
   ::= { gs2328DHCPSnoopingStatisticsEntry 24 }

gs2328DHCPSnoopingTxLeaseUnknown OBJECT-TYPE
   SYNTAX      Counter32
   MAX-ACCESS  read-only
   STATUS      current
   DESCRIPTION
       " "
   ::= { gs2328DHCPSnoopingStatisticsEntry 25 }

gs2328DHCPSnoopingTxLeaseActive OBJECT-TYPE
   SYNTAX      Counter32
   MAX-ACCESS  read-only
   STATUS      current
   DESCRIPTION
       " "
   ::= { gs2328DHCPSnoopingStatisticsEntry 26 }


gs2328DHCPRelay                                             OBJECT IDENTIFIER ::= { gs2328Security 4 }

gs2328DHCPRelayConfiguration                                         OBJECT IDENTIFIER ::= { gs2328DHCPRelay 1 }

gs2328DHCPRelayMode OBJECT-TYPE
   SYNTAX      INTEGER { disable(0), enable(1) }
   MAX-ACCESS  read-write
   STATUS      current
   DESCRIPTION
       "default: 0
       0: disable
       1: enable 
       We need at least one server"
   ::= { gs2328DHCPRelayConfiguration 1 }

gs2328DHCPRelayServer OBJECT-TYPE
   SYNTAX      IpAddress
   MAX-ACCESS  read-write
   STATUS      current
   DESCRIPTION
       " "
   ::= { gs2328DHCPRelayConfiguration 2 }

gs2328DHCPRelayInformationMode OBJECT-TYPE
   SYNTAX      INTEGER { disable(0), enable(1) }
   MAX-ACCESS  read-write
   STATUS      current
   DESCRIPTION
       "default: 0
       0: disable
       1: enable "
   ::= { gs2328DHCPRelayConfiguration 3 }

gs2328DHCPRelayInformationPolicy OBJECT-TYPE
   SYNTAX      INTEGER { replace(0), keep(1), drop(2) }
   MAX-ACCESS  read-write
   STATUS      current
   DESCRIPTION
       "default: 0
       0: replace
       1: keep
       2: drop "
   ::= { gs2328DHCPRelayConfiguration 4 }

gs2328DHCPRelayInformationCustom OBJECT-TYPE
   SYNTAX      DisplayString(SIZE(0..32))
   MAX-ACCESS  read-write
   STATUS      current
   DESCRIPTION
       "DHCP Option 82 Circuit ID custom information"
   ::= { gs2328DHCPRelayConfiguration 1500 }

gs2328DHCPRelayConfigurationGateways                                          OBJECT IDENTIFIER ::= { gs2328DHCPRelayConfiguration 5 }

gs2328DHCPRelayConfigurationGatewaysCreate OBJECT-TYPE
   SYNTAX       INTEGER { none(0), create(1) }
   MAX-ACCESS   read-write
   STATUS       current
   DESCRIPTION
       "default: 0
        0 : None  (read only)
        1 : Create entry"
   ::= { gs2328DHCPRelayConfigurationGateways 1 }

gs2328DHCPRelayConfigurationGatewaysTable OBJECT-TYPE
   SYNTAX      SEQUENCE OF Gs2328DHCPRelayConfigurationGatewaysEntry
   MAX-ACCESS  not-accessible
   STATUS      current
   DESCRIPTION
       " Create DHCP Relay Gateway IP address entry."
   ::= { gs2328DHCPRelayConfigurationGateways 2 }

gs2328DHCPRelayConfigurationGatewaysEntry OBJECT-TYPE
   SYNTAX      Gs2328DHCPRelayConfigurationGatewaysEntry
   MAX-ACCESS  not-accessible
   STATUS      current
   DESCRIPTION
       ""
   INDEX    { gs2328DHCPRelayConfigurationGatewaysIndex  }
   ::= { gs2328DHCPRelayConfigurationGatewaysTable 1 }

Gs2328DHCPRelayConfigurationGatewaysEntry ::= SEQUENCE {
   gs2328DHCPRelayConfigurationGatewaysIndex           Integer32,
   gs2328DHCPRelayConfigurationGatewaysVLANId          Integer32,
   gs2328DHCPRelayConfigurationGatewaysIP              IpAddress,
   gs2328DHCPRelayConfigurationGatewaysRowStatus       INTEGER
}

gs2328DHCPRelayConfigurationGatewaysIndex OBJECT-TYPE
   SYNTAX      Integer32(1..6)
   MAX-ACCESS  not-accessible
   STATUS      current
   DESCRIPTION
       " "
   ::= { gs2328DHCPRelayConfigurationGatewaysEntry 1 }

gs2328DHCPRelayConfigurationGatewaysVLANId OBJECT-TYPE
   SYNTAX      Integer32(1..4094)
   MAX-ACCESS  read-write
   STATUS      current
   DESCRIPTION
       " VLAN ID "
   ::= { gs2328DHCPRelayConfigurationGatewaysEntry 2 }

gs2328DHCPRelayConfigurationGatewaysIP OBJECT-TYPE
   SYNTAX      IpAddress
   MAX-ACCESS  read-write
   STATUS      current
   DESCRIPTION
       "DHCP GIADDR address."
   ::= { gs2328DHCPRelayConfigurationGatewaysEntry 3 }
   
gs2328DHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2328DHCPRelayConfigurationGatewaysEntry 4 }

gs2328DHCPRelayStatistics                                   OBJECT IDENTIFIER ::= { gs2328DHCPRelay 2 }

gs2328DHCPRelayServerStatistics                                   OBJECT IDENTIFIER ::= { gs2328DHCPRelayStatistics 1 }

gs2328ServerStatTransmitToServer OBJECT-TYPE
   SYNTAX      Counter32
   MAX-ACCESS  read-only
   STATUS      current
   DESCRIPTION
       " "
   ::= { gs2328DHCPRelayServerStatistics 1 }

gs2328ServerStatTransmitError OBJECT-TYPE
   SYNTAX      Counter32
   MAX-ACCESS  read-only
   STATUS      current
   DESCRIPTION
       " "
   ::= { gs2328DHCPRelayServerStatistics 2 }

gs2328ServerStatReceiveFromServer OBJECT-TYPE
   SYNTAX      Counter32
   MAX-ACCESS  read-only
   STATUS      current
   DESCRIPTION
       " "
   ::= { gs2328DHCPRelayServerStatistics 3 }

gs2328ServerStatReceiveMissingAgentOption OBJECT-TYPE
   SYNTAX      Counter32
   MAX-ACCESS  read-only
   STATUS      current
   DESCRIPTION
       " "
   ::= { gs2328DHCPRelayServerStatistics 4 }

gs2328ServerStatReceiveMissingCircuitID OBJECT-TYPE
   SYNTAX      Counter32
   MAX-ACCESS  read-only
   STATUS      current
   DESCRIPTION
       " "
   ::= { gs2328DHCPRelayServerStatistics 5 }

gs2328ServerStatReceiveMissingRemoteID OBJECT-TYPE
   SYNTAX      Counter32
   MAX-ACCESS  read-only
   STATUS      current
   DESCRIPTION
       " "
   ::= { gs2328DHCPRelayServerStatistics 6 }

gs2328ServerStatReceiveBadCircuitID OBJECT-TYPE
   SYNTAX      Counter32
   MAX-ACCESS  read-only
   STATUS      current
   DESCRIPTION
       " "
   ::= { gs2328DHCPRelayServerStatistics 7 }

gs2328ServerStatReceiveBadRemoteID OBJECT-TYPE
   SYNTAX      Counter32
   MAX-ACCESS  read-only
   STATUS      current
   DESCRIPTION
       " "
   ::= { gs2328DHCPRelayServerStatistics 8 }

gs2328DHCPRelayClientStatistics                                   OBJECT IDENTIFIER ::= { gs2328DHCPRelayStatistics 2 }

gs2328ClientStatTransmitToClient OBJECT-TYPE
   SYNTAX      Counter32
   MAX-ACCESS  read-only
   STATUS      current
   DESCRIPTION
       " "
   ::= { gs2328DHCPRelayClientStatistics 1 }

gs2328ClientStatTransmitError OBJECT-TYPE
   SYNTAX      Counter32
   MAX-ACCESS  read-only
   STATUS      current
   DESCRIPTION
       " "
   ::= { gs2328DHCPRelayClientStatistics 2 }

gs2328ClientStatReceivefromClient OBJECT-TYPE
   SYNTAX      Counter32
   MAX-ACCESS  read-only
   STATUS      current
   DESCRIPTION
       " "
   ::= { gs2328DHCPRelayClientStatistics 3 }

gs2328ClientStatReceiveAgentOption OBJECT-TYPE
   SYNTAX      Counter32
   MAX-ACCESS  read-only
   STATUS      current
   DESCRIPTION
       " "
   ::= { gs2328DHCPRelayClientStatistics 4 }

gs2328ClientStatReplaceAgentOption OBJECT-TYPE
   SYNTAX      Counter32
   MAX-ACCESS  read-only
   STATUS      current
   DESCRIPTION
       " "
   ::= { gs2328DHCPRelayClientStatistics 5 }

gs2328ClientStatKeepAgentOption OBJECT-TYPE
   SYNTAX      Counter32
   MAX-ACCESS  read-only
   STATUS      current
   DESCRIPTION
       " "
   ::= { gs2328DHCPRelayClientStatistics 6 }

gs2328ClientStatDropAgentOption OBJECT-TYPE
   SYNTAX      Counter32
   MAX-ACCESS  read-only
   STATUS      current
   DESCRIPTION
       " "
   ::= { gs2328DHCPRelayClientStatistics 7 }

gs2328PortSecurity                                          OBJECT IDENTIFIER ::= { gs2328Security 5 }

gs2328PortSecLimitCtrl                                      OBJECT IDENTIFIER ::= { gs2328PortSecurity 1 }

gs2328PortSecLimitCtrlSystemConf                                      OBJECT IDENTIFIER ::= { gs2328PortSecLimitCtrl 1 }

gs2328PortSecurityMode OBJECT-TYPE
   SYNTAX      INTEGER { disable(0), enable(1) }
   MAX-ACCESS  read-write
   STATUS      current
   DESCRIPTION
       "default: 0
       0: disable
       1: enable "
   ::= { gs2328PortSecLimitCtrlSystemConf 1 }

gs2328PortSecurityAging OBJECT-TYPE
   SYNTAX      INTEGER { disable(0), enable(1) }
   MAX-ACCESS  read-write
   STATUS      current
   DESCRIPTION
       "default: 0
       0: disable
       1: enable "
   ::= { gs2328PortSecLimitCtrlSystemConf 2 }

gs2328PortSecurityAgingPeriod OBJECT-TYPE
   SYNTAX      INTEGER(10..10000000)
   MAX-ACCESS  read-write
   STATUS      current
   DESCRIPTION
       "default: 3600, range: 10-10000000 "
   ::= { gs2328PortSecLimitCtrlSystemConf 3 }

gs2328PortSecLimitCtrlTable OBJECT-TYPE
   SYNTAX      SEQUENCE OF GS2328PortSecLimitCtrlEntry
   MAX-ACCESS  not-accessible
   STATUS      current
   DESCRIPTION
       " "
   ::= { gs2328PortSecLimitCtrl 2 }

gs2328PortSecLimitCtrlEntry OBJECT-TYPE
   SYNTAX      GS2328PortSecLimitCtrlEntry
   MAX-ACCESS  not-accessible
   STATUS      current
   DESCRIPTION
       ""
   INDEX    { gs2328PortSecLimitCtrlPort  }
   ::= { gs2328PortSecLimitCtrlTable 1 }

GS2328PortSecLimitCtrlEntry ::= SEQUENCE {
   gs2328PortSecLimitCtrlPort           Integer32,
   gs2328PortSecLimitCtrlPortMode       INTEGER,
   gs2328PortSecLimitCtrlPortLimit      Integer32,
   gs2328PortSecLimitCtrlPortAction     INTEGER,
   gs2328PortSecLimitCtrlPortState      DisplayString,
   gs2328PortSecLimitCtrlPortReOpen     INTEGER
}

gs2328PortSecLimitCtrlPort OBJECT-TYPE
   SYNTAX      Integer32(1..4095)
   MAX-ACCESS  not-accessible
   STATUS      current
   DESCRIPTION
       " "
   ::= { gs2328PortSecLimitCtrlEntry 1 }

gs2328PortSecLimitCtrlPortMode OBJECT-TYPE
   SYNTAX      INTEGER { disable(0), enable(1) }
   MAX-ACCESS  read-write
   STATUS      current
   DESCRIPTION
       "default: 0
       0: disable
       1: enable"
   ::= { gs2328PortSecLimitCtrlEntry 2 }

gs2328PortSecLimitCtrlPortLimit OBJECT-TYPE
   SYNTAX      Integer32(1..1024)
   MAX-ACCESS  read-write
   STATUS      current
   DESCRIPTION
       "default: 4, range: 1-1024"
   ::= { gs2328PortSecLimitCtrlEntry 3 }

gs2328PortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2328PortSecLimitCtrlEntry 4 }

gs2328PortSecLimitCtrlPortState OBJECT-TYPE
   SYNTAX      DisplayString
   MAX-ACCESS  read-only
   STATUS      current
   DESCRIPTION
       ""
   ::= { gs2328PortSecLimitCtrlEntry 5 }

gs2328PortSecLimitCtrlPortReOpen OBJECT-TYPE
   SYNTAX      INTEGER { none(0), reopen(1) }
   MAX-ACCESS  read-write
   STATUS      current
   DESCRIPTION
       "default: 0
       0: none
       1: reopen"
   ::= { gs2328PortSecLimitCtrlEntry 6 }

gs2328PortSecSwitchStatusTable OBJECT-TYPE
   SYNTAX      SEQUENCE OF GS2328PortSecSwitchStatusEntry
   MAX-ACCESS  not-accessible
   STATUS      current
   DESCRIPTION
       " "
   ::= { gs2328PortSecurity 2 }

gs2328PortSecSwitchStatusEntry OBJECT-TYPE
   SYNTAX      GS2328PortSecSwitchStatusEntry
   MAX-ACCESS  not-accessible
   STATUS      current
   DESCRIPTION
       ""
   INDEX    { gs2328PortSecSwitchStatusPort  }
   ::= { gs2328PortSecSwitchStatusTable 1 }

GS2328PortSecSwitchStatusEntry ::= SEQUENCE {
   gs2328PortSecSwitchStatusPort                Integer32,
   gs2328PortSecSwitchStatusUsers               DisplayString,
   gs2328PortSecSwitchStatusState               DisplayString,
   gs2328PortSecSwitchStatusMACCountCurrent     Integer32,
   gs2328PortSecSwitchStatusMACCountLimit       Integer32
}

gs2328PortSecSwitchStatusPort OBJECT-TYPE
   SYNTAX      Integer32(1..4095)
   MAX-ACCESS  not-accessible
   STATUS      current
   DESCRIPTION
       " "
   ::= { gs2328PortSecSwitchStatusEntry 1 }

gs2328PortSecSwitchStatusUsers OBJECT-TYPE
   SYNTAX      DisplayString
   MAX-ACCESS  read-only
   STATUS      current
   DESCRIPTION
       " Users Abbr: L = Limit Control, 8 = 802.1X, D = DHCP Snooping, V = Voice VLAN, 
         '-' means that the corresponding user module is not enabled. "
   ::= { gs2328PortSecSwitchStatusEntry 2 }

gs2328PortSecSwitchStatusState OBJECT-TYPE
   SYNTAX      DisplayString
   MAX-ACCESS  read-only
   STATUS      current
   DESCRIPTION
       " Shows the current state of the port : Disabled, Ready, Limit Reached, Shutdown. "
   ::= { gs2328PortSecSwitchStatusEntry 3 }

gs2328PortSecSwitchStatusMACCountCurrent OBJECT-TYPE
   SYNTAX      Integer32(1..4095)
   MAX-ACCESS  read-only
   STATUS      current
   DESCRIPTION
       ""
   ::= { gs2328PortSecSwitchStatusEntry 4 }

gs2328PortSecSwitchStatusMACCountLimit OBJECT-TYPE
   SYNTAX      Integer32(1..4095)
   MAX-ACCESS  read-only
   STATUS      current
   DESCRIPTION
       ""
   ::= { gs2328PortSecSwitchStatusEntry 5 }

gs2328PortSecPortStatus                                      OBJECT IDENTIFIER ::= { gs2328PortSecurity 3 }

gs2328PortSecPortStatusPort OBJECT-TYPE
   SYNTAX       Integer32(1..4095)
   MAX-ACCESS   read-write
   STATUS       current
   DESCRIPTION
       "port number
        default: 1
        range: 1 - port number."
   ::= { gs2328PortSecPortStatus 1 }

gs2328PortSecPortStatusTable OBJECT-TYPE
   SYNTAX      SEQUENCE OF GS2328PortSecPortStatusEntry
   MAX-ACCESS  not-accessible
   STATUS      current
   DESCRIPTION
      " "
   ::= { gs2328PortSecPortStatus 2 }
       
gs2328PortSecPortStatusEntry OBJECT-TYPE
   SYNTAX      GS2328PortSecPortStatusEntry
   MAX-ACCESS  not-accessible
   STATUS      current
   DESCRIPTION
       ""
   INDEX    { gs2328PortSecPortStatusIndex  }
   ::= { gs2328PortSecPortStatusTable 1 }       

GS2328PortSecPortStatusEntry ::= SEQUENCE {
   gs2328PortSecPortStatusIndex              Integer32,
   gs2328PortSecPortStatusMACAddress         MacAddress,
   gs2328PortSecPortStatusVLANId             Integer32,
   gs2328PortSecPortStatusState              DisplayString,
   gs2328PortSecPortStatusTimeOfAddition     DisplayString,
   gs2328PortSecPortStatusAgeAndHold         DisplayString
}

gs2328PortSecPortStatusIndex OBJECT-TYPE
   SYNTAX      Integer32(1..4095)
   MAX-ACCESS  not-accessible
   STATUS      current
   DESCRIPTION
       " "
   ::= { gs2328PortSecPortStatusEntry 1 }

gs2328PortSecPortStatusMACAddress OBJECT-TYPE
   SYNTAX      MacAddress
   MAX-ACCESS  read-only
   STATUS      current
   DESCRIPTION
       " "
   ::= { gs2328PortSecPortStatusEntry 2 }

gs2328PortSecPortStatusVLANId OBJECT-TYPE
   SYNTAX      Integer32(1..4094)
   MAX-ACCESS  read-only
   STATUS      current
   DESCRIPTION
       " "
   ::= { gs2328PortSecPortStatusEntry 3 }

gs2328PortSecPortStatusState OBJECT-TYPE
   SYNTAX      DisplayString
   MAX-ACCESS  read-only
   STATUS      current
   DESCRIPTION
       "Blocked / Forwarding "
   ::= { gs2328PortSecPortStatusEntry 4 }

gs2328PortSecPortStatusTimeOfAddition OBJECT-TYPE
   SYNTAX      DisplayString
   MAX-ACCESS  read-only
   STATUS      current
   DESCRIPTION
       " "
   ::= { gs2328PortSecPortStatusEntry 5 }

gs2328PortSecPortStatusAgeAndHold OBJECT-TYPE
   SYNTAX      DisplayString
   MAX-ACCESS  read-only
   STATUS      current
   DESCRIPTION
       " "
   ::= { gs2328PortSecPortStatusEntry 6 }       
       

gs2328AccessManagement                                      OBJECT IDENTIFIER ::= { gs2328Security 6 }

gs2328AccessMgtConf                                         OBJECT IDENTIFIER ::= { gs2328AccessManagement 1 }

gs2328AccessMgtConfMode OBJECT-TYPE
   SYNTAX      INTEGER { disable(0), enable(1) }
   MAX-ACCESS  read-write
   STATUS      current
   DESCRIPTION
       "default: 0
       0: disable
       1: enable "
   ::= { gs2328AccessMgtConf 1 }

gs2328AccessMgtConfCreate OBJECT-TYPE
   SYNTAX      INTEGER { none(0), create(1) }
   MAX-ACCESS  read-write
   STATUS      current
   DESCRIPTION
       "default: 0
       0: none
       1: create "
   ::= { gs2328AccessMgtConf 2 }

gs2328AccessMgtConfTable OBJECT-TYPE
   SYNTAX      SEQUENCE OF GS2328AccessMgtConfEntry
   MAX-ACCESS  not-accessible
   STATUS      current
   DESCRIPTION
       " "
   ::= { gs2328AccessMgtConf 3 }

gs2328AccessMgtConfEntry OBJECT-TYPE
   SYNTAX      GS2328AccessMgtConfEntry
   MAX-ACCESS  not-accessible
   STATUS      current
   DESCRIPTION
       ""
   INDEX    { gs2328AccessMgtIndex  }
   ::= { gs2328AccessMgtConfTable 1 }
   
GS2328AccessMgtConfEntry ::= SEQUENCE {
   gs2328AccessMgtIndex             Integer32,
   gs2328AccessMgtAddresstype       INTEGER,
   gs2328AccessMgtStartIpAddress    DisplayString,
   gs2328AccessMgtEndIpAddress      DisplayString,
   gs2328AccessMgtHttpHttps         INTEGER,
   gs2328AccessMgtSNMP              INTEGER,
   gs2328AccessMgtTelnetSSH         INTEGER,
   gs2328AccessMgtRowStatus         INTEGER
}

gs2328AccessMgtIndex OBJECT-TYPE
   SYNTAX      Integer32(1..16)
   MAX-ACCESS  read-write
   STATUS      current
   DESCRIPTION
       "Set Access Management config index
        range : 1-16."
   ::= { gs2328AccessMgtConfEntry 1 }

gs2328AccessMgtAddresstype OBJECT-TYPE
   SYNTAX      INTEGER { ipv4(0), ipv6(1) }
   MAX-ACCESS  read-write
   STATUS      current
   DESCRIPTION
       "0: ipv4
        1: ipv6 "
   ::= { gs2328AccessMgtConfEntry 2 }
   
gs2328AccessMgtStartIpAddress OBJECT-TYPE
   SYNTAX      DisplayString
   MAX-ACCESS  read-write
   STATUS      current
   DESCRIPTION
       " Start IP address. 
         IP address doesn't allowed all zero or all 'ff'H."
   ::= { gs2328AccessMgtConfEntry 3 }
   
gs2328AccessMgtEndIpAddress OBJECT-TYPE
   SYNTAX      DisplayString
   MAX-ACCESS  read-write
   STATUS      current
   DESCRIPTION
       " End IP address. 
         IP address doesn't allowed all zero or all 'ff'H.
         End ip address is not less than start ip address."
   ::= { gs2328AccessMgtConfEntry 4 }

gs2328AccessMgtHttpHttps OBJECT-TYPE
   SYNTAX      INTEGER { disable(0), enable(1) }
   MAX-ACCESS  read-write
   STATUS      current
   DESCRIPTION
       "default: 0
       0: disable
       1: enable "
   ::= { gs2328AccessMgtConfEntry 5 }

gs2328AccessMgtSNMP OBJECT-TYPE
   SYNTAX      INTEGER { disable(0), enable(1) }
   MAX-ACCESS  read-write
   STATUS      current
   DESCRIPTION
       "default: 0
       0: disable
       1: enable "
   ::= { gs2328AccessMgtConfEntry 6 }

gs2328AccessMgtTelnetSSH OBJECT-TYPE
   SYNTAX      INTEGER { disable(0), enable(1) }
   MAX-ACCESS  read-write
   STATUS      current
   DESCRIPTION
       "default: 0
       0: disable
       1: enable "
   ::= { gs2328AccessMgtConfEntry 7 }

gs2328AccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2328AccessMgtConfEntry 8 }

gs2328AccessMgtStatistics                                   OBJECT IDENTIFIER ::= { gs2328AccessManagement 2 }

gs2328HttpReceivedPkts OBJECT-TYPE
   SYNTAX      Counter32
   MAX-ACCESS  read-only
   STATUS      current
   DESCRIPTION
       " "
   ::= { gs2328AccessMgtStatistics 1 }

gs2328HttpAllowedPkts OBJECT-TYPE
   SYNTAX      Counter32
   MAX-ACCESS  read-only
   STATUS      current
   DESCRIPTION
       " "
   ::= { gs2328AccessMgtStatistics 2 }

gs2328HttpDiscardedPkts OBJECT-TYPE
   SYNTAX      Counter32
   MAX-ACCESS  read-only
   STATUS      current
   DESCRIPTION
       " "
   ::= { gs2328AccessMgtStatistics 3 }

gs2328HttpsReceivedPkts OBJECT-TYPE
   SYNTAX      Counter32
   MAX-ACCESS  read-only
   STATUS      current
   DESCRIPTION
       " "
   ::= { gs2328AccessMgtStatistics 4 }

gs2328HttpsAllowedPkts OBJECT-TYPE
   SYNTAX      Counter32
   MAX-ACCESS  read-only
   STATUS      current
   DESCRIPTION
       " "
   ::= { gs2328AccessMgtStatistics 5 }

gs2328HttpsDiscardedPkts OBJECT-TYPE
   SYNTAX      Counter32
   MAX-ACCESS  read-only
   STATUS      current
   DESCRIPTION
       " "
   ::= { gs2328AccessMgtStatistics 6 }

gs2328SnmpReceivedPkts OBJECT-TYPE
   SYNTAX      Counter32
   MAX-ACCESS  read-only
   STATUS      current
   DESCRIPTION
       " "
   ::= { gs2328AccessMgtStatistics 7 }

gs2328SnmpAllowedPkts OBJECT-TYPE
   SYNTAX      Counter32
   MAX-ACCESS  read-only
   STATUS      current
   DESCRIPTION
       " "
   ::= { gs2328AccessMgtStatistics 8 }

gs2328SnmpDiscardedPkts OBJECT-TYPE
   SYNTAX      Counter32
   MAX-ACCESS  read-only
   STATUS      current
   DESCRIPTION
       " "
   ::= { gs2328AccessMgtStatistics 9 }

gs2328TelnetReceivedPkts OBJECT-TYPE
   SYNTAX      Counter32
   MAX-ACCESS  read-only
   STATUS      current
   DESCRIPTION
       " "
   ::= { gs2328AccessMgtStatistics 10 }

gs2328TelnetAllowedPkts OBJECT-TYPE
   SYNTAX      Counter32
   MAX-ACCESS  read-only
   STATUS      current
   DESCRIPTION
       " "
   ::= { gs2328AccessMgtStatistics 11 }

gs2328TelnetDiscardedPkts OBJECT-TYPE
   SYNTAX      Counter32
   MAX-ACCESS  read-only
   STATUS      current
   DESCRIPTION
       " "
   ::= { gs2328AccessMgtStatistics 12 }

gs2328SSHReceivedPkts OBJECT-TYPE
   SYNTAX      Counter32
   MAX-ACCESS  read-only
   STATUS      current
   DESCRIPTION
       " "
   ::= { gs2328AccessMgtStatistics 13 }

gs2328SSHAllowedPkts OBJECT-TYPE
   SYNTAX      Counter32
   MAX-ACCESS  read-only
   STATUS      current
   DESCRIPTION
       " "
   ::= { gs2328AccessMgtStatistics 14 }

gs2328SSHDiscardedPkts OBJECT-TYPE
   SYNTAX      Counter32
   MAX-ACCESS  read-only
   STATUS      current
   DESCRIPTION
       " "
   ::= { gs2328AccessMgtStatistics 15 }

gs2328AccessMgtStatisticsClearAll OBJECT-TYPE
   SYNTAX      INTEGER { none(0), clear(1) }
   MAX-ACCESS  read-write
   STATUS      current
   DESCRIPTION
       "0: none
        1: clear"
   ::= { gs2328AccessMgtStatistics 16 }

gs2328SSH                                                   OBJECT IDENTIFIER ::= { gs2328Security 7 }

gs2328SSHMode OBJECT-TYPE
   SYNTAX      INTEGER { disable(0), enable(1) }
   MAX-ACCESS  read-write
   STATUS      current
   DESCRIPTION
       "default: 1
        0: disable
        1: enable"
   ::= { gs2328SSH 1 }

gs2328HTTPS                                                 OBJECT IDENTIFIER ::= { gs2328Security 8 }

gs2328HTTPSMode OBJECT-TYPE
   SYNTAX      INTEGER { disable(0), enable(1) }
   MAX-ACCESS  read-write
   STATUS      current
   DESCRIPTION
       "default: 1
        0: disable
        1: enable"
   ::= { gs2328HTTPS 1 }

gs2328HTTPSAutoRedirect OBJECT-TYPE
   SYNTAX      INTEGER { disable(0), enable(1) }
   MAX-ACCESS  read-write
   STATUS      current
   DESCRIPTION
       "default: 0
        0: disable
        1: enable"
   ::= { gs2328HTTPS 2 }

gs2328HTTPSCertRenew OBJECT-TYPE
   SYNTAX      INTEGER { doNothing(0), renew(1) }
   MAX-ACCESS  read-write
   STATUS      current
   DESCRIPTION
       "default: 0 ,
        0: doNothing
        1: renew"
   ::= { gs2328HTTPS 3 }

gs2328HTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2328HTTPS 4 }

gs2328HTTPMode OBJECT-TYPE
   SYNTAX      INTEGER { disable(0), enable(1) }
   MAX-ACCESS  read-write
   STATUS      current
   DESCRIPTION
       "default: 1
        0: disable
        1: enable"
   ::= { gs2328HTTPS 5 }

gs2328AuthMethod                                            OBJECT IDENTIFIER ::= { gs2328Security 9 }

gs2328ConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328AuthMethod 1 }

gs2328ConsoleFallback OBJECT-TYPE
   SYNTAX      INTEGER { disable(0), enable(1) }
   MAX-ACCESS  read-write
   STATUS      current
   DESCRIPTION
       "default: 0
        0:disable
        1:enable"
   ::= { gs2328AuthMethod 2 }

gs2328TelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328AuthMethod 3 }

gs2328TelnetFallback OBJECT-TYPE
   SYNTAX      INTEGER { disable(0), enable(1) }
   MAX-ACCESS  read-write
   STATUS      current
   DESCRIPTION
       "default: 0
        0:disable
        1:enable"
   ::= { gs2328AuthMethod 4 }

gs2328SshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328AuthMethod 5 }

gs2328SshFallback OBJECT-TYPE
   SYNTAX      INTEGER { disable(0), enable(1) }
   MAX-ACCESS  read-write
   STATUS      current
   DESCRIPTION
       "default: 0
        0:disable
        1:enable"
   ::= { gs2328AuthMethod 6 }

gs2328TftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328AuthMethod 9 }

gs2328TftpFallback OBJECT-TYPE
   SYNTAX      INTEGER { disable(0), enable(1) }
   MAX-ACCESS  read-write
   STATUS      current
   DESCRIPTION
       "default: 0
        0:disable
        1:enable"
   ::= { gs2328AuthMethod 10 }
   
gs2328LoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2328AuthMethod 11 }

gs2328LockMinutes OBJECT-TYPE
   SYNTAX      Integer32(1..99)
   MAX-ACCESS  read-write
   STATUS      current
   DESCRIPTION
       "Lock time to login failures trigger.
        range: 1-99.
        default: 5."
   ::= { gs2328AuthMethod 12 }

gs2328HttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328AuthMethod 13 }

gs2328HttpFallback OBJECT-TYPE
   SYNTAX      INTEGER { disable(0), enable(1) }
   MAX-ACCESS  read-write
   STATUS      current
   DESCRIPTION
       "default: 0
        0:disable
        1:enable"
   ::= { gs2328AuthMethod 14 }

gs2328HttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328AuthMethod 15 }

gs2328HttpsFallback OBJECT-TYPE
   SYNTAX      INTEGER { disable(0), enable(1) }
   MAX-ACCESS  read-write
   STATUS      current
   DESCRIPTION
       "default: 0
        0:disable
        1:enable"
   ::= { gs2328AuthMethod 16 }


gs2328AAA                                              OBJECT IDENTIFIER ::= { gs2328Security 10 }

gs2328AAACommonServer                                  OBJECT IDENTIFIER ::= { gs2328AAA 1 }

gs2328AAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2328AAACommonServer 1 }

gs2328AAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2328AAACommonServer 2 }

gs2328AAATACACSPlusAuthAndAccounting                  OBJECT IDENTIFIER ::= { gs2328AAA 2 }

gs2328AAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2328AAATACACSPlusAuthAndAccounting 1 }

gs2328AAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2328AAATACACSPlusAuthAndAccounting 2 }

gs2328AAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2328AAATACACSPlusAuthAndAccounting 3 }

gs2328RADIUSAuthenticationServerTable OBJECT-TYPE
   SYNTAX      SEQUENCE OF Gs2328RADIUSAuthenticationServerEntry
   MAX-ACCESS  not-accessible
   STATUS      current
   DESCRIPTION
       " "
   ::= { gs2328AAA 3 }

gs2328RADIUSAuthenticationServerEntry OBJECT-TYPE
   SYNTAX      Gs2328RADIUSAuthenticationServerEntry
   MAX-ACCESS  not-accessible
   STATUS      current
   DESCRIPTION
       ""
   INDEX    { gs2328RADIUSAuthenticationServerIndex  }
   ::= { gs2328RADIUSAuthenticationServerTable 1 }

Gs2328RADIUSAuthenticationServerEntry ::= SEQUENCE {
   gs2328RADIUSAuthenticationServerIndex     Integer32,
   gs2328RADIUSAuthenticationServerEnable    INTEGER,
   gs2328RADIUSAuthenticationServerIP        DisplayString,
   gs2328RADIUSAuthenticationServerPort      Integer32,
   gs2328RADIUSAuthenticationServerSecret    DisplayString
}

gs2328RADIUSAuthenticationServerIndex OBJECT-TYPE
   SYNTAX      Integer32(1..5)
   MAX-ACCESS  not-accessible
   STATUS      current
   DESCRIPTION
       "RADIUS Authentication Server index
        range : 1-5."
   ::= { gs2328RADIUSAuthenticationServerEntry 1 }

gs2328RADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2328RADIUSAuthenticationServerEntry 2 }

gs2328RADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2328RADIUSAuthenticationServerEntry 3 }

gs2328RADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2328RADIUSAuthenticationServerEntry 4 }

gs2328RADIUSAuthenticationServerSecret OBJECT-TYPE
   SYNTAX      DisplayString
   MAX-ACCESS  read-write
   STATUS      current
   DESCRIPTION
       "The secret - up to 64 characters long - shared between the RADIUS Authentication Server and the switch. "
   ::= { gs2328RADIUSAuthenticationServerEntry 5 }
   

gs2328RADIUSAccountingServerTable OBJECT-TYPE
   SYNTAX      SEQUENCE OF Gs2328RADIUSAccountingServerEntry
   MAX-ACCESS  not-accessible
   STATUS      current
   DESCRIPTION
       " "
   ::= { gs2328AAA 4 }

gs2328RADIUSAccountingServerEntry OBJECT-TYPE
   SYNTAX      Gs2328RADIUSAccountingServerEntry
   MAX-ACCESS  not-accessible
   STATUS      current
   DESCRIPTION
       ""
   INDEX    { gs2328RADIUSAccountingServerIndex  }
   ::= { gs2328RADIUSAccountingServerTable 1 }

Gs2328RADIUSAccountingServerEntry ::= SEQUENCE {
   gs2328RADIUSAccountingServerIndex     Integer32,
   gs2328RADIUSAccountingServerEnable    INTEGER,
   gs2328RADIUSAccountingServerIP        DisplayString,
   gs2328RADIUSAccountingServerPort      Integer32,
   gs2328RADIUSAccountingServerSecret    DisplayString
}

gs2328RADIUSAccountingServerIndex OBJECT-TYPE
   SYNTAX      Integer32(1..5)
   MAX-ACCESS  not-accessible
   STATUS      current
   DESCRIPTION
       "RADIUS Accounting Server index
        range : 1-5."
   ::= { gs2328RADIUSAccountingServerEntry 1 }

gs2328RADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2328RADIUSAccountingServerEntry 2 }

gs2328RADIUSAccountingServerIP OBJECT-TYPE
   SYNTAX      DisplayString
   MAX-ACCESS  read-write
   STATUS      current
   DESCRIPTION
       "The IP address or hostname of the RADIUS Accounting Server.
       IP address is expressed in  dotted decimal notation. "
   ::= { gs2328RADIUSAccountingServerEntry 3 }

gs2328RADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2328RADIUSAccountingServerEntry 4 }

gs2328RADIUSAccountingServerSecret OBJECT-TYPE
   SYNTAX      DisplayString
   MAX-ACCESS  read-write
   STATUS      current
   DESCRIPTION
       "The secret - up to 64 characters long - shared between the RADIUS Accounting Server and the switch. "
   ::= { gs2328RADIUSAccountingServerEntry 5 }

gs2328TACACSPlusAuthenticationServerTable OBJECT-TYPE
   SYNTAX      SEQUENCE OF Gs2328TACACSPlusAuthenticationServerEntry
   MAX-ACCESS  not-accessible
   STATUS      current
   DESCRIPTION
       " "
   ::= { gs2328AAA 5 }

gs2328TACACSPlusAuthenticationServerEntry OBJECT-TYPE
   SYNTAX      Gs2328TACACSPlusAuthenticationServerEntry
   MAX-ACCESS  not-accessible
   STATUS      current
   DESCRIPTION
       ""
   INDEX    { gs2328TACACSPlusAuthenticationServerIndex  }
   ::= { gs2328TACACSPlusAuthenticationServerTable 1 }

Gs2328TACACSPlusAuthenticationServerEntry ::= SEQUENCE {
   gs2328TACACSPlusAuthenticationServerIndex     Integer32,
   gs2328TACACSPlusAuthenticationServerEnable    INTEGER,
   gs2328TACACSPlusAuthenticationServerIP        DisplayString,
   gs2328TACACSPlusAuthenticationServerPort      Integer32,
   gs2328TACACSPlusAuthenticationServerSecret    DisplayString
}

gs2328TACACSPlusAuthenticationServerIndex OBJECT-TYPE
   SYNTAX      Integer32(1..5)
   MAX-ACCESS  not-accessible
   STATUS      current
   DESCRIPTION
       "TACACSPlus Authentication Server index
        range : 1-5."
   ::= { gs2328TACACSPlusAuthenticationServerEntry 1 }

gs2328TACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2328TACACSPlusAuthenticationServerEntry 2 }

gs2328TACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2328TACACSPlusAuthenticationServerEntry 3 }

gs2328TACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2328TACACSPlusAuthenticationServerEntry 4 }

gs2328TACACSPlusAuthenticationServerSecret OBJECT-TYPE
   SYNTAX      DisplayString
   MAX-ACCESS  read-write
   STATUS      current
   DESCRIPTION
       "The secret - up to 64 characters long - shared between the TACACSPlus Authentication Server and the switch. "
   ::= { gs2328TACACSPlusAuthenticationServerEntry 5 }


gs2328RADIUSStatisticsTable OBJECT-TYPE
   SYNTAX      SEQUENCE OF Gs2328RADIUSStatisticsEntry
   MAX-ACCESS  not-accessible
   STATUS      current
   DESCRIPTION
       " "
   ::= { gs2328AAA 6 }

gs2328RADIUSStatisticsEntry OBJECT-TYPE
   SYNTAX      Gs2328RADIUSStatisticsEntry
   MAX-ACCESS  not-accessible
   STATUS      current
   DESCRIPTION
       ""
   INDEX    { gs2328RADIUSAuthStatisticsServerIndex  }
   ::= { gs2328RADIUSStatisticsTable 1 }

Gs2328RADIUSStatisticsEntry ::= SEQUENCE {
   gs2328RADIUSAuthStatisticsServerIndex                           Integer32,
   gs2328RADIUSAuthStatisticsRecPktAccessAccepts                   Counter32,
   gs2328RADIUSAuthStatisticsRecPktAccessRejects                   Counter32,
   gs2328RADIUSAuthStatisticsRecPktAccessChallenges                Counter32,
   gs2328RADIUSAuthStatisticsRecPktMalformedAccResponses           Counter32,
   gs2328RADIUSAuthStatisticsRecPktBadAuthenticators               Counter32,
   gs2328RADIUSAuthStatisticsRecPktUnknownTypes                    Counter32,
   gs2328RADIUSAuthStatisticsRecPktDropped                         Counter32,
   gs2328RADIUSAuthStatisticsTransmitPktAccessRequests             Counter32,
   gs2328RADIUSAuthStatisticsTransmitPktAccessRetransmissions      Counter32,
   gs2328RADIUSAuthStatisticsTransmitPktPendingRequests            Counter32,
   gs2328RADIUSAuthStatisticsTransmitPktTimeouts                   Counter32,
   gs2328RADIUSAuthIP                                              DisplayString,
   gs2328RADIUSAuthState                                           DisplayString,
   gs2328RADIUSAuthRoundTripTime                                   DisplayString,

   gs2328RADIUSAccountingStatisticsRecPktResponses                 Counter32,
   gs2328RADIUSAccountingStatisticsRecPktMalformedResponses        Counter32,
   gs2328RADIUSAccountingStatisticsRecPktBadAuthenticators         Counter32,
   gs2328RADIUSAccountingStatisticsRecPktUnknownTypes              Counter32,
   gs2328RADIUSAccountingStatisticsRecPktDropped                   Counter32,
   gs2328RADIUSAccountingStatisticsTransmitPktRequests             Counter32,
   gs2328RADIUSAccountingStatisticsTransmitPktRetransmissions      Counter32,
   gs2328RADIUSAccountingStatisticsTransmitPktPendingRequests      Counter32,
   gs2328RADIUSAccountingStatisticsTransmitPktTimeouts             Counter32,
   gs2328RADIUSAccountingIP                                        DisplayString,
   gs2328RADIUSAccountingState                                     DisplayString,
   gs2328RADIUSAccountingRoundTripTime                             DisplayString,
   gs2328RADIUSStatisticsClear                                     INTEGER
}

gs2328RADIUSAuthStatisticsServerIndex OBJECT-TYPE
   SYNTAX      Integer32(1..5)
   MAX-ACCESS  not-accessible
   STATUS      current
   DESCRIPTION
       "RADIUS Authentication Server index
        range : 1-5."
   ::= { gs2328RADIUSStatisticsEntry 1 }

gs2328RADIUSAuthStatisticsRecPktAccessAccepts OBJECT-TYPE
   SYNTAX      Counter32
   MAX-ACCESS  read-only
   STATUS      current
   DESCRIPTION
       "The number of RADIUS Access-Accept packets (valid or invalid) received from the server."
   ::= { gs2328RADIUSStatisticsEntry 2 }

gs2328RADIUSAuthStatisticsRecPktAccessRejects OBJECT-TYPE
   SYNTAX      Counter32
   MAX-ACCESS  read-only
   STATUS      current
   DESCRIPTION
       "The number of RADIUS Access-Reject packets (valid or invalid) received from the server."
   ::= { gs2328RADIUSStatisticsEntry 3 }

gs2328RADIUSAuthStatisticsRecPktAccessChallenges OBJECT-TYPE
   SYNTAX      Counter32
   MAX-ACCESS  read-only
   STATUS      current
   DESCRIPTION
       "The number of RADIUS Access-Challenge packets (valid or invalid) received from the server. "
   ::= { gs2328RADIUSStatisticsEntry 4 }

gs2328RADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2328RADIUSStatisticsEntry 5 }

gs2328RADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2328RADIUSStatisticsEntry 6 }

gs2328RADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2328RADIUSStatisticsEntry 7 }

gs2328RADIUSAuthStatisticsRecPktDropped OBJECT-TYPE
   SYNTAX      Counter32
   MAX-ACCESS  read-only
   STATUS      current
   DESCRIPTION
       "The number of RADIUS packets that were received from the server on the
       authentication port and dropped for some other reason."
   ::= { gs2328RADIUSStatisticsEntry 8 }

gs2328RADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2328RADIUSStatisticsEntry 9 }

gs2328RADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2328RADIUSStatisticsEntry 10 }

gs2328RADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2328RADIUSStatisticsEntry 11 }

gs2328RADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2328RADIUSStatisticsEntry 12 }

gs2328RADIUSAuthIP OBJECT-TYPE
   SYNTAX      DisplayString
   MAX-ACCESS  read-only
   STATUS      current
   DESCRIPTION
       "IP address and UDP port for the authentication server in question."
   ::= { gs2328RADIUSStatisticsEntry 13 }

gs2328RADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2328RADIUSStatisticsEntry 14 }

gs2328RADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2328RADIUSStatisticsEntry 15 }

gs2328RADIUSAccountingStatisticsRecPktResponses OBJECT-TYPE
   SYNTAX      Counter32
   MAX-ACCESS  read-only
   STATUS      current
   DESCRIPTION
       "The number of RADIUS packets (valid or invalid) received from the server."
   ::= { gs2328RADIUSStatisticsEntry 16 }

gs2328RADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2328RADIUSStatisticsEntry 17 }

gs2328RADIUSAccountingStatisticsRecPktBadAuthenticators OBJECT-TYPE
   SYNTAX      Counter32
   MAX-ACCESS  read-only
   STATUS      current
   DESCRIPTION
       "The number of RADIUS packets containing invalid authenticators received
       from the server."
   ::= { gs2328RADIUSStatisticsEntry 18 }

gs2328RADIUSAccountingStatisticsRecPktUnknownTypes OBJECT-TYPE
   SYNTAX      Counter32
   MAX-ACCESS  read-only
   STATUS      current
   DESCRIPTION
       "The number of RADIUS packets of unknown types that were received from
       the server on the accounting port."
   ::= { gs2328RADIUSStatisticsEntry 19 }

gs2328RADIUSAccountingStatisticsRecPktDropped OBJECT-TYPE
   SYNTAX      Counter32
   MAX-ACCESS  read-only
   STATUS      current
   DESCRIPTION
       "The number of RADIUS packets that were received from the server on the
       accounting port and dropped for some other reason."
   ::= { gs2328RADIUSStatisticsEntry 20 }

gs2328RADIUSAccountingStatisticsTransmitPktRequests OBJECT-TYPE
   SYNTAX      Counter32
   MAX-ACCESS  read-only
   STATUS      current
   DESCRIPTION
       "The number of RADIUS packets sent to the server. This does not include
       retransmissions."
   ::= { gs2328RADIUSStatisticsEntry 21 }

gs2328RADIUSAccountingStatisticsTransmitPktRetransmissions OBJECT-TYPE
   SYNTAX      Counter32
   MAX-ACCESS  read-only
   STATUS      current
   DESCRIPTION
       "The number of RADIUS packets retransmitted to the RADIUS accounting server."
   ::= { gs2328RADIUSStatisticsEntry 22 }

gs2328RADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2328RADIUSStatisticsEntry 23 }

gs2328RADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2328RADIUSStatisticsEntry 24 }

gs2328RADIUSAccountingIP OBJECT-TYPE
   SYNTAX      DisplayString
   MAX-ACCESS  read-only
   STATUS      current
   DESCRIPTION
       "IP address and UDP port for the accounting server in question."
   ::= { gs2328RADIUSStatisticsEntry 25 }

gs2328RADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2328RADIUSStatisticsEntry 26 }
   
gs2328RADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2328RADIUSStatisticsEntry 27 }

gs2328RADIUSStatisticsClear OBJECT-TYPE
   SYNTAX      INTEGER(0|1)
   MAX-ACCESS  read-write
   STATUS      current
   DESCRIPTION
       "Clears the counters for the server.
       read: always 0
       clear: set 1"
   ::= { gs2328RADIUSStatisticsEntry 28 }

gs2328NAS                                              OBJECT IDENTIFIER ::= { gs2328Security 11 }

gs2328NASConfiguration                                 OBJECT IDENTIFIER ::= { gs2328NAS 1 }

gs2328NASConfigMode OBJECT-TYPE
   SYNTAX      INTEGER { disable(0), enable(1) }
   MAX-ACCESS  read-write
   STATUS      current
   DESCRIPTION
       "Indicates if NAS is globally enabled or disabled on the switch. 
	    If globally disabled, all ports are allowed forwarding of frames."
   ::= { gs2328NASConfiguration 1 }

gs2328NASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication 
		Period. Reauthentication for 802.1X-enabled ports can be used to 
		detect if a new device is plugged into a switch port or if a 
		supplicant is no longer attached. 
		For MAC-based ports, reauthentication is only useful if the RADIUS 
		server configuration has changed. It does not involve communication 
		between the switch and the client, and therefore doesn't imply that 
		a client is still present on a port."
   ::= { gs2328NASConfiguration 2 }

gs2328NASConfigReauthPeriod OBJECT-TYPE
   SYNTAX      Integer32(1..3600)
   MAX-ACCESS  read-write
   STATUS      current
   DESCRIPTION
       "Determines the period, in seconds, after which a connected client must 
	    be reauthenticated. This is only active if the Reauthentication Enabled 
		checkbox is checked. 
		range: 1 - 3600 seconds."
   ::= { gs2328NASConfiguration 3 }

gs2328NASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2328NASConfiguration 4 }
   
gs2328NASConfigAgingPeriod OBJECT-TYPE
   SYNTAX      Integer32(10..1000000)
   MAX-ACCESS  read-write
   STATUS      current
   DESCRIPTION
       "When the NAS module uses the Port Security module to secure MAC addresses, 
	    the Port Security module needs to check for activity on the MAC address 
		in question at regular intervals and free resources if no activity 
		is seen within a given period of time.
		Admin State supported : Single, Multi and MAC-Based Auth. 802.1X.
		range: 10 - 1000000 seconds."
   ::= { gs2328NASConfiguration 5 }   
   
gs2328NASConfigHoldTime OBJECT-TYPE
   SYNTAX      Integer32(10..1000000)
   MAX-ACCESS  read-write
   STATUS      current
   DESCRIPTION
       "If a client is denied access - either because the RADIUS server denies
	    the client access or because the RADIUS server request times out 
		- the client is put on hold in the Unauthorized state. The hold timer 
		does not count during an on-going authentication. In MAC-based Auth. 
		mode, the switch will ignore new frames coming from the client during 
		the hold time.
		Admin State supported : Single, Multi and MAC-Based Auth. 802.1X.
		range: 10 - 1000000 seconds."
   ::= { gs2328NASConfiguration 6 }  

gs2328NASConfigRADIUSAssignedQoSEnabled OBJECT-TYPE
   SYNTAX      INTEGER { disable(0), enable(1) }
   MAX-ACCESS  read-write
   STATUS      current
   DESCRIPTION
       "RADIUS-assigned QoS provides a means to centrally control the 
	    traffic class to which traffic coming from a successfully authenticated 
		supplicant is assigned on the switch. The RADIUS server must be configured 
		to transmit special RADIUS attributes to take advantage of this feature."
   ::= { gs2328NASConfiguration 7 }  
 
gs2328NASConfigRADIUSAssignedVLANEnabled OBJECT-TYPE
   SYNTAX      INTEGER { disable(0), enable(1) }
   MAX-ACCESS  read-write
   STATUS      current
   DESCRIPTION
       "RADIUS-assigned VLAN provides a means to centrally control the VLAN on 
	    which a successfully authenticated supplicant is placed on the switch. 
	    Incoming traffic will be classified to and switched on the RADIUS-assigned 
		VLAN. The RADIUS server must be configured to transmit special RADIUS 
		attributes to take advantage of this feature.When enable, the individual 
		ports' ditto setting determine whether RADIUS-assigned VLAN is enabled 
		on that port. When disable, RADIUS-server assigned VLAN is disabled on 
		all ports. "
   ::= { gs2328NASConfiguration 8 }    
   
gs2328NASConfigGuestVLANEnabled OBJECT-TYPE
   SYNTAX      INTEGER { disable(0), enable(1) }
   MAX-ACCESS  read-write
   STATUS      current
   DESCRIPTION
       "A Guest VLAN is a special VLAN - typically with limited network access - 
	   on which 802.1X-unaware clients are placed after a network administrator-defined 
	   timeout. The switch follows a set of rules for entering and leaving the Guest 
	   VLAN as listed below.When enable, the individual ports' ditto setting determines 
	   whether the port can be moved into Guest VLAN. When disable, the ability to 
	   move to the Guest VLAN is disabled on all ports. "
   ::= { gs2328NASConfiguration 9 } 
   
gs2328NASConfigGuestVLANID OBJECT-TYPE
   SYNTAX      Integer32(1..4094)
   MAX-ACCESS  read-write
   STATUS      current
   DESCRIPTION
       "This is the value that a port's Port VLAN ID is set to if a port is moved into 
	   the Guest VLAN. It is only changeable if the Guest VLAN option is globally enabled.
	   range: 1 - 4094."
   ::= { gs2328NASConfiguration 10 }

gs2328NASConfigMaxReauthCount OBJECT-TYPE
   SYNTAX      Integer32(1..255)
   MAX-ACCESS  read-write
   STATUS      current
   DESCRIPTION
       "The number of times the switch transmits an EAPOL Request Identity frame without 
	   response before considering entering the Guest VLAN is adjusted with this setting. 
	   The value can only be changed if the Guest VLAN option is globally enabled.
	   range: 1 - 255."
   ::= { gs2328NASConfiguration 11 }

gs2328NASConfigAllowGuestVLANEAPOLSeen OBJECT-TYPE
   SYNTAX      INTEGER { disable(0), enable(1) }
   MAX-ACCESS  read-write
   STATUS      current
   DESCRIPTION
       "The switch remembers if an EAPOL frame has been received on the port for the 
	   life-time of the port. Once the switch considers whether to enter the Guest VLAN, 
	   it will first check if this option is enabled or disabled. If disabled, the switch 
	   will only enter the Guest VLAN if an EAPOL frame has not been received on the port 
	   for the life-time of the port. If enabled (checked), the switch will consider 
	   entering the Guest VLAN even if an EAPOL frame has been received on the port for 
	   the life-time of the port.The value can only be changed if the Guest VLAN option 
	   is globally enabled."
   ::= { gs2328NASConfiguration 12 }

gs2328NASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2328NASConfiguration 101 }

gs2328NASPortConfigTable OBJECT-TYPE
   SYNTAX      SEQUENCE OF Gs2328NASPortConfigEntry
   MAX-ACCESS  not-accessible
   STATUS      current
   DESCRIPTION
       ""
   ::= { gs2328NASConfiguration 13 }

gs2328NASPortConfigEntry OBJECT-TYPE
   SYNTAX      Gs2328NASPortConfigEntry
   MAX-ACCESS  not-accessible
   STATUS      current
   DESCRIPTION
       ""
   INDEX    { gs2328NASPortConfigPort }
   ::= { gs2328NASPortConfigTable 1 }

Gs2328NASPortConfigEntry ::= SEQUENCE {
   gs2328NASPortConfigPort                       Integer32,
   gs2328NASPortConfigAdminState                 INTEGER,
   gs2328NASPortConfigRADIUSAssignedQoSEnabled	  INTEGER,
   gs2328NASPortConfigRADIUSAssignedVLANEnabled  INTEGER,
   gs2328NASPortConfigGuestVLANEnabled           INTEGER,   
   gs2328NASPortConfigFallbackEnabled            INTEGER,   
   gs2328NASPortConfigPortState                  DisplayString,
   gs2328NASPortConfigReauthenticate             INTEGER,
   gs2328NASPortConfigReinitialize               INTEGER
}
  
gs2328NASPortConfigPort OBJECT-TYPE
   SYNTAX      Integer32(1..255)
   MAX-ACCESS  not-accessible
   STATUS      current
   DESCRIPTION
       " port, range : 1 - port number. "
   ::= { gs2328NASPortConfigEntry 1 }   
   
gs2328NASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2328NASPortConfigEntry 2 }   
   
gs2328NASPortConfigRADIUSAssignedQoSEnabled OBJECT-TYPE
   SYNTAX      INTEGER { disable(0), enable(1) }
   MAX-ACCESS  read-write
   STATUS      current
   DESCRIPTION
       "When RADIUS-Assigned QoS is both globally enabled and enabled (checked) 
	    on a given port, the switch reacts to QoS Class information carried in 
		the RADIUS Access-Accept packet transmitted by the RADIUS server when a 
		supplicant is successfully authenticated. If present and valid, traffic 
		received on the supplicant's port will be classified to the given QoS Class.
		Admin State supported : Port-based and Single 802.1X and MAC-based Single Auth."
   ::= { gs2328NASPortConfigEntry 3 }    
   
gs2328NASPortConfigRADIUSAssignedVLANEnabled OBJECT-TYPE
   SYNTAX      INTEGER { disable(0), enable(1) }
   MAX-ACCESS  read-write
   STATUS      current
   DESCRIPTION
       "When RADIUS-Assigned VLAN is both globally enabled and enabled (checked) 
	   for a given port, the switch reacts to VLAN ID information carried in the 
	   RADIUS Access-Accept packet transmitted by the RADIUS server when a supplicant 
	   is successfully authenticated. If present and valid, the port's Port VLAN ID 
	   will be changed to this VLAN ID, the port will be set to be a member of that 
	   VLAN ID, and the port will be forced into VLAN unaware mode. Once assigned, 
	   all traffic arriving on the port will be classified and switched on the 
	   RADIUS-assigned VLAN ID.
	   Admin State supported : Port-based and Single 802.1X and MAC-based Single Auth."
   ::= { gs2328NASPortConfigEntry 4 }    
   
gs2328NASPortConfigGuestVLANEnabled OBJECT-TYPE
   SYNTAX      INTEGER { disable(0), enable(1) }
   MAX-ACCESS  read-write
   STATUS      current
   DESCRIPTION
       "When Guest VLAN is both globally enabled and enabled (checked) for a given port, 
	   the switch considers moving the port into the Guest VLAN according to the rules
	   outlined below.
	   Admin State supported : Port-based , Single and Multi 802.1X."
   ::= { gs2328NASPortConfigEntry 5 }    
   
gs2328NASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode 
		and the supplicant is authorized.
		Unauthorized: The port is in Force Unauthorized or a single-supplicant 
		mode and the supplicant is not successfully authorized by the RADIUS server.
		X Auth/Y Unauth: The port is in a multi-supplicant mode. Currently X clients 
		are authorized and Y are unauthorized."
   ::= { gs2328NASPortConfigEntry 6 }    
   
gs2328NASPortConfigReauthenticate OBJECT-TYPE
   SYNTAX      INTEGER { doNothing(0), do(1) }
   MAX-ACCESS  read-write
   STATUS      current
   DESCRIPTION
       "Schedules a reauthentication whenever the quiet-period of the port runs out 
	   (EAPOL-based authentication). For MAC-based authentication, reauthentication 
	   will be attempted immediately.The button only has effect for successfully 
	   authenticated clients on the port and will not cause the clients to get 
	   temporarily unauthorized."
   ::= { gs2328NASPortConfigEntry 7 }    

gs2328NASPortConfigReinitialize OBJECT-TYPE
   SYNTAX      INTEGER { doNothing(0), do(1) }
   MAX-ACCESS  read-write
   STATUS      current
   DESCRIPTION
       "Forces a reinitialization of the clients on the port and thereby a reauthentication 
	   immediately. The clients will transfer to the unauthorized state while the 
	   reauthentication is in progress."
   ::= { gs2328NASPortConfigEntry 8 }    

gs2328NASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2328NASPortConfigEntry 101 }

gs2328NASSwitchStatusTable OBJECT-TYPE
   SYNTAX      SEQUENCE OF Gs2328NASSwitchStatusEntry
   MAX-ACCESS  not-accessible
   STATUS      current
   DESCRIPTION
       ""
   ::= { gs2328NAS 2 }

gs2328NASSwitchStatusEntry OBJECT-TYPE
   SYNTAX      Gs2328NASSwitchStatusEntry
   MAX-ACCESS  not-accessible
   STATUS      current
   DESCRIPTION
       ""
   INDEX    { gs2328NASPortConfigPort }
   ::= { gs2328NASSwitchStatusTable 1 }

Gs2328NASSwitchStatusEntry ::= SEQUENCE {
   gs2328NASSwitchStatusAdminState 	DisplayString,
   gs2328NASSwitchStatusPortState		DisplayString,
   gs2328NASSwitchStatusLastSource		DisplayString,
   gs2328NASSwitchStatusLastID			DisplayString,
   gs2328NASSwitchStatusQoSClass		DisplayString,
   gs2328NASSwitchStatusPortVlanID		DisplayString
}
   
gs2328NASSwitchStatusAdminState OBJECT-TYPE
   SYNTAX      DisplayString
   MAX-ACCESS  read-only
   STATUS      current
   DESCRIPTION
       "The port's current administrative state. Refer to NAS Admin State for a description of possible values."
   ::= { gs2328NASSwitchStatusEntry 2 }   
   
gs2328NASSwitchStatusPortState OBJECT-TYPE
   SYNTAX      DisplayString
   MAX-ACCESS  read-only
   STATUS      current
   DESCRIPTION
       "The current state of the port. Refer to NAS Port State for a description of the individual states."
   ::= { gs2328NASSwitchStatusEntry 3 }      
   
gs2328NASSwitchStatusLastSource OBJECT-TYPE
   SYNTAX      DisplayString
   MAX-ACCESS  read-only
   STATUS      current
   DESCRIPTION
       "The source MAC address carried in the most recently received EAPOL frame for EAPOL-based authentication, 
	   and the most recently received frame from a new client for MAC-based authentication."
   ::= { gs2328NASSwitchStatusEntry 4 }      

gs2328NASSwitchStatusLastID OBJECT-TYPE
   SYNTAX      DisplayString
   MAX-ACCESS  read-only
   STATUS      current
   DESCRIPTION
       "The user name (supplicant identity) carried in the most recently received Response Identity EAPOL frame 
	   for EAPOL-based authentication, and the source MAC address from the most recently received frame from a 
	   new client for MAC-based authentication."
   ::= { gs2328NASSwitchStatusEntry 5 }      

gs2328NASSwitchStatusQoSClass OBJECT-TYPE
   SYNTAX      DisplayString
   MAX-ACCESS  read-only
   STATUS      current
   DESCRIPTION
       "QoS Class assigned to the port by the RADIUS server if enabled."
   ::= { gs2328NASSwitchStatusEntry 6 } 
   
gs2328NASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2328NASSwitchStatusEntry 7 } 

gs2328NASPortStatus                                 OBJECT IDENTIFIER ::= { gs2328NAS 3 }
   
gs2328NASPortStatusCountersTable OBJECT-TYPE
   SYNTAX      SEQUENCE OF Gs2328NASPortStatusCountersEntry
   MAX-ACCESS  not-accessible
   STATUS      current
   DESCRIPTION
       ""
   ::= { gs2328NASPortStatus 1 }

gs2328NASPortStatusCountersEntry OBJECT-TYPE
   SYNTAX      Gs2328NASPortStatusCountersEntry
   MAX-ACCESS  not-accessible
   STATUS      current
   DESCRIPTION
       ""
   INDEX    { gs2328NASPortConfigPort }
   ::= { gs2328NASPortStatusCountersTable 1 }

Gs2328NASPortStatusCountersEntry ::= SEQUENCE {
   gs2328NASRxCountersEAPOLTotal  	                  Counter32,
   gs2328NASRxCountersEAPOLResponseID	              Counter32,
   gs2328NASRxCountersEAPOLResponses	              Counter32,
   gs2328NASRxCountersEAPOLStart	                  Counter32,
   gs2328NASRxCountersEAPOLLogoff                    Counter32,
   gs2328NASRxCountersEAPOLInvalidType               Counter32,
   gs2328NASRxCountersEAPOLInvalidLength             Counter32,
   gs2328NASTxCountersEAPOLTotal                     Counter32,
   gs2328NASTxCountersEAPOLRequestID                 Counter32,
   gs2328NASTxCountersEAPOLRequests                  Counter32,
   gs2328NASRxBackendServerCountersAccessChallenges  Counter32,
   gs2328NASRxBackendServerCountersOtherRequests     Counter32,
   gs2328NASRxBackendServerCountersAuthSuccesses     Counter32,
   gs2328NASRxBackendServerCountersAuthFailures      Counter32,
   gs2328NASTxBackendServerCountersResponses         Counter32,
   gs2328NASLastSupplicantInfoMACAddress             DisplayString,
   gs2328NASLastSupplicantInfoVlanID                 Integer32,
   gs2328NASLastSupplicantInfoVersion                Integer32,
   gs2328NASLastSupplicantInfoIdentity               DisplayString,
   gs2328NASCountersDoClear                          INTEGER
}

gs2328NASRxCountersEAPOLTotal OBJECT-TYPE
   SYNTAX      Counter32
   MAX-ACCESS  read-only
   STATUS      current
   DESCRIPTION
       "The number of valid EAPOL frames of any type that have been received by the switch."
   ::= { gs2328NASPortStatusCountersEntry 2 }   

gs2328NASRxCountersEAPOLResponseID OBJECT-TYPE
   SYNTAX      Counter32
   MAX-ACCESS  read-only
   STATUS      current
   DESCRIPTION
       "The number of valid EAPOL Response Identity frames that have been received by the switch."
   ::= { gs2328NASPortStatusCountersEntry 3 }   

gs2328NASRxCountersEAPOLResponses OBJECT-TYPE
   SYNTAX      Counter32
   MAX-ACCESS  read-only
   STATUS      current
   DESCRIPTION
       "The number of valid EAPOL response frames (other than Response Identity frames) 
	   that have been received by the switch."
   ::= { gs2328NASPortStatusCountersEntry 4 }   

gs2328NASRxCountersEAPOLStart OBJECT-TYPE
   SYNTAX      Counter32
   MAX-ACCESS  read-only
   STATUS      current
   DESCRIPTION
       "The number of EAPOL Start frames that have been received by the switch."
   ::= { gs2328NASPortStatusCountersEntry 5 }   

gs2328NASRxCountersEAPOLLogoff OBJECT-TYPE
   SYNTAX      Counter32
   MAX-ACCESS  read-only
   STATUS      current
   DESCRIPTION
       "The number of valid EAPOL Logoff frames that have been received by the switch."
   ::= { gs2328NASPortStatusCountersEntry 6 }   

gs2328NASRxCountersEAPOLInvalidType OBJECT-TYPE
   SYNTAX      Counter32
   MAX-ACCESS  read-only
   STATUS      current
   DESCRIPTION
       "The number of EAPOL frames that have been received by the switch in which 
	   the frame type is not recognized."
   ::= { gs2328NASPortStatusCountersEntry 7 }   
   
gs2328NASRxCountersEAPOLInvalidLength OBJECT-TYPE
   SYNTAX      Counter32
   MAX-ACCESS  read-only
   STATUS      current
   DESCRIPTION
       "The number of EAPOL frames that have been received by the switch in which the 
	   Packet Body Length field is invalid."
   ::= { gs2328NASPortStatusCountersEntry 8 }   
   
gs2328NASTxCountersEAPOLTotal OBJECT-TYPE
   SYNTAX      Counter32
   MAX-ACCESS  read-only
   STATUS      current
   DESCRIPTION
       "The number of EAPOL frames of any type that have been transmitted by the switch."
   ::= { gs2328NASPortStatusCountersEntry 9 }   
   
gs2328NASTxCountersEAPOLRequestID OBJECT-TYPE
   SYNTAX      Counter32
   MAX-ACCESS  read-only
   STATUS      current
   DESCRIPTION
       "The number of EAPOL Request Identity frames that have been transmitted by the switch."
   ::= { gs2328NASPortStatusCountersEntry 10 }      

gs2328NASTxCountersEAPOLRequests OBJECT-TYPE
   SYNTAX      Counter32
   MAX-ACCESS  read-only
   STATUS      current
   DESCRIPTION
       "The number of valid EAPOL Request frames (other than Request Identity frames) 
	   that have been transmitted by the switch."
   ::= { gs2328NASPortStatusCountersEntry 11 }      
   
gs2328NASRxBackendServerCountersAccessChallenges OBJECT-TYPE
   SYNTAX      Counter32
   MAX-ACCESS  read-only
   STATUS      current
   DESCRIPTION
       "802.1X-based: Counts the number of times that the switch receives the first request 
	   from the backend server following the first response from the supplicant.
	   MAC-based: Counts all Access Challenges received from the backend server for this 
	   port or client."
   ::= { gs2328NASPortStatusCountersEntry 12 }      

gs2328NASRxBackendServerCountersOtherRequests OBJECT-TYPE
   SYNTAX      Counter32
   MAX-ACCESS  read-only
   STATUS      current
   DESCRIPTION
       "802.1X-based: Counts the number of times that the switch sends an EAP Request 
	   packet following the first to the supplicant.
	   MAC-based: Not applicable."
   ::= { gs2328NASPortStatusCountersEntry 13 }      
   
gs2328NASRxBackendServerCountersAuthSuccesses OBJECT-TYPE
   SYNTAX      Counter32
   MAX-ACCESS  read-only
   STATUS      current
   DESCRIPTION
       "Counts the number of times that the switch receives a success indication. 
	   Indicates that the supplicant/client has successfully authenticated to the 
	   backend server."
   ::= { gs2328NASPortStatusCountersEntry 14 }      
   
gs2328NASRxBackendServerCountersAuthFailures OBJECT-TYPE
   SYNTAX      Counter32
   MAX-ACCESS  read-only
   STATUS      current
   DESCRIPTION
       "Counts the number of times that the switch receives a failure message. 
	   This indicates that the supplicant/client has not authenticated to the 
	   backend server. "
   ::= { gs2328NASPortStatusCountersEntry 15 }      
   
gs2328NASTxBackendServerCountersResponses OBJECT-TYPE
   SYNTAX      Counter32
   MAX-ACCESS  read-only
   STATUS      current
   DESCRIPTION
       "802.1X-based: Counts the number of times that the switch attempts to 
	   send a supplicant's first response packet to the backend server. Indicates 
	   the switch attempted communication with the backend server. Possible 
	   retransmissions are not counted. 
	   MAC-based: Counts all the backend server packets sent from the switch 
	   towards the backend server for a given port or client. Possible 
	   retransmissions are not counted."
   ::= { gs2328NASPortStatusCountersEntry 16 }  

gs2328NASLastSupplicantInfoMACAddress OBJECT-TYPE
   SYNTAX      DisplayString
   MAX-ACCESS  read-only
   STATUS      current
   DESCRIPTION
       "The MAC address of the last supplicant/client."
   ::= { gs2328NASPortStatusCountersEntry 17 }  

gs2328NASLastSupplicantInfoVlanID OBJECT-TYPE
   SYNTAX      Integer32
   MAX-ACCESS  read-only
   STATUS      current
   DESCRIPTION
       "The VLAN ID on which the last frame from the last supplicant/client was received."
   ::= { gs2328NASPortStatusCountersEntry 18 }  
   
gs2328NASLastSupplicantInfoVersion OBJECT-TYPE
   SYNTAX      Integer32
   MAX-ACCESS  read-only
   STATUS      current
   DESCRIPTION
       "802.1X-based: The protocol version number carried in the most recently 
	   received EAPOL frame. 
	   MAC-based: Not applicable."
   ::= { gs2328NASPortStatusCountersEntry 19 }  

gs2328NASLastSupplicantInfoIdentity OBJECT-TYPE
   SYNTAX      DisplayString
   MAX-ACCESS  read-only
   STATUS      current
   DESCRIPTION
       "802.1X-based: The user name (supplicant identity) carried in the most recently received 
	   Response Identity EAPOL frame. 
	   MAC-based: Not applicable."
   ::= { gs2328NASPortStatusCountersEntry 20 }  

gs2328NASCountersDoClear OBJECT-TYPE
   SYNTAX      INTEGER { doNothing(0), do(1) }
   MAX-ACCESS  read-write
   STATUS      current
   DESCRIPTION
       "Clear the counters for the selected port."
   ::= { gs2328NASPortStatusCountersEntry 21 }    

gs2328NASPortStatusClientsTable OBJECT-TYPE
   SYNTAX      SEQUENCE OF Gs2328NASPortStatusClientsEntry
   MAX-ACCESS  not-accessible
   STATUS      current
   DESCRIPTION
       ""
   ::= { gs2328NASPortStatus 2 }

gs2328NASPortStatusClientsEntry OBJECT-TYPE
   SYNTAX      Gs2328NASPortStatusClientsEntry
   MAX-ACCESS  not-accessible
   STATUS      current
   DESCRIPTION
       ""
   INDEX    { gs2328NASPortConfigPort,
		gs2328NASClientsIndex}
   ::= { gs2328NASPortStatusClientsTable 1 }

Gs2328NASPortStatusClientsEntry ::= SEQUENCE {
   gs2328NASClientsIndex  	                  		    Integer32,
   gs2328NASClientsIdentity							DisplayString,
   gs2328NASClientsMACAddress  	                  	DisplayString,
   gs2328NASClientsVlanID		              			Integer32,
   gs2328NASClientsState	              				DisplayString,
   gs2328NASClientsLastAuth	                  		DisplayString,
   gs2328NASRxClientsEAPOLTotal  	                  	Counter32,
   gs2328NASRxClientsEAPOLResponseID	              	Counter32,
   gs2328NASRxClientsEAPOLResponses	              	Counter32,
   gs2328NASRxClientsEAPOLStart	                  	Counter32,
   gs2328NASRxClientsEAPOLLogoff                    	Counter32,
   gs2328NASRxClientsEAPOLInvalidType               	Counter32,
   gs2328NASRxClientsEAPOLInvalidLength             	Counter32,
   gs2328NASTxClientsEAPOLTotal                     	Counter32,
   gs2328NASTxClientsEAPOLRequestID                 	Counter32,
   gs2328NASTxClientsEAPOLRequests                  	Counter32,
   gs2328NASRxBackendServerClientsAccessChallenges  	Counter32,
   gs2328NASRxBackendServerClientsOtherRequests     	Counter32,
   gs2328NASRxBackendServerClientsAuthSuccesses     	Counter32,
   gs2328NASRxBackendServerClientsAuthFailures      	Counter32,
   gs2328NASTxBackendServerClientsResponses         	Counter32
}

gs2328NASClientsIndex OBJECT-TYPE
   SYNTAX      Integer32(1..255)
   MAX-ACCESS  not-accessible
   STATUS      current
   DESCRIPTION
       "Entry of client table in the port."
   ::= { gs2328NASPortStatusClientsEntry 1 } 
   
gs2328NASClientsIdentity OBJECT-TYPE
   SYNTAX      DisplayString
   MAX-ACCESS  read-only
   STATUS      current
   DESCRIPTION
       "Shows the identity of the supplicant, as received in the Response Identity 
	   EAPOL frame.This isn't available for MAC-based Auth."
   ::= { gs2328NASPortStatusClientsEntry 2 }
   
gs2328NASClientsMACAddress OBJECT-TYPE
   SYNTAX      DisplayString
   MAX-ACCESS  read-only
   STATUS      current
   DESCRIPTION
       "Multi 802.1X, this column holds the MAC address of the attached supplicant. 
	   MAC-based Auth., this column holds the MAC address of the attached client."
   ::= { gs2328NASPortStatusClientsEntry 3 }  

gs2328NASClientsVlanID OBJECT-TYPE
   SYNTAX      Integer32(1..4095)
   MAX-ACCESS  read-only
   STATUS      current
   DESCRIPTION
       "This column holds the VLAN ID that the corresponding client is currently 
	   secured through the Port Security module."
   ::= { gs2328NASPortStatusClientsEntry 4 }  
   
gs2328NASClientsState OBJECT-TYPE
   SYNTAX      DisplayString
   MAX-ACCESS  read-only
   STATUS      current
   DESCRIPTION
       "The client can either be authenticated or unauthenticated. In the authenticated 
	   state, it is allowed to forward frames on the port, and in the unauthenticated 
	   state, it is blocked."
   ::= { gs2328NASPortStatusClientsEntry 5 }  

gs2328NASClientsLastAuth OBJECT-TYPE
   SYNTAX      DisplayString
   MAX-ACCESS  read-only
   STATUS      current
   DESCRIPTION
       "Shows the date and time of the last authentication of the client."
   ::= { gs2328NASPortStatusClientsEntry 6 }  
   
gs2328NASRxClientsEAPOLTotal OBJECT-TYPE
   SYNTAX      Counter32
   MAX-ACCESS  read-only
   STATUS      current
   DESCRIPTION
       "The number of valid EAPOL frames of any type that have been received by the switch."
   ::= { gs2328NASPortStatusClientsEntry 7 }  

gs2328NASRxClientsEAPOLResponseID OBJECT-TYPE
   SYNTAX      Counter32
   MAX-ACCESS  read-only
   STATUS      current
   DESCRIPTION
       "The number of valid EAPOL Response Identity frames that have been received by the switch."
   ::= { gs2328NASPortStatusClientsEntry 8 }   

gs2328NASRxClientsEAPOLResponses OBJECT-TYPE
   SYNTAX      Counter32
   MAX-ACCESS  read-only
   STATUS      current
   DESCRIPTION
       "The number of valid EAPOL response frames (other than Response Identity frames) 
	   that have been received by the switch."
   ::= { gs2328NASPortStatusClientsEntry 9 }   

gs2328NASRxClientsEAPOLStart OBJECT-TYPE
   SYNTAX      Counter32
   MAX-ACCESS  read-only
   STATUS      current
   DESCRIPTION
       "The number of EAPOL Start frames that have been received by the switch."
   ::= { gs2328NASPortStatusClientsEntry 10 }   

gs2328NASRxClientsEAPOLLogoff OBJECT-TYPE
   SYNTAX      Counter32
   MAX-ACCESS  read-only
   STATUS      current
   DESCRIPTION
       "The number of valid EAPOL Logoff frames that have been received by the switch."
   ::= { gs2328NASPortStatusClientsEntry 11 }   

gs2328NASRxClientsEAPOLInvalidType OBJECT-TYPE
   SYNTAX      Counter32
   MAX-ACCESS  read-only
   STATUS      current
   DESCRIPTION
       "The number of EAPOL frames that have been received by the switch in which 
	   the frame type is not recognized."
   ::= { gs2328NASPortStatusClientsEntry 12 }   
   
gs2328NASRxClientsEAPOLInvalidLength OBJECT-TYPE
   SYNTAX      Counter32
   MAX-ACCESS  read-only
   STATUS      current
   DESCRIPTION
       "The number of EAPOL frames that have been received by the switch in which the 
	   Packet Body Length field is invalid."
   ::= { gs2328NASPortStatusClientsEntry 13 }

gs2328NASTxClientsEAPOLTotal OBJECT-TYPE
   SYNTAX      Counter32
   MAX-ACCESS  read-only
   STATUS      current
   DESCRIPTION
       "The number of EAPOL frames of any type that have been transmitted by the switch."
   ::= { gs2328NASPortStatusClientsEntry 14 }   
   
gs2328NASTxClientsEAPOLRequestID OBJECT-TYPE
   SYNTAX      Counter32
   MAX-ACCESS  read-only
   STATUS      current
   DESCRIPTION
       "The number of EAPOL Request Identity frames that have been transmitted by the switch."
   ::= { gs2328NASPortStatusClientsEntry 15 }      

gs2328NASTxClientsEAPOLRequests OBJECT-TYPE
   SYNTAX      Counter32
   MAX-ACCESS  read-only
   STATUS      current
   DESCRIPTION
       "The number of valid EAPOL Request frames (other than Request Identity frames) 
	   that have been transmitted by the switch."
   ::= { gs2328NASPortStatusClientsEntry 16 }        

gs2328NASRxBackendServerClientsAccessChallenges OBJECT-TYPE
   SYNTAX      Counter32
   MAX-ACCESS  read-only
   STATUS      current
   DESCRIPTION
       "802.1X-based: Counts the number of times that the switch receives the first request 
	   from the backend server following the first response from the supplicant.
	   MAC-based: Counts all Access Challenges received from the backend server for this 
	   port or client."
   ::= { gs2328NASPortStatusClientsEntry 17 }      

gs2328NASRxBackendServerClientsOtherRequests OBJECT-TYPE
   SYNTAX      Counter32
   MAX-ACCESS  read-only
   STATUS      current
   DESCRIPTION
       "802.1X-based: Counts the number of times that the switch sends an EAP Request 
	   packet following the first to the supplicant.
	   MAC-based: Not applicable."
   ::= { gs2328NASPortStatusClientsEntry 18 }      
   
gs2328NASRxBackendServerClientsAuthSuccesses OBJECT-TYPE
   SYNTAX      Counter32
   MAX-ACCESS  read-only
   STATUS      current
   DESCRIPTION
       "Counts the number of times that the switch receives a success indication. 
	   Indicates that the supplicant/client has successfully authenticated to the 
	   backend server."
   ::= { gs2328NASPortStatusClientsEntry 19 }      
   
gs2328NASRxBackendServerClientsAuthFailures OBJECT-TYPE
   SYNTAX      Counter32
   MAX-ACCESS  read-only
   STATUS      current
   DESCRIPTION
       "Counts the number of times that the switch receives a failure message. 
	   This indicates that the supplicant/client has not authenticated to the 
	   backend server. "
   ::= { gs2328NASPortStatusClientsEntry 20 }      
   
gs2328NASTxBackendServerClientsResponses OBJECT-TYPE
   SYNTAX      Counter32
   MAX-ACCESS  read-only
   STATUS      current
   DESCRIPTION
       "802.1X-based: Counts the number of times that the switch attempts to 
	   send a supplicant's first response packet to the backend server. Indicates 
	   the switch attempted communication with the backend server. Possible 
	   retransmissions are not counted. 
	   MAC-based: Counts all the backend server packets sent from the switch 
	   towards the backend server for a given port or client. Possible 
	   retransmissions are not counted."
   ::= { gs2328NASPortStatusClientsEntry 21 }  


gs2328Maintenance                                           OBJECT IDENTIFIER ::= { lancomGS2328  4 }

gs2328RestartDevice OBJECT-TYPE
   SYNTAX      INTEGER { disable(0), enable(1) }
   MAX-ACCESS  read-write
   STATUS      current
   DESCRIPTION
       "default: 0
        0:none
        1:yes"
   ::= { gs2328Maintenance 1 }

gs2328ColdRestartDevice OBJECT-TYPE
   SYNTAX      INTEGER { disable(0), enable(1) }
   MAX-ACCESS  read-write
   STATUS      current
   DESCRIPTION
       "default: 0
        0:none
        1:yes"
   ::= { gs2328Maintenance 1500 }

gs2328Firmware                                         OBJECT IDENTIFIER ::= { gs2328Maintenance 2 }

gs2328FirmwareIpAddress OBJECT-TYPE
   SYNTAX       IpAddress
   MAX-ACCESS   read-write
   STATUS       current
   DESCRIPTION
        "Get/Set the firmware tftp server."
   ::= { gs2328Firmware 1 }

gs2328FirmwareFileName OBJECT-TYPE
   SYNTAX       DisplayString
   MAX-ACCESS   read-write
   STATUS       current
   DESCRIPTION
        "Get/Set the path and filename for firmware upgrading."
   ::= { gs2328Firmware 2 }

gs2328DoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2328Firmware 3 }

gs2328SaveOrRestore                                         OBJECT IDENTIFIER ::= { gs2328Maintenance 3 }

gs2328FactoryDefaults OBJECT-TYPE
   SYNTAX      INTEGER { none(0), yes(1) }
   MAX-ACCESS  read-write
   STATUS      current
   DESCRIPTION
       "default: 0
        0:none
        1:yes"
   ::= { gs2328SaveOrRestore 1 }

gs2328SaveStart OBJECT-TYPE
   SYNTAX      INTEGER { none(0), yes(1) }
   MAX-ACCESS  read-write
   STATUS      current
   DESCRIPTION
       "default: 0
        0:none
        1:yes"
   ::= { gs2328SaveOrRestore 2 }

gs2328SaveUser OBJECT-TYPE
   SYNTAX      INTEGER { none(0), yes(1) }
   MAX-ACCESS  read-write
   STATUS      current
   DESCRIPTION
       "default: 0
        0:none
        1:yes"
   ::= { gs2328SaveOrRestore 3 }

gs2328RestoreUser OBJECT-TYPE
   SYNTAX      INTEGER { none(0), yes(1) }
   MAX-ACCESS  read-write
   STATUS      current
   DESCRIPTION
       "default: 0
        0:none
        1:yes"
   ::= { gs2328SaveOrRestore 4 }


gs2328ExportOrImport                                        OBJECT IDENTIFIER ::= { gs2328Maintenance 4 }

gs2328ExportIpAddress OBJECT-TYPE
   SYNTAX       IpAddress
   MAX-ACCESS   read-write
   STATUS       current
   DESCRIPTION
        "Get/Set the export tftp server."
   ::= { gs2328ExportOrImport 1 }

gs2328ExportConfigName OBJECT-TYPE
   SYNTAX       DisplayString
   MAX-ACCESS   read-write
   STATUS       current
   DESCRIPTION
       "Get/Set the export file path and name."
   ::= { gs2328ExportOrImport 2 }

gs2328DoExportConfig OBJECT-TYPE
   SYNTAX       INTEGER{ doNothing(0), do(1) }
   MAX-ACCESS   read-write
   STATUS       current
   DESCRIPTION
        "Do export-config.
         Get this OID always return zero.
         1 - export."
   ::= { gs2328ExportOrImport 3 }

gs2328ImportIpAddress OBJECT-TYPE
   SYNTAX       IpAddress
   MAX-ACCESS   read-write
   STATUS       current
   DESCRIPTION
        "Get/Set the import tftp server."
   ::= { gs2328ExportOrImport 4 }

gs2328ImportConfigName OBJECT-TYPE
   SYNTAX      DisplayString
   MAX-ACCESS  read-write
   STATUS      current
   DESCRIPTION
       "Get/Set the import file path and name."
   ::= { gs2328ExportOrImport 5 }

gs2328DoImportConfig OBJECT-TYPE
   SYNTAX       INTEGER{ doNothing(0), do(1) }
   MAX-ACCESS   read-write
   STATUS       current
   DESCRIPTION
        "Do export-config.
         Get this OID always return zero.
         1 - import."
   ::= { gs2328ExportOrImport 6 }

gs2328Diagnostics                                           OBJECT IDENTIFIER ::= { gs2328Maintenance 5 }

gs2328PingIpAddress OBJECT-TYPE
   SYNTAX      IpAddress
   MAX-ACCESS  read-write
   STATUS      current
   DESCRIPTION
       " The destination IP Address. "
   ::= { gs2328Diagnostics 1 }
   
gs2328PingSize OBJECT-TYPE
   SYNTAX      Integer32(60..1400)
   MAX-ACCESS  read-write
   STATUS      current
   DESCRIPTION
       " Size of ICMP echo packet.
         range : 60-1400, default : 64. "
   ::= { gs2328Diagnostics 2 }   

gs2328DoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2328Diagnostics 3 }

gs2328PingResult OBJECT-TYPE
   SYNTAX      DisplayString
   MAX-ACCESS  read-only
   STATUS      current
   DESCRIPTION
       " Show ping result. "
   ::= { gs2328Diagnostics 4 }

gs2328Ping6IpAddress OBJECT-TYPE
   SYNTAX      DisplayString
   MAX-ACCESS  read-write
   STATUS      current
   DESCRIPTION
       " The destination IPv6 Address. "
   ::= { gs2328Diagnostics 5 }
   
gs2328Ping6Size OBJECT-TYPE
   SYNTAX      Integer32(60..1400)
   MAX-ACCESS  read-write
   STATUS      current
   DESCRIPTION
       " Size of ICMP echo packet.
         range : 60-1400. "
   ::= { gs2328Diagnostics 6 }   

gs2328DoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2328Diagnostics 7 }

gs2328Ping6Result OBJECT-TYPE
   SYNTAX      DisplayString
   MAX-ACCESS  read-only
   STATUS      current
   DESCRIPTION
       " Show ping result. "
   ::= { gs2328Diagnostics 8 }


------------------------------------------------------------------------------------------------------------------
gs2328Trap                                                  OBJECT IDENTIFIER ::= { lancomGS2328  5 }

gs2328TrapEvent                                             OBJECT IDENTIFIER ::= { gs2328Trap 1 }

gs2328Emergency NOTIFICATION-TYPE
  OBJECTS   { gs2328Information }
  STATUS        current
    DESCRIPTION
        "The severity level is Emergency. The system is unusable."
    ::= { gs2328TrapEvent 1 }

gs2328Alert NOTIFICATION-TYPE
  OBJECTS   { gs2328Information }
  STATUS        current
    DESCRIPTION
        "The severity level is Alert. The action must be taken immediately."
    ::= { gs2328TrapEvent 2 }

gs2328Critical NOTIFICATION-TYPE
  OBJECTS   { gs2328Information }
  STATUS        current
    DESCRIPTION
        "The severity level is Critical. Critical conditions."
    ::= { gs2328TrapEvent 3 }

gs2328Error NOTIFICATION-TYPE
  OBJECTS   { gs2328Information }
  STATUS        current
    DESCRIPTION
        "The severity level is Error. Error conditions."
    ::= { gs2328TrapEvent 4 }

gs2328Warning NOTIFICATION-TYPE
  OBJECTS   { gs2328Information }
  STATUS        current
    DESCRIPTION
        "The severity level is Warning. Warning conditions."
    ::= { gs2328TrapEvent 5 }

gs2328Notice NOTIFICATION-TYPE
  OBJECTS   { gs2328Information }
  STATUS        current
    DESCRIPTION
        "The severity level is Notice. Normal but significant condition."
    ::= { gs2328TrapEvent 6 }

gs2328Informational NOTIFICATION-TYPE
  OBJECTS   { gs2328Information }
  STATUS        current
    DESCRIPTION
        "The severity level is Informational. Informational messages."
    ::= { gs2328TrapEvent 7 }

gs2328Debug NOTIFICATION-TYPE
  OBJECTS   { gs2328Information }
  STATUS        current
    DESCRIPTION
        "The severity level is Debug. debug-level messages."
    ::= { gs2328TrapEvent 8 }

gs2328TrapVariable                                          OBJECT IDENTIFIER ::= { gs2328Trap 2 }

gs2328Information OBJECT-TYPE
    SYNTAX      DisplayString
    MAX-ACCESS  read-only
    STATUS      current
    DESCRIPTION
        "Trap information."
    ::= { gs2328TrapVariable 1 }


END

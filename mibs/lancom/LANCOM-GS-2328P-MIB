LANCOM-GS-2328P-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2328P                                               OBJECT IDENTIFIER ::= { gigabitEthernetSwitches 2331 }

gs2328pSystem                                                OBJECT IDENTIFIER ::= { lancomGS2328P  1 }

gs2328pSystemInformation                                     OBJECT IDENTIFIER ::= { gs2328pSystem 1 }

gs2328pModelName OBJECT-TYPE
   SYNTAX       DisplayString
   MAX-ACCESS   read-only
   STATUS       current
   DESCRIPTION
       ""
 ::= { gs2328pSystemInformation 1 }

gs2328pBIOSVersion OBJECT-TYPE
   SYNTAX       DisplayString
   MAX-ACCESS   read-only
   STATUS       current
   DESCRIPTION
       ""
   ::= { gs2328pSystemInformation 2 }

gs2328pFirmwareVersion OBJECT-TYPE
   SYNTAX       DisplayString
   MAX-ACCESS   read-only
   STATUS       current
   DESCRIPTION
       ""
   ::= { gs2328pSystemInformation 3 }

gs2328pHardwareMechanicalVersion OBJECT-TYPE
   SYNTAX       DisplayString
   MAX-ACCESS   read-only
   STATUS       current
   DESCRIPTION
       ""
   ::= { gs2328pSystemInformation 4 }

gs2328pSerialNumber OBJECT-TYPE
   SYNTAX       DisplayString
   MAX-ACCESS   read-only
   STATUS       current
   DESCRIPTION
       ""
   ::= { gs2328pSystemInformation 5 }

gs2328pHostMACAddress OBJECT-TYPE
   SYNTAX       MacAddress
   MAX-ACCESS   read-only
   STATUS       current
   DESCRIPTION
       ""
   ::= { gs2328pSystemInformation 6 }

gs2328pConsoleBaudrate OBJECT-TYPE
   SYNTAX       DisplayString
   MAX-ACCESS   read-only
   STATUS       current
   DESCRIPTION
       ""
   ::= { gs2328pSystemInformation 7 }

gs2328pRAMSize OBJECT-TYPE
   SYNTAX       DisplayString
   MAX-ACCESS   read-only
   STATUS       current
   DESCRIPTION
       ""
   ::= { gs2328pSystemInformation 8 }

gs2328pFlashSize OBJECT-TYPE
   SYNTAX       DisplayString
   MAX-ACCESS   read-only
   STATUS       current
   DESCRIPTION
       ""
   ::= { gs2328pSystemInformation 9 }

gs2328pBridgeFDBSize OBJECT-TYPE
   SYNTAX       DisplayString
   MAX-ACCESS   read-only
   STATUS       current
   DESCRIPTION
       ""
   ::= { gs2328pSystemInformation 10 }

gs2328pTransmitQueue OBJECT-TYPE
   SYNTAX       DisplayString
   MAX-ACCESS   read-only
   STATUS       current
   DESCRIPTION
       ""
   ::= { gs2328pSystemInformation 11 }

gs2328pMaximumFrameSize OBJECT-TYPE
   SYNTAX       DisplayString
   MAX-ACCESS   read-only
   STATUS       current
   DESCRIPTION
       ""
   ::= { gs2328pSystemInformation 12 }

gs2328pCPULoad OBJECT-TYPE
   SYNTAX       DisplayString
   MAX-ACCESS   read-only
   STATUS       current
   DESCRIPTION
       ""
   ::= { gs2328pSystemInformation 13 }

gs2328pFanSpeed OBJECT-TYPE
   SYNTAX       DisplayString
   MAX-ACCESS   read-only
   STATUS       current
   DESCRIPTION
       ""
   ::= { gs2328pSystemInformation 17 }
   
gs2328pTemperature OBJECT-TYPE
   SYNTAX       DisplayString
   MAX-ACCESS   read-only
   STATUS       current
   DESCRIPTION
       ""
   ::= { gs2328pSystemInformation 19 }

gs2328pSystemDescription OBJECT-TYPE
   SYNTAX       DisplayString
   MAX-ACCESS   read-only
   STATUS       current
   DESCRIPTION
       ""
   ::= { gs2328pSystemInformation 21 }
   
gs2328pLocation OBJECT-TYPE
   SYNTAX       DisplayString
   MAX-ACCESS   read-only
   STATUS       current
   DESCRIPTION
       ""
   ::= { gs2328pSystemInformation 22 }
   
gs2328pContact OBJECT-TYPE
   SYNTAX       DisplayString
   MAX-ACCESS   read-only
   STATUS       current
   DESCRIPTION
       ""
   ::= { gs2328pSystemInformation 23 }
   
gs2328pDeviceName OBJECT-TYPE
   SYNTAX       DisplayString
   MAX-ACCESS   read-only
   STATUS       current
   DESCRIPTION
       ""
   ::= { gs2328pSystemInformation 24 }
   
gs2328pSystemDate OBJECT-TYPE
   SYNTAX       DisplayString
   MAX-ACCESS   read-only
   STATUS       current
   DESCRIPTION
       ""
   ::= { gs2328pSystemInformation 25 }
   
gs2328pSystemUptime OBJECT-TYPE
   SYNTAX       DisplayString
   MAX-ACCESS   read-only
   STATUS       current
   DESCRIPTION
       ""
   ::= { gs2328pSystemInformation 26 }
   
gs2328pSystemIPv4Address OBJECT-TYPE
   SYNTAX       DisplayString
   MAX-ACCESS   read-only
   STATUS       current
   DESCRIPTION
       ""
   ::= { gs2328pSystemInformation 27 }

gs2328pSystemIPv4SubnetMask OBJECT-TYPE
   SYNTAX       DisplayString
   MAX-ACCESS   read-only
   STATUS       current
   DESCRIPTION
       ""
   ::= { gs2328pSystemInformation 28 }
   
gs2328pSystemIPv4Gateway OBJECT-TYPE
   SYNTAX       DisplayString
   MAX-ACCESS   read-only
   STATUS       current
   DESCRIPTION
       ""
   ::= { gs2328pSystemInformation 29 }

gs2328pIPv6LinkLocalAddress OBJECT-TYPE
   SYNTAX       DisplayString
   MAX-ACCESS   read-only
   STATUS       current
   DESCRIPTION
       ""
   ::= { gs2328pSystemInformation 30 }

gs2328pIPv6Address OBJECT-TYPE
   SYNTAX       DisplayString
   MAX-ACCESS   read-only
   STATUS       current
   DESCRIPTION
       ""
   ::= { gs2328pSystemInformation 31 }

gs2328pIPv6Prefix OBJECT-TYPE
   SYNTAX       DisplayString
   MAX-ACCESS   read-only
   STATUS       current
   DESCRIPTION
       ""
   ::= { gs2328pSystemInformation 32 }
   
gs2328pIPv6Gateway OBJECT-TYPE
   SYNTAX       DisplayString
   MAX-ACCESS   read-only
   STATUS       current
   DESCRIPTION
       ""
   ::= { gs2328pSystemInformation 33 }

gs2328pLargestFreeMemBlock OBJECT-TYPE
   SYNTAX       Integer32
   MAX-ACCESS   read-only
   STATUS       current
   DESCRIPTION
       "Largest free memory block in Kb"
   ::= { gs2328pSystemInformation 1500 }   
   
gs2328pMemFree  OBJECT-TYPE
   SYNTAX       Integer32
   MAX-ACCESS   read-only
   STATUS       current
   DESCRIPTION
       "Free memory in Kb"
   ::= { gs2328pSystemInformation 1501 }

gs2328pSystemTime                                            OBJECT IDENTIFIER ::= { gs2328pSystem 2 }

gs2328pSystemTimeManual                                      OBJECT IDENTIFIER ::= { gs2328pSystemTime 1 }

gs2328pSystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2328pSystemTimeManual 1 }
   
gs2328pSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2328pSystemTimeManual 2 }

gs2328pSystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2328pSystemTimeManual 3 }
   
gs2328pSystemTimeManualDaylightSavings OBJECT-TYPE
   SYNTAX       INTEGER { disable(0), enable(1) }
   MAX-ACCESS   read-write
   STATUS       current
   DESCRIPTION
       "default: 0,
        0 : Disable,
        1 : Enable."
   ::= { gs2328pSystemTimeManual 4 }
   
gs2328pSystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2328pSystemTimeManual 5 }
   
gs2328pSystemTimeManualDaylightSavingsType OBJECT-TYPE
   SYNTAX       INTEGER { byDates(0), recurring(1) }
   MAX-ACCESS   read-write
   STATUS       current
   DESCRIPTION
       "default: 0,
        0 : By dates,
        1 : Recurring."
   ::= { gs2328pSystemTimeManual 6 }
   
gs2328pSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2328pSystemTimeManual 7 }
   
gs2328pSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2328pSystemTimeManual 8 }

gs2328pSystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2328pSystemTimeManual 9 }

gs2328pSystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2328pSystemTimeManual 10 }
   
gs2328pSystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2328pSystemTimeManual 11 }

gs2328pSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2328pSystemTimeManual 12 }
   
gs2328pSystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2328pSystemTimeManual 13 }

gs2328pSystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2328pSystemTimeManual 14 }
   
gs2328pSystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2328pSystemTimeManual 15 }

gs2328pSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2328pSystemTimeManual 16 }

gs2328pSystemTimeNTP                                     OBJECT IDENTIFIER ::= { gs2328pSystemTime 2 }

gs2328pSystemTimeNTPTable OBJECT-TYPE
   SYNTAX      SEQUENCE OF GS2328PSystemTimeNTPEntry
   MAX-ACCESS  not-accessible
   STATUS      current
   DESCRIPTION
       " "
   ::= { gs2328pSystemTimeNTP 1 }

gs2328pSystemTimeNTPEntry OBJECT-TYPE
   SYNTAX      GS2328PSystemTimeNTPEntry
   MAX-ACCESS  not-accessible
   STATUS      current
   DESCRIPTION
       ""
   INDEX    { gs2328pSystemTimeNTPIndex  }
   ::= { gs2328pSystemTimeNTPTable 1 }

GS2328PSystemTimeNTPEntry ::= SEQUENCE {
   gs2328pSystemTimeNTPIndex             Integer32,
   gs2328pSystemTimeNTPServerIPType      INTEGER,
   gs2328pSystemTimeNTPServer            DisplayString,
   gs2328pSystemTimeNTPCurrentMode       INTEGER
}

gs2328pSystemTimeNTPIndex OBJECT-TYPE
   SYNTAX      Integer32(1..5)
   MAX-ACCESS  not-accessible
   STATUS      current
   DESCRIPTION
       " The index of the ntp entry. "
   ::= { gs2328pSystemTimeNTPEntry 1 }

gs2328pSystemTimeNTPServerIPType OBJECT-TYPE
   SYNTAX       INTEGER { ipv4(0), ipv6(1) }
   MAX-ACCESS   read-write
   STATUS       current
   DESCRIPTION
       "Default: 0,
        0 : IPv4,
        1 : IPv6."
   ::= { gs2328pSystemTimeNTPEntry 2 }

gs2328pSystemTimeNTPServer OBJECT-TYPE
   SYNTAX       DisplayString
   MAX-ACCESS   read-write
   STATUS       current
   DESCRIPTION
       "Get/Set the NTP Time Server1. You can use the IP address or domain name."
   ::= { gs2328pSystemTimeNTPEntry 3 }

gs2328pSystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2328pSystemTimeNTPEntry 4 }

gs2328pSystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2328pSystemTimeNTP 2 }
   
gs2328pSystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2328pSystemTimeNTP 3 }
    

gs2328pSystemAccount                                         OBJECT IDENTIFIER ::= { gs2328pSystem 3 }

gs2328pSystemAccountUsers                                    OBJECT IDENTIFIER ::= { gs2328pSystemAccount 1 }

gs2328pSystemAccountUserCreate OBJECT-TYPE
   SYNTAX       INTEGER { none(0), create(1) }
   MAX-ACCESS   read-write
   STATUS       current
   DESCRIPTION
       "default: 0
        0 : None  (read only)
        1 : Create a user account"
   ::= { gs2328pSystemAccountUsers 1 }

gs2328pSystemAccountUsersTable OBJECT-TYPE
   SYNTAX      SEQUENCE OF GS2328PSystemAccountUsersEntry
   MAX-ACCESS  not-accessible
   STATUS      current
   DESCRIPTION
       " "
   ::= { gs2328pSystemAccountUsers 2 }

gs2328pSystemAccountUsersEntry OBJECT-TYPE
   SYNTAX      GS2328PSystemAccountUsersEntry
   MAX-ACCESS  not-accessible
   STATUS      current
   DESCRIPTION
       ""
   INDEX    { gs2328pUserIndex  }
   ::= { gs2328pSystemAccountUsersTable 1 }


GS2328PSystemAccountUsersEntry ::= SEQUENCE {
   gs2328pUserIndex              Integer32 ,
   gs2328pUserName               DisplayString,
   gs2328pPassword               DisplayString,
   gs2328pUserPrivilegeLevel     Integer32 ,
   gs2328pAccountUserRowStatus   INTEGER
}


gs2328pUserIndex OBJECT-TYPE
   SYNTAX      Integer32 (1..20)
   MAX-ACCESS  not-accessible
   STATUS      current
   DESCRIPTION
       " "
   ::= { gs2328pSystemAccountUsersEntry 1 }

gs2328pUserName OBJECT-TYPE
   SYNTAX      DisplayString (SIZE (1..32))
   MAX-ACCESS  read-write
   STATUS      current
   DESCRIPTION
       "Please use a combination of letters, numbers and underscores"
   ::= { gs2328pSystemAccountUsersEntry 2 }

gs2328pPassword OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2328pSystemAccountUsersEntry 3 }

gs2328pUserPrivilegeLevel OBJECT-TYPE
   SYNTAX      Integer32 (1..15)
   MAX-ACCESS  read-write
   STATUS      current
   DESCRIPTION
       "default:1 
        User privilege level range : 1 - 15"
   ::= { gs2328pSystemAccountUsersEntry 4 }

gs2328pAccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2328pSystemAccountUsersEntry 5 }

gs2328pSystemAccountUsersSuperUserPassword OBJECT-TYPE
   SYNTAX      OCTET STRING (SIZE (0..32))
   MAX-ACCESS read-write
   STATUS      current
   DESCRIPTION
        "Super-User Password"
   ::= { gs2328pSystemAccountUsers 1500 }

gs2328pSystemAccountEnforcePasswordRules OBJECT-TYPE
   SYNTAX       INTEGER { yes(0), no(1) }
   MAX-ACCESS   read-write
   STATUS       current
   DESCRIPTION
       "default: 0
        0 : Do not enforce rules
        1 : enforce rules"
   ::= { gs2328pSystemAccountUsers 1501 }

gs2328pSystemAccountPrivilegeLevel                           OBJECT IDENTIFIER ::= { gs2328pSystemAccount 2 }

gs2328pAccountPrivilegeLevel OBJECT-TYPE
   SYNTAX      Integer32 (1..15)
   MAX-ACCESS  read-write
   STATUS      current
   DESCRIPTION
       "Default:15, Range : 1-15. "
   ::= { gs2328pSystemAccountPrivilegeLevel 1 }

gs2328pAggregationPrivilegeLevel OBJECT-TYPE
   SYNTAX      Integer32 (1..15)
   MAX-ACCESS  read-write
   STATUS      current
   DESCRIPTION
       "Default:15, Range : 1-15. "
   ::= { gs2328pSystemAccountPrivilegeLevel 2 }

gs2328pDiagnosticsPrivilegeLevel OBJECT-TYPE
   SYNTAX      Integer32 (1..15)
   MAX-ACCESS  read-write
   STATUS      current
   DESCRIPTION
       "Default:15, Range : 1-15. "
   ::= { gs2328pSystemAccountPrivilegeLevel 3 }

gs2328pEEEPrivilegeLevel OBJECT-TYPE
   SYNTAX      Integer32 (1..15)
   MAX-ACCESS  read-write
   STATUS      current
   DESCRIPTION
       "Default:15, Range : 1-15. "
   ::= { gs2328pSystemAccountPrivilegeLevel 4 }

gs2328pEasyportPrivilegeLevel OBJECT-TYPE
   SYNTAX      Integer32 (1..15)
   MAX-ACCESS  read-write
   STATUS      current
   DESCRIPTION
       "Default:15, Range : 1-15. "
   ::= { gs2328pSystemAccountPrivilegeLevel 9 }

gs2328pGARPPrivilegeLevel OBJECT-TYPE
   SYNTAX      Integer32 (1..15)
   MAX-ACCESS  read-write
   STATUS      current
   DESCRIPTION
       "Default:15, Range : 1-15. "
   ::= { gs2328pSystemAccountPrivilegeLevel 10 }

gs2328pGVRPPrivilegeLevel OBJECT-TYPE
   SYNTAX      Integer32 (1..15)
   MAX-ACCESS  read-write
   STATUS      current
   DESCRIPTION
       "Default:15, Range : 1-15. "
   ::= { gs2328pSystemAccountPrivilegeLevel 11 }

gs2328pIPPrivilegeLevel OBJECT-TYPE
   SYNTAX      Integer32 (1..15)
   MAX-ACCESS  read-write
   STATUS      current
   DESCRIPTION
       "Default:15, Range : 1-15. "
   ::= { gs2328pSystemAccountPrivilegeLevel 12 }

gs2328pIPMCSnoopingPrivilegeLevel OBJECT-TYPE
   SYNTAX      Integer32 (1..15)
   MAX-ACCESS  read-write
   STATUS      current
   DESCRIPTION
       "Default:15, Range : 1-15. "
   ::= { gs2328pSystemAccountPrivilegeLevel 13 }

gs2328pLACPPrivilegeLevel OBJECT-TYPE
   SYNTAX      Integer32 (1..15)
   MAX-ACCESS  read-write
   STATUS      current
   DESCRIPTION
       "Default:15, Range : 1-15. "
   ::= { gs2328pSystemAccountPrivilegeLevel 14 }

gs2328pLLDPPrivilegeLevel OBJECT-TYPE
   SYNTAX      Integer32 (1..15)
   MAX-ACCESS  read-write
   STATUS      current
   DESCRIPTION
       "Default:15, Range : 1-15. "
   ::= { gs2328pSystemAccountPrivilegeLevel 15 }

gs2328pLLDPMEDPrivilegeLevel OBJECT-TYPE
   SYNTAX      Integer32 (1..15)
   MAX-ACCESS  read-write
   STATUS      current
   DESCRIPTION
       "Default:15, Range : 1-15. "
   ::= { gs2328pSystemAccountPrivilegeLevel 16 }

gs2328pLoopProtectPrivilegeLevel OBJECT-TYPE
   SYNTAX      Integer32 (1..15)
   MAX-ACCESS  read-write
   STATUS      current
   DESCRIPTION
       "Default:15, Range : 1-15. "
   ::= { gs2328pSystemAccountPrivilegeLevel 17 }

gs2328pMACTablePrivilegeLevel OBJECT-TYPE
   SYNTAX      Integer32 (1..15)
   MAX-ACCESS  read-write
   STATUS      current
   DESCRIPTION
       "Default:15, Range : 1-15. "
   ::= { gs2328pSystemAccountPrivilegeLevel 18 }

gs2328pMVRPrivilegeLevel OBJECT-TYPE
   SYNTAX      Integer32 (1..15)
   MAX-ACCESS  read-write
   STATUS      current
   DESCRIPTION
       "Default:15, Range : 1-15. "
   ::= { gs2328pSystemAccountPrivilegeLevel 22 }

gs2328pMaintenancePrivilegeLevel OBJECT-TYPE
   SYNTAX      Integer32 (1..15)
   MAX-ACCESS  read-write
   STATUS      current
   DESCRIPTION
       "Default:15, Range : 1-15. "
   ::= { gs2328pSystemAccountPrivilegeLevel 24 }

gs2328pMirroringPrivilegeLevel OBJECT-TYPE
   SYNTAX      Integer32 (1..15)
   MAX-ACCESS  read-write
   STATUS      current
   DESCRIPTION
       "Default:15, Range : 1-15. "
   ::= { gs2328pSystemAccountPrivilegeLevel 25 }

gs2328pPortsPrivilegeLevel OBJECT-TYPE
   SYNTAX      Integer32 (1..15)
   MAX-ACCESS  read-write
   STATUS      current
   DESCRIPTION
       "Default:15, Range : 1-15. "
   ::= { gs2328pSystemAccountPrivilegeLevel 27 }

gs2328pPrivateVLANsPrivilegeLevel OBJECT-TYPE
   SYNTAX      Integer32 (1..15)
   MAX-ACCESS  read-write
   STATUS      current
   DESCRIPTION
       "Default:15, Range : 1-15. "
   ::= { gs2328pSystemAccountPrivilegeLevel 28 }

gs2328pQoSPrivilegeLevel OBJECT-TYPE
   SYNTAX      Integer32 (1..15)
   MAX-ACCESS  read-write
   STATUS      current
   DESCRIPTION
       "Default:15, Range : 1-15. "
   ::= { gs2328pSystemAccountPrivilegeLevel 29 }

gs2328pSFlowPrivilegeLevel OBJECT-TYPE
   SYNTAX      Integer32 (1..15)
   MAX-ACCESS  read-write
   STATUS      current
   DESCRIPTION
       "Default:15, Range : 1-15. "
   ::= { gs2328pSystemAccountPrivilegeLevel 30 }

gs2328pSMTPPrivilegeLevel OBJECT-TYPE
   SYNTAX      Integer32 (1..15)
   MAX-ACCESS  read-write
   STATUS      current
   DESCRIPTION
       "Default:15, Range : 1-15. "
   ::= { gs2328pSystemAccountPrivilegeLevel 31 }

gs2328pSNMPPrivilegeLevel OBJECT-TYPE
   SYNTAX      Integer32 (1..15)
   MAX-ACCESS  read-write
   STATUS      current
   DESCRIPTION
       "Default:15, Range : 1-15. "
   ::= { gs2328pSystemAccountPrivilegeLevel 32 }

gs2328pSecurityPrivilegeLevel OBJECT-TYPE
   SYNTAX      Integer32 (1..15)
   MAX-ACCESS  read-write
   STATUS      current
   DESCRIPTION
       "Default:15, Range : 1-15. "
   ::= { gs2328pSystemAccountPrivilegeLevel 33 }

gs2328pSingleIPPrivilegeLevel OBJECT-TYPE
   SYNTAX      Integer32 (1..15)
   MAX-ACCESS  read-write
   STATUS      current
   DESCRIPTION
       "Default:15, Range : 1-15. "
   ::= { gs2328pSystemAccountPrivilegeLevel 34 }

gs2328pSpanningTreePrivilegeLevel OBJECT-TYPE
   SYNTAX      Integer32 (1..15)
   MAX-ACCESS  read-write
   STATUS      current
   DESCRIPTION
       "Default:15, Range : 1-15. "
   ::= { gs2328pSystemAccountPrivilegeLevel 35 }

gs2328pSystemPrivilegeLevel OBJECT-TYPE
   SYNTAX      Integer32 (1..15)
   MAX-ACCESS  read-write
   STATUS      current
   DESCRIPTION
       "Default:15, Range : 1-15. "
   ::= { gs2328pSystemAccountPrivilegeLevel 36 }

gs2328pTrapEventPrivilegeLevel OBJECT-TYPE
   SYNTAX      Integer32 (1..15)
   MAX-ACCESS  read-write
   STATUS      current
   DESCRIPTION
       "Default:15, Range : 1-15. "
   ::= { gs2328pSystemAccountPrivilegeLevel 37 }

gs2328pUPnPPrivilegeLevel OBJECT-TYPE
   SYNTAX      Integer32 (1..15)
   MAX-ACCESS  read-write
   STATUS      current
   DESCRIPTION
       "Default:15, Range : 1-15. "
   ::= { gs2328pSystemAccountPrivilegeLevel 38 }

gs2328pVCLPrivilegeLevel OBJECT-TYPE
   SYNTAX      Integer32 (1..15)
   MAX-ACCESS  read-write
   STATUS      current
   DESCRIPTION
       "Default:15, Range : 1-15. "
   ::= { gs2328pSystemAccountPrivilegeLevel 39 }

gs2328pVLANsPrivilegeLevel OBJECT-TYPE
   SYNTAX      Integer32 (1..15)
   MAX-ACCESS  read-write
   STATUS      current
   DESCRIPTION
       "Default:15, Range : 1-15. "
   ::= { gs2328pSystemAccountPrivilegeLevel 41 }

gs2328pVoiceVLANPrivilegeLevel OBJECT-TYPE
   SYNTAX      Integer32 (1..15)
   MAX-ACCESS  read-write
   STATUS      current
   DESCRIPTION
       "Default:15, Range : 1-15. "
   ::= { gs2328pSystemAccountPrivilegeLevel 42 }

gs2328pPOEPrivilegeLevel OBJECT-TYPE
   SYNTAX      Integer32 (1..15)
   MAX-ACCESS  read-write
   STATUS      current
   DESCRIPTION
       "Default:15, Range : 1-15. "
   ::= { gs2328pSystemAccountPrivilegeLevel 43 }


gs2328pIP                                                    OBJECT IDENTIFIER ::= { gs2328pSystem 4 }

gs2328pIPv4                                                  OBJECT IDENTIFIER ::= { gs2328pIP 1 }

gs2328pIPv4Configured                                                  OBJECT IDENTIFIER ::= { gs2328pIPv4 1 }

gs2328pIpv4DHCPClient OBJECT-TYPE
   SYNTAX      INTEGER { disable(0), enable(1) }
   MAX-ACCESS  read-write
   STATUS      current
   DESCRIPTION
       "default:0
       0: disable
       1: enable"
   ::= { gs2328pIPv4Configured 1 }

gs2328pIPv4Address OBJECT-TYPE
   SYNTAX      IpAddress
   MAX-ACCESS  read-write
   STATUS      current
   DESCRIPTION
       ""
   ::= { gs2328pIPv4Configured 2 }

gs2328pIPv4Mask OBJECT-TYPE
   SYNTAX      IpAddress
   MAX-ACCESS  read-write
   STATUS      current
   DESCRIPTION
       ""
   ::= { gs2328pIPv4Configured 3 }

gs2328pIPv4Gateway OBJECT-TYPE
   SYNTAX      IpAddress
   MAX-ACCESS  read-write
   STATUS      current
   DESCRIPTION
       ""
   ::= { gs2328pIPv4Configured 4 }

gs2328pIPv4VLANId OBJECT-TYPE
   SYNTAX      Integer32(1..4094)
   MAX-ACCESS  read-write
   STATUS      current
   DESCRIPTION
       "default:1"
   ::= { gs2328pIPv4Configured 5 }

gs2328pIPv4DNSServer OBJECT-TYPE
   SYNTAX      IpAddress
   MAX-ACCESS  read-write
   STATUS      current
   DESCRIPTION
       ""
   ::= { gs2328pIPv4Configured 6 }

gs2328pIPv4DNSProxy OBJECT-TYPE
   SYNTAX      INTEGER { disable(0), enable(1) }
   MAX-ACCESS  read-write
   STATUS      current
   DESCRIPTION
       "0:disable, 1:enable "
   ::= { gs2328pIPv4Configured 7 }

gs2328pIPv4Current                                                  OBJECT IDENTIFIER ::= { gs2328pIPv4 2 }

gs2328pIpv4CurrentDHCPClient OBJECT-TYPE
   SYNTAX      INTEGER { none(0), renew(1) }
   MAX-ACCESS  read-write
   STATUS      current
   DESCRIPTION
       "default:0
       0: none (for read)
       1: renew"
   ::= { gs2328pIPv4Current 1 }

gs2328pIPv4CurrentAddress OBJECT-TYPE
   SYNTAX      IpAddress
   MAX-ACCESS  read-only
   STATUS      current
   DESCRIPTION
       ""
   ::= { gs2328pIPv4Current 2 }

gs2328pIPv4CurrentMask OBJECT-TYPE
   SYNTAX      IpAddress
   MAX-ACCESS  read-only
   STATUS      current
   DESCRIPTION
       ""
   ::= { gs2328pIPv4Current 3 }

gs2328pIPv4CurrentGateway OBJECT-TYPE
   SYNTAX      IpAddress
   MAX-ACCESS  read-only
   STATUS      current
   DESCRIPTION
       ""
   ::= { gs2328pIPv4Current 4 }

gs2328pIPv4CurrentVLANId OBJECT-TYPE
   SYNTAX      Integer32(1..4094)
   MAX-ACCESS  read-only
   STATUS      current
   DESCRIPTION
       "default:1"
   ::= { gs2328pIPv4Current 5 }

gs2328pIPv4CurrentDNSServer OBJECT-TYPE
   SYNTAX      IpAddress
   MAX-ACCESS  read-only
   STATUS      current
   DESCRIPTION
       ""
   ::= { gs2328pIPv4Current 6 }


gs2328pIPv6                                                  OBJECT IDENTIFIER ::= { gs2328pIP 2 }

gs2328pIPv6Configured                                                  OBJECT IDENTIFIER ::= { gs2328pIPv6 1 }

gs2328pIpv6AutoConfiguration OBJECT-TYPE
   SYNTAX      INTEGER { disable(0), enable(1) }
   MAX-ACCESS  read-write
   STATUS      current
   DESCRIPTION
       "default:0
       0: disable
       1: enable"
   ::= { gs2328pIPv6Configured 1 }

gs2328pIpv6Address OBJECT-TYPE
   SYNTAX      DisplayString (SIZE (0..30))
   MAX-ACCESS  read-write
   STATUS      current
   DESCRIPTION
       ""
   ::= { gs2328pIPv6Configured 2 }

gs2328pIpv6Prefix OBJECT-TYPE
   SYNTAX      Integer32 (1..128)
   MAX-ACCESS  read-write
   STATUS      current
   DESCRIPTION
       "default: 96"
   ::= { gs2328pIPv6Configured 3 }

gs2328pIpv6Gateway OBJECT-TYPE
   SYNTAX      DisplayString (SIZE (0..30))
   MAX-ACCESS  read-write
   STATUS      current
   DESCRIPTION
       " "
   ::= { gs2328pIPv6Configured 4 }

gs2328pIPv6Current                                                  OBJECT IDENTIFIER ::= { gs2328pIPv6 2 }

gs2328pIpv6CurrentAutoConfiguration OBJECT-TYPE
   SYNTAX      INTEGER { disable(0), enable(1) }
   MAX-ACCESS  read-only
   STATUS      current
   DESCRIPTION
       "default:0
       0: disable
       1: enable"
   ::= { gs2328pIPv6Current 1 }

gs2328pIpv6CurrentAddress OBJECT-TYPE
   SYNTAX      DisplayString (SIZE (0..30))
   MAX-ACCESS  read-only
   STATUS      current
   DESCRIPTION
       ""
   ::= { gs2328pIPv6Current 2 }


gs2328pIpv6CurrentLinkLocalAddress OBJECT-TYPE
   SYNTAX      DisplayString(SIZE (0..30))
   MAX-ACCESS  read-only
   STATUS      current
   DESCRIPTION
       ""
   ::= { gs2328pIPv6Current 3 }


gs2328pIpv6CurrentPrefix OBJECT-TYPE
   SYNTAX      DisplayString(SIZE (0..64))
   MAX-ACCESS  read-only
   STATUS      current
   DESCRIPTION
       ""
   ::= { gs2328pIPv6Current 4 }

gs2328pIpv6CurrentGateway OBJECT-TYPE
   SYNTAX      DisplayString (SIZE (0..30))
   MAX-ACCESS  read-only
   STATUS      current
   DESCRIPTION
       " "
   ::= { gs2328pIPv6Current 5 }

gs2328pSyslog                                                OBJECT IDENTIFIER ::= { gs2328pSystem 5 }

gs2328pSyslogConf                                            OBJECT IDENTIFIER ::= { gs2328pSyslog 1 }

gs2328pServerMode OBJECT-TYPE
   SYNTAX      INTEGER { disable(0), enable(1) }
   MAX-ACCESS  read-write
   STATUS      current
   DESCRIPTION
       "default: 0
       0: disable
       1: enable "
   ::= { gs2328pSyslogConf 1 }

gs2328pServerAddress1 OBJECT-TYPE
   SYNTAX      IpAddress
   MAX-ACCESS  read-write
   STATUS      current
   DESCRIPTION
       " "
   ::= { gs2328pSyslogConf 2 }

gs2328pServerAddress2 OBJECT-TYPE
   SYNTAX      IpAddress
   MAX-ACCESS  read-write
   STATUS      current
   DESCRIPTION
       " "
   ::= { gs2328pSyslogConf 3 }

gs2328pSyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2328pSyslogConf 4 }

gs2328pSyslogDetailedInfo                                    OBJECT IDENTIFIER ::= { gs2328pSyslog 2 }

gs2328pSyslogDetailedInfoClear OBJECT-TYPE
   SYNTAX      INTEGER { none(0), clear(1) }
   MAX-ACCESS  read-write
   STATUS      current
   DESCRIPTION
      "default: 0
       0 : None  (read only)
       1 : Clear Syslog"
   ::= { gs2328pSyslogDetailedInfo 1 }

gs2328pSyslogDetailedInfoTable OBJECT-TYPE
  SYNTAX      SEQUENCE OF GS2328PSyslogDetailedInfoEntry
  MAX-ACCESS  not-accessible
  STATUS      current
  DESCRIPTION
           " "
       ::= { gs2328pSyslogDetailedInfo 2 }

gs2328pSyslogDetailedInfoEntry OBJECT-TYPE
   SYNTAX      GS2328PSyslogDetailedInfoEntry
   MAX-ACCESS  not-accessible
   STATUS      current
   DESCRIPTION
           ""
   INDEX    { gs2328pSyslogDetailedInfoIndex  }
   ::= { gs2328pSyslogDetailedInfoTable 1 }

GS2328PSyslogDetailedInfoEntry ::= SEQUENCE {
   gs2328pSyslogDetailedInfoIndex       Integer32,
   gs2328pSyslogDetailedInfoLevel       DisplayString,
   gs2328pSyslogDetailedInfoTime        DisplayString,
   gs2328pSyslogDetailedInfoMessage     DisplayString
}

gs2328pSyslogDetailedInfoIndex OBJECT-TYPE
   SYNTAX      Integer32(1..1024)
   MAX-ACCESS  not-accessible
   STATUS      current
   DESCRIPTION
       " "
   ::= { gs2328pSyslogDetailedInfoEntry 1 }
   
gs2328pSyslogDetailedInfoLevel OBJECT-TYPE
   SYNTAX      DisplayString
   MAX-ACCESS  read-only
   STATUS      current
   DESCRIPTION
       " "
   ::= { gs2328pSyslogDetailedInfoEntry 2 }

gs2328pSyslogDetailedInfoTime OBJECT-TYPE
   SYNTAX      DisplayString(SIZE (0..20))
   MAX-ACCESS  read-only
   STATUS      current
   DESCRIPTION
       " "
   ::= { gs2328pSyslogDetailedInfoEntry 3 }

gs2328pSyslogDetailedInfoMessage OBJECT-TYPE
   SYNTAX      DisplayString
   MAX-ACCESS  read-only
   STATUS      current
   DESCRIPTION
       " "
   ::= { gs2328pSyslogDetailedInfoEntry 4 }


gs2328pSnmp                                                OBJECT IDENTIFIER ::= { gs2328pSystem 6 }

gs2328pSnmpConf                                            OBJECT IDENTIFIER ::= { gs2328pSnmp 1 }

gs2328pGetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2328pSnmpConf 1 }

gs2328pGetCommunity OBJECT-TYPE
   SYNTAX       DisplayString
   MAX-ACCESS   read-write
   STATUS       current
   DESCRIPTION
       "Get/Set the get-community of the SNMP."
   ::= { gs2328pSnmpConf 2 }

gs2328pSetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2328pSnmpConf 3 }

gs2328pSetCommunity OBJECT-TYPE
   SYNTAX       DisplayString
   MAX-ACCESS   read-write
   STATUS       current
   DESCRIPTION
       "Get/Set the set-community of the SNMP."
   ::= { gs2328pSnmpConf 4 }

gs2328pGetCommunityConfTable OBJECT-TYPE
   SYNTAX      SEQUENCE OF GS2328PGetCommunityConfEntry
   MAX-ACCESS  not-accessible
   STATUS      current
   DESCRIPTION
       " Show get-community of the SNMP. "
   ::= { gs2328pSnmpConf 5 }

gs2328pGetCommunityConfEntry OBJECT-TYPE
   SYNTAX      GS2328PGetCommunityConfEntry
   MAX-ACCESS  not-accessible
   STATUS      current
   DESCRIPTION
       ""
   INDEX    { gs2328pCommunityConfIndex  }
   ::= { gs2328pGetCommunityConfTable 1 }

GS2328PGetCommunityConfEntry ::= SEQUENCE {
   gs2328pCommunityConfIndex				Integer32,
   gs2328pCommunityConfGetCommunity			DisplayString
}

gs2328pCommunityConfIndex OBJECT-TYPE
   SYNTAX      Integer32(1..4095)
   MAX-ACCESS  not-accessible
   STATUS      current
   DESCRIPTION
       " index, range : 1 - 5. "
   ::= { gs2328pGetCommunityConfEntry 1 }
   
gs2328pCommunityConfGetCommunity OBJECT-TYPE
   SYNTAX      DisplayString
   MAX-ACCESS  read-write
   STATUS      current
   DESCRIPTION
       " Get/Set the get-community of the SNMP."
   ::= { gs2328pGetCommunityConfEntry 2 }

gs2328pTrapHostConfTable OBJECT-TYPE
   SYNTAX      SEQUENCE OF GS2328PTrapHostConfEntry
   MAX-ACCESS  not-accessible
   STATUS      current
   DESCRIPTION
       "A list of trap host entry. The numbers of entries are given by the value of gs2328pTrapHostConfNumber."
   ::= { gs2328pSnmpConf 6 }
   
gs2328pTrapHostConfEntry OBJECT-TYPE
   SYNTAX      GS2328PTrapHostConfEntry
   MAX-ACCESS  not-accessible
   STATUS      current
   DESCRIPTION
       "This is the entry information for trap host."
   INDEX    { gs2328pTrapHostConfIndex  }
   ::= { gs2328pTrapHostConfTable 1 }

GS2328PTrapHostConfEntry ::= SEQUENCE {
    gs2328pTrapHostConfIndex             Integer32,
    gs2328pTrapHostConfVersion           INTEGER,
    gs2328pTrapHostConfIPType            INTEGER,
    gs2328pTrapHostConfIP                DisplayString,
    gs2328pTrapHostConfPort              Integer32,
    gs2328pTrapHostConfCommunity         DisplayString,
    gs2328pTrapHostConfSeverityLevel     INTEGER,
    gs2328pTrapHostConfSecurityLevel     INTEGER,
    gs2328pTrapHostConfAuthPtc           INTEGER,
    gs2328pTrapHostConfAuthPassword      DisplayString,
    gs2328pTrapHostConfPrivPtc           INTEGER,
    gs2328pTrapHostConfPrivPassword      DisplayString,
    gs2328pTrapHostConfCurrentMode       INTEGER
}
   
gs2328pTrapHostConfIndex OBJECT-TYPE
   SYNTAX      Integer32(1..6)
   MAX-ACCESS  not-accessible
   STATUS      current
   DESCRIPTION
       " The index of the trap host entry. "
   ::= { gs2328pTrapHostConfEntry 1 }

gs2328pTrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2328pTrapHostConfEntry 2 }

gs2328pTrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2328pTrapHostConfEntry 3 }

gs2328pTrapHostConfIP OBJECT-TYPE
   SYNTAX       DisplayString
   MAX-ACCESS   read-write
   STATUS       current
   DESCRIPTION
       "This is the IP of the trap host."
   ::= { gs2328pTrapHostConfEntry 4 }

gs2328pTrapHostConfPort OBJECT-TYPE
   SYNTAX       Integer32(1..65535)
   MAX-ACCESS   read-write
   STATUS       current
   DESCRIPTION
       "This is the receiving-port number of the trap host.
        range : 1 - 65535."
   ::= { gs2328pTrapHostConfEntry 5 }

gs2328pTrapHostConfCommunity OBJECT-TYPE
   SYNTAX       DisplayString (SIZE (1..32))
   MAX-ACCESS   read-write
   STATUS       current
   DESCRIPTION
       "The community/security name for the trap PDU."
   ::= { gs2328pTrapHostConfEntry 6 }

gs2328pTrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2328pTrapHostConfEntry 7 }

gs2328pTrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2328pTrapHostConfEntry 8 }

gs2328pTrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2328pTrapHostConfEntry 9 }

gs2328pTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2328pTrapHostConfEntry 10 }

gs2328pTrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2328pTrapHostConfEntry 11 }

gs2328pTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2328pTrapHostConfEntry 12 }

gs2328pTrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2328pTrapHostConfEntry 13 }


gs2328pSnmpSystem                                          OBJECT IDENTIFIER ::= { gs2328pSnmp 2 }

gs2328pSnmpState OBJECT-TYPE
   SYNTAX       INTEGER { disable(0), enable(1) }
   MAX-ACCESS   read-write
   STATUS       current
   DESCRIPTION
       "Get/Set the state of the SNMP.
        default : 1, 0: disable, 1: enable. "
   ::= { gs2328pSnmpSystem 1 }

gs2328pSnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2328pSnmpSystem 2 }

gs2328pSnmpCommunities                                          OBJECT IDENTIFIER ::= { gs2328pSnmp 3 }

gs2328pSnmpCommunitiesCreate OBJECT-TYPE
   SYNTAX       INTEGER { none(0), create(1) }
   MAX-ACCESS   read-write
   STATUS       current
   DESCRIPTION
       "default: 0
        0 : None  (read only)
        1 : Create entry"
   ::= { gs2328pSnmpCommunities 1 }

gs2328pSnmpCommunitiesTable OBJECT-TYPE
   SYNTAX      SEQUENCE OF GS2328PSnmpCommunitiesEntry
   MAX-ACCESS  not-accessible
   STATUS      current
   DESCRIPTION
       " Create SNMPv1/v2 Communities entry."
   ::= { gs2328pSnmpCommunities 2 }

gs2328pSnmpCommunitiesEntry OBJECT-TYPE
   SYNTAX      GS2328PSnmpCommunitiesEntry
   MAX-ACCESS  not-accessible
   STATUS      current
   DESCRIPTION
       ""
   INDEX    { gs2328pSnmpCommunitiesIndex  }
   ::= { gs2328pSnmpCommunitiesTable 1 }

GS2328PSnmpCommunitiesEntry ::= SEQUENCE {
   gs2328pSnmpCommunitiesIndex          Integer32,
   gs2328pSnmpCommunitiesCommunity      DisplayString,
   gs2328pSnmpCommunitiesUserName       DisplayString,
   gs2328pSnmpCommunitiesSourceIP       IpAddress,
   gs2328pSnmpCommunitiesSourceMask     IpAddress,
   gs2328pSnmpCommunitiesRowStatus      INTEGER
}

gs2328pSnmpCommunitiesIndex OBJECT-TYPE
   SYNTAX      Integer32(1..4)
   MAX-ACCESS  not-accessible
   STATUS      current
   DESCRIPTION
       " "
   ::= { gs2328pSnmpCommunitiesEntry 1 }

gs2328pSnmpCommunitiesCommunity OBJECT-TYPE
   SYNTAX      DisplayString (SIZE (1..32))
   MAX-ACCESS  read-write
   STATUS      current
   DESCRIPTION
       "Up to 32 characters describing Community."
   ::= { gs2328pSnmpCommunitiesEntry 2 }

gs2328pSnmpCommunitiesUserName OBJECT-TYPE
   SYNTAX      DisplayString (SIZE (1..32))
   MAX-ACCESS  read-write
   STATUS      current
   DESCRIPTION
       " Up to 32 characters describing User Name. "
   ::= { gs2328pSnmpCommunitiesEntry 3 }

gs2328pSnmpCommunitiesSourceIP OBJECT-TYPE
   SYNTAX      IpAddress
   MAX-ACCESS  read-write
   STATUS      current
   DESCRIPTION
       " SNMP access source ip. "
   ::= { gs2328pSnmpCommunitiesEntry 4 }

gs2328pSnmpCommunitiesSourceMask OBJECT-TYPE
   SYNTAX      IpAddress
   MAX-ACCESS  read-write
   STATUS      current
   DESCRIPTION
       " SNMP access source address mask. "
   ::= { gs2328pSnmpCommunitiesEntry 5 }

gs2328pSnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2328pSnmpCommunitiesEntry 6 }


gs2328pSnmpUsers                                          OBJECT IDENTIFIER ::= { gs2328pSnmp 4 }

gs2328pSnmpUsersCreate OBJECT-TYPE
   SYNTAX       INTEGER { none(0), create(1) }
   MAX-ACCESS   read-write
   STATUS       current
   DESCRIPTION
       "default: 0
        0 : None  (read only)
        1 : Create entry"
   ::= { gs2328pSnmpUsers 1 }

gs2328pSnmpUsersTable OBJECT-TYPE
   SYNTAX      SEQUENCE OF GS2328PSnmpUsersEntry
   MAX-ACCESS  not-accessible
   STATUS      current
   DESCRIPTION
       " Create SNMPv3 users entry."
   ::= { gs2328pSnmpUsers 2 }

gs2328pSnmpUsersEntry OBJECT-TYPE
   SYNTAX      GS2328PSnmpUsersEntry
   MAX-ACCESS  not-accessible
   STATUS      current
   DESCRIPTION
       ""
   INDEX    { gs2328pSnmpUsersIndex  }
   ::= { gs2328pSnmpUsersTable 1 }

GS2328PSnmpUsersEntry ::= SEQUENCE {
   gs2328pSnmpUsersIndex                    Integer32,
   gs2328pSnmpUsersUserName                 DisplayString,
   gs2328pSnmpUsersSecurityLevel            INTEGER,
   gs2328pSnmpUsersAuthenticationProtocol   INTEGER,
   gs2328pSnmpUsersAuthenticationPassword   DisplayString,
   gs2328pSnmpUsersPrivacyProtocol          INTEGER,
   gs2328pSnmpUsersPrivacyPassword          DisplayString,
   gs2328pSnmpUsersRowStatus                INTEGER
}

gs2328pSnmpUsersIndex OBJECT-TYPE
   SYNTAX      Integer32(1..10)
   MAX-ACCESS  not-accessible
   STATUS      current
   DESCRIPTION
       " "
   ::= { gs2328pSnmpUsersEntry 1 }

gs2328pSnmpUsersUserName OBJECT-TYPE
   SYNTAX      DisplayString (SIZE (1..32))
   MAX-ACCESS  read-write
   STATUS      current
   DESCRIPTION
       "Up to 32 characters describing User Name."
   ::= { gs2328pSnmpUsersEntry 2 }

gs2328pSnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy. 
         3: Authentication and privacy. "
   ::= { gs2328pSnmpUsersEntry 3 }

gs2328pSnmpUsersAuthenticationProtocol OBJECT-TYPE
   SYNTAX      INTEGER { none(0), md5(1), sha(2) }
   MAX-ACCESS  read-write
   STATUS      current
   DESCRIPTION
       " 0: None.
         1: MD5.
         2: SHA "
   ::= { gs2328pSnmpUsersEntry 4 }

gs2328pSnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2328pSnmpUsersEntry 5 }
   
gs2328pSnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2328pSnmpUsersEntry 6 }

gs2328pSnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2328pSnmpUsersEntry 7 }
   
gs2328pSnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2328pSnmpUsersEntry 8 }


gs2328pSnmpGroups                                          OBJECT IDENTIFIER ::= { gs2328pSnmp 5 }

gs2328pSnmpGroupsCreate OBJECT-TYPE
   SYNTAX       INTEGER { none(0), create(1) }
   MAX-ACCESS   read-write
   STATUS       current
   DESCRIPTION
       "default: 0
        0 : None  (read only)
        1 : Create entry"
   ::= { gs2328pSnmpGroups 1 }

gs2328pSnmpGroupsTable OBJECT-TYPE
   SYNTAX      SEQUENCE OF GS2328PSnmpGroupsEntry
   MAX-ACCESS  not-accessible
   STATUS      current
   DESCRIPTION
       " Create SNMPv3 groups entry."
   ::= { gs2328pSnmpGroups 2 }

gs2328pSnmpGroupsEntry OBJECT-TYPE
   SYNTAX      GS2328PSnmpGroupsEntry
   MAX-ACCESS  not-accessible
   STATUS      current
   DESCRIPTION
       ""
   INDEX    { gs2328pSnmpGroupsIndex  }
   ::= { gs2328pSnmpGroupsTable 1 }

GS2328PSnmpGroupsEntry ::= SEQUENCE {
   gs2328pSnmpGroupsIndex           Integer32,
   gs2328pSnmpGroupsSecurityModel   INTEGER,
   gs2328pSnmpGroupsSecurityName    DisplayString,
   gs2328pSnmpGroupsGroupName       DisplayString,
   gs2328pSnmpGroupsRowStatus       INTEGER
}

gs2328pSnmpGroupsIndex OBJECT-TYPE
   SYNTAX      Integer32(1..14)
   MAX-ACCESS  not-accessible
   STATUS      current
   DESCRIPTION
       " "
   ::= { gs2328pSnmpGroupsEntry 1 }

gs2328pSnmpGroupsSecurityModel OBJECT-TYPE
   SYNTAX      INTEGER { v1(1), v2c(2), usm(3) }
   MAX-ACCESS  read-write
   STATUS      current
   DESCRIPTION
       " 1: v1.
         2: v2c. 
         3: usm."
   ::= { gs2328pSnmpGroupsEntry 2 }

gs2328pSnmpGroupsSecurityName OBJECT-TYPE
   SYNTAX      DisplayString (SIZE (1..32))
   MAX-ACCESS  read-write
   STATUS      current
   DESCRIPTION
       "Up to 32 characters describing User Name."
   ::= { gs2328pSnmpGroupsEntry 3 }

gs2328pSnmpGroupsGroupName OBJECT-TYPE
   SYNTAX      DisplayString (SIZE (1..32))
   MAX-ACCESS  read-write
   STATUS      current
   DESCRIPTION
       "Up to 32 characters describing Group Name."
   ::= { gs2328pSnmpGroupsEntry 4 }
   
gs2328pSnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2328pSnmpGroupsEntry 5 }

gs2328pSnmpViews                                              OBJECT IDENTIFIER ::= { gs2328pSnmp 6 }

gs2328pSnmpViewsCreate OBJECT-TYPE
   SYNTAX       INTEGER { none(0), create(1) }
   MAX-ACCESS   read-write
   STATUS       current
   DESCRIPTION
       "default: 0
        0 : None  (read only)
        1 : Create entry"
   ::= { gs2328pSnmpViews 1 }

gs2328pSnmpViewsTable OBJECT-TYPE
   SYNTAX      SEQUENCE OF GS2328PSnmpViewsEntry
   MAX-ACCESS  not-accessible
   STATUS      current
   DESCRIPTION
       " Create SNMPv1/v2 Views entry."
   ::= { gs2328pSnmpViews 2 }

gs2328pSnmpViewsEntry OBJECT-TYPE
   SYNTAX      GS2328PSnmpViewsEntry
   MAX-ACCESS  not-accessible
   STATUS      current
   DESCRIPTION
       ""
   INDEX    { gs2328pSnmpViewsIndex  }
   ::= { gs2328pSnmpViewsTable 1 }

GS2328PSnmpViewsEntry ::= SEQUENCE {
   gs2328pSnmpViewsIndex        Integer32,
   gs2328pSnmpViewsName         DisplayString,
   gs2328pSnmpViewsType         INTEGER,
   gs2328pSnmpViewsOIDSubtree   DisplayString,
   gs2328pSnmpViewsRowStatus    INTEGER
}
   
gs2328pSnmpViewsIndex OBJECT-TYPE
   SYNTAX      Integer32(1..4)
   MAX-ACCESS  not-accessible
   STATUS      current
   DESCRIPTION
       " "
   ::= { gs2328pSnmpViewsEntry 1 }

gs2328pSnmpViewsName OBJECT-TYPE
   SYNTAX      DisplayString (SIZE (1..32))
   MAX-ACCESS  read-write
   STATUS      current
   DESCRIPTION
       "Up to 32 characters describing view Name."
   ::= { gs2328pSnmpViewsEntry 2 }   

gs2328pSnmpViewsType OBJECT-TYPE
   SYNTAX      INTEGER { included(1), excluded(2) }
   MAX-ACCESS  read-write
   STATUS      current
   DESCRIPTION
       "1: included, An optional flag to indicate that this view subtree should be included. 
	   2: excluded, An optional flag to indicate that this view subtree should be excluded."
   ::= { gs2328pSnmpViewsEntry 3 } 
   
gs2328pSnmpViewsOIDSubtree OBJECT-TYPE
   SYNTAX      DisplayString (SIZE (1..128))
   MAX-ACCESS  read-write
   STATUS      current
   DESCRIPTION
       "The OID defining the root of the subtree to add to the named view."
   ::= { gs2328pSnmpViewsEntry 4 } 

gs2328pSnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2328pSnmpViewsEntry 5 }   


gs2328pSnmpAccess                                          OBJECT IDENTIFIER ::= { gs2328pSnmp 7 }

gs2328pSnmpAccessCreate OBJECT-TYPE
   SYNTAX       INTEGER { none(0), create(1) }
   MAX-ACCESS   read-write
   STATUS       current
   DESCRIPTION
       "default: 0
        0 : None  (read only)
        1 : Create entry"
   ::= { gs2328pSnmpAccess 1 }

gs2328pSnmpAccessTable OBJECT-TYPE
   SYNTAX      SEQUENCE OF GS2328PSnmpAccessEntry
   MAX-ACCESS  not-accessible
   STATUS      current
   DESCRIPTION
       " Create SNMPv3 Access entry."
   ::= { gs2328pSnmpAccess 2 }

gs2328pSnmpAccessEntry OBJECT-TYPE
   SYNTAX      GS2328PSnmpAccessEntry
   MAX-ACCESS  not-accessible
   STATUS      current
   DESCRIPTION
       ""
   INDEX    { gs2328pSnmpAccessIndex  }
   ::= { gs2328pSnmpAccessTable 1 }

GS2328PSnmpAccessEntry ::= SEQUENCE {
   gs2328pSnmpAccessIndex             Integer32,
   gs2328pSnmpAccessGroupName         DisplayString,
   gs2328pSnmpAccessSecurityModel     INTEGER,
   gs2328pSnmpAccessSecurityLevel     INTEGER,
   gs2328pSnmpAccessReadViewName      DisplayString,
   gs2328pSnmpAccessWriteViewName     DisplayString,  
   gs2328pSnmpAccessRowStatus         INTEGER
}

gs2328pSnmpAccessIndex OBJECT-TYPE
   SYNTAX      Integer32(1..14)
   MAX-ACCESS  not-accessible
   STATUS      current
   DESCRIPTION
       " "
   ::= { gs2328pSnmpAccessEntry 1 }

gs2328pSnmpAccessGroupName OBJECT-TYPE
   SYNTAX      DisplayString (SIZE (1..32))
   MAX-ACCESS  read-write
   STATUS      current
   DESCRIPTION
       "Up to 32 characters describing Group Name."
   ::= { gs2328pSnmpAccessEntry 2 }

gs2328pSnmpAccessSecurityModel OBJECT-TYPE
   SYNTAX      INTEGER { any(0), v1(1), v2c(2), usm(3) }
   MAX-ACCESS  read-write
   STATUS      current
   DESCRIPTION
       " 0: any.
         1: v1.
         2: v2c. 
         3: usm."
   ::= { gs2328pSnmpAccessEntry 3 }

gs2328pSnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy. 
         3: Authentication and privacy. "
   ::= { gs2328pSnmpAccessEntry 4 }

gs2328pSnmpAccessReadViewName OBJECT-TYPE
   SYNTAX      DisplayString (SIZE (1..32))
   MAX-ACCESS  read-write
   STATUS      current
   DESCRIPTION
       "Up to 32 characters describing Read View Name.
        None is reserved for Empty."
   ::= { gs2328pSnmpAccessEntry 5 }
   
gs2328pSnmpAccessWriteViewName OBJECT-TYPE
   SYNTAX      DisplayString (SIZE (1..32))
   MAX-ACCESS  read-write
   STATUS      current
   DESCRIPTION
       "Up to 32 characters describing Write View Name.
        None is reserved for Empty."
   ::= { gs2328pSnmpAccessEntry 6 }
   
gs2328pSnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2328pSnmpAccessEntry 7 }


----------------------------------------------------------------------------------------------------

gs2328pConfiguration                                         OBJECT IDENTIFIER ::= { lancomGS2328P  2 }

gs2328pPort                                                  OBJECT IDENTIFIER ::= { gs2328pConfiguration 1 }

gs2328pPortConfigurationTable OBJECT-TYPE
   SYNTAX      SEQUENCE OF GS2328PPortConfigurationEntry
   MAX-ACCESS  not-accessible
   STATUS      current
   DESCRIPTION
       " Show port configurations. "
   ::= { gs2328pPort 1 }

gs2328pPortConfigurationEntry OBJECT-TYPE
   SYNTAX      GS2328PPortConfigurationEntry
   MAX-ACCESS  not-accessible
   STATUS      current
   DESCRIPTION
       ""
   INDEX    { gs2328pPortConfPort  }
   ::= { gs2328pPortConfigurationTable 1 }

GS2328PPortConfigurationEntry ::= SEQUENCE {
   gs2328pPortConfPort                     Integer32,
   gs2328pPortConfPortMedia                DisplayString,
   gs2328pPortConfLink                     DisplayString,
   gs2328pPortConfCurrentSpeed             DisplayString,
   gs2328pPortConfSpeed                    INTEGER,
   gs2328pPortConfCurrentFlowControlRx     INTEGER,
   gs2328pPortConfCurrentFlowControlTx     INTEGER,
   gs2328pPortConfFlowControl              INTEGER,
   gs2328pPortConfMaxFrameSize             Integer32,
   gs2328pPortConfExcessiveCollisionMode   INTEGER,
   gs2328pPortConfPowerControl             INTEGER,
   gs2328pPortConfDescription              DisplayString
}

gs2328pPortConfPort OBJECT-TYPE
   SYNTAX      Integer32(1..4095)
   MAX-ACCESS  not-accessible
   STATUS      current
   DESCRIPTION
       " port, range : 1 - port number. "
   ::= { gs2328pPortConfigurationEntry 1 }

gs2328pPortConfPortMedia OBJECT-TYPE
   SYNTAX      DisplayString(SIZE (1..4))
   MAX-ACCESS  read-only
   STATUS      current
   DESCRIPTION
       " Show port media. "
   ::= { gs2328pPortConfigurationEntry 2 }

gs2328pPortConfLink OBJECT-TYPE
   SYNTAX      DisplayString(SIZE (2..4))
   MAX-ACCESS  read-only
   STATUS      current
   DESCRIPTION
       " The current link state. "
   ::= { gs2328pPortConfigurationEntry 3 }

gs2328pPortConfCurrentSpeed OBJECT-TYPE
   SYNTAX      DisplayString(SIZE (6..12))
   MAX-ACCESS  read-only
   STATUS      current
   DESCRIPTION
       " The current link speed of the port. "
   ::= { gs2328pPortConfigurationEntry 4 }

gs2328pPortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11),
                    speed10GFull(12)
                }
   MAX-ACCESS  read-write
   STATUS      current
   DESCRIPTION
       "default: 1,
        0: disable state, 
        1: auto, 
        2: 10 Half, 
        3: 10 Full, 
        4: 100 Half, 
        5: 100 Full, 
        6: 1G full, 
        only 'Dual Media' port have 7-11 option. 
        Dual Media port default: 7,  
        7: SFP_Auto_AMS, 
        8: 100FX_AMS, 
        9: 1000X_AMS, 
        10: 100FX, 
        11: 1000X,
        12: 10G Full. "
   ::= { gs2328pPortConfigurationEntry 5 }

gs2328pPortConfCurrentFlowControlRx OBJECT-TYPE
   SYNTAX      INTEGER { disable(0), enable(1), noSupport(2) }
   MAX-ACCESS  read-only
   STATUS      current
   DESCRIPTION
       "0: disable
        1: enable
        2: no support.  "
   ::= { gs2328pPortConfigurationEntry 6 }

gs2328pPortConfCurrentFlowControlTx OBJECT-TYPE
   SYNTAX      INTEGER { disable(0), enable(1), noSupport(2) }
   MAX-ACCESS  read-only
   STATUS      current
   DESCRIPTION
       "0: disable
        1: enable
        2: no support.  "
   ::= { gs2328pPortConfigurationEntry 7 }

gs2328pPortConfFlowControl OBJECT-TYPE
   SYNTAX      INTEGER { disable(0), enable(1), noSupport(2) }
   MAX-ACCESS  read-write
   STATUS      current
   DESCRIPTION
       "default: 0,
        0: disable
        1: enable
        2: no support. "
   ::= { gs2328pPortConfigurationEntry 8 }

gs2328pPortConfMaxFrameSize OBJECT-TYPE
   SYNTAX      Integer32 (1518..9600)
   MAX-ACCESS  read-write
   STATUS      current
   DESCRIPTION
       "default: 9600 , range : 1518 - 9600 "
   ::= { gs2328pPortConfigurationEntry 9 }

gs2328pPortConfExcessiveCollisionMode OBJECT-TYPE
   SYNTAX      INTEGER { discard(0), restart(1), noSupport(2) }
   MAX-ACCESS  read-write
   STATUS      current
   DESCRIPTION
       "default: 0,
        Excessive Collision Mode : 
        0: Discard,
        1: Restart, 
        2: no support.
       "
   ::= { gs2328pPortConfigurationEntry 10 }

gs2328pPortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy, 
        2: Dynamic (perfectReach),
        3: Enable,
        4: no support.
       "
   ::= { gs2328pPortConfigurationEntry 11 }

gs2328pPortConfDescription OBJECT-TYPE
   SYNTAX      DisplayString
   MAX-ACCESS  read-write
   STATUS      current
   DESCRIPTION
       " Interface specific description.
         Up to 47 characters describing this interface. "
   ::= { gs2328pPortConfigurationEntry 12 }


gs2328pPortTrafficStatisticsTable OBJECT-TYPE
   SYNTAX      SEQUENCE OF GS2328PPortTrafficStatisticsEntry
   MAX-ACCESS  not-accessible
   STATUS      current
   DESCRIPTION
       " "
   ::= { gs2328pPort 2 }

gs2328pPortTrafficStatisticsEntry OBJECT-TYPE
   SYNTAX      GS2328PPortTrafficStatisticsEntry
   MAX-ACCESS  not-accessible
   STATUS      current
   DESCRIPTION
       ""
   INDEX    { gs2328pPortTrafficStatisticsPort  }
   ::= { gs2328pPortTrafficStatisticsTable 1 }

GS2328PPortTrafficStatisticsEntry ::= SEQUENCE {
   gs2328pPortTrafficStatisticsPort          Integer32,
   gs2328pPortTrafficStatisticsClear         INTEGER,
   gs2328pPortTrafficRxPackets               Counter64,
   gs2328pPortTrafficRxOctets                Counter64,
   gs2328pPortTrafficRxUnicast               Counter64,
   gs2328pPortTrafficRxMulticast             Counter64,
   gs2328pPortTrafficRxBroadcast             Counter64,
   gs2328pPortTrafficRxPause                 Counter64,
   gs2328pPortTrafficRx64Bytes               Counter64,
   gs2328pPortTrafficRx65to127Bytes          Counter64,
   gs2328pPortTrafficRx128to255Bytes         Counter64,
   gs2328pPortTrafficRx256to511Bytes         Counter64,
   gs2328pPortTrafficRx512to1023Bytes        Counter64,
   gs2328pPortTrafficRx1024to1526Bytes       Counter64,
   gs2328pPortTrafficRxExceecd1527Bytes      Counter64,
   gs2328pPortTrafficRxQ0                    Counter64,
   gs2328pPortTrafficRxQ1                    Counter64,
   gs2328pPortTrafficRxQ2                    Counter64,
   gs2328pPortTrafficRxQ3                    Counter64,
   gs2328pPortTrafficRxQ4                    Counter64,
   gs2328pPortTrafficRxQ5                    Counter64,
   gs2328pPortTrafficRxQ6                    Counter64,
   gs2328pPortTrafficRxQ7                    Counter64,
   gs2328pPortTrafficRxDrops                 Counter64,
   gs2328pPortTrafficRxCRCorAlignment        Counter64,
   gs2328pPortTrafficRxUndersize             Counter64,
   gs2328pPortTrafficRxOversize              Counter64,
   gs2328pPortTrafficRxFragments             Counter64,
   gs2328pPortTrafficRxJabber                Counter64,
   gs2328pPortTrafficRxFiltered              Counter64,
   gs2328pPortTrafficTxPackets               Counter64,
   gs2328pPortTrafficTxOctets                Counter64,
   gs2328pPortTrafficTxUnicast               Counter64,
   gs2328pPortTrafficTxMulticast             Counter64,
   gs2328pPortTrafficTxBroadcast             Counter64,
   gs2328pPortTrafficTxPause                 Counter64,
   gs2328pPortTrafficTx64Bytes               Counter64,
   gs2328pPortTrafficTx65to127Bytes          Counter64,
   gs2328pPortTrafficTx128to255Bytes         Counter64,
   gs2328pPortTrafficTx256to511Bytes         Counter64,
   gs2328pPortTrafficTx512to1023Bytes        Counter64,
   gs2328pPortTrafficTx1024to1526Bytes       Counter64,
   gs2328pPortTrafficTxExceecd1527Bytes      Counter64,
   gs2328pPortTrafficTxQ0                    Counter64,
   gs2328pPortTrafficTxQ1                    Counter64,
   gs2328pPortTrafficTxQ2                    Counter64,
   gs2328pPortTrafficTxQ3                    Counter64,
   gs2328pPortTrafficTxQ4                    Counter64,
   gs2328pPortTrafficTxQ5                    Counter64,
   gs2328pPortTrafficTxQ6                    Counter64,
   gs2328pPortTrafficTxQ7                    Counter64,
   gs2328pPortTrafficTxDrops                 Counter64,
   gs2328pPortTrafficTxLateOrExcColl         Counter64
}

gs2328pPortTrafficStatisticsPort OBJECT-TYPE
   SYNTAX      Integer32 (1..4095)
   MAX-ACCESS  not-accessible
   STATUS      current
   DESCRIPTION
       " "
   ::= { gs2328pPortTrafficStatisticsEntry 1 }

gs2328pPortTrafficStatisticsClear OBJECT-TYPE
   SYNTAX      INTEGER { disable(0), enable(1) }
   MAX-ACCESS  read-write
   STATUS      current
   DESCRIPTION
       " "
   ::= { gs2328pPortTrafficStatisticsEntry 2 }

gs2328pPortTrafficRxPackets OBJECT-TYPE
   SYNTAX      Counter64
   MAX-ACCESS  read-only
   STATUS      current
   DESCRIPTION
       " "
   ::= { gs2328pPortTrafficStatisticsEntry 3 }

gs2328pPortTrafficRxOctets OBJECT-TYPE
   SYNTAX      Counter64
   MAX-ACCESS  read-only
   STATUS      current
   DESCRIPTION
       " "
   ::= { gs2328pPortTrafficStatisticsEntry 4 }

gs2328pPortTrafficRxUnicast OBJECT-TYPE
   SYNTAX      Counter64
   MAX-ACCESS  read-only
   STATUS      current
   DESCRIPTION
       " "
   ::= { gs2328pPortTrafficStatisticsEntry 5 }

gs2328pPortTrafficRxMulticast OBJECT-TYPE
   SYNTAX      Counter64
   MAX-ACCESS  read-only
   STATUS      current
   DESCRIPTION
       " "
   ::= { gs2328pPortTrafficStatisticsEntry 6 }

gs2328pPortTrafficRxBroadcast OBJECT-TYPE
   SYNTAX      Counter64
   MAX-ACCESS  read-only
   STATUS      current
   DESCRIPTION
       " "
   ::= { gs2328pPortTrafficStatisticsEntry 7 }

gs2328pPortTrafficRxPause OBJECT-TYPE
   SYNTAX      Counter64
   MAX-ACCESS  read-only
   STATUS      current
   DESCRIPTION
       " "
   ::= { gs2328pPortTrafficStatisticsEntry 8 }

gs2328pPortTrafficRx64Bytes OBJECT-TYPE
   SYNTAX      Counter64
   MAX-ACCESS  read-only
   STATUS      current
   DESCRIPTION
       " "
   ::= { gs2328pPortTrafficStatisticsEntry 9 }

gs2328pPortTrafficRx65to127Bytes OBJECT-TYPE
   SYNTAX      Counter64
   MAX-ACCESS  read-only
   STATUS      current
   DESCRIPTION
       " "
   ::= { gs2328pPortTrafficStatisticsEntry 10 }

gs2328pPortTrafficRx128to255Bytes OBJECT-TYPE
   SYNTAX      Counter64
   MAX-ACCESS  read-only
   STATUS      current
   DESCRIPTION
       " "
   ::= { gs2328pPortTrafficStatisticsEntry 11 }

gs2328pPortTrafficRx256to511Bytes OBJECT-TYPE
   SYNTAX      Counter64
   MAX-ACCESS  read-only
   STATUS      current
   DESCRIPTION
       " "
   ::= { gs2328pPortTrafficStatisticsEntry 12 }

gs2328pPortTrafficRx512to1023Bytes OBJECT-TYPE
   SYNTAX      Counter64
   MAX-ACCESS  read-only
   STATUS      current
   DESCRIPTION
       " "
   ::= { gs2328pPortTrafficStatisticsEntry 13 }

gs2328pPortTrafficRx1024to1526Bytes OBJECT-TYPE
   SYNTAX      Counter64
   MAX-ACCESS  read-only
   STATUS      current
   DESCRIPTION
       " "
   ::= { gs2328pPortTrafficStatisticsEntry 14 }

gs2328pPortTrafficRxExceecd1527Bytes OBJECT-TYPE
   SYNTAX      Counter64
   MAX-ACCESS  read-only
   STATUS      current
   DESCRIPTION
       " "
   ::= { gs2328pPortTrafficStatisticsEntry 15 }

gs2328pPortTrafficRxQ0 OBJECT-TYPE
   SYNTAX      Counter64
   MAX-ACCESS  read-only
   STATUS      current
   DESCRIPTION
       " "
   ::= { gs2328pPortTrafficStatisticsEntry 16 }

gs2328pPortTrafficRxQ1 OBJECT-TYPE
   SYNTAX      Counter64
   MAX-ACCESS  read-only
   STATUS      current
   DESCRIPTION
       " "
   ::= { gs2328pPortTrafficStatisticsEntry 17 }

gs2328pPortTrafficRxQ2 OBJECT-TYPE
   SYNTAX      Counter64
   MAX-ACCESS  read-only
   STATUS      current
   DESCRIPTION
       " "
   ::= { gs2328pPortTrafficStatisticsEntry 18 }

gs2328pPortTrafficRxQ3 OBJECT-TYPE
   SYNTAX      Counter64
   MAX-ACCESS  read-only
   STATUS      current
   DESCRIPTION
       " "
   ::= { gs2328pPortTrafficStatisticsEntry 19 }

gs2328pPortTrafficRxQ4 OBJECT-TYPE
   SYNTAX      Counter64
   MAX-ACCESS  read-only
   STATUS      current
   DESCRIPTION
       " "
   ::= { gs2328pPortTrafficStatisticsEntry 20 }

gs2328pPortTrafficRxQ5 OBJECT-TYPE
   SYNTAX      Counter64
   MAX-ACCESS  read-only
   STATUS      current
   DESCRIPTION
       " "
   ::= { gs2328pPortTrafficStatisticsEntry 21 }

gs2328pPortTrafficRxQ6 OBJECT-TYPE
   SYNTAX      Counter64
   MAX-ACCESS  read-only
   STATUS      current
   DESCRIPTION
       " "
   ::= { gs2328pPortTrafficStatisticsEntry 22 }

gs2328pPortTrafficRxQ7 OBJECT-TYPE
   SYNTAX      Counter64
   MAX-ACCESS  read-only
   STATUS      current
   DESCRIPTION
       " "
   ::= { gs2328pPortTrafficStatisticsEntry 23 }

gs2328pPortTrafficRxDrops OBJECT-TYPE
   SYNTAX      Counter64
   MAX-ACCESS  read-only
   STATUS      current
   DESCRIPTION
       " "
   ::= { gs2328pPortTrafficStatisticsEntry 24 }

gs2328pPortTrafficRxCRCorAlignment OBJECT-TYPE
   SYNTAX      Counter64
   MAX-ACCESS  read-only
   STATUS      current
   DESCRIPTION
       " "
   ::= { gs2328pPortTrafficStatisticsEntry 25 }

gs2328pPortTrafficRxUndersize OBJECT-TYPE
   SYNTAX      Counter64
   MAX-ACCESS  read-only
   STATUS      current
   DESCRIPTION
       " "
   ::= { gs2328pPortTrafficStatisticsEntry 26 }

gs2328pPortTrafficRxOversize OBJECT-TYPE
   SYNTAX      Counter64
   MAX-ACCESS  read-only
   STATUS      current
   DESCRIPTION
       " "
   ::= { gs2328pPortTrafficStatisticsEntry 27 }

gs2328pPortTrafficRxFragments OBJECT-TYPE
   SYNTAX      Counter64
   MAX-ACCESS  read-only
   STATUS      current
   DESCRIPTION
       " "
   ::= { gs2328pPortTrafficStatisticsEntry 28 }

gs2328pPortTrafficRxJabber OBJECT-TYPE
   SYNTAX      Counter64
   MAX-ACCESS  read-only
   STATUS      current
   DESCRIPTION
       " "
   ::= { gs2328pPortTrafficStatisticsEntry 29 }

gs2328pPortTrafficRxFiltered OBJECT-TYPE
   SYNTAX      Counter64
   MAX-ACCESS  read-only
   STATUS      current
   DESCRIPTION
       " "
   ::= { gs2328pPortTrafficStatisticsEntry 30 }

gs2328pPortTrafficTxPackets OBJECT-TYPE
   SYNTAX      Counter64
   MAX-ACCESS  read-only
   STATUS      current
   DESCRIPTION
       " "
   ::= { gs2328pPortTrafficStatisticsEntry 31 }

gs2328pPortTrafficTxOctets OBJECT-TYPE
   SYNTAX      Counter64
   MAX-ACCESS  read-only
   STATUS      current
   DESCRIPTION
       " "
   ::= { gs2328pPortTrafficStatisticsEntry 32 }

gs2328pPortTrafficTxUnicast OBJECT-TYPE
   SYNTAX      Counter64
   MAX-ACCESS  read-only
   STATUS      current
   DESCRIPTION
       " "
   ::= { gs2328pPortTrafficStatisticsEntry 33 }

gs2328pPortTrafficTxMulticast OBJECT-TYPE
   SYNTAX      Counter64
   MAX-ACCESS  read-only
   STATUS      current
   DESCRIPTION
       " "
   ::= { gs2328pPortTrafficStatisticsEntry 34 }

gs2328pPortTrafficTxBroadcast OBJECT-TYPE
   SYNTAX      Counter64
   MAX-ACCESS  read-only
   STATUS      current
   DESCRIPTION
       " "
   ::= { gs2328pPortTrafficStatisticsEntry 35 }

gs2328pPortTrafficTxPause OBJECT-TYPE
   SYNTAX      Counter64
   MAX-ACCESS  read-only
   STATUS      current
   DESCRIPTION
       " "
   ::= { gs2328pPortTrafficStatisticsEntry 36 }

gs2328pPortTrafficTx64Bytes OBJECT-TYPE
   SYNTAX      Counter64
   MAX-ACCESS  read-only
   STATUS      current
   DESCRIPTION
       " "
   ::= { gs2328pPortTrafficStatisticsEntry 37 }

gs2328pPortTrafficTx65to127Bytes OBJECT-TYPE
   SYNTAX      Counter64
   MAX-ACCESS  read-only
   STATUS      current
   DESCRIPTION
       " "
   ::= { gs2328pPortTrafficStatisticsEntry 38 }

gs2328pPortTrafficTx128to255Bytes OBJECT-TYPE
   SYNTAX      Counter64
   MAX-ACCESS  read-only
   STATUS      current
   DESCRIPTION
       " "
   ::= { gs2328pPortTrafficStatisticsEntry 39 }

gs2328pPortTrafficTx256to511Bytes OBJECT-TYPE
   SYNTAX      Counter64
   MAX-ACCESS  read-only
   STATUS      current
   DESCRIPTION
       " "
   ::= { gs2328pPortTrafficStatisticsEntry 40 }

gs2328pPortTrafficTx512to1023Bytes OBJECT-TYPE
   SYNTAX      Counter64
   MAX-ACCESS  read-only
   STATUS      current
   DESCRIPTION
       " "
   ::= { gs2328pPortTrafficStatisticsEntry 41 }

gs2328pPortTrafficTx1024to1526Bytes OBJECT-TYPE
   SYNTAX      Counter64
   MAX-ACCESS  read-only
   STATUS      current
   DESCRIPTION
       " "
   ::= { gs2328pPortTrafficStatisticsEntry 42 }

gs2328pPortTrafficTxExceecd1527Bytes OBJECT-TYPE
   SYNTAX      Counter64
   MAX-ACCESS  read-only
   STATUS      current
   DESCRIPTION
       " "
   ::= { gs2328pPortTrafficStatisticsEntry 43 }

gs2328pPortTrafficTxQ0 OBJECT-TYPE
   SYNTAX      Counter64
   MAX-ACCESS  read-only
   STATUS      current
   DESCRIPTION
       " "
   ::= { gs2328pPortTrafficStatisticsEntry 44 }

gs2328pPortTrafficTxQ1 OBJECT-TYPE
   SYNTAX      Counter64
   MAX-ACCESS  read-only
   STATUS      current
   DESCRIPTION
       " "
   ::= { gs2328pPortTrafficStatisticsEntry 45 }

gs2328pPortTrafficTxQ2 OBJECT-TYPE
   SYNTAX      Counter64
   MAX-ACCESS  read-only
   STATUS      current
   DESCRIPTION
       " "
   ::= { gs2328pPortTrafficStatisticsEntry 46 }

gs2328pPortTrafficTxQ3 OBJECT-TYPE
   SYNTAX      Counter64
   MAX-ACCESS  read-only
   STATUS      current
   DESCRIPTION
       " "
   ::= { gs2328pPortTrafficStatisticsEntry 47 }

gs2328pPortTrafficTxQ4 OBJECT-TYPE
   SYNTAX      Counter64
   MAX-ACCESS  read-only
   STATUS      current
   DESCRIPTION
       " "
   ::= { gs2328pPortTrafficStatisticsEntry 48 }

gs2328pPortTrafficTxQ5 OBJECT-TYPE
   SYNTAX      Counter64
   MAX-ACCESS  read-only
   STATUS      current
   DESCRIPTION
       " "
   ::= { gs2328pPortTrafficStatisticsEntry 49 }

gs2328pPortTrafficTxQ6 OBJECT-TYPE
   SYNTAX      Counter64
   MAX-ACCESS  read-only
   STATUS      current
   DESCRIPTION
       " "
   ::= { gs2328pPortTrafficStatisticsEntry 50 }


gs2328pPortTrafficTxQ7 OBJECT-TYPE
   SYNTAX      Counter64
   MAX-ACCESS  read-only
   STATUS      current
   DESCRIPTION
       " "
   ::= { gs2328pPortTrafficStatisticsEntry 51 }

gs2328pPortTrafficTxDrops OBJECT-TYPE
   SYNTAX      Counter64
   MAX-ACCESS  read-only
   STATUS      current
   DESCRIPTION
       " "
   ::= { gs2328pPortTrafficStatisticsEntry 52 }

gs2328pPortTrafficTxLateOrExcColl OBJECT-TYPE
   SYNTAX      Counter64
   MAX-ACCESS  read-only
   STATUS      current
   DESCRIPTION
       " "
   ::= { gs2328pPortTrafficStatisticsEntry 53 }


gs2328pPortQoSStatistics                                     OBJECT IDENTIFIER ::= { gs2328pPort 3 }

gs2328pPortQoSStatisticsClear OBJECT-TYPE
   SYNTAX      INTEGER { none(0), clear(1) }
   MAX-ACCESS  read-only
   STATUS      current
   DESCRIPTION
       "default: 0
       0: none
       1: clear "
   ::= { gs2328pPortQoSStatistics 1 }

gs2328pPortQoSStatisticsTable OBJECT-TYPE
   SYNTAX      SEQUENCE OF GS2328PPortQoSStatisticsEntry
   MAX-ACCESS  not-accessible
   STATUS      current
   DESCRIPTION
       " "
   ::= { gs2328pPortQoSStatistics 2 }

gs2328pPortQoSStatisticsEntry OBJECT-TYPE
   SYNTAX      GS2328PPortQoSStatisticsEntry
   MAX-ACCESS  not-accessible
   STATUS      current
   DESCRIPTION
       ""
   INDEX    { gs2328pPortQoSStatisticsPort  }
   ::= { gs2328pPortQoSStatisticsTable 1 }

GS2328PPortQoSStatisticsEntry ::= SEQUENCE {
   gs2328pPortQoSStatisticsPort      Integer32,
   gs2328pPortQoSQ0Rx                Counter64,
   gs2328pPortQoSQ0Tx                Counter64,
   gs2328pPortQoSQ1Rx                Counter64,
   gs2328pPortQoSQ1Tx                Counter64,
   gs2328pPortQoSQ2Rx                Counter64,
   gs2328pPortQoSQ2Tx                Counter64,
   gs2328pPortQoSQ3Rx                Counter64,
   gs2328pPortQoSQ3Tx                Counter64,
   gs2328pPortQoSQ4Rx                Counter64,
   gs2328pPortQoSQ4Tx                Counter64,
   gs2328pPortQoSQ5Rx                Counter64,
   gs2328pPortQoSQ5Tx                Counter64,
   gs2328pPortQoSQ6Rx                Counter64,
   gs2328pPortQoSQ6Tx                Counter64,
   gs2328pPortQoSQ7Rx                Counter64,
   gs2328pPortQoSQ7Tx                Counter64
}

gs2328pPortQoSStatisticsPort OBJECT-TYPE
   SYNTAX      Integer32(1..4095)
   MAX-ACCESS  not-accessible
   STATUS      current
   DESCRIPTION
       " "
   ::= { gs2328pPortQoSStatisticsEntry 1 }

gs2328pPortQoSQ0Rx OBJECT-TYPE
   SYNTAX      Counter64
   MAX-ACCESS  read-only
   STATUS      current
   DESCRIPTION
       " "
   ::= { gs2328pPortQoSStatisticsEntry 2 }

gs2328pPortQoSQ0Tx OBJECT-TYPE
   SYNTAX      Counter64
   MAX-ACCESS  read-only
   STATUS      current
   DESCRIPTION
       " "
   ::= { gs2328pPortQoSStatisticsEntry 3 }

gs2328pPortQoSQ1Rx OBJECT-TYPE
   SYNTAX      Counter64
   MAX-ACCESS  read-only
   STATUS      current
   DESCRIPTION
       " "
   ::= { gs2328pPortQoSStatisticsEntry 4 }

gs2328pPortQoSQ1Tx OBJECT-TYPE
   SYNTAX      Counter64
   MAX-ACCESS  read-only
   STATUS      current
   DESCRIPTION
       " "
   ::= { gs2328pPortQoSStatisticsEntry 5 }

gs2328pPortQoSQ2Rx OBJECT-TYPE
   SYNTAX      Counter64
   MAX-ACCESS  read-only
   STATUS      current
   DESCRIPTION
       " "
   ::= { gs2328pPortQoSStatisticsEntry 6 }

gs2328pPortQoSQ2Tx OBJECT-TYPE
   SYNTAX      Counter64
   MAX-ACCESS  read-only
   STATUS      current
   DESCRIPTION
       " "
   ::= { gs2328pPortQoSStatisticsEntry 7 }

gs2328pPortQoSQ3Rx OBJECT-TYPE
   SYNTAX      Counter64
   MAX-ACCESS  read-only
   STATUS      current
   DESCRIPTION
       " "
   ::= { gs2328pPortQoSStatisticsEntry 8 }

gs2328pPortQoSQ3Tx OBJECT-TYPE
   SYNTAX      Counter64
   MAX-ACCESS  read-only
   STATUS      current
   DESCRIPTION
       " "
   ::= { gs2328pPortQoSStatisticsEntry 9 }

gs2328pPortQoSQ4Rx OBJECT-TYPE
   SYNTAX      Counter64
   MAX-ACCESS  read-only
   STATUS      current
   DESCRIPTION
       " "
   ::= { gs2328pPortQoSStatisticsEntry 10 }

gs2328pPortQoSQ4Tx OBJECT-TYPE
   SYNTAX      Counter64
   MAX-ACCESS  read-only
   STATUS      current
   DESCRIPTION
       " "
   ::= { gs2328pPortQoSStatisticsEntry 11 }

gs2328pPortQoSQ5Rx OBJECT-TYPE
   SYNTAX      Counter64
   MAX-ACCESS  read-only
   STATUS      current
   DESCRIPTION
       " "
   ::= { gs2328pPortQoSStatisticsEntry 12 }

gs2328pPortQoSQ5Tx OBJECT-TYPE
   SYNTAX      Counter64
   MAX-ACCESS  read-only
   STATUS      current
   DESCRIPTION
       " "
   ::= { gs2328pPortQoSStatisticsEntry 13 }

gs2328pPortQoSQ6Rx OBJECT-TYPE
   SYNTAX      Counter64
   MAX-ACCESS  read-only
   STATUS      current
   DESCRIPTION
       " "
   ::= { gs2328pPortQoSStatisticsEntry 14 }

gs2328pPortQoSQ6Tx OBJECT-TYPE
   SYNTAX      Counter64
   MAX-ACCESS  read-only
   STATUS      current
   DESCRIPTION
       " "
   ::= { gs2328pPortQoSStatisticsEntry 15 }

gs2328pPortQoSQ7Rx OBJECT-TYPE
   SYNTAX      Counter64
   MAX-ACCESS  read-only
   STATUS      current
   DESCRIPTION
       " "
   ::= { gs2328pPortQoSStatisticsEntry 16 }

gs2328pPortQoSQ7Tx OBJECT-TYPE
   SYNTAX      Counter64
   MAX-ACCESS  read-only
   STATUS      current
   DESCRIPTION
       " "
   ::= { gs2328pPortQoSStatisticsEntry 17 }

gs2328pSFPInfoTable OBJECT-TYPE
   SYNTAX      SEQUENCE OF GS2328PSFPInfoEntry
   MAX-ACCESS  not-accessible
   STATUS      current
   DESCRIPTION
       " "
   ::= { gs2328pPort 4 }

gs2328pSFPInfoEntry OBJECT-TYPE
   SYNTAX      GS2328PSFPInfoEntry
   MAX-ACCESS  not-accessible
   STATUS      current
   DESCRIPTION
       ""
   INDEX    { gs2328pSFPInfoIndex }
   ::= { gs2328pSFPInfoTable 1 }

GS2328PSFPInfoEntry ::= SEQUENCE {
   gs2328pSFPInfoIndex               Integer32,
   gs2328pSFPInfoPort                DisplayString,
   gs2328pSFPConnectorType           DisplayString,
   gs2328pSFPFiberType               DisplayString,
   gs2328pSFPTxCentralWavelength     DisplayString,
   gs2328pSFPBaudRate                DisplayString,
   gs2328pSFPVendorOUI               DisplayString,
   gs2328pSFPVendorName              DisplayString,
   gs2328pSFPVendorPN                DisplayString,
   gs2328pSFPVendorRev               DisplayString,
   gs2328pSFPVendorSN                DisplayString,
   gs2328pSFPDateCode                DisplayString,
   gs2328pSFPTemperature             DisplayString,
   gs2328pSFPVcc                     DisplayString,
   gs2328pSFPMon1Bias                DisplayString,
   gs2328pSFPMon2TxPWR               DisplayString,
   gs2328pSFPMon3RxPWR               DisplayString
}

gs2328pSFPInfoIndex OBJECT-TYPE
   SYNTAX      Integer32(1..4095)
   MAX-ACCESS  not-accessible
   STATUS      current
   DESCRIPTION
       " "
   ::= { gs2328pSFPInfoEntry 1 }

gs2328pSFPInfoPort OBJECT-TYPE
   SYNTAX      DisplayString
   MAX-ACCESS  read-only
   STATUS      current
   DESCRIPTION
       " "
   ::= { gs2328pSFPInfoEntry 2 }

gs2328pSFPConnectorType OBJECT-TYPE
   SYNTAX      DisplayString
   MAX-ACCESS  read-only
   STATUS      current
   DESCRIPTION
       " "
   ::= { gs2328pSFPInfoEntry 3 }

gs2328pSFPFiberType OBJECT-TYPE
   SYNTAX      DisplayString
   MAX-ACCESS  read-only
   STATUS      current
   DESCRIPTION
       " "
   ::= { gs2328pSFPInfoEntry 4 }

gs2328pSFPTxCentralWavelength OBJECT-TYPE
   SYNTAX      DisplayString
   MAX-ACCESS  read-only
   STATUS      current
   DESCRIPTION
       " "
   ::= { gs2328pSFPInfoEntry 5 }

gs2328pSFPBaudRate OBJECT-TYPE
   SYNTAX      DisplayString
   MAX-ACCESS  read-only
   STATUS      current
   DESCRIPTION
       " "
   ::= { gs2328pSFPInfoEntry 6 }

gs2328pSFPVendorOUI OBJECT-TYPE
   SYNTAX      DisplayString
   MAX-ACCESS  read-only
   STATUS      current
   DESCRIPTION
       " "
   ::= { gs2328pSFPInfoEntry 7 }

gs2328pSFPVendorName OBJECT-TYPE
   SYNTAX      DisplayString
   MAX-ACCESS  read-only
   STATUS      current
   DESCRIPTION
       " "
   ::= { gs2328pSFPInfoEntry 8 }

gs2328pSFPVendorPN OBJECT-TYPE
   SYNTAX      DisplayString
   MAX-ACCESS  read-only
   STATUS      current
   DESCRIPTION
       " "
   ::= { gs2328pSFPInfoEntry 9 }

gs2328pSFPVendorRev OBJECT-TYPE
   SYNTAX      DisplayString
   MAX-ACCESS  read-only
   STATUS      current
   DESCRIPTION
       " "
   ::= { gs2328pSFPInfoEntry 10 }

gs2328pSFPVendorSN OBJECT-TYPE
   SYNTAX      DisplayString
   MAX-ACCESS  read-only
   STATUS      current
   DESCRIPTION
       " "
   ::= { gs2328pSFPInfoEntry 11 }

gs2328pSFPDateCode OBJECT-TYPE
   SYNTAX      DisplayString
   MAX-ACCESS  read-only
   STATUS      current
   DESCRIPTION
       " "
   ::= { gs2328pSFPInfoEntry 12 }

gs2328pSFPTemperature OBJECT-TYPE
   SYNTAX      DisplayString
   MAX-ACCESS  read-only
   STATUS      current
   DESCRIPTION
       " "
   ::= { gs2328pSFPInfoEntry 13 }

gs2328pSFPVcc OBJECT-TYPE
   SYNTAX      DisplayString
   MAX-ACCESS  read-only
   STATUS      current
   DESCRIPTION
       " "
   ::= { gs2328pSFPInfoEntry 14 }
   
gs2328pSFPMon1Bias OBJECT-TYPE
   SYNTAX      DisplayString
   MAX-ACCESS  read-only
   STATUS      current
   DESCRIPTION
       " "
   ::= { gs2328pSFPInfoEntry 15 }
   
gs2328pSFPMon2TxPWR OBJECT-TYPE
   SYNTAX      DisplayString
   MAX-ACCESS  read-only
   STATUS      current
   DESCRIPTION
       " "
   ::= { gs2328pSFPInfoEntry 16 }

gs2328pSFPMon3RxPWR OBJECT-TYPE
   SYNTAX      DisplayString
   MAX-ACCESS  read-only
   STATUS      current
   DESCRIPTION
       " "
   ::= { gs2328pSFPInfoEntry 17 }


gs2328pVoiceVLAN                                             OBJECT IDENTIFIER ::= { gs2328pConfiguration 2 }

gs2328pVoiceVLANConf                                         OBJECT IDENTIFIER ::= { gs2328pVoiceVLAN 1 }

gs2328pVoiceVLANMode OBJECT-TYPE
   SYNTAX      INTEGER { disable(0), enable(1) }
   MAX-ACCESS  read-write
   STATUS      current
   DESCRIPTION
       " Voice VLAN mode operation.
       default: 0,
       0: disable
       1: enable"
   ::= { gs2328pVoiceVLANConf 1 }

gs2328pVoiceVLANVLANId OBJECT-TYPE
   SYNTAX      Integer32(1..4094)
   MAX-ACCESS  read-write
   STATUS      current
   DESCRIPTION
       "Voice VLAN ID.
        default: 1000,
        range : 1-4094. "
   ::= { gs2328pVoiceVLANConf 2 }

gs2328pVoiceVLANAgingTime OBJECT-TYPE
   SYNTAX      Integer32(10..1000000)
   MAX-ACCESS  read-write
   STATUS      current
   DESCRIPTION
       " Voice VLAN secure learning aging time. 
         default: 86400,
         range : 10 - 10000000. "
   ::= { gs2328pVoiceVLANConf 3 }

gs2328pVoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2328pVoiceVLANConf 4 }


gs2328pVoiceVLANPortTable OBJECT-TYPE
   SYNTAX      SEQUENCE OF GS2328PVoiceVLANPortEntry
   MAX-ACCESS  not-accessible
   STATUS      current
   DESCRIPTION
       " Show Voice Vlan configuration. "
   ::= { gs2328pVoiceVLANConf 5 }

gs2328pVoiceVLANPortEntry OBJECT-TYPE
   SYNTAX      GS2328PVoiceVLANPortEntry
   MAX-ACCESS  not-accessible
   STATUS      current
   DESCRIPTION
       ""
   INDEX    { gs2328pVoiceVLANPort  }
   ::= { gs2328pVoiceVLANPortTable 1 }

GS2328PVoiceVLANPortEntry ::= SEQUENCE {
   gs2328pVoiceVLANPort                    Integer32,
   gs2328pVoiceVLANPortMode                INTEGER,
   gs2328pVoiceVLANPortSecurity            INTEGER,
   gs2328pVoiceVLANPortDiscoveryProtocol   INTEGER
}

gs2328pVoiceVLANPort OBJECT-TYPE
   SYNTAX      Integer32(1..4095)
   MAX-ACCESS  not-accessible
   STATUS      current
   DESCRIPTION
       " port, range : 1 - port number. "
   ::= { gs2328pVoiceVLANPortEntry 1 }

gs2328pVoiceVLANPortMode OBJECT-TYPE
   SYNTAX      INTEGER { disable(0), auto(1), forced(2) }
   MAX-ACCESS  read-write
   STATUS      current
   DESCRIPTION
       " Voice VLAN port mode.  
         default: 0,
         0: Disable (Disjoin from Voice VLAN.)
         1: Auto (Enable auto detect mode. It detects whether there is VoIP phone attached to the specific port and configures the Voice VLAN members automatically.)
         2: Forced (Force join to Voice VLAN.)"
   ::= { gs2328pVoiceVLANPortEntry 2 }

gs2328pVoiceVLANPortSecurity OBJECT-TYPE
   SYNTAX      INTEGER { disable(0), enable(1) }
   MAX-ACCESS  read-write
   STATUS      current
   DESCRIPTION
       " Voice VLAN port security mode. 
         default: 0,
         0: Disable (Disjoin from Voice VLAN.)
         1: enable ( Enable Voice VLAN security mode. When the function is
                     enabled, all non-telephone MAC address in Voice VLAN
                     will be blocked 10 seconds.)"
   ::= { gs2328pVoiceVLANPortEntry 3 }

gs2328pVoiceVLANPortDiscoveryProtocol OBJECT-TYPE
   SYNTAX      INTEGER { oui(0), lldp(1), both(2) }
   MAX-ACCESS  read-write
   STATUS      current
   DESCRIPTION
       " Voice VLAN port discovery protocol.  
         default: 0
         0: OUI (Detect telephony device by OUI address.)
         1: LLDP (Detect telephony device by LLDP.)
         2: Both (Both OUI and LLDP.) "
   ::= { gs2328pVoiceVLANPortEntry 4 }

gs2328pVoiceVLANSkipNAS OBJECT-TYPE
   SYNTAX      INTEGER { disable(0), enable(1) }
   MAX-ACCESS  read-write
   STATUS      current
   DESCRIPTION
       " Voice VLAN skip NAS mode. 
         default: 0,
         0: Disable (Do not skip NAS on Voice VLAN.)
         1: enable (Enable skipping of NAS on Voice VLAN. When the function is
                    enabled, authentication through the NAS module is not
                    applied to the Voice VLAN, but clients are allowed without
                    authentication.)"
   ::= { gs2328pVoiceVLANPortEntry 5 }


gs2328pVoiceVLANOUI                                          OBJECT IDENTIFIER ::= { gs2328pVoiceVLAN 2 }

gs2328pVoiceVLANOUICreate OBJECT-TYPE
   SYNTAX       INTEGER { none(0), create(1) }
   MAX-ACCESS   read-write
   STATUS       current
   DESCRIPTION
       "default: 0
        0 : None  (read only)
        1 : Create an OUI entry"
   ::= { gs2328pVoiceVLANOUI 1 }

gs2328pVoiceVLANOUITable OBJECT-TYPE
   SYNTAX      SEQUENCE OF GS2328PVoiceVLANOUIEntry
   MAX-ACCESS  not-accessible
   STATUS      current
   DESCRIPTION
       " Create Voice VLAN OUI entry. Modify OUI table will
         restart auto detect OUI process. "
   ::= { gs2328pVoiceVLANOUI 2 }

gs2328pVoiceVLANOUIEntry OBJECT-TYPE
   SYNTAX      GS2328PVoiceVLANOUIEntry
   MAX-ACCESS  not-accessible
   STATUS      current
   DESCRIPTION
       ""
   INDEX    { gs2328pVoiceVLANOUIIndex  }
   ::= { gs2328pVoiceVLANOUITable 1 }

GS2328PVoiceVLANOUIEntry ::= SEQUENCE {
   gs2328pVoiceVLANOUIIndex         Integer32,
   gs2328pVoiceVLANTelephonyOUI     OCTET STRING,
   gs2328pVoiceVLANDescription      DisplayString,
   gs2328pVoiceVLANOUIRowStatus     INTEGER
}

gs2328pVoiceVLANOUIIndex OBJECT-TYPE
   SYNTAX      Integer32(1..16)
   MAX-ACCESS  not-accessible
   STATUS      current
   DESCRIPTION
       " "
   ::= { gs2328pVoiceVLANOUIEntry 1 }

gs2328pVoiceVLANTelephonyOUI OBJECT-TYPE
   SYNTAX      OCTET STRING (SIZE (1..32))
   MAX-ACCESS  read-write
   STATUS      current
   DESCRIPTION
       "OUI address, format : 0a 1b 2c "
   ::= { gs2328pVoiceVLANOUIEntry 2 }

gs2328pVoiceVLANDescription OBJECT-TYPE
   SYNTAX      DisplayString (SIZE (1..32))
   MAX-ACCESS  read-write
   STATUS      current
   DESCRIPTION
       " Up to 32 characters describing OUI address. "
   ::= { gs2328pVoiceVLANOUIEntry 3 }

gs2328pVoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2328pVoiceVLANOUIEntry 4 }

gs2328pGARP                                                   OBJECT IDENTIFIER ::= { gs2328pConfiguration 3 }

gs2328pGARPConfTable OBJECT-TYPE
   SYNTAX      SEQUENCE OF GS2328PGARPConfEntry
   MAX-ACCESS  not-accessible
   STATUS      current
   DESCRIPTION
       " "
   ::= { gs2328pGARP 1 }

gs2328pGARPConfEntry OBJECT-TYPE
   SYNTAX      GS2328PGARPConfEntry
   MAX-ACCESS  not-accessible
   STATUS      current
   DESCRIPTION
       ""
   INDEX    { gs2328pGARPConfPort  }
   ::= { gs2328pGARPConfTable 1 }

GS2328PGARPConfEntry ::= SEQUENCE {
   gs2328pGARPConfPort           Integer32,
   gs2328pGARPJoinTimer          Integer32,
   gs2328pGARPLeaveTimer         Integer32,
   gs2328pGARPLeaveAllTimer      Integer32,
   gs2328pGARPApplicantion       INTEGER,
   gs2328pGARPAttributeType      INTEGER,
   gs2328pGARPApplicant          INTEGER
}

gs2328pGARPConfPort OBJECT-TYPE
   SYNTAX      Integer32(1..4095)
   MAX-ACCESS  not-accessible
   STATUS      current
   DESCRIPTION
       " "
   ::= { gs2328pGARPConfEntry 1 }

gs2328pGARPJoinTimer OBJECT-TYPE
   SYNTAX      Integer32(200..1000)
   MAX-ACCESS  read-write
   STATUS      current
   DESCRIPTION
       "default: 200, range : 200 - 1000 "
   ::= { gs2328pGARPConfEntry 2 }

gs2328pGARPLeaveTimer OBJECT-TYPE
   SYNTAX      Integer32(600..3000)
   MAX-ACCESS  read-write
   STATUS      current
   DESCRIPTION
       "default: 600 , range : 600 - 3000"
   ::= { gs2328pGARPConfEntry 3 }

gs2328pGARPLeaveAllTimer OBJECT-TYPE
   SYNTAX      Integer32(10000..50000)
   MAX-ACCESS  read-write
   STATUS      current
   DESCRIPTION
       "default: 10000, range : 10000 - 50000 "
   ::= { gs2328pGARPConfEntry 4 }

gs2328pGARPApplicantion OBJECT-TYPE
   SYNTAX      INTEGER { gvrp(1)}
   MAX-ACCESS  read-write
   STATUS      current
   DESCRIPTION
       "default: 1
       1: GVRP"
   ::= { gs2328pGARPConfEntry 5 }

gs2328pGARPAttributeType OBJECT-TYPE
   SYNTAX      INTEGER { vlan(1)}
   MAX-ACCESS  read-write
   STATUS      current
   DESCRIPTION
       "default: 1
       1: VLAN"
   ::= { gs2328pGARPConfEntry 6 }

gs2328pGARPApplicant OBJECT-TYPE
   SYNTAX      INTEGER { participant(0), nonParticipant(1) }
   MAX-ACCESS  read-write
   STATUS      current
   DESCRIPTION
       "default: 0
       0: normal-participant
       1: non-participant"
   ::= { gs2328pGARPConfEntry 7 }

gs2328pGARPStatisticsTable OBJECT-TYPE
   SYNTAX      SEQUENCE OF GS2328PGARPStatisticsEntry
   MAX-ACCESS  not-accessible
   STATUS      current
   DESCRIPTION
       " Show the basic GARP port statistics. "
   ::= { gs2328pGARP 2 }

gs2328pGARPStatisticsEntry OBJECT-TYPE
   SYNTAX      GS2328PGARPStatisticsEntry
   MAX-ACCESS  not-accessible
   STATUS      current
   DESCRIPTION
       ""
   INDEX    { gs2328pGARPStatisticsPort  }
   ::= { gs2328pGARPStatisticsTable 1 }

GS2328PGARPStatisticsEntry ::= SEQUENCE {
   gs2328pGARPStatisticsPort             Integer32,
   gs2328pGARPStatisticsPeerMAC          DisplayString,
   gs2328pGARPStatisticsFailedCount      Counter32
}

gs2328pGARPStatisticsPort OBJECT-TYPE
   SYNTAX      Integer32(1..4095)
   MAX-ACCESS  not-accessible
   STATUS      current
   DESCRIPTION
       " port, range : 1 - port number. "
   ::= { gs2328pGARPStatisticsEntry 1 }

gs2328pGARPStatisticsPeerMAC OBJECT-TYPE
   SYNTAX      DisplayString
   MAX-ACCESS  read-only
   STATUS      current
   DESCRIPTION
       " Peer MAC is MAC address of the neighbour Switch from with GARP frame is received.  "
   ::= { gs2328pGARPStatisticsEntry 2 }

gs2328pGARPStatisticsFailedCount OBJECT-TYPE
   SYNTAX      Counter32
   MAX-ACCESS  read-only
   STATUS      current
   DESCRIPTION
       " explain Failed count here. "
   ::= { gs2328pGARPStatisticsEntry 3 }

gs2328pGVRP                                                   OBJECT IDENTIFIER ::= { gs2328pConfiguration 4 }

gs2328pGVRPConf                                                   OBJECT IDENTIFIER ::= { gs2328pGVRP 1 }

gs2328pGVRPMode OBJECT-TYPE
   SYNTAX      INTEGER { disable(0), enable(1) }
   MAX-ACCESS  read-write
   STATUS      current
   DESCRIPTION
       "default: 0,
        0: disable, 
        1: enable. "
   ::= { gs2328pGVRPConf 1 }

gs2328pGVRPConfTable OBJECT-TYPE
   SYNTAX      SEQUENCE OF GS2328PGVRPConfEntry
   MAX-ACCESS  not-accessible
   STATUS      current
   DESCRIPTION
       " "
   ::= { gs2328pGVRPConf 2 }

gs2328pGVRPConfEntry OBJECT-TYPE
   SYNTAX      GS2328PGVRPConfEntry
   MAX-ACCESS  not-accessible
   STATUS      current
   DESCRIPTION
       ""
   INDEX    { gs2328pGVRPConfPort  }
   ::= { gs2328pGVRPConfTable 1 }

GS2328PGVRPConfEntry ::= SEQUENCE {
   gs2328pGVRPConfPort           Integer32,
   gs2328pGVRPConfPortMode       INTEGER,
   gs2328pGVRPConfPortRRole      INTEGER
}

gs2328pGVRPConfPort OBJECT-TYPE
   SYNTAX      Integer32(1..4095)
   MAX-ACCESS  not-accessible
   STATUS      current
   DESCRIPTION
       " "
   ::= { gs2328pGVRPConfEntry 1 }

gs2328pGVRPConfPortMode OBJECT-TYPE
   SYNTAX      INTEGER { disable(0), enable(1) }
   MAX-ACCESS  read-write
   STATUS      current
   DESCRIPTION
       "default: 0
       1: enable
       0: disable"
   ::= { gs2328pGVRPConfEntry 2 }

gs2328pGVRPConfPortRRole OBJECT-TYPE
   SYNTAX      INTEGER { disable(0), enable(1) }
   MAX-ACCESS  read-write
   STATUS      current
   DESCRIPTION
       "default: 0
       1: enable
       0: disable"
   ::= { gs2328pGVRPConfEntry 3 }

gs2328pGVRPStatisticsTable OBJECT-TYPE
   SYNTAX      SEQUENCE OF GS2328PGVRPStatisticsEntry
   MAX-ACCESS  not-accessible
   STATUS      current
   DESCRIPTION
       " "
   ::= { gs2328pGVRP 2 }

gs2328pGVRPStatisticsEntry OBJECT-TYPE
   SYNTAX      GS2328PGVRPStatisticsEntry
   MAX-ACCESS  not-accessible
   STATUS      current
   DESCRIPTION
       ""
   INDEX    { gs2328pGVRPStatisticsPort  }
   ::= { gs2328pGVRPStatisticsTable 1 }

GS2328PGVRPStatisticsEntry ::= SEQUENCE {
   gs2328pGVRPStatisticsPort         Integer32,
   gs2328pGVRPStatisticsJoinTxCnt    Counter32,
   gs2328pGVRPStatisticsLeaveTxCnt   Counter32
}

gs2328pGVRPStatisticsPort OBJECT-TYPE
   SYNTAX      Integer32(1..4095)
   MAX-ACCESS  not-accessible
   STATUS      current
   DESCRIPTION
       " "
   ::= { gs2328pGVRPStatisticsEntry 1 }

gs2328pGVRPStatisticsJoinTxCnt OBJECT-TYPE
   SYNTAX      Counter32
   MAX-ACCESS  read-only
   STATUS      current
   DESCRIPTION
       ""
   ::= { gs2328pGVRPStatisticsEntry 2 }

gs2328pGVRPStatisticsLeaveTxCnt OBJECT-TYPE
   SYNTAX      Counter32
   MAX-ACCESS  read-only
   STATUS      current
   DESCRIPTION
       ""
   ::= { gs2328pGVRPStatisticsEntry 3 }


gs2328pMirroring                                             OBJECT IDENTIFIER ::= { gs2328pConfiguration 6 }

gs2328pPortToMirrorOn OBJECT-TYPE
   SYNTAX      Integer32(0..10)
   MAX-ACCESS  read-write
   STATUS      current
   DESCRIPTION
       "default: 0 
        0: disable,
        range : 1 - port number. "
   ::= { gs2328pMirroring 1 }

gs2328pMirrorTable OBJECT-TYPE
   SYNTAX      SEQUENCE OF GS2328PMirrorEntry
   MAX-ACCESS  not-accessible
   STATUS      current
   DESCRIPTION
       " "
   ::= { gs2328pMirroring 2 }

gs2328pMirrorEntry OBJECT-TYPE
   SYNTAX      GS2328PMirrorEntry
   MAX-ACCESS  not-accessible
   STATUS      current
   DESCRIPTION
       ""
   INDEX    { gs2328pMirrorPort  }
   ::= { gs2328pMirrorTable 1 }

GS2328PMirrorEntry ::= SEQUENCE {
   gs2328pMirrorPort		Integer32,
   gs2328pMirrorMode		INTEGER
}

gs2328pMirrorPort OBJECT-TYPE
   SYNTAX      Integer32(1..4095)
   MAX-ACCESS  not-accessible
   STATUS      current
   DESCRIPTION
       " "
   ::= { gs2328pMirrorEntry 1 }

gs2328pMirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2328pMirrorEntry 2 }

gs2328pTrapEventSeverity                                             OBJECT IDENTIFIER ::= { gs2328pConfiguration 7 }

gs2328pTrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 1 }

gs2328pTrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2328pTrapEventSeverity 2 }

gs2328pTrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 3 }

gs2328pTrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328pTrapEventSeverity 4 }

gs2328pTrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328pTrapEventSeverity 5 }

gs2328pTrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 6 }

gs2328pTrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 7 }

gs2328pTrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 8 }

gs2328pTrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 9 }

gs2328pTrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328pTrapEventSeverity 10 }

gs2328pTrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 11 }

gs2328pTrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 12 }

gs2328pTrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 13 }

gs2328pTrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 14 }

gs2328pTrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2328pTrapEventSeverity 15 }

gs2328pTrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 16 }

gs2328pTrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 17 }

gs2328pTrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 18 }

gs2328pTrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2328pTrapEventSeverity 20 }

gs2328pTrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328pTrapEventSeverity 21 }

gs2328pTrapEventSeverityPoEAutoCheck OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328pTrapEventSeverity 22 }

gs2328pTrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328pTrapEventSeverity 25 }

gs2328pTrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328pTrapEventSeverity 27 }
   
gs2328pTrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2328pTrapEventSeverity 28 }

gs2328pSMTP                                             OBJECT IDENTIFIER ::= { gs2328pConfiguration 8 }

gs2328pSMTPMailServer OBJECT-TYPE
   SYNTAX      DisplayString
   MAX-ACCESS  read-write
   STATUS      current
   DESCRIPTION
       " Up to 47 characters describing email server. "
   ::= { gs2328pSMTP 1 }

gs2328pSMTPUserName OBJECT-TYPE
   SYNTAX      DisplayString
   MAX-ACCESS  read-write
   STATUS      current
   DESCRIPTION
       " Up to 47 characters describing user name. "
   ::= { gs2328pSMTP 2 }

gs2328pSMTPPassword OBJECT-TYPE
   SYNTAX      DisplayString
   MAX-ACCESS  read-write
   STATUS      current
   DESCRIPTION
       " Up to 47 characters describing password. "
   ::= { gs2328pSMTP 3 }

gs2328pSMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2328pSMTP 4 }

gs2328pSMTPSender OBJECT-TYPE
   SYNTAX      DisplayString
   MAX-ACCESS  read-write
   STATUS      current
   DESCRIPTION
       " Up to 47 characters describing sender. "
   ::= { gs2328pSMTP 5 }

gs2328pSMTPReturnPath OBJECT-TYPE
   SYNTAX      DisplayString
   MAX-ACCESS  read-write
   STATUS      current
   DESCRIPTION
       " Up to 47 characters describing return path. "
   ::= { gs2328pSMTP 6 }

gs2328pSMTPEmailAddress1 OBJECT-TYPE
   SYNTAX      DisplayString
   MAX-ACCESS  read-write
   STATUS      current
   DESCRIPTION
       " Up to 47 characters describing mail address. "
   ::= { gs2328pSMTP 7 }

gs2328pSMTPEmailAddress2 OBJECT-TYPE
   SYNTAX      DisplayString
   MAX-ACCESS  read-write
   STATUS      current
   DESCRIPTION
       " Up to 47 characters describing mail address. "
   ::= { gs2328pSMTP 8 }

gs2328pSMTPEmailAddress3 OBJECT-TYPE
   SYNTAX      DisplayString
   MAX-ACCESS  read-write
   STATUS      current
   DESCRIPTION
       " Up to 47 characters describing mail address. "
   ::= { gs2328pSMTP 9 }

gs2328pSMTPEmailAddress4 OBJECT-TYPE
   SYNTAX      DisplayString
   MAX-ACCESS  read-write
   STATUS      current
   DESCRIPTION
       " Up to 47 characters describing mail address. "
   ::= { gs2328pSMTP 10 }

gs2328pSMTPEmailAddress5 OBJECT-TYPE
   SYNTAX      DisplayString
   MAX-ACCESS  read-write
   STATUS      current
   DESCRIPTION
       " Up to 47 characters describing mail address. "
   ::= { gs2328pSMTP 11 }

gs2328pSMTPEmailAddress6 OBJECT-TYPE
   SYNTAX      DisplayString
   MAX-ACCESS  read-write
   STATUS      current
   DESCRIPTION
       " Up to 47 characters describing mail address. "
   ::= { gs2328pSMTP 12 }


gs2328pACL                                                   OBJECT IDENTIFIER ::= { gs2328pConfiguration 9 }

gs2328pACLPortsConfTable OBJECT-TYPE
   SYNTAX      SEQUENCE OF GS2328PACLPortsConfEntry
   MAX-ACCESS  not-accessible
   STATUS      current
   DESCRIPTION
       " "
   ::= { gs2328pACL 1 }

gs2328pACLPortsConfEntry OBJECT-TYPE
   SYNTAX      GS2328PACLPortsConfEntry
   MAX-ACCESS  not-accessible
   STATUS      current
   DESCRIPTION
       ""
   INDEX    { gs2328pACLPortsConfPort  }
   ::= { gs2328pACLPortsConfTable 1 }

GS2328PACLPortsConfEntry ::= SEQUENCE {
   gs2328pACLPortsConfPort               Integer32,
   gs2328pACLPortsConfPolicyID           Integer32,
   gs2328pACLPortsConfAction             INTEGER,
   gs2328pACLPortsConfRateLimiterID      Integer32,
   gs2328pACLPortsConfPortRedirect       Integer32,
   gs2328pACLPortsConfMirror             INTEGER,
   gs2328pACLPortsConfLogging            INTEGER,
   gs2328pACLPortsConfShutdown           INTEGER,
   gs2328pACLPortsConfState              INTEGER,
   gs2328pACLPortsConfCounter            Counter32
}

gs2328pACLPortsConfPort OBJECT-TYPE
   SYNTAX      Integer32 (1..4095)
   MAX-ACCESS  not-accessible
   STATUS      current
   DESCRIPTION
       " "
   ::= { gs2328pACLPortsConfEntry 1 }

gs2328pACLPortsConfPolicyID OBJECT-TYPE
   SYNTAX      Integer32 (0..255)
   MAX-ACCESS  read-write
   STATUS      current
   DESCRIPTION
       "default: 0, range : 0 - 255 "
   ::= { gs2328pACLPortsConfEntry 2 }

gs2328pACLPortsConfAction OBJECT-TYPE
   SYNTAX      INTEGER { deny(0), permit(1) }
   MAX-ACCESS  read-write
   STATUS      current
   DESCRIPTION
       "default: 1,
        0: Deny
        1: Permit"
   ::= { gs2328pACLPortsConfEntry 3 }

gs2328pACLPortsConfRateLimiterID OBJECT-TYPE
   SYNTAX      Integer32 (0..12)
   MAX-ACCESS  read-write
   STATUS      current
   DESCRIPTION
       "default: 0,
        0: Disable
        range : 0 - 12 "
   ::= { gs2328pACLPortsConfEntry 4 }

gs2328pACLPortsConfPortRedirect OBJECT-TYPE
   SYNTAX      Integer32 (0..4095)
   MAX-ACCESS  read-write
   STATUS      current
   DESCRIPTION
       "default: 0
        0: Disable
        range : 0 - end port number "
   ::= { gs2328pACLPortsConfEntry 5 }

gs2328pACLPortsConfMirror OBJECT-TYPE
   SYNTAX      INTEGER { disable(0), enable(1) }
   MAX-ACCESS  read-write
   STATUS      current
   DESCRIPTION
       "default: 0
        0: Disable
        1: Enable "
   ::= { gs2328pACLPortsConfEntry 6 }

gs2328pACLPortsConfLogging OBJECT-TYPE
   SYNTAX      INTEGER { disable(0), enable(1) }
   MAX-ACCESS  read-write
   STATUS      current
   DESCRIPTION
       "default: 0
        0: Disable
        1: Enable "
   ::= { gs2328pACLPortsConfEntry 7 }

gs2328pACLPortsConfShutdown OBJECT-TYPE
   SYNTAX      INTEGER { disable(0), enable(1) }
   MAX-ACCESS  read-write
   STATUS      current
   DESCRIPTION
       "default: 0
        0: Disable
        1: Enable "
   ::= { gs2328pACLPortsConfEntry 8 }
   
gs2328pACLPortsConfState OBJECT-TYPE
   SYNTAX      INTEGER { disable(0), enable(1) }
   MAX-ACCESS  read-write
   STATUS      current
   DESCRIPTION
       "default: 1
        0: Disable
        1: Enable "
   ::= { gs2328pACLPortsConfEntry 9 }

gs2328pACLPortsConfCounter OBJECT-TYPE
   SYNTAX      Counter32
   MAX-ACCESS  read-only
   STATUS      current
   DESCRIPTION
       "Counts the number of frames that match this ACE. "
   ::= { gs2328pACLPortsConfEntry 10 }


gs2328pACLRateLimiterTable OBJECT-TYPE
   SYNTAX      SEQUENCE OF GS2328PACLRateLimiterEntry
   MAX-ACCESS  not-accessible
   STATUS      current
   DESCRIPTION
       " "
   ::= { gs2328pACL 2 }

gs2328pACLRateLimiterEntry OBJECT-TYPE
   SYNTAX      GS2328PACLRateLimiterEntry
   MAX-ACCESS  not-accessible
   STATUS      current
   DESCRIPTION
       ""
   INDEX    { gs2328pACLRateLimiterID  }
   ::= { gs2328pACLRateLimiterTable 1 }

GS2328PACLRateLimiterEntry ::= SEQUENCE {
   gs2328pACLRateLimiterID       Integer32,
   gs2328pACLRateLimiterUnit     INTEGER,
   gs2328pACLRateLimiterRate     Integer32
}

gs2328pACLRateLimiterID OBJECT-TYPE
   SYNTAX      Integer32 (1..12)
   MAX-ACCESS  not-accessible
   STATUS      current
   DESCRIPTION
       " Rate Limiter ID.
         range : 1-12 "
   ::= { gs2328pACLRateLimiterEntry 1 }

gs2328pACLRateLimiterUnit OBJECT-TYPE
   SYNTAX      INTEGER { pps(0), kbps(1) }
   MAX-ACCESS  read-write
   STATUS      current
   DESCRIPTION
       "default: 0, 
        0: pps
        1: kbps"
   ::= { gs2328pACLRateLimiterEntry 2 }

gs2328pACLRateLimiterRate OBJECT-TYPE
   SYNTAX      Integer32(0..3276700)
   MAX-ACCESS  read-write
   STATUS      current
   DESCRIPTION
       "default: 1, 
        range : <0-3276700> pps
                <0-10000> kbps"
   ::= { gs2328pACLRateLimiterEntry 3 }


gs2328pACLACE                                          OBJECT IDENTIFIER ::= { gs2328pACL 3 }

gs2328pACLACECreate OBJECT-TYPE
   SYNTAX       INTEGER { none(0), create(1) }
   MAX-ACCESS   read-write
   STATUS       current
   DESCRIPTION
       "default: 0
        0 : None  (read only)
        1 : Create an ACE entry"
   ::= { gs2328pACLACE 1 }

gs2328pACLACETable OBJECT-TYPE
   SYNTAX      SEQUENCE OF GS2328PACLACEEntry
   MAX-ACCESS  not-accessible
   STATUS      current
   DESCRIPTION
       " Create ACL ACE entry. "
   ::= { gs2328pACLACE 2 }

gs2328pACLACEEntry OBJECT-TYPE
   SYNTAX      GS2328PACLACEEntry
   MAX-ACCESS  not-accessible
   STATUS      current
   DESCRIPTION
       ""
   INDEX    { gs2328pACLACEIndex  }
   ::= { gs2328pACLACETable 1 }

GS2328PACLACEEntry ::= SEQUENCE {
   gs2328pACLACEIndex                Integer32,
   gs2328pACLACEID                   Integer32,
   gs2328pACLACENextID               Integer32,
   gs2328pACLACEIngressPort          DisplayString,
   gs2328pACLACEPortPolicyNumber     Integer32,
   
   gs2328pACLACEPortPolicyBitmask    Integer32,
   gs2328pACLACEFrameType            INTEGER,
   gs2328pACLACEAction               INTEGER,
   gs2328pACLACEDenyPortRedirect     DisplayString,
   gs2328pACLACELogging              INTEGER,
   
   gs2328pACLACEMirror               INTEGER,
   gs2328pACLACERateLimiter          Integer32,
   gs2328pACLACEShutdown             INTEGER,
   gs2328pACLACEVLAN8021QTagged      INTEGER,
   gs2328pACLACEVLANTagPriority      Integer32,
   
   gs2328pACLACEVLANVID              Integer32,
   gs2328pACLACEEtherType            Integer32,
   gs2328pACLACESMAC                 DisplayString,
   gs2328pACLACEDMACType             INTEGER,
   gs2328pACLACEDMAC                 DisplayString,
   
   gs2328pACLACEArpOpcode            INTEGER,
   gs2328pACLACEArpFlagsRequestReply INTEGER,
   gs2328pACLACEArpFlagsArpSmac      INTEGER,
   gs2328pACLACEArpFlagsRarpDmac     INTEGER,
   gs2328pACLACEArpFlagsLength       INTEGER,
   
   gs2328pACLACEArpFlagsIp           INTEGER,
   gs2328pACLACEArpFlagsEthernet     INTEGER,
   gs2328pACLACESIPType              INTEGER,
   gs2328pACLACESIPIPAddress         IpAddress,                      
   gs2328pACLACESIPNetworkPrefix     Integer32,
   
   gs2328pACLACEDIPType              INTEGER,
   gs2328pACLACEDIPIPAddress         IpAddress,                      
   gs2328pACLACEDIPNetworkPrefix     Integer32,
   
   gs2328pACLACEIPProtocol           Integer32,
   gs2328pACLACEIPFlagsTTL           INTEGER,
   gs2328pACLACEIPFlagsOptions       INTEGER,
   gs2328pACLACEIPFlagsFragment      INTEGER,
   gs2328pACLACEICMPType             Integer32,
   
   gs2328pACLACEICMPCode             Integer32,
   gs2328pACLACESourcePortMin        Integer32,
   gs2328pACLACESourcePortMax        Integer32,
   gs2328pACLACEDestPortMin          Integer32,
   gs2328pACLACEDestPortMax          Integer32,
   
   gs2328pACLACETCPFlagsFin          INTEGER,
   gs2328pACLACETCPFlagsSyn          INTEGER,
   gs2328pACLACETCPFlagsRst          INTEGER,
   gs2328pACLACETCPFlagsPsh          INTEGER,
   gs2328pACLACETCPFlagsAck          INTEGER,
   
   gs2328pACLACETCPFlagsUrg          INTEGER,
   
   gs2328pACLACERowStatus            INTEGER
}

gs2328pACLACEIndex OBJECT-TYPE
   SYNTAX      Integer32(1..256)
   MAX-ACCESS  not-accessible
   STATUS      current
   DESCRIPTION
       " "
   ::= { gs2328pACLACEEntry 1 }

gs2328pACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2328pACLACEEntry 2 }

gs2328pACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2328pACLACEEntry 3 }

gs2328pACLACEIngressPort OBJECT-TYPE
   SYNTAX      DisplayString
   MAX-ACCESS  read-write
   STATUS      current
   DESCRIPTION
       " Indicates the ingress port of the ACE. Possible values are: 
         All: The ACE will match all ingress port. 
         Port: The ACE will match a specific ingress port.Format: 1,3,6."
   ::= { gs2328pACLACEEntry 4 }

gs2328pACLACEPortPolicyNumber OBJECT-TYPE
   SYNTAX      Integer32(0..255)
   MAX-ACCESS  read-write
   STATUS      current
   DESCRIPTION
       " policy value.
         range : 0 - 255. "
   ::= { gs2328pACLACEEntry 5 }
   
gs2328pACLACEPortPolicyBitmask OBJECT-TYPE
   SYNTAX      Integer32(0..255)
   MAX-ACCESS  read-write
   STATUS      current
   DESCRIPTION
       " policy bitmask.
         range : 0 - 255(0xff). "
   ::= { gs2328pACLACEEntry 6 }

gs2328pACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2328pACLACEEntry 7 }

gs2328pACLACEAction OBJECT-TYPE
   SYNTAX      INTEGER { deny(0), permit(1) }
   MAX-ACCESS  read-write
   STATUS      current
   DESCRIPTION
       "default: 1,
        0: Deny
        1: Permit"
   ::= { gs2328pACLACEEntry 8 }

gs2328pACLACEDenyPortRedirect OBJECT-TYPE
   SYNTAX      DisplayString
   MAX-ACCESS  read-write
   STATUS      current
   DESCRIPTION
       " Frames that hit the ACE are redirected to the port number specified here.  
         Disabled: indicates that the port redirect operation is disabled. 
         Port Format: 1,3,6."
   ::= { gs2328pACLACEEntry 9 }

gs2328pACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2328pACLACEEntry 10 }

gs2328pACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { gs2328pACLACEEntry 11 }

gs2328pACLACERateLimiter OBJECT-TYPE
   SYNTAX      Integer32(0..12)
   MAX-ACCESS  read-write
   STATUS      current
   DESCRIPTION
       "default: 0,
        0: Disable
        range : 0 - 12 "
   ::= { gs2328pACLACEEntry 12 }

gs2328pACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2328pACLACEEntry 13 }

gs2328pACLACEVLAN8021QTagged OBJECT-TYPE
   SYNTAX      INTEGER { disable(0), enable(1), any(2) }
   MAX-ACCESS  read-write
   STATUS      current
   DESCRIPTION
       "Specify whether frames can hit the action according to the 802.1Q tagged. 
        default: 2,
        0: disable - Untagged frame only.
        1: enable - Tagged frame only.
        2: Any - Any value is allowed. "
   ::= { gs2328pACLACEEntry 14 }

gs2328pACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2328pACLACEEntry 15 }

gs2328pACLACEVLANVID OBJECT-TYPE
   SYNTAX      Integer32(0..4094)
   MAX-ACCESS  read-write
   STATUS      current
   DESCRIPTION
       "Specify the VLAN ID filter for this ACE.
        The vid can't be set when 802.1Q Tagged is disabled. 
        default: 0,
        0: Any - No VLAN ID filter is specified.
        range : 0 - 4094 "
   ::= { gs2328pACLACEEntry 16 }

gs2328pACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2328pACLACEEntry 17 }

gs2328pACLACESMAC OBJECT-TYPE
   SYNTAX      DisplayString
   MAX-ACCESS  read-write
   STATUS      current
   DESCRIPTION
       " Configure source MAC address for this ACE.
         <mac-address>: A frame that hits this ACE matches this source MAC address value. 
         Any: Don't care."
   ::= { gs2328pACLACEEntry 18 }

gs2328pACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { gs2328pACLACEEntry 19 }

gs2328pACLACEDMAC OBJECT-TYPE
   SYNTAX      DisplayString
   MAX-ACCESS  read-write
   STATUS      current
   DESCRIPTION
       " Configure destination MAC address for this ACE. 
         <mac-address>: A frame that hits this ACE matches this destination MAC address value.            
         Any: Don't care.
         Broadcast: Frame must be broadcast.
         Unicast: Frame must be unicast.
         Multicast: Frame must be multicast. "
   ::= { gs2328pACLACEEntry 20 }

gs2328pACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2328pACLACEEntry 21 }

gs2328pACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2328pACLACEEntry 22 }

gs2328pACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2328pACLACEEntry 23 }   

gs2328pACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2328pACLACEEntry 24 }

gs2328pACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2328pACLACEEntry 25 }

gs2328pACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2328pACLACEEntry 26 }

gs2328pACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2328pACLACEEntry 27 }
   
gs2328pACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { gs2328pACLACEEntry 28 }   
   
gs2328pACLACESIPIPAddress OBJECT-TYPE
   SYNTAX      IpAddress
   MAX-ACCESS  read-write
   STATUS      current
   DESCRIPTION
       "A frame that hits this ACE matches this source IP address value."
   ::= { gs2328pACLACEEntry 29 }      
   
gs2328pACLACESIPNetworkPrefix OBJECT-TYPE
   SYNTAX      Integer32(0..32)
   MAX-ACCESS  read-write
   STATUS      current
   DESCRIPTION
       "Network prefix.
        default: 32,
        0: No data.
        range : 1 - 32"
   ::= { gs2328pACLACEEntry 30 }   
   

gs2328pACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2328pACLACEEntry 32 }   
   
gs2328pACLACEDIPIPAddress OBJECT-TYPE
   SYNTAX      IpAddress
   MAX-ACCESS  read-write
   STATUS      current
   DESCRIPTION
       "A frame that hits this ACE matches this destination IP address value."
   ::= { gs2328pACLACEEntry 33 }      
   
gs2328pACLACEDIPNetworkPrefix OBJECT-TYPE
   SYNTAX      Integer32(0..32)
   MAX-ACCESS  read-write
   STATUS      current
   DESCRIPTION
       "Network prefix.
        default: 32,
        0: No data.
        range : 1 - 32"
   ::= { gs2328pACLACEEntry 34 }  
   
   
gs2328pACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { gs2328pACLACEEntry 36 } 

gs2328pACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2328pACLACEEntry 37 }   
   
gs2328pACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2328pACLACEEntry 38 }

gs2328pACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2328pACLACEEntry 39 }

gs2328pACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { gs2328pACLACEEntry 40 }   

gs2328pACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2328pACLACEEntry 41 } 

gs2328pACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2328pACLACEEntry 42 }     
   
gs2328pACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2328pACLACEEntry 43 } 
      
gs2328pACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { gs2328pACLACEEntry 44 }     

gs2328pACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { gs2328pACLACEEntry 45 }

gs2328pACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2328pACLACEEntry 46 }

gs2328pACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2328pACLACEEntry 47 }

gs2328pACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2328pACLACEEntry 48 }

gs2328pACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2328pACLACEEntry 49 }

gs2328pACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2328pACLACEEntry 50 }

gs2328pACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2328pACLACEEntry 51 }

gs2328pACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2328pACLACEEntry 66 }


gs2328pACLACEClear OBJECT-TYPE
   SYNTAX       INTEGER { noAction(0), clear(1) }
   MAX-ACCESS   read-write
   STATUS       current
   DESCRIPTION
       "default: 0
        0 : No action
        1 : Clear all ACL counters."
   ::= { gs2328pACLACE 3 }

gs2328pACLACEMoveACEID OBJECT-TYPE
   SYNTAX       Integer32(0..256)
   MAX-ACCESS   read-write
   STATUS       current
   DESCRIPTION
       "Move ACE,
        default: 0
        ACE ID must be exist.
        range : 1 - 256."
   ::= { gs2328pACLACE 4 }

gs2328pACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2328pACLACE 5 }

gs2328pACLACEStatusTable OBJECT-TYPE
   SYNTAX      SEQUENCE OF GS2328PACLACEStatusEntry
   MAX-ACCESS  not-accessible
   STATUS      current
   DESCRIPTION
       " ACL ACE Status entry. "
   ::= { gs2328pACLACE 6 }

gs2328pACLACEStatusEntry OBJECT-TYPE
   SYNTAX      GS2328PACLACEStatusEntry
   MAX-ACCESS  not-accessible
   STATUS      current
   DESCRIPTION
       ""
   INDEX    { gs2328pACLACEStatusIndex  }
   ::= { gs2328pACLACEStatusTable 1 }

GS2328PACLACEStatusEntry ::= SEQUENCE {
   gs2328pACLACEStatusIndex          Integer32,
   gs2328pACLACEStatusUser           DisplayString,
   gs2328pACLACEStatusID             Integer32,
   gs2328pACLACEStatusIngressPort    DisplayString,
   gs2328pACLACEStatusFrameType      DisplayString,
   gs2328pACLACEStatusAction         DisplayString,
   gs2328pACLACEStatusRateLimiter    DisplayString,
   gs2328pACLACEStatusPortCopy       DisplayString,
   gs2328pACLACEStatusMirror         DisplayString,
   gs2328pACLACEStatusCPU            DisplayString,
   gs2328pACLACEStatusCounter        Counter32,
   gs2328pACLACEStatusConflict       DisplayString
}

gs2328pACLACEStatusIndex OBJECT-TYPE
   SYNTAX      Integer32(1..256)
   MAX-ACCESS  not-accessible
   STATUS      current
   DESCRIPTION
       " "
   ::= { gs2328pACLACEStatusEntry 1 }

gs2328pACLACEStatusUser OBJECT-TYPE
   SYNTAX      DisplayString
   MAX-ACCESS  read-only
   STATUS      current
   DESCRIPTION
       " Indicates the ACL user. 
         S : Static.  
         IPMG : IP Management.  
         IPSG : IP Source Guard.  
         IPMC : IPMC.  
         ARPI : Arp Inspection.  
         UPnP : UPnP.  
         DHCP : DHCP. "
   ::= { gs2328pACLACEStatusEntry 2 }

gs2328pACLACEStatusID OBJECT-TYPE
   SYNTAX      Integer32(1..256)
   MAX-ACCESS  read-only
   STATUS      current
   DESCRIPTION
       " ACE ID.
         range : 1 - 256. "
   ::= { gs2328pACLACEStatusEntry 3 }

gs2328pACLACEStatusIngressPort OBJECT-TYPE
   SYNTAX      DisplayString
   MAX-ACCESS  read-only
   STATUS      current
   DESCRIPTION
       " Indicates the ingress port of the ACE. Possible values are: 
         All: The ACE will match all ingress port. 
         Port: The ACE will match a specific ingress port. "
   ::= { gs2328pACLACEStatusEntry 4 }

gs2328pACLACEStatusFrameType OBJECT-TYPE
   SYNTAX      DisplayString
   MAX-ACCESS  read-only
   STATUS      current
   DESCRIPTION
       " Indicates the frame type of the ACE. "
   ::= { gs2328pACLACEStatusEntry 5 }

gs2328pACLACEStatusAction OBJECT-TYPE
   SYNTAX      DisplayString
   MAX-ACCESS  read-only
   STATUS      current
   DESCRIPTION
       " Indicates the forwarding action of the ACE. "
   ::= { gs2328pACLACEStatusEntry 6 }

gs2328pACLACEStatusRateLimiter OBJECT-TYPE
   SYNTAX      DisplayString
   MAX-ACCESS  read-only
   STATUS      current
   DESCRIPTION
       " Indicates the rate limiter number of the ACE. "
   ::= { gs2328pACLACEStatusEntry 7 }

gs2328pACLACEStatusPortCopy OBJECT-TYPE
   SYNTAX      DisplayString
   MAX-ACCESS  read-only
   STATUS      current
   DESCRIPTION
       " Indicates the port redirect operation of the ACE. Frames matching the ACE are redirected to the port number. "
   ::= { gs2328pACLACEStatusEntry 8 }

gs2328pACLACEStatusMirror OBJECT-TYPE
   SYNTAX      DisplayString
   MAX-ACCESS  read-only
   STATUS      current
   DESCRIPTION
       " Specify the mirror operation of this port. "
   ::= { gs2328pACLACEStatusEntry 9 }

gs2328pACLACEStatusCPU OBJECT-TYPE
   SYNTAX      DisplayString
   MAX-ACCESS  read-only
   STATUS      current
   DESCRIPTION
       " Forward packet that matched the specific ACE to CPU. "
   ::= { gs2328pACLACEStatusEntry 10 }

gs2328pACLACEStatusCounter OBJECT-TYPE
   SYNTAX      Counter32
   MAX-ACCESS  read-only
   STATUS      current
   DESCRIPTION
       " The counter indicates the number of times the ACE was hit by a frame. "
   ::= { gs2328pACLACEStatusEntry 11 }
   
gs2328pACLACEStatusConflict OBJECT-TYPE
   SYNTAX      DisplayString
   MAX-ACCESS  read-only
   STATUS      current
   DESCRIPTION
       " Indicates the hardware status of the specific ACE. The specific ACE is not applied to the hardware due to hardware limitations. "
   ::= { gs2328pACLACEStatusEntry 12 }

gs2328pLoopProtection                                                  OBJECT IDENTIFIER ::= { gs2328pConfiguration 12 }

gs2328pLoopProtectionConfig                                            OBJECT IDENTIFIER ::= { gs2328pLoopProtection 1 }

gs2328pLoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2328pLoopProtectionConfig 1 }
   
gs2328pLoopProtectionTranmisstionTime OBJECT-TYPE
   SYNTAX      Integer32(1..10)
   MAX-ACCESS  read-write
   STATUS      current
   DESCRIPTION
       "Configure loop protection transmit interval.
        default: 5,
        range: 1-10. "
   ::= { gs2328pLoopProtectionConfig 2 }
   
gs2328pLoopProtectionShutdownTime OBJECT-TYPE
   SYNTAX      Integer32(0..604800)
   MAX-ACCESS  read-write
   STATUS      current
   DESCRIPTION
       "Configure loop protection shutdown time.
        default: 180,
        range: 0-604800. "
   ::= { gs2328pLoopProtectionConfig 3 }

gs2328pLoopProtectionConfigurationTable OBJECT-TYPE
   SYNTAX      SEQUENCE OF GS2328PLoopProtectionConfigurationEntry
   MAX-ACCESS  not-accessible
   STATUS      current
   DESCRIPTION
       " Show Loop Protection configurations. "
   ::= { gs2328pLoopProtectionConfig 4 }

gs2328pLoopProtectionConfigurationEntry OBJECT-TYPE
   SYNTAX      GS2328PLoopProtectionConfigurationEntry
   MAX-ACCESS  not-accessible
   STATUS      current
   DESCRIPTION
       ""
   INDEX    { gs2328pLoopProtectionConfPort  }
   ::= { gs2328pLoopProtectionConfigurationTable 1 }

GS2328PLoopProtectionConfigurationEntry ::= SEQUENCE {
   gs2328pLoopProtectionConfPort	    Integer32,
   gs2328pLoopProtectionConfEnable	INTEGER,
   gs2328pLoopProtectionConfAction	INTEGER,
   gs2328pLoopProtectionConfTxmode	INTEGER
}

gs2328pLoopProtectionConfPort OBJECT-TYPE
   SYNTAX      Integer32(1..4095)
   MAX-ACCESS  not-accessible
   STATUS      current
   DESCRIPTION
       " port, range : 1 - port number. "
   ::= { gs2328pLoopProtectionConfigurationEntry 1 }

gs2328pLoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2328pLoopProtectionConfigurationEntry 2 }

gs2328pLoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2328pLoopProtectionConfigurationEntry 3 }
   
gs2328pLoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2328pLoopProtectionConfigurationEntry 4 }
   
gs2328pLoopProtectionStatusTable OBJECT-TYPE
   SYNTAX      SEQUENCE OF GS2328PLoopProtectionStatusEntry
   MAX-ACCESS  not-accessible
   STATUS      current
   DESCRIPTION
       " Show Loop Protection Status. "
   ::= { gs2328pLoopProtection 2 }

gs2328pLoopProtectionStatusEntry OBJECT-TYPE
   SYNTAX      GS2328PLoopProtectionStatusEntry
   MAX-ACCESS  not-accessible
   STATUS      current
   DESCRIPTION
       ""
   INDEX    { gs2328pLoopProtectionStatusPort  }
   ::= { gs2328pLoopProtectionStatusTable 1 }

GS2328PLoopProtectionStatusEntry ::= SEQUENCE {
   gs2328pLoopProtectionStatusPort	       Integer32,
   gs2328pLoopProtectionStatusAction	       DisplayString,
   gs2328pLoopProtectionStatusTransmit	   DisplayString,
   gs2328pLoopProtectionStatusLoops	       Integer32,
   gs2328pLoopProtectionStatusStatus	       DisplayString,
   gs2328pLoopProtectionStatusLoop	       DisplayString,
   gs2328pLoopProtectionStatusTimeLastLoop  DisplayString
}

gs2328pLoopProtectionStatusPort OBJECT-TYPE
   SYNTAX      Integer32(1..4095)
   MAX-ACCESS  not-accessible
   STATUS      current
   DESCRIPTION
       " port, range : 1 - port number. "
   ::= { gs2328pLoopProtectionStatusEntry 1 }
   
gs2328pLoopProtectionStatusAction OBJECT-TYPE
   SYNTAX      DisplayString
   MAX-ACCESS  read-only
   STATUS      current
   DESCRIPTION
       " The currently configured port action. "
   ::= { gs2328pLoopProtectionStatusEntry 2 }
   
gs2328pLoopProtectionStatusTransmit OBJECT-TYPE
   SYNTAX      DisplayString
   MAX-ACCESS  read-only
   STATUS      current
   DESCRIPTION
       " The currently configured port transmit mode. "
   ::= { gs2328pLoopProtectionStatusEntry 3 }
   
gs2328pLoopProtectionStatusLoops OBJECT-TYPE
   SYNTAX      Integer32(0..1000000)
   MAX-ACCESS  read-only
   STATUS      current
   DESCRIPTION
       " The number of loops detected on this port. "
   ::= { gs2328pLoopProtectionStatusEntry 4 }
   
gs2328pLoopProtectionStatusStatus OBJECT-TYPE
   SYNTAX      DisplayString
   MAX-ACCESS  read-only
   STATUS      current
   DESCRIPTION
       " The current loop protection status of the port. "
   ::= { gs2328pLoopProtectionStatusEntry 5 }
   
gs2328pLoopProtectionStatusLoop OBJECT-TYPE
   SYNTAX      DisplayString
   MAX-ACCESS  read-only
   STATUS      current
   DESCRIPTION
       " Whether a loop is currently detected on the port. "
   ::= { gs2328pLoopProtectionStatusEntry 6 }

gs2328pLoopProtectionStatusTimeLastLoop OBJECT-TYPE
   SYNTAX      DisplayString
   MAX-ACCESS  read-only
   STATUS      current
   DESCRIPTION
       " The time of the last loop event detected. "
   ::= { gs2328pLoopProtectionStatusEntry 7 }

gs2328pPoe                                                           OBJECT IDENTIFIER ::= { gs2328pConfiguration 13 }

gs2328pPoeStatus                                            OBJECT IDENTIFIER ::= { gs2328pPoe 1 }

gs2328pPoeStatusTable OBJECT-TYPE
   SYNTAX      SEQUENCE OF GS2328PPoeStatusEntry
   MAX-ACCESS  not-accessible
   STATUS      current
   DESCRIPTION
       " Configure PoE Scheduling Table. "
   ::= { gs2328pPoeStatus 1 }

gs2328pPoeStatusEntry OBJECT-TYPE
   SYNTAX      GS2328PPoeStatusEntry
   MAX-ACCESS  not-accessible
   STATUS      current
   DESCRIPTION
       ""
   INDEX    { gs2328pPoeStatusLocalPort }
   ::= { gs2328pPoeStatusTable 1 }

GS2328PPoeStatusEntry ::= SEQUENCE {
   gs2328pPoeStatusLocalPort	        Integer32,
   gs2328pPoeStatusPDclass	        INTEGER,
   gs2328pPoeStatusPowerRequested	    DisplayString,
   gs2328pPoeStatusPowerAllocated     DisplayString,
   gs2328pPoeStatusPowerUsed          DisplayString,
   gs2328pPoeStatusCurrentUsed        DisplayString,
   gs2328pPoeStatusPriority           DisplayString,
   gs2328pPoeStatusPortStatus         DisplayString
}

gs2328pPoeStatusLocalPort OBJECT-TYPE
   SYNTAX      Integer32(1..4094)
   MAX-ACCESS  not-accessible
   STATUS      current
   DESCRIPTION
       " port, range : 1 - port number. "
   ::= { gs2328pPoeStatusEntry 1}

gs2328pPoeStatusPDclass OBJECT-TYPE
   SYNTAX      INTEGER (0..4)
   MAX-ACCESS  read-only
   STATUS      current
   DESCRIPTION
       " Indicates the QCL user.
         0: Max. power 15.4 W,
         1: Max. power 4.0 W,
         2: Max. power 7.0 W,
         3: Max. power 15.4 W,
         4: Max. power 30.0 W. "
   ::= { gs2328pPoeStatusEntry 2 }

gs2328pPoeStatusPowerRequested OBJECT-TYPE
   SYNTAX      DisplayString
   MAX-ACCESS  read-only
   STATUS      current
   DESCRIPTION
      " The Power Requested shows the requested amount of power the PD wants to be reserved. "
   ::= { gs2328pPoeStatusEntry 3}

gs2328pPoeStatusPowerAllocated OBJECT-TYPE
   SYNTAX      DisplayString
   MAX-ACCESS  read-only
   STATUS      current
   DESCRIPTION
      " The Power Allocated shows the amount of power the switch has allocated for the PD. "
   ::= { gs2328pPoeStatusEntry 4}

gs2328pPoeStatusPowerUsed OBJECT-TYPE
   SYNTAX      DisplayString
   MAX-ACCESS  read-only
   STATUS      current
   DESCRIPTION
      " The Power Used shows how much power the PD currently is using. "
   ::= { gs2328pPoeStatusEntry 5}

gs2328pPoeStatusCurrentUsed OBJECT-TYPE
   SYNTAX      DisplayString
   MAX-ACCESS  read-only
   STATUS      current
   DESCRIPTION
      " The Power Used shows how much current the PD currently is using. "
   ::= { gs2328pPoeStatusEntry 6}

gs2328pPoeStatusPriority OBJECT-TYPE
   SYNTAX      DisplayString
   MAX-ACCESS  read-only
   STATUS      current
   DESCRIPTION
      " The Priority shows the port's priority configured by the user.  "
   ::= { gs2328pPoeStatusEntry 7}

gs2328pPoeStatusPortStatus OBJECT-TYPE
   SYNTAX      DisplayString
   MAX-ACCESS  read-only
   STATUS      current
   DESCRIPTION
      " The Port Status shows the port's status.  "
   ::= { gs2328pPoeStatusEntry 8}


gs2328pPoeStatusTotalPowerRequested OBJECT-TYPE
   SYNTAX      DisplayString
   MAX-ACCESS  read-only
   STATUS      current
   DESCRIPTION
      " Total Power Requested."
   ::= { gs2328pPoeStatus 2}

gs2328pPoeStatusTotalPowerAllocated OBJECT-TYPE
   SYNTAX      DisplayString
   MAX-ACCESS  read-only
   STATUS      current
   DESCRIPTION
      " Total Power allocated."
   ::= { gs2328pPoeStatus 3}

gs2328pPoeStatusTotalPowerUsed OBJECT-TYPE
   SYNTAX      DisplayString
   MAX-ACCESS  read-only
   STATUS      current
   DESCRIPTION
      " Total Power Used."
   ::= { gs2328pPoeStatus 4}

gs2328pPoeStatusTotalCurrentUsed OBJECT-TYPE
   SYNTAX      DisplayString
   MAX-ACCESS  read-only
   STATUS      current
   DESCRIPTION
      " Total Current Used."
   ::= { gs2328pPoeStatus 5}

gs2328pPoeMcuVersion OBJECT-TYPE
   SYNTAX      DisplayString
   MAX-ACCESS  read-only
   STATUS      current
   DESCRIPTION
      " PoE MCU version."
   ::= { gs2328pPoeStatus 6 }

gs2328pPoePowerDelay                                                 OBJECT IDENTIFIER ::= { gs2328pPoe 2 }

gs2328pPoePowerDelayTable OBJECT-TYPE
   SYNTAX      SEQUENCE OF GS2328PPoePowerDelayEntry
   MAX-ACCESS  not-accessible
   STATUS      current
   DESCRIPTION
       " Configure PoE Power Delay mode. "
   ::= { gs2328pPoePowerDelay 1 }

gs2328pPoePowerDelayEntry OBJECT-TYPE
   SYNTAX      GS2328PPoePowerDelayEntry
   MAX-ACCESS  not-accessible
   STATUS      current
   DESCRIPTION
       ""
   INDEX    { gs2328pPoePowerDelayPort  }
   ::= { gs2328pPoePowerDelayTable 1 }

GS2328PPoePowerDelayEntry ::= SEQUENCE {
   gs2328pPoePowerDelayPort	        Integer32,
   gs2328pPoePowerDelayMode	        INTEGER,
   gs2328pPoePowerDelayTime         Integer32
}

gs2328pPoePowerDelayPort OBJECT-TYPE
   SYNTAX      Integer32(1..4094)
   MAX-ACCESS  not-accessible
   STATUS      current
   DESCRIPTION
       " port, range : 1 - port number. "
   ::= { gs2328pPoePowerDelayEntry 1 }

gs2328pPoePowerDelayMode OBJECT-TYPE
   SYNTAX      INTEGER { disable(0), enable(1) }
   MAX-ACCESS  read-write
   STATUS      current
   DESCRIPTION
       "Turn on / off the power delay function,
        0: disable,
        1: enable,
        default: disable. "
   ::= { gs2328pPoePowerDelayEntry 2 }
   
gs2328pPoePowerDelayTime OBJECT-TYPE
   SYNTAX      Integer32(0..300)
   MAX-ACCESS  read-write
   STATUS      current
   DESCRIPTION
       "set Delay Time,
        default: 0,
        range: 0-300 sec. "
   ::= { gs2328pPoePowerDelayEntry 3 }
   
gs2328pPoeAutoCheck                                                 OBJECT IDENTIFIER ::= { gs2328pPoe 3 }

gs2328pPoeAutoCheckPingCheck OBJECT-TYPE
   SYNTAX      INTEGER { disable(0), enable(1) }
   MAX-ACCESS  read-write
   STATUS      current
   DESCRIPTION
       "connection between PoE port and power device.
        0: disable,
        1: enable,
        default: disable. "
   ::= { gs2328pPoeAutoCheck 1 }

gs2328pPoeAutoCheckTable OBJECT-TYPE
   SYNTAX      SEQUENCE OF GS2328PPoeAutoCheckEntry
   MAX-ACCESS  not-accessible
   STATUS      current
   DESCRIPTION
       " Configure PoE Power Delay mode. "
   ::= { gs2328pPoeAutoCheck 2 }

gs2328pPoeAutoCheckEntry OBJECT-TYPE
   SYNTAX      GS2328PPoeAutoCheckEntry
   MAX-ACCESS  not-accessible
   STATUS      current
   DESCRIPTION
       ""
   INDEX    { gs2328pPoeAutoCheckPort  }
   ::= { gs2328pPoeAutoCheckTable 1 }

GS2328PPoeAutoCheckEntry ::= SEQUENCE {
   gs2328pPoeAutoCheckPort	       Integer32,
   gs2328pPoeAutoCheckPingIPAddress  DisplayString,
   gs2328pPoeAutoCheckIntervalTime   Integer32,
   gs2328pPoeAutoCheckRetryTime      Integer32,
   gs2328pPoeAutoCheckFailureLog     DisplayString,
   gs2328pPoeAutoCheckFailureAction  INTEGER,
   gs2328pPoeAutoCheckRebootTime     Integer32
}

gs2328pPoeAutoCheckPort OBJECT-TYPE
   SYNTAX      Integer32(1..4094)
   MAX-ACCESS  not-accessible
   STATUS      current
   DESCRIPTION
       " port, range : 1 - port number. "
   ::= { gs2328pPoeAutoCheckEntry 1 }

gs2328pPoeAutoCheckPingIPAddress OBJECT-TYPE
   SYNTAX      DisplayString
   MAX-ACCESS  read-write
   STATUS      current
   DESCRIPTION
       "IP Address the system should ping.
        default: 0.0.0.0 . "
   ::= { gs2328pPoeAutoCheckEntry 2 }

gs2328pPoeAutoCheckIntervalTime OBJECT-TYPE
   SYNTAX      Integer32(10..120)
   MAX-ACCESS  read-write
   STATUS      current
   DESCRIPTION
       "Device will send checking message to PD each interval time.
        default: 30,
        range: 10-120 sec.  "
   ::= { gs2328pPoeAutoCheckEntry 3 }

gs2328pPoeAutoCheckRetryTime OBJECT-TYPE
   SYNTAX      Integer32(1..5)
   MAX-ACCESS  read-write
   STATUS      current
   DESCRIPTION
       "It will retry to send detection again.
        default: 3,
        range: 1-5.  "
   ::= { gs2328pPoeAutoCheckEntry 4 }
   
gs2328pPoeAutoCheckFailureLog OBJECT-TYPE
   SYNTAX      DisplayString
   MAX-ACCESS  read-only
   STATUS      current
   DESCRIPTION
       "Failure loggings counter. "
   ::= { gs2328pPoeAutoCheckEntry 5 }
   
gs2328pPoeAutoCheckFailureAction OBJECT-TYPE
   SYNTAX      INTEGER { nothing(0), reboot(1) }
   MAX-ACCESS  read-write
   STATUS      current
   DESCRIPTION
       "It will retry to send detection again,
        0: Nothing,
        1: Reboot Remote PD,
        default: Nothing. "
   ::= { gs2328pPoeAutoCheckEntry 6 }
   
gs2328pPoeAutoCheckRebootTime OBJECT-TYPE
   SYNTAX      Integer32(3..120)
   MAX-ACCESS  read-write
   STATUS      current
   DESCRIPTION
       "When PD has been rebooted, the PoE port restored power after the specified time.
        default: 15,
        range: 3-120 sec. "
   ::= { gs2328pPoeAutoCheckEntry 7 }

gs2328pPoeScheduling                                                 OBJECT IDENTIFIER ::= { gs2328pPoe 4 }

gs2328pPoeSchedulingTable OBJECT-TYPE
   SYNTAX      SEQUENCE OF GS2328PPoeSchedulingEntry
   MAX-ACCESS  not-accessible
   STATUS      current
   DESCRIPTION
       " Configure PoE Scheduling Table. "
   ::= { gs2328pPoeScheduling 1 }

gs2328pPoeSchedulingEntry OBJECT-TYPE
   SYNTAX      GS2328PPoeSchedulingEntry
   MAX-ACCESS  not-accessible
   STATUS      current
   DESCRIPTION
       ""
   INDEX    { gs2328pPoeSchedulingPort }
   ::= { gs2328pPoeSchedulingTable 1 }

GS2328PPoeSchedulingEntry ::= SEQUENCE {
   gs2328pPoeSchedulingPort	        Integer32,
   gs2328pPoeSchedulingStatus	        INTEGER
}

gs2328pPoeSchedulingPort OBJECT-TYPE
   SYNTAX      Integer32(1..4094)
   MAX-ACCESS  not-accessible
   STATUS      current
   DESCRIPTION
       " port, range : 1 - port number. "
   ::= { gs2328pPoeSchedulingEntry 1 }

gs2328pPoeSchedulingStatus OBJECT-TYPE
   SYNTAX      INTEGER { disable(0), enable(1) }
   MAX-ACCESS  read-write
   STATUS      current
   DESCRIPTION
       "PoE Scheduling Status.
        0: Disable,
        1: Enable,
        default: Disable. "
   ::= { gs2328pPoeSchedulingEntry 2 }

gs2328pPoeSchedulingTimeTable OBJECT-TYPE
   SYNTAX      SEQUENCE OF GS2328PPoeSchedulingTimeEntry
   MAX-ACCESS  not-accessible
   STATUS      current
   DESCRIPTION
       " Show Poe Scheduling Time Config. "
   ::= { gs2328pPoeScheduling 2 }

gs2328pPoeSchedulingTimeEntry OBJECT-TYPE
   SYNTAX      GS2328PPoeSchedulingTimeEntry
   MAX-ACCESS  not-accessible
   STATUS      current
   DESCRIPTION
       ""
   INDEX    { gs2328pPoeSchedulingTimePort, gs2328pPoeSchedulingTimeWeek, gs2328pPoeSchedulingTimeHour  }
   ::= { gs2328pPoeSchedulingTimeTable 1 }

GS2328PPoeSchedulingTimeEntry ::= SEQUENCE {
   gs2328pPoeSchedulingTimePort		Integer32,
   gs2328pPoeSchedulingTimeWeek		INTEGER,
   gs2328pPoeSchedulingTimeHour		Integer32,
   gs2328pPoeSchedulingProvidePower	INTEGER
}

gs2328pPoeSchedulingTimePort OBJECT-TYPE
   SYNTAX      Integer32(1..4095)
   MAX-ACCESS  not-accessible
   STATUS      current
   DESCRIPTION
       " port, range : 1 - port number. "
   ::= { gs2328pPoeSchedulingTimeEntry 1 }

gs2328pPoeSchedulingTimeWeek OBJECT-TYPE
   SYNTAX      INTEGER {
                        monday(1),
                        tuseday(2),
                        wednesday(3),
                        thursday(4),
                        friday(5),
                        saturday(6),
                        sunday(7)
                        }
   MAX-ACCESS  not-accessible
   STATUS      current
   DESCRIPTION
       " range: 1-7, 
         Sunday:7, Monday:1, Tuseday:2, Wednesday:3, Thursday:4, Friday:5, Saturday:6.  "
   ::= { gs2328pPoeSchedulingTimeEntry 2 }

gs2328pPoeSchedulingTimeHour OBJECT-TYPE
   SYNTAX      Integer32(1..24)
   MAX-ACCESS  not-accessible
   STATUS      current
   DESCRIPTION
       " range: 1-24,
         24: hour 0, 1: hour 1, 2: hour2..."
   ::= { gs2328pPoeSchedulingTimeEntry 3 }

gs2328pPoeSchedulingProvidePower OBJECT-TYPE
   SYNTAX      INTEGER { disable(0), enable(1) }
   MAX-ACCESS  read-write
   STATUS      current
   DESCRIPTION
       " 0: disable,
         1: enable,
         default: disable.  "
   ::= { gs2328pPoeSchedulingTimeEntry 4 }

gs2328pPoeConfiguration                                                 OBJECT IDENTIFIER ::= { gs2328pPoe 5 }

gs2328pPoeConfigurationPrimaryPowerSupply  OBJECT-TYPE
   SYNTAX      Integer32(0..1000)
   MAX-ACCESS  read-only
   STATUS      current
   DESCRIPTION
       "It must be defined what amount of power the primary and backup power sources
        can deliver. "
   ::= { gs2328pPoeConfiguration 1 }

gs2328pPoeConfigurationRetryTime OBJECT-TYPE
   SYNTAX      Integer32(0|5|10|20|30|40|50|60)
   MAX-ACCESS  read-write
   STATUS      current
   DESCRIPTION
       "The period (in seconds) for trying to turn on an overloaded PoE port.
        0: disable,
        5 sec,10 sec,20 sec,30 sec,40 sec,50 sec,60 sec,
        default: 60 sec. "
   ::= { gs2328pPoeConfiguration 2 }

gs2328pPoeConfigurationTable OBJECT-TYPE
   SYNTAX      SEQUENCE OF GS2328PPoeConfigurationEntry
   MAX-ACCESS  not-accessible
   STATUS      current
   DESCRIPTION
       " Configure PoE Configuration mode. "
   ::= { gs2328pPoeConfiguration 3 }

gs2328pPoeConfigurationEntry OBJECT-TYPE
   SYNTAX      GS2328PPoeConfigurationEntry
   MAX-ACCESS  not-accessible
   STATUS      current
   DESCRIPTION
       ""
   INDEX    { gs2328pPoeConfigurationPort  }
   ::= { gs2328pPoeConfigurationTable 1 }

GS2328PPoeConfigurationEntry ::= SEQUENCE {
   gs2328pPoeConfigurationPort	       Integer32,
   gs2328pPoeConfigurationPoEMode       INTEGER,
   gs2328pPoeConfigurationPriority      INTEGER,
   gs2328pPoeConfigurationMaximumPower  DisplayString,
   gs2328pPoeConfigurationDetection     INTEGER,
   gs2328pPoeConfigurationReset         INTEGER
}

gs2328pPoeConfigurationPort OBJECT-TYPE
   SYNTAX      Integer32(1..4094)
   MAX-ACCESS  not-accessible
   STATUS      current
   DESCRIPTION
       " port, range : 1 - port number. "
   ::= { gs2328pPoeConfigurationEntry 1 }

gs2328pPoeConfigurationPoEMode OBJECT-TYPE
   SYNTAX      INTEGER { disable(0), enable(1) }
   MAX-ACCESS  read-write
   STATUS      current
   DESCRIPTION
       "The PoE Mode represents the PoE operating mode for the port.
        0: Disable,
        1: Enable,
        default: Enable. "
   ::= { gs2328pPoeConfigurationEntry 2 }

gs2328pPoeConfigurationPriority OBJECT-TYPE
   SYNTAX      INTEGER { low(0), high(1), critical(2) }
   MAX-ACCESS  read-write
   STATUS      current
   DESCRIPTION
       "The Priority represents the ports priority. There are three levels of power priority named Low, High and Critical.
        0: Low,
        1: High,
        2: Critical,
        default: Low.  "
   ::= { gs2328pPoeConfigurationEntry 3 }

gs2328pPoeConfigurationMaximumPower OBJECT-TYPE
   SYNTAX      DisplayString
   MAX-ACCESS  read-write
   STATUS      current
   DESCRIPTION
       "The Maximum Power value contains a numerical value that indicates the maximum
        power in watts that can be delivered to a remote device.
        default: 15.4[W],
        max: 30[W]. "
   ::= { gs2328pPoeConfigurationEntry 4 }

gs2328pPoeConfigurationDetection OBJECT-TYPE
   SYNTAX      INTEGER(0..5)
   MAX-ACCESS  read-write
   STATUS      current
   DESCRIPTION
       "Configure PoE port capacitor detection.
        0: No Detection(read only),
        1: legacy,
        2: 4-point,
        3: 4-point-legacy,
        4: 2-point,
        5: 2-point-legacy, 
        default: 4-point. "
   ::= { gs2328pPoeConfigurationEntry 5 }

gs2328pPoeConfigurationReset OBJECT-TYPE
   SYNTAX      INTEGER { disable(0), enable(1) }
   MAX-ACCESS  read-write
   STATUS      current
   DESCRIPTION
       "Reset the specific PoE port.
        0: Disable,
        1: Enable,
        default: Disable. "
   ::= { gs2328pPoeConfigurationEntry 6 }

gs2328pPoeConfigurationLegacyMode  OBJECT-TYPE
   SYNTAX      INTEGER { disable(0), enable(1) }
   MAX-ACCESS  read-write
   STATUS      current
   DESCRIPTION
       "Legacy Detection.
        0: Disable,
        1: Enable,
        default: Disable. "
   ::= { gs2328pPoeConfiguration 4 }


gs2328pQos                                                             OBJECT IDENTIFIER ::= { gs2328pConfiguration 14 }

gs2328pQosPortClassification                                           OBJECT IDENTIFIER ::= { gs2328pQos 1 }

gs2328pQosPortClassificationTable OBJECT-TYPE
   SYNTAX      SEQUENCE OF GS2328PQosPortClassificationEntry
   MAX-ACCESS  not-accessible
   STATUS      current
   DESCRIPTION
       " QoS Ingress Port Classification . "
   ::= { gs2328pQosPortClassification  1 }

gs2328pQosPortClassificationEntry OBJECT-TYPE
   SYNTAX      GS2328PQosPortClassificationEntry
   MAX-ACCESS  not-accessible
   STATUS      current
   DESCRIPTION
       ""
   INDEX    { gs2328pQosPortClassificationPort  }
   ::= { gs2328pQosPortClassificationTable 1 }

GS2328PQosPortClassificationEntry ::= SEQUENCE {
   gs2328pQosPortClassificationPort	        Integer32,
   gs2328pQosPortClassificationQoSclass       Integer32,
   gs2328pQosPortClassificationDPlevel	    Integer32,
   gs2328pQosPortClassificationPCP	        Integer32,
   gs2328pQosPortClassificationDEI	        INTEGER,
   gs2328pQosPortClassificationTagClass	    INTEGER,
   gs2328pQosPortClassificationDSCPBased    INTEGER,
   gs2328pQosPortClassificationAddressMode  INTEGER
}

gs2328pQosPortClassificationPort OBJECT-TYPE
   SYNTAX      Integer32(1..4095)
   MAX-ACCESS  not-accessible
   STATUS      current
   DESCRIPTION
       " port, range : 1 - port number. "
   ::= { gs2328pQosPortClassificationEntry 1 }

gs2328pQosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2328pQosPortClassificationEntry 2 }

gs2328pQosPortClassificationDPlevel OBJECT-TYPE
   SYNTAX      Integer32(0|1)
   MAX-ACCESS  read-write
   STATUS      current
   DESCRIPTION
       " DP level for frames not classified in any other way.
         range: 0-1,
         default: 0. "
   ::= { gs2328pQosPortClassificationEntry 3 }

gs2328pQosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2328pQosPortClassificationEntry 4 }

gs2328pQosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2328pQosPortClassificationEntry 5 }

gs2328pQosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2328pQosPortClassificationEntry 6 }

gs2328pQosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2328pQosPortClassificationEntry 7 }

gs2328pQosPortClassificationAddressMode OBJECT-TYPE
   SYNTAX      INTEGER { source(0), destination(1) }
   MAX-ACCESS  read-write
   STATUS      current
   DESCRIPTION
      "The IP/MAC address mode specifying whether the QCL classification
       must be based on source (SMAC/SIP) or destination (DMAC/DIP)
       addresses on this port.
        0: source,
        1: destination,
        default: source. "
   ::= { gs2328pQosPortClassificationEntry 8 }

gs2328pQoSIngressPortTagClassificationTable OBJECT-TYPE
   SYNTAX      SEQUENCE OF GS2328PQoSIngressPortTagClassificationEntry
   MAX-ACCESS  not-accessible
   STATUS      current
   DESCRIPTION
       " Show QoS Ingress Port Tag Classification. "
   ::= { gs2328pQosPortClassification 2 }

gs2328pQoSIngressPortTagClassificationEntry OBJECT-TYPE
   SYNTAX      GS2328PQoSIngressPortTagClassificationEntry
   MAX-ACCESS  not-accessible
   STATUS      current
   DESCRIPTION
       ""
   INDEX    { gs2328pQoSIngressPortTagClassificationPort, gs2328pQoSIngressPortTagPCP, gs2328pQoSIngressPortTagDEI  }
   ::= { gs2328pQoSIngressPortTagClassificationTable 1 }

GS2328PQoSIngressPortTagClassificationEntry ::= SEQUENCE {
   gs2328pQoSIngressPortTagClassificationPort	Integer32,
   gs2328pQoSIngressPortTagPCP					INTEGER,
   gs2328pQoSIngressPortTagDEI					INTEGER,
   gs2328pQoSIngressPortTagQosClass				Integer32,
   gs2328pQoSIngressPortTagDPLevel				Integer32
}

gs2328pQoSIngressPortTagClassificationPort OBJECT-TYPE
   SYNTAX      Integer32(1..4095)
   MAX-ACCESS  not-accessible
   STATUS      current
   DESCRIPTION
       " port, range : 1 - port number. "
   ::= { gs2328pQoSIngressPortTagClassificationEntry 1 }

gs2328pQoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8, 
         PCP0:1, PCP1:2...  "
   ::= { gs2328pQoSIngressPortTagClassificationEntry 2 }

gs2328pQoSIngressPortTagDEI OBJECT-TYPE
   SYNTAX      INTEGER { dei0(1), dei1(2) }
   MAX-ACCESS  not-accessible
   STATUS      current
   DESCRIPTION
       " range: 1-2,
         DEI0:1, DEI1:2. "
   ::= { gs2328pQoSIngressPortTagClassificationEntry 3 }

gs2328pQoSIngressPortTagQosClass OBJECT-TYPE
   SYNTAX      Integer32 (0..7)
   MAX-ACCESS  read-write
   STATUS      current
   DESCRIPTION
       " range: 0-7.  "
   ::= { gs2328pQoSIngressPortTagClassificationEntry 4 }
   
gs2328pQoSIngressPortTagDPLevel OBJECT-TYPE
   SYNTAX      Integer32 (0|1)
   MAX-ACCESS  read-write
   STATUS      current
   DESCRIPTION
       " range: 0-1.  "
   ::= { gs2328pQoSIngressPortTagClassificationEntry 5 }


gs2328pQosPortPolicingTable OBJECT-TYPE
   SYNTAX      SEQUENCE OF GS2328PQosPortPolicingEntry
   MAX-ACCESS  not-accessible
   STATUS      current
   DESCRIPTION
       "  configure the Policer settings for all switch ports. "
   ::= { gs2328pQos  2 }

gs2328pQosPortPolicingEntry OBJECT-TYPE
   SYNTAX      GS2328PQosPortPolicingEntry
   MAX-ACCESS  not-accessible
   STATUS      current
   DESCRIPTION
       ""
   INDEX    { gs2328pQosPortPolicingPort  }
   ::= { gs2328pQosPortPolicingTable 1 }

GS2328PQosPortPolicingEntry ::= SEQUENCE {
   gs2328pQosPortPolicingPort	        Integer32,
   gs2328pQosPortPolicingMode           INTEGER,
   gs2328pQosPortPolicingRate	        Integer32,
   gs2328pQosPortPolicingUnit	        INTEGER,
   gs2328pQosPortPolicingFlowControl	INTEGER
}

gs2328pQosPortPolicingPort OBJECT-TYPE
   SYNTAX      Integer32 (1..4095)
   MAX-ACCESS  not-accessible
   STATUS      current
   DESCRIPTION
       " port, range : 1 - port number. "
   ::= { gs2328pQosPortPolicingEntry 1 }

gs2328pQosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2328pQosPortPolicingEntry 2 }

gs2328pQosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2328pQosPortPolicingEntry 3 }

gs2328pQosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2328pQosPortPolicingEntry 4 }

gs2328pQosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2328pQosPortPolicingEntry 5 }

gs2328pQosPortScheduler                                           OBJECT IDENTIFIER ::= { gs2328pQos 3 }

gs2328pQosPortSchedulerModeTable OBJECT-TYPE
   SYNTAX      SEQUENCE OF GS2328PQosPortSchedulerModeEntry
   MAX-ACCESS  not-accessible
   STATUS      current
   DESCRIPTION
       " configure the basic QoS Port Scheduler Mode settings for all switch ports. "
   ::= { gs2328pQosPortScheduler  1 }

gs2328pQosPortSchedulerModeEntry OBJECT-TYPE
   SYNTAX      GS2328PQosPortSchedulerModeEntry
   MAX-ACCESS  not-accessible
   STATUS      current
   DESCRIPTION
       ""
   INDEX    { gs2328pQosSchedulerModePort  }
   ::= { gs2328pQosPortSchedulerModeTable 1 }

GS2328PQosPortSchedulerModeEntry ::= SEQUENCE {
   gs2328pQosSchedulerModePort	                Integer32,
   gs2328pQosSchedulerMode                        INTEGER,
   gs2328pQosSchedulerShaper	                    INTEGER,
   gs2328pQosSchedulerShaperRate	                Integer32
}

gs2328pQosSchedulerModePort OBJECT-TYPE
   SYNTAX      Integer32 (1..4095)
   MAX-ACCESS  not-accessible
   STATUS      current
   DESCRIPTION
       " port, range : 1 - port number. "
   ::= { gs2328pQosPortSchedulerModeEntry 1 }

gs2328pQosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2328pQosPortSchedulerModeEntry 2 }

gs2328pQosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2328pQosPortSchedulerModeEntry 3 }

gs2328pQosSchedulerShaperRate OBJECT-TYPE
   SYNTAX      Integer32(100..1000000)
   MAX-ACCESS  read-write
   STATUS      current
   DESCRIPTION
       " Controls the rate for the port shaper.
         range: 100-1000000
         default: 500 kbps. "
   ::= { gs2328pQosPortSchedulerModeEntry 4 }

gs2328pQosPortSchedulerTable OBJECT-TYPE
   SYNTAX      SEQUENCE OF GS2328PQosPortSchedulerEntry
   MAX-ACCESS  not-accessible
   STATUS      current
   DESCRIPTION
       " Show Qos Port Scheduler. "
   ::= { gs2328pQosPortScheduler 2 }

gs2328pQosPortSchedulerEntry OBJECT-TYPE
   SYNTAX      GS2328PQosPortSchedulerEntry
   MAX-ACCESS  not-accessible
   STATUS      current
   DESCRIPTION
       ""
   INDEX    { gs2328pQosSchedulerPort, gs2328pQosSchedulerPortQueue}
   ::= { gs2328pQosPortSchedulerTable 1 }

GS2328PQosPortSchedulerEntry ::= SEQUENCE {
   gs2328pQosSchedulerPort						Integer32,
   gs2328pQosSchedulerPortQueue					INTEGER,
   gs2328pQosSchedulerPortQueueShaper				INTEGER,
   gs2328pQosSchedulerPortQueueShaperRate			Integer32,
   gs2328pQosSchedulerPortQueueShaperExcess		INTEGER,
   gs2328pQosSchedulerPortQueueSchedulerWeight	Integer32,
   gs2328pQosSchedulerPortQueueSchedulerPercent	DisplayString
}

gs2328pQosSchedulerPort OBJECT-TYPE
   SYNTAX      Integer32 (1..4095)
   MAX-ACCESS  not-accessible
   STATUS      current
   DESCRIPTION
       " port, range : 1 - port number. "
   ::= { gs2328pQosPortSchedulerEntry 1 }

gs2328pQosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2328pQosPortSchedulerEntry 2 }
   
gs2328pQosSchedulerPortQueueShaper OBJECT-TYPE
   SYNTAX      INTEGER { disable(0), enable(1) }
   MAX-ACCESS  read-write
   STATUS      current
   DESCRIPTION
       " 0: disable  1:enable,
         default: 0.  "
   ::= { gs2328pQosPortSchedulerEntry 3 }
   
gs2328pQosSchedulerPortQueueShaperRate OBJECT-TYPE
   SYNTAX      Integer32(100..1000000)
   MAX-ACCESS  read-write
   STATUS      current
   DESCRIPTION
       " range: 100..1000000 kbps.  "
   ::= { gs2328pQosPortSchedulerEntry 4 }
   
gs2328pQosSchedulerPortQueueShaperExcess OBJECT-TYPE
   SYNTAX      INTEGER { disable(0), enable(1) }
   MAX-ACCESS  read-write
   STATUS      current
   DESCRIPTION
       " 0: disable  1:enable,
         default: 0.  "
   ::= { gs2328pQosPortSchedulerEntry 5 }
   
gs2328pQosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2328pQosPortSchedulerEntry 6 }
   
gs2328pQosSchedulerPortQueueSchedulerPercent OBJECT-TYPE
   SYNTAX      DisplayString
   MAX-ACCESS  read-only
   STATUS      current
   DESCRIPTION
       " Only use in Q0 - Q5. Q6 & Q7 show empty "
   ::= { gs2328pQosPortSchedulerEntry 7 }

gs2328pQosPortEgressTagRemarking                                           OBJECT IDENTIFIER ::= { gs2328pQos 4 }

gs2328pQosPortEgressTagRemarkingTable OBJECT-TYPE
   SYNTAX      SEQUENCE OF GS2328PQosPortEgressTagRemarkingEntry
   MAX-ACCESS  not-accessible
   STATUS      current
   DESCRIPTION
       " configure the basic QoS Port Egress Tag Remark Configuration settings for all switch ports. "
   ::= { gs2328pQosPortEgressTagRemarking  1 }

gs2328pQosPortEgressTagRemarkingEntry OBJECT-TYPE
   SYNTAX      GS2328PQosPortEgressTagRemarkingEntry
   MAX-ACCESS  not-accessible
   STATUS      current
   DESCRIPTION
       ""
   INDEX    { gs2328pQosEgressTagRemarkingPort  }
   ::= { gs2328pQosPortEgressTagRemarkingTable 1 }

GS2328PQosPortEgressTagRemarkingEntry ::= SEQUENCE {
   gs2328pQosEgressTagRemarkingPort	                Integer32,
   gs2328pQosEgressTagRemarkingMode	                INTEGER
}

gs2328pQosEgressTagRemarkingPort OBJECT-TYPE
   SYNTAX      Integer32 (1..4095)
   MAX-ACCESS  not-accessible
   STATUS      current
   DESCRIPTION
       " port, range : 1 - port number. "
   ::= { gs2328pQosPortEgressTagRemarkingEntry 1 }

gs2328pQosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2328pQosPortEgressTagRemarkingEntry 2 }


gs2328pQosPortEgressTagRemarkingDefTable OBJECT-TYPE
   SYNTAX      SEQUENCE OF GS2328PQosPortEgressTagRemarkingDefEntry
   MAX-ACCESS  not-accessible
   STATUS      current
   DESCRIPTION
       " configure the basic QoS Port Egress Tag Remark Configuration settings for all switch ports. "
   ::= { gs2328pQosPortEgressTagRemarking  2 }

gs2328pQosPortEgressTagRemarkingDefEntry OBJECT-TYPE
   SYNTAX      GS2328PQosPortEgressTagRemarkingDefEntry
   MAX-ACCESS  not-accessible
   STATUS      current
   DESCRIPTION
       ""
   INDEX    { gs2328pQosEgressTagRemarkingDefPort  }
   ::= { gs2328pQosPortEgressTagRemarkingDefTable 1 }

GS2328PQosPortEgressTagRemarkingDefEntry ::= SEQUENCE {
   gs2328pQosEgressTagRemarkingDefPort	            Integer32,
   gs2328pQosEgressTagRemarkingDefPCP	                Integer32,
   gs2328pQosEgressTagRemarkingDefDEI	                INTEGER
}

gs2328pQosEgressTagRemarkingDefPort OBJECT-TYPE
   SYNTAX      Integer32(1..4095)
   MAX-ACCESS  not-accessible
   STATUS      current
   DESCRIPTION
       " port, range : 1 - port number. "
   ::= { gs2328pQosPortEgressTagRemarkingDefEntry 1 }

gs2328pQosEgressTagRemarkingDefPCP OBJECT-TYPE
   SYNTAX      Integer32(0..7)
   MAX-ACCESS  read-write
   STATUS      current
   DESCRIPTION
       " Controls the default PCP
       Range : 0-7"
   ::= { gs2328pQosPortEgressTagRemarkingDefEntry 2 }

gs2328pQosEgressTagRemarkingDefDEI OBJECT-TYPE
   SYNTAX      INTEGER { disable(0), enable(1) }
   MAX-ACCESS  read-write
   STATUS      current
   DESCRIPTION
       " controls the DEI
       Range 0-1"
   ::= { gs2328pQosPortEgressTagRemarkingDefEntry 3 }

gs2328pQosPortEgressTagRemarkingMapTable OBJECT-TYPE
   SYNTAX      SEQUENCE OF GS2328PQosPortEgressTagRemarkingMapEntry
   MAX-ACCESS  not-accessible
   STATUS      current
   DESCRIPTION
       " Show Qos Port Egress Tag Remarking Map. "
   ::= { gs2328pQosPortEgressTagRemarking 4 }

gs2328pQosPortEgressTagRemarkingMapEntry OBJECT-TYPE
   SYNTAX      GS2328PQosPortEgressTagRemarkingMapEntry
   MAX-ACCESS  not-accessible
   STATUS      current
   DESCRIPTION
       ""
   INDEX    { gs2328pQosPortEgressTagRemarkingMapPort, gs2328pQosTagRemarkingQoSClass, gs2328pQosTagRemarkingDPLevel  }
   ::= { gs2328pQosPortEgressTagRemarkingMapTable 1 }

GS2328PQosPortEgressTagRemarkingMapEntry ::= SEQUENCE {
   gs2328pQosPortEgressTagRemarkingMapPort	Integer32,
   gs2328pQosTagRemarkingQoSClass			INTEGER,
   gs2328pQosTagRemarkingDPLevel				INTEGER,
   gs2328pQosTagRemarkingPCP					Integer32,
   gs2328pQosTagRemarkingDEI					INTEGER
}

gs2328pQosPortEgressTagRemarkingMapPort OBJECT-TYPE
   SYNTAX      Integer32 (1..4095)
   MAX-ACCESS  not-accessible
   STATUS      current
   DESCRIPTION
       " port, range : 1 - port number. "
   ::= { gs2328pQosPortEgressTagRemarkingMapEntry 1 }

gs2328pQosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8, 
         QoS Class0: 1, QoS Class1: 2...  "
   ::= { gs2328pQosPortEgressTagRemarkingMapEntry 2 }

gs2328pQosTagRemarkingDPLevel OBJECT-TYPE
   SYNTAX      INTEGER { level0(1), level1(2) }
   MAX-ACCESS  not-accessible
   STATUS      current
   DESCRIPTION
       " range: 1-2,
         DP Level0: 1, DP Level1: 2. "
   ::= { gs2328pQosPortEgressTagRemarkingMapEntry 3 }

gs2328pQosTagRemarkingPCP OBJECT-TYPE
   SYNTAX      Integer32 (0..7)
   MAX-ACCESS  read-write
   STATUS      current
   DESCRIPTION
       " range: 0-7.  "
   ::= { gs2328pQosPortEgressTagRemarkingMapEntry 4 }
   
gs2328pQosTagRemarkingDEI OBJECT-TYPE
   SYNTAX      INTEGER (0|1)
   MAX-ACCESS  read-write
   STATUS      current
   DESCRIPTION
       " range: 0-1.  "
   ::= { gs2328pQosPortEgressTagRemarkingMapEntry 5 }


gs2328pQosPortDSCPTable OBJECT-TYPE
   SYNTAX      SEQUENCE OF GS2328PQosPortDSCPEntry
   MAX-ACCESS  not-accessible
   STATUS      current
   DESCRIPTION
       " configure the basic QoS Port DSCP Configuration settings for all switch ports. "
   ::= { gs2328pQos  5 }

gs2328pQosPortDSCPEntry OBJECT-TYPE
   SYNTAX      GS2328PQosPortDSCPEntry
   MAX-ACCESS  not-accessible
   STATUS      current
   DESCRIPTION
       ""
   INDEX    { gs2328pQosPortDSCPPort  }
   ::= { gs2328pQosPortDSCPTable 1 }

GS2328PQosPortDSCPEntry ::= SEQUENCE {
   gs2328pQosPortDSCPPort	                Integer32,
   gs2328pQosPortDSCPIngressTranslate       INTEGER,
   gs2328pQosPortDSCPIngressClassify	    INTEGER,
   gs2328pQosPortDSCPEgressRewrite	        INTEGER
}

gs2328pQosPortDSCPPort OBJECT-TYPE
   SYNTAX      Integer32 (1..4095)
   MAX-ACCESS  not-accessible
   STATUS      current
   DESCRIPTION
       " port, range : 1 - port number. "
   ::= { gs2328pQosPortDSCPEntry 1 }

gs2328pQosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2328pQosPortDSCPEntry 2 }

gs2328pQosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2328pQosPortDSCPEntry 3 }

gs2328pQosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { gs2328pQosPortDSCPEntry 4 }


gs2328pQosDSCPTable OBJECT-TYPE
   SYNTAX      SEQUENCE OF GS2328PQosDSCPEntry
   MAX-ACCESS  not-accessible
   STATUS      current
   DESCRIPTION
       " configure the basic QoS DSCP based QoS Ingress Classification settings for all switches. "
   ::= { gs2328pQos  6 }

gs2328pQosDSCPEntry OBJECT-TYPE
   SYNTAX      GS2328PQosDSCPEntry
   MAX-ACCESS  not-accessible
   STATUS      current
   DESCRIPTION
       ""
   INDEX    { gs2328pQosDSCPList  }
   ::= { gs2328pQosDSCPTable 1 }

GS2328PQosDSCPEntry ::= SEQUENCE {
   gs2328pQosDSCPList       Integer32,
   gs2328pQosDSCP           DisplayString,
   gs2328pQosDSCPTrust      INTEGER,
   gs2328pQosDSCPQosClass	  Integer32,
   gs2328pQosDSCPDPL	      INTEGER
}

gs2328pQosDSCPList OBJECT-TYPE
   SYNTAX      Integer32(1..64)
   MAX-ACCESS  not-accessible
   STATUS      current
   DESCRIPTION
      " DSCP mapping table index(1-64). "
   ::= { gs2328pQosDSCPEntry 1 }

gs2328pQosDSCP OBJECT-TYPE
   SYNTAX      DisplayString
   MAX-ACCESS  read-only
   STATUS      current
   DESCRIPTION
      "Maximum number of supported DSCP values are 64."
   ::= { gs2328pQosDSCPEntry 2 }

gs2328pQosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2328pQosDSCPEntry 3 }

gs2328pQosDSCPQosClass OBJECT-TYPE
   SYNTAX      Integer32(0..7)
   MAX-ACCESS  read-write
   STATUS      current
   DESCRIPTION
      " QoS class.
        range: 0-7,
        default: 0. "
   ::= { gs2328pQosDSCPEntry 4 }

gs2328pQosDSCPDPL OBJECT-TYPE
   SYNTAX      INTEGER(0|1)
   MAX-ACCESS  read-write
   STATUS      current
   DESCRIPTION
      " Drop Precedence Level.
        range: 0-1,
        default: disable. "
   ::= { gs2328pQosDSCPEntry 5 }

gs2328pQosDSCPTranslationTable OBJECT-TYPE
   SYNTAX      SEQUENCE OF GS2328PQosDSCPTranslationEntry
   MAX-ACCESS  not-accessible
   STATUS      current
   DESCRIPTION
       "  configure the basic QoS DSCP Translation settings for all switches. "
   ::= { gs2328pQos  7 }

gs2328pQosDSCPTranslationEntry OBJECT-TYPE
   SYNTAX      GS2328PQosDSCPTranslationEntry
   MAX-ACCESS  not-accessible
   STATUS      current
   DESCRIPTION
       ""
   INDEX    { gs2328pQosDSCPTranslationList  }
   ::= { gs2328pQosDSCPTranslationTable 1 }

GS2328PQosDSCPTranslationEntry ::= SEQUENCE {
   gs2328pQosDSCPTranslationList                 Integer32,
   gs2328pQosDSCPTranslationDSCPBasedId          DisplayString,
   gs2328pQosDSCPTranslationIngressTranslate     Integer32,
   gs2328pQosDSCPTranslationIngressClassify      INTEGER,
   gs2328pQosDSCPTranslationEgressRemapDP0       Integer32,
   gs2328pQosDSCPTranslationEgressRemapDP1       Integer32
}

gs2328pQosDSCPTranslationList OBJECT-TYPE
   SYNTAX      Integer32(1..64)
   MAX-ACCESS  not-accessible
   STATUS      current
   DESCRIPTION
      " DSCP translation table index(1-64). "
   ::= { gs2328pQosDSCPTranslationEntry 1 }

gs2328pQosDSCPTranslationDSCPBasedId OBJECT-TYPE
   SYNTAX      DisplayString
   MAX-ACCESS  read-write
   STATUS      current
   DESCRIPTION
      " Configure global ingress DSCP translation table. "
   ::= { gs2328pQosDSCPTranslationEntry 2 }

gs2328pQosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2328pQosDSCPTranslationEntry 3 }

gs2328pQosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2328pQosDSCPTranslationEntry 4 }

gs2328pQosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { gs2328pQosDSCPTranslationEntry 5 }

gs2328pQosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { gs2328pQosDSCPTranslationEntry 6 }


gs2328pQosDSCPClassificationTable OBJECT-TYPE
   SYNTAX      SEQUENCE OF GS2328PQosDSCPClassificationEntry
   MAX-ACCESS  not-accessible
   STATUS      current
   DESCRIPTION
       "   configure the mapping of QoS class  to DSCP value. "
   ::= { gs2328pQos  8 }

gs2328pQosDSCPClassificationEntry OBJECT-TYPE
   SYNTAX      GS2328PQosDSCPClassificationEntry
   MAX-ACCESS  not-accessible
   STATUS      current
   DESCRIPTION
       ""
   INDEX    { gs2328pQosDSCPClassificationQoSClass, gs2328pQosDSCPClassificationDPL }
   ::= { gs2328pQosDSCPClassificationTable 1 }

GS2328PQosDSCPClassificationEntry ::= SEQUENCE {
   gs2328pQosDSCPClassificationQoSClass		INTEGER,
   gs2328pQosDSCPClassificationDPL			INTEGER,
   gs2328pQosDSCPClassificationDSCP			Integer32
}

gs2328pQosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2328pQosDSCPClassificationEntry 1 }

gs2328pQosDSCPClassificationDPL OBJECT-TYPE
   SYNTAX      INTEGER(1|2)
   MAX-ACCESS  not-accessible
   STATUS      current
   DESCRIPTION
      " DPL. Index 1~2 mean DPL 0~1."
   ::= { gs2328pQosDSCPClassificationEntry 2 }

gs2328pQosDSCPClassificationDSCP OBJECT-TYPE
   SYNTAX      Integer32(0..63)
   MAX-ACCESS  read-write
   STATUS      current
   DESCRIPTION
      " Select the classified DSCP value.
        range: 0-63,
        default: 0. "
   ::= { gs2328pQosDSCPClassificationEntry 3 }

gs2328pQosControlList                                         OBJECT IDENTIFIER ::= { gs2328pQos 9 }

gs2328pQosQceCreate OBJECT-TYPE
   SYNTAX       INTEGER { none(0), create(1) }
   MAX-ACCESS   read-write
   STATUS       current
   DESCRIPTION
       "default: 0
        0 : None  (read only)
        1 : Create an Qos entry"
   ::= { gs2328pQosControlList 1 }

gs2328pQosQceTable OBJECT-TYPE
   SYNTAX      SEQUENCE OF GS2328PQosQceEntry
   MAX-ACCESS  not-accessible
   STATUS      current
   DESCRIPTION
       " Create Qos QCE entry. "
   ::= { gs2328pQosControlList 2 }

gs2328pQosQceEntry OBJECT-TYPE
   SYNTAX      GS2328PQosQceEntry
   MAX-ACCESS  not-accessible
   STATUS      current
   DESCRIPTION
       ""
   INDEX    { gs2328pQosQceIndex  }
   ::= { gs2328pQosQceTable 1 }

GS2328PQosQceEntry ::= SEQUENCE {
   gs2328pQosQceIndex                Integer32,
   gs2328pQosQceID                   Integer32,
   gs2328pQosQceNextID               Integer32,
   gs2328pQosQcePortMembers          DisplayString,
   
   gs2328pQosQceTag                  DisplayString,
   gs2328pQosQceVID                  DisplayString,
   gs2328pQosPCP                     DisplayString,
   gs2328pQosDEI                     DisplayString,
   gs2328pQosSMAC                    DisplayString,
   gs2328pQosDMACType                DisplayString,
   gs2328pQosFrameType               INTEGER,
   
   gs2328pQosMacEtherType            DisplayString,
   
   gs2328pQosLLCSSAPAddr             DisplayString,
   gs2328pQosLLCDSAPAddr             DisplayString,
   gs2328pQosLLCControl              DisplayString,
   
   gs2328pQosSNAPPID                 DisplayString,
   
   gs2328pQosIpv4Protocol            DisplayString,
   gs2328pQosIpv4ProtocolValue       Integer32,
   gs2328pQosIpv4ProtocolUDPSport    DisplayString,
   gs2328pQosIpv4ProtocolUDPDport    DisplayString,
   gs2328pQosIpv4ProtocolTCPSport    DisplayString,
   gs2328pQosIpv4ProtocolTCPDport    DisplayString,
   gs2328pQosIpv4Ip                  DisplayString,
   gs2328pQosIpv4Mask                DisplayString,
   gs2328pQosIpv4IPFragment          INTEGER,
   gs2328pQosIpv4DSCP                DisplayString,


   gs2328pQosIpv6Protocol            DisplayString,
   gs2328pQosIpv6ProtocolValue       Integer32,
   gs2328pQosIpv6ProtocolUDPSport    DisplayString,
   gs2328pQosIpv6ProtocolUDPDport    DisplayString,
   gs2328pQosIpv6ProtocolTCPSport    DisplayString,
   gs2328pQosIpv6ProtocolTCPDport    DisplayString,
   gs2328pQosIpv6Ip                  DisplayString,
   gs2328pQosIpv6Mask                DisplayString,
   gs2328pQosIpv6DSCP                DisplayString,
   
   gs2328pQosActionClass             Integer32,
   gs2328pQosActionDPL               INTEGER,
   gs2328pQosActionDSCP              Integer32,
   gs2328pQosQceRowStatus            INTEGER
}

gs2328pQosQceIndex OBJECT-TYPE
   SYNTAX      Integer32(1..256)
   MAX-ACCESS  not-accessible
   STATUS      current
   DESCRIPTION
       " "
   ::= { gs2328pQosQceEntry 1 }

gs2328pQosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2328pQosQceEntry 2 }

gs2328pQosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2328pQosQceEntry 3 }

gs2328pQosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2328pQosQceEntry 4 }

gs2328pQosQceTag OBJECT-TYPE
   SYNTAX      DisplayString
   MAX-ACCESS  read-write
   STATUS      current
   DESCRIPTION
       " Value of Tag field can be 'Any', 'Untag' or 'Tag'. "
   ::= { gs2328pQosQceEntry 5 }

gs2328pQosQceVID OBJECT-TYPE
   SYNTAX      DisplayString
   MAX-ACCESS  read-write
   STATUS      current
   DESCRIPTION
       " Valid value of VLAN ID can be any value in 'Specific 1~4094' or 'range 1-4094' or 'Any'. "
   ::= { gs2328pQosQceEntry 6 }

gs2328pQosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2328pQosQceEntry 7 }

gs2328pQosDEI OBJECT-TYPE
   SYNTAX      DisplayString
   MAX-ACCESS  read-write
   STATUS      current
   DESCRIPTION
       " Drop Eligible Indicator: Valid value of DEI can be any of values between 0, 1 or 'Any'. "
   ::= { gs2328pQosQceEntry 8 }

gs2328pQosSMAC  OBJECT-TYPE
   SYNTAX      DisplayString
   MAX-ACCESS  read-write
   STATUS      current
   DESCRIPTION
       "  Source MAC address: 24 MS bits OUI(00-00-00 ~ FF-FF-FF) or 'Any'. "
   ::= { gs2328pQosQceEntry 9 }

gs2328pQosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2328pQosQceEntry 10 }

gs2328pQosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2328pQosQceEntry 11 }

gs2328pQosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2328pQosQceEntry 12 }

gs2328pQosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2328pQosQceEntry 13 }

gs2328pQosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2328pQosQceEntry 14 }

gs2328pQosLLCControl OBJECT-TYPE
   SYNTAX      DisplayString
   MAX-ACCESS  read-write
   STATUS      current
   DESCRIPTION
       " Valid Control field can vary from 0x00 to 0xFF or 'Any',
         range: 00-FF,
         default: Any. "
   ::= { gs2328pQosQceEntry 15 }

gs2328pQosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2328pQosQceEntry 16 }

gs2328pQosIpv4Protocol OBJECT-TYPE
   SYNTAX      DisplayString
   MAX-ACCESS  read-write
   STATUS      current
   DESCRIPTION
       " IP protocol number: (Other, TCP or UDP) or 'Any'. "
   ::= { gs2328pQosQceEntry 17 }

gs2328pQosIpv4ProtocolValue  OBJECT-TYPE
   SYNTAX      Integer32(0..255)
   MAX-ACCESS  read-write
   STATUS      current
   DESCRIPTION
       " Ipv4 Protocol is Other.
         range: 0-255
         default: 0. "
   ::= { gs2328pQosQceEntry 18 }

gs2328pQosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2328pQosQceEntry 19 }

gs2328pQosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2328pQosQceEntry 20 }

gs2328pQosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2328pQosQceEntry 21 }

gs2328pQosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2328pQosQceEntry 22 }

gs2328pQosIpv4Ip OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223.
          If a port is configured to match on DMAC/DIP, this field is the
          Destination IP address."
   ::= { gs2328pQosQceEntry 23 }

gs2328pQosIpv4Mask OBJECT-TYPE
   SYNTAX      DisplayString
   MAX-ACCESS  read-write
   STATUS      current
   DESCRIPTION
       " Specific IP address in mask format or value 0.0.0.0 is 'Any'. "
   ::= { gs2328pQosQceEntry 24 }

gs2328pQosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2328pQosQceEntry 25 }

gs2328pQosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2328pQosQceEntry 26 }

gs2328pQosIpv6Protocol OBJECT-TYPE
   SYNTAX      DisplayString
   MAX-ACCESS  read-write
   STATUS      current
   DESCRIPTION
       " IP protocol number: (Other, TCP or UDP) or 'Any'. "
   ::= { gs2328pQosQceEntry 27 }

gs2328pQosIpv6ProtocolValue OBJECT-TYPE
   SYNTAX      Integer32(0..255)
   MAX-ACCESS  read-write
   STATUS      current
   DESCRIPTION
       " when IPv6 protocol is Other ,
         range: 0-255. "
   ::= { gs2328pQosQceEntry 28 }

gs2328pQosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2328pQosQceEntry 29 }

gs2328pQosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2328pQosQceEntry 30 }

gs2328pQosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2328pQosQceEntry 31 }


gs2328pQosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2328pQosQceEntry 32 }

gs2328pQosIpv6Ip OBJECT-TYPE
   SYNTAX      DisplayString
   MAX-ACCESS  read-write
   STATUS      current
   DESCRIPTION
       " IPv6 source address: (a.b.c.d) or value 0.0.0.0 is 'Any', 32 LS bits.
         If a port is configured to match on DMAC/DIP, this field is the
         Destination IP address."
   ::= { gs2328pQosQceEntry 33 }

gs2328pQosIpv6Mask OBJECT-TYPE
   SYNTAX      DisplayString
   MAX-ACCESS  read-write
   STATUS      current
   DESCRIPTION
       " IPv6 mask address: (a.b.c.d) or value 0.0.0.0 is 'Any', 32 LS bits. "
   ::= { gs2328pQosQceEntry 34 }

gs2328pQosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2328pQosQceEntry 35 }

gs2328pQosActionClass  OBJECT-TYPE
   SYNTAX      Integer32(0..8)
   MAX-ACCESS  read-write
   STATUS      current
   DESCRIPTION
       " QoS class: (0-7) or 8: Default."
   ::= { gs2328pQosQceEntry 36 }

gs2328pQosActionDPL OBJECT-TYPE
   SYNTAX      INTEGER (0..4)
   MAX-ACCESS  read-write
   STATUS      current
   DESCRIPTION
       " DP Valid Drop Precedence Level can be (0-3) or 4: Default. "
   ::= { gs2328pQosQceEntry 37 }

gs2328pQosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2328pQosQceEntry 38 }

gs2328pQosQceRowStatus OBJECT-TYPE
   SYNTAX      INTEGER { active(1), notInservice(2), destroy(4) }
   MAX-ACCESS  read-write
   STATUS      current
   DESCRIPTION
       "  1: active2: notInservice 4: destroy"
   ::= { gs2328pQosQceEntry 39 }

gs2328pQosQceMoveID OBJECT-TYPE
   SYNTAX       Integer32(0..256)
   MAX-ACCESS   read-write
   STATUS       current
   DESCRIPTION
       " Move Qos,
         default: 0
         Qos ID must be exist.
         range : 0 - 256."
   ::= { gs2328pQosControlList 3 }

gs2328pQosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2328pQosControlList 4 }


gs2328pQosQCLStatusTable OBJECT-TYPE
   SYNTAX      SEQUENCE OF GS2328PQosQCLStatusEntry
   MAX-ACCESS  not-accessible
   STATUS      current
   DESCRIPTION
       "  configure the basic QoS DSCP Translation settings for all switches. "
   ::= { gs2328pQos  10 }

gs2328pQosQCLStatusEntry OBJECT-TYPE
   SYNTAX      GS2328PQosQCLStatusEntry
   MAX-ACCESS  not-accessible
   STATUS      current
   DESCRIPTION
       ""
   INDEX    { gs2328pQosQCLStatusList  }
   ::= { gs2328pQosQCLStatusTable 1 }

GS2328PQosQCLStatusEntry ::= SEQUENCE {
   gs2328pQosQCLStatusList               Integer32,
   gs2328pQosQCLStatusUser               DisplayString,
   gs2328pQosQCLStatusQCEId              DisplayString,
   gs2328pQosQCLStatusFrameType          DisplayString,
   gs2328pQosQCLStatusPortlist           DisplayString,
   gs2328pQosQCLStatusActionClass	       DisplayString,
   gs2328pQosQCLStatusActionDPL	       DisplayString,
   gs2328pQosQCLStatusActionDSCP	       DisplayString,
   gs2328pQosQCLStatusActionConflict     DisplayString
}

gs2328pQosQCLStatusList OBJECT-TYPE
   SYNTAX      Integer32(1..4095)
   MAX-ACCESS  not-accessible
   STATUS      current
   DESCRIPTION
       " QCL table index. "
   ::= { gs2328pQosQCLStatusEntry 1}
   
gs2328pQosQCLStatusUser OBJECT-TYPE
   SYNTAX      DisplayString
   MAX-ACCESS  read-only
   STATUS      current
   DESCRIPTION
       " Indicates the QCL user. "
   ::= { gs2328pQosQCLStatusEntry 2 }

gs2328pQosQCLStatusQCEId OBJECT-TYPE
   SYNTAX      DisplayString
   MAX-ACCESS  read-only
   STATUS      current
   DESCRIPTION
      " Indicates the index of QCE. "
   ::= { gs2328pQosQCLStatusEntry 3}

gs2328pQosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2328pQosQCLStatusEntry 4}

gs2328pQosQCLStatusPortlist OBJECT-TYPE
   SYNTAX      DisplayString
   MAX-ACCESS  read-only
   STATUS      current
   DESCRIPTION
       " Indicates the list of ports configured with the QCE. "
   ::= { gs2328pQosQCLStatusEntry 5}

gs2328pQosQCLStatusActionClass OBJECT-TYPE
   SYNTAX      DisplayString
   MAX-ACCESS  read-only
   STATUS      current
   DESCRIPTION
       " Classified QoS class; if a frame matches the QCE it will be put in the
       queue. "
   ::= { gs2328pQosQCLStatusEntry 6}

gs2328pQosQCLStatusActionDPL OBJECT-TYPE
   SYNTAX      DisplayString
   MAX-ACCESS  read-only
   STATUS      current
   DESCRIPTION
       " Drop Precedence Level; if a frame matches the QCE then DP level will
       set to value displayed under DPL column."
   ::= { gs2328pQosQCLStatusEntry 7}

gs2328pQosQCLStatusActionDSCP OBJECT-TYPE
   SYNTAX      DisplayString
   MAX-ACCESS  read-only
   STATUS      current
   DESCRIPTION
       " If a frame matches the QCE then DSCP will be classified with the value
       displayed under DSCP column."
   ::= { gs2328pQosQCLStatusEntry 8}

gs2328pQosQCLStatusActionConflict OBJECT-TYPE
   SYNTAX      DisplayString
   MAX-ACCESS  read-only
   STATUS      current
   DESCRIPTION
       " If a frame matches the QCE then DSCP will be classified with the value
        displayed under DSCP column. "
   ::= { gs2328pQosQCLStatusEntry 9}


gs2328pQosStormControl                                           OBJECT IDENTIFIER ::= { gs2328pQos 11 }

gs2328pQoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { gs2328pQosStormControl 2 }

gs2328pQoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2328pQosStormControl 3 }

gs2328pQoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { gs2328pQosStormControl 4 }

gs2328pQoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2328pQosStormControl 5 }

gs2328pQoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { gs2328pQosStormControl 6 }

gs2328pQoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2328pQosStormControl 7 }


gs2328pVlan                                                           OBJECT IDENTIFIER ::= { gs2328pConfiguration 15 }

gs2328pVlanPorts                                                      OBJECT IDENTIFIER ::= { gs2328pVlan 1 }

gs2328pVlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2328pVlanPorts 1 }

gs2328pVlanPortsTable OBJECT-TYPE
   SYNTAX      SEQUENCE OF GS2328PVlanPortsEntry
   MAX-ACCESS  not-accessible
   STATUS      current
   DESCRIPTION
       " Configure Vlan ports Configuration mode. "
   ::= { gs2328pVlanPorts 2 }

gs2328pVlanPortsEntry OBJECT-TYPE
   SYNTAX      GS2328PVlanPortsEntry
   MAX-ACCESS  not-accessible
   STATUS      current
   DESCRIPTION
       ""
   INDEX    { gs2328pVlanPortsPort  }
   ::= { gs2328pVlanPortsTable 1 }

GS2328PVlanPortsEntry ::= SEQUENCE {
   gs2328pVlanPortsPort	         Integer32,
   gs2328pVlanPortsPVID     Integer32,
   gs2328pVlanPortsFrameType      INTEGER,
   gs2328pVlanPortsIngressFilter  INTEGER,
   gs2328pVlanPortsEgressRule     INTEGER,
   gs2328pVlanPortsPortType       INTEGER
}

gs2328pVlanPortsPort OBJECT-TYPE
   SYNTAX      Integer32(1..4094)
   MAX-ACCESS  not-accessible
   STATUS      current
   DESCRIPTION
       " port, range : 1 - port number. "
   ::= { gs2328pVlanPortsEntry 1 }

gs2328pVlanPortsPVID OBJECT-TYPE
   SYNTAX      Integer32(1..4094)
   MAX-ACCESS  read-write
   STATUS      current
   DESCRIPTION
       "Configure PVID.
        range: 1-4094,
        default: 1. "
   ::= { gs2328pVlanPortsEntry 2 }

gs2328pVlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2328pVlanPortsEntry 3 }

gs2328pVlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2328pVlanPortsEntry 4 }

gs2328pVlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2328pVlanPortsEntry 5 }

gs2328pVlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2328pVlanPortsEntry 6 }

gs2328pVlanPrivateVLAN                                                              OBJECT IDENTIFIER ::= { gs2328pVlan 2 }

gs2328pVlanPrivateVLANMembership                                                    OBJECT IDENTIFIER ::= { gs2328pVlanPrivateVLAN 1 }

gs2328pVlanPrivateVLANMembershipCreate OBJECT-TYPE
   SYNTAX       Integer32(1..4094)
   MAX-ACCESS   read-write
   STATUS       current
   DESCRIPTION
       "default: 0
        0 : None  (read only)
        1 : Create a pvlan"
   ::= { gs2328pVlanPrivateVLANMembership 1 }

gs2328pVlanPrivateVLANMembershipTable OBJECT-TYPE
   SYNTAX      SEQUENCE OF Gs2328pVlanPrivateVLANMembershipEntry
   MAX-ACCESS  not-accessible
   STATUS      current
   DESCRIPTION
       " Configure Private Vlan Configuration. "
   ::= { gs2328pVlanPrivateVLANMembership 2 }

gs2328pVlanPrivateVLANMembershipEntry OBJECT-TYPE
   SYNTAX      Gs2328pVlanPrivateVLANMembershipEntry
   MAX-ACCESS  not-accessible
   STATUS      current
   DESCRIPTION
       ""
   INDEX    { gs2328pVlanPrivateVLANIndex  }
   ::= { gs2328pVlanPrivateVLANMembershipTable 1 }

Gs2328pVlanPrivateVLANMembershipEntry ::= SEQUENCE {
   gs2328pVlanPrivateVLANIndex          Integer32,
   gs2328pVlanPrivateVLANID             Integer32,
   gs2328pVlanPrivateVLANMemberships    DisplayString,
   gs2328pVlanPrivateVLANRowStatus      INTEGER
}

gs2328pVlanPrivateVLANIndex OBJECT-TYPE
   SYNTAX      Integer32(1..52)
   MAX-ACCESS  not-accessible
   STATUS      current
   DESCRIPTION
       "private VLAN Index. "
   ::= { gs2328pVlanPrivateVLANMembershipEntry 1 }

gs2328pVlanPrivateVLANID OBJECT-TYPE
   SYNTAX      Integer32(1..52)
   MAX-ACCESS  read-write
   STATUS      current
   DESCRIPTION
       "Indicates the ID of this particular private VLAN.
       The CreateEntry can be modify, the other entry can't be modify."
   ::= { gs2328pVlanPrivateVLANMembershipEntry 2 }

gs2328pVlanPrivateVLANMemberships OBJECT-TYPE
   SYNTAX      DisplayString
   MAX-ACCESS  read-write
   STATUS      current
   DESCRIPTION
       "To include the ports in a Private VLAN"
   ::= { gs2328pVlanPrivateVLANMembershipEntry 3 }

gs2328pVlanPrivateVLANRowStatus OBJECT-TYPE
   SYNTAX      INTEGER { active(1), notInservice(2), destroy(4) }
   MAX-ACCESS  read-write
   STATUS      current
   DESCRIPTION
       "1: active
        2: notInservice
        4: destroy"
   ::= { gs2328pVlanPrivateVLANMembershipEntry 4 }

gs2328pVlanPortIsolationTable OBJECT-TYPE
   SYNTAX      SEQUENCE OF Gs2328pVlanPortIsolationEntry
   MAX-ACCESS  not-accessible
   STATUS      current
   DESCRIPTION
       " Configure Vlan Port Isolation Configuration. "
   ::= { gs2328pVlanPrivateVLAN 2 }

gs2328pVlanPortIsolationEntry OBJECT-TYPE
   SYNTAX      Gs2328pVlanPortIsolationEntry
   MAX-ACCESS  not-accessible
   STATUS      current
   DESCRIPTION
       ""
   INDEX    { gs2328pVlanPortIsolationPort  }
   ::= { gs2328pVlanPortIsolationTable 1 }

Gs2328pVlanPortIsolationEntry ::= SEQUENCE {
   gs2328pVlanPortIsolationPort Integer32,
   gs2328pVlanPortIsolation     INTEGER
}

gs2328pVlanPortIsolationPort OBJECT-TYPE
   SYNTAX      Integer32(1..4094)
   MAX-ACCESS  not-accessible
   STATUS      current
   DESCRIPTION
       " port, range : 1 - port number. "
   ::= { gs2328pVlanPortIsolationEntry 1 }

gs2328pVlanPortIsolation OBJECT-TYPE
   SYNTAX      INTEGER{ disable(0), enable(1) }
   MAX-ACCESS  read-write
   STATUS      current
   DESCRIPTION
       "default: 0
        0:disable
        1:enable"
   ::= { gs2328pVlanPortIsolationEntry 2 }


gs2328pMACbasedVLAN                                                      OBJECT IDENTIFIER ::= { gs2328pVlan 3 }

gs2328pMACbasedVLANConf                                                      OBJECT IDENTIFIER ::= { gs2328pMACbasedVLAN 1 }

gs2328pMACbasedVLANConfCreate OBJECT-TYPE
   SYNTAX       Integer32
   MAX-ACCESS   read-write
   STATUS       current
   DESCRIPTION
       "default: 0
       0 : None  (read only) 1 : Create MAC base vlan"
   ::= { gs2328pMACbasedVLANConf 1 }

gs2328pMACbasedVLANConfTable OBJECT-TYPE
   SYNTAX      SEQUENCE OF Gs2328pMACbasedVLANConfEntry
   MAX-ACCESS  not-accessible
   STATUS      current
   DESCRIPTION
       " Configure Vlan Port Isolation Configuration. "
   ::= { gs2328pMACbasedVLANConf 2 }

gs2328pMACbasedVLANConfEntry OBJECT-TYPE
   SYNTAX      Gs2328pMACbasedVLANConfEntry
   MAX-ACCESS  not-accessible
   STATUS      current
   DESCRIPTION
       ""
   INDEX    { gs2328pMACbasedVLANIndex  }
   ::= { gs2328pMACbasedVLANConfTable 1 }

Gs2328pMACbasedVLANConfEntry ::= SEQUENCE {
   gs2328pMACbasedVLANIndex         Integer32,
   gs2328pMACbasedVLANMACAddress    MacAddress,
   gs2328pMACbasedVLANID            Integer32,
   gs2328pMACbasedMemberships       DisplayString,
   gs2328pMACbaseRowStatus          INTEGER
}

gs2328pMACbasedVLANIndex OBJECT-TYPE
   SYNTAX      Integer32(1..256)
   MAX-ACCESS  read-write
   STATUS      current
   DESCRIPTION
       "Indicates the VLAN ID. "
   ::= { gs2328pMACbasedVLANConfEntry 1 }

gs2328pMACbasedVLANMACAddress OBJECT-TYPE
   SYNTAX      MacAddress
   MAX-ACCESS  read-write
   STATUS      current
   DESCRIPTION
       "Indicates the MAC address.
       The CreateEntry can be modify, the other entry can't be modify."
   ::= { gs2328pMACbasedVLANConfEntry 2 }

gs2328pMACbasedVLANID OBJECT-TYPE
   SYNTAX      Integer32(1..4094)
   MAX-ACCESS  read-write
   STATUS      current
   DESCRIPTION
       "Indicates the VLAN ID. "
   ::= { gs2328pMACbasedVLANConfEntry 3 }

gs2328pMACbasedMemberships OBJECT-TYPE
   SYNTAX      DisplayString
   MAX-ACCESS  read-write
   STATUS      current
   DESCRIPTION
       "The ports are displayed for each MAC-based VLAN entry.
        To include the port in a MAC-based VLAN"
   ::= { gs2328pMACbasedVLANConfEntry 4 }


gs2328pMACbaseRowStatus OBJECT-TYPE
   SYNTAX      INTEGER { active(1), notInservice(2), destroy(4)}
   MAX-ACCESS  read-write
   STATUS      current
   DESCRIPTION
       "1: active
        2: notInservice
        4: destroy"
   ::= { gs2328pMACbasedVLANConfEntry 5 }


gs2328pIGMPSnooping                                                           OBJECT IDENTIFIER ::= { gs2328pConfiguration 16 }

gs2328pIGMPSnoopingBasic                                                      OBJECT IDENTIFIER ::= { gs2328pIGMPSnooping 1 }

gs2328pIGMPSnoopingEnable  OBJECT-TYPE
   SYNTAX      INTEGER { disable(0), enable(1) }
   MAX-ACCESS  read-write
   STATUS      current
   DESCRIPTION
       "Enable/Disable the Global IGMP Snooping"
   ::= { gs2328pIGMPSnoopingBasic 1 }

gs2328pIGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2328pIGMPSnoopingBasic 2 }

gs2328pIGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2328pIGMPSnoopingBasic 3 }
   
gs2328pIGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2328pIGMPSnoopingBasic 4 }

gs2328pIGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2328pIGMPSnoopingBasic 5 }

gs2328pIGMPSnoopingPortRelatedTable OBJECT-TYPE
   SYNTAX      SEQUENCE OF Gs2328pIGMPSnoopingPortRelatedEntry
   MAX-ACCESS  not-accessible
   STATUS      current
   DESCRIPTION
       " Configure IGMP Snooping Port Related Configuration. "
   ::= { gs2328pIGMPSnoopingBasic 6 }

gs2328pIGMPSnoopingPortRelatedEntry OBJECT-TYPE
   SYNTAX      Gs2328pIGMPSnoopingPortRelatedEntry
   MAX-ACCESS  not-accessible
   STATUS      current
   DESCRIPTION
       ""
   INDEX    { ifIndex  }
   ::= { gs2328pIGMPSnoopingPortRelatedTable 1 }

Gs2328pIGMPSnoopingPortRelatedEntry ::= SEQUENCE {
   gs2328pIGMPSnoopingRouterPort	INTEGER,
   gs2328pIGMPSnoopingFastLeave  	INTEGER,
   gs2328pIGMPSnoopingThrottling    Integer32
}

gs2328pIGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2328pIGMPSnoopingPortRelatedEntry 1 }

gs2328pIGMPSnoopingFastLeave OBJECT-TYPE
   SYNTAX      INTEGER { disable(0), enable(1) }
   MAX-ACCESS  read-write
   STATUS      current
   DESCRIPTION
       "Enable/Disable the fast leave on the port. "
   ::= { gs2328pIGMPSnoopingPortRelatedEntry 2 }
   
gs2328pIGMPSnoopingThrottling OBJECT-TYPE
   SYNTAX      Integer32(0..10)
   MAX-ACCESS  read-write
   STATUS      current
   DESCRIPTION
       "Enable to limit the number of multicast groups to which a switch port can belong.
       0: unlimited"
   ::= { gs2328pIGMPSnoopingPortRelatedEntry 3 }
   
gs2328pIGMPSnoopingVLANTable OBJECT-TYPE
   SYNTAX      SEQUENCE OF Gs2328pIGMPSnoopingVLANEntry
   MAX-ACCESS  not-accessible
   STATUS      current
   DESCRIPTION
       " Configure IGMP Snooping Vlan Configuration. "
   ::= { gs2328pIGMPSnooping 2 }

gs2328pIGMPSnoopingVLANEntry OBJECT-TYPE
   SYNTAX      Gs2328pIGMPSnoopingVLANEntry
   MAX-ACCESS  not-accessible
   STATUS      current
   DESCRIPTION
       ""
   INDEX    { gs2328pIGMPSnoopingVLANID  }
   ::= { gs2328pIGMPSnoopingVLANTable 1 }

Gs2328pIGMPSnoopingVLANEntry ::= SEQUENCE {
   gs2328pIGMPSnoopingVLANID        	Integer32,
   gs2328pIGMPSnoopingVLANEnable    	INTEGER,
   gs2328pIGMPSnoopingVLANIGMPQuerier   INTEGER,
   gs2328pIGMPSnoopingVLANCompatibility INTEGER,
   gs2328pIGMPSnoopingVLANRV        	Integer32,
   gs2328pIGMPSnoopingVLANQI      	    Integer32,
   gs2328pIGMPSnoopingVLANQRI   	    Integer32,
   gs2328pIGMPSnoopingVLANLLQI   	    Integer32,
   gs2328pIGMPSnoopingVLANURI    	    Integer32
}

gs2328pIGMPSnoopingVLANID OBJECT-TYPE
   SYNTAX      Integer32(1..4095)
   MAX-ACCESS  read-write
   STATUS      current
   DESCRIPTION
       "The VLAN ID of the entry"
   ::= { gs2328pIGMPSnoopingVLANEntry 1 }

gs2328pIGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2328pIGMPSnoopingVLANEntry 2 }

gs2328pIGMPSnoopingVLANIGMPQuerier OBJECT-TYPE
   SYNTAX      INTEGER { disable(0), enable(1) }
   MAX-ACCESS  read-write
   STATUS      current
   DESCRIPTION
       "Enable/Disable the IGMP Querier in the VLAN. "
   ::= { gs2328pIGMPSnoopingVLANEntry 3 }

gs2328pIGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2328pIGMPSnoopingVLANEntry 4 }
   
gs2328pIGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2328pIGMPSnoopingVLANEntry 5 }
   
gs2328pIGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2328pIGMPSnoopingVLANEntry 6 }
   
gs2328pIGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2328pIGMPSnoopingVLANEntry 7 }
   
gs2328pIGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2328pIGMPSnoopingVLANEntry 8 }

gs2328pIGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2328pIGMPSnoopingVLANEntry 9 }

gs2328pIGMPSnoopingPortGroupFiltering                                                      OBJECT IDENTIFIER ::= { gs2328pIGMPSnooping 3 }

gs2328pIGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2328pIGMPSnoopingPortGroupFiltering 1 }

gs2328pIGMPSnoopingPortGroupFilteringTable OBJECT-TYPE
   SYNTAX      SEQUENCE OF Gs2328pIGMPSnoopingPortGroupFilteringEntry
   MAX-ACCESS  not-accessible
   STATUS      current
   DESCRIPTION
       " Configure IGMP Snooping port group filtering. "
   ::= { gs2328pIGMPSnoopingPortGroupFiltering 2 }

gs2328pIGMPSnoopingPortGroupFilteringEntry OBJECT-TYPE
   SYNTAX      Gs2328pIGMPSnoopingPortGroupFilteringEntry
   MAX-ACCESS  not-accessible
   STATUS      current
   DESCRIPTION
       ""
   INDEX    { gs2328pIGMPSnoopingPortGroupFilteringIndex  }
   ::= { gs2328pIGMPSnoopingPortGroupFilteringTable 1 }

Gs2328pIGMPSnoopingPortGroupFilteringEntry ::= SEQUENCE {
   gs2328pIGMPSnoopingPortGroupFilteringIndex         Integer32,
   gs2328pIGMPSnoopingPortGroupFilteringPort          Integer32,
   gs2328pIGMPSnoopingPortGroupFilteringGroups        DisplayString,
   gs2328pIGMPSnoopingPortGroupFilteringRowStatus     INTEGER
}

gs2328pIGMPSnoopingPortGroupFilteringIndex OBJECT-TYPE
   SYNTAX      Integer32(1..65535)
   MAX-ACCESS  not-accessible
   STATUS      current
   DESCRIPTION
       "IGMP Snooping Port Group Filtering Configuration Index. "
   ::= { gs2328pIGMPSnoopingPortGroupFilteringEntry 1 }

gs2328pIGMPSnoopingPortGroupFilteringPort OBJECT-TYPE
   SYNTAX      Integer32(1..65535)
   MAX-ACCESS  read-write
   STATUS      current
   DESCRIPTION
       "The logical port for the settings. "
   ::= { gs2328pIGMPSnoopingPortGroupFilteringEntry 2 }

gs2328pIGMPSnoopingPortGroupFilteringGroups OBJECT-TYPE
   SYNTAX      DisplayString
   MAX-ACCESS  read-write
   STATUS      current
   DESCRIPTION
       "The IP Multicast Group that will be filtered. "
   ::= { gs2328pIGMPSnoopingPortGroupFilteringEntry 3 }

gs2328pIGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2328pIGMPSnoopingPortGroupFilteringEntry 4 }

gs2328pIGMPSnoopingStatus                                                      OBJECT IDENTIFIER ::= { gs2328pIGMPSnooping 4 }

gs2328pIGMPSnoopingstatisticClear OBJECT-TYPE
   SYNTAX      INTEGER { none(0), clear(1)}
   MAX-ACCESS  read-write
   STATUS      current
   DESCRIPTION
       "Clears all Statistics counters."
   ::= { gs2328pIGMPSnoopingStatus 1 }


gs2328pIGMPSnoopingstatisticTable OBJECT-TYPE
   SYNTAX      SEQUENCE OF Gs2328pIGMPSnoopingstatisticEntry
   MAX-ACCESS  not-accessible
   STATUS      current
   DESCRIPTION
       " Configure Vlan Port Isolation Configuration. "
   ::= { gs2328pIGMPSnoopingStatus 2 }

gs2328pIGMPSnoopingstatisticEntry OBJECT-TYPE
   SYNTAX      Gs2328pIGMPSnoopingstatisticEntry
   MAX-ACCESS  not-accessible
   STATUS      current
   DESCRIPTION
       ""
   INDEX    { gs2328pIGMPSnoopingstatisticVLANID  }
   ::= { gs2328pIGMPSnoopingstatisticTable 1 }

Gs2328pIGMPSnoopingstatisticEntry ::= SEQUENCE {
   gs2328pIGMPSnoopingstatisticVLANID              Integer32,
   gs2328pIGMPSnoopingstatisticQuerierVersion      DisplayString,
   gs2328pIGMPSnoopingstatisticHostVersion         DisplayString,
   gs2328pIGMPSnoopingstatisticQuerierStatus       DisplayString,
   gs2328pIGMPSnoopingstatisticQueriesTransmitted  Counter32,
   gs2328pIGMPSnoopingstatisticQueriesReceived     Counter32,
   gs2328pIGMPSnoopingstatisticV1ReportsReceived   Counter32,
   gs2328pIGMPSnoopingstatisticV2ReportsReceived   Counter32,
   gs2328pIGMPSnoopingstatisticV3ReportsReceived   Counter32,
   gs2328pIGMPSnoopingstatisticV2LeavesReceived    Counter32
}


gs2328pIGMPSnoopingstatisticVLANID OBJECT-TYPE
   SYNTAX      Integer32(1..4095)
   MAX-ACCESS  read-only
   STATUS      current
   DESCRIPTION
       "The VLAN ID of the entry. "
   ::= { gs2328pIGMPSnoopingstatisticEntry 1 }

gs2328pIGMPSnoopingstatisticQuerierVersion OBJECT-TYPE
   SYNTAX      DisplayString
   MAX-ACCESS  read-only
   STATUS      current
   DESCRIPTION
       "Working Querier Version currently. "
   ::= { gs2328pIGMPSnoopingstatisticEntry 2 }
   
gs2328pIGMPSnoopingstatisticHostVersion OBJECT-TYPE
   SYNTAX      DisplayString
   MAX-ACCESS  read-only
   STATUS      current
   DESCRIPTION
       "Working Host Version currently. "
   ::= { gs2328pIGMPSnoopingstatisticEntry 3 }

gs2328pIGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2328pIGMPSnoopingstatisticEntry 4 }

gs2328pIGMPSnoopingstatisticQueriesTransmitted OBJECT-TYPE
   SYNTAX      Counter32
   MAX-ACCESS  read-only
   STATUS      current
   DESCRIPTION
       "The number of Transmitted Queries. "
   ::= { gs2328pIGMPSnoopingstatisticEntry 5 }

gs2328pIGMPSnoopingstatisticQueriesReceived OBJECT-TYPE
   SYNTAX      Counter32
   MAX-ACCESS  read-only
   STATUS      current
   DESCRIPTION
       "The number of Received Queries. "
   ::= { gs2328pIGMPSnoopingstatisticEntry 6 }

gs2328pIGMPSnoopingstatisticV1ReportsReceived OBJECT-TYPE
   SYNTAX      Counter32
   MAX-ACCESS  read-only
   STATUS      current
   DESCRIPTION
       "The number of Received V1 Reports. "
   ::= { gs2328pIGMPSnoopingstatisticEntry 7 }

gs2328pIGMPSnoopingstatisticV2ReportsReceived OBJECT-TYPE
   SYNTAX      Counter32
   MAX-ACCESS  read-only
   STATUS      current
   DESCRIPTION
       "The number of Received V2 Reports. "
   ::= { gs2328pIGMPSnoopingstatisticEntry 8 }

gs2328pIGMPSnoopingstatisticV3ReportsReceived OBJECT-TYPE
   SYNTAX      Counter32
   MAX-ACCESS  read-only
   STATUS      current
   DESCRIPTION
       "The number of Received V3 Reports. "
   ::= { gs2328pIGMPSnoopingstatisticEntry 9 }

gs2328pIGMPSnoopingstatisticV2LeavesReceived OBJECT-TYPE
   SYNTAX      Counter32
   MAX-ACCESS  read-only
   STATUS      current
   DESCRIPTION
       "The number of Received V2 Leaves. "
   ::= { gs2328pIGMPSnoopingstatisticEntry 10 }

gs2328pIGMPSnoopingRouterPortTable OBJECT-TYPE
   SYNTAX      SEQUENCE OF Gs2328pIGMPSnoopingRouterPortEntry
   MAX-ACCESS  not-accessible
   STATUS      current
   DESCRIPTION
       " Configure Vlan Port Isolation Configuration. "
   ::= { gs2328pIGMPSnoopingStatus 3 }

gs2328pIGMPSnoopingRouterPortEntry OBJECT-TYPE
   SYNTAX      Gs2328pIGMPSnoopingRouterPortEntry
   MAX-ACCESS  not-accessible
   STATUS      current
   DESCRIPTION
       ""
   INDEX    { ifIndex  }
   ::= { gs2328pIGMPSnoopingRouterPortTable 1 }

Gs2328pIGMPSnoopingRouterPortEntry ::= SEQUENCE {
   gs2328pIGMPSnoopingRouterPortStatus            DisplayString
}

gs2328pIGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2328pIGMPSnoopingRouterPortEntry 1 }

gs2328pIGMPSnoopingGroupsTable OBJECT-TYPE
   SYNTAX      SEQUENCE OF Gs2328pIGMPSnoopingGroupsEntry
   MAX-ACCESS  not-accessible
   STATUS      current
   DESCRIPTION
       "IGMP Snooping Groups Information . "
   ::= { gs2328pIGMPSnooping 5 }

gs2328pIGMPSnoopingGroupsEntry OBJECT-TYPE
   SYNTAX      Gs2328pIGMPSnoopingGroupsEntry
   MAX-ACCESS  not-accessible
   STATUS      current
   DESCRIPTION
       ""
   INDEX    { gs2328pIGMPSnoopingGroupsIndex  }
   ::= { gs2328pIGMPSnoopingGroupsTable 1 }

Gs2328pIGMPSnoopingGroupsEntry ::= SEQUENCE {
   gs2328pIGMPSnoopingGroupsIndex          Integer32,
   gs2328pIGMPSnoopingGroupsVLANID         Integer32,
   gs2328pIGMPSnoopingGroups               InetAddress,
   gs2328pIGMPSnoopingGroupsMemberships    DisplayString
}

gs2328pIGMPSnoopingGroupsIndex OBJECT-TYPE
   SYNTAX      Integer32(1..65535)
   MAX-ACCESS  not-accessible
   STATUS      current
   DESCRIPTION
       "IGMP Snooping Groups Index"
   ::= { gs2328pIGMPSnoopingGroupsEntry 1 }

gs2328pIGMPSnoopingGroupsVLANID OBJECT-TYPE
   SYNTAX      Integer32(1..4095)
   MAX-ACCESS  read-only
   STATUS      current
   DESCRIPTION
       "VLAN ID of the group. "
   ::= { gs2328pIGMPSnoopingGroupsEntry 2 }

gs2328pIGMPSnoopingGroups OBJECT-TYPE
   SYNTAX      DisplayString
   MAX-ACCESS  read-only
   STATUS      current
   DESCRIPTION
       "Group address of the group displayed."
   ::= { gs2328pIGMPSnoopingGroupsEntry 3 }

gs2328pIGMPSnoopingGroupsMemberships OBJECT-TYPE
   SYNTAX      DisplayString
   MAX-ACCESS  read-only
   STATUS      current
   DESCRIPTION
       "Ports under this group."
   ::= { gs2328pIGMPSnoopingGroupsEntry 4 }
   
gs2328pIGMPSnoopingSSMTable OBJECT-TYPE
   SYNTAX      SEQUENCE OF Gs2328pIGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2328pIGMPSnooping 6 }

gs2328pIGMPSnoopingSSMEntry OBJECT-TYPE
   SYNTAX      Gs2328pIGMPSnoopingSSMEntry
   MAX-ACCESS  not-accessible
   STATUS      current
   DESCRIPTION
       ""
   INDEX    { gs2328pIGMPSnoopingSSMIndex  }
   ::= { gs2328pIGMPSnoopingSSMTable 1 }

Gs2328pIGMPSnoopingSSMEntry ::= SEQUENCE {
   gs2328pIGMPSnoopingSSMIndex          Integer32,
   gs2328pIGMPSnoopingSSMVLANID         Integer32,
   gs2328pIGMPSnoopingSSMGroup          DisplayString,
   gs2328pIGMPSnoopingSSMPort           Integer32,
   gs2328pIGMPSnoopingSSMMode           DisplayString,
   gs2328pIGMPSnoopingSSMSourceAddress  DisplayString,
   gs2328pIGMPSnoopingSSMType           DisplayString
}

gs2328pIGMPSnoopingSSMIndex OBJECT-TYPE
   SYNTAX      Integer32(1..65535)
   MAX-ACCESS  not-accessible
   STATUS      current
   DESCRIPTION
       "IGMP Snooping SSM Index"
   ::= { gs2328pIGMPSnoopingSSMEntry 1 }

gs2328pIGMPSnoopingSSMVLANID OBJECT-TYPE
   SYNTAX      Integer32(1..4095)
   MAX-ACCESS  read-only
   STATUS      current
   DESCRIPTION
       "VLAN ID of the group. "
   ::= { gs2328pIGMPSnoopingSSMEntry 2 }

gs2328pIGMPSnoopingSSMGroup OBJECT-TYPE
   SYNTAX      DisplayString
   MAX-ACCESS  read-only
   STATUS      current
   DESCRIPTION
       "Group address of the group displayed."
   ::= { gs2328pIGMPSnoopingSSMEntry 3 }

gs2328pIGMPSnoopingSSMPort OBJECT-TYPE
   SYNTAX      Integer32(1..65535)
   MAX-ACCESS  read-only
   STATUS      current
   DESCRIPTION
       "Ports under this group."
   ::= { gs2328pIGMPSnoopingSSMEntry 4 }
   
gs2328pIGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2328pIGMPSnoopingSSMEntry 5 }
   
gs2328pIGMPSnoopingSSMSourceAddress OBJECT-TYPE
   SYNTAX      DisplayString
   MAX-ACCESS  read-only
   STATUS      current
   DESCRIPTION
       "IP Address of the source. Currently, system limits the total number of
       IP source addresses for filtering to be 128."
   ::= { gs2328pIGMPSnoopingSSMEntry 6 }

gs2328pIGMPSnoopingSSMType OBJECT-TYPE
   SYNTAX      DisplayString
   MAX-ACCESS  read-only
   STATUS      current
   DESCRIPTION
       "Indicates the Type. It can be either Allow or Deny."
   ::= { gs2328pIGMPSnoopingSSMEntry 7 }   

gs2328pMLDSnooping                                                           OBJECT IDENTIFIER ::= { gs2328pConfiguration 17 }

gs2328pMLDSnoopingBasic                                                      OBJECT IDENTIFIER ::= { gs2328pMLDSnooping 1 }

gs2328pMLDSnoopingEnable  OBJECT-TYPE
   SYNTAX      INTEGER { disable(0), enable(1) }
   MAX-ACCESS  read-write
   STATUS      current
   DESCRIPTION
       "Enable/Disable the Global MLD Snooping"
   ::= { gs2328pMLDSnoopingBasic 1 }

gs2328pMLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2328pMLDSnoopingBasic 2 }

gs2328pMLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2328pMLDSnoopingBasic 3 }
   
gs2328pMLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2328pMLDSnoopingBasic 4 }

gs2328pMLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2328pMLDSnoopingBasic 5 }

gs2328pMLDSnoopingPortRelatedTable OBJECT-TYPE
   SYNTAX      SEQUENCE OF Gs2328pMLDSnoopingPortRelatedEntry
   MAX-ACCESS  not-accessible
   STATUS      current
   DESCRIPTION
       " Configure MLD Snooping Port Related Configuration. "
   ::= { gs2328pMLDSnoopingBasic 6 }

gs2328pMLDSnoopingPortRelatedEntry OBJECT-TYPE
   SYNTAX      Gs2328pMLDSnoopingPortRelatedEntry
   MAX-ACCESS  not-accessible
   STATUS      current
   DESCRIPTION
       ""
   INDEX    { ifIndex  }
   ::= { gs2328pMLDSnoopingPortRelatedTable 1 }

Gs2328pMLDSnoopingPortRelatedEntry ::= SEQUENCE {
   gs2328pMLDSnoopingRouterPort	INTEGER,
   gs2328pMLDSnoopingFastLeave  	INTEGER,
   gs2328pMLDSnoopingThrottling    Integer32
}

gs2328pMLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2328pMLDSnoopingPortRelatedEntry 1 }

gs2328pMLDSnoopingFastLeave OBJECT-TYPE
   SYNTAX      INTEGER { disable(0), enable(1) }
   MAX-ACCESS  read-write
   STATUS      current
   DESCRIPTION
       "Enable/Disable the fast leave on the port. "
   ::= { gs2328pMLDSnoopingPortRelatedEntry 2 }
   
gs2328pMLDSnoopingThrottling OBJECT-TYPE
   SYNTAX      Integer32(0..10)
   MAX-ACCESS  read-write
   STATUS      current
   DESCRIPTION
       "Enable to limit the number of multicast groups to which a switch port can belong.
       0: unlimited"
   ::= { gs2328pMLDSnoopingPortRelatedEntry 3 }
   
gs2328pMLDSnoopingVLANTable OBJECT-TYPE
   SYNTAX      SEQUENCE OF Gs2328pMLDSnoopingVLANEntry
   MAX-ACCESS  not-accessible
   STATUS      current
   DESCRIPTION
       " Configure MLD Snooping Vlan Configuration. "
   ::= { gs2328pMLDSnooping 2 }

gs2328pMLDSnoopingVLANEntry OBJECT-TYPE
   SYNTAX      Gs2328pMLDSnoopingVLANEntry
   MAX-ACCESS  not-accessible
   STATUS      current
   DESCRIPTION
       ""
   INDEX    { gs2328pMLDSnoopingVLANID  }
   ::= { gs2328pMLDSnoopingVLANTable 1 }

Gs2328pMLDSnoopingVLANEntry ::= SEQUENCE {
   gs2328pMLDSnoopingVLANID        	Integer32,
   gs2328pMLDSnoopingVLANEnable    	INTEGER,
   gs2328pMLDSnoopingVLANIGMPQuerier   INTEGER,
   gs2328pMLDSnoopingVLANCompatibility INTEGER,
   gs2328pMLDSnoopingVLANRV        	Integer32,
   gs2328pMLDSnoopingVLANQI      	    Integer32,
   gs2328pMLDSnoopingVLANQRI   	    Integer32,
   gs2328pMLDSnoopingVLANLLQI   	    Integer32,
   gs2328pMLDSnoopingVLANURI    	    Integer32
}

gs2328pMLDSnoopingVLANID OBJECT-TYPE
   SYNTAX      Integer32(1..4095)
   MAX-ACCESS  read-write
   STATUS      current
   DESCRIPTION
       "The VLAN ID of the entry"
   ::= { gs2328pMLDSnoopingVLANEntry 1 }

gs2328pMLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2328pMLDSnoopingVLANEntry 2 }

gs2328pMLDSnoopingVLANIGMPQuerier OBJECT-TYPE
   SYNTAX      INTEGER { disable(0), enable(1) }
   MAX-ACCESS  read-write
   STATUS      current
   DESCRIPTION
       "Enable/Disable the MLD Querier in the VLAN. "
   ::= { gs2328pMLDSnoopingVLANEntry 3 }

gs2328pMLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2328pMLDSnoopingVLANEntry 4 }
   
gs2328pMLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2328pMLDSnoopingVLANEntry 5 }
   
gs2328pMLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2328pMLDSnoopingVLANEntry 6 }
   
gs2328pMLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2328pMLDSnoopingVLANEntry 7 }
   
gs2328pMLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2328pMLDSnoopingVLANEntry 8 }

gs2328pMLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2328pMLDSnoopingVLANEntry 9 }

gs2328pMLDSnoopingPortGroupFiltering                                                      OBJECT IDENTIFIER ::= { gs2328pMLDSnooping 3 }

gs2328pMLDSnoopingPortGroupFilteringCreate OBJECT-TYPE
   SYNTAX       Integer32
   MAX-ACCESS   read-write
   STATUS       current
   DESCRIPTION
       "default: 0
       0 : None  (read only) 1 : Create MLD Snooping Port Group Filtering "
   ::= { gs2328pMLDSnoopingPortGroupFiltering 1 }

gs2328pMLDSnoopingPortGroupFilteringTable OBJECT-TYPE
   SYNTAX      SEQUENCE OF Gs2328pMLDSnoopingPortGroupFilteringEntry
   MAX-ACCESS  not-accessible
   STATUS      current
   DESCRIPTION
       " Configure MLD Snooping port group filtering. "
   ::= { gs2328pMLDSnoopingPortGroupFiltering 2 }

gs2328pMLDSnoopingPortGroupFilteringEntry OBJECT-TYPE
   SYNTAX      Gs2328pMLDSnoopingPortGroupFilteringEntry
   MAX-ACCESS  not-accessible
   STATUS      current
   DESCRIPTION
       ""
   INDEX    { gs2328pMLDSnoopingPortGroupFilteringIndex  }
   ::= { gs2328pMLDSnoopingPortGroupFilteringTable 1 }

Gs2328pMLDSnoopingPortGroupFilteringEntry ::= SEQUENCE {
   gs2328pMLDSnoopingPortGroupFilteringIndex         Integer32,
   gs2328pMLDSnoopingPortGroupFilteringPort          Integer32,
   gs2328pMLDSnoopingPortGroupFilteringGroups        DisplayString,
   gs2328pMLDSnoopingPortGroupFilteringRowStatus     INTEGER
}

gs2328pMLDSnoopingPortGroupFilteringIndex OBJECT-TYPE
   SYNTAX      Integer32(1..65535)
   MAX-ACCESS  not-accessible
   STATUS      current
   DESCRIPTION
       "MLD Snooping Port Group Filtering Configuration Index. "
   ::= { gs2328pMLDSnoopingPortGroupFilteringEntry 1 }

gs2328pMLDSnoopingPortGroupFilteringPort OBJECT-TYPE
   SYNTAX      Integer32(1..65535)
   MAX-ACCESS  read-write
   STATUS      current
   DESCRIPTION
       "The logical port for the settings. "
   ::= { gs2328pMLDSnoopingPortGroupFilteringEntry 2 }

gs2328pMLDSnoopingPortGroupFilteringGroups OBJECT-TYPE
   SYNTAX      DisplayString
   MAX-ACCESS  read-write
   STATUS      current
   DESCRIPTION
       "The IP Multicast Group that will be filtered. "
   ::= { gs2328pMLDSnoopingPortGroupFilteringEntry 3 }

gs2328pMLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2328pMLDSnoopingPortGroupFilteringEntry 4 }

gs2328pMLDSnoopingStatus                                                      OBJECT IDENTIFIER ::= { gs2328pMLDSnooping 4 }

gs2328pMLDSnoopingstatisticClear OBJECT-TYPE
   SYNTAX      INTEGER { none(0), clear(1)}
   MAX-ACCESS  read-write
   STATUS      current
   DESCRIPTION
       "Clears all Statistics counters."
   ::= { gs2328pMLDSnoopingStatus 1 }


gs2328pMLDSnoopingstatisticTable OBJECT-TYPE
   SYNTAX      SEQUENCE OF Gs2328pMLDSnoopingstatisticEntry
   MAX-ACCESS  not-accessible
   STATUS      current
   DESCRIPTION
       " Configure Vlan Port Isolation Configuration. "
   ::= { gs2328pMLDSnoopingStatus 2 }

gs2328pMLDSnoopingstatisticEntry OBJECT-TYPE
   SYNTAX      Gs2328pMLDSnoopingstatisticEntry
   MAX-ACCESS  not-accessible
   STATUS      current
   DESCRIPTION
       ""
   INDEX    { gs2328pMLDSnoopingstatisticVLANID  }
   ::= { gs2328pMLDSnoopingstatisticTable 1 }

Gs2328pMLDSnoopingstatisticEntry ::= SEQUENCE {
   gs2328pMLDSnoopingstatisticVLANID              Integer32,
   gs2328pMLDSnoopingstatisticQuerierVersion      DisplayString,
   gs2328pMLDSnoopingstatisticHostVersion         DisplayString,
   gs2328pMLDSnoopingstatisticQuerierStatus       DisplayString,
   gs2328pMLDSnoopingstatisticQueriesTransmitted  Counter32,
   gs2328pMLDSnoopingstatisticQueriesReceived     Counter32,
   gs2328pMLDSnoopingstatisticV1ReportsReceived   Counter32,
   gs2328pMLDSnoopingstatisticV2ReportsReceived   Counter32,
   gs2328pMLDSnoopingstatisticV1LeavesReceived    Counter32
}


gs2328pMLDSnoopingstatisticVLANID OBJECT-TYPE
   SYNTAX      Integer32(1..4095)
   MAX-ACCESS  read-only
   STATUS      current
   DESCRIPTION
       "The VLAN ID of the entry. "
   ::= { gs2328pMLDSnoopingstatisticEntry 1 }

gs2328pMLDSnoopingstatisticQuerierVersion OBJECT-TYPE
   SYNTAX      DisplayString
   MAX-ACCESS  read-only
   STATUS      current
   DESCRIPTION
       "Working Querier Version currently. "
   ::= { gs2328pMLDSnoopingstatisticEntry 2 }
   
gs2328pMLDSnoopingstatisticHostVersion OBJECT-TYPE
   SYNTAX      DisplayString
   MAX-ACCESS  read-only
   STATUS      current
   DESCRIPTION
       "Working Host Version currently. "
   ::= { gs2328pMLDSnoopingstatisticEntry 3 }

gs2328pMLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2328pMLDSnoopingstatisticEntry 4 }

gs2328pMLDSnoopingstatisticQueriesTransmitted OBJECT-TYPE
   SYNTAX      Counter32
   MAX-ACCESS  read-only
   STATUS      current
   DESCRIPTION
       "The number of Transmitted Queries. "
   ::= { gs2328pMLDSnoopingstatisticEntry 5 }

gs2328pMLDSnoopingstatisticQueriesReceived OBJECT-TYPE
   SYNTAX      Counter32
   MAX-ACCESS  read-only
   STATUS      current
   DESCRIPTION
       "The number of Received Queries. "
   ::= { gs2328pMLDSnoopingstatisticEntry 6 }

gs2328pMLDSnoopingstatisticV1ReportsReceived OBJECT-TYPE
   SYNTAX      Counter32
   MAX-ACCESS  read-only
   STATUS      current
   DESCRIPTION
       "The number of Received V1 Reports. "
   ::= { gs2328pMLDSnoopingstatisticEntry 7 }

gs2328pMLDSnoopingstatisticV2ReportsReceived OBJECT-TYPE
   SYNTAX      Counter32
   MAX-ACCESS  read-only
   STATUS      current
   DESCRIPTION
       "The number of Received V2 Reports. "
   ::= { gs2328pMLDSnoopingstatisticEntry 8 }

gs2328pMLDSnoopingstatisticV1LeavesReceived OBJECT-TYPE
   SYNTAX      Counter32
   MAX-ACCESS  read-only
   STATUS      current
   DESCRIPTION
       "The number of Received V1 Leaves. "
   ::= { gs2328pMLDSnoopingstatisticEntry 9 }

gs2328pMLDSnoopingRouterPortTable OBJECT-TYPE
   SYNTAX      SEQUENCE OF Gs2328pMLDSnoopingRouterPortEntry
   MAX-ACCESS  not-accessible
   STATUS      current
   DESCRIPTION
       " Configure Vlan Port Isolation Configuration. "
   ::= { gs2328pMLDSnoopingStatus 3 }

gs2328pMLDSnoopingRouterPortEntry OBJECT-TYPE
   SYNTAX      Gs2328pMLDSnoopingRouterPortEntry
   MAX-ACCESS  not-accessible
   STATUS      current
   DESCRIPTION
       ""
   INDEX    { ifIndex  }
   ::= { gs2328pMLDSnoopingRouterPortTable 1 }

Gs2328pMLDSnoopingRouterPortEntry ::= SEQUENCE {
   gs2328pMLDSnoopingRouterPortStatus            DisplayString
}

gs2328pMLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2328pMLDSnoopingRouterPortEntry 1 }

gs2328pMLDSnoopingGroupsTable OBJECT-TYPE
   SYNTAX      SEQUENCE OF Gs2328pMLDSnoopingGroupsEntry
   MAX-ACCESS  not-accessible
   STATUS      current
   DESCRIPTION
       "MLD Snooping Groups Information . "
   ::= { gs2328pMLDSnooping 5 }

gs2328pMLDSnoopingGroupsEntry OBJECT-TYPE
   SYNTAX      Gs2328pMLDSnoopingGroupsEntry
   MAX-ACCESS  not-accessible
   STATUS      current
   DESCRIPTION
       ""
   INDEX    { gs2328pMLDSnoopingGroupsIndex  }
   ::= { gs2328pMLDSnoopingGroupsTable 1 }

Gs2328pMLDSnoopingGroupsEntry ::= SEQUENCE {
   gs2328pMLDSnoopingGroupsIndex          Integer32,
   gs2328pMLDSnoopingGroupsVLANID         Integer32,
   gs2328pMLDSnoopingGroups               InetAddress,
   gs2328pMLDSnoopingGroupsMemberships    DisplayString
}

gs2328pMLDSnoopingGroupsIndex OBJECT-TYPE
   SYNTAX      Integer32(1..65535)
   MAX-ACCESS  not-accessible
   STATUS      current
   DESCRIPTION
       "MLD Snooping Groups Index"
   ::= { gs2328pMLDSnoopingGroupsEntry 1 }

gs2328pMLDSnoopingGroupsVLANID OBJECT-TYPE
   SYNTAX      Integer32(1..4095)
   MAX-ACCESS  read-only
   STATUS      current
   DESCRIPTION
       "VLAN ID of the group. "
   ::= { gs2328pMLDSnoopingGroupsEntry 2 }

gs2328pMLDSnoopingGroups OBJECT-TYPE
   SYNTAX      DisplayString
   MAX-ACCESS  read-only
   STATUS      current
   DESCRIPTION
       "Group address of the group displayed."
   ::= { gs2328pMLDSnoopingGroupsEntry 3 }

gs2328pMLDSnoopingGroupsMemberships OBJECT-TYPE
   SYNTAX      DisplayString
   MAX-ACCESS  read-only
   STATUS      current
   DESCRIPTION
       "Ports under this group."
   ::= { gs2328pMLDSnoopingGroupsEntry 4 }
   
gs2328pMLDSnoopingSSMTable OBJECT-TYPE
   SYNTAX      SEQUENCE OF Gs2328pMLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2328pMLDSnooping 6 }

gs2328pMLDSnoopingSSMEntry OBJECT-TYPE
   SYNTAX      Gs2328pMLDSnoopingSSMEntry
   MAX-ACCESS  not-accessible
   STATUS      current
   DESCRIPTION
       ""
   INDEX    { gs2328pMLDSnoopingSSMIndex  }
   ::= { gs2328pMLDSnoopingSSMTable 1 }

Gs2328pMLDSnoopingSSMEntry ::= SEQUENCE {
   gs2328pMLDSnoopingSSMIndex          Integer32,
   gs2328pMLDSnoopingSSMVLANID         Integer32,
   gs2328pMLDSnoopingSSMGroup          DisplayString,
   gs2328pMLDSnoopingSSMPort           Integer32,
   gs2328pMLDSnoopingSSMMode           DisplayString,
   gs2328pMLDSnoopingSSMSourceAddress  DisplayString,
   gs2328pMLDSnoopingSSMType           DisplayString
}

gs2328pMLDSnoopingSSMIndex OBJECT-TYPE
   SYNTAX      Integer32(1..65535)
   MAX-ACCESS  not-accessible
   STATUS      current
   DESCRIPTION
       "MLD Snooping SSM Index"
   ::= { gs2328pMLDSnoopingSSMEntry 1 }

gs2328pMLDSnoopingSSMVLANID OBJECT-TYPE
   SYNTAX      Integer32(1..4095)
   MAX-ACCESS  read-only
   STATUS      current
   DESCRIPTION
       "VLAN ID of the group. "
   ::= { gs2328pMLDSnoopingSSMEntry 2 }

gs2328pMLDSnoopingSSMGroup OBJECT-TYPE
   SYNTAX      DisplayString
   MAX-ACCESS  read-only
   STATUS      current
   DESCRIPTION
       "Group address of the group displayed."
   ::= { gs2328pMLDSnoopingSSMEntry 3 }

gs2328pMLDSnoopingSSMPort OBJECT-TYPE
   SYNTAX      Integer32(1..65535)
   MAX-ACCESS  read-only
   STATUS      current
   DESCRIPTION
       "Ports under this group."
   ::= { gs2328pMLDSnoopingSSMEntry 4 }
   
gs2328pMLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2328pMLDSnoopingSSMEntry 5 }
   
gs2328pMLDSnoopingSSMSourceAddress OBJECT-TYPE
   SYNTAX      DisplayString
   MAX-ACCESS  read-only
   STATUS      current
   DESCRIPTION
       "IP Address of the source. Currently, system limits the total number of
       IP source addresses for filtering to be 128."
   ::= { gs2328pMLDSnoopingSSMEntry 6 }

gs2328pMLDSnoopingSSMType OBJECT-TYPE
   SYNTAX      DisplayString
   MAX-ACCESS  read-only
   STATUS      current
   DESCRIPTION
       "Indicates the Type. It can be either Allow or Deny."
   ::= { gs2328pMLDSnoopingSSMEntry 7 }      
   

gs2328pMVR                                                                   OBJECT IDENTIFIER ::= { gs2328pConfiguration 18 }

gs2328pMVRConfiguration                                                      OBJECT IDENTIFIER ::= { gs2328pMVR 1 }

gs2328pMVRMode  OBJECT-TYPE
   SYNTAX      INTEGER { disable(0), enable(1) }
   MAX-ACCESS  read-write
   STATUS      current
   DESCRIPTION
       "Enable/Disable the Global MVR. "
   ::= { gs2328pMVRConfiguration 1 }

gs2328pMVRVLANId  OBJECT-TYPE
   SYNTAX      Integer32(1..4094)
   MAX-ACCESS  read-write
   STATUS      current
   DESCRIPTION
       "Specify the Multicast VLAN ID. "
   ::= { gs2328pMVRConfiguration 2 }

gs2328pMVRPortConfigurationTable OBJECT-TYPE
   SYNTAX      SEQUENCE OF Gs2328pMVRPortConfigurationEntry
   MAX-ACCESS  not-accessible
   STATUS      current
   DESCRIPTION
       " Configure MVR Port Configuration. "
   ::= { gs2328pMVRConfiguration 3 }

gs2328pMVRPortConfigurationEntry OBJECT-TYPE
   SYNTAX      Gs2328pMVRPortConfigurationEntry
   MAX-ACCESS  not-accessible
   STATUS      current
   DESCRIPTION
       ""
   INDEX    { ifIndex  }
   ::= { gs2328pMVRPortConfigurationTable 1 }

Gs2328pMVRPortConfigurationEntry ::= SEQUENCE {
   gs2328pMVRPortConfigurationMode	INTEGER,
   gs2328pMVRPortConfigurationType  	INTEGER,
   gs2328pMVRPortConfigurationImmediateLeave    INTEGER
}

gs2328pMVRPortConfigurationMode OBJECT-TYPE
   SYNTAX      INTEGER { disable(0), enable(1) }
   MAX-ACCESS  read-write
   STATUS      current
   DESCRIPTION
       "Enable MVR on the port. "
   ::= { gs2328pMVRPortConfigurationEntry 1 }

gs2328pMVRPortConfigurationType OBJECT-TYPE
   SYNTAX      INTEGER { receiver(0), source(1) }
   MAX-ACCESS  read-write
   STATUS      current
   DESCRIPTION
       "Specify the MVR port type on the port. "
   ::= { gs2328pMVRPortConfigurationEntry 2 }
   
gs2328pMVRPortConfigurationImmediateLeave OBJECT-TYPE
   SYNTAX      INTEGER { disable(0), enable(1) }
   MAX-ACCESS  read-write
   STATUS      current
   DESCRIPTION
       "Enable the fast leave on the port. "
   ::= { gs2328pMVRPortConfigurationEntry 3 }
      

gs2328pMVRPortGroupFiltering                                                      OBJECT IDENTIFIER ::= { gs2328pMVR 2 }

gs2328pMVRPortGroupFilteringCreate OBJECT-TYPE
   SYNTAX       Integer32
   MAX-ACCESS   read-write
   STATUS       current
   DESCRIPTION
       "default: 0
       0 : None  (read only) 1 : Create MLD Snooping Port Group Filtering "
   ::= { gs2328pMVRPortGroupFiltering 1 }

gs2328pMVRPortGroupFilteringTable OBJECT-TYPE
   SYNTAX      SEQUENCE OF Gs2328pMVRPortGroupFilteringEntry
   MAX-ACCESS  not-accessible
   STATUS      current
   DESCRIPTION
       " Configure MVR port group filtering. "
   ::= { gs2328pMVRPortGroupFiltering 2 }

gs2328pMVRPortGroupFilteringEntry OBJECT-TYPE
   SYNTAX      Gs2328pMVRPortGroupFilteringEntry
   MAX-ACCESS  not-accessible
   STATUS      current
   DESCRIPTION
       ""
   INDEX    { gs2328pMVRPortGroupFilteringIndex  }
   ::= { gs2328pMVRPortGroupFilteringTable 1 }

Gs2328pMVRPortGroupFilteringEntry ::= SEQUENCE {
   gs2328pMVRPortGroupFilteringIndex         Integer32,
   gs2328pMVRPortGroupFilteringPort          Integer32,
   gs2328pMVRPortGroupFilteringStartGroups   DisplayString,
   gs2328pMVRPortGroupFilteringEndGroups     DisplayString,
   gs2328pMVRPortGroupFilteringRowStatus     INTEGER
}

gs2328pMVRPortGroupFilteringIndex OBJECT-TYPE
   SYNTAX      Integer32(1..65535)
   MAX-ACCESS  not-accessible
   STATUS      current
   DESCRIPTION
       "MVR Port Group Filtering Configuration Index. "
   ::= { gs2328pMVRPortGroupFilteringEntry 1 }

gs2328pMVRPortGroupFilteringPort OBJECT-TYPE
   SYNTAX      Integer32(1..65535)
   MAX-ACCESS  read-write
   STATUS      current
   DESCRIPTION
       "The logical port for the settings. "
   ::= { gs2328pMVRPortGroupFilteringEntry 2 }

gs2328pMVRPortGroupFilteringStartGroups OBJECT-TYPE
   SYNTAX      DisplayString
   MAX-ACCESS  read-write
   STATUS      current
   DESCRIPTION
       "The IP Multicast Group that will be allowed. "
   ::= { gs2328pMVRPortGroupFilteringEntry 3 }

gs2328pMVRPortGroupFilteringEndGroups OBJECT-TYPE
   SYNTAX      DisplayString
   MAX-ACCESS  read-write
   STATUS      current
   DESCRIPTION
       "The IP Multicast Group that will be allowed. "
   ::= { gs2328pMVRPortGroupFilteringEntry 4 }   

gs2328pMVRPortGroupFilteringRowStatus OBJECT-TYPE
   SYNTAX      INTEGER { active(1), notInservice(2), destroy(4)}
   MAX-ACCESS  read-write
   STATUS      current
   DESCRIPTION
       "1: active
        2: notInservice
        4: destroy"
   ::= { gs2328pMVRPortGroupFilteringEntry 5 }

gs2328pMVRGroupsTable OBJECT-TYPE
   SYNTAX      SEQUENCE OF Gs2328pMVRGroupsEntry
   MAX-ACCESS  not-accessible
   STATUS      current
   DESCRIPTION
       "MVR Groups Information . "
   ::= { gs2328pMVR 3 }

gs2328pMVRGroupsEntry OBJECT-TYPE
   SYNTAX      Gs2328pMVRGroupsEntry
   MAX-ACCESS  not-accessible
   STATUS      current
   DESCRIPTION
       ""
   INDEX    { gs2328pMVRGroupsIndex  }
   ::= { gs2328pMVRGroupsTable 1 }

Gs2328pMVRGroupsEntry ::= SEQUENCE {
   gs2328pMVRGroupsIndex          Integer32,
   gs2328pMVRGroupsVLANID         Integer32,
   gs2328pMVRGroups               InetAddress,
   gs2328pMVRGroupsMemberships    DisplayString
}

gs2328pMVRGroupsIndex OBJECT-TYPE
   SYNTAX      Integer32(1..65535)
   MAX-ACCESS  not-accessible
   STATUS      current
   DESCRIPTION
       "MVR Groups Index"
   ::= { gs2328pMVRGroupsEntry 1 }

gs2328pMVRGroupsVLANID OBJECT-TYPE
   SYNTAX      Integer32(1..4095)
   MAX-ACCESS  read-only
   STATUS      current
   DESCRIPTION
       "VLAN ID of the group. "
   ::= { gs2328pMVRGroupsEntry 2 }

gs2328pMVRGroups OBJECT-TYPE
   SYNTAX      DisplayString
   MAX-ACCESS  read-only
   STATUS      current
   DESCRIPTION
       "Group address of the group displayed."
   ::= { gs2328pMVRGroupsEntry 3 }

gs2328pMVRGroupsMemberships OBJECT-TYPE
   SYNTAX      DisplayString
   MAX-ACCESS  read-only
   STATUS      current
   DESCRIPTION
       "Ports under this group."
   ::= { gs2328pMVRGroupsEntry 4 }
            

gs2328pMVRStatus                                                      OBJECT IDENTIFIER ::= { gs2328pMVR 4 }

gs2328pMVRstatisticClear OBJECT-TYPE
   SYNTAX      INTEGER { none(0), clear(1)}
   MAX-ACCESS  read-write
   STATUS      current
   DESCRIPTION
       "Clears all Statistics counters."
   ::= { gs2328pMVRStatus 1 }

gs2328pMVRstatisticVLANID OBJECT-TYPE
   SYNTAX      Integer32(1..4095)
   MAX-ACCESS  read-only
   STATUS      current
   DESCRIPTION
       "The VLAN ID of the entry. "
   ::= { gs2328pMVRStatus 2 }

gs2328pMVRstatisticV1ReportsReceived OBJECT-TYPE
   SYNTAX      Counter32
   MAX-ACCESS  read-only
   STATUS      current
   DESCRIPTION
       "The number of Received V1 Reports. "
   ::= { gs2328pMVRStatus 3 }

gs2328pMVRstatisticV2ReportsReceived OBJECT-TYPE
   SYNTAX      Counter32
   MAX-ACCESS  read-only
   STATUS      current
   DESCRIPTION
       "The number of Received V2 Reports. "
   ::= { gs2328pMVRStatus 4 }
   
gs2328pMVRstatisticV3ReportsReceived OBJECT-TYPE
   SYNTAX      Counter32
   MAX-ACCESS  read-only
   STATUS      current
   DESCRIPTION
       "The number of Received V3 Reports. "
   ::= { gs2328pMVRStatus 5 }

gs2328pMVRstatisticV2LeavesReceived OBJECT-TYPE
   SYNTAX      Counter32
   MAX-ACCESS  read-only
   STATUS      current
   DESCRIPTION
       "The number of Received V2 Leaves. "
   ::= { gs2328pMVRStatus 6 }

gs2328pLACP                                                     OBJECT IDENTIFIER ::= { gs2328pConfiguration 19 }

gs2328pLACPConf                                                 OBJECT IDENTIFIER ::= { gs2328pLACP 1 }

gs2328pLACPPortConfigurationTable OBJECT-TYPE
   SYNTAX      SEQUENCE OF Gs2328pLACPPortConfigurationEntry
   MAX-ACCESS  not-accessible
   STATUS      current
   DESCRIPTION
       " "
   ::= { gs2328pLACPConf 1 }

gs2328pLACPPortConfigurationEntry OBJECT-TYPE
   SYNTAX      Gs2328pLACPPortConfigurationEntry
   MAX-ACCESS  not-accessible
   STATUS      current
   DESCRIPTION
       ""
   INDEX    { gs2328pLACPPortConfigurationPort  }
   ::= { gs2328pLACPPortConfigurationTable 1 }
   
Gs2328pLACPPortConfigurationEntry ::= SEQUENCE {
    gs2328pLACPPortConfigurationPort         Integer32,
    gs2328pLACPPortConfigurationMode         INTEGER,
    gs2328pLACPPortConfigurationKey          Integer32,
    gs2328pLACPPortConfigurationRole         INTEGER
}

gs2328pLACPPortConfigurationPort OBJECT-TYPE
   SYNTAX      Integer32(1..4095)
   MAX-ACCESS  not-accessible
   STATUS      current
   DESCRIPTION
       " "
   ::= { gs2328pLACPPortConfigurationEntry 1 }

gs2328pLACPPortConfigurationMode OBJECT-TYPE
   SYNTAX      INTEGER { disable(0), enable(1) }
   MAX-ACCESS  read-write
   STATUS      current
   DESCRIPTION
       "Enable/Disable LACP Mode."
   ::= { gs2328pLACPPortConfigurationEntry 2 }
   
gs2328pLACPPortConfigurationKey OBJECT-TYPE
   SYNTAX      Integer32(0..65535)
   MAX-ACCESS  read-write
   STATUS      current
   DESCRIPTION
       "LACP key : 1-65535. 0 : Auto"
   ::= { gs2328pLACPPortConfigurationEntry 3 }
   
gs2328pLACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2328pLACPPortConfigurationEntry 4 }

gs2328pLACPSystemStatusTable OBJECT-TYPE
   SYNTAX      SEQUENCE OF Gs2328pLACPSystemStatusEntry
   MAX-ACCESS  not-accessible
   STATUS      current
   DESCRIPTION
       " "
   ::= { gs2328pLACP 2 }

gs2328pLACPSystemStatusEntry OBJECT-TYPE
   SYNTAX      Gs2328pLACPSystemStatusEntry
   MAX-ACCESS  not-accessible
   STATUS      current
   DESCRIPTION
       ""
   INDEX    { gs2328pLACPSystemStatusIndex  }
   ::= { gs2328pLACPSystemStatusTable 1 }

Gs2328pLACPSystemStatusEntry ::= SEQUENCE {
   gs2328pLACPSystemStatusIndex             Integer32,
   gs2328pLACPSystemStatusAggrID            DisplayString,
   gs2328pLACPSystemStatusPartnerSystemID   MacAddress,
   gs2328pLACPSystemStatusPartnerKey        DisplayString,
   gs2328pLACPSystemStatusLastchanged       DisplayString,
   gs2328pLACPSystemStatusLocalPorts        DisplayString
}

gs2328pLACPSystemStatusIndex OBJECT-TYPE
   SYNTAX      Integer32(1..12)
   MAX-ACCESS  not-accessible
   STATUS      current
   DESCRIPTION
       " "
   ::= { gs2328pLACPSystemStatusEntry 1 }

gs2328pLACPSystemStatusAggrID OBJECT-TYPE
   SYNTAX      DisplayString
   MAX-ACCESS  read-only
   STATUS      current
   DESCRIPTION
       "The Aggregation ID associated with this aggregation instance."
   ::= { gs2328pLACPSystemStatusEntry 2 }
   
gs2328pLACPSystemStatusPartnerSystemID OBJECT-TYPE
   SYNTAX      MacAddress
   MAX-ACCESS  read-only
   STATUS      current
   DESCRIPTION
       "The system ID (MAC address) of the aggregation partner."
   ::= { gs2328pLACPSystemStatusEntry 3 }

gs2328pLACPSystemStatusPartnerKey OBJECT-TYPE
   SYNTAX      DisplayString
   MAX-ACCESS  read-only
   STATUS      current
   DESCRIPTION
       " The Key that the partner has assigned to this aggregation ID. "
   ::= { gs2328pLACPSystemStatusEntry 4 }

gs2328pLACPSystemStatusLastchanged OBJECT-TYPE
   SYNTAX      DisplayString
   MAX-ACCESS  read-only
   STATUS      current
   DESCRIPTION
       " The time since this aggregation changed. "
   ::= { gs2328pLACPSystemStatusEntry 5 }
   
gs2328pLACPSystemStatusLocalPorts OBJECT-TYPE
   SYNTAX      DisplayString
   MAX-ACCESS  read-only
   STATUS      current
   DESCRIPTION
       " Shows which ports are a part of this aggregation for this switch. "
   ::= { gs2328pLACPSystemStatusEntry 6 }

gs2328pLACPStatusTable OBJECT-TYPE
   SYNTAX      SEQUENCE OF Gs2328pLACPStatusEntry
   MAX-ACCESS  not-accessible
   STATUS      current
   DESCRIPTION
       " "
   ::= { gs2328pLACP 3 }

gs2328pLACPStatusEntry OBJECT-TYPE
   SYNTAX      Gs2328pLACPStatusEntry
   MAX-ACCESS  not-accessible
   STATUS      current
   DESCRIPTION
       ""
   INDEX    { gs2328pLACPStatusPort  }
   ::= { gs2328pLACPStatusTable 1 }

Gs2328pLACPStatusEntry ::= SEQUENCE {
   gs2328pLACPStatusPort                Integer32,
   gs2328pLACPStatusLACP                DisplayString,
   gs2328pLACPStatusKey                 DisplayString,
   gs2328pLACPStatusAggrID              DisplayString,
   gs2328pLACPStatusPartnerSystemID     DisplayString,
   gs2328pLACPStatusPartnerPort         DisplayString
}

gs2328pLACPStatusPort OBJECT-TYPE
   SYNTAX      Integer32(1..4095)
   MAX-ACCESS  not-accessible
   STATUS      current
   DESCRIPTION
       " "
   ::= { gs2328pLACPStatusEntry 1 }

gs2328pLACPStatusLACP OBJECT-TYPE
   SYNTAX      DisplayString
   MAX-ACCESS  read-only
   STATUS      current
   DESCRIPTION
       "Enabled means that LACP is enabled and the port link is up. 
        Disabled means that LACP is not enabled or that the port link is down. 
        Backup means that the port could not join the aggregation group but will join if other port leaves. 
        Meanwhile it's LACP status is disabled."
   ::= { gs2328pLACPStatusEntry 2 }
   
gs2328pLACPStatusKey OBJECT-TYPE
   SYNTAX      DisplayString
   MAX-ACCESS  read-only
   STATUS      current
   DESCRIPTION
       "The key assigned to this port. Only ports with the same key can aggregate together."
   ::= { gs2328pLACPStatusEntry 3 }

gs2328pLACPStatusAggrID	 OBJECT-TYPE
   SYNTAX      DisplayString
   MAX-ACCESS  read-only
   STATUS      current
   DESCRIPTION
       " The Aggregation ID assigned to this aggregation group. "
   ::= { gs2328pLACPStatusEntry 4 }

gs2328pLACPStatusPartnerSystemID OBJECT-TYPE
   SYNTAX      DisplayString
   MAX-ACCESS  read-only
   STATUS      current
   DESCRIPTION
       " The partner's System ID. "
   ::= { gs2328pLACPStatusEntry 5 }
   
gs2328pLACPStatusPartnerPort OBJECT-TYPE
   SYNTAX      DisplayString
   MAX-ACCESS  read-only
   STATUS      current
   DESCRIPTION
       " The partner's port number connected to this port. "
   ::= { gs2328pLACPStatusEntry 6 }


gs2328pLACPStatisticsTable OBJECT-TYPE
   SYNTAX      SEQUENCE OF Gs2328pLACPStatisticsEntry
   MAX-ACCESS  not-accessible
   STATUS      current
   DESCRIPTION
       " "
   ::= { gs2328pLACP 4 }

gs2328pLACPStatisticsEntry OBJECT-TYPE
   SYNTAX      Gs2328pLACPStatisticsEntry
   MAX-ACCESS  not-accessible
   STATUS      current
   DESCRIPTION
       ""
   INDEX    { gs2328pLACPStatisticsPort  }
   ::= { gs2328pLACPStatisticsTable 1 }

Gs2328pLACPStatisticsEntry ::= SEQUENCE {
   gs2328pLACPStatisticsPort        Integer32,
   gs2328pLACPReceived              Counter32,
   gs2328pLACPTransmitted           Counter32,
   gs2328pLACPDiscardedUnknown      Counter32,
   gs2328pLACPDiscardedIllegal      Counter32
}

gs2328pLACPStatisticsPort OBJECT-TYPE
   SYNTAX      Integer32(1..4095)
   MAX-ACCESS  not-accessible
   STATUS      current
   DESCRIPTION
       " "
   ::= { gs2328pLACPStatisticsEntry 1 }
   
gs2328pLACPReceived OBJECT-TYPE
   SYNTAX      Counter32
   MAX-ACCESS  read-only
   STATUS      current
   DESCRIPTION
       "Shows how many LACP frames have been received at each port. "
   ::= { gs2328pLACPStatisticsEntry 2 }

gs2328pLACPTransmitted OBJECT-TYPE
   SYNTAX      Counter32
   MAX-ACCESS  read-only
   STATUS      current
   DESCRIPTION
       " Shows how many LACP frames have been sent from each port. "
   ::= { gs2328pLACPStatisticsEntry 3 }

gs2328pLACPDiscardedUnknown OBJECT-TYPE
   SYNTAX      Counter32
   MAX-ACCESS  read-only
   STATUS      current
   DESCRIPTION
       " Shows how many unknown LACP frames have been discarded at each port. "
   ::= { gs2328pLACPStatisticsEntry 4 }
   
gs2328pLACPDiscardedIllegal OBJECT-TYPE
   SYNTAX      Counter32
   MAX-ACCESS  read-only
   STATUS      current
   DESCRIPTION
       " Shows how many illegal LACP frames have been discarded at each port. "
   ::= { gs2328pLACPStatisticsEntry 5 }
   
gs2328pLACPStatisticsClear OBJECT-TYPE
   SYNTAX      INTEGER { none(0), clear(1) }
   MAX-ACCESS  read-write
   STATUS      current
   DESCRIPTION
       "default: 0
       0: none
       1: clear"
   ::= { gs2328pLACP 5 }
   
gs2328pSTP                                                     OBJECT IDENTIFIER ::= { gs2328pConfiguration 20 }

gs2328pSTPBridgeBasicConf                                                 OBJECT IDENTIFIER ::= { gs2328pSTP 1 }

gs2328pSTPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2328pSTPBridgeBasicConf 1 }

gs2328pSTPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2328pSTPBridgeBasicConf 2 }
   
gs2328pSTPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2328pSTPBridgeBasicConf 3 }
   
gs2328pSTPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2328pSTPBridgeBasicConf 4 }
   
gs2328pSTPBridgeMaximumHopCount OBJECT-TYPE
   SYNTAX      Integer32(6..40)
   MAX-ACCESS  read-write
   STATUS      current
   DESCRIPTION
       " Maximum Hop Count default: 20, range: 6 - 40."
   ::= { gs2328pSTPBridgeBasicConf 5 }
   
gs2328pSTPBridgeTransmitHoldCount OBJECT-TYPE
   SYNTAX      Integer32(1..10)
   MAX-ACCESS  read-write
   STATUS      current
   DESCRIPTION
       " Transmit Hold Count default: 6, range: 1 - 10."
   ::= { gs2328pSTPBridgeBasicConf 6 }
   
gs2328pSTPBridgeAdvancedConf                                                 OBJECT IDENTIFIER ::= { gs2328pSTP 2 }

gs2328pSTPBridgeEdgePortBPDUFiltering OBJECT-TYPE
   SYNTAX      INTEGER { disable(0), enable(1) }
   MAX-ACCESS  read-write
   STATUS      current
   DESCRIPTION
       " default: 0,
        0: disable
        1: enable"
   ::= { gs2328pSTPBridgeAdvancedConf 1 }
   
gs2328pSTPBridgeEdgePortBPDUGuard OBJECT-TYPE
   SYNTAX      INTEGER { disable(0), enable(1) }
   MAX-ACCESS  read-write
   STATUS      current
   DESCRIPTION
       " default: 0,
        0: disable
        1: enable"
   ::= { gs2328pSTPBridgeAdvancedConf 2 }
   
gs2328pSTPBridgePortErrorRecoveryTimeout OBJECT-TYPE
   SYNTAX      Integer32(0..86400)
   MAX-ACCESS  read-write
   STATUS      current
   DESCRIPTION
       " Port Error Recovery Timeout disable: 0, range: 30 - 86400."
   ::= { gs2328pSTPBridgeAdvancedConf 3 }
   
gs2328pSTPMSTIConf                                                 OBJECT IDENTIFIER ::= { gs2328pSTP 3 }
   
gs2328pSTPMSTIConfigurationName OBJECT-TYPE
   SYNTAX      DisplayString (SIZE (1..32))
   MAX-ACCESS  read-write
   STATUS      current
   DESCRIPTION
       "A text string up to 32 characters long."
   ::= { gs2328pSTPMSTIConf 1 }
   
gs2328pSTPMSTIConfigurationRevision   OBJECT-TYPE
   SYNTAX      Integer32(0..65535)
   MAX-ACCESS  read-write
   STATUS      current
   DESCRIPTION
       " Configuration Revision default: 0, range: 0 - 65535."
   ::= { gs2328pSTPMSTIConf 2 }
   
gs2328pSTPMSTIMappingConf                                                 OBJECT IDENTIFIER ::= { gs2328pSTP 4 }
   
gs2328pSTPMSTI1VLANsMapped OBJECT-TYPE
   SYNTAX      DisplayString (SIZE (1..4096))
   MAX-ACCESS  read-write
   STATUS      current
   DESCRIPTION
       "The list of VLANs mapped to the MSTI1. 
       The VLANs must be separated with comma or space. 
       An unused MSTI should just be left empty. "
   ::= { gs2328pSTPMSTIMappingConf 1 }

gs2328pSTPMSTI2VLANsMapped OBJECT-TYPE
   SYNTAX      DisplayString (SIZE (1..4096))
   MAX-ACCESS  read-write
   STATUS      current
   DESCRIPTION
       "The list of VLANs mapped to the MSTI2. 
       The VLANs must be separated with comma or space. 
       An unused MSTI should just be left empty. "
   ::= { gs2328pSTPMSTIMappingConf 2 }
   
gs2328pSTPMSTI3VLANsMapped OBJECT-TYPE
   SYNTAX      DisplayString (SIZE (1..4096))
   MAX-ACCESS  read-write
   STATUS      current
   DESCRIPTION
       "The list of VLANs mapped to the MSTI3. 
       The VLANs must be separated with comma or space. 
       An unused MSTI should just be left empty. "
   ::= { gs2328pSTPMSTIMappingConf 3 }
   
gs2328pSTPMSTI4VLANsMapped OBJECT-TYPE
   SYNTAX      DisplayString (SIZE (1..4096))
   MAX-ACCESS  read-write
   STATUS      current
   DESCRIPTION
       "The list of VLANs mapped to the MSTI4. 
       The VLANs must be separated with comma or space. 
       An unused MSTI should just be left empty. "
   ::= { gs2328pSTPMSTIMappingConf 4 }
   
gs2328pSTPMSTI5VLANsMapped OBJECT-TYPE
   SYNTAX      DisplayString (SIZE (1..4096))
   MAX-ACCESS  read-write
   STATUS      current
   DESCRIPTION
       "The list of VLANs mapped to the MSTI5. 
       The VLANs must be separated with comma or space. 
       An unused MSTI should just be left empty. "
   ::= { gs2328pSTPMSTIMappingConf 5 }

gs2328pSTPMSTI6VLANsMapped OBJECT-TYPE
   SYNTAX      DisplayString (SIZE (1..4096))
   MAX-ACCESS  read-write
   STATUS      current
   DESCRIPTION
       "The list of VLANs mapped to the MSTI6. 
       The VLANs must be separated with comma or space. 
       An unused MSTI should just be left empty. "
   ::= { gs2328pSTPMSTIMappingConf 6 }
   
gs2328pSTPMSTI7VLANsMapped OBJECT-TYPE
   SYNTAX      DisplayString (SIZE (1..4096))
   MAX-ACCESS  read-write
   STATUS      current
   DESCRIPTION
       "The list of VLANs mapped to the MSTI7. 
       The VLANs must be separated with comma or space. 
       An unused MSTI should just be left empty. "
   ::= { gs2328pSTPMSTIMappingConf 7 }
   
gs2328pSTPMSTIPriority                                                 OBJECT IDENTIFIER ::= { gs2328pSTP 5 }
   
gs2328pSTPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328pSTPMSTIPriority 1 }
   
gs2328pSTPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328pSTPMSTIPriority 2 }
   
gs2328pSTPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328pSTPMSTIPriority 3 }
   
gs2328pSTPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328pSTPMSTIPriority 4 }
   
gs2328pSTPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328pSTPMSTIPriority 5 }
   
gs2328pSTPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328pSTPMSTIPriority 6 }

gs2328pSTPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328pSTPMSTIPriority 7 }  

gs2328pSTPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2328pSTPMSTIPriority 8 }
   
gs2328pSTPCISTPort                                                          OBJECT IDENTIFIER ::= { gs2328pSTP 6 }

gs2328pSTPCISTAggregatedPort                                                OBJECT IDENTIFIER ::= { gs2328pSTPCISTPort 1 }
   
gs2328pSTPCISTAggregatedPortSTPEnabled OBJECT-TYPE
   SYNTAX      INTEGER { disable(0), enable(1) }
   MAX-ACCESS  read-write
   STATUS      current
   DESCRIPTION
       " default: 0,
        0: disable
        1: enable"
   ::= { gs2328pSTPCISTAggregatedPort 1 }
   
gs2328pSTPCISTAggregatedPortPathCost OBJECT-TYPE
   SYNTAX      Integer32(0..200000000)
   MAX-ACCESS  read-write
   STATUS      current
   DESCRIPTION
       " Auto: 0,
        Specific Path Cost range: 1 - 200000000."
   ::= { gs2328pSTPCISTAggregatedPort 2 }
   
gs2328pSTPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2328pSTPCISTAggregatedPort 3 }
   
gs2328pSTPCISTAggregatedPortAdminEdge OBJECT-TYPE
   SYNTAX      INTEGER { non-edge(0), edge(1) }
   MAX-ACCESS  read-write
   STATUS      current
   DESCRIPTION
       " default: 0,
        0: non-edge
        1: edge"
   ::= { gs2328pSTPCISTAggregatedPort 4 }

gs2328pSTPCISTAggregatedPortAutoEdge OBJECT-TYPE
   SYNTAX      INTEGER { disable(0), enable(1) }
   MAX-ACCESS  read-write
   STATUS      current
   DESCRIPTION
       " default: 1,
        0: disable
        1: enable"
   ::= { gs2328pSTPCISTAggregatedPort 5 }
   
gs2328pSTPCISTAggregatedPortRestrictedRole OBJECT-TYPE
   SYNTAX      INTEGER { disable(0), enable(1) }
   MAX-ACCESS  read-write
   STATUS      current
   DESCRIPTION
       " default: 0,
        0: disable
        1: enable"
   ::= { gs2328pSTPCISTAggregatedPort 6 }
   
gs2328pSTPCISTAggregatedPortRestrictedTCN OBJECT-TYPE
   SYNTAX      INTEGER { disable(0), enable(1) }
   MAX-ACCESS  read-write
   STATUS      current
   DESCRIPTION
       " default: 0,
        0: disable
        1: enable"
   ::= { gs2328pSTPCISTAggregatedPort 7 }
   
gs2328pSTPCISTAggregatedPortBPDUGuard OBJECT-TYPE
   SYNTAX      INTEGER { disable(0), enable(1) }
   MAX-ACCESS  read-write
   STATUS      current
   DESCRIPTION
       " default: 0,
        0: disable
        1: enable"
   ::= { gs2328pSTPCISTAggregatedPort 8 }
   
gs2328pSTPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2328pSTPCISTAggregatedPort 9 }
   
gs2328pSTPCISTNormalPortTable OBJECT-TYPE
   SYNTAX      SEQUENCE OF Gs2328pSTPCISTNormalPortEntry
   MAX-ACCESS  not-accessible
   STATUS      current
   DESCRIPTION
       " Show CIST Normal Port Configurations. "
   ::= { gs2328pSTPCISTPort 2 }

gs2328pSTPCISTNormalPortEntry OBJECT-TYPE
   SYNTAX      Gs2328pSTPCISTNormalPortEntry
   MAX-ACCESS  not-accessible
   STATUS      current
   DESCRIPTION
       ""
   INDEX    { gs2328pSTPCISTNormalPortConfPort  }
   ::= { gs2328pSTPCISTNormalPortTable 1 }

Gs2328pSTPCISTNormalPortEntry ::= SEQUENCE {
   gs2328pSTPCISTNormalPortConfPort         Integer32,
   gs2328pSTPCISTNormalPortSTPEnabled       INTEGER,
   gs2328pSTPCISTNormalPortPathCost         Integer32,
   gs2328pSTPCISTNormalPortPriority         Integer32,
   gs2328pSTPCISTNormalPortAdminEdge        INTEGER,
   gs2328pSTPCISTNormalPortAutoEdge         INTEGER,
   gs2328pSTPCISTNormalPortRestrictedRole   INTEGER,
   gs2328pSTPCISTNormalPortRestrictedTCN    INTEGER,
   gs2328pSTPCISTNormalPortBPDUGuard        INTEGER,
   gs2328pSTPCISTNormalPortPointtoPoint     INTEGER
}

gs2328pSTPCISTNormalPortConfPort OBJECT-TYPE
   SYNTAX      Integer32(1..4095)
   MAX-ACCESS  not-accessible
   STATUS      current
   DESCRIPTION
       " port, range : 1 - port number. "
   ::= { gs2328pSTPCISTNormalPortEntry 1 }
   
gs2328pSTPCISTNormalPortSTPEnabled OBJECT-TYPE
   SYNTAX      INTEGER { disable(0), enable(1) }
   MAX-ACCESS  read-write
   STATUS      current
   DESCRIPTION
       " default: 0,
        0: disable
        1: enable"
   ::= { gs2328pSTPCISTNormalPortEntry 2 }
   
gs2328pSTPCISTNormalPortPathCost OBJECT-TYPE
   SYNTAX      Integer32(0..200000000)
   MAX-ACCESS  read-write
   STATUS      current
   DESCRIPTION
       " Auto: 0,
        Specific Path Cost range: 1 - 200000000."
   ::= { gs2328pSTPCISTNormalPortEntry 3 }
   
gs2328pSTPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2328pSTPCISTNormalPortEntry 4 }
   
gs2328pSTPCISTNormalPortAdminEdge OBJECT-TYPE
   SYNTAX      INTEGER { non-edge(0), edge(1) }
   MAX-ACCESS  read-write
   STATUS      current
   DESCRIPTION
       " default: 0,
        0: non-edge
        1: edge"
   ::= { gs2328pSTPCISTNormalPortEntry 5 }
   
gs2328pSTPCISTNormalPortAutoEdge OBJECT-TYPE
   SYNTAX      INTEGER { disable(0), enable(1) }
   MAX-ACCESS  read-write
   STATUS      current
   DESCRIPTION
       " default: 1,
        0: disable
        1: enable"
   ::= { gs2328pSTPCISTNormalPortEntry 6 }
   
gs2328pSTPCISTNormalPortRestrictedRole OBJECT-TYPE
   SYNTAX      INTEGER { disable(0), enable(1) }
   MAX-ACCESS  read-write
   STATUS      current
   DESCRIPTION
       " default: 0,
        0: disable
        1: enable"
   ::= { gs2328pSTPCISTNormalPortEntry 7 }
   
gs2328pSTPCISTNormalPortRestrictedTCN OBJECT-TYPE
   SYNTAX      INTEGER { disable(0), enable(1) }
   MAX-ACCESS  read-write
   STATUS      current
   DESCRIPTION
       " default: 0,
        0: disable
        1: enable"
   ::= { gs2328pSTPCISTNormalPortEntry 8 }
   
gs2328pSTPCISTNormalPortBPDUGuard OBJECT-TYPE
   SYNTAX      INTEGER { disable(0), enable(1) }
   MAX-ACCESS  read-write
   STATUS      current
   DESCRIPTION
       " default: 0,
        0: disable
        1: enable"
   ::= { gs2328pSTPCISTNormalPortEntry 9 }
   
gs2328pSTPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2328pSTPCISTNormalPortEntry 10 }
   

gs2328pSTPMSTIPort                                                          OBJECT IDENTIFIER ::= { gs2328pSTP 7 }

gs2328pSTPMSTI1Port                                                         OBJECT IDENTIFIER ::= { gs2328pSTPMSTIPort 1 }

gs2328pSTPMSTI1AggregatedPort                                                OBJECT IDENTIFIER ::= { gs2328pSTPMSTI1Port 1 }
      
gs2328pSTPMSTI1AggregatedPortPathCost OBJECT-TYPE
   SYNTAX      Integer32(0..200000000)
   MAX-ACCESS  read-write
   STATUS      current
   DESCRIPTION
       " Auto: 0,
        Specific Path Cost range: 1 - 200000000."
   ::= { gs2328pSTPMSTI1AggregatedPort 1 }
   
gs2328pSTPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI1AggregatedPort 2 }
   
gs2328pSTPMSTI1NormalPortTable OBJECT-TYPE
   SYNTAX      SEQUENCE OF Gs2328pSTPMSTI1NormalPortEntry
   MAX-ACCESS  not-accessible
   STATUS      current
   DESCRIPTION
       " Show MSTI1 Normal Port Configurations. "
   ::= { gs2328pSTPMSTI1Port 2 }

gs2328pSTPMSTI1NormalPortEntry OBJECT-TYPE
   SYNTAX      Gs2328pSTPMSTI1NormalPortEntry
   MAX-ACCESS  not-accessible
   STATUS      current
   DESCRIPTION
       ""
   INDEX    { gs2328pSTPMSTI1NormalPortConfPort  }
   ::= { gs2328pSTPMSTI1NormalPortTable 1 }

Gs2328pSTPMSTI1NormalPortEntry ::= SEQUENCE {
   gs2328pSTPMSTI1NormalPortConfPort         Integer32,
   gs2328pSTPMSTI1NormalPortPathCost         Integer32,
   gs2328pSTPMSTI1NormalPortPriority         Integer32
}

gs2328pSTPMSTI1NormalPortConfPort OBJECT-TYPE
   SYNTAX      Integer32(1..4095)
   MAX-ACCESS  not-accessible
   STATUS      current
   DESCRIPTION
       " port, range : 1 - port number. "
   ::= { gs2328pSTPMSTI1NormalPortEntry 1 }
   
gs2328pSTPMSTI1NormalPortPathCost OBJECT-TYPE
   SYNTAX      Integer32(0..200000000)
   MAX-ACCESS  read-write
   STATUS      current
   DESCRIPTION
       " Auto: 0,
        Specific Path Cost range: 1 - 200000000."
   ::= { gs2328pSTPMSTI1NormalPortEntry 2 }
   
gs2328pSTPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI1NormalPortEntry 3 }

gs2328pSTPMSTI2Port                                                          OBJECT IDENTIFIER ::= { gs2328pSTPMSTIPort 2 }

gs2328pSTPMSTI2AggregatedPort                                                OBJECT IDENTIFIER ::= { gs2328pSTPMSTI2Port 1 }
      
gs2328pSTPMSTI2AggregatedPortPathCost OBJECT-TYPE
   SYNTAX      Integer32(0..200000000)
   MAX-ACCESS  read-write
   STATUS      current
   DESCRIPTION
       " Auto: 0,
        Specific Path Cost range: 1 - 200000000."
   ::= { gs2328pSTPMSTI2AggregatedPort 1 }
   
gs2328pSTPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI2AggregatedPort 2 }
   
gs2328pSTPMSTI2NormalPortTable OBJECT-TYPE
   SYNTAX      SEQUENCE OF Gs2328pSTPMSTI2NormalPortEntry
   MAX-ACCESS  not-accessible
   STATUS      current
   DESCRIPTION
       " Show MSTI2 Normal Port Configurations. "
   ::= { gs2328pSTPMSTI2Port 2 }

gs2328pSTPMSTI2NormalPortEntry OBJECT-TYPE
   SYNTAX      Gs2328pSTPMSTI2NormalPortEntry
   MAX-ACCESS  not-accessible
   STATUS      current
   DESCRIPTION
       ""
   INDEX    { gs2328pSTPMSTI2NormalPortConfPort  }
   ::= { gs2328pSTPMSTI2NormalPortTable 1 }

Gs2328pSTPMSTI2NormalPortEntry ::= SEQUENCE {
   gs2328pSTPMSTI2NormalPortConfPort         Integer32,
   gs2328pSTPMSTI2NormalPortPathCost         Integer32,
   gs2328pSTPMSTI2NormalPortPriority         Integer32
}

gs2328pSTPMSTI2NormalPortConfPort OBJECT-TYPE
   SYNTAX      Integer32(1..4095)
   MAX-ACCESS  not-accessible
   STATUS      current
   DESCRIPTION
       " port, range : 1 - port number. "
   ::= { gs2328pSTPMSTI2NormalPortEntry 1 }
   
gs2328pSTPMSTI2NormalPortPathCost OBJECT-TYPE
   SYNTAX      Integer32(0..200000000)
   MAX-ACCESS  read-write
   STATUS      current
   DESCRIPTION
       " Auto: 0,
        Specific Path Cost range: 1 - 200000000."
   ::= { gs2328pSTPMSTI2NormalPortEntry 2 }
   
gs2328pSTPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI2NormalPortEntry 3 }
   
gs2328pSTPMSTI3Port                                                          OBJECT IDENTIFIER ::= { gs2328pSTPMSTIPort 3 }

gs2328pSTPMSTI3AggregatedPort                                                OBJECT IDENTIFIER ::= { gs2328pSTPMSTI3Port 1 }
      
gs2328pSTPMSTI3AggregatedPortPathCost OBJECT-TYPE
   SYNTAX      Integer32(0..200000000)
   MAX-ACCESS  read-write
   STATUS      current
   DESCRIPTION
       " Auto: 0,
        Specific Path Cost range: 1 - 200000000."
   ::= { gs2328pSTPMSTI3AggregatedPort 1 }
   
gs2328pSTPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI3AggregatedPort 2 }
   
gs2328pSTPMSTI3NormalPortTable OBJECT-TYPE
   SYNTAX      SEQUENCE OF Gs2328pSTPMSTI3NormalPortEntry
   MAX-ACCESS  not-accessible
   STATUS      current
   DESCRIPTION
       " Show MSTI3 Normal Port Configurations. "
   ::= { gs2328pSTPMSTI3Port 2 }

gs2328pSTPMSTI3NormalPortEntry OBJECT-TYPE
   SYNTAX      Gs2328pSTPMSTI3NormalPortEntry
   MAX-ACCESS  not-accessible
   STATUS      current
   DESCRIPTION
       ""
   INDEX    { gs2328pSTPMSTI3NormalPortConfPort  }
   ::= { gs2328pSTPMSTI3NormalPortTable 1 }

Gs2328pSTPMSTI3NormalPortEntry ::= SEQUENCE {
   gs2328pSTPMSTI3NormalPortConfPort         Integer32,
   gs2328pSTPMSTI3NormalPortPathCost         Integer32,
   gs2328pSTPMSTI3NormalPortPriority         Integer32
}

gs2328pSTPMSTI3NormalPortConfPort OBJECT-TYPE
   SYNTAX      Integer32(1..4095)
   MAX-ACCESS  not-accessible
   STATUS      current
   DESCRIPTION
       " port, range : 1 - port number. "
   ::= { gs2328pSTPMSTI3NormalPortEntry 1 }
   
gs2328pSTPMSTI3NormalPortPathCost OBJECT-TYPE
   SYNTAX      Integer32(0..200000000)
   MAX-ACCESS  read-write
   STATUS      current
   DESCRIPTION
       " Auto: 0,
        Specific Path Cost range: 1 - 200000000."
   ::= { gs2328pSTPMSTI3NormalPortEntry 2 }
   
gs2328pSTPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI3NormalPortEntry 3 }
   
gs2328pSTPMSTI4Port                                                          OBJECT IDENTIFIER ::= { gs2328pSTPMSTIPort 4 }

gs2328pSTPMSTI4AggregatedPort                                                OBJECT IDENTIFIER ::= { gs2328pSTPMSTI4Port 1 }
      
gs2328pSTPMSTI4AggregatedPortPathCost OBJECT-TYPE
   SYNTAX      Integer32(0..200000000)
   MAX-ACCESS  read-write
   STATUS      current
   DESCRIPTION
       " Auto: 0,
        Specific Path Cost range: 1 - 200000000."
   ::= { gs2328pSTPMSTI4AggregatedPort 1 }
   
gs2328pSTPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI4AggregatedPort 2 }
   
gs2328pSTPMSTI4NormalPortTable OBJECT-TYPE
   SYNTAX      SEQUENCE OF Gs2328pSTPMSTI4NormalPortEntry
   MAX-ACCESS  not-accessible
   STATUS      current
   DESCRIPTION
       " Show MSTI4 Normal Port Configurations. "
   ::= { gs2328pSTPMSTI4Port 2 }

gs2328pSTPMSTI4NormalPortEntry OBJECT-TYPE
   SYNTAX      Gs2328pSTPMSTI4NormalPortEntry
   MAX-ACCESS  not-accessible
   STATUS      current
   DESCRIPTION
       ""
   INDEX    { gs2328pSTPMSTI4NormalPortConfPort  }
   ::= { gs2328pSTPMSTI4NormalPortTable 1 }

Gs2328pSTPMSTI4NormalPortEntry ::= SEQUENCE {
   gs2328pSTPMSTI4NormalPortConfPort         Integer32,
   gs2328pSTPMSTI4NormalPortPathCost         Integer32,
   gs2328pSTPMSTI4NormalPortPriority         Integer32
}

gs2328pSTPMSTI4NormalPortConfPort OBJECT-TYPE
   SYNTAX      Integer32(1..4095)
   MAX-ACCESS  not-accessible
   STATUS      current
   DESCRIPTION
       " port, range : 1 - port number. "
   ::= { gs2328pSTPMSTI4NormalPortEntry 1 }
   
gs2328pSTPMSTI4NormalPortPathCost OBJECT-TYPE
   SYNTAX      Integer32(0..200000000)
   MAX-ACCESS  read-write
   STATUS      current
   DESCRIPTION
       " Auto: 0,
        Specific Path Cost range: 1 - 200000000."
   ::= { gs2328pSTPMSTI4NormalPortEntry 2 }
   
gs2328pSTPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI4NormalPortEntry 3 }
   
gs2328pSTPMSTI5Port                                                          OBJECT IDENTIFIER ::= { gs2328pSTPMSTIPort 5 }

gs2328pSTPMSTI5AggregatedPort                                                OBJECT IDENTIFIER ::= { gs2328pSTPMSTI5Port 1 }
      
gs2328pSTPMSTI5AggregatedPortPathCost OBJECT-TYPE
   SYNTAX      Integer32(0..200000000)
   MAX-ACCESS  read-write
   STATUS      current
   DESCRIPTION
       " Auto: 0,
        Specific Path Cost range: 1 - 200000000."
   ::= { gs2328pSTPMSTI5AggregatedPort 1 }
   
gs2328pSTPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI5AggregatedPort 2 }
   
gs2328pSTPMSTI5NormalPortTable OBJECT-TYPE
   SYNTAX      SEQUENCE OF Gs2328pSTPMSTI5NormalPortEntry
   MAX-ACCESS  not-accessible
   STATUS      current
   DESCRIPTION
       " Show MSTI5 Normal Port Configurations. "
   ::= { gs2328pSTPMSTI5Port 2 }

gs2328pSTPMSTI5NormalPortEntry OBJECT-TYPE
   SYNTAX      Gs2328pSTPMSTI5NormalPortEntry
   MAX-ACCESS  not-accessible
   STATUS      current
   DESCRIPTION
       ""
   INDEX    { gs2328pSTPMSTI5NormalPortConfPort  }
   ::= { gs2328pSTPMSTI5NormalPortTable 1 }

Gs2328pSTPMSTI5NormalPortEntry ::= SEQUENCE {
   gs2328pSTPMSTI5NormalPortConfPort         Integer32,
   gs2328pSTPMSTI5NormalPortPathCost         Integer32,
   gs2328pSTPMSTI5NormalPortPriority         Integer32
}

gs2328pSTPMSTI5NormalPortConfPort OBJECT-TYPE
   SYNTAX      Integer32(1..4095)
   MAX-ACCESS  not-accessible
   STATUS      current
   DESCRIPTION
       " port, range : 1 - port number. "
   ::= { gs2328pSTPMSTI5NormalPortEntry 1 }
   
gs2328pSTPMSTI5NormalPortPathCost OBJECT-TYPE
   SYNTAX      Integer32(0..200000000)
   MAX-ACCESS  read-write
   STATUS      current
   DESCRIPTION
       " Auto: 0,
        Specific Path Cost range: 1 - 200000000."
   ::= { gs2328pSTPMSTI5NormalPortEntry 2 }
   
gs2328pSTPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI5NormalPortEntry 3 }
   
gs2328pSTPMSTI6Port                                                          OBJECT IDENTIFIER ::= { gs2328pSTPMSTIPort 6 }

gs2328pSTPMSTI6AggregatedPort                                                OBJECT IDENTIFIER ::= { gs2328pSTPMSTI6Port 1 }
      
gs2328pSTPMSTI6AggregatedPortPathCost OBJECT-TYPE
   SYNTAX      Integer32(0..200000000)
   MAX-ACCESS  read-write
   STATUS      current
   DESCRIPTION
       " Auto: 0,
        Specific Path Cost range: 1 - 200000000."
   ::= { gs2328pSTPMSTI6AggregatedPort 1 }
   
gs2328pSTPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI6AggregatedPort 2 }
   
gs2328pSTPMSTI6NormalPortTable OBJECT-TYPE
   SYNTAX      SEQUENCE OF Gs2328pSTPMSTI6NormalPortEntry
   MAX-ACCESS  not-accessible
   STATUS      current
   DESCRIPTION
       " Show MSTI6 Normal Port Configurations. "
   ::= { gs2328pSTPMSTI6Port 2 }

gs2328pSTPMSTI6NormalPortEntry OBJECT-TYPE
   SYNTAX      Gs2328pSTPMSTI6NormalPortEntry
   MAX-ACCESS  not-accessible
   STATUS      current
   DESCRIPTION
       ""
   INDEX    { gs2328pSTPMSTI6NormalPortConfPort  }
   ::= { gs2328pSTPMSTI6NormalPortTable 1 }

Gs2328pSTPMSTI6NormalPortEntry ::= SEQUENCE {
   gs2328pSTPMSTI6NormalPortConfPort         Integer32,
   gs2328pSTPMSTI6NormalPortPathCost         Integer32,
   gs2328pSTPMSTI6NormalPortPriority         Integer32
}

gs2328pSTPMSTI6NormalPortConfPort OBJECT-TYPE
   SYNTAX      Integer32(1..4095)
   MAX-ACCESS  not-accessible
   STATUS      current
   DESCRIPTION
       " port, range : 1 - port number. "
   ::= { gs2328pSTPMSTI6NormalPortEntry 1 }
   
gs2328pSTPMSTI6NormalPortPathCost OBJECT-TYPE
   SYNTAX      Integer32(0..200000000)
   MAX-ACCESS  read-write
   STATUS      current
   DESCRIPTION
       " Auto: 0,
        Specific Path Cost range: 1 - 200000000."
   ::= { gs2328pSTPMSTI6NormalPortEntry 2 }
   
gs2328pSTPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI6NormalPortEntry 3 }
   
gs2328pSTPMSTI7Port                                                          OBJECT IDENTIFIER ::= { gs2328pSTPMSTIPort 7 }

gs2328pSTPMSTI7AggregatedPort                                                OBJECT IDENTIFIER ::= { gs2328pSTPMSTI7Port 1 }
      
gs2328pSTPMSTI7AggregatedPortPathCost OBJECT-TYPE
   SYNTAX      Integer32(0..200000000)
   MAX-ACCESS  read-write
   STATUS      current
   DESCRIPTION
       " Auto: 0,
        Specific Path Cost range: 1 - 200000000."
   ::= { gs2328pSTPMSTI7AggregatedPort 1 }
   
gs2328pSTPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI7AggregatedPort 2 }
   
gs2328pSTPMSTI7NormalPortTable OBJECT-TYPE
   SYNTAX      SEQUENCE OF Gs2328pSTPMSTI7NormalPortEntry
   MAX-ACCESS  not-accessible
   STATUS      current
   DESCRIPTION
       " Show MSTI7 Normal Port Configurations. "
   ::= { gs2328pSTPMSTI7Port 2 }

gs2328pSTPMSTI7NormalPortEntry OBJECT-TYPE
   SYNTAX      Gs2328pSTPMSTI7NormalPortEntry
   MAX-ACCESS  not-accessible
   STATUS      current
   DESCRIPTION
       ""
   INDEX    { gs2328pSTPMSTI7NormalPortConfPort  }
   ::= { gs2328pSTPMSTI7NormalPortTable 1 }

Gs2328pSTPMSTI7NormalPortEntry ::= SEQUENCE {
   gs2328pSTPMSTI7NormalPortConfPort         Integer32,
   gs2328pSTPMSTI7NormalPortPathCost         Integer32,
   gs2328pSTPMSTI7NormalPortPriority         Integer32
}

gs2328pSTPMSTI7NormalPortConfPort OBJECT-TYPE
   SYNTAX      Integer32(1..4095)
   MAX-ACCESS  not-accessible
   STATUS      current
   DESCRIPTION
       " port, range : 1 - port number. "
   ::= { gs2328pSTPMSTI7NormalPortEntry 1 }
   
gs2328pSTPMSTI7NormalPortPathCost OBJECT-TYPE
   SYNTAX      Integer32(0..200000000)
   MAX-ACCESS  read-write
   STATUS      current
   DESCRIPTION
       " Auto: 0,
        Specific Path Cost range: 1 - 200000000."
   ::= { gs2328pSTPMSTI7NormalPortEntry 2 }
   
gs2328pSTPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2328pSTPMSTI7NormalPortEntry 3 }
   

gs2328pSTPBridgeStatus                                                      OBJECT IDENTIFIER ::= { gs2328pSTP 8 }

gs2328pCISTBridgeSTP                                                        OBJECT IDENTIFIER ::= { gs2328pSTPBridgeStatus 1 }

gs2328pCISTBridgeSTPStatus                                                  OBJECT IDENTIFIER ::= { gs2328pCISTBridgeSTP 1 }
      
gs2328pCISTBridgeInstance OBJECT-TYPE
   SYNTAX       DisplayString
   MAX-ACCESS   read-only
   STATUS       current
   DESCRIPTION
       "The Bridge instance - CIST, MST1, ..."
   ::= { gs2328pCISTBridgeSTPStatus 1 }
   
gs2328pCISTBridgeID OBJECT-TYPE
   SYNTAX       DisplayString
   MAX-ACCESS   read-only
   STATUS       current
   DESCRIPTION
       "The Bridge ID of this Bridge instance."
   ::= { gs2328pCISTBridgeSTPStatus 2 }
   
gs2328pCISTRootID OBJECT-TYPE
   SYNTAX       DisplayString
   MAX-ACCESS   read-only
   STATUS       current
   DESCRIPTION
       "The Bridge ID of the currently elected root bridge."
   ::= { gs2328pCISTBridgeSTPStatus 3 }
   
gs2328pCISTRootPort OBJECT-TYPE
   SYNTAX       DisplayString
   MAX-ACCESS   read-only
   STATUS       current
   DESCRIPTION
       "The switch port currently assigned the root port role."
   ::= { gs2328pCISTBridgeSTPStatus 4 }

gs2328pCISTRootCost OBJECT-TYPE
   SYNTAX       Integer32(0..200000000)
   MAX-ACCESS   read-only
   STATUS       current
   DESCRIPTION
       "Root Path Cost."
   ::= { gs2328pCISTBridgeSTPStatus 5 }
   
gs2328pCISTRegionalRoot OBJECT-TYPE
   SYNTAX       DisplayString
   MAX-ACCESS   read-only
   STATUS       current
   DESCRIPTION
       "The Bridge ID of the currently elected regional root bridge, inside the MSTP region of this bridge."
   ::= { gs2328pCISTBridgeSTPStatus 6 }
   
gs2328pCISTInternalRootCost OBJECT-TYPE
   SYNTAX       Integer32(0..200000000)
   MAX-ACCESS   read-only
   STATUS       current
   DESCRIPTION
       "The Regional Root Path Cost."
   ::= { gs2328pCISTBridgeSTPStatus 7 }

gs2328pCISTTopologyFlag OBJECT-TYPE
   SYNTAX       DisplayString
   MAX-ACCESS   read-only
   STATUS       current
   DESCRIPTION
       "The current state of the Topology Change Flag of this Bridge instance."
   ::= { gs2328pCISTBridgeSTPStatus 8 }

gs2328pCISTTopologyChangeCount OBJECT-TYPE
   SYNTAX       Counter32
   MAX-ACCESS   read-only
   STATUS       current
   DESCRIPTION
       "The number of times where the topology change flag has been set."
   ::= { gs2328pCISTBridgeSTPStatus 9 }
   
gs2328pCISTTopologyChangeLast OBJECT-TYPE
   SYNTAX       DisplayString
   MAX-ACCESS   read-only
   STATUS       current
   DESCRIPTION
       "The time passed since the Topology Flag was last set."
   ::= { gs2328pCISTBridgeSTPStatus 10 }
   
gs2328pCISTPortStateTable OBJECT-TYPE
   SYNTAX      SEQUENCE OF Gs2328pCISTPortStateEntry
   MAX-ACCESS  not-accessible
   STATUS      current
   DESCRIPTION
       " Show CIST Ports and Aggregations State Configurations. "
   ::= { gs2328pCISTBridgeSTP 2 }

gs2328pCISTPortStateEntry OBJECT-TYPE
   SYNTAX      Gs2328pCISTPortStateEntry
   MAX-ACCESS  not-accessible
   STATUS      current
   DESCRIPTION
       ""
   INDEX    { gs2328pCISTPortStateIndex  }
   ::= { gs2328pCISTPortStateTable 1 }

Gs2328pCISTPortStateEntry ::= SEQUENCE {
   gs2328pCISTPortStateIndex        Integer32,
   gs2328pCISTPortStatePort         DisplayString,
   gs2328pCISTPortStatePortID       DisplayString,
   gs2328pCISTPortStateRole         DisplayString,
   gs2328pCISTPortStateState        DisplayString,
   gs2328pCISTPortStatePathCost     Integer32,
   gs2328pCISTPortStateEdge         DisplayString,
   gs2328pCISTPortStatePoint2Point  DisplayString,
   gs2328pCISTPortStateUptime       DisplayString
}

gs2328pCISTPortStateIndex OBJECT-TYPE
   SYNTAX      Integer32(1..4095)
   MAX-ACCESS  not-accessible
   STATUS      current
   DESCRIPTION
       "table index."
   ::= { gs2328pCISTPortStateEntry 1 }
   
gs2328pCISTPortStatePort OBJECT-TYPE
   SYNTAX      DisplayString
   MAX-ACCESS  read-only
   STATUS      current
   DESCRIPTION
       "The switch port number of the logical STP port."
   ::= { gs2328pCISTPortStateEntry 2 }
   
gs2328pCISTPortStatePortID OBJECT-TYPE
   SYNTAX      DisplayString
   MAX-ACCESS  read-only
   STATUS      current
   DESCRIPTION
       "The port id as used by the STP protocol. 
        This is the priority part and the logical port index of the bridge port."
   ::= { gs2328pCISTPortStateEntry 3 }
   
gs2328pCISTPortStateRole OBJECT-TYPE
   SYNTAX      DisplayString
   MAX-ACCESS  read-only
   STATUS      current
   DESCRIPTION
       "The current STP port role."
   ::= { gs2328pCISTPortStateEntry 4 }
   
gs2328pCISTPortStateState OBJECT-TYPE
   SYNTAX      DisplayString
   MAX-ACCESS  read-only
   STATUS      current
   DESCRIPTION
       "The current STP port state."
   ::= { gs2328pCISTPortStateEntry 5 }
   
gs2328pCISTPortStatePathCost OBJECT-TYPE
   SYNTAX      Integer32(0..200000000)
   MAX-ACCESS  read-only
   STATUS      current
   DESCRIPTION
       "The current STP port path cost."
   ::= { gs2328pCISTPortStateEntry 6 }
   
gs2328pCISTPortStateEdge OBJECT-TYPE
   SYNTAX      DisplayString
   MAX-ACCESS  read-only
   STATUS      current
   DESCRIPTION
       "The current STP port Edge Flag."
   ::= { gs2328pCISTPortStateEntry 7 }
   
gs2328pCISTPortStatePoint2Point OBJECT-TYPE
   SYNTAX      DisplayString
   MAX-ACCESS  read-only
   STATUS      current
   DESCRIPTION
       "The current STP port point-to-point flag."
   ::= { gs2328pCISTPortStateEntry 8 }
   
gs2328pCISTPortStateUptime OBJECT-TYPE
   SYNTAX      DisplayString
   MAX-ACCESS  read-only
   STATUS      current
   DESCRIPTION
       "The time since the bridge port was last initialized."
   ::= { gs2328pCISTPortStateEntry 9 }
   
gs2328pMSTI1BridgeSTP                                                        OBJECT IDENTIFIER ::= { gs2328pSTPBridgeStatus 2 }

gs2328pMSTI1BridgeSTPStatus                                                  OBJECT IDENTIFIER ::= { gs2328pMSTI1BridgeSTP 1 }
      
gs2328pMSTI1BridgeInstance OBJECT-TYPE
   SYNTAX       DisplayString
   MAX-ACCESS   read-only
   STATUS       current
   DESCRIPTION
       "The Bridge instance - CIST, MST1, ..."
   ::= { gs2328pMSTI1BridgeSTPStatus 1 }
   
gs2328pMSTI1BridgeID OBJECT-TYPE
   SYNTAX       DisplayString
   MAX-ACCESS   read-only
   STATUS       current
   DESCRIPTION
       "The Bridge ID of this Bridge instance."
   ::= { gs2328pMSTI1BridgeSTPStatus 2 }
   
gs2328pMSTI1RootID OBJECT-TYPE
   SYNTAX       DisplayString
   MAX-ACCESS   read-only
   STATUS       current
   DESCRIPTION
       "The Bridge ID of the currently elected root bridge."
   ::= { gs2328pMSTI1BridgeSTPStatus 3 }
   
gs2328pMSTI1RootPort OBJECT-TYPE
   SYNTAX       DisplayString
   MAX-ACCESS   read-only
   STATUS       current
   DESCRIPTION
       "The switch port currently assigned the root port role."
   ::= { gs2328pMSTI1BridgeSTPStatus 4 }

gs2328pMSTI1RootCost OBJECT-TYPE
   SYNTAX       Integer32(0..200000000)
   MAX-ACCESS   read-only
   STATUS       current
   DESCRIPTION
       "Root Path Cost."
   ::= { gs2328pMSTI1BridgeSTPStatus 5 }

gs2328pMSTI1TopologyFlag OBJECT-TYPE
   SYNTAX       DisplayString
   MAX-ACCESS   read-only
   STATUS       current
   DESCRIPTION
       "The current state of the Topology Change Flag of this Bridge instance."
   ::= { gs2328pMSTI1BridgeSTPStatus 8 }

gs2328pMSTI1TopologyChangeCount OBJECT-TYPE
   SYNTAX       Counter32
   MAX-ACCESS   read-only
   STATUS       current
   DESCRIPTION
       "The number of times where the topology change flag has been set."
   ::= { gs2328pMSTI1BridgeSTPStatus 9 }
   
gs2328pMSTI1TopologyChangeLast OBJECT-TYPE
   SYNTAX       DisplayString
   MAX-ACCESS   read-only
   STATUS       current
   DESCRIPTION
       "The time passed since the Topology Flag was last set."
   ::= { gs2328pMSTI1BridgeSTPStatus 10 }
   
gs2328pMSTI1PortStateTable OBJECT-TYPE
   SYNTAX      SEQUENCE OF Gs2328pMSTI1PortStateEntry
   MAX-ACCESS  not-accessible
   STATUS      current
   DESCRIPTION
       " Show MSTI1 Ports and Aggregations State Configurations. "
   ::= { gs2328pMSTI1BridgeSTP 2 }

gs2328pMSTI1PortStateEntry OBJECT-TYPE
   SYNTAX      Gs2328pMSTI1PortStateEntry
   MAX-ACCESS  not-accessible
   STATUS      current
   DESCRIPTION
       ""
   INDEX    { gs2328pMSTI1PortStateIndex  }
   ::= { gs2328pMSTI1PortStateTable 1 }

Gs2328pMSTI1PortStateEntry ::= SEQUENCE {
   gs2328pMSTI1PortStateIndex        Integer32,
   gs2328pMSTI1PortStatePort         DisplayString,
   gs2328pMSTI1PortStatePortID       DisplayString,
   gs2328pMSTI1PortStateRole         DisplayString,
   gs2328pMSTI1PortStateState        DisplayString,
   gs2328pMSTI1PortStatePathCost     Integer32,
   gs2328pMSTI1PortStateEdge         DisplayString,
   gs2328pMSTI1PortStatePoint2Point  DisplayString,
   gs2328pMSTI1PortStateUptime       DisplayString
}

gs2328pMSTI1PortStateIndex OBJECT-TYPE
   SYNTAX      Integer32(1..4095)
   MAX-ACCESS  not-accessible
   STATUS      current
   DESCRIPTION
       "table index."
   ::= { gs2328pMSTI1PortStateEntry 1 }
   
gs2328pMSTI1PortStatePort OBJECT-TYPE
   SYNTAX      DisplayString
   MAX-ACCESS  read-only
   STATUS      current
   DESCRIPTION
       "The switch port number of the logical STP port."
   ::= { gs2328pMSTI1PortStateEntry 2 }
   
gs2328pMSTI1PortStatePortID OBJECT-TYPE
   SYNTAX      DisplayString
   MAX-ACCESS  read-only
   STATUS      current
   DESCRIPTION
       "The port id as used by the STP protocol. 
        This is the priority part and the logical port index of the bridge port."
   ::= { gs2328pMSTI1PortStateEntry 3 }
   
gs2328pMSTI1PortStateRole OBJECT-TYPE
   SYNTAX      DisplayString
   MAX-ACCESS  read-only
   STATUS      current
   DESCRIPTION
       "The current STP port role."
   ::= { gs2328pMSTI1PortStateEntry 4 }
   
gs2328pMSTI1PortStateState OBJECT-TYPE
   SYNTAX      DisplayString
   MAX-ACCESS  read-only
   STATUS      current
   DESCRIPTION
       "The current STP port state."
   ::= { gs2328pMSTI1PortStateEntry 5 }
   
gs2328pMSTI1PortStatePathCost OBJECT-TYPE
   SYNTAX      Integer32(0..200000000)
   MAX-ACCESS  read-only
   STATUS      current
   DESCRIPTION
       "The current STP port path cost."
   ::= { gs2328pMSTI1PortStateEntry 6 }
   
gs2328pMSTI1PortStateEdge OBJECT-TYPE
   SYNTAX      DisplayString
   MAX-ACCESS  read-only
   STATUS      current
   DESCRIPTION
       "The current STP port Edge Flag."
   ::= { gs2328pMSTI1PortStateEntry 7 }
   
gs2328pMSTI1PortStatePoint2Point OBJECT-TYPE
   SYNTAX      DisplayString
   MAX-ACCESS  read-only
   STATUS      current
   DESCRIPTION
       "The current STP port point-to-point flag."
   ::= { gs2328pMSTI1PortStateEntry 8 }
   
gs2328pMSTI1PortStateUptime OBJECT-TYPE
   SYNTAX      DisplayString
   MAX-ACCESS  read-only
   STATUS      current
   DESCRIPTION
       "The time since the bridge port was last initialized."
   ::= { gs2328pMSTI1PortStateEntry 9 }
   
gs2328pMSTI2BridgeSTP                                                        OBJECT IDENTIFIER ::= { gs2328pSTPBridgeStatus 3 }

gs2328pMSTI2BridgeSTPStatus                                                  OBJECT IDENTIFIER ::= { gs2328pMSTI2BridgeSTP 1 }
      
gs2328pMSTI2BridgeInstance OBJECT-TYPE
   SYNTAX       DisplayString
   MAX-ACCESS   read-only
   STATUS       current
   DESCRIPTION
       "The Bridge instance - CIST, MST1, ..."
   ::= { gs2328pMSTI2BridgeSTPStatus 1 }
   
gs2328pMSTI2BridgeID OBJECT-TYPE
   SYNTAX       DisplayString
   MAX-ACCESS   read-only
   STATUS       current
   DESCRIPTION
       "The Bridge ID of this Bridge instance."
   ::= { gs2328pMSTI2BridgeSTPStatus 2 }
   
gs2328pMSTI2RootID OBJECT-TYPE
   SYNTAX       DisplayString
   MAX-ACCESS   read-only
   STATUS       current
   DESCRIPTION
       "The Bridge ID of the currently elected root bridge."
   ::= { gs2328pMSTI2BridgeSTPStatus 3 }
   
gs2328pMSTI2RootPort OBJECT-TYPE
   SYNTAX       DisplayString
   MAX-ACCESS   read-only
   STATUS       current
   DESCRIPTION
       "The switch port currently assigned the root port role."
   ::= { gs2328pMSTI2BridgeSTPStatus 4 }

gs2328pMSTI2RootCost OBJECT-TYPE
   SYNTAX       Integer32(0..200000000)
   MAX-ACCESS   read-only
   STATUS       current
   DESCRIPTION
       "Root Path Cost."
   ::= { gs2328pMSTI2BridgeSTPStatus 5 }

gs2328pMSTI2TopologyFlag OBJECT-TYPE
   SYNTAX       DisplayString
   MAX-ACCESS   read-only
   STATUS       current
   DESCRIPTION
       "The current state of the Topology Change Flag of this Bridge instance."
   ::= { gs2328pMSTI2BridgeSTPStatus 8 }

gs2328pMSTI2TopologyChangeCount OBJECT-TYPE
   SYNTAX       Counter32
   MAX-ACCESS   read-only
   STATUS       current
   DESCRIPTION
       "The number of times where the topology change flag has been set."
   ::= { gs2328pMSTI2BridgeSTPStatus 9 }
   
gs2328pMSTI2TopologyChangeLast OBJECT-TYPE
   SYNTAX       DisplayString
   MAX-ACCESS   read-only
   STATUS       current
   DESCRIPTION
       "The time passed since the Topology Flag was last set."
   ::= { gs2328pMSTI2BridgeSTPStatus 10 }
   
gs2328pMSTI2PortStateTable OBJECT-TYPE
   SYNTAX      SEQUENCE OF Gs2328pMSTI2PortStateEntry
   MAX-ACCESS  not-accessible
   STATUS      current
   DESCRIPTION
       " Show MSTI2 Ports and Aggregations State Configurations. "
   ::= { gs2328pMSTI2BridgeSTP 2 }

gs2328pMSTI2PortStateEntry OBJECT-TYPE
   SYNTAX      Gs2328pMSTI2PortStateEntry
   MAX-ACCESS  not-accessible
   STATUS      current
   DESCRIPTION
       ""
   INDEX    { gs2328pMSTI2PortStateIndex  }
   ::= { gs2328pMSTI2PortStateTable 1 }

Gs2328pMSTI2PortStateEntry ::= SEQUENCE {
   gs2328pMSTI2PortStateIndex        Integer32,
   gs2328pMSTI2PortStatePort         DisplayString,
   gs2328pMSTI2PortStatePortID       DisplayString,
   gs2328pMSTI2PortStateRole         DisplayString,
   gs2328pMSTI2PortStateState        DisplayString,
   gs2328pMSTI2PortStatePathCost     Integer32,
   gs2328pMSTI2PortStateEdge         DisplayString,
   gs2328pMSTI2PortStatePoint2Point  DisplayString,
   gs2328pMSTI2PortStateUptime       DisplayString
}

gs2328pMSTI2PortStateIndex OBJECT-TYPE
   SYNTAX      Integer32(1..4095)
   MAX-ACCESS  not-accessible
   STATUS      current
   DESCRIPTION
       "table index."
   ::= { gs2328pMSTI2PortStateEntry 1 }
   
gs2328pMSTI2PortStatePort OBJECT-TYPE
   SYNTAX      DisplayString
   MAX-ACCESS  read-only
   STATUS      current
   DESCRIPTION
       "The switch port number of the logical STP port."
   ::= { gs2328pMSTI2PortStateEntry 2 }
   
gs2328pMSTI2PortStatePortID OBJECT-TYPE
   SYNTAX      DisplayString
   MAX-ACCESS  read-only
   STATUS      current
   DESCRIPTION
       "The port id as used by the STP protocol. 
        This is the priority part and the logical port index of the bridge port."
   ::= { gs2328pMSTI2PortStateEntry 3 }
   
gs2328pMSTI2PortStateRole OBJECT-TYPE
   SYNTAX      DisplayString
   MAX-ACCESS  read-only
   STATUS      current
   DESCRIPTION
       "The current STP port role."
   ::= { gs2328pMSTI2PortStateEntry 4 }
   
gs2328pMSTI2PortStateState OBJECT-TYPE
   SYNTAX      DisplayString
   MAX-ACCESS  read-only
   STATUS      current
   DESCRIPTION
       "The current STP port state."
   ::= { gs2328pMSTI2PortStateEntry 5 }
   
gs2328pMSTI2PortStatePathCost OBJECT-TYPE
   SYNTAX      Integer32(0..200000000)
   MAX-ACCESS  read-only
   STATUS      current
   DESCRIPTION
       "The current STP port path cost."
   ::= { gs2328pMSTI2PortStateEntry 6 }
   
gs2328pMSTI2PortStateEdge OBJECT-TYPE
   SYNTAX      DisplayString
   MAX-ACCESS  read-only
   STATUS      current
   DESCRIPTION
       "The current STP port Edge Flag."
   ::= { gs2328pMSTI2PortStateEntry 7 }
   
gs2328pMSTI2PortStatePoint2Point OBJECT-TYPE
   SYNTAX      DisplayString
   MAX-ACCESS  read-only
   STATUS      current
   DESCRIPTION
       "The current STP port point-to-point flag."
   ::= { gs2328pMSTI2PortStateEntry 8 }
   
gs2328pMSTI2PortStateUptime OBJECT-TYPE
   SYNTAX      DisplayString
   MAX-ACCESS  read-only
   STATUS      current
   DESCRIPTION
       "The time since the bridge port was last initialized."
   ::= { gs2328pMSTI2PortStateEntry 9 }

gs2328pMSTI3BridgeSTP                                                        OBJECT IDENTIFIER ::= { gs2328pSTPBridgeStatus 4 }

gs2328pMSTI3BridgeSTPStatus                                                  OBJECT IDENTIFIER ::= { gs2328pMSTI3BridgeSTP 1 }
      
gs2328pMSTI3BridgeInstance OBJECT-TYPE
   SYNTAX       DisplayString
   MAX-ACCESS   read-only
   STATUS       current
   DESCRIPTION
       "The Bridge instance - CIST, MST1, ..."
   ::= { gs2328pMSTI3BridgeSTPStatus 1 }
   
gs2328pMSTI3BridgeID OBJECT-TYPE
   SYNTAX       DisplayString
   MAX-ACCESS   read-only
   STATUS       current
   DESCRIPTION
       "The Bridge ID of this Bridge instance."
   ::= { gs2328pMSTI3BridgeSTPStatus 2 }
   
gs2328pMSTI3RootID OBJECT-TYPE
   SYNTAX       DisplayString
   MAX-ACCESS   read-only
   STATUS       current
   DESCRIPTION
       "The Bridge ID of the currently elected root bridge."
   ::= { gs2328pMSTI3BridgeSTPStatus 3 }
   
gs2328pMSTI3RootPort OBJECT-TYPE
   SYNTAX       DisplayString
   MAX-ACCESS   read-only
   STATUS       current
   DESCRIPTION
       "The switch port currently assigned the root port role."
   ::= { gs2328pMSTI3BridgeSTPStatus 4 }

gs2328pMSTI3RootCost OBJECT-TYPE
   SYNTAX       Integer32(0..200000000)
   MAX-ACCESS   read-only
   STATUS       current
   DESCRIPTION
       "Root Path Cost."
   ::= { gs2328pMSTI3BridgeSTPStatus 5 }

gs2328pMSTI3TopologyFlag OBJECT-TYPE
   SYNTAX       DisplayString
   MAX-ACCESS   read-only
   STATUS       current
   DESCRIPTION
       "The current state of the Topology Change Flag of this Bridge instance."
   ::= { gs2328pMSTI3BridgeSTPStatus 8 }

gs2328pMSTI3TopologyChangeCount OBJECT-TYPE
   SYNTAX       Counter32
   MAX-ACCESS   read-only
   STATUS       current
   DESCRIPTION
       "The number of times where the topology change flag has been set."
   ::= { gs2328pMSTI3BridgeSTPStatus 9 }
   
gs2328pMSTI3TopologyChangeLast OBJECT-TYPE
   SYNTAX       DisplayString
   MAX-ACCESS   read-only
   STATUS       current
   DESCRIPTION
       "The time passed since the Topology Flag was last set."
   ::= { gs2328pMSTI3BridgeSTPStatus 10 }
   
gs2328pMSTI3PortStateTable OBJECT-TYPE
   SYNTAX      SEQUENCE OF Gs2328pMSTI3PortStateEntry
   MAX-ACCESS  not-accessible
   STATUS      current
   DESCRIPTION
       " Show MSTI3 Ports and Aggregations State Configurations. "
   ::= { gs2328pMSTI3BridgeSTP 2 }

gs2328pMSTI3PortStateEntry OBJECT-TYPE
   SYNTAX      Gs2328pMSTI3PortStateEntry
   MAX-ACCESS  not-accessible
   STATUS      current
   DESCRIPTION
       ""
   INDEX    { gs2328pMSTI3PortStateIndex  }
   ::= { gs2328pMSTI3PortStateTable 1 }

Gs2328pMSTI3PortStateEntry ::= SEQUENCE {
   gs2328pMSTI3PortStateIndex        Integer32,
   gs2328pMSTI3PortStatePort         DisplayString,
   gs2328pMSTI3PortStatePortID       DisplayString,
   gs2328pMSTI3PortStateRole         DisplayString,
   gs2328pMSTI3PortStateState        DisplayString,
   gs2328pMSTI3PortStatePathCost     Integer32,
   gs2328pMSTI3PortStateEdge         DisplayString,
   gs2328pMSTI3PortStatePoint2Point  DisplayString,
   gs2328pMSTI3PortStateUptime       DisplayString
}

gs2328pMSTI3PortStateIndex OBJECT-TYPE
   SYNTAX      Integer32(1..4095)
   MAX-ACCESS  not-accessible
   STATUS      current
   DESCRIPTION
       "table index."
   ::= { gs2328pMSTI3PortStateEntry 1 }
   
gs2328pMSTI3PortStatePort OBJECT-TYPE
   SYNTAX      DisplayString
   MAX-ACCESS  read-only
   STATUS      current
   DESCRIPTION
       "The switch port number of the logical STP port."
   ::= { gs2328pMSTI3PortStateEntry 2 }
   
gs2328pMSTI3PortStatePortID OBJECT-TYPE
   SYNTAX      DisplayString
   MAX-ACCESS  read-only
   STATUS      current
   DESCRIPTION
       "The port id as used by the STP protocol. 
        This is the priority part and the logical port index of the bridge port."
   ::= { gs2328pMSTI3PortStateEntry 3 }
   
gs2328pMSTI3PortStateRole OBJECT-TYPE
   SYNTAX      DisplayString
   MAX-ACCESS  read-only
   STATUS      current
   DESCRIPTION
       "The current STP port role."
   ::= { gs2328pMSTI3PortStateEntry 4 }
   
gs2328pMSTI3PortStateState OBJECT-TYPE
   SYNTAX      DisplayString
   MAX-ACCESS  read-only
   STATUS      current
   DESCRIPTION
       "The current STP port state."
   ::= { gs2328pMSTI3PortStateEntry 5 }
   
gs2328pMSTI3PortStatePathCost OBJECT-TYPE
   SYNTAX      Integer32(0..200000000)
   MAX-ACCESS  read-only
   STATUS      current
   DESCRIPTION
       "The current STP port path cost."
   ::= { gs2328pMSTI3PortStateEntry 6 }
   
gs2328pMSTI3PortStateEdge OBJECT-TYPE
   SYNTAX      DisplayString
   MAX-ACCESS  read-only
   STATUS      current
   DESCRIPTION
       "The current STP port Edge Flag."
   ::= { gs2328pMSTI3PortStateEntry 7 }
   
gs2328pMSTI3PortStatePoint2Point OBJECT-TYPE
   SYNTAX      DisplayString
   MAX-ACCESS  read-only
   STATUS      current
   DESCRIPTION
       "The current STP port point-to-point flag."
   ::= { gs2328pMSTI3PortStateEntry 8 }
   
gs2328pMSTI3PortStateUptime OBJECT-TYPE
   SYNTAX      DisplayString
   MAX-ACCESS  read-only
   STATUS      current
   DESCRIPTION
       "The time since the bridge port was last initialized."
   ::= { gs2328pMSTI3PortStateEntry 9 }
   
gs2328pMSTI4BridgeSTP                                                        OBJECT IDENTIFIER ::= { gs2328pSTPBridgeStatus 5 }

gs2328pMSTI4BridgeSTPStatus                                                  OBJECT IDENTIFIER ::= { gs2328pMSTI4BridgeSTP 1 }
      
gs2328pMSTI4BridgeInstance OBJECT-TYPE
   SYNTAX       DisplayString
   MAX-ACCESS   read-only
   STATUS       current
   DESCRIPTION
       "The Bridge instance - CIST, MST1, ..."
   ::= { gs2328pMSTI4BridgeSTPStatus 1 }
   
gs2328pMSTI4BridgeID OBJECT-TYPE
   SYNTAX       DisplayString
   MAX-ACCESS   read-only
   STATUS       current
   DESCRIPTION
       "The Bridge ID of this Bridge instance."
   ::= { gs2328pMSTI4BridgeSTPStatus 2 }
   
gs2328pMSTI4RootID OBJECT-TYPE
   SYNTAX       DisplayString
   MAX-ACCESS   read-only
   STATUS       current
   DESCRIPTION
       "The Bridge ID of the currently elected root bridge."
   ::= { gs2328pMSTI4BridgeSTPStatus 3 }
   
gs2328pMSTI4RootPort OBJECT-TYPE
   SYNTAX       DisplayString
   MAX-ACCESS   read-only
   STATUS       current
   DESCRIPTION
       "The switch port currently assigned the root port role."
   ::= { gs2328pMSTI4BridgeSTPStatus 4 }

gs2328pMSTI4RootCost OBJECT-TYPE
   SYNTAX       Integer32(0..200000000)
   MAX-ACCESS   read-only
   STATUS       current
   DESCRIPTION
       "Root Path Cost."
   ::= { gs2328pMSTI4BridgeSTPStatus 5 }

gs2328pMSTI4TopologyFlag OBJECT-TYPE
   SYNTAX       DisplayString
   MAX-ACCESS   read-only
   STATUS       current
   DESCRIPTION
       "The current state of the Topology Change Flag of this Bridge instance."
   ::= { gs2328pMSTI4BridgeSTPStatus 8 }

gs2328pMSTI4TopologyChangeCount OBJECT-TYPE
   SYNTAX       Counter32
   MAX-ACCESS   read-only
   STATUS       current
   DESCRIPTION
       "The number of times where the topology change flag has been set."
   ::= { gs2328pMSTI4BridgeSTPStatus 9 }
   
gs2328pMSTI4TopologyChangeLast OBJECT-TYPE
   SYNTAX       DisplayString
   MAX-ACCESS   read-only
   STATUS       current
   DESCRIPTION
       "The time passed since the Topology Flag was last set."
   ::= { gs2328pMSTI4BridgeSTPStatus 10 }
   
gs2328pMSTI4PortStateTable OBJECT-TYPE
   SYNTAX      SEQUENCE OF Gs2328pMSTI4PortStateEntry
   MAX-ACCESS  not-accessible
   STATUS      current
   DESCRIPTION
       " Show MSTI4 Ports and Aggregations State Configurations. "
   ::= { gs2328pMSTI4BridgeSTP 2 }

gs2328pMSTI4PortStateEntry OBJECT-TYPE
   SYNTAX      Gs2328pMSTI4PortStateEntry
   MAX-ACCESS  not-accessible
   STATUS      current
   DESCRIPTION
       ""
   INDEX    { gs2328pMSTI4PortStateIndex  }
   ::= { gs2328pMSTI4PortStateTable 1 }

Gs2328pMSTI4PortStateEntry ::= SEQUENCE {
   gs2328pMSTI4PortStateIndex        Integer32,
   gs2328pMSTI4PortStatePort         DisplayString,
   gs2328pMSTI4PortStatePortID       DisplayString,
   gs2328pMSTI4PortStateRole         DisplayString,
   gs2328pMSTI4PortStateState        DisplayString,
   gs2328pMSTI4PortStatePathCost     Integer32,
   gs2328pMSTI4PortStateEdge         DisplayString,
   gs2328pMSTI4PortStatePoint2Point  DisplayString,
   gs2328pMSTI4PortStateUptime       DisplayString
}

gs2328pMSTI4PortStateIndex OBJECT-TYPE
   SYNTAX      Integer32(1..4095)
   MAX-ACCESS  not-accessible
   STATUS      current
   DESCRIPTION
       "table index."
   ::= { gs2328pMSTI4PortStateEntry 1 }
   
gs2328pMSTI4PortStatePort OBJECT-TYPE
   SYNTAX      DisplayString
   MAX-ACCESS  read-only
   STATUS      current
   DESCRIPTION
       "The switch port number of the logical STP port."
   ::= { gs2328pMSTI4PortStateEntry 2 }
   
gs2328pMSTI4PortStatePortID OBJECT-TYPE
   SYNTAX      DisplayString
   MAX-ACCESS  read-only
   STATUS      current
   DESCRIPTION
       "The port id as used by the STP protocol. 
        This is the priority part and the logical port index of the bridge port."
   ::= { gs2328pMSTI4PortStateEntry 3 }
   
gs2328pMSTI4PortStateRole OBJECT-TYPE
   SYNTAX      DisplayString
   MAX-ACCESS  read-only
   STATUS      current
   DESCRIPTION
       "The current STP port role."
   ::= { gs2328pMSTI4PortStateEntry 4 }
   
gs2328pMSTI4PortStateState OBJECT-TYPE
   SYNTAX      DisplayString
   MAX-ACCESS  read-only
   STATUS      current
   DESCRIPTION
       "The current STP port state."
   ::= { gs2328pMSTI4PortStateEntry 5 }
   
gs2328pMSTI4PortStatePathCost OBJECT-TYPE
   SYNTAX      Integer32(0..200000000)
   MAX-ACCESS  read-only
   STATUS      current
   DESCRIPTION
       "The current STP port path cost."
   ::= { gs2328pMSTI4PortStateEntry 6 }
   
gs2328pMSTI4PortStateEdge OBJECT-TYPE
   SYNTAX      DisplayString
   MAX-ACCESS  read-only
   STATUS      current
   DESCRIPTION
       "The current STP port Edge Flag."
   ::= { gs2328pMSTI4PortStateEntry 7 }
   
gs2328pMSTI4PortStatePoint2Point OBJECT-TYPE
   SYNTAX      DisplayString
   MAX-ACCESS  read-only
   STATUS      current
   DESCRIPTION
       "The current STP port point-to-point flag."
   ::= { gs2328pMSTI4PortStateEntry 8 }
   
gs2328pMSTI4PortStateUptime OBJECT-TYPE
   SYNTAX      DisplayString
   MAX-ACCESS  read-only
   STATUS      current
   DESCRIPTION
       "The time since the bridge port was last initialized."
   ::= { gs2328pMSTI4PortStateEntry 9 }
   
gs2328pMSTI5BridgeSTP                                                        OBJECT IDENTIFIER ::= { gs2328pSTPBridgeStatus 6 }

gs2328pMSTI5BridgeSTPStatus                                                  OBJECT IDENTIFIER ::= { gs2328pMSTI5BridgeSTP 1 }
      
gs2328pMSTI5BridgeInstance OBJECT-TYPE
   SYNTAX       DisplayString
   MAX-ACCESS   read-only
   STATUS       current
   DESCRIPTION
       "The Bridge instance - CIST, MST1, ..."
   ::= { gs2328pMSTI5BridgeSTPStatus 1 }
   
gs2328pMSTI5BridgeID OBJECT-TYPE
   SYNTAX       DisplayString
   MAX-ACCESS   read-only
   STATUS       current
   DESCRIPTION
       "The Bridge ID of this Bridge instance."
   ::= { gs2328pMSTI5BridgeSTPStatus 2 }
   
gs2328pMSTI5RootID OBJECT-TYPE
   SYNTAX       DisplayString
   MAX-ACCESS   read-only
   STATUS       current
   DESCRIPTION
       "The Bridge ID of the currently elected root bridge."
   ::= { gs2328pMSTI5BridgeSTPStatus 3 }
   
gs2328pMSTI5RootPort OBJECT-TYPE
   SYNTAX       DisplayString
   MAX-ACCESS   read-only
   STATUS       current
   DESCRIPTION
       "The switch port currently assigned the root port role."
   ::= { gs2328pMSTI5BridgeSTPStatus 4 }

gs2328pMSTI5RootCost OBJECT-TYPE
   SYNTAX       Integer32(0..200000000)
   MAX-ACCESS   read-only
   STATUS       current
   DESCRIPTION
       "Root Path Cost."
   ::= { gs2328pMSTI5BridgeSTPStatus 5 }

gs2328pMSTI5TopologyFlag OBJECT-TYPE
   SYNTAX       DisplayString
   MAX-ACCESS   read-only
   STATUS       current
   DESCRIPTION
       "The current state of the Topology Change Flag of this Bridge instance."
   ::= { gs2328pMSTI5BridgeSTPStatus 8 }

gs2328pMSTI5TopologyChangeCount OBJECT-TYPE
   SYNTAX       Counter32
   MAX-ACCESS   read-only
   STATUS       current
   DESCRIPTION
       "The number of times where the topology change flag has been set."
   ::= { gs2328pMSTI5BridgeSTPStatus 9 }
   
gs2328pMSTI5TopologyChangeLast OBJECT-TYPE
   SYNTAX       DisplayString
   MAX-ACCESS   read-only
   STATUS       current
   DESCRIPTION
       "The time passed since the Topology Flag was last set."
   ::= { gs2328pMSTI5BridgeSTPStatus 10 }
   
gs2328pMSTI5PortStateTable OBJECT-TYPE
   SYNTAX      SEQUENCE OF Gs2328pMSTI5PortStateEntry
   MAX-ACCESS  not-accessible
   STATUS      current
   DESCRIPTION
       " Show MSTI5 Ports and Aggregations State Configurations. "
   ::= { gs2328pMSTI5BridgeSTP 2 }

gs2328pMSTI5PortStateEntry OBJECT-TYPE
   SYNTAX      Gs2328pMSTI5PortStateEntry
   MAX-ACCESS  not-accessible
   STATUS      current
   DESCRIPTION
       ""
   INDEX    { gs2328pMSTI5PortStateIndex  }
   ::= { gs2328pMSTI5PortStateTable 1 }

Gs2328pMSTI5PortStateEntry ::= SEQUENCE {
   gs2328pMSTI5PortStateIndex        Integer32,
   gs2328pMSTI5PortStatePort         DisplayString,
   gs2328pMSTI5PortStatePortID       DisplayString,
   gs2328pMSTI5PortStateRole         DisplayString,
   gs2328pMSTI5PortStateState        DisplayString,
   gs2328pMSTI5PortStatePathCost     Integer32,
   gs2328pMSTI5PortStateEdge         DisplayString,
   gs2328pMSTI5PortStatePoint2Point  DisplayString,
   gs2328pMSTI5PortStateUptime       DisplayString
}

gs2328pMSTI5PortStateIndex OBJECT-TYPE
   SYNTAX      Integer32(1..4095)
   MAX-ACCESS  not-accessible
   STATUS      current
   DESCRIPTION
       "table index."
   ::= { gs2328pMSTI5PortStateEntry 1 }
   
gs2328pMSTI5PortStatePort OBJECT-TYPE
   SYNTAX      DisplayString
   MAX-ACCESS  read-only
   STATUS      current
   DESCRIPTION
       "The switch port number of the logical STP port."
   ::= { gs2328pMSTI5PortStateEntry 2 }
   
gs2328pMSTI5PortStatePortID OBJECT-TYPE
   SYNTAX      DisplayString
   MAX-ACCESS  read-only
   STATUS      current
   DESCRIPTION
       "The port id as used by the STP protocol. 
        This is the priority part and the logical port index of the bridge port."
   ::= { gs2328pMSTI5PortStateEntry 3 }
   
gs2328pMSTI5PortStateRole OBJECT-TYPE
   SYNTAX      DisplayString
   MAX-ACCESS  read-only
   STATUS      current
   DESCRIPTION
       "The current STP port role."
   ::= { gs2328pMSTI5PortStateEntry 4 }
   
gs2328pMSTI5PortStateState OBJECT-TYPE
   SYNTAX      DisplayString
   MAX-ACCESS  read-only
   STATUS      current
   DESCRIPTION
       "The current STP port state."
   ::= { gs2328pMSTI5PortStateEntry 5 }
   
gs2328pMSTI5PortStatePathCost OBJECT-TYPE
   SYNTAX      Integer32(0..200000000)
   MAX-ACCESS  read-only
   STATUS      current
   DESCRIPTION
       "The current STP port path cost."
   ::= { gs2328pMSTI5PortStateEntry 6 }
   
gs2328pMSTI5PortStateEdge OBJECT-TYPE
   SYNTAX      DisplayString
   MAX-ACCESS  read-only
   STATUS      current
   DESCRIPTION
       "The current STP port Edge Flag."
   ::= { gs2328pMSTI5PortStateEntry 7 }
   
gs2328pMSTI5PortStatePoint2Point OBJECT-TYPE
   SYNTAX      DisplayString
   MAX-ACCESS  read-only
   STATUS      current
   DESCRIPTION
       "The current STP port point-to-point flag."
   ::= { gs2328pMSTI5PortStateEntry 8 }
   
gs2328pMSTI5PortStateUptime OBJECT-TYPE
   SYNTAX      DisplayString
   MAX-ACCESS  read-only
   STATUS      current
   DESCRIPTION
       "The time since the bridge port was last initialized."
   ::= { gs2328pMSTI5PortStateEntry 9 }
   
gs2328pMSTI6BridgeSTP                                                        OBJECT IDENTIFIER ::= { gs2328pSTPBridgeStatus 7 }

gs2328pMSTI6BridgeSTPStatus                                                  OBJECT IDENTIFIER ::= { gs2328pMSTI6BridgeSTP 1 }
      
gs2328pMSTI6BridgeInstance OBJECT-TYPE
   SYNTAX       DisplayString
   MAX-ACCESS   read-only
   STATUS       current
   DESCRIPTION
       "The Bridge instance - CIST, MST1, ..."
   ::= { gs2328pMSTI6BridgeSTPStatus 1 }
   
gs2328pMSTI6BridgeID OBJECT-TYPE
   SYNTAX       DisplayString
   MAX-ACCESS   read-only
   STATUS       current
   DESCRIPTION
       "The Bridge ID of this Bridge instance."
   ::= { gs2328pMSTI6BridgeSTPStatus 2 }
   
gs2328pMSTI6RootID OBJECT-TYPE
   SYNTAX       DisplayString
   MAX-ACCESS   read-only
   STATUS       current
   DESCRIPTION
       "The Bridge ID of the currently elected root bridge."
   ::= { gs2328pMSTI6BridgeSTPStatus 3 }
   
gs2328pMSTI6RootPort OBJECT-TYPE
   SYNTAX       DisplayString
   MAX-ACCESS   read-only
   STATUS       current
   DESCRIPTION
       "The switch port currently assigned the root port role."
   ::= { gs2328pMSTI6BridgeSTPStatus 4 }

gs2328pMSTI6RootCost OBJECT-TYPE
   SYNTAX       Integer32(0..200000000)
   MAX-ACCESS   read-only
   STATUS       current
   DESCRIPTION
       "Root Path Cost."
   ::= { gs2328pMSTI6BridgeSTPStatus 5 }

gs2328pMSTI6TopologyFlag OBJECT-TYPE
   SYNTAX       DisplayString
   MAX-ACCESS   read-only
   STATUS       current
   DESCRIPTION
       "The current state of the Topology Change Flag of this Bridge instance."
   ::= { gs2328pMSTI6BridgeSTPStatus 8 }

gs2328pMSTI6TopologyChangeCount OBJECT-TYPE
   SYNTAX       Counter32
   MAX-ACCESS   read-only
   STATUS       current
   DESCRIPTION
       "The number of times where the topology change flag has been set."
   ::= { gs2328pMSTI6BridgeSTPStatus 9 }
   
gs2328pMSTI6TopologyChangeLast OBJECT-TYPE
   SYNTAX       DisplayString
   MAX-ACCESS   read-only
   STATUS       current
   DESCRIPTION
       "The time passed since the Topology Flag was last set."
   ::= { gs2328pMSTI6BridgeSTPStatus 10 }
   
gs2328pMSTI6PortStateTable OBJECT-TYPE
   SYNTAX      SEQUENCE OF Gs2328pMSTI6PortStateEntry
   MAX-ACCESS  not-accessible
   STATUS      current
   DESCRIPTION
       " Show MSTI6 Ports and Aggregations State Configurations. "
   ::= { gs2328pMSTI6BridgeSTP 2 }

gs2328pMSTI6PortStateEntry OBJECT-TYPE
   SYNTAX      Gs2328pMSTI6PortStateEntry
   MAX-ACCESS  not-accessible
   STATUS      current
   DESCRIPTION
       ""
   INDEX    { gs2328pMSTI6PortStateIndex  }
   ::= { gs2328pMSTI6PortStateTable 1 }

Gs2328pMSTI6PortStateEntry ::= SEQUENCE {
   gs2328pMSTI6PortStateIndex        Integer32,
   gs2328pMSTI6PortStatePort         DisplayString,
   gs2328pMSTI6PortStatePortID       DisplayString,
   gs2328pMSTI6PortStateRole         DisplayString,
   gs2328pMSTI6PortStateState        DisplayString,
   gs2328pMSTI6PortStatePathCost     Integer32,
   gs2328pMSTI6PortStateEdge         DisplayString,
   gs2328pMSTI6PortStatePoint2Point  DisplayString,
   gs2328pMSTI6PortStateUptime       DisplayString
}

gs2328pMSTI6PortStateIndex OBJECT-TYPE
   SYNTAX      Integer32(1..4095)
   MAX-ACCESS  not-accessible
   STATUS      current
   DESCRIPTION
       "table index."
   ::= { gs2328pMSTI6PortStateEntry 1 }
   
gs2328pMSTI6PortStatePort OBJECT-TYPE
   SYNTAX      DisplayString
   MAX-ACCESS  read-only
   STATUS      current
   DESCRIPTION
       "The switch port number of the logical STP port."
   ::= { gs2328pMSTI6PortStateEntry 2 }
   
gs2328pMSTI6PortStatePortID OBJECT-TYPE
   SYNTAX      DisplayString
   MAX-ACCESS  read-only
   STATUS      current
   DESCRIPTION
       "The port id as used by the STP protocol. 
        This is the priority part and the logical port index of the bridge port."
   ::= { gs2328pMSTI6PortStateEntry 3 }
   
gs2328pMSTI6PortStateRole OBJECT-TYPE
   SYNTAX      DisplayString
   MAX-ACCESS  read-only
   STATUS      current
   DESCRIPTION
       "The current STP port role."
   ::= { gs2328pMSTI6PortStateEntry 4 }
   
gs2328pMSTI6PortStateState OBJECT-TYPE
   SYNTAX      DisplayString
   MAX-ACCESS  read-only
   STATUS      current
   DESCRIPTION
       "The current STP port state."
   ::= { gs2328pMSTI6PortStateEntry 5 }
   
gs2328pMSTI6PortStatePathCost OBJECT-TYPE
   SYNTAX      Integer32(0..200000000)
   MAX-ACCESS  read-only
   STATUS      current
   DESCRIPTION
       "The current STP port path cost."
   ::= { gs2328pMSTI6PortStateEntry 6 }
   
gs2328pMSTI6PortStateEdge OBJECT-TYPE
   SYNTAX      DisplayString
   MAX-ACCESS  read-only
   STATUS      current
   DESCRIPTION
       "The current STP port Edge Flag."
   ::= { gs2328pMSTI6PortStateEntry 7 }
   
gs2328pMSTI6PortStatePoint2Point OBJECT-TYPE
   SYNTAX      DisplayString
   MAX-ACCESS  read-only
   STATUS      current
   DESCRIPTION
       "The current STP port point-to-point flag."
   ::= { gs2328pMSTI6PortStateEntry 8 }
   
gs2328pMSTI6PortStateUptime OBJECT-TYPE
   SYNTAX      DisplayString
   MAX-ACCESS  read-only
   STATUS      current
   DESCRIPTION
       "The time since the bridge port was last initialized."
   ::= { gs2328pMSTI6PortStateEntry 9 }
   
gs2328pMSTI7BridgeSTP                                                        OBJECT IDENTIFIER ::= { gs2328pSTPBridgeStatus 8 }

gs2328pMSTI7BridgeSTPStatus                                                  OBJECT IDENTIFIER ::= { gs2328pMSTI7BridgeSTP 1 }
      
gs2328pMSTI7BridgeInstance OBJECT-TYPE
   SYNTAX       DisplayString
   MAX-ACCESS   read-only
   STATUS       current
   DESCRIPTION
       "The Bridge instance - CIST, MST1, ..."
   ::= { gs2328pMSTI7BridgeSTPStatus 1 }
   
gs2328pMSTI7BridgeID OBJECT-TYPE
   SYNTAX       DisplayString
   MAX-ACCESS   read-only
   STATUS       current
   DESCRIPTION
       "The Bridge ID of this Bridge instance."
   ::= { gs2328pMSTI7BridgeSTPStatus 2 }
   
gs2328pMSTI7RootID OBJECT-TYPE
   SYNTAX       DisplayString
   MAX-ACCESS   read-only
   STATUS       current
   DESCRIPTION
       "The Bridge ID of the currently elected root bridge."
   ::= { gs2328pMSTI7BridgeSTPStatus 3 }
   
gs2328pMSTI7RootPort OBJECT-TYPE
   SYNTAX       DisplayString
   MAX-ACCESS   read-only
   STATUS       current
   DESCRIPTION
       "The switch port currently assigned the root port role."
   ::= { gs2328pMSTI7BridgeSTPStatus 4 }

gs2328pMSTI7RootCost OBJECT-TYPE
   SYNTAX       Integer32(0..200000000)
   MAX-ACCESS   read-only
   STATUS       current
   DESCRIPTION
       "Root Path Cost."
   ::= { gs2328pMSTI7BridgeSTPStatus 5 }

gs2328pMSTI7TopologyFlag OBJECT-TYPE
   SYNTAX       DisplayString
   MAX-ACCESS   read-only
   STATUS       current
   DESCRIPTION
       "The current state of the Topology Change Flag of this Bridge instance."
   ::= { gs2328pMSTI7BridgeSTPStatus 8 }

gs2328pMSTI7TopologyChangeCount OBJECT-TYPE
   SYNTAX       Counter32
   MAX-ACCESS   read-only
   STATUS       current
   DESCRIPTION
       "The number of times where the topology change flag has been set."
   ::= { gs2328pMSTI7BridgeSTPStatus 9 }
   
gs2328pMSTI7TopologyChangeLast OBJECT-TYPE
   SYNTAX       DisplayString
   MAX-ACCESS   read-only
   STATUS       current
   DESCRIPTION
       "The time passed since the Topology Flag was last set."
   ::= { gs2328pMSTI7BridgeSTPStatus 10 }
   
gs2328pMSTI7PortStateTable OBJECT-TYPE
   SYNTAX      SEQUENCE OF Gs2328pMSTI7PortStateEntry
   MAX-ACCESS  not-accessible
   STATUS      current
   DESCRIPTION
       " Show MSTI7 Ports and Aggregations State Configurations. "
   ::= { gs2328pMSTI7BridgeSTP 2 }

gs2328pMSTI7PortStateEntry OBJECT-TYPE
   SYNTAX      Gs2328pMSTI7PortStateEntry
   MAX-ACCESS  not-accessible
   STATUS      current
   DESCRIPTION
       ""
   INDEX    { gs2328pMSTI7PortStateIndex  }
   ::= { gs2328pMSTI7PortStateTable 1 }

Gs2328pMSTI7PortStateEntry ::= SEQUENCE {
   gs2328pMSTI7PortStateIndex        Integer32,
   gs2328pMSTI7PortStatePort         DisplayString,
   gs2328pMSTI7PortStatePortID       DisplayString,
   gs2328pMSTI7PortStateRole         DisplayString,
   gs2328pMSTI7PortStateState        DisplayString,
   gs2328pMSTI7PortStatePathCost     Integer32,
   gs2328pMSTI7PortStateEdge         DisplayString,
   gs2328pMSTI7PortStatePoint2Point  DisplayString,
   gs2328pMSTI7PortStateUptime       DisplayString
}

gs2328pMSTI7PortStateIndex OBJECT-TYPE
   SYNTAX      Integer32(1..4095)
   MAX-ACCESS  not-accessible
   STATUS      current
   DESCRIPTION
       "table index."
   ::= { gs2328pMSTI7PortStateEntry 1 }
   
gs2328pMSTI7PortStatePort OBJECT-TYPE
   SYNTAX      DisplayString
   MAX-ACCESS  read-only
   STATUS      current
   DESCRIPTION
       "The switch port number of the logical STP port."
   ::= { gs2328pMSTI7PortStateEntry 2 }
   
gs2328pMSTI7PortStatePortID OBJECT-TYPE
   SYNTAX      DisplayString
   MAX-ACCESS  read-only
   STATUS      current
   DESCRIPTION
       "The port id as used by the STP protocol. 
        This is the priority part and the logical port index of the bridge port."
   ::= { gs2328pMSTI7PortStateEntry 3 }
   
gs2328pMSTI7PortStateRole OBJECT-TYPE
   SYNTAX      DisplayString
   MAX-ACCESS  read-only
   STATUS      current
   DESCRIPTION
       "The current STP port role."
   ::= { gs2328pMSTI7PortStateEntry 4 }
   
gs2328pMSTI7PortStateState OBJECT-TYPE
   SYNTAX      DisplayString
   MAX-ACCESS  read-only
   STATUS      current
   DESCRIPTION
       "The current STP port state."
   ::= { gs2328pMSTI7PortStateEntry 5 }
   
gs2328pMSTI7PortStatePathCost OBJECT-TYPE
   SYNTAX      Integer32(0..200000000)
   MAX-ACCESS  read-only
   STATUS      current
   DESCRIPTION
       "The current STP port path cost."
   ::= { gs2328pMSTI7PortStateEntry 6 }
   
gs2328pMSTI7PortStateEdge OBJECT-TYPE
   SYNTAX      DisplayString
   MAX-ACCESS  read-only
   STATUS      current
   DESCRIPTION
       "The current STP port Edge Flag."
   ::= { gs2328pMSTI7PortStateEntry 7 }
   
gs2328pMSTI7PortStatePoint2Point OBJECT-TYPE
   SYNTAX      DisplayString
   MAX-ACCESS  read-only
   STATUS      current
   DESCRIPTION
       "The current STP port point-to-point flag."
   ::= { gs2328pMSTI7PortStateEntry 8 }
   
gs2328pMSTI7PortStateUptime OBJECT-TYPE
   SYNTAX      DisplayString
   MAX-ACCESS  read-only
   STATUS      current
   DESCRIPTION
       "The time since the bridge port was last initialized."
   ::= { gs2328pMSTI7PortStateEntry 9 }
   
gs2328pSTPPortStatusTable OBJECT-TYPE
   SYNTAX      SEQUENCE OF Gs2328pSTPPortStatusEntry
   MAX-ACCESS  not-accessible
   STATUS      current
   DESCRIPTION
       " Show STP Port Status."
   ::= { gs2328pSTP 9 }

gs2328pSTPPortStatusEntry OBJECT-TYPE
   SYNTAX      Gs2328pSTPPortStatusEntry
   MAX-ACCESS  not-accessible
   STATUS      current
   DESCRIPTION
       ""
   INDEX    { gs2328pSTPPortStatusPort  }
   ::= { gs2328pSTPPortStatusTable 1 }

Gs2328pSTPPortStatusEntry ::= SEQUENCE {
   gs2328pSTPPortStatusPort         Integer32,
   gs2328pSTPPortStatusCISTRole     DisplayString,
   gs2328pSTPPortStatusCISTState    DisplayString,
   gs2328pSTPPortStatusUptime       DisplayString
}

gs2328pSTPPortStatusPort OBJECT-TYPE
   SYNTAX      Integer32(1..4095)
   MAX-ACCESS  not-accessible
   STATUS      current
   DESCRIPTION
       " port, range : 1 - port number. "
   ::= { gs2328pSTPPortStatusEntry 1 }

gs2328pSTPPortStatusCISTRole OBJECT-TYPE
   SYNTAX      DisplayString
   MAX-ACCESS  read-only
   STATUS      current
   DESCRIPTION
       " The current STP port role of the CIST port. "
   ::= { gs2328pSTPPortStatusEntry 2 }

gs2328pSTPPortStatusCISTState OBJECT-TYPE
   SYNTAX      DisplayString
   MAX-ACCESS  read-only
   STATUS      current
   DESCRIPTION
       " The current STP port state of the CIST port. "
   ::= { gs2328pSTPPortStatusEntry 3 }

gs2328pSTPPortStatusUptime OBJECT-TYPE
   SYNTAX      DisplayString
   MAX-ACCESS  read-only
   STATUS      current
   DESCRIPTION
       " The time since the bridge port was last initialized. "
   ::= { gs2328pSTPPortStatusEntry 4 }
   
gs2328pSTPPortStatisticsTable OBJECT-TYPE
   SYNTAX      SEQUENCE OF Gs2328pSTPPortStatisticsEntry
   MAX-ACCESS  not-accessible
   STATUS      current
   DESCRIPTION
       " Show STP Port Statistics."
   ::= { gs2328pSTP 10 }

gs2328pSTPPortStatisticsEntry OBJECT-TYPE
   SYNTAX      Gs2328pSTPPortStatisticsEntry
   MAX-ACCESS  not-accessible
   STATUS      current
   DESCRIPTION
       ""
   INDEX    { gs2328pSTPStatisticsIndex  }
   ::= { gs2328pSTPPortStatisticsTable 1 }

Gs2328pSTPPortStatisticsEntry ::= SEQUENCE {
   gs2328pSTPStatisticsIndex            Integer32,
   gs2328pSTPStatisticsPort             DisplayString,
   gs2328pSTPStatisticsTxMSTP           Counter32,
   gs2328pSTPStatisticsTxRSTP           Counter32,
   gs2328pSTPStatisticsTxSTP            Counter32,
   gs2328pSTPStatisticsTxTCN            Counter32,
   gs2328pSTPStatisticsRxMSTP           Counter32,
   gs2328pSTPStatisticsRxRSTP           Counter32,
   gs2328pSTPStatisticsRxSTP            Counter32,
   gs2328pSTPStatisticsRxTCN            Counter32,
   gs2328pSTPStatisticsDiscardedUnknown Counter32,
   gs2328pSTPStatisticsDiscardedIllegal Counter32
}

gs2328pSTPStatisticsIndex OBJECT-TYPE
   SYNTAX      Integer32(1..4095)
   MAX-ACCESS  not-accessible
   STATUS      current
   DESCRIPTION
       "table index."
   ::= { gs2328pSTPPortStatisticsEntry 1 }
   
gs2328pSTPStatisticsPort OBJECT-TYPE
   SYNTAX      DisplayString
   MAX-ACCESS  not-accessible
   STATUS      current
   DESCRIPTION
       " port, range : 1 - port number. "
   ::= { gs2328pSTPPortStatisticsEntry 2 }

gs2328pSTPStatisticsTxMSTP OBJECT-TYPE
   SYNTAX      Counter32
   MAX-ACCESS  read-only
   STATUS      current
   DESCRIPTION
       " The number of MSTP Configuration BPDU's received/transmitted on the port."
   ::= { gs2328pSTPPortStatisticsEntry 3 }

gs2328pSTPStatisticsTxRSTP OBJECT-TYPE
   SYNTAX      Counter32
   MAX-ACCESS  read-only
   STATUS      current
   DESCRIPTION
       " The number of RSTP Configuration BPDU's received/transmitted on the port. "
   ::= { gs2328pSTPPortStatisticsEntry 4 }

gs2328pSTPStatisticsTxSTP OBJECT-TYPE
   SYNTAX      Counter32
   MAX-ACCESS  read-only
   STATUS      current
   DESCRIPTION
       " The number of legacy STP Configuration BPDU's received/transmitted on the port. "
   ::= { gs2328pSTPPortStatisticsEntry 5 }

gs2328pSTPStatisticsTxTCN OBJECT-TYPE
   SYNTAX      Counter32
   MAX-ACCESS  read-only
   STATUS      current
   DESCRIPTION
       " The number of Topology Change Notification BPDU's received/transmitted on the port. "
   ::= { gs2328pSTPPortStatisticsEntry 6 }
   
gs2328pSTPStatisticsRxMSTP OBJECT-TYPE
   SYNTAX      Counter32
   MAX-ACCESS  read-only
   STATUS      current
   DESCRIPTION
       " The number of MSTP Configuration BPDU's received/transmitted on the port."
   ::= { gs2328pSTPPortStatisticsEntry 7 }

gs2328pSTPStatisticsRxRSTP OBJECT-TYPE
   SYNTAX      Counter32
   MAX-ACCESS  read-only
   STATUS      current
   DESCRIPTION
       " The number of RSTP Configuration BPDU's received/transmitted on the port. "
   ::= { gs2328pSTPPortStatisticsEntry 8 }

gs2328pSTPStatisticsRxSTP OBJECT-TYPE
   SYNTAX      Counter32
   MAX-ACCESS  read-only
   STATUS      current
   DESCRIPTION
       " The number of legacy STP Configuration BPDU's received/transmitted on the port. "
   ::= { gs2328pSTPPortStatisticsEntry 9 }

gs2328pSTPStatisticsRxTCN OBJECT-TYPE
   SYNTAX      Counter32
   MAX-ACCESS  read-only
   STATUS      current
   DESCRIPTION
       " The number of Topology Change Notification BPDU's received/transmitted on the port. "
   ::= { gs2328pSTPPortStatisticsEntry 10 }

gs2328pSTPStatisticsDiscardedUnknown OBJECT-TYPE
   SYNTAX      Counter32
   MAX-ACCESS  read-only
   STATUS      current
   DESCRIPTION
       " The number of unknown Spanning Tree BPDU's received and discarded on the port. "
   ::= { gs2328pSTPPortStatisticsEntry 11 }
   
gs2328pSTPStatisticsDiscardedIllegal OBJECT-TYPE
   SYNTAX      Counter32
   MAX-ACCESS  read-only
   STATUS      current
   DESCRIPTION
       " The number of illegal Spanning Tree BPDU's received and discarded on the port. "
   ::= { gs2328pSTPPortStatisticsEntry 12 }


gs2328pFilteringDataBase                                                  OBJECT IDENTIFIER ::= { gs2328pConfiguration 21 }

gs2328pFilteringDataBaseConfig                                            OBJECT IDENTIFIER ::= { gs2328pFilteringDataBase 1 }

gs2328pFilteringDataBaseAgingTime OBJECT-TYPE
   SYNTAX      Integer32(0..1000000)
   MAX-ACCESS  read-write
   STATUS      current
   DESCRIPTION
       "Configure aging time by entering a value here in seconds.
        default: 300,
        range: 10-1000000. 
        Disable automatic aging : 0."
   ::= { gs2328pFilteringDataBaseConfig 1 }

gs2328pFilteringDataBaseConfigTable OBJECT-TYPE
   SYNTAX      SEQUENCE OF GS2328PFilteringDataBaseConfigEntry
   MAX-ACCESS  not-accessible
   STATUS      current
   DESCRIPTION
       " "
   ::= { gs2328pFilteringDataBaseConfig 2 }

gs2328pFilteringDataBaseConfigEntry OBJECT-TYPE
   SYNTAX      GS2328PFilteringDataBaseConfigEntry
   MAX-ACCESS  not-accessible
   STATUS      current
   DESCRIPTION
       ""
   INDEX    { gs2328pFilteringDataBaseConfigPort  }
   ::= { gs2328pFilteringDataBaseConfigTable 1 }
   
GS2328PFilteringDataBaseConfigEntry ::= SEQUENCE {
   gs2328pFilteringDataBaseConfigPort        Integer32,
   gs2328pFilteringDataBaseConfigLearning    INTEGER
}

gs2328pFilteringDataBaseConfigPort OBJECT-TYPE
   SYNTAX      Integer32(1..4095)
   MAX-ACCESS  not-accessible
   STATUS      current
   DESCRIPTION
       " "
   ::= { gs2328pFilteringDataBaseConfigEntry 1 }

gs2328pFilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2328pFilteringDataBaseConfigEntry 2 }


gs2328pFilteringDataBaseStaticMAC                                OBJECT IDENTIFIER ::= { gs2328pFilteringDataBaseConfig 3 }

gs2328pFilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2328pFilteringDataBaseStaticMAC 1 }

gs2328pFilteringDataBaseStaticMACTable OBJECT-TYPE
   SYNTAX      SEQUENCE OF GS2328PFilteringDataBaseStaticMACEntry
   MAX-ACCESS  not-accessible
   STATUS      current
   DESCRIPTION
       " "
   ::= { gs2328pFilteringDataBaseStaticMAC 2 }

gs2328pFilteringDataBaseStaticMACEntry OBJECT-TYPE
   SYNTAX      GS2328PFilteringDataBaseStaticMACEntry
   MAX-ACCESS  not-accessible
   STATUS      current
   DESCRIPTION
       ""
   INDEX    { gs2328pFilteringDataBaseStaticMACIndex  }
   ::= { gs2328pFilteringDataBaseStaticMACTable 1 }

GS2328PFilteringDataBaseStaticMACEntry ::= SEQUENCE {
   gs2328pFilteringDataBaseStaticMACIndex	    Integer32,
   gs2328pFilteringDataBaseStaticMACVLANId	    Integer32,
   gs2328pFilteringDataBaseStaticMACAddress      MacAddress,
   gs2328pFilteringDataBaseStaticMACPortMembers  DisplayString,
   gs2328pFilteringDataBaseStaticMACRowStatus	INTEGER
}

gs2328pFilteringDataBaseStaticMACIndex OBJECT-TYPE
   SYNTAX      Integer32(1..4095)
   MAX-ACCESS  not-accessible
   STATUS      current
   DESCRIPTION
       " "
   ::= { gs2328pFilteringDataBaseStaticMACEntry 1 }

gs2328pFilteringDataBaseStaticMACVLANId OBJECT-TYPE
   SYNTAX      Integer32(1..4094)
   MAX-ACCESS  read-write
   STATUS      current
   DESCRIPTION
       " VLAN ID, range: 1 - 4094. "
   ::= { gs2328pFilteringDataBaseStaticMACEntry 2 }

gs2328pFilteringDataBaseStaticMACAddress OBJECT-TYPE
   SYNTAX      MacAddress
   MAX-ACCESS  read-write
   STATUS      current
   DESCRIPTION
       " MAC address, format 0a 1b 2c 3d 4e 5f "
   ::= { gs2328pFilteringDataBaseStaticMACEntry 3 }

gs2328pFilteringDataBaseStaticMACPortMembers OBJECT-TYPE
   SYNTAX      DisplayString
   MAX-ACCESS  read-write
   STATUS      current
   DESCRIPTION
       "To include the ports in a Static MAC Table"
   ::= { gs2328pFilteringDataBaseStaticMACEntry 4 }

gs2328pFilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2328pFilteringDataBaseStaticMACEntry 5 }
   

gs2328pFilteringDataBaseDynamicMACTable OBJECT-TYPE
   SYNTAX      SEQUENCE OF GS2328PFilteringDataBaseDynamicMACEntry
   MAX-ACCESS  not-accessible
   STATUS      current
   DESCRIPTION
       " "
   ::= { gs2328pFilteringDataBaseConfig 4 }

gs2328pFilteringDataBaseDynamicMACEntry OBJECT-TYPE
   SYNTAX      GS2328PFilteringDataBaseDynamicMACEntry
   MAX-ACCESS  not-accessible
   STATUS      current
   DESCRIPTION
       ""
   INDEX    { gs2328pFilteringDataBaseDynamicMACIndex  }
   ::= { gs2328pFilteringDataBaseDynamicMACTable 1 }
   
GS2328PFilteringDataBaseDynamicMACEntry ::= SEQUENCE {
   gs2328pFilteringDataBaseDynamicMACIndex	    Integer32,
   gs2328pFilteringDataBaseDynamicMACType	    INTEGER,
   gs2328pFilteringDataBaseDynamicMACVLAN	    Integer32,
   gs2328pFilteringDataBaseDynamicMACAddress     MacAddress,
   gs2328pFilteringDataBaseDynamicPortMembers    DisplayString
}

gs2328pFilteringDataBaseDynamicMACIndex OBJECT-TYPE
   SYNTAX      Integer32(1..4095)
   MAX-ACCESS  not-accessible
   STATUS      current
   DESCRIPTION
       " "
   ::= { gs2328pFilteringDataBaseDynamicMACEntry 1 }

gs2328pFilteringDataBaseDynamicMACType OBJECT-TYPE
   SYNTAX      INTEGER { dynamic(0), static(1) }
   MAX-ACCESS  read-only
   STATUS      current
   DESCRIPTION
       "Indicates whether the entry is a static or a dynamic entry."
   ::= { gs2328pFilteringDataBaseDynamicMACEntry 2 }

gs2328pFilteringDataBaseDynamicMACVLAN OBJECT-TYPE
   SYNTAX      Integer32(1..4094)
   MAX-ACCESS  read-only
   STATUS      current
   DESCRIPTION
       "The VLAN ID of the entry."
   ::= { gs2328pFilteringDataBaseDynamicMACEntry 3 }

gs2328pFilteringDataBaseDynamicMACAddress OBJECT-TYPE
   SYNTAX      MacAddress
   MAX-ACCESS  read-only
   STATUS      current
   DESCRIPTION
       "The MAC address of the entry."
   ::= { gs2328pFilteringDataBaseDynamicMACEntry 4 }
   
gs2328pFilteringDataBaseDynamicPortMembers OBJECT-TYPE
   SYNTAX      DisplayString
   MAX-ACCESS  read-only
   STATUS      current
   DESCRIPTION
       "The ports that are members of the entry."
   ::= { gs2328pFilteringDataBaseDynamicMACEntry 5 } 


gs2328pSFlowAgent                                                  OBJECT IDENTIFIER ::= { gs2328pConfiguration 22 }

gs2328pSFlowAgentCollector                                            OBJECT IDENTIFIER ::= { gs2328pSFlowAgent 1 }

gs2328pSFlowAgentReceiverMode OBJECT-TYPE
   SYNTAX      INTEGER { disable(0), enable(1) }
   MAX-ACCESS  read-write
   STATUS      current
   DESCRIPTION
       "default: 0
       0: disable
       1: enable "
   ::= { gs2328pSFlowAgentCollector 1 }


gs2328pLMC                                                   OBJECT IDENTIFIER ::= { gs2328pConfiguration 1500 }

gs2328pLMCOperating OBJECT-TYPE
   SYNTAX      INTEGER { disabled(0), enabled(1), try(2) }
   MAX-ACCESS  read-write
   STATUS      current
   DESCRIPTION
       "0: disabled
        1: enabled
        2: try"
   ::= { gs2328pLMC 1 }

gs2328pLMCConfigViaDhcp OBJECT-TYPE
   SYNTAX      INTEGER { disabled(0), enabled(1) }
   MAX-ACCESS  read-write
   STATUS      current
   DESCRIPTION
       "0: disabled
        1: enabled"
   ::= { gs2328pLMC 2 }

gs2328pLMCDomain OBJECT-TYPE
   SYNTAX      DisplayString(SIZE(0..255))
   MAX-ACCESS  read-write
   STATUS      current
   DESCRIPTION
       "0: disabled
        1: enabled"
   ::= { gs2328pLMC 3 }

gs2328pLMCDhcpClientAutoRenew OBJECT-TYPE
   SYNTAX      INTEGER { disabled(0), enabled(1) }
   MAX-ACCESS  read-write
   STATUS      current
   DESCRIPTION
       "0: disabled
        1: enabled"
   ::= { gs2328pLMC 4 }
   
   
   
   
   
gs2328pLMCZeroTouchSupport OBJECT-TYPE
   SYNTAX      INTEGER { No(0), Yes(1) }
   MAX-ACCESS  read-only
   STATUS      current
   DESCRIPTION
       "0: No
        1: Yes"
   ::= { gs2328pLMC 50 }  
   
gs2328pLMCPairingTokenPresent OBJECT-TYPE
   SYNTAX      INTEGER { No(0), Yes(1) }
   MAX-ACCESS  read-only
   STATUS      current
   DESCRIPTION
       "0: No
        1: Yes"
   ::= { gs2328pLMC 51 }
   
gs2328pLMCClientStatus OBJECT-TYPE
   SYNTAX      DisplayString
   MAX-ACCESS  read-only
   STATUS      current
   DESCRIPTION
           ""
   ::= { gs2328pLMC  52 }
   
   
gs2328pLMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2328pLMC  53 }
   
gs2328pLMCControlStatus OBJECT-TYPE
   SYNTAX      INTEGER {Disabled(2), Operating(4)}
   MAX-ACCESS  read-only
   STATUS      current
   DESCRIPTION
           "2: Disabled
            4: Operating"
   ::= { gs2328pLMC  54 }          
   
gs2328pLMCMonitoringStatus OBJECT-TYPE
   SYNTAX      INTEGER {Disabled(2), Operating(4)}
   MAX-ACCESS  read-only
   STATUS      current
   DESCRIPTION
           "2: Disabled
            4: Operating"
   ::= { gs2328pLMC  55 }
   
gs2328pLMCConfigurationSource OBJECT-TYPE
   SYNTAX      DisplayString
   MAX-ACCESS  read-only
   STATUS      current
   DESCRIPTION
           ""
   ::= { gs2328pLMC  56 }
   
gs2328pLMCConfigModified OBJECT-TYPE
   SYNTAX      INTEGER { No(0), Yes(1) }
   MAX-ACCESS  read-only
   STATUS      current
   DESCRIPTION
       "0: No
        1: Yes"
   ::= { gs2328pLMC 57 }
   
gs2328pLMCDeviceID OBJECT-TYPE
   SYNTAX      DisplayString
   MAX-ACCESS  read-only
   STATUS      current
   DESCRIPTION
           ""
   ::= { gs2328pLMC  58 }
   
gs2328pLMCRoundTripTime OBJECT-TYPE
   SYNTAX      INTEGER
   MAX-ACCESS  read-only
   STATUS      current
   DESCRIPTION
           ""
   ::= { gs2328pLMC  100 }
----------------------------------------------------------------------------------------------------------------------------
gs2328pSecurity                                              OBJECT IDENTIFIER ::= { lancomGS2328P  3 }

gs2328pIPSourceGuard                                         OBJECT IDENTIFIER ::= { gs2328pSecurity 1 }

gs2328pIPSourceGuardConf                                     OBJECT IDENTIFIER ::= { gs2328pIPSourceGuard 1 }

gs2328pIPSourceGuardMode OBJECT-TYPE
   SYNTAX      INTEGER { disable(0), enable(1) }
   MAX-ACCESS  read-write
   STATUS      current
   DESCRIPTION
       " default:  0
        0: disable
        1: enable"
   ::= { gs2328pIPSourceGuardConf 1 }

gs2328pIPSourceGuardPortConfigTable OBJECT-TYPE
   SYNTAX      SEQUENCE OF GS2328PIPSourceGuardPortConfigEntry
   MAX-ACCESS  not-accessible
   STATUS      current
   DESCRIPTION
       " "
   ::= { gs2328pIPSourceGuardConf 2 }

gs2328pIPSourceGuardPortConfigEntry OBJECT-TYPE
   SYNTAX      GS2328PIPSourceGuardPortConfigEntry
   MAX-ACCESS  not-accessible
   STATUS      current
   DESCRIPTION
       ""
   INDEX    { gs2328pIPSourceGuardPortConfigPort  }
   ::= { gs2328pIPSourceGuardPortConfigTable 1 }

GS2328PIPSourceGuardPortConfigEntry ::= SEQUENCE {
   gs2328pIPSourceGuardPortConfigPort               Integer32,
   gs2328pIPSourceGuardPortConfigMode               INTEGER,
   gs2328pIPSourceGuardPortMaxDynamicClients        Integer32
}

gs2328pIPSourceGuardPortConfigPort OBJECT-TYPE
   SYNTAX      Integer32(1..4095)
   MAX-ACCESS  not-accessible
   STATUS      current
   DESCRIPTION
       " "
   ::= { gs2328pIPSourceGuardPortConfigEntry 1 }

gs2328pIPSourceGuardPortConfigMode OBJECT-TYPE
   SYNTAX      INTEGER { disable(0), enable(1) }
   MAX-ACCESS  read-write
   STATUS      current
   DESCRIPTION
       "default: 0
       0:disable
       1:enable "
   ::= { gs2328pIPSourceGuardPortConfigEntry 2 }

gs2328pIPSourceGuardPortMaxDynamicClients OBJECT-TYPE
   SYNTAX      Integer32(0..2|99)
   MAX-ACCESS  read-write
   STATUS      current
   DESCRIPTION
       "default: 99
       0~2: Max Dynamic clients
       99:Unlimited "
   ::= { gs2328pIPSourceGuardPortConfigEntry 3 }


gs2328pIPSourceGuardStatic                                OBJECT IDENTIFIER ::= { gs2328pIPSourceGuard 2 }

gs2328pIPSourceGuardStaticCreate OBJECT-TYPE
   SYNTAX       INTEGER { none(0), create(1) }
   MAX-ACCESS   read-write
   STATUS       current
   DESCRIPTION
       "default: 0
        0 : None  (read only)
        1 : Create a IP Source Guard"
   ::= { gs2328pIPSourceGuardStatic 1 }

gs2328pIPSourceGuardStaticTable OBJECT-TYPE
   SYNTAX      SEQUENCE OF GS2328PIPSourceGuardStaticEntry
   MAX-ACCESS  not-accessible
   STATUS      current
   DESCRIPTION
       " "
   ::= { gs2328pIPSourceGuardStatic 2 }

gs2328pIPSourceGuardStaticEntry OBJECT-TYPE
   SYNTAX      GS2328PIPSourceGuardStaticEntry
   MAX-ACCESS  not-accessible
   STATUS      current
   DESCRIPTION
       ""
   INDEX    { gs2328pIPSourceGuardStaticIndex  }
   ::= { gs2328pIPSourceGuardStaticTable 1 }

GS2328PIPSourceGuardStaticEntry ::= SEQUENCE {
   gs2328pIPSourceGuardStaticIndex         Integer32,
   gs2328pIPSourceGuardStaticPort          Integer32,
   gs2328pIPSourceGuardStaticVLANId        Integer32,
   gs2328pIPSourceGuardStaticIPAddress     IpAddress,
   gs2328pIPSourceGuardStaticMACAddress    MacAddress,
   gs2328pIPSourceGuardStaticRowStatus     INTEGER
}

gs2328pIPSourceGuardStaticIndex OBJECT-TYPE
   SYNTAX      Integer32(1..28)
   MAX-ACCESS  not-accessible
   STATUS      current
   DESCRIPTION
       " "
   ::= { gs2328pIPSourceGuardStaticEntry 1 }

gs2328pIPSourceGuardStaticPort OBJECT-TYPE
   SYNTAX      Integer32(1..4095)
   MAX-ACCESS  read-write
   STATUS      current
   DESCRIPTION
       " Port, range: 1 - port number. "
   ::= { gs2328pIPSourceGuardStaticEntry 2 }

gs2328pIPSourceGuardStaticVLANId OBJECT-TYPE
   SYNTAX      Integer32(1..4094)
   MAX-ACCESS  read-write
   STATUS      current
   DESCRIPTION
       " VLAN ID, range: 1 - 4094. "
   ::= { gs2328pIPSourceGuardStaticEntry 3 }

gs2328pIPSourceGuardStaticIPAddress OBJECT-TYPE
   SYNTAX      IpAddress
   MAX-ACCESS  read-write
   STATUS      current
   DESCRIPTION
       " IP address allowed for doing IP source guard. "
   ::= { gs2328pIPSourceGuardStaticEntry 4 }

gs2328pIPSourceGuardStaticMACAddress OBJECT-TYPE
   SYNTAX      MacAddress
   MAX-ACCESS  read-write
   STATUS      current
   DESCRIPTION
       " Allowed Source MAC address, format 0a 1b 2c 3d 4e 5f "
   ::= { gs2328pIPSourceGuardStaticEntry 5 }

gs2328pIPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2328pIPSourceGuardStaticEntry 6 }

gs2328pIPSourceGuardDynamicTable OBJECT-TYPE
   SYNTAX      SEQUENCE OF GS2328PIPSourceGuardDynamicEntry
   MAX-ACCESS  not-accessible
   STATUS      current
   DESCRIPTION
       " "
   ::= { gs2328pIPSourceGuard 3 }

gs2328pIPSourceGuardDynamicEntry OBJECT-TYPE
   SYNTAX      GS2328PIPSourceGuardDynamicEntry
   MAX-ACCESS  not-accessible
   STATUS      current
   DESCRIPTION
       ""
   INDEX    { gs2328pIPSourceGuardDynamicIndex  }
   ::= { gs2328pIPSourceGuardDynamicTable 1 }

GS2328PIPSourceGuardDynamicEntry ::= SEQUENCE {
   gs2328pIPSourceGuardDynamicIndex          Integer32,
   gs2328pIPSourceGuardDynamicPort           Integer32,
   gs2328pIPSourceGuardDynamicVLANId         Integer32,
   gs2328pIPSourceGuardDynamicIPAddress      IpAddress,
   gs2328pIPSourceGuardDynamicMACAddress     MacAddress
}

gs2328pIPSourceGuardDynamicIndex OBJECT-TYPE
   SYNTAX      Integer32(1..4095)
   MAX-ACCESS  not-accessible
   STATUS      current
   DESCRIPTION
       " "
   ::= { gs2328pIPSourceGuardDynamicEntry 1 }

gs2328pIPSourceGuardDynamicPort OBJECT-TYPE
   SYNTAX      Integer32(1..10)
   MAX-ACCESS  read-only
   STATUS      current
   DESCRIPTION
       " "
   ::= { gs2328pIPSourceGuardDynamicEntry 2 }

gs2328pIPSourceGuardDynamicVLANId OBJECT-TYPE
   SYNTAX      Integer32(1..4094)
   MAX-ACCESS  read-only
   STATUS      current
   DESCRIPTION
       " "
   ::= { gs2328pIPSourceGuardDynamicEntry 3 }

gs2328pIPSourceGuardDynamicIPAddress OBJECT-TYPE
   SYNTAX      IpAddress
   MAX-ACCESS  read-only
   STATUS      current
   DESCRIPTION
       " "
   ::= { gs2328pIPSourceGuardDynamicEntry 4 }

gs2328pIPSourceGuardDynamicMACAddress OBJECT-TYPE
   SYNTAX      MacAddress
   MAX-ACCESS  read-only
   STATUS      current
   DESCRIPTION
       " "
   ::= { gs2328pIPSourceGuardDynamicEntry 5 }

gs2328pARPInspection                                         OBJECT IDENTIFIER ::= { gs2328pSecurity 2 }

gs2328pARPInspectionConf                                     OBJECT IDENTIFIER ::= { gs2328pARPInspection 1 }

gs2328pARPInspectionConfMode OBJECT-TYPE
   SYNTAX      INTEGER { disable(0), enable(1) }
   MAX-ACCESS  read-write
   STATUS      current
   DESCRIPTION
       "default: 0
        0: disable
        1: enable"
   ::= { gs2328pARPInspectionConf 1 }

gs2328pARPInspectionConfTable OBJECT-TYPE
   SYNTAX      SEQUENCE OF GS2328PARPInspectionConfEntry
   MAX-ACCESS  not-accessible
   STATUS      current
   DESCRIPTION
       " "
   ::= { gs2328pARPInspectionConf 2 }

gs2328pARPInspectionConfEntry OBJECT-TYPE
   SYNTAX      GS2328PARPInspectionConfEntry
   MAX-ACCESS  not-accessible
   STATUS      current
   DESCRIPTION
       ""
   INDEX    { gs2328pARPInspectionConfPortIndex  }
   ::= { gs2328pARPInspectionConfTable 1 }

GS2328PARPInspectionConfEntry ::= SEQUENCE {
   gs2328pARPInspectionConfPortIndex	Integer32,
   gs2328pARPInspectionConfPortMode	INTEGER
}

gs2328pARPInspectionConfPortIndex OBJECT-TYPE
   SYNTAX      Integer32(1..4095)
   MAX-ACCESS  not-accessible
   STATUS      current
   DESCRIPTION
       " "
   ::= { gs2328pARPInspectionConfEntry 1 }

gs2328pARPInspectionConfPortMode OBJECT-TYPE
   SYNTAX      INTEGER { disable(0), enable(1) }
   MAX-ACCESS  read-write
   STATUS      current
   DESCRIPTION
       "default: 0
        0: disable
        1: enable"
   ::= { gs2328pARPInspectionConfEntry 2 }


gs2328pARPInspectionStatic                                OBJECT IDENTIFIER ::= { gs2328pARPInspection 2 }

gs2328pARPInspectionStaticCreate OBJECT-TYPE
   SYNTAX      INTEGER { none(0), create(1) }
   MAX-ACCESS  read-write
   STATUS      current
   DESCRIPTION
       "default: 0
        0: none
        1: create"
   ::= { gs2328pARPInspectionStatic 1 }

gs2328pARPInspectionStaticTable OBJECT-TYPE
   SYNTAX      SEQUENCE OF GS2328PARPInspectionStaticEntry
   MAX-ACCESS  not-accessible
   STATUS      current
   DESCRIPTION
       " "
   ::= { gs2328pARPInspectionStatic 2 }

gs2328pARPInspectionStaticEntry OBJECT-TYPE
   SYNTAX      GS2328PARPInspectionStaticEntry
   MAX-ACCESS  not-accessible
   STATUS      current
   DESCRIPTION
       ""
   INDEX    { gs2328pARPInspectionStaticIndex  }
   ::= { gs2328pARPInspectionStaticTable 1 }

GS2328PARPInspectionStaticEntry ::= SEQUENCE {
   gs2328pARPInspectionStaticIndex       Integer32,
   gs2328pARPInspectionStaticPort        Integer32,
   gs2328pARPInspectionStaticVLANId      Integer32,
   gs2328pARPInspectionStaticIPAddress   IpAddress,
   gs2328pARPInspectionStaticMACAddress  MacAddress,
   gs2328pARPInspectionStaticRowStatus   INTEGER
}

gs2328pARPInspectionStaticIndex OBJECT-TYPE
   SYNTAX      Integer32(1..4095)
   MAX-ACCESS  not-accessible
   STATUS      current
   DESCRIPTION
       ""
   ::= { gs2328pARPInspectionStaticEntry 1 }

gs2328pARPInspectionStaticPort OBJECT-TYPE
   SYNTAX      Integer32(1..4095)
   MAX-ACCESS  read-write
   STATUS      current
   DESCRIPTION
       " Port, range: 1 - port number. "
   ::= { gs2328pARPInspectionStaticEntry 2 }

gs2328pARPInspectionStaticVLANId OBJECT-TYPE
   SYNTAX      Integer32(1..4094)
   MAX-ACCESS  read-write
   STATUS      current
   DESCRIPTION
       " VLAN ID, range: 1 - 4094. "
   ::= { gs2328pARPInspectionStaticEntry 3 }

gs2328pARPInspectionStaticIPAddress OBJECT-TYPE
   SYNTAX      IpAddress
   MAX-ACCESS  read-write
   STATUS      current
   DESCRIPTION
       " IP address allowed for doing ARP request. "
   ::= { gs2328pARPInspectionStaticEntry 4 }

gs2328pARPInspectionStaticMACAddress OBJECT-TYPE
   SYNTAX      MacAddress
   MAX-ACCESS  read-write
   STATUS      current
   DESCRIPTION
       " Allowed Source MAC address in ARP request packets, format 0a 1b 2c 3d 4e 5f "
   ::= { gs2328pARPInspectionStaticEntry 5 }

gs2328pARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2328pARPInspectionStaticEntry 6 }

gs2328pARPInspectionDynamicTable OBJECT-TYPE
   SYNTAX      SEQUENCE OF GS2328PARPInspectionDynamicEntry
   MAX-ACCESS  not-accessible
   STATUS      current
   DESCRIPTION
       " "
   ::= { gs2328pARPInspection 3 }

gs2328pARPInspectionDynamicEntry OBJECT-TYPE
   SYNTAX      GS2328PARPInspectionDynamicEntry
   MAX-ACCESS  not-accessible
   STATUS      current
   DESCRIPTION
       ""
   INDEX    { gs2328pARPInspectionDynamicIndex  }
   ::= { gs2328pARPInspectionDynamicTable 1 }

GS2328PARPInspectionDynamicEntry ::= SEQUENCE {
   gs2328pARPInspectionDynamicIndex          Integer32,
   gs2328pARPInspectionDynamicPort           Integer32,
   gs2328pARPInspectionDynamicVLANId         Integer32,
   gs2328pARPInspectionDynamicIPAddress      IpAddress,
   gs2328pARPInspectionDynamicMACAddress     MacAddress
}

gs2328pARPInspectionDynamicIndex OBJECT-TYPE
   SYNTAX      Integer32(1..4095)
   MAX-ACCESS  not-accessible
   STATUS      current
   DESCRIPTION
       " "
   ::= { gs2328pARPInspectionDynamicEntry 1 }

gs2328pARPInspectionDynamicPort OBJECT-TYPE
   SYNTAX      Integer32(1..4095)
   MAX-ACCESS  read-only
   STATUS      current
   DESCRIPTION
       ""
   ::= { gs2328pARPInspectionDynamicEntry 2 }

gs2328pARPInspectionDynamicVLANId OBJECT-TYPE
   SYNTAX      Integer32(1..4094)
   MAX-ACCESS  read-only
   STATUS      current
   DESCRIPTION
       ""
   ::= { gs2328pARPInspectionDynamicEntry 3 }

gs2328pARPInspectionDynamicIPAddress OBJECT-TYPE
   SYNTAX      IpAddress
   MAX-ACCESS  read-only
   STATUS      current
   DESCRIPTION
       ""
   ::= { gs2328pARPInspectionDynamicEntry 4 }

gs2328pARPInspectionDynamicMACAddress OBJECT-TYPE
   SYNTAX      MacAddress
   MAX-ACCESS  read-only
   STATUS      current
   DESCRIPTION
       ""
   ::= { gs2328pARPInspectionDynamicEntry 5 }

gs2328pARPStaticGatewayCtrl	                                OBJECT IDENTIFIER ::= { gs2328pARPInspection 6 }

gs2328pARPStaticGatewayCtrlSystemConf                                      OBJECT IDENTIFIER ::= { gs2328pARPStaticGatewayCtrl 1 }

gs2328pARPStaticGatewayCtrlMode OBJECT-TYPE
   SYNTAX      INTEGER { disable(0), enable(1) }
   MAX-ACCESS  read-write
   STATUS      current
   DESCRIPTION
       "default: 0
       0: disable
       1: enable "
   ::= { gs2328pARPStaticGatewayCtrlSystemConf 1 }

gs2328pARPStaticGatewayCtrlCreate OBJECT-TYPE
   SYNTAX      INTEGER { none(0), create(1) }
   MAX-ACCESS  read-write
   STATUS      current
   DESCRIPTION
       "default: 0
        0: none
        1: create"
   ::= { gs2328pARPStaticGatewayCtrl 2 }

gs2328pARPStaticGatewayCtrlTable OBJECT-TYPE
   SYNTAX      SEQUENCE OF GS2328PARPStaticGatewayCtrlEntry
   MAX-ACCESS  not-accessible
   STATUS      current
   DESCRIPTION
       " "
   ::= { gs2328pARPStaticGatewayCtrl 3 }

gs2328pARPStaticGatewayCtrlEntry OBJECT-TYPE
   SYNTAX      GS2328PARPStaticGatewayCtrlEntry
   MAX-ACCESS  not-accessible
   STATUS      current
   DESCRIPTION
       ""
   INDEX    { gs2328pARPStaticGatewayCtrlIndex  }
   ::= { gs2328pARPStaticGatewayCtrlTable 1 }

GS2328PARPStaticGatewayCtrlEntry ::= SEQUENCE {
   gs2328pARPStaticGatewayCtrlIndex       Integer32,
   gs2328pARPStaticGatewayCtrlIPAddress   IpAddress,
   gs2328pARPStaticGatewayCtrlMACAddress  MacAddress,
   gs2328pARPStaticGatewayCtrlPort        Integer32,
   gs2328pARPStaticGatewayCtrlAction      INTEGER,
   gs2328pARPStaticGatewayCtrlState       DisplayString,
   gs2328pARPStaticGatewayCtrlReOpen      INTEGER,
   gs2328pARPStaticGatewayCtrlRowStatus   INTEGER
}

gs2328pARPStaticGatewayCtrlIndex OBJECT-TYPE
   SYNTAX      Integer32(1..4)
   MAX-ACCESS  not-accessible
   STATUS      current
   DESCRIPTION
       ""
   ::= { gs2328pARPStaticGatewayCtrlEntry 1 }

gs2328pARPStaticGatewayCtrlIPAddress OBJECT-TYPE
   SYNTAX      IpAddress
   MAX-ACCESS  read-write
   STATUS      current
   DESCRIPTION
       " Source IP address. "
   ::= { gs2328pARPStaticGatewayCtrlEntry 2 }

gs2328pARPStaticGatewayCtrlMACAddress OBJECT-TYPE
   SYNTAX      MacAddress
   MAX-ACCESS  read-write
   STATUS      current
   DESCRIPTION
       " Source MAC address , format 0a 1b 2c 3d 4e 5f "
   ::= { gs2328pARPStaticGatewayCtrlEntry 3 }

gs2328pARPStaticGatewayCtrlPort OBJECT-TYPE
   SYNTAX      Integer32(1..4095)
   MAX-ACCESS  read-write
   STATUS      current
   DESCRIPTION
       " Port, range: 1 - port number. "
   ::= { gs2328pARPStaticGatewayCtrlEntry 4 }

gs2328pARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2328pARPStaticGatewayCtrlEntry 5 }

gs2328pARPStaticGatewayCtrlState OBJECT-TYPE
   SYNTAX      DisplayString
   MAX-ACCESS  read-only
   STATUS      current
   DESCRIPTION
       ""
   ::= { gs2328pARPStaticGatewayCtrlEntry 6 }

gs2328pARPStaticGatewayCtrlReOpen OBJECT-TYPE
   SYNTAX      INTEGER { none(0), reopen(1) }
   MAX-ACCESS  read-write
   STATUS      current
   DESCRIPTION
       "default: 0
       0: none
       1: reopen"
   ::= { gs2328pARPStaticGatewayCtrlEntry 7 }  
   
gs2328pARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2328pARPStaticGatewayCtrlEntry 8 }

gs2328pARPSpoofingPrevention	                                OBJECT IDENTIFIER ::= { gs2328pARPInspection 7 }

gs2328pARPSpoofingPreventionSystemConf                                      OBJECT IDENTIFIER ::= { gs2328pARPSpoofingPrevention 1 }

gs2328pARPSpoofingPreventionMode OBJECT-TYPE
   SYNTAX      INTEGER { disable(0), enable(1) }
   MAX-ACCESS  read-write
   STATUS      current
   DESCRIPTION
       "default: 0
       0: disable
       1: enable "
   ::= { gs2328pARPSpoofingPreventionSystemConf 1 }

gs2328pARPSpoofingPreventionTable OBJECT-TYPE
   SYNTAX      SEQUENCE OF GS2328PARPSpoofingPreventionEntry
   MAX-ACCESS  not-accessible
   STATUS      current
   DESCRIPTION
       " "
   ::= { gs2328pARPSpoofingPrevention 2 }

gs2328pARPSpoofingPreventionEntry OBJECT-TYPE
   SYNTAX      GS2328PARPSpoofingPreventionEntry
   MAX-ACCESS  not-accessible
   STATUS      current
   DESCRIPTION
       ""
   INDEX    { gs2328pARPSpoofingPreventionPort  }
   ::= { gs2328pARPSpoofingPreventionTable 1 }

GS2328PARPSpoofingPreventionEntry ::= SEQUENCE {
   gs2328pARPSpoofingPreventionPort           Integer32,
   gs2328pARPSpoofingPreventionPortMode       INTEGER,
   gs2328pARPSpoofingPreventionPortLimit      Integer32,
   gs2328pARPSpoofingPreventionPortAction     INTEGER,
   gs2328pARPSpoofingPreventionPortState      DisplayString,
   gs2328pARPSpoofingPreventionPortReOpen     INTEGER
}

gs2328pARPSpoofingPreventionPort OBJECT-TYPE
   SYNTAX      Integer32(1..4095)
   MAX-ACCESS  not-accessible
   STATUS      current
   DESCRIPTION
       " "
   ::= { gs2328pARPSpoofingPreventionEntry 1 }

gs2328pARPSpoofingPreventionPortMode OBJECT-TYPE
   SYNTAX      INTEGER { disable(0), enable(1) }
   MAX-ACCESS  read-write
   STATUS      current
   DESCRIPTION
       "default: 0
       0: disable
       1: enable"
   ::= { gs2328pARPSpoofingPreventionEntry 2 }

gs2328pARPSpoofingPreventionPortLimit OBJECT-TYPE
   SYNTAX      Integer32(1..100)
   MAX-ACCESS  read-write
   STATUS      current
   DESCRIPTION
       "default: 1, range: 1-100"
   ::= { gs2328pARPSpoofingPreventionEntry 3 }

gs2328pARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2328pARPSpoofingPreventionEntry 4 }

gs2328pARPSpoofingPreventionPortState OBJECT-TYPE
   SYNTAX      DisplayString
   MAX-ACCESS  read-only
   STATUS      current
   DESCRIPTION
       ""
   ::= { gs2328pARPSpoofingPreventionEntry 5 }

gs2328pARPSpoofingPreventionPortReOpen OBJECT-TYPE
   SYNTAX      INTEGER { none(0), reopen(1) }
   MAX-ACCESS  read-write
   STATUS      current
   DESCRIPTION
       "default: 0
       0: none
       1: reopen"
   ::= { gs2328pARPSpoofingPreventionEntry 6 }  

gs2328pARPIPDoSPrevention	                                OBJECT IDENTIFIER ::= { gs2328pARPInspection 8 }

gs2328pARPIPDoSPreventionTCPMode OBJECT-TYPE
   SYNTAX      INTEGER { disable(0), enable(1) }
   MAX-ACCESS  read-write
   STATUS      current
   DESCRIPTION
       "default: 0
       0: disable
       1: enable "
   ::= { gs2328pARPIPDoSPrevention 1 }

gs2328pARPIPDoSPreventionUDPMode OBJECT-TYPE
   SYNTAX      INTEGER { disable(0), enable(1) }
   MAX-ACCESS  read-write
   STATUS      current
   DESCRIPTION
       "default: 0
       0: disable
       1: enable "
   ::= { gs2328pARPIPDoSPrevention 2 }
   
gs2328pARPIPDoSPreventionICMPMode OBJECT-TYPE
   SYNTAX      INTEGER { disable(0), enable(1) }
   MAX-ACCESS  read-write
   STATUS      current
   DESCRIPTION
       "default: 0
       0: disable
       1: enable "
   ::= { gs2328pARPIPDoSPrevention 3 }   

gs2328pARPIPDoSPreventionServerPort1 OBJECT-TYPE
   SYNTAX      Integer32(0..4094)
   MAX-ACCESS  read-write
   STATUS      current
   DESCRIPTION
       " Port, range: 0 - port number. 0: none. "
   ::= { gs2328pARPIPDoSPrevention 4 }  

gs2328pARPIPDoSPreventionServerPort2 OBJECT-TYPE
   SYNTAX      Integer32(0..4094)
   MAX-ACCESS  read-write
   STATUS      current
   DESCRIPTION
       " Port, range: 0 - port number. 0: none. "
   ::= { gs2328pARPIPDoSPrevention 5 }  
   
gs2328pARPIPDoSPreventionServerPort3 OBJECT-TYPE
   SYNTAX      Integer32(0..4094)
   MAX-ACCESS  read-write
   STATUS      current
   DESCRIPTION
       " Port, range: 0 - port number. 0: none. "
   ::= { gs2328pARPIPDoSPrevention 6 }  
   
gs2328pARPIPDoSPreventionServerPort4 OBJECT-TYPE
   SYNTAX      Integer32(0..4094)
   MAX-ACCESS  read-write
   STATUS      current
   DESCRIPTION
       " Port, range: 0 - port number. 0: none. "
   ::= { gs2328pARPIPDoSPrevention 7 }        

gs2328pDHCPSnooping                                          OBJECT IDENTIFIER ::= { gs2328pSecurity 3 }

gs2328pDHCPSnoopingConf                                          OBJECT IDENTIFIER ::= { gs2328pDHCPSnooping 1 }

gs2328pDHCPSnoopingMode OBJECT-TYPE
   SYNTAX      INTEGER { disable(0), enable(1) }
   MAX-ACCESS  read-write
   STATUS      current
   DESCRIPTION
       "default: 0
       0: disable
       1: enable"
   ::= { gs2328pDHCPSnoopingConf 1 }

gs2328pDHCPSnoopingPortModeConfigurationTable OBJECT-TYPE
   SYNTAX      SEQUENCE OF GS2328PDHCPSnoopingPortModeConfigurationEntry
   MAX-ACCESS  not-accessible
   STATUS      current
   DESCRIPTION
       " "
   ::= { gs2328pDHCPSnoopingConf 2 }

gs2328pDHCPSnoopingPortModeConfigurationEntry OBJECT-TYPE
   SYNTAX      GS2328PDHCPSnoopingPortModeConfigurationEntry
   MAX-ACCESS  not-accessible
   STATUS      current
   DESCRIPTION
       ""
   INDEX    { gs2328pDHCPSnoopingPortModeConfigurationPort  }
   ::= { gs2328pDHCPSnoopingPortModeConfigurationTable 1 }
   
GS2328PDHCPSnoopingPortModeConfigurationEntry ::= SEQUENCE {
   gs2328pDHCPSnoopingPortModeConfigurationPort	Integer32,
   gs2328pDHCPSnoopingPortModeConfigurationMode	INTEGER
}

gs2328pDHCPSnoopingPortModeConfigurationPort OBJECT-TYPE
   SYNTAX      Integer32(1..4095)
   MAX-ACCESS  not-accessible
   STATUS      current
   DESCRIPTION
       " "
   ::= { gs2328pDHCPSnoopingPortModeConfigurationEntry 1 }

gs2328pDHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2328pDHCPSnoopingPortModeConfigurationEntry 2 }

gs2328pDHCPSnoopingStatisticsTable OBJECT-TYPE
   SYNTAX      SEQUENCE OF GS2328PDHCPSnoopingStatisticsEntry
   MAX-ACCESS  not-accessible
   STATUS      current
   DESCRIPTION
       " "
   ::= { gs2328pDHCPSnooping 2 }

gs2328pDHCPSnoopingStatisticsEntry OBJECT-TYPE
   SYNTAX      GS2328PDHCPSnoopingStatisticsEntry
   MAX-ACCESS  not-accessible
   STATUS      current
   DESCRIPTION
       ""
   INDEX    { gs2328pDHCPSnoopingStatisticsPort  }
   ::= { gs2328pDHCPSnoopingStatisticsTable 1 }

GS2328PDHCPSnoopingStatisticsEntry ::= SEQUENCE {
   gs2328pDHCPSnoopingStatisticsPort         Integer32,
   gs2328pDHCPSnoopingStatisticsClear        INTEGER,
   gs2328pDHCPSnoopingRxDiscover             Counter32,
   gs2328pDHCPSnoopingRxOffer                Counter32,
   gs2328pDHCPSnoopingRxRequest              Counter32,
   gs2328pDHCPSnoopingRxDecline              Counter32,
   gs2328pDHCPSnoopingRxACK                  Counter32,
   gs2328pDHCPSnoopingRxNAK                  Counter32,
   gs2328pDHCPSnoopingRxRelease              Counter32,
   gs2328pDHCPSnoopingRxInform               Counter32,
   gs2328pDHCPSnoopingRxLeaseQuery           Counter32,
   gs2328pDHCPSnoopingRxLeaseUnassigned      Counter32,
   gs2328pDHCPSnoopingRxLeaseUnknown         Counter32,
   gs2328pDHCPSnoopingRxLeaseActive          Counter32,
   gs2328pDHCPSnoopingTxDiscover             Counter32,
   gs2328pDHCPSnoopingTxOffer                Counter32,
   gs2328pDHCPSnoopingTxRequest              Counter32,
   gs2328pDHCPSnoopingTxDecline              Counter32,
   gs2328pDHCPSnoopingTxACK                  Counter32,
   gs2328pDHCPSnoopingTxNAK                  Counter32,
   gs2328pDHCPSnoopingTxRelease              Counter32,
   gs2328pDHCPSnoopingTxInform               Counter32,
   gs2328pDHCPSnoopingTxLeaseQuery           Counter32,
   gs2328pDHCPSnoopingTxLeaseUnassigned      Counter32,
   gs2328pDHCPSnoopingTxLeaseUnknown         Counter32,
   gs2328pDHCPSnoopingTxLeaseActive          Counter32
}

gs2328pDHCPSnoopingStatisticsPort OBJECT-TYPE
   SYNTAX      Integer32(1..4095)
   MAX-ACCESS  not-accessible
   STATUS      current
   DESCRIPTION
       " "
   ::= { gs2328pDHCPSnoopingStatisticsEntry 1 }

gs2328pDHCPSnoopingStatisticsClear OBJECT-TYPE
   SYNTAX      INTEGER { none(0), clear(1) }
   MAX-ACCESS  read-write
   STATUS      current
   DESCRIPTION
       "default: 0
       0: none
       1: clear"
   ::= { gs2328pDHCPSnoopingStatisticsEntry 2 }
   
gs2328pDHCPSnoopingRxDiscover OBJECT-TYPE
   SYNTAX      Counter32
   MAX-ACCESS  read-only
   STATUS      current
   DESCRIPTION
       " "
   ::= { gs2328pDHCPSnoopingStatisticsEntry 3 }

gs2328pDHCPSnoopingRxOffer OBJECT-TYPE
   SYNTAX      Counter32
   MAX-ACCESS  read-only
   STATUS      current
   DESCRIPTION
       " "
   ::= { gs2328pDHCPSnoopingStatisticsEntry 4 }

gs2328pDHCPSnoopingRxRequest OBJECT-TYPE
   SYNTAX      Counter32
   MAX-ACCESS  read-only
   STATUS      current
   DESCRIPTION
       " "
   ::= { gs2328pDHCPSnoopingStatisticsEntry 5 }

gs2328pDHCPSnoopingRxDecline OBJECT-TYPE
   SYNTAX      Counter32
   MAX-ACCESS  read-only
   STATUS      current
   DESCRIPTION
       " "
   ::= { gs2328pDHCPSnoopingStatisticsEntry 6 }

gs2328pDHCPSnoopingRxACK OBJECT-TYPE
   SYNTAX      Counter32
   MAX-ACCESS  read-only
   STATUS      current
   DESCRIPTION
       " "
   ::= { gs2328pDHCPSnoopingStatisticsEntry 7 }

gs2328pDHCPSnoopingRxNAK OBJECT-TYPE
   SYNTAX      Counter32
   MAX-ACCESS  read-only
   STATUS      current
   DESCRIPTION
       " "
   ::= { gs2328pDHCPSnoopingStatisticsEntry 8 }   

gs2328pDHCPSnoopingRxRelease OBJECT-TYPE
   SYNTAX      Counter32
   MAX-ACCESS  read-only
   STATUS      current
   DESCRIPTION
       " "
   ::= { gs2328pDHCPSnoopingStatisticsEntry 9 }

gs2328pDHCPSnoopingRxInform OBJECT-TYPE
   SYNTAX      Counter32
   MAX-ACCESS  read-only
   STATUS      current
   DESCRIPTION
       " "
   ::= { gs2328pDHCPSnoopingStatisticsEntry 10 }

gs2328pDHCPSnoopingRxLeaseQuery OBJECT-TYPE
   SYNTAX      Counter32
   MAX-ACCESS  read-only
   STATUS      current
   DESCRIPTION
       " "
   ::= { gs2328pDHCPSnoopingStatisticsEntry 11 }

gs2328pDHCPSnoopingRxLeaseUnassigned OBJECT-TYPE
   SYNTAX      Counter32
   MAX-ACCESS  read-only
   STATUS      current
   DESCRIPTION
       " "
   ::= { gs2328pDHCPSnoopingStatisticsEntry 12 }

gs2328pDHCPSnoopingRxLeaseUnknown OBJECT-TYPE
   SYNTAX      Counter32
   MAX-ACCESS  read-only
   STATUS      current
   DESCRIPTION
       " "
   ::= { gs2328pDHCPSnoopingStatisticsEntry 13 }

gs2328pDHCPSnoopingRxLeaseActive OBJECT-TYPE
   SYNTAX      Counter32
   MAX-ACCESS  read-only
   STATUS      current
   DESCRIPTION
       " "
   ::= { gs2328pDHCPSnoopingStatisticsEntry 14 }

gs2328pDHCPSnoopingTxDiscover OBJECT-TYPE
   SYNTAX      Counter32
   MAX-ACCESS  read-only
   STATUS      current
   DESCRIPTION
       " "
   ::= { gs2328pDHCPSnoopingStatisticsEntry 15 }

gs2328pDHCPSnoopingTxOffer OBJECT-TYPE
   SYNTAX      Counter32
   MAX-ACCESS  read-only
   STATUS      current
   DESCRIPTION
       " "
   ::= { gs2328pDHCPSnoopingStatisticsEntry 16 }

gs2328pDHCPSnoopingTxRequest OBJECT-TYPE
   SYNTAX      Counter32
   MAX-ACCESS  read-only
   STATUS      current
   DESCRIPTION
       " "
   ::= { gs2328pDHCPSnoopingStatisticsEntry 17 }

gs2328pDHCPSnoopingTxDecline OBJECT-TYPE
   SYNTAX      Counter32
   MAX-ACCESS  read-only
   STATUS      current
   DESCRIPTION
       " "
   ::= { gs2328pDHCPSnoopingStatisticsEntry 18 }

gs2328pDHCPSnoopingTxACK OBJECT-TYPE
   SYNTAX      Counter32
   MAX-ACCESS  read-only
   STATUS      current
   DESCRIPTION
       " "
   ::= { gs2328pDHCPSnoopingStatisticsEntry 19 }

gs2328pDHCPSnoopingTxNAK OBJECT-TYPE
   SYNTAX      Counter32
   MAX-ACCESS  read-only
   STATUS      current
   DESCRIPTION
       " "
   ::= { gs2328pDHCPSnoopingStatisticsEntry 20 }   

gs2328pDHCPSnoopingTxRelease OBJECT-TYPE
   SYNTAX      Counter32
   MAX-ACCESS  read-only
   STATUS      current
   DESCRIPTION
       " "
   ::= { gs2328pDHCPSnoopingStatisticsEntry 21 }

gs2328pDHCPSnoopingTxInform OBJECT-TYPE
   SYNTAX      Counter32
   MAX-ACCESS  read-only
   STATUS      current
   DESCRIPTION
       " "
   ::= { gs2328pDHCPSnoopingStatisticsEntry 22 }

gs2328pDHCPSnoopingTxLeaseQuery OBJECT-TYPE
   SYNTAX      Counter32
   MAX-ACCESS  read-only
   STATUS      current
   DESCRIPTION
       " "
   ::= { gs2328pDHCPSnoopingStatisticsEntry 23 }

gs2328pDHCPSnoopingTxLeaseUnassigned OBJECT-TYPE
   SYNTAX      Counter32
   MAX-ACCESS  read-only
   STATUS      current
   DESCRIPTION
       " "
   ::= { gs2328pDHCPSnoopingStatisticsEntry 24 }

gs2328pDHCPSnoopingTxLeaseUnknown OBJECT-TYPE
   SYNTAX      Counter32
   MAX-ACCESS  read-only
   STATUS      current
   DESCRIPTION
       " "
   ::= { gs2328pDHCPSnoopingStatisticsEntry 25 }

gs2328pDHCPSnoopingTxLeaseActive OBJECT-TYPE
   SYNTAX      Counter32
   MAX-ACCESS  read-only
   STATUS      current
   DESCRIPTION
       " "
   ::= { gs2328pDHCPSnoopingStatisticsEntry 26 }


gs2328pDHCPRelay                                             OBJECT IDENTIFIER ::= { gs2328pSecurity 4 }

gs2328pDHCPRelayConfiguration                                         OBJECT IDENTIFIER ::= { gs2328pDHCPRelay 1 }

gs2328pDHCPRelayMode OBJECT-TYPE
   SYNTAX      INTEGER { disable(0), enable(1) }
   MAX-ACCESS  read-write
   STATUS      current
   DESCRIPTION
       "default: 0
       0: disable
       1: enable 
       We need at least one server"
   ::= { gs2328pDHCPRelayConfiguration 1 }

gs2328pDHCPRelayServer OBJECT-TYPE
   SYNTAX      IpAddress
   MAX-ACCESS  read-write
   STATUS      current
   DESCRIPTION
       " "
   ::= { gs2328pDHCPRelayConfiguration 2 }

gs2328pDHCPRelayInformationMode OBJECT-TYPE
   SYNTAX      INTEGER { disable(0), enable(1) }
   MAX-ACCESS  read-write
   STATUS      current
   DESCRIPTION
       "default: 0
       0: disable
       1: enable "
   ::= { gs2328pDHCPRelayConfiguration 3 }

gs2328pDHCPRelayInformationPolicy OBJECT-TYPE
   SYNTAX      INTEGER { replace(0), keep(1), drop(2) }
   MAX-ACCESS  read-write
   STATUS      current
   DESCRIPTION
       "default: 0
       0: replace
       1: keep
       2: drop "
   ::= { gs2328pDHCPRelayConfiguration 4 }

gs2328pDHCPRelayInformationCustom OBJECT-TYPE
   SYNTAX      DisplayString(SIZE(0..32))
   MAX-ACCESS  read-write
   STATUS      current
   DESCRIPTION
       "DHCP Option 82 Circuit ID custom information"
   ::= { gs2328pDHCPRelayConfiguration 1500 }

gs2328pDHCPRelayConfigurationGateways                                          OBJECT IDENTIFIER ::= { gs2328pDHCPRelayConfiguration 5 }

gs2328pDHCPRelayConfigurationGatewaysCreate OBJECT-TYPE
   SYNTAX       INTEGER { none(0), create(1) }
   MAX-ACCESS   read-write
   STATUS       current
   DESCRIPTION
       "default: 0
        0 : None  (read only)
        1 : Create entry"
   ::= { gs2328pDHCPRelayConfigurationGateways 1 }

gs2328pDHCPRelayConfigurationGatewaysTable OBJECT-TYPE
   SYNTAX      SEQUENCE OF Gs2328pDHCPRelayConfigurationGatewaysEntry
   MAX-ACCESS  not-accessible
   STATUS      current
   DESCRIPTION
       " Create DHCP Relay Gateway IP address entry."
   ::= { gs2328pDHCPRelayConfigurationGateways 2 }

gs2328pDHCPRelayConfigurationGatewaysEntry OBJECT-TYPE
   SYNTAX      Gs2328pDHCPRelayConfigurationGatewaysEntry
   MAX-ACCESS  not-accessible
   STATUS      current
   DESCRIPTION
       ""
   INDEX    { gs2328pDHCPRelayConfigurationGatewaysIndex  }
   ::= { gs2328pDHCPRelayConfigurationGatewaysTable 1 }

Gs2328pDHCPRelayConfigurationGatewaysEntry ::= SEQUENCE {
   gs2328pDHCPRelayConfigurationGatewaysIndex           Integer32,
   gs2328pDHCPRelayConfigurationGatewaysVLANId          Integer32,
   gs2328pDHCPRelayConfigurationGatewaysIP              IpAddress,
   gs2328pDHCPRelayConfigurationGatewaysRowStatus       INTEGER
}

gs2328pDHCPRelayConfigurationGatewaysIndex OBJECT-TYPE
   SYNTAX      Integer32(1..6)
   MAX-ACCESS  not-accessible
   STATUS      current
   DESCRIPTION
       " "
   ::= { gs2328pDHCPRelayConfigurationGatewaysEntry 1 }

gs2328pDHCPRelayConfigurationGatewaysVLANId OBJECT-TYPE
   SYNTAX      Integer32(1..4094)
   MAX-ACCESS  read-write
   STATUS      current
   DESCRIPTION
       " VLAN ID "
   ::= { gs2328pDHCPRelayConfigurationGatewaysEntry 2 }

gs2328pDHCPRelayConfigurationGatewaysIP OBJECT-TYPE
   SYNTAX      IpAddress
   MAX-ACCESS  read-write
   STATUS      current
   DESCRIPTION
       "DHCP GIADDR address."
   ::= { gs2328pDHCPRelayConfigurationGatewaysEntry 3 }
   
gs2328pDHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2328pDHCPRelayConfigurationGatewaysEntry 4 }

gs2328pDHCPRelayStatistics                                   OBJECT IDENTIFIER ::= { gs2328pDHCPRelay 2 }

gs2328pDHCPRelayServerStatistics                                   OBJECT IDENTIFIER ::= { gs2328pDHCPRelayStatistics 1 }

gs2328pServerStatTransmitToServer OBJECT-TYPE
   SYNTAX      Counter32
   MAX-ACCESS  read-only
   STATUS      current
   DESCRIPTION
       " "
   ::= { gs2328pDHCPRelayServerStatistics 1 }

gs2328pServerStatTransmitError OBJECT-TYPE
   SYNTAX      Counter32
   MAX-ACCESS  read-only
   STATUS      current
   DESCRIPTION
       " "
   ::= { gs2328pDHCPRelayServerStatistics 2 }

gs2328pServerStatReceiveFromServer OBJECT-TYPE
   SYNTAX      Counter32
   MAX-ACCESS  read-only
   STATUS      current
   DESCRIPTION
       " "
   ::= { gs2328pDHCPRelayServerStatistics 3 }

gs2328pServerStatReceiveMissingAgentOption OBJECT-TYPE
   SYNTAX      Counter32
   MAX-ACCESS  read-only
   STATUS      current
   DESCRIPTION
       " "
   ::= { gs2328pDHCPRelayServerStatistics 4 }

gs2328pServerStatReceiveMissingCircuitID OBJECT-TYPE
   SYNTAX      Counter32
   MAX-ACCESS  read-only
   STATUS      current
   DESCRIPTION
       " "
   ::= { gs2328pDHCPRelayServerStatistics 5 }

gs2328pServerStatReceiveMissingRemoteID OBJECT-TYPE
   SYNTAX      Counter32
   MAX-ACCESS  read-only
   STATUS      current
   DESCRIPTION
       " "
   ::= { gs2328pDHCPRelayServerStatistics 6 }

gs2328pServerStatReceiveBadCircuitID OBJECT-TYPE
   SYNTAX      Counter32
   MAX-ACCESS  read-only
   STATUS      current
   DESCRIPTION
       " "
   ::= { gs2328pDHCPRelayServerStatistics 7 }

gs2328pServerStatReceiveBadRemoteID OBJECT-TYPE
   SYNTAX      Counter32
   MAX-ACCESS  read-only
   STATUS      current
   DESCRIPTION
       " "
   ::= { gs2328pDHCPRelayServerStatistics 8 }

gs2328pDHCPRelayClientStatistics                                   OBJECT IDENTIFIER ::= { gs2328pDHCPRelayStatistics 2 }

gs2328pClientStatTransmitToClient OBJECT-TYPE
   SYNTAX      Counter32
   MAX-ACCESS  read-only
   STATUS      current
   DESCRIPTION
       " "
   ::= { gs2328pDHCPRelayClientStatistics 1 }

gs2328pClientStatTransmitError OBJECT-TYPE
   SYNTAX      Counter32
   MAX-ACCESS  read-only
   STATUS      current
   DESCRIPTION
       " "
   ::= { gs2328pDHCPRelayClientStatistics 2 }

gs2328pClientStatReceivefromClient OBJECT-TYPE
   SYNTAX      Counter32
   MAX-ACCESS  read-only
   STATUS      current
   DESCRIPTION
       " "
   ::= { gs2328pDHCPRelayClientStatistics 3 }

gs2328pClientStatReceiveAgentOption OBJECT-TYPE
   SYNTAX      Counter32
   MAX-ACCESS  read-only
   STATUS      current
   DESCRIPTION
       " "
   ::= { gs2328pDHCPRelayClientStatistics 4 }

gs2328pClientStatReplaceAgentOption OBJECT-TYPE
   SYNTAX      Counter32
   MAX-ACCESS  read-only
   STATUS      current
   DESCRIPTION
       " "
   ::= { gs2328pDHCPRelayClientStatistics 5 }

gs2328pClientStatKeepAgentOption OBJECT-TYPE
   SYNTAX      Counter32
   MAX-ACCESS  read-only
   STATUS      current
   DESCRIPTION
       " "
   ::= { gs2328pDHCPRelayClientStatistics 6 }

gs2328pClientStatDropAgentOption OBJECT-TYPE
   SYNTAX      Counter32
   MAX-ACCESS  read-only
   STATUS      current
   DESCRIPTION
       " "
   ::= { gs2328pDHCPRelayClientStatistics 7 }

gs2328pPortSecurity                                          OBJECT IDENTIFIER ::= { gs2328pSecurity 5 }

gs2328pPortSecLimitCtrl                                      OBJECT IDENTIFIER ::= { gs2328pPortSecurity 1 }

gs2328pPortSecLimitCtrlSystemConf                                      OBJECT IDENTIFIER ::= { gs2328pPortSecLimitCtrl 1 }

gs2328pPortSecurityMode OBJECT-TYPE
   SYNTAX      INTEGER { disable(0), enable(1) }
   MAX-ACCESS  read-write
   STATUS      current
   DESCRIPTION
       "default: 0
       0: disable
       1: enable "
   ::= { gs2328pPortSecLimitCtrlSystemConf 1 }

gs2328pPortSecurityAging OBJECT-TYPE
   SYNTAX      INTEGER { disable(0), enable(1) }
   MAX-ACCESS  read-write
   STATUS      current
   DESCRIPTION
       "default: 0
       0: disable
       1: enable "
   ::= { gs2328pPortSecLimitCtrlSystemConf 2 }

gs2328pPortSecurityAgingPeriod OBJECT-TYPE
   SYNTAX      INTEGER(10..10000000)
   MAX-ACCESS  read-write
   STATUS      current
   DESCRIPTION
       "default: 3600, range: 10-10000000 "
   ::= { gs2328pPortSecLimitCtrlSystemConf 3 }

gs2328pPortSecLimitCtrlTable OBJECT-TYPE
   SYNTAX      SEQUENCE OF GS2328PPortSecLimitCtrlEntry
   MAX-ACCESS  not-accessible
   STATUS      current
   DESCRIPTION
       " "
   ::= { gs2328pPortSecLimitCtrl 2 }

gs2328pPortSecLimitCtrlEntry OBJECT-TYPE
   SYNTAX      GS2328PPortSecLimitCtrlEntry
   MAX-ACCESS  not-accessible
   STATUS      current
   DESCRIPTION
       ""
   INDEX    { gs2328pPortSecLimitCtrlPort  }
   ::= { gs2328pPortSecLimitCtrlTable 1 }

GS2328PPortSecLimitCtrlEntry ::= SEQUENCE {
   gs2328pPortSecLimitCtrlPort           Integer32,
   gs2328pPortSecLimitCtrlPortMode       INTEGER,
   gs2328pPortSecLimitCtrlPortLimit      Integer32,
   gs2328pPortSecLimitCtrlPortAction     INTEGER,
   gs2328pPortSecLimitCtrlPortState      DisplayString,
   gs2328pPortSecLimitCtrlPortReOpen     INTEGER
}

gs2328pPortSecLimitCtrlPort OBJECT-TYPE
   SYNTAX      Integer32(1..4095)
   MAX-ACCESS  not-accessible
   STATUS      current
   DESCRIPTION
       " "
   ::= { gs2328pPortSecLimitCtrlEntry 1 }

gs2328pPortSecLimitCtrlPortMode OBJECT-TYPE
   SYNTAX      INTEGER { disable(0), enable(1) }
   MAX-ACCESS  read-write
   STATUS      current
   DESCRIPTION
       "default: 0
       0: disable
       1: enable"
   ::= { gs2328pPortSecLimitCtrlEntry 2 }

gs2328pPortSecLimitCtrlPortLimit OBJECT-TYPE
   SYNTAX      Integer32(1..1024)
   MAX-ACCESS  read-write
   STATUS      current
   DESCRIPTION
       "default: 4, range: 1-1024"
   ::= { gs2328pPortSecLimitCtrlEntry 3 }

gs2328pPortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2328pPortSecLimitCtrlEntry 4 }

gs2328pPortSecLimitCtrlPortState OBJECT-TYPE
   SYNTAX      DisplayString
   MAX-ACCESS  read-only
   STATUS      current
   DESCRIPTION
       ""
   ::= { gs2328pPortSecLimitCtrlEntry 5 }

gs2328pPortSecLimitCtrlPortReOpen OBJECT-TYPE
   SYNTAX      INTEGER { none(0), reopen(1) }
   MAX-ACCESS  read-write
   STATUS      current
   DESCRIPTION
       "default: 0
       0: none
       1: reopen"
   ::= { gs2328pPortSecLimitCtrlEntry 6 }

gs2328pPortSecSwitchStatusTable OBJECT-TYPE
   SYNTAX      SEQUENCE OF GS2328PPortSecSwitchStatusEntry
   MAX-ACCESS  not-accessible
   STATUS      current
   DESCRIPTION
       " "
   ::= { gs2328pPortSecurity 2 }

gs2328pPortSecSwitchStatusEntry OBJECT-TYPE
   SYNTAX      GS2328PPortSecSwitchStatusEntry
   MAX-ACCESS  not-accessible
   STATUS      current
   DESCRIPTION
       ""
   INDEX    { gs2328pPortSecSwitchStatusPort  }
   ::= { gs2328pPortSecSwitchStatusTable 1 }

GS2328PPortSecSwitchStatusEntry ::= SEQUENCE {
   gs2328pPortSecSwitchStatusPort                Integer32,
   gs2328pPortSecSwitchStatusUsers               DisplayString,
   gs2328pPortSecSwitchStatusState               DisplayString,
   gs2328pPortSecSwitchStatusMACCountCurrent     Integer32,
   gs2328pPortSecSwitchStatusMACCountLimit       Integer32
}

gs2328pPortSecSwitchStatusPort OBJECT-TYPE
   SYNTAX      Integer32(1..4095)
   MAX-ACCESS  not-accessible
   STATUS      current
   DESCRIPTION
       " "
   ::= { gs2328pPortSecSwitchStatusEntry 1 }

gs2328pPortSecSwitchStatusUsers OBJECT-TYPE
   SYNTAX      DisplayString
   MAX-ACCESS  read-only
   STATUS      current
   DESCRIPTION
       " Users Abbr: L = Limit Control, 8 = 802.1X, D = DHCP Snooping, V = Voice VLAN, 
         '-' means that the corresponding user module is not enabled. "
   ::= { gs2328pPortSecSwitchStatusEntry 2 }

gs2328pPortSecSwitchStatusState OBJECT-TYPE
   SYNTAX      DisplayString
   MAX-ACCESS  read-only
   STATUS      current
   DESCRIPTION
       " Shows the current state of the port : Disabled, Ready, Limit Reached, Shutdown. "
   ::= { gs2328pPortSecSwitchStatusEntry 3 }

gs2328pPortSecSwitchStatusMACCountCurrent OBJECT-TYPE
   SYNTAX      Integer32(1..4095)
   MAX-ACCESS  read-only
   STATUS      current
   DESCRIPTION
       ""
   ::= { gs2328pPortSecSwitchStatusEntry 4 }

gs2328pPortSecSwitchStatusMACCountLimit OBJECT-TYPE
   SYNTAX      Integer32(1..4095)
   MAX-ACCESS  read-only
   STATUS      current
   DESCRIPTION
       ""
   ::= { gs2328pPortSecSwitchStatusEntry 5 }

gs2328pPortSecPortStatus                                      OBJECT IDENTIFIER ::= { gs2328pPortSecurity 3 }

gs2328pPortSecPortStatusPort OBJECT-TYPE
   SYNTAX       Integer32(1..4095)
   MAX-ACCESS   read-write
   STATUS       current
   DESCRIPTION
       "port number
        default: 1
        range: 1 - port number."
   ::= { gs2328pPortSecPortStatus 1 }

gs2328pPortSecPortStatusTable OBJECT-TYPE
   SYNTAX      SEQUENCE OF GS2328PPortSecPortStatusEntry
   MAX-ACCESS  not-accessible
   STATUS      current
   DESCRIPTION
      " "
   ::= { gs2328pPortSecPortStatus 2 }
       
gs2328pPortSecPortStatusEntry OBJECT-TYPE
   SYNTAX      GS2328PPortSecPortStatusEntry
   MAX-ACCESS  not-accessible
   STATUS      current
   DESCRIPTION
       ""
   INDEX    { gs2328pPortSecPortStatusIndex  }
   ::= { gs2328pPortSecPortStatusTable 1 }       

GS2328PPortSecPortStatusEntry ::= SEQUENCE {
   gs2328pPortSecPortStatusIndex              Integer32,
   gs2328pPortSecPortStatusMACAddress         MacAddress,
   gs2328pPortSecPortStatusVLANId             Integer32,
   gs2328pPortSecPortStatusState              DisplayString,
   gs2328pPortSecPortStatusTimeOfAddition     DisplayString,
   gs2328pPortSecPortStatusAgeAndHold         DisplayString
}

gs2328pPortSecPortStatusIndex OBJECT-TYPE
   SYNTAX      Integer32(1..4095)
   MAX-ACCESS  not-accessible
   STATUS      current
   DESCRIPTION
       " "
   ::= { gs2328pPortSecPortStatusEntry 1 }

gs2328pPortSecPortStatusMACAddress OBJECT-TYPE
   SYNTAX      MacAddress
   MAX-ACCESS  read-only
   STATUS      current
   DESCRIPTION
       " "
   ::= { gs2328pPortSecPortStatusEntry 2 }

gs2328pPortSecPortStatusVLANId OBJECT-TYPE
   SYNTAX      Integer32(1..4094)
   MAX-ACCESS  read-only
   STATUS      current
   DESCRIPTION
       " "
   ::= { gs2328pPortSecPortStatusEntry 3 }

gs2328pPortSecPortStatusState OBJECT-TYPE
   SYNTAX      DisplayString
   MAX-ACCESS  read-only
   STATUS      current
   DESCRIPTION
       "Blocked / Forwarding "
   ::= { gs2328pPortSecPortStatusEntry 4 }

gs2328pPortSecPortStatusTimeOfAddition OBJECT-TYPE
   SYNTAX      DisplayString
   MAX-ACCESS  read-only
   STATUS      current
   DESCRIPTION
       " "
   ::= { gs2328pPortSecPortStatusEntry 5 }

gs2328pPortSecPortStatusAgeAndHold OBJECT-TYPE
   SYNTAX      DisplayString
   MAX-ACCESS  read-only
   STATUS      current
   DESCRIPTION
       " "
   ::= { gs2328pPortSecPortStatusEntry 6 }       
       

gs2328pAccessManagement                                      OBJECT IDENTIFIER ::= { gs2328pSecurity 6 }

gs2328pAccessMgtConf                                         OBJECT IDENTIFIER ::= { gs2328pAccessManagement 1 }

gs2328pAccessMgtConfMode OBJECT-TYPE
   SYNTAX      INTEGER { disable(0), enable(1) }
   MAX-ACCESS  read-write
   STATUS      current
   DESCRIPTION
       "default: 0
       0: disable
       1: enable "
   ::= { gs2328pAccessMgtConf 1 }

gs2328pAccessMgtConfCreate OBJECT-TYPE
   SYNTAX      INTEGER { none(0), create(1) }
   MAX-ACCESS  read-write
   STATUS      current
   DESCRIPTION
       "default: 0
       0: none
       1: create "
   ::= { gs2328pAccessMgtConf 2 }

gs2328pAccessMgtConfTable OBJECT-TYPE
   SYNTAX      SEQUENCE OF GS2328PAccessMgtConfEntry
   MAX-ACCESS  not-accessible
   STATUS      current
   DESCRIPTION
       " "
   ::= { gs2328pAccessMgtConf 3 }

gs2328pAccessMgtConfEntry OBJECT-TYPE
   SYNTAX      GS2328PAccessMgtConfEntry
   MAX-ACCESS  not-accessible
   STATUS      current
   DESCRIPTION
       ""
   INDEX    { gs2328pAccessMgtIndex  }
   ::= { gs2328pAccessMgtConfTable 1 }
   
GS2328PAccessMgtConfEntry ::= SEQUENCE {
   gs2328pAccessMgtIndex             Integer32,
   gs2328pAccessMgtAddresstype       INTEGER,
   gs2328pAccessMgtStartIpAddress    DisplayString,
   gs2328pAccessMgtEndIpAddress      DisplayString,
   gs2328pAccessMgtHttpHttps         INTEGER,
   gs2328pAccessMgtSNMP              INTEGER,
   gs2328pAccessMgtTelnetSSH         INTEGER,
   gs2328pAccessMgtRowStatus         INTEGER
}

gs2328pAccessMgtIndex OBJECT-TYPE
   SYNTAX      Integer32(1..16)
   MAX-ACCESS  read-write
   STATUS      current
   DESCRIPTION
       "Set Access Management config index
        range : 1-16."
   ::= { gs2328pAccessMgtConfEntry 1 }

gs2328pAccessMgtAddresstype OBJECT-TYPE
   SYNTAX      INTEGER { ipv4(0), ipv6(1) }
   MAX-ACCESS  read-write
   STATUS      current
   DESCRIPTION
       "0: ipv4
        1: ipv6 "
   ::= { gs2328pAccessMgtConfEntry 2 }
   
gs2328pAccessMgtStartIpAddress OBJECT-TYPE
   SYNTAX      DisplayString
   MAX-ACCESS  read-write
   STATUS      current
   DESCRIPTION
       " Start IP address. 
         IP address doesn't allowed all zero or all 'ff'H."
   ::= { gs2328pAccessMgtConfEntry 3 }
   
gs2328pAccessMgtEndIpAddress OBJECT-TYPE
   SYNTAX      DisplayString
   MAX-ACCESS  read-write
   STATUS      current
   DESCRIPTION
       " End IP address. 
         IP address doesn't allowed all zero or all 'ff'H.
         End ip address is not less than start ip address."
   ::= { gs2328pAccessMgtConfEntry 4 }

gs2328pAccessMgtHttpHttps OBJECT-TYPE
   SYNTAX      INTEGER { disable(0), enable(1) }
   MAX-ACCESS  read-write
   STATUS      current
   DESCRIPTION
       "default: 0
       0: disable
       1: enable "
   ::= { gs2328pAccessMgtConfEntry 5 }

gs2328pAccessMgtSNMP OBJECT-TYPE
   SYNTAX      INTEGER { disable(0), enable(1) }
   MAX-ACCESS  read-write
   STATUS      current
   DESCRIPTION
       "default: 0
       0: disable
       1: enable "
   ::= { gs2328pAccessMgtConfEntry 6 }

gs2328pAccessMgtTelnetSSH OBJECT-TYPE
   SYNTAX      INTEGER { disable(0), enable(1) }
   MAX-ACCESS  read-write
   STATUS      current
   DESCRIPTION
       "default: 0
       0: disable
       1: enable "
   ::= { gs2328pAccessMgtConfEntry 7 }

gs2328pAccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2328pAccessMgtConfEntry 8 }

gs2328pAccessMgtStatistics                                   OBJECT IDENTIFIER ::= { gs2328pAccessManagement 2 }

gs2328pHttpReceivedPkts OBJECT-TYPE
   SYNTAX      Counter32
   MAX-ACCESS  read-only
   STATUS      current
   DESCRIPTION
       " "
   ::= { gs2328pAccessMgtStatistics 1 }

gs2328pHttpAllowedPkts OBJECT-TYPE
   SYNTAX      Counter32
   MAX-ACCESS  read-only
   STATUS      current
   DESCRIPTION
       " "
   ::= { gs2328pAccessMgtStatistics 2 }

gs2328pHttpDiscardedPkts OBJECT-TYPE
   SYNTAX      Counter32
   MAX-ACCESS  read-only
   STATUS      current
   DESCRIPTION
       " "
   ::= { gs2328pAccessMgtStatistics 3 }

gs2328pHttpsReceivedPkts OBJECT-TYPE
   SYNTAX      Counter32
   MAX-ACCESS  read-only
   STATUS      current
   DESCRIPTION
       " "
   ::= { gs2328pAccessMgtStatistics 4 }

gs2328pHttpsAllowedPkts OBJECT-TYPE
   SYNTAX      Counter32
   MAX-ACCESS  read-only
   STATUS      current
   DESCRIPTION
       " "
   ::= { gs2328pAccessMgtStatistics 5 }

gs2328pHttpsDiscardedPkts OBJECT-TYPE
   SYNTAX      Counter32
   MAX-ACCESS  read-only
   STATUS      current
   DESCRIPTION
       " "
   ::= { gs2328pAccessMgtStatistics 6 }

gs2328pSnmpReceivedPkts OBJECT-TYPE
   SYNTAX      Counter32
   MAX-ACCESS  read-only
   STATUS      current
   DESCRIPTION
       " "
   ::= { gs2328pAccessMgtStatistics 7 }

gs2328pSnmpAllowedPkts OBJECT-TYPE
   SYNTAX      Counter32
   MAX-ACCESS  read-only
   STATUS      current
   DESCRIPTION
       " "
   ::= { gs2328pAccessMgtStatistics 8 }

gs2328pSnmpDiscardedPkts OBJECT-TYPE
   SYNTAX      Counter32
   MAX-ACCESS  read-only
   STATUS      current
   DESCRIPTION
       " "
   ::= { gs2328pAccessMgtStatistics 9 }

gs2328pTelnetReceivedPkts OBJECT-TYPE
   SYNTAX      Counter32
   MAX-ACCESS  read-only
   STATUS      current
   DESCRIPTION
       " "
   ::= { gs2328pAccessMgtStatistics 10 }

gs2328pTelnetAllowedPkts OBJECT-TYPE
   SYNTAX      Counter32
   MAX-ACCESS  read-only
   STATUS      current
   DESCRIPTION
       " "
   ::= { gs2328pAccessMgtStatistics 11 }

gs2328pTelnetDiscardedPkts OBJECT-TYPE
   SYNTAX      Counter32
   MAX-ACCESS  read-only
   STATUS      current
   DESCRIPTION
       " "
   ::= { gs2328pAccessMgtStatistics 12 }

gs2328pSSHReceivedPkts OBJECT-TYPE
   SYNTAX      Counter32
   MAX-ACCESS  read-only
   STATUS      current
   DESCRIPTION
       " "
   ::= { gs2328pAccessMgtStatistics 13 }

gs2328pSSHAllowedPkts OBJECT-TYPE
   SYNTAX      Counter32
   MAX-ACCESS  read-only
   STATUS      current
   DESCRIPTION
       " "
   ::= { gs2328pAccessMgtStatistics 14 }

gs2328pSSHDiscardedPkts OBJECT-TYPE
   SYNTAX      Counter32
   MAX-ACCESS  read-only
   STATUS      current
   DESCRIPTION
       " "
   ::= { gs2328pAccessMgtStatistics 15 }

gs2328pAccessMgtStatisticsClearAll OBJECT-TYPE
   SYNTAX      INTEGER { none(0), clear(1) }
   MAX-ACCESS  read-write
   STATUS      current
   DESCRIPTION
       "0: none
        1: clear"
   ::= { gs2328pAccessMgtStatistics 16 }

gs2328pSSH                                                   OBJECT IDENTIFIER ::= { gs2328pSecurity 7 }

gs2328pSSHMode OBJECT-TYPE
   SYNTAX      INTEGER { disable(0), enable(1) }
   MAX-ACCESS  read-write
   STATUS      current
   DESCRIPTION
       "default: 1
        0: disable
        1: enable"
   ::= { gs2328pSSH 1 }

gs2328pHTTPS                                                 OBJECT IDENTIFIER ::= { gs2328pSecurity 8 }

gs2328pHTTPSMode OBJECT-TYPE
   SYNTAX      INTEGER { disable(0), enable(1) }
   MAX-ACCESS  read-write
   STATUS      current
   DESCRIPTION
       "default: 1
        0: disable
        1: enable"
   ::= { gs2328pHTTPS 1 }

gs2328pHTTPSAutoRedirect OBJECT-TYPE
   SYNTAX      INTEGER { disable(0), enable(1) }
   MAX-ACCESS  read-write
   STATUS      current
   DESCRIPTION
       "default: 0
        0: disable
        1: enable"
   ::= { gs2328pHTTPS 2 }

gs2328pHTTPSCertRenew OBJECT-TYPE
   SYNTAX      INTEGER { doNothing(0), renew(1) }
   MAX-ACCESS  read-write
   STATUS      current
   DESCRIPTION
       "default: 0 ,
        0: doNothing
        1: renew"
   ::= { gs2328pHTTPS 3 }

gs2328pHTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2328pHTTPS 4 }

gs2328pHTTPMode OBJECT-TYPE
   SYNTAX      INTEGER { disable(0), enable(1) }
   MAX-ACCESS  read-write
   STATUS      current
   DESCRIPTION
       "default: 1
        0: disable
        1: enable"
   ::= { gs2328pHTTPS 5 }

gs2328pAuthMethod                                            OBJECT IDENTIFIER ::= { gs2328pSecurity 9 }

gs2328pConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328pAuthMethod 1 }

gs2328pConsoleFallback OBJECT-TYPE
   SYNTAX      INTEGER { disable(0), enable(1) }
   MAX-ACCESS  read-write
   STATUS      current
   DESCRIPTION
       "default: 0
        0:disable
        1:enable"
   ::= { gs2328pAuthMethod 2 }

gs2328pTelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328pAuthMethod 3 }

gs2328pTelnetFallback OBJECT-TYPE
   SYNTAX      INTEGER { disable(0), enable(1) }
   MAX-ACCESS  read-write
   STATUS      current
   DESCRIPTION
       "default: 0
        0:disable
        1:enable"
   ::= { gs2328pAuthMethod 4 }

gs2328pSshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328pAuthMethod 5 }

gs2328pSshFallback OBJECT-TYPE
   SYNTAX      INTEGER { disable(0), enable(1) }
   MAX-ACCESS  read-write
   STATUS      current
   DESCRIPTION
       "default: 0
        0:disable
        1:enable"
   ::= { gs2328pAuthMethod 6 }

gs2328pTftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328pAuthMethod 9 }

gs2328pTftpFallback OBJECT-TYPE
   SYNTAX      INTEGER { disable(0), enable(1) }
   MAX-ACCESS  read-write
   STATUS      current
   DESCRIPTION
       "default: 0
        0:disable
        1:enable"
   ::= { gs2328pAuthMethod 10 }
   
gs2328pLoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2328pAuthMethod 11 }

gs2328pLockMinutes OBJECT-TYPE
   SYNTAX      Integer32(1..99)
   MAX-ACCESS  read-write
   STATUS      current
   DESCRIPTION
       "Lock time to login failures trigger.
        range: 1-99.
        default: 5."
   ::= { gs2328pAuthMethod 12 }

gs2328pHttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328pAuthMethod 13 }

gs2328pHttpFallback OBJECT-TYPE
   SYNTAX      INTEGER { disable(0), enable(1) }
   MAX-ACCESS  read-write
   STATUS      current
   DESCRIPTION
       "default: 0
        0:disable
        1:enable"
   ::= { gs2328pAuthMethod 14 }

gs2328pHttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2328pAuthMethod 15 }

gs2328pHttpsFallback OBJECT-TYPE
   SYNTAX      INTEGER { disable(0), enable(1) }
   MAX-ACCESS  read-write
   STATUS      current
   DESCRIPTION
       "default: 0
        0:disable
        1:enable"
   ::= { gs2328pAuthMethod 16 }


gs2328pAAA                                              OBJECT IDENTIFIER ::= { gs2328pSecurity 10 }

gs2328pAAACommonServer                                  OBJECT IDENTIFIER ::= { gs2328pAAA 1 }

gs2328pAAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2328pAAACommonServer 1 }

gs2328pAAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2328pAAACommonServer 2 }

gs2328pAAATACACSPlusAuthAndAccounting                  OBJECT IDENTIFIER ::= { gs2328pAAA 2 }

gs2328pAAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2328pAAATACACSPlusAuthAndAccounting 1 }

gs2328pAAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2328pAAATACACSPlusAuthAndAccounting 2 }

gs2328pAAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2328pAAATACACSPlusAuthAndAccounting 3 }

gs2328pRADIUSAuthenticationServerTable OBJECT-TYPE
   SYNTAX      SEQUENCE OF Gs2328pRADIUSAuthenticationServerEntry
   MAX-ACCESS  not-accessible
   STATUS      current
   DESCRIPTION
       " "
   ::= { gs2328pAAA 3 }

gs2328pRADIUSAuthenticationServerEntry OBJECT-TYPE
   SYNTAX      Gs2328pRADIUSAuthenticationServerEntry
   MAX-ACCESS  not-accessible
   STATUS      current
   DESCRIPTION
       ""
   INDEX    { gs2328pRADIUSAuthenticationServerIndex  }
   ::= { gs2328pRADIUSAuthenticationServerTable 1 }

Gs2328pRADIUSAuthenticationServerEntry ::= SEQUENCE {
   gs2328pRADIUSAuthenticationServerIndex     Integer32,
   gs2328pRADIUSAuthenticationServerEnable    INTEGER,
   gs2328pRADIUSAuthenticationServerIP        DisplayString,
   gs2328pRADIUSAuthenticationServerPort      Integer32,
   gs2328pRADIUSAuthenticationServerSecret    DisplayString
}

gs2328pRADIUSAuthenticationServerIndex OBJECT-TYPE
   SYNTAX      Integer32(1..5)
   MAX-ACCESS  not-accessible
   STATUS      current
   DESCRIPTION
       "RADIUS Authentication Server index
        range : 1-5."
   ::= { gs2328pRADIUSAuthenticationServerEntry 1 }

gs2328pRADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2328pRADIUSAuthenticationServerEntry 2 }

gs2328pRADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2328pRADIUSAuthenticationServerEntry 3 }

gs2328pRADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2328pRADIUSAuthenticationServerEntry 4 }

gs2328pRADIUSAuthenticationServerSecret OBJECT-TYPE
   SYNTAX      DisplayString
   MAX-ACCESS  read-write
   STATUS      current
   DESCRIPTION
       "The secret - up to 64 characters long - shared between the RADIUS Authentication Server and the switch. "
   ::= { gs2328pRADIUSAuthenticationServerEntry 5 }
   

gs2328pRADIUSAccountingServerTable OBJECT-TYPE
   SYNTAX      SEQUENCE OF Gs2328pRADIUSAccountingServerEntry
   MAX-ACCESS  not-accessible
   STATUS      current
   DESCRIPTION
       " "
   ::= { gs2328pAAA 4 }

gs2328pRADIUSAccountingServerEntry OBJECT-TYPE
   SYNTAX      Gs2328pRADIUSAccountingServerEntry
   MAX-ACCESS  not-accessible
   STATUS      current
   DESCRIPTION
       ""
   INDEX    { gs2328pRADIUSAccountingServerIndex  }
   ::= { gs2328pRADIUSAccountingServerTable 1 }

Gs2328pRADIUSAccountingServerEntry ::= SEQUENCE {
   gs2328pRADIUSAccountingServerIndex     Integer32,
   gs2328pRADIUSAccountingServerEnable    INTEGER,
   gs2328pRADIUSAccountingServerIP        DisplayString,
   gs2328pRADIUSAccountingServerPort      Integer32,
   gs2328pRADIUSAccountingServerSecret    DisplayString
}

gs2328pRADIUSAccountingServerIndex OBJECT-TYPE
   SYNTAX      Integer32(1..5)
   MAX-ACCESS  not-accessible
   STATUS      current
   DESCRIPTION
       "RADIUS Accounting Server index
        range : 1-5."
   ::= { gs2328pRADIUSAccountingServerEntry 1 }

gs2328pRADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2328pRADIUSAccountingServerEntry 2 }

gs2328pRADIUSAccountingServerIP OBJECT-TYPE
   SYNTAX      DisplayString
   MAX-ACCESS  read-write
   STATUS      current
   DESCRIPTION
       "The IP address or hostname of the RADIUS Accounting Server.
       IP address is expressed in  dotted decimal notation. "
   ::= { gs2328pRADIUSAccountingServerEntry 3 }

gs2328pRADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2328pRADIUSAccountingServerEntry 4 }

gs2328pRADIUSAccountingServerSecret OBJECT-TYPE
   SYNTAX      DisplayString
   MAX-ACCESS  read-write
   STATUS      current
   DESCRIPTION
       "The secret - up to 64 characters long - shared between the RADIUS Accounting Server and the switch. "
   ::= { gs2328pRADIUSAccountingServerEntry 5 }

gs2328pTACACSPlusAuthenticationServerTable OBJECT-TYPE
   SYNTAX      SEQUENCE OF Gs2328pTACACSPlusAuthenticationServerEntry
   MAX-ACCESS  not-accessible
   STATUS      current
   DESCRIPTION
       " "
   ::= { gs2328pAAA 5 }

gs2328pTACACSPlusAuthenticationServerEntry OBJECT-TYPE
   SYNTAX      Gs2328pTACACSPlusAuthenticationServerEntry
   MAX-ACCESS  not-accessible
   STATUS      current
   DESCRIPTION
       ""
   INDEX    { gs2328pTACACSPlusAuthenticationServerIndex  }
   ::= { gs2328pTACACSPlusAuthenticationServerTable 1 }

Gs2328pTACACSPlusAuthenticationServerEntry ::= SEQUENCE {
   gs2328pTACACSPlusAuthenticationServerIndex     Integer32,
   gs2328pTACACSPlusAuthenticationServerEnable    INTEGER,
   gs2328pTACACSPlusAuthenticationServerIP        DisplayString,
   gs2328pTACACSPlusAuthenticationServerPort      Integer32,
   gs2328pTACACSPlusAuthenticationServerSecret    DisplayString
}

gs2328pTACACSPlusAuthenticationServerIndex OBJECT-TYPE
   SYNTAX      Integer32(1..5)
   MAX-ACCESS  not-accessible
   STATUS      current
   DESCRIPTION
       "TACACSPlus Authentication Server index
        range : 1-5."
   ::= { gs2328pTACACSPlusAuthenticationServerEntry 1 }

gs2328pTACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2328pTACACSPlusAuthenticationServerEntry 2 }

gs2328pTACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2328pTACACSPlusAuthenticationServerEntry 3 }

gs2328pTACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2328pTACACSPlusAuthenticationServerEntry 4 }

gs2328pTACACSPlusAuthenticationServerSecret OBJECT-TYPE
   SYNTAX      DisplayString
   MAX-ACCESS  read-write
   STATUS      current
   DESCRIPTION
       "The secret - up to 64 characters long - shared between the TACACSPlus Authentication Server and the switch. "
   ::= { gs2328pTACACSPlusAuthenticationServerEntry 5 }


gs2328pRADIUSStatisticsTable OBJECT-TYPE
   SYNTAX      SEQUENCE OF Gs2328pRADIUSStatisticsEntry
   MAX-ACCESS  not-accessible
   STATUS      current
   DESCRIPTION
       " "
   ::= { gs2328pAAA 6 }

gs2328pRADIUSStatisticsEntry OBJECT-TYPE
   SYNTAX      Gs2328pRADIUSStatisticsEntry
   MAX-ACCESS  not-accessible
   STATUS      current
   DESCRIPTION
       ""
   INDEX    { gs2328pRADIUSAuthStatisticsServerIndex  }
   ::= { gs2328pRADIUSStatisticsTable 1 }

Gs2328pRADIUSStatisticsEntry ::= SEQUENCE {
   gs2328pRADIUSAuthStatisticsServerIndex                           Integer32,
   gs2328pRADIUSAuthStatisticsRecPktAccessAccepts                   Counter32,
   gs2328pRADIUSAuthStatisticsRecPktAccessRejects                   Counter32,
   gs2328pRADIUSAuthStatisticsRecPktAccessChallenges                Counter32,
   gs2328pRADIUSAuthStatisticsRecPktMalformedAccResponses           Counter32,
   gs2328pRADIUSAuthStatisticsRecPktBadAuthenticators               Counter32,
   gs2328pRADIUSAuthStatisticsRecPktUnknownTypes                    Counter32,
   gs2328pRADIUSAuthStatisticsRecPktDropped                         Counter32,
   gs2328pRADIUSAuthStatisticsTransmitPktAccessRequests             Counter32,
   gs2328pRADIUSAuthStatisticsTransmitPktAccessRetransmissions      Counter32,
   gs2328pRADIUSAuthStatisticsTransmitPktPendingRequests            Counter32,
   gs2328pRADIUSAuthStatisticsTransmitPktTimeouts                   Counter32,
   gs2328pRADIUSAuthIP                                              DisplayString,
   gs2328pRADIUSAuthState                                           DisplayString,
   gs2328pRADIUSAuthRoundTripTime                                   DisplayString,

   gs2328pRADIUSAccountingStatisticsRecPktResponses                 Counter32,
   gs2328pRADIUSAccountingStatisticsRecPktMalformedResponses        Counter32,
   gs2328pRADIUSAccountingStatisticsRecPktBadAuthenticators         Counter32,
   gs2328pRADIUSAccountingStatisticsRecPktUnknownTypes              Counter32,
   gs2328pRADIUSAccountingStatisticsRecPktDropped                   Counter32,
   gs2328pRADIUSAccountingStatisticsTransmitPktRequests             Counter32,
   gs2328pRADIUSAccountingStatisticsTransmitPktRetransmissions      Counter32,
   gs2328pRADIUSAccountingStatisticsTransmitPktPendingRequests      Counter32,
   gs2328pRADIUSAccountingStatisticsTransmitPktTimeouts             Counter32,
   gs2328pRADIUSAccountingIP                                        DisplayString,
   gs2328pRADIUSAccountingState                                     DisplayString,
   gs2328pRADIUSAccountingRoundTripTime                             DisplayString,
   gs2328pRADIUSStatisticsClear                                     INTEGER
}

gs2328pRADIUSAuthStatisticsServerIndex OBJECT-TYPE
   SYNTAX      Integer32(1..5)
   MAX-ACCESS  not-accessible
   STATUS      current
   DESCRIPTION
       "RADIUS Authentication Server index
        range : 1-5."
   ::= { gs2328pRADIUSStatisticsEntry 1 }

gs2328pRADIUSAuthStatisticsRecPktAccessAccepts OBJECT-TYPE
   SYNTAX      Counter32
   MAX-ACCESS  read-only
   STATUS      current
   DESCRIPTION
       "The number of RADIUS Access-Accept packets (valid or invalid) received from the server."
   ::= { gs2328pRADIUSStatisticsEntry 2 }

gs2328pRADIUSAuthStatisticsRecPktAccessRejects OBJECT-TYPE
   SYNTAX      Counter32
   MAX-ACCESS  read-only
   STATUS      current
   DESCRIPTION
       "The number of RADIUS Access-Reject packets (valid or invalid) received from the server."
   ::= { gs2328pRADIUSStatisticsEntry 3 }

gs2328pRADIUSAuthStatisticsRecPktAccessChallenges OBJECT-TYPE
   SYNTAX      Counter32
   MAX-ACCESS  read-only
   STATUS      current
   DESCRIPTION
       "The number of RADIUS Access-Challenge packets (valid or invalid) received from the server. "
   ::= { gs2328pRADIUSStatisticsEntry 4 }

gs2328pRADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2328pRADIUSStatisticsEntry 5 }

gs2328pRADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2328pRADIUSStatisticsEntry 6 }

gs2328pRADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2328pRADIUSStatisticsEntry 7 }

gs2328pRADIUSAuthStatisticsRecPktDropped OBJECT-TYPE
   SYNTAX      Counter32
   MAX-ACCESS  read-only
   STATUS      current
   DESCRIPTION
       "The number of RADIUS packets that were received from the server on the
       authentication port and dropped for some other reason."
   ::= { gs2328pRADIUSStatisticsEntry 8 }

gs2328pRADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2328pRADIUSStatisticsEntry 9 }

gs2328pRADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2328pRADIUSStatisticsEntry 10 }

gs2328pRADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2328pRADIUSStatisticsEntry 11 }

gs2328pRADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2328pRADIUSStatisticsEntry 12 }

gs2328pRADIUSAuthIP OBJECT-TYPE
   SYNTAX      DisplayString
   MAX-ACCESS  read-only
   STATUS      current
   DESCRIPTION
       "IP address and UDP port for the authentication server in question."
   ::= { gs2328pRADIUSStatisticsEntry 13 }

gs2328pRADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2328pRADIUSStatisticsEntry 14 }

gs2328pRADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2328pRADIUSStatisticsEntry 15 }

gs2328pRADIUSAccountingStatisticsRecPktResponses OBJECT-TYPE
   SYNTAX      Counter32
   MAX-ACCESS  read-only
   STATUS      current
   DESCRIPTION
       "The number of RADIUS packets (valid or invalid) received from the server."
   ::= { gs2328pRADIUSStatisticsEntry 16 }

gs2328pRADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2328pRADIUSStatisticsEntry 17 }

gs2328pRADIUSAccountingStatisticsRecPktBadAuthenticators OBJECT-TYPE
   SYNTAX      Counter32
   MAX-ACCESS  read-only
   STATUS      current
   DESCRIPTION
       "The number of RADIUS packets containing invalid authenticators received
       from the server."
   ::= { gs2328pRADIUSStatisticsEntry 18 }

gs2328pRADIUSAccountingStatisticsRecPktUnknownTypes OBJECT-TYPE
   SYNTAX      Counter32
   MAX-ACCESS  read-only
   STATUS      current
   DESCRIPTION
       "The number of RADIUS packets of unknown types that were received from
       the server on the accounting port."
   ::= { gs2328pRADIUSStatisticsEntry 19 }

gs2328pRADIUSAccountingStatisticsRecPktDropped OBJECT-TYPE
   SYNTAX      Counter32
   MAX-ACCESS  read-only
   STATUS      current
   DESCRIPTION
       "The number of RADIUS packets that were received from the server on the
       accounting port and dropped for some other reason."
   ::= { gs2328pRADIUSStatisticsEntry 20 }

gs2328pRADIUSAccountingStatisticsTransmitPktRequests OBJECT-TYPE
   SYNTAX      Counter32
   MAX-ACCESS  read-only
   STATUS      current
   DESCRIPTION
       "The number of RADIUS packets sent to the server. This does not include
       retransmissions."
   ::= { gs2328pRADIUSStatisticsEntry 21 }

gs2328pRADIUSAccountingStatisticsTransmitPktRetransmissions OBJECT-TYPE
   SYNTAX      Counter32
   MAX-ACCESS  read-only
   STATUS      current
   DESCRIPTION
       "The number of RADIUS packets retransmitted to the RADIUS accounting server."
   ::= { gs2328pRADIUSStatisticsEntry 22 }

gs2328pRADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2328pRADIUSStatisticsEntry 23 }

gs2328pRADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2328pRADIUSStatisticsEntry 24 }

gs2328pRADIUSAccountingIP OBJECT-TYPE
   SYNTAX      DisplayString
   MAX-ACCESS  read-only
   STATUS      current
   DESCRIPTION
       "IP address and UDP port for the accounting server in question."
   ::= { gs2328pRADIUSStatisticsEntry 25 }

gs2328pRADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2328pRADIUSStatisticsEntry 26 }
   
gs2328pRADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2328pRADIUSStatisticsEntry 27 }

gs2328pRADIUSStatisticsClear OBJECT-TYPE
   SYNTAX      INTEGER(0|1)
   MAX-ACCESS  read-write
   STATUS      current
   DESCRIPTION
       "Clears the counters for the server.
       read: always 0
       clear: set 1"
   ::= { gs2328pRADIUSStatisticsEntry 28 }

gs2328pNAS                                              OBJECT IDENTIFIER ::= { gs2328pSecurity 11 }

gs2328pNASConfiguration                                 OBJECT IDENTIFIER ::= { gs2328pNAS 1 }

gs2328pNASConfigMode OBJECT-TYPE
   SYNTAX      INTEGER { disable(0), enable(1) }
   MAX-ACCESS  read-write
   STATUS      current
   DESCRIPTION
       "Indicates if NAS is globally enabled or disabled on the switch. 
	    If globally disabled, all ports are allowed forwarding of frames."
   ::= { gs2328pNASConfiguration 1 }

gs2328pNASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication 
		Period. Reauthentication for 802.1X-enabled ports can be used to 
		detect if a new device is plugged into a switch port or if a 
		supplicant is no longer attached. 
		For MAC-based ports, reauthentication is only useful if the RADIUS 
		server configuration has changed. It does not involve communication 
		between the switch and the client, and therefore doesn't imply that 
		a client is still present on a port."
   ::= { gs2328pNASConfiguration 2 }

gs2328pNASConfigReauthPeriod OBJECT-TYPE
   SYNTAX      Integer32(1..3600)
   MAX-ACCESS  read-write
   STATUS      current
   DESCRIPTION
       "Determines the period, in seconds, after which a connected client must 
	    be reauthenticated. This is only active if the Reauthentication Enabled 
		checkbox is checked. 
		range: 1 - 3600 seconds."
   ::= { gs2328pNASConfiguration 3 }

gs2328pNASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2328pNASConfiguration 4 }
   
gs2328pNASConfigAgingPeriod OBJECT-TYPE
   SYNTAX      Integer32(10..1000000)
   MAX-ACCESS  read-write
   STATUS      current
   DESCRIPTION
       "When the NAS module uses the Port Security module to secure MAC addresses, 
	    the Port Security module needs to check for activity on the MAC address 
		in question at regular intervals and free resources if no activity 
		is seen within a given period of time.
		Admin State supported : Single, Multi and MAC-Based Auth. 802.1X.
		range: 10 - 1000000 seconds."
   ::= { gs2328pNASConfiguration 5 }   
   
gs2328pNASConfigHoldTime OBJECT-TYPE
   SYNTAX      Integer32(10..1000000)
   MAX-ACCESS  read-write
   STATUS      current
   DESCRIPTION
       "If a client is denied access - either because the RADIUS server denies
	    the client access or because the RADIUS server request times out 
		- the client is put on hold in the Unauthorized state. The hold timer 
		does not count during an on-going authentication. In MAC-based Auth. 
		mode, the switch will ignore new frames coming from the client during 
		the hold time.
		Admin State supported : Single, Multi and MAC-Based Auth. 802.1X.
		range: 10 - 1000000 seconds."
   ::= { gs2328pNASConfiguration 6 }  

gs2328pNASConfigRADIUSAssignedQoSEnabled OBJECT-TYPE
   SYNTAX      INTEGER { disable(0), enable(1) }
   MAX-ACCESS  read-write
   STATUS      current
   DESCRIPTION
       "RADIUS-assigned QoS provides a means to centrally control the 
	    traffic class to which traffic coming from a successfully authenticated 
		supplicant is assigned on the switch. The RADIUS server must be configured 
		to transmit special RADIUS attributes to take advantage of this feature."
   ::= { gs2328pNASConfiguration 7 }  
 
gs2328pNASConfigRADIUSAssignedVLANEnabled OBJECT-TYPE
   SYNTAX      INTEGER { disable(0), enable(1) }
   MAX-ACCESS  read-write
   STATUS      current
   DESCRIPTION
       "RADIUS-assigned VLAN provides a means to centrally control the VLAN on 
	    which a successfully authenticated supplicant is placed on the switch. 
	    Incoming traffic will be classified to and switched on the RADIUS-assigned 
		VLAN. The RADIUS server must be configured to transmit special RADIUS 
		attributes to take advantage of this feature.When enable, the individual 
		ports' ditto setting determine whether RADIUS-assigned VLAN is enabled 
		on that port. When disable, RADIUS-server assigned VLAN is disabled on 
		all ports. "
   ::= { gs2328pNASConfiguration 8 }    
   
gs2328pNASConfigGuestVLANEnabled OBJECT-TYPE
   SYNTAX      INTEGER { disable(0), enable(1) }
   MAX-ACCESS  read-write
   STATUS      current
   DESCRIPTION
       "A Guest VLAN is a special VLAN - typically with limited network access - 
	   on which 802.1X-unaware clients are placed after a network administrator-defined 
	   timeout. The switch follows a set of rules for entering and leaving the Guest 
	   VLAN as listed below.When enable, the individual ports' ditto setting determines 
	   whether the port can be moved into Guest VLAN. When disable, the ability to 
	   move to the Guest VLAN is disabled on all ports. "
   ::= { gs2328pNASConfiguration 9 } 
   
gs2328pNASConfigGuestVLANID OBJECT-TYPE
   SYNTAX      Integer32(1..4094)
   MAX-ACCESS  read-write
   STATUS      current
   DESCRIPTION
       "This is the value that a port's Port VLAN ID is set to if a port is moved into 
	   the Guest VLAN. It is only changeable if the Guest VLAN option is globally enabled.
	   range: 1 - 4094."
   ::= { gs2328pNASConfiguration 10 }

gs2328pNASConfigMaxReauthCount OBJECT-TYPE
   SYNTAX      Integer32(1..255)
   MAX-ACCESS  read-write
   STATUS      current
   DESCRIPTION
       "The number of times the switch transmits an EAPOL Request Identity frame without 
	   response before considering entering the Guest VLAN is adjusted with this setting. 
	   The value can only be changed if the Guest VLAN option is globally enabled.
	   range: 1 - 255."
   ::= { gs2328pNASConfiguration 11 }

gs2328pNASConfigAllowGuestVLANEAPOLSeen OBJECT-TYPE
   SYNTAX      INTEGER { disable(0), enable(1) }
   MAX-ACCESS  read-write
   STATUS      current
   DESCRIPTION
       "The switch remembers if an EAPOL frame has been received on the port for the 
	   life-time of the port. Once the switch considers whether to enter the Guest VLAN, 
	   it will first check if this option is enabled or disabled. If disabled, the switch 
	   will only enter the Guest VLAN if an EAPOL frame has not been received on the port 
	   for the life-time of the port. If enabled (checked), the switch will consider 
	   entering the Guest VLAN even if an EAPOL frame has been received on the port for 
	   the life-time of the port.The value can only be changed if the Guest VLAN option 
	   is globally enabled."
   ::= { gs2328pNASConfiguration 12 }

gs2328pNASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2328pNASConfiguration 101 }

gs2328pNASPortConfigTable OBJECT-TYPE
   SYNTAX      SEQUENCE OF Gs2328pNASPortConfigEntry
   MAX-ACCESS  not-accessible
   STATUS      current
   DESCRIPTION
       ""
   ::= { gs2328pNASConfiguration 13 }

gs2328pNASPortConfigEntry OBJECT-TYPE
   SYNTAX      Gs2328pNASPortConfigEntry
   MAX-ACCESS  not-accessible
   STATUS      current
   DESCRIPTION
       ""
   INDEX    { gs2328pNASPortConfigPort }
   ::= { gs2328pNASPortConfigTable 1 }

Gs2328pNASPortConfigEntry ::= SEQUENCE {
   gs2328pNASPortConfigPort                       Integer32,
   gs2328pNASPortConfigAdminState                 INTEGER,
   gs2328pNASPortConfigRADIUSAssignedQoSEnabled	  INTEGER,
   gs2328pNASPortConfigRADIUSAssignedVLANEnabled  INTEGER,
   gs2328pNASPortConfigGuestVLANEnabled           INTEGER,   
   gs2328pNASPortConfigFallbackEnabled            INTEGER,   
   gs2328pNASPortConfigPortState                  DisplayString,
   gs2328pNASPortConfigReauthenticate             INTEGER,
   gs2328pNASPortConfigReinitialize               INTEGER
}
  
gs2328pNASPortConfigPort OBJECT-TYPE
   SYNTAX      Integer32(1..255)
   MAX-ACCESS  not-accessible
   STATUS      current
   DESCRIPTION
       " port, range : 1 - port number. "
   ::= { gs2328pNASPortConfigEntry 1 }   
   
gs2328pNASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2328pNASPortConfigEntry 2 }   
   
gs2328pNASPortConfigRADIUSAssignedQoSEnabled OBJECT-TYPE
   SYNTAX      INTEGER { disable(0), enable(1) }
   MAX-ACCESS  read-write
   STATUS      current
   DESCRIPTION
       "When RADIUS-Assigned QoS is both globally enabled and enabled (checked) 
	    on a given port, the switch reacts to QoS Class information carried in 
		the RADIUS Access-Accept packet transmitted by the RADIUS server when a 
		supplicant is successfully authenticated. If present and valid, traffic 
		received on the supplicant's port will be classified to the given QoS Class.
		Admin State supported : Port-based and Single 802.1X and MAC-based Single Auth."
   ::= { gs2328pNASPortConfigEntry 3 }    
   
gs2328pNASPortConfigRADIUSAssignedVLANEnabled OBJECT-TYPE
   SYNTAX      INTEGER { disable(0), enable(1) }
   MAX-ACCESS  read-write
   STATUS      current
   DESCRIPTION
       "When RADIUS-Assigned VLAN is both globally enabled and enabled (checked) 
	   for a given port, the switch reacts to VLAN ID information carried in the 
	   RADIUS Access-Accept packet transmitted by the RADIUS server when a supplicant 
	   is successfully authenticated. If present and valid, the port's Port VLAN ID 
	   will be changed to this VLAN ID, the port will be set to be a member of that 
	   VLAN ID, and the port will be forced into VLAN unaware mode. Once assigned, 
	   all traffic arriving on the port will be classified and switched on the 
	   RADIUS-assigned VLAN ID.
	   Admin State supported : Port-based and Single 802.1X and MAC-based Single Auth."
   ::= { gs2328pNASPortConfigEntry 4 }    
   
gs2328pNASPortConfigGuestVLANEnabled OBJECT-TYPE
   SYNTAX      INTEGER { disable(0), enable(1) }
   MAX-ACCESS  read-write
   STATUS      current
   DESCRIPTION
       "When Guest VLAN is both globally enabled and enabled (checked) for a given port, 
	   the switch considers moving the port into the Guest VLAN according to the rules
	   outlined below.
	   Admin State supported : Port-based , Single and Multi 802.1X."
   ::= { gs2328pNASPortConfigEntry 5 }    
   
gs2328pNASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode 
		and the supplicant is authorized.
		Unauthorized: The port is in Force Unauthorized or a single-supplicant 
		mode and the supplicant is not successfully authorized by the RADIUS server.
		X Auth/Y Unauth: The port is in a multi-supplicant mode. Currently X clients 
		are authorized and Y are unauthorized."
   ::= { gs2328pNASPortConfigEntry 6 }    
   
gs2328pNASPortConfigReauthenticate OBJECT-TYPE
   SYNTAX      INTEGER { doNothing(0), do(1) }
   MAX-ACCESS  read-write
   STATUS      current
   DESCRIPTION
       "Schedules a reauthentication whenever the quiet-period of the port runs out 
	   (EAPOL-based authentication). For MAC-based authentication, reauthentication 
	   will be attempted immediately.The button only has effect for successfully 
	   authenticated clients on the port and will not cause the clients to get 
	   temporarily unauthorized."
   ::= { gs2328pNASPortConfigEntry 7 }    

gs2328pNASPortConfigReinitialize OBJECT-TYPE
   SYNTAX      INTEGER { doNothing(0), do(1) }
   MAX-ACCESS  read-write
   STATUS      current
   DESCRIPTION
       "Forces a reinitialization of the clients on the port and thereby a reauthentication 
	   immediately. The clients will transfer to the unauthorized state while the 
	   reauthentication is in progress."
   ::= { gs2328pNASPortConfigEntry 8 }    

gs2328pNASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2328pNASPortConfigEntry 101 }

gs2328pNASSwitchStatusTable OBJECT-TYPE
   SYNTAX      SEQUENCE OF Gs2328pNASSwitchStatusEntry
   MAX-ACCESS  not-accessible
   STATUS      current
   DESCRIPTION
       ""
   ::= { gs2328pNAS 2 }

gs2328pNASSwitchStatusEntry OBJECT-TYPE
   SYNTAX      Gs2328pNASSwitchStatusEntry
   MAX-ACCESS  not-accessible
   STATUS      current
   DESCRIPTION
       ""
   INDEX    { gs2328pNASPortConfigPort }
   ::= { gs2328pNASSwitchStatusTable 1 }

Gs2328pNASSwitchStatusEntry ::= SEQUENCE {
   gs2328pNASSwitchStatusAdminState 	DisplayString,
   gs2328pNASSwitchStatusPortState		DisplayString,
   gs2328pNASSwitchStatusLastSource		DisplayString,
   gs2328pNASSwitchStatusLastID			DisplayString,
   gs2328pNASSwitchStatusQoSClass		DisplayString,
   gs2328pNASSwitchStatusPortVlanID		DisplayString
}
   
gs2328pNASSwitchStatusAdminState OBJECT-TYPE
   SYNTAX      DisplayString
   MAX-ACCESS  read-only
   STATUS      current
   DESCRIPTION
       "The port's current administrative state. Refer to NAS Admin State for a description of possible values."
   ::= { gs2328pNASSwitchStatusEntry 2 }   
   
gs2328pNASSwitchStatusPortState OBJECT-TYPE
   SYNTAX      DisplayString
   MAX-ACCESS  read-only
   STATUS      current
   DESCRIPTION
       "The current state of the port. Refer to NAS Port State for a description of the individual states."
   ::= { gs2328pNASSwitchStatusEntry 3 }      
   
gs2328pNASSwitchStatusLastSource OBJECT-TYPE
   SYNTAX      DisplayString
   MAX-ACCESS  read-only
   STATUS      current
   DESCRIPTION
       "The source MAC address carried in the most recently received EAPOL frame for EAPOL-based authentication, 
	   and the most recently received frame from a new client for MAC-based authentication."
   ::= { gs2328pNASSwitchStatusEntry 4 }      

gs2328pNASSwitchStatusLastID OBJECT-TYPE
   SYNTAX      DisplayString
   MAX-ACCESS  read-only
   STATUS      current
   DESCRIPTION
       "The user name (supplicant identity) carried in the most recently received Response Identity EAPOL frame 
	   for EAPOL-based authentication, and the source MAC address from the most recently received frame from a 
	   new client for MAC-based authentication."
   ::= { gs2328pNASSwitchStatusEntry 5 }      

gs2328pNASSwitchStatusQoSClass OBJECT-TYPE
   SYNTAX      DisplayString
   MAX-ACCESS  read-only
   STATUS      current
   DESCRIPTION
       "QoS Class assigned to the port by the RADIUS server if enabled."
   ::= { gs2328pNASSwitchStatusEntry 6 } 
   
gs2328pNASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2328pNASSwitchStatusEntry 7 } 

gs2328pNASPortStatus                                 OBJECT IDENTIFIER ::= { gs2328pNAS 3 }
   
gs2328pNASPortStatusCountersTable OBJECT-TYPE
   SYNTAX      SEQUENCE OF Gs2328pNASPortStatusCountersEntry
   MAX-ACCESS  not-accessible
   STATUS      current
   DESCRIPTION
       ""
   ::= { gs2328pNASPortStatus 1 }

gs2328pNASPortStatusCountersEntry OBJECT-TYPE
   SYNTAX      Gs2328pNASPortStatusCountersEntry
   MAX-ACCESS  not-accessible
   STATUS      current
   DESCRIPTION
       ""
   INDEX    { gs2328pNASPortConfigPort }
   ::= { gs2328pNASPortStatusCountersTable 1 }

Gs2328pNASPortStatusCountersEntry ::= SEQUENCE {
   gs2328pNASRxCountersEAPOLTotal  	                  Counter32,
   gs2328pNASRxCountersEAPOLResponseID	              Counter32,
   gs2328pNASRxCountersEAPOLResponses	              Counter32,
   gs2328pNASRxCountersEAPOLStart	                  Counter32,
   gs2328pNASRxCountersEAPOLLogoff                    Counter32,
   gs2328pNASRxCountersEAPOLInvalidType               Counter32,
   gs2328pNASRxCountersEAPOLInvalidLength             Counter32,
   gs2328pNASTxCountersEAPOLTotal                     Counter32,
   gs2328pNASTxCountersEAPOLRequestID                 Counter32,
   gs2328pNASTxCountersEAPOLRequests                  Counter32,
   gs2328pNASRxBackendServerCountersAccessChallenges  Counter32,
   gs2328pNASRxBackendServerCountersOtherRequests     Counter32,
   gs2328pNASRxBackendServerCountersAuthSuccesses     Counter32,
   gs2328pNASRxBackendServerCountersAuthFailures      Counter32,
   gs2328pNASTxBackendServerCountersResponses         Counter32,
   gs2328pNASLastSupplicantInfoMACAddress             DisplayString,
   gs2328pNASLastSupplicantInfoVlanID                 Integer32,
   gs2328pNASLastSupplicantInfoVersion                Integer32,
   gs2328pNASLastSupplicantInfoIdentity               DisplayString,
   gs2328pNASCountersDoClear                          INTEGER
}

gs2328pNASRxCountersEAPOLTotal OBJECT-TYPE
   SYNTAX      Counter32
   MAX-ACCESS  read-only
   STATUS      current
   DESCRIPTION
       "The number of valid EAPOL frames of any type that have been received by the switch."
   ::= { gs2328pNASPortStatusCountersEntry 2 }   

gs2328pNASRxCountersEAPOLResponseID OBJECT-TYPE
   SYNTAX      Counter32
   MAX-ACCESS  read-only
   STATUS      current
   DESCRIPTION
       "The number of valid EAPOL Response Identity frames that have been received by the switch."
   ::= { gs2328pNASPortStatusCountersEntry 3 }   

gs2328pNASRxCountersEAPOLResponses OBJECT-TYPE
   SYNTAX      Counter32
   MAX-ACCESS  read-only
   STATUS      current
   DESCRIPTION
       "The number of valid EAPOL response frames (other than Response Identity frames) 
	   that have been received by the switch."
   ::= { gs2328pNASPortStatusCountersEntry 4 }   

gs2328pNASRxCountersEAPOLStart OBJECT-TYPE
   SYNTAX      Counter32
   MAX-ACCESS  read-only
   STATUS      current
   DESCRIPTION
       "The number of EAPOL Start frames that have been received by the switch."
   ::= { gs2328pNASPortStatusCountersEntry 5 }   

gs2328pNASRxCountersEAPOLLogoff OBJECT-TYPE
   SYNTAX      Counter32
   MAX-ACCESS  read-only
   STATUS      current
   DESCRIPTION
       "The number of valid EAPOL Logoff frames that have been received by the switch."
   ::= { gs2328pNASPortStatusCountersEntry 6 }   

gs2328pNASRxCountersEAPOLInvalidType OBJECT-TYPE
   SYNTAX      Counter32
   MAX-ACCESS  read-only
   STATUS      current
   DESCRIPTION
       "The number of EAPOL frames that have been received by the switch in which 
	   the frame type is not recognized."
   ::= { gs2328pNASPortStatusCountersEntry 7 }   
   
gs2328pNASRxCountersEAPOLInvalidLength OBJECT-TYPE
   SYNTAX      Counter32
   MAX-ACCESS  read-only
   STATUS      current
   DESCRIPTION
       "The number of EAPOL frames that have been received by the switch in which the 
	   Packet Body Length field is invalid."
   ::= { gs2328pNASPortStatusCountersEntry 8 }   
   
gs2328pNASTxCountersEAPOLTotal OBJECT-TYPE
   SYNTAX      Counter32
   MAX-ACCESS  read-only
   STATUS      current
   DESCRIPTION
       "The number of EAPOL frames of any type that have been transmitted by the switch."
   ::= { gs2328pNASPortStatusCountersEntry 9 }   
   
gs2328pNASTxCountersEAPOLRequestID OBJECT-TYPE
   SYNTAX      Counter32
   MAX-ACCESS  read-only
   STATUS      current
   DESCRIPTION
       "The number of EAPOL Request Identity frames that have been transmitted by the switch."
   ::= { gs2328pNASPortStatusCountersEntry 10 }      

gs2328pNASTxCountersEAPOLRequests OBJECT-TYPE
   SYNTAX      Counter32
   MAX-ACCESS  read-only
   STATUS      current
   DESCRIPTION
       "The number of valid EAPOL Request frames (other than Request Identity frames) 
	   that have been transmitted by the switch."
   ::= { gs2328pNASPortStatusCountersEntry 11 }      
   
gs2328pNASRxBackendServerCountersAccessChallenges OBJECT-TYPE
   SYNTAX      Counter32
   MAX-ACCESS  read-only
   STATUS      current
   DESCRIPTION
       "802.1X-based: Counts the number of times that the switch receives the first request 
	   from the backend server following the first response from the supplicant.
	   MAC-based: Counts all Access Challenges received from the backend server for this 
	   port or client."
   ::= { gs2328pNASPortStatusCountersEntry 12 }      

gs2328pNASRxBackendServerCountersOtherRequests OBJECT-TYPE
   SYNTAX      Counter32
   MAX-ACCESS  read-only
   STATUS      current
   DESCRIPTION
       "802.1X-based: Counts the number of times that the switch sends an EAP Request 
	   packet following the first to the supplicant.
	   MAC-based: Not applicable."
   ::= { gs2328pNASPortStatusCountersEntry 13 }      
   
gs2328pNASRxBackendServerCountersAuthSuccesses OBJECT-TYPE
   SYNTAX      Counter32
   MAX-ACCESS  read-only
   STATUS      current
   DESCRIPTION
       "Counts the number of times that the switch receives a success indication. 
	   Indicates that the supplicant/client has successfully authenticated to the 
	   backend server."
   ::= { gs2328pNASPortStatusCountersEntry 14 }      
   
gs2328pNASRxBackendServerCountersAuthFailures OBJECT-TYPE
   SYNTAX      Counter32
   MAX-ACCESS  read-only
   STATUS      current
   DESCRIPTION
       "Counts the number of times that the switch receives a failure message. 
	   This indicates that the supplicant/client has not authenticated to the 
	   backend server. "
   ::= { gs2328pNASPortStatusCountersEntry 15 }      
   
gs2328pNASTxBackendServerCountersResponses OBJECT-TYPE
   SYNTAX      Counter32
   MAX-ACCESS  read-only
   STATUS      current
   DESCRIPTION
       "802.1X-based: Counts the number of times that the switch attempts to 
	   send a supplicant's first response packet to the backend server. Indicates 
	   the switch attempted communication with the backend server. Possible 
	   retransmissions are not counted. 
	   MAC-based: Counts all the backend server packets sent from the switch 
	   towards the backend server for a given port or client. Possible 
	   retransmissions are not counted."
   ::= { gs2328pNASPortStatusCountersEntry 16 }  

gs2328pNASLastSupplicantInfoMACAddress OBJECT-TYPE
   SYNTAX      DisplayString
   MAX-ACCESS  read-only
   STATUS      current
   DESCRIPTION
       "The MAC address of the last supplicant/client."
   ::= { gs2328pNASPortStatusCountersEntry 17 }  

gs2328pNASLastSupplicantInfoVlanID OBJECT-TYPE
   SYNTAX      Integer32
   MAX-ACCESS  read-only
   STATUS      current
   DESCRIPTION
       "The VLAN ID on which the last frame from the last supplicant/client was received."
   ::= { gs2328pNASPortStatusCountersEntry 18 }  
   
gs2328pNASLastSupplicantInfoVersion OBJECT-TYPE
   SYNTAX      Integer32
   MAX-ACCESS  read-only
   STATUS      current
   DESCRIPTION
       "802.1X-based: The protocol version number carried in the most recently 
	   received EAPOL frame. 
	   MAC-based: Not applicable."
   ::= { gs2328pNASPortStatusCountersEntry 19 }  

gs2328pNASLastSupplicantInfoIdentity OBJECT-TYPE
   SYNTAX      DisplayString
   MAX-ACCESS  read-only
   STATUS      current
   DESCRIPTION
       "802.1X-based: The user name (supplicant identity) carried in the most recently received 
	   Response Identity EAPOL frame. 
	   MAC-based: Not applicable."
   ::= { gs2328pNASPortStatusCountersEntry 20 }  

gs2328pNASCountersDoClear OBJECT-TYPE
   SYNTAX      INTEGER { doNothing(0), do(1) }
   MAX-ACCESS  read-write
   STATUS      current
   DESCRIPTION
       "Clear the counters for the selected port."
   ::= { gs2328pNASPortStatusCountersEntry 21 }    

gs2328pNASPortStatusClientsTable OBJECT-TYPE
   SYNTAX      SEQUENCE OF Gs2328pNASPortStatusClientsEntry
   MAX-ACCESS  not-accessible
   STATUS      current
   DESCRIPTION
       ""
   ::= { gs2328pNASPortStatus 2 }

gs2328pNASPortStatusClientsEntry OBJECT-TYPE
   SYNTAX      Gs2328pNASPortStatusClientsEntry
   MAX-ACCESS  not-accessible
   STATUS      current
   DESCRIPTION
       ""
   INDEX    { gs2328pNASPortConfigPort,
		gs2328pNASClientsIndex}
   ::= { gs2328pNASPortStatusClientsTable 1 }

Gs2328pNASPortStatusClientsEntry ::= SEQUENCE {
   gs2328pNASClientsIndex  	                  		    Integer32,
   gs2328pNASClientsIdentity							DisplayString,
   gs2328pNASClientsMACAddress  	                  	DisplayString,
   gs2328pNASClientsVlanID		              			Integer32,
   gs2328pNASClientsState	              				DisplayString,
   gs2328pNASClientsLastAuth	                  		DisplayString,
   gs2328pNASRxClientsEAPOLTotal  	                  	Counter32,
   gs2328pNASRxClientsEAPOLResponseID	              	Counter32,
   gs2328pNASRxClientsEAPOLResponses	              	Counter32,
   gs2328pNASRxClientsEAPOLStart	                  	Counter32,
   gs2328pNASRxClientsEAPOLLogoff                    	Counter32,
   gs2328pNASRxClientsEAPOLInvalidType               	Counter32,
   gs2328pNASRxClientsEAPOLInvalidLength             	Counter32,
   gs2328pNASTxClientsEAPOLTotal                     	Counter32,
   gs2328pNASTxClientsEAPOLRequestID                 	Counter32,
   gs2328pNASTxClientsEAPOLRequests                  	Counter32,
   gs2328pNASRxBackendServerClientsAccessChallenges  	Counter32,
   gs2328pNASRxBackendServerClientsOtherRequests     	Counter32,
   gs2328pNASRxBackendServerClientsAuthSuccesses     	Counter32,
   gs2328pNASRxBackendServerClientsAuthFailures      	Counter32,
   gs2328pNASTxBackendServerClientsResponses         	Counter32
}

gs2328pNASClientsIndex OBJECT-TYPE
   SYNTAX      Integer32(1..255)
   MAX-ACCESS  not-accessible
   STATUS      current
   DESCRIPTION
       "Entry of client table in the port."
   ::= { gs2328pNASPortStatusClientsEntry 1 } 
   
gs2328pNASClientsIdentity OBJECT-TYPE
   SYNTAX      DisplayString
   MAX-ACCESS  read-only
   STATUS      current
   DESCRIPTION
       "Shows the identity of the supplicant, as received in the Response Identity 
	   EAPOL frame.This isn't available for MAC-based Auth."
   ::= { gs2328pNASPortStatusClientsEntry 2 }
   
gs2328pNASClientsMACAddress OBJECT-TYPE
   SYNTAX      DisplayString
   MAX-ACCESS  read-only
   STATUS      current
   DESCRIPTION
       "Multi 802.1X, this column holds the MAC address of the attached supplicant. 
	   MAC-based Auth., this column holds the MAC address of the attached client."
   ::= { gs2328pNASPortStatusClientsEntry 3 }  

gs2328pNASClientsVlanID OBJECT-TYPE
   SYNTAX      Integer32(1..4095)
   MAX-ACCESS  read-only
   STATUS      current
   DESCRIPTION
       "This column holds the VLAN ID that the corresponding client is currently 
	   secured through the Port Security module."
   ::= { gs2328pNASPortStatusClientsEntry 4 }  
   
gs2328pNASClientsState OBJECT-TYPE
   SYNTAX      DisplayString
   MAX-ACCESS  read-only
   STATUS      current
   DESCRIPTION
       "The client can either be authenticated or unauthenticated. In the authenticated 
	   state, it is allowed to forward frames on the port, and in the unauthenticated 
	   state, it is blocked."
   ::= { gs2328pNASPortStatusClientsEntry 5 }  

gs2328pNASClientsLastAuth OBJECT-TYPE
   SYNTAX      DisplayString
   MAX-ACCESS  read-only
   STATUS      current
   DESCRIPTION
       "Shows the date and time of the last authentication of the client."
   ::= { gs2328pNASPortStatusClientsEntry 6 }  
   
gs2328pNASRxClientsEAPOLTotal OBJECT-TYPE
   SYNTAX      Counter32
   MAX-ACCESS  read-only
   STATUS      current
   DESCRIPTION
       "The number of valid EAPOL frames of any type that have been received by the switch."
   ::= { gs2328pNASPortStatusClientsEntry 7 }  

gs2328pNASRxClientsEAPOLResponseID OBJECT-TYPE
   SYNTAX      Counter32
   MAX-ACCESS  read-only
   STATUS      current
   DESCRIPTION
       "The number of valid EAPOL Response Identity frames that have been received by the switch."
   ::= { gs2328pNASPortStatusClientsEntry 8 }   

gs2328pNASRxClientsEAPOLResponses OBJECT-TYPE
   SYNTAX      Counter32
   MAX-ACCESS  read-only
   STATUS      current
   DESCRIPTION
       "The number of valid EAPOL response frames (other than Response Identity frames) 
	   that have been received by the switch."
   ::= { gs2328pNASPortStatusClientsEntry 9 }   

gs2328pNASRxClientsEAPOLStart OBJECT-TYPE
   SYNTAX      Counter32
   MAX-ACCESS  read-only
   STATUS      current
   DESCRIPTION
       "The number of EAPOL Start frames that have been received by the switch."
   ::= { gs2328pNASPortStatusClientsEntry 10 }   

gs2328pNASRxClientsEAPOLLogoff OBJECT-TYPE
   SYNTAX      Counter32
   MAX-ACCESS  read-only
   STATUS      current
   DESCRIPTION
       "The number of valid EAPOL Logoff frames that have been received by the switch."
   ::= { gs2328pNASPortStatusClientsEntry 11 }   

gs2328pNASRxClientsEAPOLInvalidType OBJECT-TYPE
   SYNTAX      Counter32
   MAX-ACCESS  read-only
   STATUS      current
   DESCRIPTION
       "The number of EAPOL frames that have been received by the switch in which 
	   the frame type is not recognized."
   ::= { gs2328pNASPortStatusClientsEntry 12 }   
   
gs2328pNASRxClientsEAPOLInvalidLength OBJECT-TYPE
   SYNTAX      Counter32
   MAX-ACCESS  read-only
   STATUS      current
   DESCRIPTION
       "The number of EAPOL frames that have been received by the switch in which the 
	   Packet Body Length field is invalid."
   ::= { gs2328pNASPortStatusClientsEntry 13 }

gs2328pNASTxClientsEAPOLTotal OBJECT-TYPE
   SYNTAX      Counter32
   MAX-ACCESS  read-only
   STATUS      current
   DESCRIPTION
       "The number of EAPOL frames of any type that have been transmitted by the switch."
   ::= { gs2328pNASPortStatusClientsEntry 14 }   
   
gs2328pNASTxClientsEAPOLRequestID OBJECT-TYPE
   SYNTAX      Counter32
   MAX-ACCESS  read-only
   STATUS      current
   DESCRIPTION
       "The number of EAPOL Request Identity frames that have been transmitted by the switch."
   ::= { gs2328pNASPortStatusClientsEntry 15 }      

gs2328pNASTxClientsEAPOLRequests OBJECT-TYPE
   SYNTAX      Counter32
   MAX-ACCESS  read-only
   STATUS      current
   DESCRIPTION
       "The number of valid EAPOL Request frames (other than Request Identity frames) 
	   that have been transmitted by the switch."
   ::= { gs2328pNASPortStatusClientsEntry 16 }        

gs2328pNASRxBackendServerClientsAccessChallenges OBJECT-TYPE
   SYNTAX      Counter32
   MAX-ACCESS  read-only
   STATUS      current
   DESCRIPTION
       "802.1X-based: Counts the number of times that the switch receives the first request 
	   from the backend server following the first response from the supplicant.
	   MAC-based: Counts all Access Challenges received from the backend server for this 
	   port or client."
   ::= { gs2328pNASPortStatusClientsEntry 17 }      

gs2328pNASRxBackendServerClientsOtherRequests OBJECT-TYPE
   SYNTAX      Counter32
   MAX-ACCESS  read-only
   STATUS      current
   DESCRIPTION
       "802.1X-based: Counts the number of times that the switch sends an EAP Request 
	   packet following the first to the supplicant.
	   MAC-based: Not applicable."
   ::= { gs2328pNASPortStatusClientsEntry 18 }      
   
gs2328pNASRxBackendServerClientsAuthSuccesses OBJECT-TYPE
   SYNTAX      Counter32
   MAX-ACCESS  read-only
   STATUS      current
   DESCRIPTION
       "Counts the number of times that the switch receives a success indication. 
	   Indicates that the supplicant/client has successfully authenticated to the 
	   backend server."
   ::= { gs2328pNASPortStatusClientsEntry 19 }      
   
gs2328pNASRxBackendServerClientsAuthFailures OBJECT-TYPE
   SYNTAX      Counter32
   MAX-ACCESS  read-only
   STATUS      current
   DESCRIPTION
       "Counts the number of times that the switch receives a failure message. 
	   This indicates that the supplicant/client has not authenticated to the 
	   backend server. "
   ::= { gs2328pNASPortStatusClientsEntry 20 }      
   
gs2328pNASTxBackendServerClientsResponses OBJECT-TYPE
   SYNTAX      Counter32
   MAX-ACCESS  read-only
   STATUS      current
   DESCRIPTION
       "802.1X-based: Counts the number of times that the switch attempts to 
	   send a supplicant's first response packet to the backend server. Indicates 
	   the switch attempted communication with the backend server. Possible 
	   retransmissions are not counted. 
	   MAC-based: Counts all the backend server packets sent from the switch 
	   towards the backend server for a given port or client. Possible 
	   retransmissions are not counted."
   ::= { gs2328pNASPortStatusClientsEntry 21 }  


gs2328pMaintenance                                           OBJECT IDENTIFIER ::= { lancomGS2328P  4 }

gs2328pRestartDevice OBJECT-TYPE
   SYNTAX      INTEGER { disable(0), enable(1) }
   MAX-ACCESS  read-write
   STATUS      current
   DESCRIPTION
       "default: 0
        0:none
        1:yes"
   ::= { gs2328pMaintenance 1 }

gs2328pColdRestartDevice OBJECT-TYPE
   SYNTAX      INTEGER { disable(0), enable(1) }
   MAX-ACCESS  read-write
   STATUS      current
   DESCRIPTION
       "default: 0
        0:none
        1:yes"
   ::= { gs2328pMaintenance 1500 }

gs2328pFirmware                                         OBJECT IDENTIFIER ::= { gs2328pMaintenance 2 }

gs2328pFirmwareIpAddress OBJECT-TYPE
   SYNTAX       IpAddress
   MAX-ACCESS   read-write
   STATUS       current
   DESCRIPTION
        "Get/Set the firmware tftp server."
   ::= { gs2328pFirmware 1 }

gs2328pFirmwareFileName OBJECT-TYPE
   SYNTAX       DisplayString
   MAX-ACCESS   read-write
   STATUS       current
   DESCRIPTION
        "Get/Set the path and filename for firmware upgrading."
   ::= { gs2328pFirmware 2 }

gs2328pDoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2328pFirmware 3 }

gs2328pSaveOrRestore                                         OBJECT IDENTIFIER ::= { gs2328pMaintenance 3 }

gs2328pFactoryDefaults OBJECT-TYPE
   SYNTAX      INTEGER { none(0), yes(1) }
   MAX-ACCESS  read-write
   STATUS      current
   DESCRIPTION
       "default: 0
        0:none
        1:yes"
   ::= { gs2328pSaveOrRestore 1 }

gs2328pSaveStart OBJECT-TYPE
   SYNTAX      INTEGER { none(0), yes(1) }
   MAX-ACCESS  read-write
   STATUS      current
   DESCRIPTION
       "default: 0
        0:none
        1:yes"
   ::= { gs2328pSaveOrRestore 2 }

gs2328pSaveUser OBJECT-TYPE
   SYNTAX      INTEGER { none(0), yes(1) }
   MAX-ACCESS  read-write
   STATUS      current
   DESCRIPTION
       "default: 0
        0:none
        1:yes"
   ::= { gs2328pSaveOrRestore 3 }

gs2328pRestoreUser OBJECT-TYPE
   SYNTAX      INTEGER { none(0), yes(1) }
   MAX-ACCESS  read-write
   STATUS      current
   DESCRIPTION
       "default: 0
        0:none
        1:yes"
   ::= { gs2328pSaveOrRestore 4 }


gs2328pExportOrImport                                        OBJECT IDENTIFIER ::= { gs2328pMaintenance 4 }

gs2328pExportIpAddress OBJECT-TYPE
   SYNTAX       IpAddress
   MAX-ACCESS   read-write
   STATUS       current
   DESCRIPTION
        "Get/Set the export tftp server."
   ::= { gs2328pExportOrImport 1 }

gs2328pExportConfigName OBJECT-TYPE
   SYNTAX       DisplayString
   MAX-ACCESS   read-write
   STATUS       current
   DESCRIPTION
       "Get/Set the export file path and name."
   ::= { gs2328pExportOrImport 2 }

gs2328pDoExportConfig OBJECT-TYPE
   SYNTAX       INTEGER{ doNothing(0), do(1) }
   MAX-ACCESS   read-write
   STATUS       current
   DESCRIPTION
        "Do export-config.
         Get this OID always return zero.
         1 - export."
   ::= { gs2328pExportOrImport 3 }

gs2328pImportIpAddress OBJECT-TYPE
   SYNTAX       IpAddress
   MAX-ACCESS   read-write
   STATUS       current
   DESCRIPTION
        "Get/Set the import tftp server."
   ::= { gs2328pExportOrImport 4 }

gs2328pImportConfigName OBJECT-TYPE
   SYNTAX      DisplayString
   MAX-ACCESS  read-write
   STATUS      current
   DESCRIPTION
       "Get/Set the import file path and name."
   ::= { gs2328pExportOrImport 5 }

gs2328pDoImportConfig OBJECT-TYPE
   SYNTAX       INTEGER{ doNothing(0), do(1) }
   MAX-ACCESS   read-write
   STATUS       current
   DESCRIPTION
        "Do export-config.
         Get this OID always return zero.
         1 - import."
   ::= { gs2328pExportOrImport 6 }

gs2328pDiagnostics                                           OBJECT IDENTIFIER ::= { gs2328pMaintenance 5 }

gs2328pPingIpAddress OBJECT-TYPE
   SYNTAX      IpAddress
   MAX-ACCESS  read-write
   STATUS      current
   DESCRIPTION
       " The destination IP Address. "
   ::= { gs2328pDiagnostics 1 }
   
gs2328pPingSize OBJECT-TYPE
   SYNTAX      Integer32(60..1400)
   MAX-ACCESS  read-write
   STATUS      current
   DESCRIPTION
       " Size of ICMP echo packet.
         range : 60-1400, default : 64. "
   ::= { gs2328pDiagnostics 2 }   

gs2328pDoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2328pDiagnostics 3 }

gs2328pPingResult OBJECT-TYPE
   SYNTAX      DisplayString
   MAX-ACCESS  read-only
   STATUS      current
   DESCRIPTION
       " Show ping result. "
   ::= { gs2328pDiagnostics 4 }

gs2328pPing6IpAddress OBJECT-TYPE
   SYNTAX      DisplayString
   MAX-ACCESS  read-write
   STATUS      current
   DESCRIPTION
       " The destination IPv6 Address. "
   ::= { gs2328pDiagnostics 5 }
   
gs2328pPing6Size OBJECT-TYPE
   SYNTAX      Integer32(60..1400)
   MAX-ACCESS  read-write
   STATUS      current
   DESCRIPTION
       " Size of ICMP echo packet.
         range : 60-1400. "
   ::= { gs2328pDiagnostics 6 }   

gs2328pDoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2328pDiagnostics 7 }

gs2328pPing6Result OBJECT-TYPE
   SYNTAX      DisplayString
   MAX-ACCESS  read-only
   STATUS      current
   DESCRIPTION
       " Show ping result. "
   ::= { gs2328pDiagnostics 8 }


------------------------------------------------------------------------------------------------------------------
gs2328pTrap                                                  OBJECT IDENTIFIER ::= { lancomGS2328P  5 }

gs2328pTrapEvent                                             OBJECT IDENTIFIER ::= { gs2328pTrap 1 }

gs2328pEmergency NOTIFICATION-TYPE
  OBJECTS   { gs2328pInformation }
  STATUS        current
    DESCRIPTION
        "The severity level is Emergency. The system is unusable."
    ::= { gs2328pTrapEvent 1 }

gs2328pAlert NOTIFICATION-TYPE
  OBJECTS   { gs2328pInformation }
  STATUS        current
    DESCRIPTION
        "The severity level is Alert. The action must be taken immediately."
    ::= { gs2328pTrapEvent 2 }

gs2328pCritical NOTIFICATION-TYPE
  OBJECTS   { gs2328pInformation }
  STATUS        current
    DESCRIPTION
        "The severity level is Critical. Critical conditions."
    ::= { gs2328pTrapEvent 3 }

gs2328pError NOTIFICATION-TYPE
  OBJECTS   { gs2328pInformation }
  STATUS        current
    DESCRIPTION
        "The severity level is Error. Error conditions."
    ::= { gs2328pTrapEvent 4 }

gs2328pWarning NOTIFICATION-TYPE
  OBJECTS   { gs2328pInformation }
  STATUS        current
    DESCRIPTION
        "The severity level is Warning. Warning conditions."
    ::= { gs2328pTrapEvent 5 }

gs2328pNotice NOTIFICATION-TYPE
  OBJECTS   { gs2328pInformation }
  STATUS        current
    DESCRIPTION
        "The severity level is Notice. Normal but significant condition."
    ::= { gs2328pTrapEvent 6 }

gs2328pInformational NOTIFICATION-TYPE
  OBJECTS   { gs2328pInformation }
  STATUS        current
    DESCRIPTION
        "The severity level is Informational. Informational messages."
    ::= { gs2328pTrapEvent 7 }

gs2328pDebug NOTIFICATION-TYPE
  OBJECTS   { gs2328pInformation }
  STATUS        current
    DESCRIPTION
        "The severity level is Debug. debug-level messages."
    ::= { gs2328pTrapEvent 8 }

gs2328pTrapVariable                                          OBJECT IDENTIFIER ::= { gs2328pTrap 2 }

gs2328pInformation OBJECT-TYPE
    SYNTAX      DisplayString
    MAX-ACCESS  read-only
    STATUS      current
    DESCRIPTION
        "Trap information."
    ::= { gs2328pTrapVariable 1 }


END

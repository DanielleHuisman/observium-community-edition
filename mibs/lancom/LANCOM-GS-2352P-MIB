LANCOM-GS-2352P-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2352P                                             OBJECT IDENTIFIER ::= { gigabitEthernetSwitches 2353 }

gs2352pSystem                                                OBJECT IDENTIFIER ::= { lancomGS2352P 1 }

gs2352pSystemInformation                                     OBJECT IDENTIFIER ::= { gs2352pSystem 1 }

gs2352pModelName OBJECT-TYPE
   SYNTAX       DisplayString
   MAX-ACCESS   read-only
   STATUS       current
   DESCRIPTION
       ""
 ::= { gs2352pSystemInformation 1 }

gs2352pBIOSVersion OBJECT-TYPE
   SYNTAX       DisplayString
   MAX-ACCESS   read-only
   STATUS       current
   DESCRIPTION
       ""
   ::= { gs2352pSystemInformation 2 }

gs2352pFirmwareVersion OBJECT-TYPE
   SYNTAX       DisplayString
   MAX-ACCESS   read-only
   STATUS       current
   DESCRIPTION
       ""
   ::= { gs2352pSystemInformation 3 }

gs2352pHardwareMechanicalVersion OBJECT-TYPE
   SYNTAX       DisplayString
   MAX-ACCESS   read-only
   STATUS       current
   DESCRIPTION
       ""
   ::= { gs2352pSystemInformation 4 }

gs2352pSerialNumber OBJECT-TYPE
   SYNTAX       DisplayString
   MAX-ACCESS   read-only
   STATUS       current
   DESCRIPTION
       ""
   ::= { gs2352pSystemInformation 5 }

gs2352pHostMACAddress OBJECT-TYPE
   SYNTAX       MacAddress
   MAX-ACCESS   read-only
   STATUS       current
   DESCRIPTION
       ""
   ::= { gs2352pSystemInformation 6 }

gs2352pConsoleBaudrate OBJECT-TYPE
   SYNTAX       DisplayString
   MAX-ACCESS   read-only
   STATUS       current
   DESCRIPTION
       ""
   ::= { gs2352pSystemInformation 7 }

gs2352pRAMSize OBJECT-TYPE
   SYNTAX       DisplayString
   MAX-ACCESS   read-only
   STATUS       current
   DESCRIPTION
       ""
   ::= { gs2352pSystemInformation 8 }

gs2352pFlashSize OBJECT-TYPE
   SYNTAX       DisplayString
   MAX-ACCESS   read-only
   STATUS       current
   DESCRIPTION
       ""
   ::= { gs2352pSystemInformation 9 }

gs2352pBridgeFDBSize OBJECT-TYPE
   SYNTAX       DisplayString
   MAX-ACCESS   read-only
   STATUS       current
   DESCRIPTION
       ""
   ::= { gs2352pSystemInformation 10 }

gs2352pTransmitQueue OBJECT-TYPE
   SYNTAX       DisplayString
   MAX-ACCESS   read-only
   STATUS       current
   DESCRIPTION
       ""
   ::= { gs2352pSystemInformation 11 }

gs2352pMaximumFrameSize OBJECT-TYPE
   SYNTAX       DisplayString
   MAX-ACCESS   read-only
   STATUS       current
   DESCRIPTION
       ""
   ::= { gs2352pSystemInformation 12 }

gs2352pCPULoad OBJECT-TYPE
   SYNTAX       DisplayString
   MAX-ACCESS   read-only
   STATUS       current
   DESCRIPTION
       ""
   ::= { gs2352pSystemInformation 13 }

gs2352pFanSpeed OBJECT-TYPE
   SYNTAX       DisplayString
   MAX-ACCESS   read-only
   STATUS       current
   DESCRIPTION
       ""
   ::= { gs2352pSystemInformation 17 }
   
gs2352pACPower OBJECT-TYPE
   SYNTAX       DisplayString
   MAX-ACCESS   read-only
   STATUS       current
   DESCRIPTION
       ""
   ::= { gs2352pSystemInformation 18 }
   
gs2352pTemperature OBJECT-TYPE
   SYNTAX       DisplayString
   MAX-ACCESS   read-only
   STATUS       current
   DESCRIPTION
       ""
   ::= { gs2352pSystemInformation 19 }

gs2352pSystemDescription OBJECT-TYPE
   SYNTAX       DisplayString
   MAX-ACCESS   read-only
   STATUS       current
   DESCRIPTION
       ""
   ::= { gs2352pSystemInformation 21 }
   
gs2352pLocation OBJECT-TYPE
   SYNTAX       DisplayString
   MAX-ACCESS   read-only
   STATUS       current
   DESCRIPTION
       ""
   ::= { gs2352pSystemInformation 22 }
   
gs2352pContact OBJECT-TYPE
   SYNTAX       DisplayString
   MAX-ACCESS   read-only
   STATUS       current
   DESCRIPTION
       ""
   ::= { gs2352pSystemInformation 23 }
   
gs2352pDeviceName OBJECT-TYPE
   SYNTAX       DisplayString
   MAX-ACCESS   read-only
   STATUS       current
   DESCRIPTION
       ""
   ::= { gs2352pSystemInformation 24 }
   
gs2352pSystemDate OBJECT-TYPE
   SYNTAX       DisplayString
   MAX-ACCESS   read-only
   STATUS       current
   DESCRIPTION
       ""
   ::= { gs2352pSystemInformation 25 }
   
gs2352pSystemUptime OBJECT-TYPE
   SYNTAX       DisplayString
   MAX-ACCESS   read-only
   STATUS       current
   DESCRIPTION
       ""
   ::= { gs2352pSystemInformation 26 }
   
gs2352pSystemIPv4Address OBJECT-TYPE
   SYNTAX       DisplayString
   MAX-ACCESS   read-only
   STATUS       current
   DESCRIPTION
       ""
   ::= { gs2352pSystemInformation 27 }

gs2352pSystemIPv4SubnetMask OBJECT-TYPE
   SYNTAX       DisplayString
   MAX-ACCESS   read-only
   STATUS       current
   DESCRIPTION
       ""
   ::= { gs2352pSystemInformation 28 }
   
gs2352pSystemIPv4Gateway OBJECT-TYPE
   SYNTAX       DisplayString
   MAX-ACCESS   read-only
   STATUS       current
   DESCRIPTION
       ""
   ::= { gs2352pSystemInformation 29 }

gs2352pIPv6LinkLocalAddress OBJECT-TYPE
   SYNTAX       DisplayString
   MAX-ACCESS   read-only
   STATUS       current
   DESCRIPTION
       ""
   ::= { gs2352pSystemInformation 30 }

gs2352pIPv6Address OBJECT-TYPE
   SYNTAX       DisplayString
   MAX-ACCESS   read-only
   STATUS       current
   DESCRIPTION
       ""
   ::= { gs2352pSystemInformation 31 }

gs2352pIPv6Prefix OBJECT-TYPE
   SYNTAX       DisplayString
   MAX-ACCESS   read-only
   STATUS       current
   DESCRIPTION
       ""
   ::= { gs2352pSystemInformation 32 }
   
gs2352pIPv6Gateway OBJECT-TYPE
   SYNTAX       DisplayString
   MAX-ACCESS   read-only
   STATUS       current
   DESCRIPTION
       ""
   ::= { gs2352pSystemInformation 33 }
   
gs2352pLargestFreeMemBlock OBJECT-TYPE
   SYNTAX       Integer32
   MAX-ACCESS   read-only
   STATUS       current
   DESCRIPTION
       "Largest free memory block in Kb"
   ::= { gs2352pSystemInformation 1500 }   
   
gs2352pMemFree  OBJECT-TYPE
   SYNTAX       Integer32
   MAX-ACCESS   read-only
   STATUS       current
   DESCRIPTION
       "Free memory in Kb"
   ::= { gs2352pSystemInformation 1501 }
   
   
gs2352pSystemTime                                            OBJECT IDENTIFIER ::= { gs2352pSystem 2 }

gs2352pSystemTimeManual                                      OBJECT IDENTIFIER ::= { gs2352pSystemTime 1 }

gs2352pSystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2352pSystemTimeManual 1 }
   
gs2352pSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2352pSystemTimeManual 2 }

gs2352pSystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2352pSystemTimeManual 3 }
   
gs2352pSystemTimeManualDaylightSavings OBJECT-TYPE
   SYNTAX       INTEGER { disable(0), enable(1) }
   MAX-ACCESS   read-write
   STATUS       current
   DESCRIPTION
       "default: 0,
        0 : Disable,
        1 : Enable."
   ::= { gs2352pSystemTimeManual 4 }
   
gs2352pSystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2352pSystemTimeManual 5 }
   
gs2352pSystemTimeManualDaylightSavingsType OBJECT-TYPE
   SYNTAX       INTEGER { byDates(0), recurring(1) }
   MAX-ACCESS   read-write
   STATUS       current
   DESCRIPTION
       "default: 0,
        0 : By dates,
        1 : Recurring."
   ::= { gs2352pSystemTimeManual 6 }
   
gs2352pSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2352pSystemTimeManual 7 }
   
gs2352pSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2352pSystemTimeManual 8 }

gs2352pSystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2352pSystemTimeManual 9 }

gs2352pSystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2352pSystemTimeManual 10 }
   
gs2352pSystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2352pSystemTimeManual 11 }

gs2352pSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2352pSystemTimeManual 12 }
   
gs2352pSystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2352pSystemTimeManual 13 }

gs2352pSystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2352pSystemTimeManual 14 }
   
gs2352pSystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2352pSystemTimeManual 15 }

gs2352pSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2352pSystemTimeManual 16 }

gs2352pSystemTimeNTP                                     OBJECT IDENTIFIER ::= { gs2352pSystemTime 2 }

gs2352pSystemTimeNTPTable OBJECT-TYPE
   SYNTAX      SEQUENCE OF GS2352PSystemTimeNTPEntry
   MAX-ACCESS  not-accessible
   STATUS      current
   DESCRIPTION
       " "
   ::= { gs2352pSystemTimeNTP 1 }

gs2352pSystemTimeNTPEntry OBJECT-TYPE
   SYNTAX      GS2352PSystemTimeNTPEntry
   MAX-ACCESS  not-accessible
   STATUS      current
   DESCRIPTION
       ""
   INDEX    { gs2352pSystemTimeNTPIndex  }
   ::= { gs2352pSystemTimeNTPTable 1 }

GS2352PSystemTimeNTPEntry ::= SEQUENCE {
   gs2352pSystemTimeNTPIndex             Integer32,
   gs2352pSystemTimeNTPServerIPType      INTEGER,
   gs2352pSystemTimeNTPServer            DisplayString,
   gs2352pSystemTimeNTPCurrentMode       INTEGER
}

gs2352pSystemTimeNTPIndex OBJECT-TYPE
   SYNTAX      Integer32(1..5)
   MAX-ACCESS  not-accessible
   STATUS      current
   DESCRIPTION
       " The index of the ntp entry. "
   ::= { gs2352pSystemTimeNTPEntry 1 }

gs2352pSystemTimeNTPServerIPType OBJECT-TYPE
   SYNTAX       INTEGER { ipv4(0), ipv6(1) }
   MAX-ACCESS   read-write
   STATUS       current
   DESCRIPTION
       "Default: 0,
        0 : IPv4,
        1 : IPv6."
   ::= { gs2352pSystemTimeNTPEntry 2 }

gs2352pSystemTimeNTPServer OBJECT-TYPE
   SYNTAX       DisplayString
   MAX-ACCESS   read-write
   STATUS       current
   DESCRIPTION
       "Get/Set the NTP Time Server1. You can use the IP address or domain name."
   ::= { gs2352pSystemTimeNTPEntry 3 }

gs2352pSystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2352pSystemTimeNTPEntry 4 }

gs2352pSystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2352pSystemTimeNTP 2 }
   
gs2352pSystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2352pSystemTimeNTP 3 }
    

gs2352pSystemAccount                                         OBJECT IDENTIFIER ::= { gs2352pSystem 3 }

gs2352pSystemAccountUsers                                    OBJECT IDENTIFIER ::= { gs2352pSystemAccount 1 }

gs2352pSystemAccountUserCreate OBJECT-TYPE
   SYNTAX       INTEGER { none(0), create(1) }
   MAX-ACCESS   read-write
   STATUS       current
   DESCRIPTION
       "default: 0
        0 : None  (read only)
        1 : Create a user account"
   ::= { gs2352pSystemAccountUsers 1 }

gs2352pSystemAccountUsersTable OBJECT-TYPE
   SYNTAX      SEQUENCE OF GS2352PSystemAccountUsersEntry
   MAX-ACCESS  not-accessible
   STATUS      current
   DESCRIPTION
       " "
   ::= { gs2352pSystemAccountUsers 2 }

gs2352pSystemAccountUsersEntry OBJECT-TYPE
   SYNTAX      GS2352PSystemAccountUsersEntry
   MAX-ACCESS  not-accessible
   STATUS      current
   DESCRIPTION
       ""
   INDEX    { gs2352pUserIndex  }
   ::= { gs2352pSystemAccountUsersTable 1 }


GS2352PSystemAccountUsersEntry ::= SEQUENCE {
   gs2352pUserIndex              Integer32 ,
   gs2352pUserName               DisplayString,
   gs2352pPassword               DisplayString,
   gs2352pUserPrivilegeLevel     Integer32 ,
   gs2352pAccountUserRowStatus   INTEGER
}


gs2352pUserIndex OBJECT-TYPE
   SYNTAX      Integer32 (1..20)
   MAX-ACCESS  not-accessible
   STATUS      current
   DESCRIPTION
       " "
   ::= { gs2352pSystemAccountUsersEntry 1 }

gs2352pUserName OBJECT-TYPE
   SYNTAX      DisplayString (SIZE (1..32))
   MAX-ACCESS  read-write
   STATUS      current
   DESCRIPTION
       "Please use a combination of letters, numbers and underscores"
   ::= { gs2352pSystemAccountUsersEntry 2 }

gs2352pPassword OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2352pSystemAccountUsersEntry 3 }

gs2352pUserPrivilegeLevel OBJECT-TYPE
   SYNTAX      Integer32 (1..15)
   MAX-ACCESS  read-write
   STATUS      current
   DESCRIPTION
       "default:1 
        User privilege level range : 1 - 15"
   ::= { gs2352pSystemAccountUsersEntry 4 }

gs2352pAccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2352pSystemAccountUsersEntry 5 }

gs2352pSystemAccountUsersSuperUserPassword OBJECT-TYPE
   SYNTAX      OCTET STRING (SIZE (0..32))
   MAX-ACCESS read-write
   STATUS      current
   DESCRIPTION
        "Super-User Password"
   ::= { gs2352pSystemAccountUsers 1500 }

gs2352pSystemAccountEnforcePasswordRules OBJECT-TYPE
   SYNTAX       INTEGER { yes(0), no(1) }
   MAX-ACCESS   read-write
   STATUS       current
   DESCRIPTION
       "default: 0
        0 : Do not enforce rules
        1 : enforce rules"
   ::= { gs2352pSystemAccountUsers 1501 }

gs2352pSystemAccountPrivilegeLevel                           OBJECT IDENTIFIER ::= { gs2352pSystemAccount 2 }

gs2352pAccountPrivilegeLevel OBJECT-TYPE
   SYNTAX      Integer32 (1..15)
   MAX-ACCESS  read-write
   STATUS      current
   DESCRIPTION
       "Default:15, Range : 1-15. "
   ::= { gs2352pSystemAccountPrivilegeLevel 1 }

gs2352pAggregationPrivilegeLevel OBJECT-TYPE
   SYNTAX      Integer32 (1..15)
   MAX-ACCESS  read-write
   STATUS      current
   DESCRIPTION
       "Default:15, Range : 1-15. "
   ::= { gs2352pSystemAccountPrivilegeLevel 2 }

gs2352pDiagnosticsPrivilegeLevel OBJECT-TYPE
   SYNTAX      Integer32 (1..15)
   MAX-ACCESS  read-write
   STATUS      current
   DESCRIPTION
       "Default:15, Range : 1-15. "
   ::= { gs2352pSystemAccountPrivilegeLevel 3 }

gs2352pEasyportPrivilegeLevel OBJECT-TYPE
   SYNTAX      Integer32 (1..15)
   MAX-ACCESS  read-write
   STATUS      current
   DESCRIPTION
       "Default:15, Range : 1-15. "
   ::= { gs2352pSystemAccountPrivilegeLevel 9 }

gs2352pGARPPrivilegeLevel OBJECT-TYPE
   SYNTAX      Integer32 (1..15)
   MAX-ACCESS  read-write
   STATUS      current
   DESCRIPTION
       "Default:15, Range : 1-15. "
   ::= { gs2352pSystemAccountPrivilegeLevel 10 }

gs2352pGVRPPrivilegeLevel OBJECT-TYPE
   SYNTAX      Integer32 (1..15)
   MAX-ACCESS  read-write
   STATUS      current
   DESCRIPTION
       "Default:15, Range : 1-15. "
   ::= { gs2352pSystemAccountPrivilegeLevel 11 }

gs2352pIPPrivilegeLevel OBJECT-TYPE
   SYNTAX      Integer32 (1..15)
   MAX-ACCESS  read-write
   STATUS      current
   DESCRIPTION
       "Default:15, Range : 1-15. "
   ::= { gs2352pSystemAccountPrivilegeLevel 12 }

gs2352pIPMCSnoopingPrivilegeLevel OBJECT-TYPE
   SYNTAX      Integer32 (1..15)
   MAX-ACCESS  read-write
   STATUS      current
   DESCRIPTION
       "Default:15, Range : 1-15. "
   ::= { gs2352pSystemAccountPrivilegeLevel 13 }

gs2352pLACPPrivilegeLevel OBJECT-TYPE
   SYNTAX      Integer32 (1..15)
   MAX-ACCESS  read-write
   STATUS      current
   DESCRIPTION
       "Default:15, Range : 1-15. "
   ::= { gs2352pSystemAccountPrivilegeLevel 14 }

gs2352pLLDPPrivilegeLevel OBJECT-TYPE
   SYNTAX      Integer32 (1..15)
   MAX-ACCESS  read-write
   STATUS      current
   DESCRIPTION
       "Default:15, Range : 1-15. "
   ::= { gs2352pSystemAccountPrivilegeLevel 15 }

gs2352pLLDPMEDPrivilegeLevel OBJECT-TYPE
   SYNTAX      Integer32 (1..15)
   MAX-ACCESS  read-write
   STATUS      current
   DESCRIPTION
       "Default:15, Range : 1-15. "
   ::= { gs2352pSystemAccountPrivilegeLevel 16 }

gs2352pLoopProtectPrivilegeLevel OBJECT-TYPE
   SYNTAX      Integer32 (1..15)
   MAX-ACCESS  read-write
   STATUS      current
   DESCRIPTION
       "Default:15, Range : 1-15. "
   ::= { gs2352pSystemAccountPrivilegeLevel 17 }

gs2352pMACTablePrivilegeLevel OBJECT-TYPE
   SYNTAX      Integer32 (1..15)
   MAX-ACCESS  read-write
   STATUS      current
   DESCRIPTION
       "Default:15, Range : 1-15. "
   ::= { gs2352pSystemAccountPrivilegeLevel 18 }

gs2352pMVRPrivilegeLevel OBJECT-TYPE
   SYNTAX      Integer32 (1..15)
   MAX-ACCESS  read-write
   STATUS      current
   DESCRIPTION
       "Default:15, Range : 1-15. "
   ::= { gs2352pSystemAccountPrivilegeLevel 22 }

gs2352pMaintenancePrivilegeLevel OBJECT-TYPE
   SYNTAX      Integer32 (1..15)
   MAX-ACCESS  read-write
   STATUS      current
   DESCRIPTION
       "Default:15, Range : 1-15. "
   ::= { gs2352pSystemAccountPrivilegeLevel 24 }

gs2352pMirroringPrivilegeLevel OBJECT-TYPE
   SYNTAX      Integer32 (1..15)
   MAX-ACCESS  read-write
   STATUS      current
   DESCRIPTION
       "Default:15, Range : 1-15. "
   ::= { gs2352pSystemAccountPrivilegeLevel 25 }

gs2352pPortsPrivilegeLevel OBJECT-TYPE
   SYNTAX      Integer32 (1..15)
   MAX-ACCESS  read-write
   STATUS      current
   DESCRIPTION
       "Default:15, Range : 1-15. "
   ::= { gs2352pSystemAccountPrivilegeLevel 27 }

gs2352pPrivateVLANsPrivilegeLevel OBJECT-TYPE
   SYNTAX      Integer32 (1..15)
   MAX-ACCESS  read-write
   STATUS      current
   DESCRIPTION
       "Default:15, Range : 1-15. "
   ::= { gs2352pSystemAccountPrivilegeLevel 28 }

gs2352pQoSPrivilegeLevel OBJECT-TYPE
   SYNTAX      Integer32 (1..15)
   MAX-ACCESS  read-write
   STATUS      current
   DESCRIPTION
       "Default:15, Range : 1-15. "
   ::= { gs2352pSystemAccountPrivilegeLevel 29 }

gs2352pSFlowPrivilegeLevel OBJECT-TYPE
   SYNTAX      Integer32 (1..15)
   MAX-ACCESS  read-write
   STATUS      current
   DESCRIPTION
       "Default:15, Range : 1-15. "
   ::= { gs2352pSystemAccountPrivilegeLevel 30 }

gs2352pSMTPPrivilegeLevel OBJECT-TYPE
   SYNTAX      Integer32 (1..15)
   MAX-ACCESS  read-write
   STATUS      current
   DESCRIPTION
       "Default:15, Range : 1-15. "
   ::= { gs2352pSystemAccountPrivilegeLevel 31 }

gs2352pSNMPPrivilegeLevel OBJECT-TYPE
   SYNTAX      Integer32 (1..15)
   MAX-ACCESS  read-write
   STATUS      current
   DESCRIPTION
       "Default:15, Range : 1-15. "
   ::= { gs2352pSystemAccountPrivilegeLevel 32 }

gs2352pSecurityPrivilegeLevel OBJECT-TYPE
   SYNTAX      Integer32 (1..15)
   MAX-ACCESS  read-write
   STATUS      current
   DESCRIPTION
       "Default:15, Range : 1-15. "
   ::= { gs2352pSystemAccountPrivilegeLevel 33 }

gs2352pSingleIPPrivilegeLevel OBJECT-TYPE
   SYNTAX      Integer32 (1..15)
   MAX-ACCESS  read-write
   STATUS      current
   DESCRIPTION
       "Default:15, Range : 1-15. "
   ::= { gs2352pSystemAccountPrivilegeLevel 34 }

gs2352pSpanningTreePrivilegeLevel OBJECT-TYPE
   SYNTAX      Integer32 (1..15)
   MAX-ACCESS  read-write
   STATUS      current
   DESCRIPTION
       "Default:15, Range : 1-15. "
   ::= { gs2352pSystemAccountPrivilegeLevel 35 }

gs2352pSystemPrivilegeLevel OBJECT-TYPE
   SYNTAX      Integer32 (1..15)
   MAX-ACCESS  read-write
   STATUS      current
   DESCRIPTION
       "Default:15, Range : 1-15. "
   ::= { gs2352pSystemAccountPrivilegeLevel 36 }

gs2352pTrapEventPrivilegeLevel OBJECT-TYPE
   SYNTAX      Integer32 (1..15)
   MAX-ACCESS  read-write
   STATUS      current
   DESCRIPTION
       "Default:15, Range : 1-15. "
   ::= { gs2352pSystemAccountPrivilegeLevel 37 }

gs2352pUPnPPrivilegeLevel OBJECT-TYPE
   SYNTAX      Integer32 (1..15)
   MAX-ACCESS  read-write
   STATUS      current
   DESCRIPTION
       "Default:15, Range : 1-15. "
   ::= { gs2352pSystemAccountPrivilegeLevel 38 }

gs2352pVCLPrivilegeLevel OBJECT-TYPE
   SYNTAX      Integer32 (1..15)
   MAX-ACCESS  read-write
   STATUS      current
   DESCRIPTION
       "Default:15, Range : 1-15. "
   ::= { gs2352pSystemAccountPrivilegeLevel 39 }

gs2352pVLANsPrivilegeLevel OBJECT-TYPE
   SYNTAX      Integer32 (1..15)
   MAX-ACCESS  read-write
   STATUS      current
   DESCRIPTION
       "Default:15, Range : 1-15. "
   ::= { gs2352pSystemAccountPrivilegeLevel 41 }

gs2352pVoiceVLANPrivilegeLevel OBJECT-TYPE
   SYNTAX      Integer32 (1..15)
   MAX-ACCESS  read-write
   STATUS      current
   DESCRIPTION
       "Default:15, Range : 1-15. "
   ::= { gs2352pSystemAccountPrivilegeLevel 42 }
   
gs2352pPOEPrivilegeLevel OBJECT-TYPE
   SYNTAX      Integer32 (1..15)
   MAX-ACCESS  read-write
   STATUS      current
   DESCRIPTION
       "Default:15, Range : 1-15. "
   ::= { gs2352pSystemAccountPrivilegeLevel 43 }


gs2352pIP                                                    OBJECT IDENTIFIER ::= { gs2352pSystem 4 }

gs2352pIPv4                                                  OBJECT IDENTIFIER ::= { gs2352pIP 1 }

gs2352pIPv4Configured                                                  OBJECT IDENTIFIER ::= { gs2352pIPv4 1 }

gs2352pIpv4DHCPClient OBJECT-TYPE
   SYNTAX      INTEGER { disable(0), enable(1) }
   MAX-ACCESS  read-write
   STATUS      current
   DESCRIPTION
       "default:0
       0: disable
       1: enable"
   ::= { gs2352pIPv4Configured 1 }

gs2352pIPv4Address OBJECT-TYPE
   SYNTAX      IpAddress
   MAX-ACCESS  read-write
   STATUS      current
   DESCRIPTION
       ""
   ::= { gs2352pIPv4Configured 2 }

gs2352pIPv4Mask OBJECT-TYPE
   SYNTAX      IpAddress
   MAX-ACCESS  read-write
   STATUS      current
   DESCRIPTION
       ""
   ::= { gs2352pIPv4Configured 3 }

gs2352pIPv4Gateway OBJECT-TYPE
   SYNTAX      IpAddress
   MAX-ACCESS  read-write
   STATUS      current
   DESCRIPTION
       ""
   ::= { gs2352pIPv4Configured 4 }

gs2352pIPv4VLANId OBJECT-TYPE
   SYNTAX      Integer32(1..4094)
   MAX-ACCESS  read-write
   STATUS      current
   DESCRIPTION
       "default:1"
   ::= { gs2352pIPv4Configured 5 }

gs2352pIPv4DNSServer OBJECT-TYPE
   SYNTAX      IpAddress
   MAX-ACCESS  read-write
   STATUS      current
   DESCRIPTION
       ""
   ::= { gs2352pIPv4Configured 6 }

gs2352pIPv4DNSProxy OBJECT-TYPE
   SYNTAX      INTEGER { disable(0), enable(1) }
   MAX-ACCESS  read-write
   STATUS      current
   DESCRIPTION
       "0:disable, 1:enable "
   ::= { gs2352pIPv4Configured 7 }

gs2352pIPv4Current                                                  OBJECT IDENTIFIER ::= { gs2352pIPv4 2 }

gs2352pIpv4CurrentDHCPClient OBJECT-TYPE
   SYNTAX      INTEGER { none(0), renew(1) }
   MAX-ACCESS  read-write
   STATUS      current
   DESCRIPTION
       "default:0
       0: none (for read)
       1: renew"
   ::= { gs2352pIPv4Current 1 }

gs2352pIPv4CurrentAddress OBJECT-TYPE
   SYNTAX      IpAddress
   MAX-ACCESS  read-only
   STATUS      current
   DESCRIPTION
       ""
   ::= { gs2352pIPv4Current 2 }

gs2352pIPv4CurrentMask OBJECT-TYPE
   SYNTAX      IpAddress
   MAX-ACCESS  read-only
   STATUS      current
   DESCRIPTION
       ""
   ::= { gs2352pIPv4Current 3 }

gs2352pIPv4CurrentGateway OBJECT-TYPE
   SYNTAX      IpAddress
   MAX-ACCESS  read-only
   STATUS      current
   DESCRIPTION
       ""
   ::= { gs2352pIPv4Current 4 }

gs2352pIPv4CurrentVLANId OBJECT-TYPE
   SYNTAX      Integer32(1..4094)
   MAX-ACCESS  read-only
   STATUS      current
   DESCRIPTION
       "default:1"
   ::= { gs2352pIPv4Current 5 }

gs2352pIPv4CurrentDNSServer OBJECT-TYPE
   SYNTAX      IpAddress
   MAX-ACCESS  read-only
   STATUS      current
   DESCRIPTION
       ""
   ::= { gs2352pIPv4Current 6 }


gs2352pIPv6                                                  OBJECT IDENTIFIER ::= { gs2352pIP 2 }

gs2352pIPv6Configured                                                  OBJECT IDENTIFIER ::= { gs2352pIPv6 1 }

gs2352pIpv6AutoConfiguration OBJECT-TYPE
   SYNTAX      INTEGER { disable(0), enable(1) }
   MAX-ACCESS  read-write
   STATUS      current
   DESCRIPTION
       "default:0
       0: disable
       1: enable"
   ::= { gs2352pIPv6Configured 1 }

gs2352pIpv6Address OBJECT-TYPE
   SYNTAX      DisplayString (SIZE (0..30))
   MAX-ACCESS  read-write
   STATUS      current
   DESCRIPTION
       ""
   ::= { gs2352pIPv6Configured 2 }

gs2352pIpv6Prefix OBJECT-TYPE
   SYNTAX      Integer32(1..128)
   MAX-ACCESS  read-write
   STATUS      current
   DESCRIPTION
       "default: 96"
   ::= { gs2352pIPv6Configured 3 }

gs2352pIpv6Gateway OBJECT-TYPE
   SYNTAX      DisplayString (SIZE (0..30))
   MAX-ACCESS  read-write
   STATUS      current
   DESCRIPTION
       " "
   ::= { gs2352pIPv6Configured 4 }

gs2352pIPv6Current                                                  OBJECT IDENTIFIER ::= { gs2352pIPv6 2 }

gs2352pIpv6CurrentAutoConfiguration OBJECT-TYPE
   SYNTAX      INTEGER { disable(0), enable(1) }
   MAX-ACCESS  read-only
   STATUS      current
   DESCRIPTION
       "default:0
       0: disable
       1: enable"
   ::= { gs2352pIPv6Current 1 }

gs2352pIpv6CurrentAddress OBJECT-TYPE
   SYNTAX      DisplayString (SIZE (0..30))
   MAX-ACCESS  read-only
   STATUS      current
   DESCRIPTION
       ""
   ::= { gs2352pIPv6Current 2 }


gs2352pIpv6CurrentLinkLocalAddress OBJECT-TYPE
   SYNTAX      DisplayString(SIZE (0..30))
   MAX-ACCESS  read-only
   STATUS      current
   DESCRIPTION
       ""
   ::= { gs2352pIPv6Current 3 }


gs2352pIpv6CurrentPrefix OBJECT-TYPE
   SYNTAX      DisplayString(SIZE (0..64))
   MAX-ACCESS  read-only
   STATUS      current
   DESCRIPTION
       ""
   ::= { gs2352pIPv6Current 4 }

gs2352pIpv6CurrentGateway OBJECT-TYPE
   SYNTAX      DisplayString (SIZE (0..30))
   MAX-ACCESS  read-only
   STATUS      current
   DESCRIPTION
       " "
   ::= { gs2352pIPv6Current 5 }

gs2352pSyslog                                                OBJECT IDENTIFIER ::= { gs2352pSystem 5 }

gs2352pSyslogConf                                            OBJECT IDENTIFIER ::= { gs2352pSyslog 1 }

gs2352pServerMode OBJECT-TYPE
   SYNTAX      INTEGER { disable(0), enable(1) }
   MAX-ACCESS  read-write
   STATUS      current
   DESCRIPTION
       "default: 0
       0: disable
       1: enable "
   ::= { gs2352pSyslogConf 1 }

gs2352pServerAddress1 OBJECT-TYPE
   SYNTAX      IpAddress
   MAX-ACCESS  read-write
   STATUS      current
   DESCRIPTION
       " "
   ::= { gs2352pSyslogConf 2 }

gs2352pServerAddress2 OBJECT-TYPE
   SYNTAX      IpAddress
   MAX-ACCESS  read-write
   STATUS      current
   DESCRIPTION
       " "
   ::= { gs2352pSyslogConf 3 }

gs2352pSyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2352pSyslogConf 4 }

gs2352pSyslogDetailedInfo                                    OBJECT IDENTIFIER ::= { gs2352pSyslog 2 }

gs2352pSyslogDetailedInfoClear OBJECT-TYPE
   SYNTAX      INTEGER { none(0), clear(1) }
   MAX-ACCESS  read-write
   STATUS      current
   DESCRIPTION
      "default: 0
       0 : None  (read only)
       1 : Clear Syslog"
   ::= { gs2352pSyslogDetailedInfo 1 }

gs2352pSyslogDetailedInfoTable OBJECT-TYPE
  SYNTAX      SEQUENCE OF GS2352PSyslogDetailedInfoEntry
  MAX-ACCESS  not-accessible
  STATUS      current
  DESCRIPTION
           " "
       ::= { gs2352pSyslogDetailedInfo 2 }

gs2352pSyslogDetailedInfoEntry OBJECT-TYPE
   SYNTAX      GS2352PSyslogDetailedInfoEntry
   MAX-ACCESS  not-accessible
   STATUS      current
   DESCRIPTION
           ""
   INDEX    { gs2352pSyslogDetailedInfoIndex  }
   ::= { gs2352pSyslogDetailedInfoTable 1 }

GS2352PSyslogDetailedInfoEntry ::= SEQUENCE {
   gs2352pSyslogDetailedInfoIndex       Integer32,
   gs2352pSyslogDetailedInfoLevel       DisplayString,
   gs2352pSyslogDetailedInfoTime        DisplayString,
   gs2352pSyslogDetailedInfoMessage     DisplayString
}

gs2352pSyslogDetailedInfoIndex OBJECT-TYPE
   SYNTAX      Integer32(1..1024)
   MAX-ACCESS  not-accessible
   STATUS      current
   DESCRIPTION
       " "
   ::= { gs2352pSyslogDetailedInfoEntry 1 }
   
gs2352pSyslogDetailedInfoLevel OBJECT-TYPE
   SYNTAX      DisplayString
   MAX-ACCESS  read-only
   STATUS      current
   DESCRIPTION
       " "
   ::= { gs2352pSyslogDetailedInfoEntry 2 }

gs2352pSyslogDetailedInfoTime OBJECT-TYPE
   SYNTAX      DisplayString(SIZE (0..20))
   MAX-ACCESS  read-only
   STATUS      current
   DESCRIPTION
       " "
   ::= { gs2352pSyslogDetailedInfoEntry 3 }

gs2352pSyslogDetailedInfoMessage OBJECT-TYPE
   SYNTAX      DisplayString
   MAX-ACCESS  read-only
   STATUS      current
   DESCRIPTION
       " "
   ::= { gs2352pSyslogDetailedInfoEntry 4 }


gs2352pSnmp                                                OBJECT IDENTIFIER ::= { gs2352pSystem 6 }

gs2352pSnmpConf                                            OBJECT IDENTIFIER ::= { gs2352pSnmp 1 }

gs2352pGetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2352pSnmpConf 1 }

gs2352pGetCommunity OBJECT-TYPE
   SYNTAX       DisplayString
   MAX-ACCESS   read-write
   STATUS       current
   DESCRIPTION
       "Get/Set the get-community of the SNMP."
   ::= { gs2352pSnmpConf 2 }

gs2352pSetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2352pSnmpConf 3 }

gs2352pSetCommunity OBJECT-TYPE
   SYNTAX       DisplayString
   MAX-ACCESS   read-write
   STATUS       current
   DESCRIPTION
       "Get/Set the set-community of the SNMP."
   ::= { gs2352pSnmpConf 4 }

gs2352pGetCommunityConfTable OBJECT-TYPE
   SYNTAX      SEQUENCE OF GS2352PGetCommunityConfEntry
   MAX-ACCESS  not-accessible
   STATUS      current
   DESCRIPTION
       " Show get-community of the SNMP. "
   ::= { gs2352pSnmpConf 5 }

gs2352pGetCommunityConfEntry OBJECT-TYPE
   SYNTAX      GS2352PGetCommunityConfEntry
   MAX-ACCESS  not-accessible
   STATUS      current
   DESCRIPTION
       ""
   INDEX    { gs2352pCommunityConfIndex  }
   ::= { gs2352pGetCommunityConfTable 1 }

GS2352PGetCommunityConfEntry ::= SEQUENCE {
   gs2352pCommunityConfIndex				Integer32,
   gs2352pCommunityConfGetCommunity			DisplayString
}

gs2352pCommunityConfIndex OBJECT-TYPE
   SYNTAX      Integer32(1..4095)
   MAX-ACCESS  not-accessible
   STATUS      current
   DESCRIPTION
       " index, range : 1 - 5. "
   ::= { gs2352pGetCommunityConfEntry 1 }
   
gs2352pCommunityConfGetCommunity OBJECT-TYPE
   SYNTAX      DisplayString
   MAX-ACCESS  read-write
   STATUS      current
   DESCRIPTION
       " Get/Set the get-community of the SNMP."
   ::= { gs2352pGetCommunityConfEntry 2 }

gs2352pTrapHostConfTable OBJECT-TYPE
   SYNTAX      SEQUENCE OF GS2352PTrapHostConfEntry
   MAX-ACCESS  not-accessible
   STATUS      current
   DESCRIPTION
       "A list of trap host entry. The numbers of entries are given by the value of gs2352pTrapHostConfNumber."
   ::= { gs2352pSnmpConf 6 }
   
gs2352pTrapHostConfEntry OBJECT-TYPE
   SYNTAX      GS2352PTrapHostConfEntry
   MAX-ACCESS  not-accessible
   STATUS      current
   DESCRIPTION
       "This is the entry information for trap host."
   INDEX    { gs2352pTrapHostConfIndex  }
   ::= { gs2352pTrapHostConfTable 1 }

GS2352PTrapHostConfEntry ::= SEQUENCE {
    gs2352pTrapHostConfIndex             Integer32,
    gs2352pTrapHostConfVersion           INTEGER,
    gs2352pTrapHostConfIPType            INTEGER,
    gs2352pTrapHostConfIP                DisplayString,
    gs2352pTrapHostConfPort              Integer32,
    gs2352pTrapHostConfCommunity         DisplayString,
    gs2352pTrapHostConfSeverityLevel     INTEGER,
    gs2352pTrapHostConfSecurityLevel     INTEGER,
    gs2352pTrapHostConfAuthPtc           INTEGER,
    gs2352pTrapHostConfAuthPassword      DisplayString,
    gs2352pTrapHostConfPrivPtc           INTEGER,
    gs2352pTrapHostConfPrivPassword      DisplayString,
    gs2352pTrapHostConfCurrentMode       INTEGER
}
   
gs2352pTrapHostConfIndex OBJECT-TYPE
   SYNTAX      Integer32(1..6)
   MAX-ACCESS  not-accessible
   STATUS      current
   DESCRIPTION
       " The index of the trap host entry. "
   ::= { gs2352pTrapHostConfEntry 1 }

gs2352pTrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2352pTrapHostConfEntry 2 }

gs2352pTrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2352pTrapHostConfEntry 3 }

gs2352pTrapHostConfIP OBJECT-TYPE
   SYNTAX       DisplayString
   MAX-ACCESS   read-write
   STATUS       current
   DESCRIPTION
       "This is the IP of the trap host."
   ::= { gs2352pTrapHostConfEntry 4 }

gs2352pTrapHostConfPort OBJECT-TYPE
   SYNTAX       Integer32(1..65535)
   MAX-ACCESS   read-write
   STATUS       current
   DESCRIPTION
       "This is the receiving-port number of the trap host.
        range : 1 - 65535."
   ::= { gs2352pTrapHostConfEntry 5 }

gs2352pTrapHostConfCommunity OBJECT-TYPE
   SYNTAX       DisplayString (SIZE (1..32))
   MAX-ACCESS   read-write
   STATUS       current
   DESCRIPTION
       "The community/security name for the trap PDU."
   ::= { gs2352pTrapHostConfEntry 6 }

gs2352pTrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2352pTrapHostConfEntry 7 }

gs2352pTrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2352pTrapHostConfEntry 8 }

gs2352pTrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2352pTrapHostConfEntry 9 }

gs2352pTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2352pTrapHostConfEntry 10 }

gs2352pTrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2352pTrapHostConfEntry 11 }

gs2352pTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2352pTrapHostConfEntry 12 }

gs2352pTrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2352pTrapHostConfEntry 13 }


gs2352pSnmpSystem                                          OBJECT IDENTIFIER ::= { gs2352pSnmp 2 }

gs2352pSnmpState OBJECT-TYPE
   SYNTAX       INTEGER { disable(0), enable(1) }
   MAX-ACCESS   read-write
   STATUS       current
   DESCRIPTION
       "Get/Set the state of the SNMP.
        default : 1, 0: disable, 1: enable. "
   ::= { gs2352pSnmpSystem 1 }

gs2352pSnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2352pSnmpSystem 2 }

gs2352pSnmpCommunities                                          OBJECT IDENTIFIER ::= { gs2352pSnmp 3 }

gs2352pSnmpCommunitiesCreate OBJECT-TYPE
   SYNTAX       INTEGER { none(0), create(1) }
   MAX-ACCESS   read-write
   STATUS       current
   DESCRIPTION
       "default: 0
        0 : None  (read only)
        1 : Create entry"
   ::= { gs2352pSnmpCommunities 1 }

gs2352pSnmpCommunitiesTable OBJECT-TYPE
   SYNTAX      SEQUENCE OF GS2352PSnmpCommunitiesEntry
   MAX-ACCESS  not-accessible
   STATUS      current
   DESCRIPTION
       " Create SNMPv1/v2 Communities entry."
   ::= { gs2352pSnmpCommunities 2 }

gs2352pSnmpCommunitiesEntry OBJECT-TYPE
   SYNTAX      GS2352PSnmpCommunitiesEntry
   MAX-ACCESS  not-accessible
   STATUS      current
   DESCRIPTION
       ""
   INDEX    { gs2352pSnmpCommunitiesIndex  }
   ::= { gs2352pSnmpCommunitiesTable 1 }

GS2352PSnmpCommunitiesEntry ::= SEQUENCE {
   gs2352pSnmpCommunitiesIndex          Integer32,
   gs2352pSnmpCommunitiesCommunity      DisplayString,
   gs2352pSnmpCommunitiesUserName       DisplayString,
   gs2352pSnmpCommunitiesSourceIP       IpAddress,
   gs2352pSnmpCommunitiesSourceMask     IpAddress,
   gs2352pSnmpCommunitiesRowStatus      INTEGER
}

gs2352pSnmpCommunitiesIndex OBJECT-TYPE
   SYNTAX      Integer32(1..4)
   MAX-ACCESS  not-accessible
   STATUS      current
   DESCRIPTION
       " "
   ::= { gs2352pSnmpCommunitiesEntry 1 }

gs2352pSnmpCommunitiesCommunity OBJECT-TYPE
   SYNTAX      DisplayString (SIZE (1..32))
   MAX-ACCESS  read-write
   STATUS      current
   DESCRIPTION
       "Up to 32 characters describing Community."
   ::= { gs2352pSnmpCommunitiesEntry 2 }

gs2352pSnmpCommunitiesUserName OBJECT-TYPE
   SYNTAX      DisplayString (SIZE (1..32))
   MAX-ACCESS  read-write
   STATUS      current
   DESCRIPTION
       " Up to 32 characters describing User Name. "
   ::= { gs2352pSnmpCommunitiesEntry 3 }

gs2352pSnmpCommunitiesSourceIP OBJECT-TYPE
   SYNTAX      IpAddress
   MAX-ACCESS  read-write
   STATUS      current
   DESCRIPTION
       " SNMP access source ip. "
   ::= { gs2352pSnmpCommunitiesEntry 4 }

gs2352pSnmpCommunitiesSourceMask OBJECT-TYPE
   SYNTAX      IpAddress
   MAX-ACCESS  read-write
   STATUS      current
   DESCRIPTION
       " SNMP access source address mask. "
   ::= { gs2352pSnmpCommunitiesEntry 5 }

gs2352pSnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2352pSnmpCommunitiesEntry 6 }


gs2352pSnmpUsers                                          OBJECT IDENTIFIER ::= { gs2352pSnmp 4 }

gs2352pSnmpUsersCreate OBJECT-TYPE
   SYNTAX       INTEGER { none(0), create(1) }
   MAX-ACCESS   read-write
   STATUS       current
   DESCRIPTION
       "default: 0
        0 : None  (read only)
        1 : Create entry"
   ::= { gs2352pSnmpUsers 1 }

gs2352pSnmpUsersTable OBJECT-TYPE
   SYNTAX      SEQUENCE OF GS2352PSnmpUsersEntry
   MAX-ACCESS  not-accessible
   STATUS      current
   DESCRIPTION
       " Create SNMPv3 users entry."
   ::= { gs2352pSnmpUsers 2 }

gs2352pSnmpUsersEntry OBJECT-TYPE
   SYNTAX      GS2352PSnmpUsersEntry
   MAX-ACCESS  not-accessible
   STATUS      current
   DESCRIPTION
       ""
   INDEX    { gs2352pSnmpUsersIndex  }
   ::= { gs2352pSnmpUsersTable 1 }

GS2352PSnmpUsersEntry ::= SEQUENCE {
   gs2352pSnmpUsersIndex                    Integer32,
   gs2352pSnmpUsersUserName                 DisplayString,
   gs2352pSnmpUsersSecurityLevel            INTEGER,
   gs2352pSnmpUsersAuthenticationProtocol   INTEGER,
   gs2352pSnmpUsersAuthenticationPassword   DisplayString,
   gs2352pSnmpUsersPrivacyProtocol          INTEGER,
   gs2352pSnmpUsersPrivacyPassword          DisplayString,
   gs2352pSnmpUsersRowStatus                INTEGER
}

gs2352pSnmpUsersIndex OBJECT-TYPE
   SYNTAX      Integer32(1..10)
   MAX-ACCESS  not-accessible
   STATUS      current
   DESCRIPTION
       " "
   ::= { gs2352pSnmpUsersEntry 1 }

gs2352pSnmpUsersUserName OBJECT-TYPE
   SYNTAX      DisplayString (SIZE (1..32))
   MAX-ACCESS  read-write
   STATUS      current
   DESCRIPTION
       "Up to 32 characters describing User Name."
   ::= { gs2352pSnmpUsersEntry 2 }

gs2352pSnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy. 
         3: Authentication and privacy. "
   ::= { gs2352pSnmpUsersEntry 3 }

gs2352pSnmpUsersAuthenticationProtocol OBJECT-TYPE
   SYNTAX      INTEGER { none(0), md5(1), sha(2) }
   MAX-ACCESS  read-write
   STATUS      current
   DESCRIPTION
       " 0: None.
         1: MD5.
         2: SHA "
   ::= { gs2352pSnmpUsersEntry 4 }

gs2352pSnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2352pSnmpUsersEntry 5 }
   
gs2352pSnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2352pSnmpUsersEntry 6 }

gs2352pSnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2352pSnmpUsersEntry 7 }
   
gs2352pSnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2352pSnmpUsersEntry 8 }


gs2352pSnmpGroups                                          OBJECT IDENTIFIER ::= { gs2352pSnmp 5 }

gs2352pSnmpGroupsCreate OBJECT-TYPE
   SYNTAX       INTEGER { none(0), create(1) }
   MAX-ACCESS   read-write
   STATUS       current
   DESCRIPTION
       "default: 0
        0 : None  (read only)
        1 : Create entry"
   ::= { gs2352pSnmpGroups 1 }

gs2352pSnmpGroupsTable OBJECT-TYPE
   SYNTAX      SEQUENCE OF GS2352PSnmpGroupsEntry
   MAX-ACCESS  not-accessible
   STATUS      current
   DESCRIPTION
       " Create SNMPv3 groups entry."
   ::= { gs2352pSnmpGroups 2 }

gs2352pSnmpGroupsEntry OBJECT-TYPE
   SYNTAX      GS2352PSnmpGroupsEntry
   MAX-ACCESS  not-accessible
   STATUS      current
   DESCRIPTION
       ""
   INDEX    { gs2352pSnmpGroupsIndex  }
   ::= { gs2352pSnmpGroupsTable 1 }

GS2352PSnmpGroupsEntry ::= SEQUENCE {
   gs2352pSnmpGroupsIndex           Integer32,
   gs2352pSnmpGroupsSecurityModel   INTEGER,
   gs2352pSnmpGroupsSecurityName    DisplayString,
   gs2352pSnmpGroupsGroupName       DisplayString,
   gs2352pSnmpGroupsRowStatus       INTEGER
}

gs2352pSnmpGroupsIndex OBJECT-TYPE
   SYNTAX      Integer32(1..14)
   MAX-ACCESS  not-accessible
   STATUS      current
   DESCRIPTION
       " "
   ::= { gs2352pSnmpGroupsEntry 1 }

gs2352pSnmpGroupsSecurityModel OBJECT-TYPE
   SYNTAX      INTEGER { v1(1), v2c(2), usm(3) }
   MAX-ACCESS  read-write
   STATUS      current
   DESCRIPTION
       " 1: v1.
         2: v2c. 
         3: usm."
   ::= { gs2352pSnmpGroupsEntry 2 }

gs2352pSnmpGroupsSecurityName OBJECT-TYPE
   SYNTAX      DisplayString (SIZE (1..32))
   MAX-ACCESS  read-write
   STATUS      current
   DESCRIPTION
       "Up to 32 characters describing User Name."
   ::= { gs2352pSnmpGroupsEntry 3 }

gs2352pSnmpGroupsGroupName OBJECT-TYPE
   SYNTAX      DisplayString (SIZE (1..32))
   MAX-ACCESS  read-write
   STATUS      current
   DESCRIPTION
       "Up to 32 characters describing Group Name."
   ::= { gs2352pSnmpGroupsEntry 4 }
   
gs2352pSnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2352pSnmpGroupsEntry 5 }

gs2352pSnmpViews                                              OBJECT IDENTIFIER ::= { gs2352pSnmp 6 }

gs2352pSnmpViewsCreate OBJECT-TYPE
   SYNTAX       INTEGER { none(0), create(1) }
   MAX-ACCESS   read-write
   STATUS       current
   DESCRIPTION
       "default: 0
        0 : None  (read only)
        1 : Create entry"
   ::= { gs2352pSnmpViews 1 }

gs2352pSnmpViewsTable OBJECT-TYPE
   SYNTAX      SEQUENCE OF GS2352PSnmpViewsEntry
   MAX-ACCESS  not-accessible
   STATUS      current
   DESCRIPTION
       " Create SNMPv1/v2 Views entry."
   ::= { gs2352pSnmpViews 2 }

gs2352pSnmpViewsEntry OBJECT-TYPE
   SYNTAX      GS2352PSnmpViewsEntry
   MAX-ACCESS  not-accessible
   STATUS      current
   DESCRIPTION
       ""
   INDEX    { gs2352pSnmpViewsIndex  }
   ::= { gs2352pSnmpViewsTable 1 }

GS2352PSnmpViewsEntry ::= SEQUENCE {
   gs2352pSnmpViewsIndex        Integer32,
   gs2352pSnmpViewsName         DisplayString,
   gs2352pSnmpViewsType         INTEGER,
   gs2352pSnmpViewsOIDSubtree   DisplayString,
   gs2352pSnmpViewsRowStatus    INTEGER
}
   
gs2352pSnmpViewsIndex OBJECT-TYPE
   SYNTAX      Integer32(1..4)
   MAX-ACCESS  not-accessible
   STATUS      current
   DESCRIPTION
       " "
   ::= { gs2352pSnmpViewsEntry 1 }

gs2352pSnmpViewsName OBJECT-TYPE
   SYNTAX      DisplayString (SIZE (1..32))
   MAX-ACCESS  read-write
   STATUS      current
   DESCRIPTION
       "Up to 32 characters describing view Name."
   ::= { gs2352pSnmpViewsEntry 2 }   

gs2352pSnmpViewsType OBJECT-TYPE
   SYNTAX      INTEGER { included(1), excluded(2) }
   MAX-ACCESS  read-write
   STATUS      current
   DESCRIPTION
       "1: included, An optional flag to indicate that this view subtree should be included. 
	   2: excluded, An optional flag to indicate that this view subtree should be excluded."
   ::= { gs2352pSnmpViewsEntry 3 } 
   
gs2352pSnmpViewsOIDSubtree OBJECT-TYPE
   SYNTAX      DisplayString (SIZE (1..128))
   MAX-ACCESS  read-write
   STATUS      current
   DESCRIPTION
       "The OID defining the root of the subtree to add to the named view."
   ::= { gs2352pSnmpViewsEntry 4 } 

gs2352pSnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2352pSnmpViewsEntry 5 }   


gs2352pSnmpAccess                                          OBJECT IDENTIFIER ::= { gs2352pSnmp 7 }

gs2352pSnmpAccessCreate OBJECT-TYPE
   SYNTAX       INTEGER { none(0), create(1) }
   MAX-ACCESS   read-write
   STATUS       current
   DESCRIPTION
       "default: 0
        0 : None  (read only)
        1 : Create entry"
   ::= { gs2352pSnmpAccess 1 }

gs2352pSnmpAccessTable OBJECT-TYPE
   SYNTAX      SEQUENCE OF GS2352PSnmpAccessEntry
   MAX-ACCESS  not-accessible
   STATUS      current
   DESCRIPTION
       " Create SNMPv3 Access entry."
   ::= { gs2352pSnmpAccess 2 }

gs2352pSnmpAccessEntry OBJECT-TYPE
   SYNTAX      GS2352PSnmpAccessEntry
   MAX-ACCESS  not-accessible
   STATUS      current
   DESCRIPTION
       ""
   INDEX    { gs2352pSnmpAccessIndex  }
   ::= { gs2352pSnmpAccessTable 1 }

GS2352PSnmpAccessEntry ::= SEQUENCE {
   gs2352pSnmpAccessIndex             Integer32,
   gs2352pSnmpAccessGroupName         DisplayString,
   gs2352pSnmpAccessSecurityModel     INTEGER,
   gs2352pSnmpAccessSecurityLevel     INTEGER,
   gs2352pSnmpAccessReadViewName      DisplayString,
   gs2352pSnmpAccessWriteViewName     DisplayString,  
   gs2352pSnmpAccessRowStatus         INTEGER
}

gs2352pSnmpAccessIndex OBJECT-TYPE
   SYNTAX      Integer32(1..14)
   MAX-ACCESS  not-accessible
   STATUS      current
   DESCRIPTION
       " "
   ::= { gs2352pSnmpAccessEntry 1 }

gs2352pSnmpAccessGroupName OBJECT-TYPE
   SYNTAX      DisplayString (SIZE (1..32))
   MAX-ACCESS  read-write
   STATUS      current
   DESCRIPTION
       "Up to 32 characters describing Group Name."
   ::= { gs2352pSnmpAccessEntry 2 }

gs2352pSnmpAccessSecurityModel OBJECT-TYPE
   SYNTAX      INTEGER { any(0), v1(1), v2c(2), usm(3) }
   MAX-ACCESS  read-write
   STATUS      current
   DESCRIPTION
       " 0: any.
         1: v1.
         2: v2c. 
         3: usm."
   ::= { gs2352pSnmpAccessEntry 3 }

gs2352pSnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy. 
         3: Authentication and privacy. "
   ::= { gs2352pSnmpAccessEntry 4 }

gs2352pSnmpAccessReadViewName OBJECT-TYPE
   SYNTAX      DisplayString (SIZE (1..32))
   MAX-ACCESS  read-write
   STATUS      current
   DESCRIPTION
       "Up to 32 characters describing Read View Name.
        None is reserved for Empty."
   ::= { gs2352pSnmpAccessEntry 5 }
   
gs2352pSnmpAccessWriteViewName OBJECT-TYPE
   SYNTAX      DisplayString (SIZE (1..32))
   MAX-ACCESS  read-write
   STATUS      current
   DESCRIPTION
       "Up to 32 characters describing Write View Name.
        None is reserved for Empty."
   ::= { gs2352pSnmpAccessEntry 6 }
   
gs2352pSnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2352pSnmpAccessEntry 7 }


----------------------------------------------------------------------------------------------------

gs2352pConfiguration                                         OBJECT IDENTIFIER ::= { lancomGS2352P 2 }

gs2352pPort                                                  OBJECT IDENTIFIER ::= { gs2352pConfiguration 1 }

gs2352pPortConfigurationTable OBJECT-TYPE
   SYNTAX      SEQUENCE OF GS2352PPortConfigurationEntry
   MAX-ACCESS  not-accessible
   STATUS      current
   DESCRIPTION
       " Show port configurations. "
   ::= { gs2352pPort 1 }

gs2352pPortConfigurationEntry OBJECT-TYPE
   SYNTAX      GS2352PPortConfigurationEntry
   MAX-ACCESS  not-accessible
   STATUS      current
   DESCRIPTION
       ""
   INDEX    { gs2352pPortConfPort  }
   ::= { gs2352pPortConfigurationTable 1 }

GS2352PPortConfigurationEntry ::= SEQUENCE {
   gs2352pPortConfPort                     Integer32,
   gs2352pPortConfPortMedia                DisplayString,
   gs2352pPortConfLink                     DisplayString,
   gs2352pPortConfCurrentSpeed             DisplayString,
   gs2352pPortConfSpeed                    INTEGER,
   gs2352pPortConfCurrentFlowControlRx     INTEGER,
   gs2352pPortConfCurrentFlowControlTx     INTEGER,
   gs2352pPortConfFlowControl              INTEGER,
   gs2352pPortConfMaxFrameSize             Integer32,
   gs2352pPortConfExcessiveCollisionMode   INTEGER,
   gs2352pPortConfPowerControl             INTEGER,
   gs2352pPortConfDescription              DisplayString
}

gs2352pPortConfPort OBJECT-TYPE
   SYNTAX      Integer32(1..4095)
   MAX-ACCESS  not-accessible
   STATUS      current
   DESCRIPTION
       " port, range : 1 - port number. "
   ::= { gs2352pPortConfigurationEntry 1 }

gs2352pPortConfPortMedia OBJECT-TYPE
   SYNTAX      DisplayString(SIZE (1..4))
   MAX-ACCESS  read-only
   STATUS      current
   DESCRIPTION
       " Show port media. "
   ::= { gs2352pPortConfigurationEntry 2 }

gs2352pPortConfLink OBJECT-TYPE
   SYNTAX      DisplayString(SIZE (2..4))
   MAX-ACCESS  read-only
   STATUS      current
   DESCRIPTION
       " The current link state. "
   ::= { gs2352pPortConfigurationEntry 3 }

gs2352pPortConfCurrentSpeed OBJECT-TYPE
   SYNTAX      DisplayString(SIZE (6..12))
   MAX-ACCESS  read-only
   STATUS      current
   DESCRIPTION
       " The current link speed of the port. "
   ::= { gs2352pPortConfigurationEntry 4 }

gs2352pPortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11),
                    speed10GFull(12)
                }
   MAX-ACCESS  read-write
   STATUS      current
   DESCRIPTION
       "default: 1,
        0: disable state, 
        1: auto, 
        2: 10 Half, 
        3: 10 Full, 
        4: 100 Half, 
        5: 100 Full, 
        6: 1G full, 
        only 'Dual Media' port have 7-11 option. 
        Dual Media port default: 7,  
        7: SFP_Auto_AMS, 
        8: 100FX_AMS, 
        9: 1000X_AMS, 
        10: 100FX, 
        11: 1000X,
        12: 10G Full. "
   ::= { gs2352pPortConfigurationEntry 5 }

gs2352pPortConfCurrentFlowControlRx OBJECT-TYPE
   SYNTAX      INTEGER { disable(0), enable(1), noSupport(2) }
   MAX-ACCESS  read-only
   STATUS      current
   DESCRIPTION
       "0: disable
        1: enable
        2: no support.  "
   ::= { gs2352pPortConfigurationEntry 6 }

gs2352pPortConfCurrentFlowControlTx OBJECT-TYPE
   SYNTAX      INTEGER { disable(0), enable(1), noSupport(2) }
   MAX-ACCESS  read-only
   STATUS      current
   DESCRIPTION
       "0: disable
        1: enable
        2: no support.  "
   ::= { gs2352pPortConfigurationEntry 7 }

gs2352pPortConfFlowControl OBJECT-TYPE
   SYNTAX      INTEGER { disable(0), enable(1), noSupport(2) }
   MAX-ACCESS  read-write
   STATUS      current
   DESCRIPTION
       "default: 0,
        0: disable
        1: enable
        2: no support. "
   ::= { gs2352pPortConfigurationEntry 8 }

gs2352pPortConfMaxFrameSize OBJECT-TYPE
   SYNTAX      Integer32 (1518..9600)
   MAX-ACCESS  read-write
   STATUS      current
   DESCRIPTION
       "default: 9600 , range : 1518 - 9600 "
   ::= { gs2352pPortConfigurationEntry 9 }

gs2352pPortConfExcessiveCollisionMode OBJECT-TYPE
   SYNTAX      INTEGER { discard(0), restart(1), noSupport(2) }
   MAX-ACCESS  read-write
   STATUS      current
   DESCRIPTION
       "default: 0,
        Excessive Collision Mode : 
        0: Discard,
        1: Restart, 
        2: no support.
       "
   ::= { gs2352pPortConfigurationEntry 10 }

gs2352pPortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy, 
        2: Dynamic (perfectReach),
        3: Enable,
        4: no support.
       "
   ::= { gs2352pPortConfigurationEntry 11 }

gs2352pPortConfDescription OBJECT-TYPE
   SYNTAX      DisplayString
   MAX-ACCESS  read-write
   STATUS      current
   DESCRIPTION
       " Interface specific description.
         Up to 47 characters describing this interface. "
   ::= { gs2352pPortConfigurationEntry 12 }


gs2352pPortTrafficStatisticsTable OBJECT-TYPE
   SYNTAX      SEQUENCE OF GS2352PPortTrafficStatisticsEntry
   MAX-ACCESS  not-accessible
   STATUS      current
   DESCRIPTION
       " "
   ::= { gs2352pPort 2 }

gs2352pPortTrafficStatisticsEntry OBJECT-TYPE
   SYNTAX      GS2352PPortTrafficStatisticsEntry
   MAX-ACCESS  not-accessible
   STATUS      current
   DESCRIPTION
       ""
   INDEX    { gs2352pPortTrafficStatisticsPort  }
   ::= { gs2352pPortTrafficStatisticsTable 1 }

GS2352PPortTrafficStatisticsEntry ::= SEQUENCE {
   gs2352pPortTrafficStatisticsPort          Integer32,
   gs2352pPortTrafficStatisticsClear         INTEGER,
   gs2352pPortTrafficRxPackets               Counter64,
   gs2352pPortTrafficRxOctets                Counter64,
   gs2352pPortTrafficRxUnicast               Counter64,
   gs2352pPortTrafficRxMulticast             Counter64,
   gs2352pPortTrafficRxBroadcast             Counter64,
   gs2352pPortTrafficRxPause                 Counter64,
   gs2352pPortTrafficRx64Bytes               Counter64,
   gs2352pPortTrafficRx65to127Bytes          Counter64,
   gs2352pPortTrafficRx128to255Bytes         Counter64,
   gs2352pPortTrafficRx256to511Bytes         Counter64,
   gs2352pPortTrafficRx512to1023Bytes        Counter64,
   gs2352pPortTrafficRx1024to1526Bytes       Counter64,
   gs2352pPortTrafficRxExceecd1527Bytes      Counter64,
   gs2352pPortTrafficRxQ0                    Counter64,
   gs2352pPortTrafficRxQ1                    Counter64,
   gs2352pPortTrafficRxQ2                    Counter64,
   gs2352pPortTrafficRxQ3                    Counter64,
   gs2352pPortTrafficRxQ4                    Counter64,
   gs2352pPortTrafficRxQ5                    Counter64,
   gs2352pPortTrafficRxQ6                    Counter64,
   gs2352pPortTrafficRxQ7                    Counter64,
   gs2352pPortTrafficRxDrops                 Counter64,
   gs2352pPortTrafficRxCRCorAlignment        Counter64,
   gs2352pPortTrafficRxUndersize             Counter64,
   gs2352pPortTrafficRxOversize              Counter64,
   gs2352pPortTrafficRxFragments             Counter64,
   gs2352pPortTrafficRxJabber                Counter64,
   gs2352pPortTrafficRxFiltered              Counter64,
   gs2352pPortTrafficTxPackets               Counter64,
   gs2352pPortTrafficTxOctets                Counter64,
   gs2352pPortTrafficTxUnicast               Counter64,
   gs2352pPortTrafficTxMulticast             Counter64,
   gs2352pPortTrafficTxBroadcast             Counter64,
   gs2352pPortTrafficTxPause                 Counter64,
   gs2352pPortTrafficTx64Bytes               Counter64,
   gs2352pPortTrafficTx65to127Bytes          Counter64,
   gs2352pPortTrafficTx128to255Bytes         Counter64,
   gs2352pPortTrafficTx256to511Bytes         Counter64,
   gs2352pPortTrafficTx512to1023Bytes        Counter64,
   gs2352pPortTrafficTx1024to1526Bytes       Counter64,
   gs2352pPortTrafficTxExceecd1527Bytes      Counter64,
   gs2352pPortTrafficTxQ0                    Counter64,
   gs2352pPortTrafficTxQ1                    Counter64,
   gs2352pPortTrafficTxQ2                    Counter64,
   gs2352pPortTrafficTxQ3                    Counter64,
   gs2352pPortTrafficTxQ4                    Counter64,
   gs2352pPortTrafficTxQ5                    Counter64,
   gs2352pPortTrafficTxQ6                    Counter64,
   gs2352pPortTrafficTxQ7                    Counter64,
   gs2352pPortTrafficTxDrops                 Counter64,
   gs2352pPortTrafficTxLateOrExcColl         Counter64
}

gs2352pPortTrafficStatisticsPort OBJECT-TYPE
   SYNTAX      Integer32 (1..4095)
   MAX-ACCESS  not-accessible
   STATUS      current
   DESCRIPTION
       " "
   ::= { gs2352pPortTrafficStatisticsEntry 1 }

gs2352pPortTrafficStatisticsClear OBJECT-TYPE
   SYNTAX      INTEGER { disable(0), enable(1) }
   MAX-ACCESS  read-write
   STATUS      current
   DESCRIPTION
       " "
   ::= { gs2352pPortTrafficStatisticsEntry 2 }

gs2352pPortTrafficRxPackets OBJECT-TYPE
   SYNTAX      Counter64
   MAX-ACCESS  read-only
   STATUS      current
   DESCRIPTION
       " "
   ::= { gs2352pPortTrafficStatisticsEntry 3 }

gs2352pPortTrafficRxOctets OBJECT-TYPE
   SYNTAX      Counter64
   MAX-ACCESS  read-only
   STATUS      current
   DESCRIPTION
       " "
   ::= { gs2352pPortTrafficStatisticsEntry 4 }

gs2352pPortTrafficRxUnicast OBJECT-TYPE
   SYNTAX      Counter64
   MAX-ACCESS  read-only
   STATUS      current
   DESCRIPTION
       " "
   ::= { gs2352pPortTrafficStatisticsEntry 5 }

gs2352pPortTrafficRxMulticast OBJECT-TYPE
   SYNTAX      Counter64
   MAX-ACCESS  read-only
   STATUS      current
   DESCRIPTION
       " "
   ::= { gs2352pPortTrafficStatisticsEntry 6 }

gs2352pPortTrafficRxBroadcast OBJECT-TYPE
   SYNTAX      Counter64
   MAX-ACCESS  read-only
   STATUS      current
   DESCRIPTION
       " "
   ::= { gs2352pPortTrafficStatisticsEntry 7 }

gs2352pPortTrafficRxPause OBJECT-TYPE
   SYNTAX      Counter64
   MAX-ACCESS  read-only
   STATUS      current
   DESCRIPTION
       " "
   ::= { gs2352pPortTrafficStatisticsEntry 8 }

gs2352pPortTrafficRx64Bytes OBJECT-TYPE
   SYNTAX      Counter64
   MAX-ACCESS  read-only
   STATUS      current
   DESCRIPTION
       " "
   ::= { gs2352pPortTrafficStatisticsEntry 9 }

gs2352pPortTrafficRx65to127Bytes OBJECT-TYPE
   SYNTAX      Counter64
   MAX-ACCESS  read-only
   STATUS      current
   DESCRIPTION
       " "
   ::= { gs2352pPortTrafficStatisticsEntry 10 }

gs2352pPortTrafficRx128to255Bytes OBJECT-TYPE
   SYNTAX      Counter64
   MAX-ACCESS  read-only
   STATUS      current
   DESCRIPTION
       " "
   ::= { gs2352pPortTrafficStatisticsEntry 11 }

gs2352pPortTrafficRx256to511Bytes OBJECT-TYPE
   SYNTAX      Counter64
   MAX-ACCESS  read-only
   STATUS      current
   DESCRIPTION
       " "
   ::= { gs2352pPortTrafficStatisticsEntry 12 }

gs2352pPortTrafficRx512to1023Bytes OBJECT-TYPE
   SYNTAX      Counter64
   MAX-ACCESS  read-only
   STATUS      current
   DESCRIPTION
       " "
   ::= { gs2352pPortTrafficStatisticsEntry 13 }

gs2352pPortTrafficRx1024to1526Bytes OBJECT-TYPE
   SYNTAX      Counter64
   MAX-ACCESS  read-only
   STATUS      current
   DESCRIPTION
       " "
   ::= { gs2352pPortTrafficStatisticsEntry 14 }

gs2352pPortTrafficRxExceecd1527Bytes OBJECT-TYPE
   SYNTAX      Counter64
   MAX-ACCESS  read-only
   STATUS      current
   DESCRIPTION
       " "
   ::= { gs2352pPortTrafficStatisticsEntry 15 }

gs2352pPortTrafficRxQ0 OBJECT-TYPE
   SYNTAX      Counter64
   MAX-ACCESS  read-only
   STATUS      current
   DESCRIPTION
       " "
   ::= { gs2352pPortTrafficStatisticsEntry 16 }

gs2352pPortTrafficRxQ1 OBJECT-TYPE
   SYNTAX      Counter64
   MAX-ACCESS  read-only
   STATUS      current
   DESCRIPTION
       " "
   ::= { gs2352pPortTrafficStatisticsEntry 17 }

gs2352pPortTrafficRxQ2 OBJECT-TYPE
   SYNTAX      Counter64
   MAX-ACCESS  read-only
   STATUS      current
   DESCRIPTION
       " "
   ::= { gs2352pPortTrafficStatisticsEntry 18 }

gs2352pPortTrafficRxQ3 OBJECT-TYPE
   SYNTAX      Counter64
   MAX-ACCESS  read-only
   STATUS      current
   DESCRIPTION
       " "
   ::= { gs2352pPortTrafficStatisticsEntry 19 }

gs2352pPortTrafficRxQ4 OBJECT-TYPE
   SYNTAX      Counter64
   MAX-ACCESS  read-only
   STATUS      current
   DESCRIPTION
       " "
   ::= { gs2352pPortTrafficStatisticsEntry 20 }

gs2352pPortTrafficRxQ5 OBJECT-TYPE
   SYNTAX      Counter64
   MAX-ACCESS  read-only
   STATUS      current
   DESCRIPTION
       " "
   ::= { gs2352pPortTrafficStatisticsEntry 21 }

gs2352pPortTrafficRxQ6 OBJECT-TYPE
   SYNTAX      Counter64
   MAX-ACCESS  read-only
   STATUS      current
   DESCRIPTION
       " "
   ::= { gs2352pPortTrafficStatisticsEntry 22 }

gs2352pPortTrafficRxQ7 OBJECT-TYPE
   SYNTAX      Counter64
   MAX-ACCESS  read-only
   STATUS      current
   DESCRIPTION
       " "
   ::= { gs2352pPortTrafficStatisticsEntry 23 }

gs2352pPortTrafficRxDrops OBJECT-TYPE
   SYNTAX      Counter64
   MAX-ACCESS  read-only
   STATUS      current
   DESCRIPTION
       " "
   ::= { gs2352pPortTrafficStatisticsEntry 24 }

gs2352pPortTrafficRxCRCorAlignment OBJECT-TYPE
   SYNTAX      Counter64
   MAX-ACCESS  read-only
   STATUS      current
   DESCRIPTION
       " "
   ::= { gs2352pPortTrafficStatisticsEntry 25 }

gs2352pPortTrafficRxUndersize OBJECT-TYPE
   SYNTAX      Counter64
   MAX-ACCESS  read-only
   STATUS      current
   DESCRIPTION
       " "
   ::= { gs2352pPortTrafficStatisticsEntry 26 }

gs2352pPortTrafficRxOversize OBJECT-TYPE
   SYNTAX      Counter64
   MAX-ACCESS  read-only
   STATUS      current
   DESCRIPTION
       " "
   ::= { gs2352pPortTrafficStatisticsEntry 27 }

gs2352pPortTrafficRxFragments OBJECT-TYPE
   SYNTAX      Counter64
   MAX-ACCESS  read-only
   STATUS      current
   DESCRIPTION
       " "
   ::= { gs2352pPortTrafficStatisticsEntry 28 }

gs2352pPortTrafficRxJabber OBJECT-TYPE
   SYNTAX      Counter64
   MAX-ACCESS  read-only
   STATUS      current
   DESCRIPTION
       " "
   ::= { gs2352pPortTrafficStatisticsEntry 29 }

gs2352pPortTrafficRxFiltered OBJECT-TYPE
   SYNTAX      Counter64
   MAX-ACCESS  read-only
   STATUS      current
   DESCRIPTION
       " "
   ::= { gs2352pPortTrafficStatisticsEntry 30 }

gs2352pPortTrafficTxPackets OBJECT-TYPE
   SYNTAX      Counter64
   MAX-ACCESS  read-only
   STATUS      current
   DESCRIPTION
       " "
   ::= { gs2352pPortTrafficStatisticsEntry 31 }

gs2352pPortTrafficTxOctets OBJECT-TYPE
   SYNTAX      Counter64
   MAX-ACCESS  read-only
   STATUS      current
   DESCRIPTION
       " "
   ::= { gs2352pPortTrafficStatisticsEntry 32 }

gs2352pPortTrafficTxUnicast OBJECT-TYPE
   SYNTAX      Counter64
   MAX-ACCESS  read-only
   STATUS      current
   DESCRIPTION
       " "
   ::= { gs2352pPortTrafficStatisticsEntry 33 }

gs2352pPortTrafficTxMulticast OBJECT-TYPE
   SYNTAX      Counter64
   MAX-ACCESS  read-only
   STATUS      current
   DESCRIPTION
       " "
   ::= { gs2352pPortTrafficStatisticsEntry 34 }

gs2352pPortTrafficTxBroadcast OBJECT-TYPE
   SYNTAX      Counter64
   MAX-ACCESS  read-only
   STATUS      current
   DESCRIPTION
       " "
   ::= { gs2352pPortTrafficStatisticsEntry 35 }

gs2352pPortTrafficTxPause OBJECT-TYPE
   SYNTAX      Counter64
   MAX-ACCESS  read-only
   STATUS      current
   DESCRIPTION
       " "
   ::= { gs2352pPortTrafficStatisticsEntry 36 }

gs2352pPortTrafficTx64Bytes OBJECT-TYPE
   SYNTAX      Counter64
   MAX-ACCESS  read-only
   STATUS      current
   DESCRIPTION
       " "
   ::= { gs2352pPortTrafficStatisticsEntry 37 }

gs2352pPortTrafficTx65to127Bytes OBJECT-TYPE
   SYNTAX      Counter64
   MAX-ACCESS  read-only
   STATUS      current
   DESCRIPTION
       " "
   ::= { gs2352pPortTrafficStatisticsEntry 38 }

gs2352pPortTrafficTx128to255Bytes OBJECT-TYPE
   SYNTAX      Counter64
   MAX-ACCESS  read-only
   STATUS      current
   DESCRIPTION
       " "
   ::= { gs2352pPortTrafficStatisticsEntry 39 }

gs2352pPortTrafficTx256to511Bytes OBJECT-TYPE
   SYNTAX      Counter64
   MAX-ACCESS  read-only
   STATUS      current
   DESCRIPTION
       " "
   ::= { gs2352pPortTrafficStatisticsEntry 40 }

gs2352pPortTrafficTx512to1023Bytes OBJECT-TYPE
   SYNTAX      Counter64
   MAX-ACCESS  read-only
   STATUS      current
   DESCRIPTION
       " "
   ::= { gs2352pPortTrafficStatisticsEntry 41 }

gs2352pPortTrafficTx1024to1526Bytes OBJECT-TYPE
   SYNTAX      Counter64
   MAX-ACCESS  read-only
   STATUS      current
   DESCRIPTION
       " "
   ::= { gs2352pPortTrafficStatisticsEntry 42 }

gs2352pPortTrafficTxExceecd1527Bytes OBJECT-TYPE
   SYNTAX      Counter64
   MAX-ACCESS  read-only
   STATUS      current
   DESCRIPTION
       " "
   ::= { gs2352pPortTrafficStatisticsEntry 43 }

gs2352pPortTrafficTxQ0 OBJECT-TYPE
   SYNTAX      Counter64
   MAX-ACCESS  read-only
   STATUS      current
   DESCRIPTION
       " "
   ::= { gs2352pPortTrafficStatisticsEntry 44 }

gs2352pPortTrafficTxQ1 OBJECT-TYPE
   SYNTAX      Counter64
   MAX-ACCESS  read-only
   STATUS      current
   DESCRIPTION
       " "
   ::= { gs2352pPortTrafficStatisticsEntry 45 }

gs2352pPortTrafficTxQ2 OBJECT-TYPE
   SYNTAX      Counter64
   MAX-ACCESS  read-only
   STATUS      current
   DESCRIPTION
       " "
   ::= { gs2352pPortTrafficStatisticsEntry 46 }

gs2352pPortTrafficTxQ3 OBJECT-TYPE
   SYNTAX      Counter64
   MAX-ACCESS  read-only
   STATUS      current
   DESCRIPTION
       " "
   ::= { gs2352pPortTrafficStatisticsEntry 47 }

gs2352pPortTrafficTxQ4 OBJECT-TYPE
   SYNTAX      Counter64
   MAX-ACCESS  read-only
   STATUS      current
   DESCRIPTION
       " "
   ::= { gs2352pPortTrafficStatisticsEntry 48 }

gs2352pPortTrafficTxQ5 OBJECT-TYPE
   SYNTAX      Counter64
   MAX-ACCESS  read-only
   STATUS      current
   DESCRIPTION
       " "
   ::= { gs2352pPortTrafficStatisticsEntry 49 }

gs2352pPortTrafficTxQ6 OBJECT-TYPE
   SYNTAX      Counter64
   MAX-ACCESS  read-only
   STATUS      current
   DESCRIPTION
       " "
   ::= { gs2352pPortTrafficStatisticsEntry 50 }


gs2352pPortTrafficTxQ7 OBJECT-TYPE
   SYNTAX      Counter64
   MAX-ACCESS  read-only
   STATUS      current
   DESCRIPTION
       " "
   ::= { gs2352pPortTrafficStatisticsEntry 51 }

gs2352pPortTrafficTxDrops OBJECT-TYPE
   SYNTAX      Counter64
   MAX-ACCESS  read-only
   STATUS      current
   DESCRIPTION
       " "
   ::= { gs2352pPortTrafficStatisticsEntry 52 }

gs2352pPortTrafficTxLateOrExcColl OBJECT-TYPE
   SYNTAX      Counter64
   MAX-ACCESS  read-only
   STATUS      current
   DESCRIPTION
       " "
   ::= { gs2352pPortTrafficStatisticsEntry 53 }


gs2352pPortQoSStatistics                                     OBJECT IDENTIFIER ::= { gs2352pPort 3 }

gs2352pPortQoSStatisticsClear OBJECT-TYPE
   SYNTAX      INTEGER { none(0), clear(1) }
   MAX-ACCESS  read-only
   STATUS      current
   DESCRIPTION
       "default: 0
       0: none
       1: clear "
   ::= { gs2352pPortQoSStatistics 1 }

gs2352pPortQoSStatisticsTable OBJECT-TYPE
   SYNTAX      SEQUENCE OF GS2352PPortQoSStatisticsEntry
   MAX-ACCESS  not-accessible
   STATUS      current
   DESCRIPTION
       " "
   ::= { gs2352pPortQoSStatistics 2 }

gs2352pPortQoSStatisticsEntry OBJECT-TYPE
   SYNTAX      GS2352PPortQoSStatisticsEntry
   MAX-ACCESS  not-accessible
   STATUS      current
   DESCRIPTION
       ""
   INDEX    { gs2352pPortQoSStatisticsPort  }
   ::= { gs2352pPortQoSStatisticsTable 1 }

GS2352PPortQoSStatisticsEntry ::= SEQUENCE {
   gs2352pPortQoSStatisticsPort      Integer32,
   gs2352pPortQoSQ0Rx                Counter64,
   gs2352pPortQoSQ0Tx                Counter64,
   gs2352pPortQoSQ1Rx                Counter64,
   gs2352pPortQoSQ1Tx                Counter64,
   gs2352pPortQoSQ2Rx                Counter64,
   gs2352pPortQoSQ2Tx                Counter64,
   gs2352pPortQoSQ3Rx                Counter64,
   gs2352pPortQoSQ3Tx                Counter64,
   gs2352pPortQoSQ4Rx                Counter64,
   gs2352pPortQoSQ4Tx                Counter64,
   gs2352pPortQoSQ5Rx                Counter64,
   gs2352pPortQoSQ5Tx                Counter64,
   gs2352pPortQoSQ6Rx                Counter64,
   gs2352pPortQoSQ6Tx                Counter64,
   gs2352pPortQoSQ7Rx                Counter64,
   gs2352pPortQoSQ7Tx                Counter64
}

gs2352pPortQoSStatisticsPort OBJECT-TYPE
   SYNTAX      Integer32(1..4095)
   MAX-ACCESS  not-accessible
   STATUS      current
   DESCRIPTION
       " "
   ::= { gs2352pPortQoSStatisticsEntry 1 }

gs2352pPortQoSQ0Rx OBJECT-TYPE
   SYNTAX      Counter64
   MAX-ACCESS  read-only
   STATUS      current
   DESCRIPTION
       " "
   ::= { gs2352pPortQoSStatisticsEntry 2 }

gs2352pPortQoSQ0Tx OBJECT-TYPE
   SYNTAX      Counter64
   MAX-ACCESS  read-only
   STATUS      current
   DESCRIPTION
       " "
   ::= { gs2352pPortQoSStatisticsEntry 3 }

gs2352pPortQoSQ1Rx OBJECT-TYPE
   SYNTAX      Counter64
   MAX-ACCESS  read-only
   STATUS      current
   DESCRIPTION
       " "
   ::= { gs2352pPortQoSStatisticsEntry 4 }

gs2352pPortQoSQ1Tx OBJECT-TYPE
   SYNTAX      Counter64
   MAX-ACCESS  read-only
   STATUS      current
   DESCRIPTION
       " "
   ::= { gs2352pPortQoSStatisticsEntry 5 }

gs2352pPortQoSQ2Rx OBJECT-TYPE
   SYNTAX      Counter64
   MAX-ACCESS  read-only
   STATUS      current
   DESCRIPTION
       " "
   ::= { gs2352pPortQoSStatisticsEntry 6 }

gs2352pPortQoSQ2Tx OBJECT-TYPE
   SYNTAX      Counter64
   MAX-ACCESS  read-only
   STATUS      current
   DESCRIPTION
       " "
   ::= { gs2352pPortQoSStatisticsEntry 7 }

gs2352pPortQoSQ3Rx OBJECT-TYPE
   SYNTAX      Counter64
   MAX-ACCESS  read-only
   STATUS      current
   DESCRIPTION
       " "
   ::= { gs2352pPortQoSStatisticsEntry 8 }

gs2352pPortQoSQ3Tx OBJECT-TYPE
   SYNTAX      Counter64
   MAX-ACCESS  read-only
   STATUS      current
   DESCRIPTION
       " "
   ::= { gs2352pPortQoSStatisticsEntry 9 }

gs2352pPortQoSQ4Rx OBJECT-TYPE
   SYNTAX      Counter64
   MAX-ACCESS  read-only
   STATUS      current
   DESCRIPTION
       " "
   ::= { gs2352pPortQoSStatisticsEntry 10 }

gs2352pPortQoSQ4Tx OBJECT-TYPE
   SYNTAX      Counter64
   MAX-ACCESS  read-only
   STATUS      current
   DESCRIPTION
       " "
   ::= { gs2352pPortQoSStatisticsEntry 11 }

gs2352pPortQoSQ5Rx OBJECT-TYPE
   SYNTAX      Counter64
   MAX-ACCESS  read-only
   STATUS      current
   DESCRIPTION
       " "
   ::= { gs2352pPortQoSStatisticsEntry 12 }

gs2352pPortQoSQ5Tx OBJECT-TYPE
   SYNTAX      Counter64
   MAX-ACCESS  read-only
   STATUS      current
   DESCRIPTION
       " "
   ::= { gs2352pPortQoSStatisticsEntry 13 }

gs2352pPortQoSQ6Rx OBJECT-TYPE
   SYNTAX      Counter64
   MAX-ACCESS  read-only
   STATUS      current
   DESCRIPTION
       " "
   ::= { gs2352pPortQoSStatisticsEntry 14 }

gs2352pPortQoSQ6Tx OBJECT-TYPE
   SYNTAX      Counter64
   MAX-ACCESS  read-only
   STATUS      current
   DESCRIPTION
       " "
   ::= { gs2352pPortQoSStatisticsEntry 15 }

gs2352pPortQoSQ7Rx OBJECT-TYPE
   SYNTAX      Counter64
   MAX-ACCESS  read-only
   STATUS      current
   DESCRIPTION
       " "
   ::= { gs2352pPortQoSStatisticsEntry 16 }

gs2352pPortQoSQ7Tx OBJECT-TYPE
   SYNTAX      Counter64
   MAX-ACCESS  read-only
   STATUS      current
   DESCRIPTION
       " "
   ::= { gs2352pPortQoSStatisticsEntry 17 }

gs2352pSFPInfoTable OBJECT-TYPE
   SYNTAX      SEQUENCE OF GS2352PSFPInfoEntry
   MAX-ACCESS  not-accessible
   STATUS      current
   DESCRIPTION
       " "
   ::= { gs2352pPort 4 }

gs2352pSFPInfoEntry OBJECT-TYPE
   SYNTAX      GS2352PSFPInfoEntry
   MAX-ACCESS  not-accessible
   STATUS      current
   DESCRIPTION
       ""
   INDEX    { gs2352pSFPInfoIndex }
   ::= { gs2352pSFPInfoTable 1 }

GS2352PSFPInfoEntry ::= SEQUENCE {
   gs2352pSFPInfoIndex               Integer32,
   gs2352pSFPInfoPort                DisplayString,
   gs2352pSFPConnectorType           DisplayString,
   gs2352pSFPFiberType               DisplayString,
   gs2352pSFPTxCentralWavelength     DisplayString,
   gs2352pSFPBaudRate                DisplayString,
   gs2352pSFPVendorOUI               DisplayString,
   gs2352pSFPVendorName              DisplayString,
   gs2352pSFPVendorPN                DisplayString,
   gs2352pSFPVendorRev               DisplayString,
   gs2352pSFPVendorSN                DisplayString,
   gs2352pSFPDateCode                DisplayString,
   gs2352pSFPTemperature             DisplayString,
   gs2352pSFPVcc                     DisplayString,
   gs2352pSFPMon1Bias                DisplayString,
   gs2352pSFPMon2TxPWR               DisplayString,
   gs2352pSFPMon3RxPWR               DisplayString
}

gs2352pSFPInfoIndex OBJECT-TYPE
   SYNTAX      Integer32(1..4095)
   MAX-ACCESS  not-accessible
   STATUS      current
   DESCRIPTION
       " "
   ::= { gs2352pSFPInfoEntry 1 }

gs2352pSFPInfoPort OBJECT-TYPE
   SYNTAX      DisplayString
   MAX-ACCESS  read-only
   STATUS      current
   DESCRIPTION
       " "
   ::= { gs2352pSFPInfoEntry 2 }

gs2352pSFPConnectorType OBJECT-TYPE
   SYNTAX      DisplayString
   MAX-ACCESS  read-only
   STATUS      current
   DESCRIPTION
       " "
   ::= { gs2352pSFPInfoEntry 3 }

gs2352pSFPFiberType OBJECT-TYPE
   SYNTAX      DisplayString
   MAX-ACCESS  read-only
   STATUS      current
   DESCRIPTION
       " "
   ::= { gs2352pSFPInfoEntry 4 }

gs2352pSFPTxCentralWavelength OBJECT-TYPE
   SYNTAX      DisplayString
   MAX-ACCESS  read-only
   STATUS      current
   DESCRIPTION
       " "
   ::= { gs2352pSFPInfoEntry 5 }

gs2352pSFPBaudRate OBJECT-TYPE
   SYNTAX      DisplayString
   MAX-ACCESS  read-only
   STATUS      current
   DESCRIPTION
       " "
   ::= { gs2352pSFPInfoEntry 6 }

gs2352pSFPVendorOUI OBJECT-TYPE
   SYNTAX      DisplayString
   MAX-ACCESS  read-only
   STATUS      current
   DESCRIPTION
       " "
   ::= { gs2352pSFPInfoEntry 7 }

gs2352pSFPVendorName OBJECT-TYPE
   SYNTAX      DisplayString
   MAX-ACCESS  read-only
   STATUS      current
   DESCRIPTION
       " "
   ::= { gs2352pSFPInfoEntry 8 }

gs2352pSFPVendorPN OBJECT-TYPE
   SYNTAX      DisplayString
   MAX-ACCESS  read-only
   STATUS      current
   DESCRIPTION
       " "
   ::= { gs2352pSFPInfoEntry 9 }

gs2352pSFPVendorRev OBJECT-TYPE
   SYNTAX      DisplayString
   MAX-ACCESS  read-only
   STATUS      current
   DESCRIPTION
       " "
   ::= { gs2352pSFPInfoEntry 10 }

gs2352pSFPVendorSN OBJECT-TYPE
   SYNTAX      DisplayString
   MAX-ACCESS  read-only
   STATUS      current
   DESCRIPTION
       " "
   ::= { gs2352pSFPInfoEntry 11 }

gs2352pSFPDateCode OBJECT-TYPE
   SYNTAX      DisplayString
   MAX-ACCESS  read-only
   STATUS      current
   DESCRIPTION
       " "
   ::= { gs2352pSFPInfoEntry 12 }

gs2352pSFPTemperature OBJECT-TYPE
   SYNTAX      DisplayString
   MAX-ACCESS  read-only
   STATUS      current
   DESCRIPTION
       " "
   ::= { gs2352pSFPInfoEntry 13 }

gs2352pSFPVcc OBJECT-TYPE
   SYNTAX      DisplayString
   MAX-ACCESS  read-only
   STATUS      current
   DESCRIPTION
       " "
   ::= { gs2352pSFPInfoEntry 14 }
   
gs2352pSFPMon1Bias OBJECT-TYPE
   SYNTAX      DisplayString
   MAX-ACCESS  read-only
   STATUS      current
   DESCRIPTION
       " "
   ::= { gs2352pSFPInfoEntry 15 }
   
gs2352pSFPMon2TxPWR OBJECT-TYPE
   SYNTAX      DisplayString
   MAX-ACCESS  read-only
   STATUS      current
   DESCRIPTION
       " "
   ::= { gs2352pSFPInfoEntry 16 }

gs2352pSFPMon3RxPWR OBJECT-TYPE
   SYNTAX      DisplayString
   MAX-ACCESS  read-only
   STATUS      current
   DESCRIPTION
       " "
   ::= { gs2352pSFPInfoEntry 17 }


gs2352pVoiceVLAN                                             OBJECT IDENTIFIER ::= { gs2352pConfiguration 2 }

gs2352pVoiceVLANConf                                         OBJECT IDENTIFIER ::= { gs2352pVoiceVLAN 1 }

gs2352pVoiceVLANMode OBJECT-TYPE
   SYNTAX      INTEGER { disable(0), enable(1) }
   MAX-ACCESS  read-write
   STATUS      current
   DESCRIPTION
       " Voice VLAN mode operation.
       default: 0,
       0: disable
       1: enable"
   ::= { gs2352pVoiceVLANConf 1 }

gs2352pVoiceVLANVLANId OBJECT-TYPE
   SYNTAX      Integer32(1..4094)
   MAX-ACCESS  read-write
   STATUS      current
   DESCRIPTION
       "Voice VLAN ID.
        default: 1000,
        range : 1-4094. "
   ::= { gs2352pVoiceVLANConf 2 }

gs2352pVoiceVLANAgingTime OBJECT-TYPE
   SYNTAX      Integer32(10..1000000)
   MAX-ACCESS  read-write
   STATUS      current
   DESCRIPTION
       " Voice VLAN secure learning aging time. 
         default: 86400,
         range : 10 - 10000000. "
   ::= { gs2352pVoiceVLANConf 3 }

gs2352pVoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2352pVoiceVLANConf 4 }


gs2352pVoiceVLANPortTable OBJECT-TYPE
   SYNTAX      SEQUENCE OF GS2352PVoiceVLANPortEntry
   MAX-ACCESS  not-accessible
   STATUS      current
   DESCRIPTION
       " Show Voice Vlan configuration. "
   ::= { gs2352pVoiceVLANConf 5 }

gs2352pVoiceVLANPortEntry OBJECT-TYPE
   SYNTAX      GS2352PVoiceVLANPortEntry
   MAX-ACCESS  not-accessible
   STATUS      current
   DESCRIPTION
       ""
   INDEX    { gs2352pVoiceVLANPort  }
   ::= { gs2352pVoiceVLANPortTable 1 }

GS2352PVoiceVLANPortEntry ::= SEQUENCE {
   gs2352pVoiceVLANPort                    Integer32,
   gs2352pVoiceVLANPortMode                INTEGER,
   gs2352pVoiceVLANPortSecurity            INTEGER,
   gs2352pVoiceVLANPortDiscoveryProtocol   INTEGER
}

gs2352pVoiceVLANPort OBJECT-TYPE
   SYNTAX      Integer32(1..4095)
   MAX-ACCESS  not-accessible
   STATUS      current
   DESCRIPTION
       " port, range : 1 - port number. "
   ::= { gs2352pVoiceVLANPortEntry 1 }

gs2352pVoiceVLANPortMode OBJECT-TYPE
   SYNTAX      INTEGER { disable(0), auto(1), forced(2) }
   MAX-ACCESS  read-write
   STATUS      current
   DESCRIPTION
       " Voice VLAN port mode.  
         default: 0,
         0: Disable (Disjoin from Voice VLAN.)
         1: Auto (Enable auto detect mode. It detects whether there is VoIP phone attached to the specific port and configures the Voice VLAN members automatically.)
         2: Forced (Force join to Voice VLAN.)"
   ::= { gs2352pVoiceVLANPortEntry 2 }

gs2352pVoiceVLANPortSecurity OBJECT-TYPE
   SYNTAX      INTEGER { disable(0), enable(1) }
   MAX-ACCESS  read-write
   STATUS      current
   DESCRIPTION
       " Voice VLAN port security mode. 
         default: 0,
         0: Disable (Disjoin from Voice VLAN.)
         1: enable ( Enable Voice VLAN security mode. When the function is
                     enabled, all non-telephone MAC address in Voice VLAN
                     will be blocked 10 seconds.)"
   ::= { gs2352pVoiceVLANPortEntry 3 }

gs2352pVoiceVLANPortDiscoveryProtocol OBJECT-TYPE
   SYNTAX      INTEGER { oui(0), lldp(1), both(2) }
   MAX-ACCESS  read-write
   STATUS      current
   DESCRIPTION
       " Voice VLAN port discovery protocol.  
         default: 0
         0: OUI (Detect telephony device by OUI address.)
         1: LLDP (Detect telephony device by LLDP.)
         2: Both (Both OUI and LLDP.) "
   ::= { gs2352pVoiceVLANPortEntry 4 }

gs2352pVoiceVLANSkipNAS OBJECT-TYPE
   SYNTAX      INTEGER { disable(0), enable(1) }
   MAX-ACCESS  read-write
   STATUS      current
   DESCRIPTION
       " Voice VLAN skip NAS mode. 
         default: 0,
         0: Disable (Do not skip NAS on Voice VLAN.)
         1: enable (Enable skipping of NAS on Voice VLAN. When the function is
                    enabled, authentication through the NAS module is not
                    applied to the Voice VLAN, but clients are allowed without
                    authentication.)"
   ::= { gs2352pVoiceVLANPortEntry 5 }


gs2352pVoiceVLANOUI                                          OBJECT IDENTIFIER ::= { gs2352pVoiceVLAN 2 }

gs2352pVoiceVLANOUICreate OBJECT-TYPE
   SYNTAX       INTEGER { none(0), create(1) }
   MAX-ACCESS   read-write
   STATUS       current
   DESCRIPTION
       "default: 0
        0 : None  (read only)
        1 : Create an OUI entry"
   ::= { gs2352pVoiceVLANOUI 1 }

gs2352pVoiceVLANOUITable OBJECT-TYPE
   SYNTAX      SEQUENCE OF GS2352PVoiceVLANOUIEntry
   MAX-ACCESS  not-accessible
   STATUS      current
   DESCRIPTION
       " Create Voice VLAN OUI entry. Modify OUI table will
         restart auto detect OUI process. "
   ::= { gs2352pVoiceVLANOUI 2 }

gs2352pVoiceVLANOUIEntry OBJECT-TYPE
   SYNTAX      GS2352PVoiceVLANOUIEntry
   MAX-ACCESS  not-accessible
   STATUS      current
   DESCRIPTION
       ""
   INDEX    { gs2352pVoiceVLANOUIIndex  }
   ::= { gs2352pVoiceVLANOUITable 1 }

GS2352PVoiceVLANOUIEntry ::= SEQUENCE {
   gs2352pVoiceVLANOUIIndex         Integer32,
   gs2352pVoiceVLANTelephonyOUI     OCTET STRING,
   gs2352pVoiceVLANDescription      DisplayString,
   gs2352pVoiceVLANOUIRowStatus     INTEGER
}

gs2352pVoiceVLANOUIIndex OBJECT-TYPE
   SYNTAX      Integer32(1..16)
   MAX-ACCESS  not-accessible
   STATUS      current
   DESCRIPTION
       " "
   ::= { gs2352pVoiceVLANOUIEntry 1 }

gs2352pVoiceVLANTelephonyOUI OBJECT-TYPE
   SYNTAX      OCTET STRING (SIZE (1..32))
   MAX-ACCESS  read-write
   STATUS      current
   DESCRIPTION
       "OUI address, format : 0a 1b 2c "
   ::= { gs2352pVoiceVLANOUIEntry 2 }

gs2352pVoiceVLANDescription OBJECT-TYPE
   SYNTAX      DisplayString (SIZE (1..32))
   MAX-ACCESS  read-write
   STATUS      current
   DESCRIPTION
       " Up to 32 characters describing OUI address. "
   ::= { gs2352pVoiceVLANOUIEntry 3 }

gs2352pVoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2352pVoiceVLANOUIEntry 4 }

gs2352pGARP                                                   OBJECT IDENTIFIER ::= { gs2352pConfiguration 3 }

gs2352pGARPConfTable OBJECT-TYPE
   SYNTAX      SEQUENCE OF GS2352PGARPConfEntry
   MAX-ACCESS  not-accessible
   STATUS      current
   DESCRIPTION
       " "
   ::= { gs2352pGARP 1 }

gs2352pGARPConfEntry OBJECT-TYPE
   SYNTAX      GS2352PGARPConfEntry
   MAX-ACCESS  not-accessible
   STATUS      current
   DESCRIPTION
       ""
   INDEX    { gs2352pGARPConfPort  }
   ::= { gs2352pGARPConfTable 1 }

GS2352PGARPConfEntry ::= SEQUENCE {
   gs2352pGARPConfPort           Integer32,
   gs2352pGARPJoinTimer          Integer32,
   gs2352pGARPLeaveTimer         Integer32,
   gs2352pGARPLeaveAllTimer      Integer32,
   gs2352pGARPApplicantion       INTEGER,
   gs2352pGARPAttributeType      INTEGER,
   gs2352pGARPApplicant          INTEGER
}

gs2352pGARPConfPort OBJECT-TYPE
   SYNTAX      Integer32(1..4095)
   MAX-ACCESS  not-accessible
   STATUS      current
   DESCRIPTION
       " "
   ::= { gs2352pGARPConfEntry 1 }

gs2352pGARPJoinTimer OBJECT-TYPE
   SYNTAX      Integer32(200..1000)
   MAX-ACCESS  read-write
   STATUS      current
   DESCRIPTION
       "default: 200, range : 200 - 1000 "
   ::= { gs2352pGARPConfEntry 2 }

gs2352pGARPLeaveTimer OBJECT-TYPE
   SYNTAX      Integer32(600..3000)
   MAX-ACCESS  read-write
   STATUS      current
   DESCRIPTION
       "default: 600 , range : 600 - 3000"
   ::= { gs2352pGARPConfEntry 3 }

gs2352pGARPLeaveAllTimer OBJECT-TYPE
   SYNTAX      Integer32(10000..50000)
   MAX-ACCESS  read-write
   STATUS      current
   DESCRIPTION
       "default: 10000, range : 10000 - 50000 "
   ::= { gs2352pGARPConfEntry 4 }

gs2352pGARPApplicantion OBJECT-TYPE
   SYNTAX      INTEGER { gvrp(1)}
   MAX-ACCESS  read-write
   STATUS      current
   DESCRIPTION
       "default: 1
       1: GVRP"
   ::= { gs2352pGARPConfEntry 5 }

gs2352pGARPAttributeType OBJECT-TYPE
   SYNTAX      INTEGER { vlan(1)}
   MAX-ACCESS  read-write
   STATUS      current
   DESCRIPTION
       "default: 1
       1: VLAN"
   ::= { gs2352pGARPConfEntry 6 }

gs2352pGARPApplicant OBJECT-TYPE
   SYNTAX      INTEGER { participant(0), nonParticipant(1) }
   MAX-ACCESS  read-write
   STATUS      current
   DESCRIPTION
       "default: 0
       0: normal-participant
       1: non-participant"
   ::= { gs2352pGARPConfEntry 7 }

gs2352pGARPStatisticsTable OBJECT-TYPE
   SYNTAX      SEQUENCE OF GS2352PGARPStatisticsEntry
   MAX-ACCESS  not-accessible
   STATUS      current
   DESCRIPTION
       " Show the basic GARP port statistics. "
   ::= { gs2352pGARP 2 }

gs2352pGARPStatisticsEntry OBJECT-TYPE
   SYNTAX      GS2352PGARPStatisticsEntry
   MAX-ACCESS  not-accessible
   STATUS      current
   DESCRIPTION
       ""
   INDEX    { gs2352pGARPStatisticsPort  }
   ::= { gs2352pGARPStatisticsTable 1 }

GS2352PGARPStatisticsEntry ::= SEQUENCE {
   gs2352pGARPStatisticsPort             Integer32,
   gs2352pGARPStatisticsPeerMAC          DisplayString,
   gs2352pGARPStatisticsFailedCount      Counter32
}

gs2352pGARPStatisticsPort OBJECT-TYPE
   SYNTAX      Integer32(1..4095)
   MAX-ACCESS  not-accessible
   STATUS      current
   DESCRIPTION
       " port, range : 1 - port number. "
   ::= { gs2352pGARPStatisticsEntry 1 }

gs2352pGARPStatisticsPeerMAC OBJECT-TYPE
   SYNTAX      DisplayString
   MAX-ACCESS  read-only
   STATUS      current
   DESCRIPTION
       " Peer MAC is MAC address of the neighbour Switch from with GARP frame is received.  "
   ::= { gs2352pGARPStatisticsEntry 2 }

gs2352pGARPStatisticsFailedCount OBJECT-TYPE
   SYNTAX      Counter32
   MAX-ACCESS  read-only
   STATUS      current
   DESCRIPTION
       " explain Failed count here. "
   ::= { gs2352pGARPStatisticsEntry 3 }

gs2352pGVRP                                                   OBJECT IDENTIFIER ::= { gs2352pConfiguration 4 }

gs2352pGVRPConf                                                   OBJECT IDENTIFIER ::= { gs2352pGVRP 1 }

gs2352pGVRPMode OBJECT-TYPE
   SYNTAX      INTEGER { disable(0), enable(1) }
   MAX-ACCESS  read-write
   STATUS      current
   DESCRIPTION
       "default: 0,
        0: disable, 
        1: enable. "
   ::= { gs2352pGVRPConf 1 }

gs2352pGVRPConfTable OBJECT-TYPE
   SYNTAX      SEQUENCE OF GS2352PGVRPConfEntry
   MAX-ACCESS  not-accessible
   STATUS      current
   DESCRIPTION
       " "
   ::= { gs2352pGVRPConf 2 }

gs2352pGVRPConfEntry OBJECT-TYPE
   SYNTAX      GS2352PGVRPConfEntry
   MAX-ACCESS  not-accessible
   STATUS      current
   DESCRIPTION
       ""
   INDEX    { gs2352pGVRPConfPort  }
   ::= { gs2352pGVRPConfTable 1 }

GS2352PGVRPConfEntry ::= SEQUENCE {
   gs2352pGVRPConfPort           Integer32,
   gs2352pGVRPConfPortMode       INTEGER,
   gs2352pGVRPConfPortRRole      INTEGER
}

gs2352pGVRPConfPort OBJECT-TYPE
   SYNTAX      Integer32(1..4095)
   MAX-ACCESS  not-accessible
   STATUS      current
   DESCRIPTION
       " "
   ::= { gs2352pGVRPConfEntry 1 }

gs2352pGVRPConfPortMode OBJECT-TYPE
   SYNTAX      INTEGER { disable(0), enable(1) }
   MAX-ACCESS  read-write
   STATUS      current
   DESCRIPTION
       "default: 0
       1: enable
       0: disable"
   ::= { gs2352pGVRPConfEntry 2 }

gs2352pGVRPConfPortRRole OBJECT-TYPE
   SYNTAX      INTEGER { disable(0), enable(1) }
   MAX-ACCESS  read-write
   STATUS      current
   DESCRIPTION
       "default: 0
       1: enable
       0: disable"
   ::= { gs2352pGVRPConfEntry 3 }

gs2352pGVRPStatisticsTable OBJECT-TYPE
   SYNTAX      SEQUENCE OF GS2352PGVRPStatisticsEntry
   MAX-ACCESS  not-accessible
   STATUS      current
   DESCRIPTION
       " "
   ::= { gs2352pGVRP 2 }

gs2352pGVRPStatisticsEntry OBJECT-TYPE
   SYNTAX      GS2352PGVRPStatisticsEntry
   MAX-ACCESS  not-accessible
   STATUS      current
   DESCRIPTION
       ""
   INDEX    { gs2352pGVRPStatisticsPort  }
   ::= { gs2352pGVRPStatisticsTable 1 }

GS2352PGVRPStatisticsEntry ::= SEQUENCE {
   gs2352pGVRPStatisticsPort         Integer32,
   gs2352pGVRPStatisticsJoinTxCnt    Counter32,
   gs2352pGVRPStatisticsLeaveTxCnt   Counter32
}

gs2352pGVRPStatisticsPort OBJECT-TYPE
   SYNTAX      Integer32(1..4095)
   MAX-ACCESS  not-accessible
   STATUS      current
   DESCRIPTION
       " "
   ::= { gs2352pGVRPStatisticsEntry 1 }

gs2352pGVRPStatisticsJoinTxCnt OBJECT-TYPE
   SYNTAX      Counter32
   MAX-ACCESS  read-only
   STATUS      current
   DESCRIPTION
       ""
   ::= { gs2352pGVRPStatisticsEntry 2 }

gs2352pGVRPStatisticsLeaveTxCnt OBJECT-TYPE
   SYNTAX      Counter32
   MAX-ACCESS  read-only
   STATUS      current
   DESCRIPTION
       ""
   ::= { gs2352pGVRPStatisticsEntry 3 }


gs2352pMirroring                                             OBJECT IDENTIFIER ::= { gs2352pConfiguration 6 }

gs2352pPortToMirrorOn OBJECT-TYPE
   SYNTAX      Integer32(0..10)
   MAX-ACCESS  read-write
   STATUS      current
   DESCRIPTION
       "default: 0 
        0: disable,
        range : 1 - port number. "
   ::= { gs2352pMirroring 1 }

gs2352pMirrorTable OBJECT-TYPE
   SYNTAX      SEQUENCE OF GS2352PMirrorEntry
   MAX-ACCESS  not-accessible
   STATUS      current
   DESCRIPTION
       " "
   ::= { gs2352pMirroring 2 }

gs2352pMirrorEntry OBJECT-TYPE
   SYNTAX      GS2352PMirrorEntry
   MAX-ACCESS  not-accessible
   STATUS      current
   DESCRIPTION
       ""
   INDEX    { gs2352pMirrorPort  }
   ::= { gs2352pMirrorTable 1 }

GS2352PMirrorEntry ::= SEQUENCE {
   gs2352pMirrorPort		Integer32,
   gs2352pMirrorMode		INTEGER
}

gs2352pMirrorPort OBJECT-TYPE
   SYNTAX      Integer32(1..4095)
   MAX-ACCESS  not-accessible
   STATUS      current
   DESCRIPTION
       " "
   ::= { gs2352pMirrorEntry 1 }

gs2352pMirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2352pMirrorEntry 2 }

gs2352pTrapEventSeverity                                             OBJECT IDENTIFIER ::= { gs2352pConfiguration 7 }

gs2352pTrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 1 }

gs2352pTrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2352pTrapEventSeverity 2 }

gs2352pTrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 3 }

gs2352pTrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352pTrapEventSeverity 4 }

gs2352pTrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352pTrapEventSeverity 5 }

gs2352pTrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 6 }

gs2352pTrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 7 }

gs2352pTrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 8 }

gs2352pTrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 9 }

gs2352pTrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352pTrapEventSeverity 10 }

gs2352pTrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 11 }

gs2352pTrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 12 }

gs2352pTrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 13 }

gs2352pTrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 14 }

gs2352pTrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2352pTrapEventSeverity 15 }

gs2352pTrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 16 }

gs2352pTrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 17 }

gs2352pTrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 18 }

gs2352pTrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2352pTrapEventSeverity 20 }

gs2352pTrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352pTrapEventSeverity 21 }

gs2352pTrapEventSeverityPoEAutoCheck OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352pTrapEventSeverity 22 }

gs2352pTrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352pTrapEventSeverity 25 }

gs2352pTrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352pTrapEventSeverity 27 }
   
gs2352pTrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2352pTrapEventSeverity 28 }

gs2352pSMTP                                             OBJECT IDENTIFIER ::= { gs2352pConfiguration 8 }

gs2352pSMTPMailServer OBJECT-TYPE
   SYNTAX      DisplayString
   MAX-ACCESS  read-write
   STATUS      current
   DESCRIPTION
       " Up to 47 characters describing email server. "
   ::= { gs2352pSMTP 1 }

gs2352pSMTPUserName OBJECT-TYPE
   SYNTAX      DisplayString
   MAX-ACCESS  read-write
   STATUS      current
   DESCRIPTION
       " Up to 47 characters describing user name. "
   ::= { gs2352pSMTP 2 }

gs2352pSMTPPassword OBJECT-TYPE
   SYNTAX      DisplayString
   MAX-ACCESS  read-write
   STATUS      current
   DESCRIPTION
       " Up to 47 characters describing password. "
   ::= { gs2352pSMTP 3 }

gs2352pSMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2352pSMTP 4 }

gs2352pSMTPSender OBJECT-TYPE
   SYNTAX      DisplayString
   MAX-ACCESS  read-write
   STATUS      current
   DESCRIPTION
       " Up to 47 characters describing sender. "
   ::= { gs2352pSMTP 5 }

gs2352pSMTPReturnPath OBJECT-TYPE
   SYNTAX      DisplayString
   MAX-ACCESS  read-write
   STATUS      current
   DESCRIPTION
       " Up to 47 characters describing return path. "
   ::= { gs2352pSMTP 6 }

gs2352pSMTPEmailAddress1 OBJECT-TYPE
   SYNTAX      DisplayString
   MAX-ACCESS  read-write
   STATUS      current
   DESCRIPTION
       " Up to 47 characters describing mail address. "
   ::= { gs2352pSMTP 7 }

gs2352pSMTPEmailAddress2 OBJECT-TYPE
   SYNTAX      DisplayString
   MAX-ACCESS  read-write
   STATUS      current
   DESCRIPTION
       " Up to 47 characters describing mail address. "
   ::= { gs2352pSMTP 8 }

gs2352pSMTPEmailAddress3 OBJECT-TYPE
   SYNTAX      DisplayString
   MAX-ACCESS  read-write
   STATUS      current
   DESCRIPTION
       " Up to 47 characters describing mail address. "
   ::= { gs2352pSMTP 9 }

gs2352pSMTPEmailAddress4 OBJECT-TYPE
   SYNTAX      DisplayString
   MAX-ACCESS  read-write
   STATUS      current
   DESCRIPTION
       " Up to 47 characters describing mail address. "
   ::= { gs2352pSMTP 10 }

gs2352pSMTPEmailAddress5 OBJECT-TYPE
   SYNTAX      DisplayString
   MAX-ACCESS  read-write
   STATUS      current
   DESCRIPTION
       " Up to 47 characters describing mail address. "
   ::= { gs2352pSMTP 11 }

gs2352pSMTPEmailAddress6 OBJECT-TYPE
   SYNTAX      DisplayString
   MAX-ACCESS  read-write
   STATUS      current
   DESCRIPTION
       " Up to 47 characters describing mail address. "
   ::= { gs2352pSMTP 12 }


gs2352pACL                                                   OBJECT IDENTIFIER ::= { gs2352pConfiguration 9 }

gs2352pACLPortsConfTable OBJECT-TYPE
   SYNTAX      SEQUENCE OF GS2352PACLPortsConfEntry
   MAX-ACCESS  not-accessible
   STATUS      current
   DESCRIPTION
       " "
   ::= { gs2352pACL 1 }

gs2352pACLPortsConfEntry OBJECT-TYPE
   SYNTAX      GS2352PACLPortsConfEntry
   MAX-ACCESS  not-accessible
   STATUS      current
   DESCRIPTION
       ""
   INDEX    { gs2352pACLPortsConfPort  }
   ::= { gs2352pACLPortsConfTable 1 }

GS2352PACLPortsConfEntry ::= SEQUENCE {
   gs2352pACLPortsConfPort               Integer32,
   gs2352pACLPortsConfPolicyID           Integer32,
   gs2352pACLPortsConfAction             INTEGER,
   gs2352pACLPortsConfRateLimiterID      Integer32,
   gs2352pACLPortsConfPortRedirect       Integer32,
   gs2352pACLPortsConfLogging            INTEGER,
   gs2352pACLPortsConfShutdown           INTEGER,
   gs2352pACLPortsConfState              INTEGER,
   gs2352pACLPortsConfCounter            Counter32
}

gs2352pACLPortsConfPort OBJECT-TYPE
   SYNTAX      Integer32(1..4095)
   MAX-ACCESS  not-accessible
   STATUS      current
   DESCRIPTION
       " "
   ::= { gs2352pACLPortsConfEntry 1 }

gs2352pACLPortsConfPolicyID OBJECT-TYPE
   SYNTAX      Integer32(0..255)
   MAX-ACCESS  read-write
   STATUS      current
   DESCRIPTION
       "default: 0, range : 0 - 255 "
   ::= { gs2352pACLPortsConfEntry 2 }

gs2352pACLPortsConfAction OBJECT-TYPE
   SYNTAX      INTEGER { deny(0), permit(1) }
   MAX-ACCESS  read-write
   STATUS      current
   DESCRIPTION
       "default: 1,
        0: Deny
        1: Permit"
   ::= { gs2352pACLPortsConfEntry 3 }

gs2352pACLPortsConfRateLimiterID OBJECT-TYPE
   SYNTAX      Integer32(0..12)
   MAX-ACCESS  read-write
   STATUS      current
   DESCRIPTION
       "default: 0,
        0: Disable
        range : 0 - 12 "
   ::= { gs2352pACLPortsConfEntry 4 }

gs2352pACLPortsConfPortRedirect OBJECT-TYPE
   SYNTAX      Integer32(0..4095)
   MAX-ACCESS  read-write
   STATUS      current
   DESCRIPTION
       "default: 0
        0: Disable
        range : 0 - end port number "
   ::= { gs2352pACLPortsConfEntry 5 }

gs2352pACLPortsConfLogging OBJECT-TYPE
   SYNTAX      INTEGER { disable(0), enable(1) }
   MAX-ACCESS  read-write
   STATUS      current
   DESCRIPTION
       "default: 0
        0: Disable
        1: Enable "
   ::= { gs2352pACLPortsConfEntry 7 }

gs2352pACLPortsConfShutdown OBJECT-TYPE
   SYNTAX      INTEGER { disable(0), enable(1) }
   MAX-ACCESS  read-write
   STATUS      current
   DESCRIPTION
       "default: 0
        0: Disable
        1: Enable "
   ::= { gs2352pACLPortsConfEntry 8 }
   
gs2352pACLPortsConfState OBJECT-TYPE
   SYNTAX      INTEGER { disable(0), enable(1) }
   MAX-ACCESS  read-write
   STATUS      current
   DESCRIPTION
       "default: 1
        0: Disable
        1: Enable "
   ::= { gs2352pACLPortsConfEntry 9 }

gs2352pACLPortsConfCounter OBJECT-TYPE
   SYNTAX      Counter32
   MAX-ACCESS  read-only
   STATUS      current
   DESCRIPTION
       "Counts the number of frames that match this ACE. "
   ::= { gs2352pACLPortsConfEntry 10 }


gs2352pACLRateLimiterTable OBJECT-TYPE
   SYNTAX      SEQUENCE OF GS2352PACLRateLimiterEntry
   MAX-ACCESS  not-accessible
   STATUS      current
   DESCRIPTION
       " "
   ::= { gs2352pACL 2 }

gs2352pACLRateLimiterEntry OBJECT-TYPE
   SYNTAX      GS2352PACLRateLimiterEntry
   MAX-ACCESS  not-accessible
   STATUS      current
   DESCRIPTION
       ""
   INDEX    { gs2352pACLRateLimiterID  }
   ::= { gs2352pACLRateLimiterTable 1 }

GS2352PACLRateLimiterEntry ::= SEQUENCE {
   gs2352pACLRateLimiterID       Integer32,
   gs2352pACLRateLimiterRate     Integer32
}

gs2352pACLRateLimiterID OBJECT-TYPE
   SYNTAX      Integer32(1..12)
   MAX-ACCESS  not-accessible
   STATUS      current
   DESCRIPTION
       " Rate Limiter ID.
         range : 1-12 "
   ::= { gs2352pACLRateLimiterEntry 1 }

gs2352pACLRateLimiterRate OBJECT-TYPE
   SYNTAX      Integer32(0..3276700)
   MAX-ACCESS  read-write
   STATUS      current
   DESCRIPTION
       "default: 1, 
        range : <0-3276700> pps
       "
   ::= { gs2352pACLRateLimiterEntry 3 }


gs2352pACLACE                                          OBJECT IDENTIFIER ::= { gs2352pACL 3 }

gs2352pACLACECreate OBJECT-TYPE
   SYNTAX       INTEGER { none(0), create(1) }
   MAX-ACCESS   read-write
   STATUS       current
   DESCRIPTION
       "default: 0
        0 : None  (read only)
        1 : Create an ACE entry"
   ::= { gs2352pACLACE 1 }

gs2352pACLACETable OBJECT-TYPE
   SYNTAX      SEQUENCE OF GS2352PACLACEEntry
   MAX-ACCESS  not-accessible
   STATUS      current
   DESCRIPTION
       " Create ACL ACE entry. "
   ::= { gs2352pACLACE 2 }

gs2352pACLACEEntry OBJECT-TYPE
   SYNTAX      GS2352PACLACEEntry
   MAX-ACCESS  not-accessible
   STATUS      current
   DESCRIPTION
       ""
   INDEX    { gs2352pACLACEIndex  }
   ::= { gs2352pACLACETable 1 }

GS2352PACLACEEntry ::= SEQUENCE {
   gs2352pACLACEIndex                Integer32,
   gs2352pACLACEID                   Integer32,
   gs2352pACLACENextID               Integer32,
   gs2352pACLACEIngressPort          DisplayString,
   gs2352pACLACEPortPolicyNumber     Integer32,
   
   gs2352pACLACEPortPolicyBitmask    Integer32,
   gs2352pACLACEFrameType            INTEGER,
   gs2352pACLACEAction               INTEGER,
   gs2352pACLACEDenyPortRedirect     DisplayString,
   gs2352pACLACELogging              INTEGER,
   
   gs2352pACLACERateLimiter          Integer32,
   gs2352pACLACEShutdown             INTEGER,
   gs2352pACLACEVLANTagPriority      Integer32,
   
   gs2352pACLACEVLANVID              Integer32,
   gs2352pACLACEEtherType            Integer32,
   gs2352pACLACESMAC                 DisplayString,
   gs2352pACLACEDMACType             INTEGER,
   gs2352pACLACEDMAC                 DisplayString,
   
   gs2352pACLACEArpOpcode            INTEGER,
   gs2352pACLACEArpFlagsRequestReply INTEGER,
   gs2352pACLACEArpFlagsArpSmac      INTEGER,
   gs2352pACLACEArpFlagsRarpDmac     INTEGER,
   gs2352pACLACEArpFlagsLength       INTEGER,
   
   gs2352pACLACEArpFlagsIp           INTEGER,
   gs2352pACLACEArpFlagsEthernet     INTEGER,
   gs2352pACLACESIPType              INTEGER,
   gs2352pACLACESIPIPAddress         IpAddress,                      
   gs2352pACLACESIPNetworkPrefix     Integer32,
   
   gs2352pACLACEDIPType              INTEGER,
   gs2352pACLACEDIPIPAddress         IpAddress,                      
   gs2352pACLACEDIPNetworkPrefix     Integer32,
   
   gs2352pACLACEIPProtocol           Integer32,
   gs2352pACLACEIPFlagsTTL           INTEGER,
   gs2352pACLACEIPFlagsOptions       INTEGER,
   gs2352pACLACEIPFlagsFragment      INTEGER,
   gs2352pACLACEICMPType             Integer32,
   
   gs2352pACLACEICMPCode             Integer32,
   gs2352pACLACESourcePortMin        Integer32,
   gs2352pACLACESourcePortMax        Integer32,
   gs2352pACLACEDestPortMin          Integer32,
   gs2352pACLACEDestPortMax          Integer32,
   
   gs2352pACLACETCPFlagsFin          INTEGER,
   gs2352pACLACETCPFlagsSyn          INTEGER,
   gs2352pACLACETCPFlagsRst          INTEGER,
   gs2352pACLACETCPFlagsPsh          INTEGER,
   gs2352pACLACETCPFlagsAck          INTEGER,
   
   gs2352pACLACETCPFlagsUrg          INTEGER,
   
   gs2352pACLACERowStatus            INTEGER
}

gs2352pACLACEIndex OBJECT-TYPE
   SYNTAX      Integer32(1..256)
   MAX-ACCESS  not-accessible
   STATUS      current
   DESCRIPTION
       " "
   ::= { gs2352pACLACEEntry 1 }

gs2352pACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2352pACLACEEntry 2 }

gs2352pACLACENextID OBJECT-TYPE
   SYNTAX      Integer32(0..256)
   MAX-ACCESS  read-write
   STATUS      current
   DESCRIPTION
       " If the next ACE ID is non zero, the ACE will be placed
         before this ACE in the list. If the next ACE ID is zero,
         the ACE will be placed last in the list.
         range : 0 - 256. "
   ::= { gs2352pACLACEEntry 3 }

gs2352pACLACEIngressPort OBJECT-TYPE
   SYNTAX      DisplayString
   MAX-ACCESS  read-write
   STATUS      current
   DESCRIPTION
       " Indicates the ingress port of the ACE. Possible values are: 
         All: The ACE will match all ingress port. 
         Port: The ACE will match a specific ingress port.Format: 1,3,6."
   ::= { gs2352pACLACEEntry 4 }

gs2352pACLACEPortPolicyNumber OBJECT-TYPE
   SYNTAX      Integer32(0..255)
   MAX-ACCESS  read-write
   STATUS      current
   DESCRIPTION
       " policy value.
         range : 0 - 255. "
   ::= { gs2352pACLACEEntry 5 }
   
gs2352pACLACEPortPolicyBitmask OBJECT-TYPE
   SYNTAX      Integer32(0..255)
   MAX-ACCESS  read-write
   STATUS      current
   DESCRIPTION
       " policy bitmask.
         range : 0 - 255(0xff). "
   ::= { gs2352pACLACEEntry 6 }

gs2352pACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2352pACLACEEntry 7 }

gs2352pACLACEAction OBJECT-TYPE
   SYNTAX      INTEGER { deny(0), permit(1) }
   MAX-ACCESS  read-write
   STATUS      current
   DESCRIPTION
       "default: 1,
        0: Deny
        1: Permit"
   ::= { gs2352pACLACEEntry 8 }

gs2352pACLACEDenyPortRedirect OBJECT-TYPE
   SYNTAX      DisplayString
   MAX-ACCESS  read-write
   STATUS      current
   DESCRIPTION
       " Frames that hit the ACE are redirected to the port number specified here.  
         Disabled: indicates that the port redirect operation is disabled. 
         Port Format: 1,3,6."
   ::= { gs2352pACLACEEntry 9 }

gs2352pACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2352pACLACEEntry 10 }

gs2352pACLACERateLimiter OBJECT-TYPE
   SYNTAX      Integer32(0..12)
   MAX-ACCESS  read-write
   STATUS      current
   DESCRIPTION
       "default: 0,
        0: Disable
        range : 0 - 12 "
   ::= { gs2352pACLACEEntry 12 }

gs2352pACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2352pACLACEEntry 13 }

gs2352pACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2352pACLACEEntry 15 }

gs2352pACLACEVLANVID OBJECT-TYPE
   SYNTAX      Integer32(0..4094)
   MAX-ACCESS  read-write
   STATUS      current
   DESCRIPTION
       "Specify the VLAN ID filter for this ACE.
        The vid can't be set when 802.1Q Tagged is disabled. 
        default: 0,
        0: Any - No VLAN ID filter is specified.
        range : 0 - 4094 "
   ::= { gs2352pACLACEEntry 16 }

gs2352pACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2352pACLACEEntry 17 }

gs2352pACLACESMAC OBJECT-TYPE
   SYNTAX      DisplayString
   MAX-ACCESS  read-write
   STATUS      current
   DESCRIPTION
       " Configure source MAC address for this ACE.
         <mac-address>: A frame that hits this ACE matches this source MAC address value. 
         Any: Don't care."
   ::= { gs2352pACLACEEntry 18 }

gs2352pACLACEDMACType OBJECT-TYPE
   SYNTAX      INTEGER { any(0), broadcast(1), unicast(2), multicast(3) , macaddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address
        range : 0 - 4 "
   ::= { gs2352pACLACEEntry 19 }

gs2352pACLACEDMAC OBJECT-TYPE
   SYNTAX      DisplayString
   MAX-ACCESS  read-write
   STATUS      current
   DESCRIPTION
       " Configure destination MAC address for this ACE. 
         <mac-address>: A frame that hits this ACE matches this destination MAC address value.            
         Any: Don't care.
         Broadcast: Frame must be broadcast.
         Unicast: Frame must be unicast.
         Multicast: Frame must be multicast. "
   ::= { gs2352pACLACEEntry 20 }

gs2352pACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2352pACLACEEntry 21 }

gs2352pACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2352pACLACEEntry 22 }

gs2352pACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2352pACLACEEntry 23 }   

gs2352pACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2352pACLACEEntry 24 }

gs2352pACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2352pACLACEEntry 25 }

gs2352pACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2352pACLACEEntry 26 }

gs2352pACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2352pACLACEEntry 27 }
   
gs2352pACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 2"
   ::= { gs2352pACLACEEntry 28 }   
   
gs2352pACLACESIPIPAddress OBJECT-TYPE
   SYNTAX      IpAddress
   MAX-ACCESS  read-write
   STATUS      current
   DESCRIPTION
       "A frame that hits this ACE matches this source IP address value."
   ::= { gs2352pACLACEEntry 29 }      
   
gs2352pACLACESIPNetworkPrefix OBJECT-TYPE
   SYNTAX      Integer32(1..32)
   MAX-ACCESS  read-write
   STATUS      current
   DESCRIPTION
       "Network prefix.
        default: 32,
        0: No data.
        range : 1 - 32"
   ::= { gs2352pACLACEEntry 30 }   
   

gs2352pACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2352pACLACEEntry 32 }   
   
gs2352pACLACEDIPIPAddress OBJECT-TYPE
   SYNTAX      IpAddress
   MAX-ACCESS  read-write
   STATUS      current
   DESCRIPTION
       "A frame that hits this ACE matches this destination IP address value."
   ::= { gs2352pACLACEEntry 33 }      
   
gs2352pACLACEDIPNetworkPrefix OBJECT-TYPE
   SYNTAX      Integer32(0..32)
   MAX-ACCESS  read-write
   STATUS      current
   DESCRIPTION
       "Network prefix.
        default: 32,
        0: No data.
        range : 1 - 32"
   ::= { gs2352pACLACEEntry 34 }  
   
   
gs2352pACLACEIPProtocol OBJECT-TYPE
   SYNTAX      Integer32(0..257)
   MAX-ACCESS  read-write
   STATUS      current
   DESCRIPTION
       "Configure IP protocol for this ACE.
        default: 256,
        256: Any - Don't care.
        257: No data.
        range : 0 - 257"
   ::= { gs2352pACLACEEntry 36 } 

gs2352pACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2352pACLACEEntry 37 }   
   
gs2352pACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2352pACLACEEntry 38 }

gs2352pACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2352pACLACEEntry 39 }

gs2352pACLACEICMPType OBJECT-TYPE
   SYNTAX      Integer32(0..257)
   MAX-ACCESS  read-write
   STATUS      current
   DESCRIPTION
       "Configure ICMP type for this ACE.
        default: 256,
        256: Any - Don't care.
        257: No data.
        range : 0 - 257"
   ::= { gs2352pACLACEEntry 40 }   

gs2352pACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2352pACLACEEntry 41 } 

gs2352pACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2352pACLACEEntry 42 }     
   
gs2352pACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2352pACLACEEntry 43 } 
      
gs2352pACLACEDestPortMin OBJECT-TYPE
   SYNTAX      Integer32(0..65536)
   MAX-ACCESS  read-write
   STATUS      current
   DESCRIPTION
       "Configure Destination UDP/TCP port range for this ACE.
        default: 0,
        65536: No data.
        range : 0 - 65536"
   ::= { gs2352pACLACEEntry 44 }     

gs2352pACLACEDestPortMax OBJECT-TYPE
   SYNTAX      Integer32(0..65536)
   MAX-ACCESS  read-write
   STATUS      current
   DESCRIPTION
       "Configure Destination UDP/TCP port range for this ACE.
        default: 0,
        65536: No data.
        range : 0 - 65536"
   ::= { gs2352pACLACEEntry 45 }

gs2352pACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2352pACLACEEntry 46 }

gs2352pACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2352pACLACEEntry 47 }

gs2352pACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2352pACLACEEntry 48 }

gs2352pACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2352pACLACEEntry 49 }

gs2352pACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2352pACLACEEntry 50 }

gs2352pACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2352pACLACEEntry 51 }

gs2352pACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2352pACLACEEntry 66 }


gs2352pACLACEClear OBJECT-TYPE
   SYNTAX       INTEGER { noAction(0), clear(1) }
   MAX-ACCESS   read-write
   STATUS       current
   DESCRIPTION
       "default: 0
        0 : No action
        1 : Clear all ACL counters."
   ::= { gs2352pACLACE 3 }

gs2352pACLACEMoveACEID OBJECT-TYPE
   SYNTAX       Integer32(0..256)
   MAX-ACCESS   read-write
   STATUS       current
   DESCRIPTION
       "Move ACE,
        default: 0
        ACE ID must be exist.
        range : 0 - 256."
   ::= { gs2352pACLACE 4 }

gs2352pACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2352pACLACE 5 }

gs2352pACLACEStatusTable OBJECT-TYPE
   SYNTAX      SEQUENCE OF GS2352PACLACEStatusEntry
   MAX-ACCESS  not-accessible
   STATUS      current
   DESCRIPTION
       " ACL ACE Status entry. "
   ::= { gs2352pACLACE 6 }

gs2352pACLACEStatusEntry OBJECT-TYPE
   SYNTAX      GS2352PACLACEStatusEntry
   MAX-ACCESS  not-accessible
   STATUS      current
   DESCRIPTION
       ""
   INDEX    { gs2352pACLACEStatusIndex  }
   ::= { gs2352pACLACEStatusTable 1 }

GS2352PACLACEStatusEntry ::= SEQUENCE {
   gs2352pACLACEStatusIndex          Integer32,
   gs2352pACLACEStatusUser           DisplayString,
   gs2352pACLACEStatusID             Integer32,
   gs2352pACLACEStatusIngressPort    DisplayString,
   gs2352pACLACEStatusFrameType      DisplayString,
   gs2352pACLACEStatusAction         DisplayString,
   gs2352pACLACEStatusRateLimiter    DisplayString,
   gs2352pACLACEStatusPortCopy       DisplayString,
   gs2352pACLACEStatusMirror         DisplayString,
   gs2352pACLACEStatusCPU            DisplayString,
   gs2352pACLACEStatusCounter        Counter32,
   gs2352pACLACEStatusConflict       DisplayString
}

gs2352pACLACEStatusIndex OBJECT-TYPE
   SYNTAX      Integer32(1..256)
   MAX-ACCESS  not-accessible
   STATUS      current
   DESCRIPTION
       " "
   ::= { gs2352pACLACEStatusEntry 1 }

gs2352pACLACEStatusUser OBJECT-TYPE
   SYNTAX      DisplayString
   MAX-ACCESS  read-only
   STATUS      current
   DESCRIPTION
       " Indicates the ACL user. 
         S : Static.  
         IPMG : IP Management.  
         IPSG : IP Source Guard.  
         IPMC : IPMC.  
         ARPI : Arp Inspection.  
         UPnP : UPnP.  
         DHCP : DHCP. "
   ::= { gs2352pACLACEStatusEntry 2 }

gs2352pACLACEStatusID OBJECT-TYPE
   SYNTAX      Integer32(1..256)
   MAX-ACCESS  read-only
   STATUS      current
   DESCRIPTION
       " ACE ID.
         range : 1 - 256. "
   ::= { gs2352pACLACEStatusEntry 3 }

gs2352pACLACEStatusIngressPort OBJECT-TYPE
   SYNTAX      DisplayString
   MAX-ACCESS  read-only
   STATUS      current
   DESCRIPTION
       " Indicates the ingress port of the ACE. Possible values are: 
         All: The ACE will match all ingress port. 
         Port: The ACE will match a specific ingress port. "
   ::= { gs2352pACLACEStatusEntry 4 }

gs2352pACLACEStatusFrameType OBJECT-TYPE
   SYNTAX      DisplayString
   MAX-ACCESS  read-only
   STATUS      current
   DESCRIPTION
       " Indicates the frame type of the ACE. "
   ::= { gs2352pACLACEStatusEntry 5 }

gs2352pACLACEStatusAction OBJECT-TYPE
   SYNTAX      DisplayString
   MAX-ACCESS  read-only
   STATUS      current
   DESCRIPTION
       " Indicates the forwarding action of the ACE. "
   ::= { gs2352pACLACEStatusEntry 6 }

gs2352pACLACEStatusRateLimiter OBJECT-TYPE
   SYNTAX      DisplayString
   MAX-ACCESS  read-only
   STATUS      current
   DESCRIPTION
       " Indicates the rate limiter number of the ACE. "
   ::= { gs2352pACLACEStatusEntry 7 }

gs2352pACLACEStatusPortCopy OBJECT-TYPE
   SYNTAX      DisplayString
   MAX-ACCESS  read-only
   STATUS      current
   DESCRIPTION
       " Indicates the port redirect operation of the ACE. Frames matching the ACE are redirected to the port number. "
   ::= { gs2352pACLACEStatusEntry 8 }

gs2352pACLACEStatusMirror OBJECT-TYPE
   SYNTAX      DisplayString
   MAX-ACCESS  read-only
   STATUS      current
   DESCRIPTION
       " Specify the mirror operation of this port. "
   ::= { gs2352pACLACEStatusEntry 9 }

gs2352pACLACEStatusCPU OBJECT-TYPE
   SYNTAX      DisplayString
   MAX-ACCESS  read-only
   STATUS      current
   DESCRIPTION
       " Forward packet that matched the specific ACE to CPU. "
   ::= { gs2352pACLACEStatusEntry 10 }

gs2352pACLACEStatusCounter OBJECT-TYPE
   SYNTAX      Counter32
   MAX-ACCESS  read-only
   STATUS      current
   DESCRIPTION
       " The counter indicates the number of times the ACE was hit by a frame. "
   ::= { gs2352pACLACEStatusEntry 11 }
   
gs2352pACLACEStatusConflict OBJECT-TYPE
   SYNTAX      DisplayString
   MAX-ACCESS  read-only
   STATUS      current
   DESCRIPTION
       " Indicates the hardware status of the specific ACE. The specific ACE is not applied to the hardware due to hardware limitations. "
   ::= { gs2352pACLACEStatusEntry 12 }

gs2352pLoopProtection                                                  OBJECT IDENTIFIER ::= { gs2352pConfiguration 12 }

gs2352pLoopProtectionConfig                                            OBJECT IDENTIFIER ::= { gs2352pLoopProtection 1 }

gs2352pLoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2352pLoopProtectionConfig 1 }
   
gs2352pLoopProtectionTranmisstionTime OBJECT-TYPE
   SYNTAX      Integer32(1..10)
   MAX-ACCESS  read-write
   STATUS      current
   DESCRIPTION
       "Configure loop protection transmit interval.
        default: 5,
        range: 1-10. "
   ::= { gs2352pLoopProtectionConfig 2 }
   
gs2352pLoopProtectionShutdownTime OBJECT-TYPE
   SYNTAX      Integer32(0..604800)
   MAX-ACCESS  read-write
   STATUS      current
   DESCRIPTION
       "Configure loop protection shutdown time.
        default: 180,
        range: 0-604800. "
   ::= { gs2352pLoopProtectionConfig 3 }

gs2352pLoopProtectionConfigurationTable OBJECT-TYPE
   SYNTAX      SEQUENCE OF GS2352PLoopProtectionConfigurationEntry
   MAX-ACCESS  not-accessible
   STATUS      current
   DESCRIPTION
       " Show Loop Protection configurations. "
   ::= { gs2352pLoopProtectionConfig 4 }

gs2352pLoopProtectionConfigurationEntry OBJECT-TYPE
   SYNTAX      GS2352PLoopProtectionConfigurationEntry
   MAX-ACCESS  not-accessible
   STATUS      current
   DESCRIPTION
       ""
   INDEX    { gs2352pLoopProtectionConfPort  }
   ::= { gs2352pLoopProtectionConfigurationTable 1 }

GS2352PLoopProtectionConfigurationEntry ::= SEQUENCE {
   gs2352pLoopProtectionConfPort	        Integer32,
   gs2352pLoopProtectionConfEnable	INTEGER,
   gs2352pLoopProtectionConfAction	INTEGER,
   gs2352pLoopProtectionConfTxmode	INTEGER
}

gs2352pLoopProtectionConfPort OBJECT-TYPE
   SYNTAX      Integer32(1..4095)
   MAX-ACCESS  not-accessible
   STATUS      current
   DESCRIPTION
       " port, range : 1 - port number. "
   ::= { gs2352pLoopProtectionConfigurationEntry 1 }

gs2352pLoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2352pLoopProtectionConfigurationEntry 2 }

gs2352pLoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2352pLoopProtectionConfigurationEntry 3 }
   
gs2352pLoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2352pLoopProtectionConfigurationEntry 4 }
   
gs2352pLoopProtectionStatusTable OBJECT-TYPE
   SYNTAX      SEQUENCE OF GS2352PLoopProtectionStatusEntry
   MAX-ACCESS  not-accessible
   STATUS      current
   DESCRIPTION
       " Show Loop Protection Status. "
   ::= { gs2352pLoopProtection 2 }

gs2352pLoopProtectionStatusEntry OBJECT-TYPE
   SYNTAX      GS2352PLoopProtectionStatusEntry
   MAX-ACCESS  not-accessible
   STATUS      current
   DESCRIPTION
       ""
   INDEX    { gs2352pLoopProtectionStatusPort  }
   ::= { gs2352pLoopProtectionStatusTable 1 }

GS2352PLoopProtectionStatusEntry ::= SEQUENCE {
   gs2352pLoopProtectionStatusPort	       Integer32,
   gs2352pLoopProtectionStatusAction	       DisplayString,
   gs2352pLoopProtectionStatusTransmit	       DisplayString,
   gs2352pLoopProtectionStatusLoops	       Integer32,
   gs2352pLoopProtectionStatusStatus	       DisplayString,
   gs2352pLoopProtectionStatusLoop	       DisplayString,
   gs2352pLoopProtectionStatusTimeLastLoop  DisplayString
}

gs2352pLoopProtectionStatusPort OBJECT-TYPE
   SYNTAX      Integer32(1..4095)
   MAX-ACCESS  not-accessible
   STATUS      current
   DESCRIPTION
       " port, range : 1 - port number. "
   ::= { gs2352pLoopProtectionStatusEntry 1 }
   
gs2352pLoopProtectionStatusAction OBJECT-TYPE
   SYNTAX      DisplayString
   MAX-ACCESS  read-only
   STATUS      current
   DESCRIPTION
       " The currently configured port action. "
   ::= { gs2352pLoopProtectionStatusEntry 2 }
   
gs2352pLoopProtectionStatusTransmit OBJECT-TYPE
   SYNTAX      DisplayString
   MAX-ACCESS  read-only
   STATUS      current
   DESCRIPTION
       " The currently configured port transmit mode. "
   ::= { gs2352pLoopProtectionStatusEntry 3 }
   
gs2352pLoopProtectionStatusLoops OBJECT-TYPE
   SYNTAX      Integer32(0..1000000)
   MAX-ACCESS  read-only
   STATUS      current
   DESCRIPTION
       " The number of loops detected on this port. "
   ::= { gs2352pLoopProtectionStatusEntry 4 }
   
gs2352pLoopProtectionStatusStatus OBJECT-TYPE
   SYNTAX      DisplayString
   MAX-ACCESS  read-only
   STATUS      current
   DESCRIPTION
       " The current loop protection status of the port. "
   ::= { gs2352pLoopProtectionStatusEntry 5 }
   
gs2352pLoopProtectionStatusLoop OBJECT-TYPE
   SYNTAX      DisplayString
   MAX-ACCESS  read-only
   STATUS      current
   DESCRIPTION
       " Whether a loop is currently detected on the port. "
   ::= { gs2352pLoopProtectionStatusEntry 6 }

gs2352pLoopProtectionStatusTimeLastLoop OBJECT-TYPE
   SYNTAX      DisplayString
   MAX-ACCESS  read-only
   STATUS      current
   DESCRIPTION
       " The time of the last loop event detected. "
   ::= { gs2352pLoopProtectionStatusEntry 7 }

gs2352pPoe                                                           OBJECT IDENTIFIER ::= { gs2352pConfiguration 13 }

gs2352pPoeStatus                                            OBJECT IDENTIFIER ::= { gs2352pPoe 1 }

gs2352pPoeStatusTable OBJECT-TYPE
   SYNTAX      SEQUENCE OF GS2352PPoeStatusEntry
   MAX-ACCESS  not-accessible
   STATUS      current
   DESCRIPTION
       " Configure PoE Scheduling Table. "
   ::= { gs2352pPoeStatus 1 }

gs2352pPoeStatusEntry OBJECT-TYPE
   SYNTAX      GS2352PPoeStatusEntry
   MAX-ACCESS  not-accessible
   STATUS      current
   DESCRIPTION
       ""
   INDEX    { gs2352pPoeStatusLocalPort }
   ::= { gs2352pPoeStatusTable 1 }

GS2352PPoeStatusEntry ::= SEQUENCE {
   gs2352pPoeStatusLocalPort	        Integer32,
   gs2352pPoeStatusPDclass	        INTEGER,
   gs2352pPoeStatusPowerRequested	    DisplayString,
   gs2352pPoeStatusPowerAllocated     DisplayString,
   gs2352pPoeStatusPowerUsed          DisplayString,
   gs2352pPoeStatusCurrentUsed        DisplayString,
   gs2352pPoeStatusPriority           DisplayString,
   gs2352pPoeStatusPortStatus         DisplayString
}

gs2352pPoeStatusLocalPort OBJECT-TYPE
   SYNTAX      Integer32(1..4094)
   MAX-ACCESS  not-accessible
   STATUS      current
   DESCRIPTION
       " port, range : 1 - port number. "
   ::= { gs2352pPoeStatusEntry 1}

gs2352pPoeStatusPDclass OBJECT-TYPE
   SYNTAX      INTEGER (0..4)
   MAX-ACCESS  read-only
   STATUS      current
   DESCRIPTION
       " Indicates the QCL user.
         0: Max. power 15.4 W,
         1: Max. power 4.0 W,
         2: Max. power 7.0 W,
         3: Max. power 15.4 W,
         4: Max. power 30.0 W. "
   ::= { gs2352pPoeStatusEntry 2 }

gs2352pPoeStatusPowerRequested OBJECT-TYPE
   SYNTAX      DisplayString
   MAX-ACCESS  read-only
   STATUS      current
   DESCRIPTION
      " The Power Requested shows the requested amount of power the PD wants to be reserved. "
   ::= { gs2352pPoeStatusEntry 3}

gs2352pPoeStatusPowerAllocated OBJECT-TYPE
   SYNTAX      DisplayString
   MAX-ACCESS  read-only
   STATUS      current
   DESCRIPTION
      " The Power Allocated shows the amount of power the switch has allocated for the PD. "
   ::= { gs2352pPoeStatusEntry 4}

gs2352pPoeStatusPowerUsed OBJECT-TYPE
   SYNTAX      DisplayString
   MAX-ACCESS  read-only
   STATUS      current
   DESCRIPTION
      " The Power Used shows how much power the PD currently is using. "
   ::= { gs2352pPoeStatusEntry 5}

gs2352pPoeStatusCurrentUsed OBJECT-TYPE
   SYNTAX      DisplayString
   MAX-ACCESS  read-only
   STATUS      current
   DESCRIPTION
      " The Power Used shows how much current the PD currently is using. "
   ::= { gs2352pPoeStatusEntry 6}

gs2352pPoeStatusPriority OBJECT-TYPE
   SYNTAX      DisplayString
   MAX-ACCESS  read-only
   STATUS      current
   DESCRIPTION
      " The Priority shows the port's priority configured by the user.  "
   ::= { gs2352pPoeStatusEntry 7}

gs2352pPoeStatusPortStatus OBJECT-TYPE
   SYNTAX      DisplayString
   MAX-ACCESS  read-only
   STATUS      current
   DESCRIPTION
      " The Port Status shows the port's status.  "
   ::= { gs2352pPoeStatusEntry 8}


gs2352pPoeStatusTotalPowerRequested OBJECT-TYPE
   SYNTAX      DisplayString
   MAX-ACCESS  read-only
   STATUS      current
   DESCRIPTION
      " Total Power Requested."
   ::= { gs2352pPoeStatus 2}

gs2352pPoeStatusTotalPowerAllocated OBJECT-TYPE
   SYNTAX      DisplayString
   MAX-ACCESS  read-only
   STATUS      current
   DESCRIPTION
      " Total Power allocated."
   ::= { gs2352pPoeStatus 3}

gs2352pPoeStatusTotalPowerUsed OBJECT-TYPE
   SYNTAX      DisplayString
   MAX-ACCESS  read-only
   STATUS      current
   DESCRIPTION
      " Total Power Used."
   ::= { gs2352pPoeStatus 4}

gs2352pPoeStatusTotalCurrentUsed OBJECT-TYPE
   SYNTAX      DisplayString
   MAX-ACCESS  read-only
   STATUS      current
   DESCRIPTION
      " Total Current Used."
   ::= { gs2352pPoeStatus 5}

gs2352pPoeMcuVersion OBJECT-TYPE
   SYNTAX      DisplayString
   MAX-ACCESS  read-only
   STATUS      current
   DESCRIPTION
      " PoE MCU version."
   ::= { gs2352pPoeStatus 6 }

gs2352pPoePowerDelay                                                 OBJECT IDENTIFIER ::= { gs2352pPoe 2 }

gs2352pPoePowerDelayTable OBJECT-TYPE
   SYNTAX      SEQUENCE OF GS2352PPoePowerDelayEntry
   MAX-ACCESS  not-accessible
   STATUS      current
   DESCRIPTION
       " Configure PoE Power Delay mode. "
   ::= { gs2352pPoePowerDelay 1 }

gs2352pPoePowerDelayEntry OBJECT-TYPE
   SYNTAX      GS2352PPoePowerDelayEntry
   MAX-ACCESS  not-accessible
   STATUS      current
   DESCRIPTION
       ""
   INDEX    { gs2352pPoePowerDelayPort  }
   ::= { gs2352pPoePowerDelayTable 1 }

GS2352PPoePowerDelayEntry ::= SEQUENCE {
   gs2352pPoePowerDelayPort	        Integer32,
   gs2352pPoePowerDelayMode	        INTEGER,
   gs2352pPoePowerDelayTime               Integer32
}

gs2352pPoePowerDelayPort OBJECT-TYPE
   SYNTAX      Integer32(1..4094)
   MAX-ACCESS  not-accessible
   STATUS      current
   DESCRIPTION
       " port, range : 1 - port number. "
   ::= { gs2352pPoePowerDelayEntry 1 }

gs2352pPoePowerDelayMode OBJECT-TYPE
   SYNTAX      INTEGER { disable(0), enable(1) }
   MAX-ACCESS  read-write
   STATUS      current
   DESCRIPTION
       "Turn on / off the power delay function,
        0: disable,
        1: enable,
        default: disable. "
   ::= { gs2352pPoePowerDelayEntry 2 }
   
gs2352pPoePowerDelayTime OBJECT-TYPE
   SYNTAX      Integer32(0..300)
   MAX-ACCESS  read-write
   STATUS      current
   DESCRIPTION
       "set Delay Time,
        default: 0,
        range: 0-300 sec. "
   ::= { gs2352pPoePowerDelayEntry 3 }
   
gs2352pPoeAutoCheck                                                 OBJECT IDENTIFIER ::= { gs2352pPoe 3 }

gs2352pPoeAutoCheckPingCheck OBJECT-TYPE
   SYNTAX      INTEGER { disable(0), enable(1) }
   MAX-ACCESS  read-write
   STATUS      current
   DESCRIPTION
       "connection between PoE port and power device.
        0: disable,
        1: enable,
        default: disable. "
   ::= { gs2352pPoeAutoCheck 1 }

gs2352pPoeAutoCheckTable OBJECT-TYPE
   SYNTAX      SEQUENCE OF GS2352PPoeAutoCheckEntry
   MAX-ACCESS  not-accessible
   STATUS      current
   DESCRIPTION
       " Configure PoE Power Delay mode. "
   ::= { gs2352pPoeAutoCheck 2 }

gs2352pPoeAutoCheckEntry OBJECT-TYPE
   SYNTAX      GS2352PPoeAutoCheckEntry
   MAX-ACCESS  not-accessible
   STATUS      current
   DESCRIPTION
       ""
   INDEX    { gs2352pPoeAutoCheckPort  }
   ::= { gs2352pPoeAutoCheckTable 1 }

GS2352PPoeAutoCheckEntry ::= SEQUENCE {
   gs2352pPoeAutoCheckPort	   Integer32,
   gs2352pPoeAutoCheckPingIPAddress  DisplayString,
   gs2352pPoeAutoCheckIntervalTime   Integer32,
   gs2352pPoeAutoCheckRetryTime      Integer32,
   gs2352pPoeAutoCheckFailureLog     DisplayString,
   gs2352pPoeAutoCheckFailureAction  INTEGER,
   gs2352pPoeAutoCheckRebootTime     Integer32
}

gs2352pPoeAutoCheckPort OBJECT-TYPE
   SYNTAX      Integer32(1..4094)
   MAX-ACCESS  not-accessible
   STATUS      current
   DESCRIPTION
       " port, range : 1 - port number. "
   ::= { gs2352pPoeAutoCheckEntry 1 }

gs2352pPoeAutoCheckPingIPAddress OBJECT-TYPE
   SYNTAX      DisplayString
   MAX-ACCESS  read-write
   STATUS      current
   DESCRIPTION
       "IP Address the system should ping.
        default: 0.0.0.0 . "
   ::= { gs2352pPoeAutoCheckEntry 2 }

gs2352pPoeAutoCheckIntervalTime OBJECT-TYPE
   SYNTAX      Integer32(10..120)
   MAX-ACCESS  read-write
   STATUS      current
   DESCRIPTION
       "Device will send checking message to PD each interval time.
        default: 30,
        range: 10-120 sec.  "
   ::= { gs2352pPoeAutoCheckEntry 3 }

gs2352pPoeAutoCheckRetryTime OBJECT-TYPE
   SYNTAX      Integer32(1..5)
   MAX-ACCESS  read-write
   STATUS      current
   DESCRIPTION
       "It will retry to send detection again.
        default: 3,
        range: 1-5.  "
   ::= { gs2352pPoeAutoCheckEntry 4 }
   
gs2352pPoeAutoCheckFailureLog OBJECT-TYPE
   SYNTAX      DisplayString
   MAX-ACCESS  read-only
   STATUS      current
   DESCRIPTION
       "Failure loggings counter. "
   ::= { gs2352pPoeAutoCheckEntry 5 }
   
gs2352pPoeAutoCheckFailureAction OBJECT-TYPE
   SYNTAX      INTEGER { nothing(0), reboot(1) }
   MAX-ACCESS  read-write
   STATUS      current
   DESCRIPTION
       "It will retry to send detection again,
        0: Nothing,
        1: Reboot Remote PD,
        default: Nothing. "
   ::= { gs2352pPoeAutoCheckEntry 6 }
   
gs2352pPoeAutoCheckRebootTime OBJECT-TYPE
   SYNTAX      Integer32(3..120)
   MAX-ACCESS  read-write
   STATUS      current
   DESCRIPTION
       "When PD has been rebooted, the PoE port restored power after the specified time.
        default: 15,
        range: 3-120 sec. "
   ::= { gs2352pPoeAutoCheckEntry 7 }

gs2352pPoeScheduling                                                 OBJECT IDENTIFIER ::= { gs2352pPoe 4 }

gs2352pPoeSchedulingTable OBJECT-TYPE
   SYNTAX      SEQUENCE OF GS2352PPoeSchedulingEntry
   MAX-ACCESS  not-accessible
   STATUS      current
   DESCRIPTION
       " Configure PoE Scheduling Table. "
   ::= { gs2352pPoeScheduling 1 }

gs2352pPoeSchedulingEntry OBJECT-TYPE
   SYNTAX      GS2352PPoeSchedulingEntry
   MAX-ACCESS  not-accessible
   STATUS      current
   DESCRIPTION
       ""
   INDEX    { gs2352pPoeSchedulingPort }
   ::= { gs2352pPoeSchedulingTable 1 }

GS2352PPoeSchedulingEntry ::= SEQUENCE {
   gs2352pPoeSchedulingPort	        Integer32,
   gs2352pPoeSchedulingStatus	        INTEGER
}

gs2352pPoeSchedulingPort OBJECT-TYPE
   SYNTAX      Integer32(1..4094)
   MAX-ACCESS  not-accessible
   STATUS      current
   DESCRIPTION
       " port, range : 1 - port number. "
   ::= { gs2352pPoeSchedulingEntry 1 }

gs2352pPoeSchedulingStatus OBJECT-TYPE
   SYNTAX      INTEGER { disable(0), enable(1) }
   MAX-ACCESS  read-write
   STATUS      current
   DESCRIPTION
       "PoE Scheduling Status.
        0: Disable,
        1: Enable,
        default: Disable. "
   ::= { gs2352pPoeSchedulingEntry 2 }

gs2352pPoeSchedulingTimeTable OBJECT-TYPE
   SYNTAX      SEQUENCE OF GS2352PPoeSchedulingTimeEntry
   MAX-ACCESS  not-accessible
   STATUS      current
   DESCRIPTION
       " Show Poe Scheduling Time Config. "
   ::= { gs2352pPoeScheduling 2 }

gs2352pPoeSchedulingTimeEntry OBJECT-TYPE
   SYNTAX      GS2352PPoeSchedulingTimeEntry
   MAX-ACCESS  not-accessible
   STATUS      current
   DESCRIPTION
       ""
   INDEX    { gs2352pPoeSchedulingTimePort, gs2352pPoeSchedulingTimeWeek, gs2352pPoeSchedulingTimeHour  }
   ::= { gs2352pPoeSchedulingTimeTable 1 }

GS2352PPoeSchedulingTimeEntry ::= SEQUENCE {
   gs2352pPoeSchedulingTimePort		Integer32,
   gs2352pPoeSchedulingTimeWeek		INTEGER,
   gs2352pPoeSchedulingTimeHour		Integer32,
   gs2352pPoeSchedulingProvidePower	INTEGER
}

gs2352pPoeSchedulingTimePort OBJECT-TYPE
   SYNTAX      Integer32(1..4095)
   MAX-ACCESS  not-accessible
   STATUS      current
   DESCRIPTION
       " port, range : 1 - port number. "
   ::= { gs2352pPoeSchedulingTimeEntry 1 }

gs2352pPoeSchedulingTimeWeek OBJECT-TYPE
   SYNTAX      INTEGER {
                        monday(1),
                        tuseday(2),
                        wednesday(3),
                        thursday(4),
                        friday(5),
                        saturday(6),
                        sunday(7)
                        }
   MAX-ACCESS  not-accessible
   STATUS      current
   DESCRIPTION
       " range: 1-7, 
         Sunday:7, Monday:1, Tuseday:2, Wednesday:3, Thursday:4, Friday:5, Saturday:6.  "
   ::= { gs2352pPoeSchedulingTimeEntry 2 }

gs2352pPoeSchedulingTimeHour OBJECT-TYPE
   SYNTAX      Integer32(1..24)
   MAX-ACCESS  not-accessible
   STATUS      current
   DESCRIPTION
       " range: 1-24,
         24: hour 0, 1: hour 1, 2: hour2..."
   ::= { gs2352pPoeSchedulingTimeEntry 3 }

gs2352pPoeSchedulingProvidePower OBJECT-TYPE
   SYNTAX      INTEGER { disable(0), enable(1) }
   MAX-ACCESS  read-write
   STATUS      current
   DESCRIPTION
       " 0: disable,
         1: enable,
         default: disable.  "
   ::= { gs2352pPoeSchedulingTimeEntry 4 }

gs2352pPoeConfiguration                                                 OBJECT IDENTIFIER ::= { gs2352pPoe 5 }

gs2352pPoeConfigurationPrimaryPowerSupply  OBJECT-TYPE
   SYNTAX      Integer32(0..1000)
   MAX-ACCESS  read-only
   STATUS      current
   DESCRIPTION
       "It must be defined what amount of power the primary and backup power sources
        can deliver. "
   ::= { gs2352pPoeConfiguration 1 }

gs2352pPoeConfigurationRetryTime OBJECT-TYPE
   SYNTAX      Integer32(0|5|10|20|30|40|50|60)
   MAX-ACCESS  read-write
   STATUS      current
   DESCRIPTION
       "The period (in seconds) for trying to turn on an overloaded PoE port.
        0: disable,
        5 sec,10 sec,20 sec,30 sec,40 sec,50 sec,60 sec,
        default: 60 sec. "
   ::= { gs2352pPoeConfiguration 2 }

gs2352pPoeConfigurationTable OBJECT-TYPE
   SYNTAX      SEQUENCE OF GS2352PPoeConfigurationEntry
   MAX-ACCESS  not-accessible
   STATUS      current
   DESCRIPTION
       " Configure PoE Configuration mode. "
   ::= { gs2352pPoeConfiguration 3 }

gs2352pPoeConfigurationEntry OBJECT-TYPE
   SYNTAX      GS2352PPoeConfigurationEntry
   MAX-ACCESS  not-accessible
   STATUS      current
   DESCRIPTION
       ""
   INDEX    { gs2352pPoeConfigurationPort  }
   ::= { gs2352pPoeConfigurationTable 1 }

GS2352PPoeConfigurationEntry ::= SEQUENCE {
   gs2352pPoeConfigurationPort	       Integer32,
   gs2352pPoeConfigurationPoEMode       INTEGER,
   gs2352pPoeConfigurationPriority      INTEGER,
   gs2352pPoeConfigurationMaximumPower  DisplayString,
   gs2352pPoeConfigurationDetection     INTEGER,
   gs2352pPoeConfigurationReset         INTEGER
}

gs2352pPoeConfigurationPort OBJECT-TYPE
   SYNTAX      Integer32(1..4094)
   MAX-ACCESS  not-accessible
   STATUS      current
   DESCRIPTION
       " port, range : 1 - port number. "
   ::= { gs2352pPoeConfigurationEntry 1 }

gs2352pPoeConfigurationPoEMode OBJECT-TYPE
   SYNTAX      INTEGER { disable(0), enable(1) }
   MAX-ACCESS  read-write
   STATUS      current
   DESCRIPTION
       "The PoE Mode represents the PoE operating mode for the port.
        0: Disable,
        1: Enable,
        default: Enable. "
   ::= { gs2352pPoeConfigurationEntry 2 }

gs2352pPoeConfigurationPriority OBJECT-TYPE
   SYNTAX      INTEGER { low(0), high(1), critical(2) }
   MAX-ACCESS  read-write
   STATUS      current
   DESCRIPTION
       "The Priority represents the ports priority. There are three levels of power priority named Low, High and Critical.
        0: Low,
        1: High,
        2: Critical,
        default: Low.  "
   ::= { gs2352pPoeConfigurationEntry 3 }

gs2352pPoeConfigurationMaximumPower OBJECT-TYPE
   SYNTAX      DisplayString
   MAX-ACCESS  read-write
   STATUS      current
   DESCRIPTION
       "The Maximum Power value contains a numerical value that indicates the maximum
        power in watts that can be delivered to a remote device.
        default: 15.4[W],
        max: 30[W]. "
   ::= { gs2352pPoeConfigurationEntry 4 }

gs2352pPoeConfigurationDetection OBJECT-TYPE
   SYNTAX      INTEGER(0..5)
   MAX-ACCESS  read-write
   STATUS      current
   DESCRIPTION
       "Configure PoE port capacitor detection.
        0: No Detection(read only),
        1: legacy,
        2: 4-point,
        3: 4-point-legacy,
        4: 2-point,
        5: 2-point-legacy, 
        default: 4-point. "
   ::= { gs2352pPoeConfigurationEntry 5 }

gs2352pPoeConfigurationReset OBJECT-TYPE
   SYNTAX      INTEGER { disable(0), enable(1) }
   MAX-ACCESS  read-write
   STATUS      current
   DESCRIPTION
       "Reset the specific PoE port.
        0: Disable,
        1: Enable,
        default: Disable. "
   ::= { gs2352pPoeConfigurationEntry 6 }

gs2352pPoeConfigurationLegacyMode  OBJECT-TYPE
   SYNTAX      INTEGER { disable(0), enable(1) }
   MAX-ACCESS  read-write
   STATUS      current
   DESCRIPTION
       "Legacy Detection.
        0: Disable,
        1: Enable,
        default: Disable. "
   ::= { gs2352pPoeConfiguration 4 }


gs2352pQos                                                             OBJECT IDENTIFIER ::= { gs2352pConfiguration 14 }

gs2352pQosPortClassification                                           OBJECT IDENTIFIER ::= { gs2352pQos 1 }

gs2352pQosPortClassificationTable OBJECT-TYPE
   SYNTAX      SEQUENCE OF GS2352PQosPortClassificationEntry
   MAX-ACCESS  not-accessible
   STATUS      current
   DESCRIPTION
       " QoS Ingress Port Classification . "
   ::= { gs2352pQosPortClassification  1 }

gs2352pQosPortClassificationEntry OBJECT-TYPE
   SYNTAX      GS2352PQosPortClassificationEntry
   MAX-ACCESS  not-accessible
   STATUS      current
   DESCRIPTION
       ""
   INDEX    { gs2352pQosPortClassificationPort  }
   ::= { gs2352pQosPortClassificationTable 1 }

GS2352PQosPortClassificationEntry ::= SEQUENCE {
   gs2352pQosPortClassificationPort	    Integer32,
   gs2352pQosPortClassificationQoSclass       Integer32,
   gs2352pQosPortClassificationDPlevel	    Integer32,
   gs2352pQosPortClassificationPCP	    Integer32,
   gs2352pQosPortClassificationDEI	    INTEGER,
   gs2352pQosPortClassificationTagClass	    INTEGER,
   gs2352pQosPortClassificationDSCPBased      INTEGER
}

gs2352pQosPortClassificationPort OBJECT-TYPE
   SYNTAX      Integer32(1..4095)
   MAX-ACCESS  not-accessible
   STATUS      current
   DESCRIPTION
       " port, range : 1 - port number. "
   ::= { gs2352pQosPortClassificationEntry 1 }

gs2352pQosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2352pQosPortClassificationEntry 2 }

gs2352pQosPortClassificationDPlevel OBJECT-TYPE
   SYNTAX      Integer32(0..3)
   MAX-ACCESS  read-write
   STATUS      current
   DESCRIPTION
       " DP level for frames not classified in any other way.
         range: 0-3,
         default: 0. "
   ::= { gs2352pQosPortClassificationEntry 3 }

gs2352pQosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2352pQosPortClassificationEntry 4 }

gs2352pQosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2352pQosPortClassificationEntry 5 }

gs2352pQosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2352pQosPortClassificationEntry 6 }

gs2352pQosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2352pQosPortClassificationEntry 7 }

gs2352pQoSIngressPortTagClassificationTable OBJECT-TYPE
   SYNTAX      SEQUENCE OF GS2352PQoSIngressPortTagClassificationEntry
   MAX-ACCESS  not-accessible
   STATUS      current
   DESCRIPTION
       " Show QoS Ingress Port Tag Classification. "
   ::= { gs2352pQosPortClassification 2 }

gs2352pQoSIngressPortTagClassificationEntry OBJECT-TYPE
   SYNTAX      GS2352PQoSIngressPortTagClassificationEntry
   MAX-ACCESS  not-accessible
   STATUS      current
   DESCRIPTION
       ""
   INDEX    { gs2352pQoSIngressPortTagClassificationPort, gs2352pQoSIngressPortTagPCP, gs2352pQoSIngressPortTagDEI  }
   ::= { gs2352pQoSIngressPortTagClassificationTable 1 }

GS2352PQoSIngressPortTagClassificationEntry ::= SEQUENCE {
   gs2352pQoSIngressPortTagClassificationPort	 Integer32,
   gs2352pQoSIngressPortTagPCP			 INTEGER,
   gs2352pQoSIngressPortTagDEI			 INTEGER,
   gs2352pQoSIngressPortTagQosClass		 Integer32,
   gs2352pQoSIngressPortTagDPLevel                 Integer32
}

gs2352pQoSIngressPortTagClassificationPort OBJECT-TYPE
   SYNTAX      Integer32(1..4095)
   MAX-ACCESS  not-accessible
   STATUS      current
   DESCRIPTION
       " port, range : 1 - port number. "
   ::= { gs2352pQoSIngressPortTagClassificationEntry 1 }

gs2352pQoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8, 
         PCP0:1, PCP1:2...  "
   ::= { gs2352pQoSIngressPortTagClassificationEntry 2 }

gs2352pQoSIngressPortTagDEI OBJECT-TYPE
   SYNTAX      INTEGER { dei0(1), dei1(2) }
   MAX-ACCESS  not-accessible
   STATUS      current
   DESCRIPTION
       " range: 1-2,
         DEI0:1, DEI1:2. "
   ::= { gs2352pQoSIngressPortTagClassificationEntry 3 }

gs2352pQoSIngressPortTagQosClass OBJECT-TYPE
   SYNTAX      Integer32(0..7)
   MAX-ACCESS  read-write
   STATUS      current
   DESCRIPTION
       " range: 0-7.  "
   ::= { gs2352pQoSIngressPortTagClassificationEntry 4 }
   
gs2352pQoSIngressPortTagDPLevel OBJECT-TYPE
   SYNTAX      Integer32(0..3)
   MAX-ACCESS  read-write
   STATUS      current
   DESCRIPTION
       " range: 0-3.  "
   ::= { gs2352pQoSIngressPortTagClassificationEntry 5 }

gs2352pQosPortPolicingTable OBJECT-TYPE
   SYNTAX      SEQUENCE OF GS2352PQosPortPolicingEntry
   MAX-ACCESS  not-accessible
   STATUS      current
   DESCRIPTION
       "  configure the Policer settings for all switch ports. "
   ::= { gs2352pQos  2 }

gs2352pQosPortPolicingEntry OBJECT-TYPE
   SYNTAX      GS2352PQosPortPolicingEntry
   MAX-ACCESS  not-accessible
   STATUS      current
   DESCRIPTION
       ""
   INDEX    { gs2352pQosPortPolicingPort  }
   ::= { gs2352pQosPortPolicingTable 1 }

GS2352PQosPortPolicingEntry ::= SEQUENCE {
   gs2352pQosPortPolicingPort	        Integer32,
   gs2352pQosPortPolicingMode             INTEGER,
   gs2352pQosPortPolicingRate	        Integer32,
   gs2352pQosPortPolicingUnit	        INTEGER,
   gs2352pQosPortPolicingFlowControl	INTEGER
}

gs2352pQosPortPolicingPort OBJECT-TYPE
   SYNTAX      Integer32(1..4095)
   MAX-ACCESS  not-accessible
   STATUS      current
   DESCRIPTION
       " port, range : 1 - port number. "
   ::= { gs2352pQosPortPolicingEntry 1 }

gs2352pQosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2352pQosPortPolicingEntry 2 }

gs2352pQosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2352pQosPortPolicingEntry 3 }

gs2352pQosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2352pQosPortPolicingEntry 4 }

gs2352pQosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2352pQosPortPolicingEntry 5 }

gs2352pQosPortScheduler                                           OBJECT IDENTIFIER ::= { gs2352pQos 3 }

gs2352pQosPortSchedulerModeTable OBJECT-TYPE
   SYNTAX      SEQUENCE OF GS2352PQosPortSchedulerModeEntry
   MAX-ACCESS  not-accessible
   STATUS      current
   DESCRIPTION
       " configure the basic QoS Port Scheduler Mode settings for all switch ports. "
   ::= { gs2352pQosPortScheduler  1 }

gs2352pQosPortSchedulerModeEntry OBJECT-TYPE
   SYNTAX      GS2352PQosPortSchedulerModeEntry
   MAX-ACCESS  not-accessible
   STATUS      current
   DESCRIPTION
       ""
   INDEX    { gs2352pQosSchedulerModePort  }
   ::= { gs2352pQosPortSchedulerModeTable 1 }

GS2352PQosPortSchedulerModeEntry ::= SEQUENCE {
   gs2352pQosSchedulerModePort	                Integer32,
   gs2352pQosSchedulerMode                        INTEGER,
   gs2352pQosSchedulerShaper	                INTEGER,
   gs2352pQosSchedulerShaperRate                  Integer32
}

gs2352pQosSchedulerModePort OBJECT-TYPE
   SYNTAX      Integer32(1..4095)
   MAX-ACCESS  not-accessible
   STATUS      current
   DESCRIPTION
       " port, range : 1 - port number. "
   ::= { gs2352pQosPortSchedulerModeEntry 1 }

gs2352pQosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2352pQosPortSchedulerModeEntry 2 }

gs2352pQosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2352pQosPortSchedulerModeEntry 3 }

gs2352pQosSchedulerShaperRate OBJECT-TYPE
   SYNTAX      Integer32(100..1000000)
   MAX-ACCESS  read-write
   STATUS      current
   DESCRIPTION
       " Controls the rate for the port shaper.
         range: 100-1000000
         default: 500 kbps. "
   ::= { gs2352pQosPortSchedulerModeEntry 4 }

gs2352pQosPortSchedulerTable OBJECT-TYPE
   SYNTAX      SEQUENCE OF GS2352PQosPortSchedulerEntry
   MAX-ACCESS  not-accessible
   STATUS      current
   DESCRIPTION
       " Show Qos Port Scheduler. "
   ::= { gs2352pQosPortScheduler 2 }

gs2352pQosPortSchedulerEntry OBJECT-TYPE
   SYNTAX      GS2352PQosPortSchedulerEntry
   MAX-ACCESS  not-accessible
   STATUS      current
   DESCRIPTION
       ""
   INDEX    { gs2352pQosSchedulerPort, gs2352pQosSchedulerPortQueue}
   ::= { gs2352pQosPortSchedulerTable 1 }

GS2352PQosPortSchedulerEntry ::= SEQUENCE {
   gs2352pQosSchedulerPort				Integer32,
   gs2352pQosSchedulerPortQueue				INTEGER,
   gs2352pQosSchedulerPortQueueShaper			INTEGER,
   gs2352pQosSchedulerPortQueueShaperRate			Integer32,
   gs2352pQosSchedulerPortQueueShaperExcess		INTEGER,
   gs2352pQosSchedulerPortQueueSchedulerWeight	        Integer32,
   gs2352pQosSchedulerPortQueueSchedulerPercent	        DisplayString
}

gs2352pQosSchedulerPort OBJECT-TYPE
   SYNTAX      Integer32(1..4095)
   MAX-ACCESS  not-accessible
   STATUS      current
   DESCRIPTION
       " port, range : 1 - port number. "
   ::= { gs2352pQosPortSchedulerEntry 1 }

gs2352pQosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2352pQosPortSchedulerEntry 2 }
   
gs2352pQosSchedulerPortQueueShaper OBJECT-TYPE
   SYNTAX      INTEGER { disable(0), enable(1) }
   MAX-ACCESS  read-write
   STATUS      current
   DESCRIPTION
       " 0: disable  1:enable,
         default: 0.  "
   ::= { gs2352pQosPortSchedulerEntry 3 }
   
gs2352pQosSchedulerPortQueueShaperRate OBJECT-TYPE
   SYNTAX      Integer32(100..1000000)
   MAX-ACCESS  read-write
   STATUS      current
   DESCRIPTION
       " range: 100..1000000 kbps.  "
   ::= { gs2352pQosPortSchedulerEntry 4 }
   
gs2352pQosSchedulerPortQueueShaperExcess OBJECT-TYPE
   SYNTAX      INTEGER { disable(0), enable(1) }
   MAX-ACCESS  read-write
   STATUS      current
   DESCRIPTION
       " 0: disable  1:enable,
         default: 0.  "
   ::= { gs2352pQosPortSchedulerEntry 5 }
   
gs2352pQosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2352pQosPortSchedulerEntry 6 }
   
gs2352pQosSchedulerPortQueueSchedulerPercent OBJECT-TYPE
   SYNTAX      DisplayString
   MAX-ACCESS  read-only
   STATUS      current
   DESCRIPTION
       " Only use in Q0 - Q5. Q6 & Q7 show empty "
   ::= { gs2352pQosPortSchedulerEntry 7 }


gs2352pQosPortEgressTagRemarking                                           OBJECT IDENTIFIER ::= { gs2352pQos 4 }

gs2352pQosPortEgressTagRemarkingTable OBJECT-TYPE
   SYNTAX      SEQUENCE OF GS2352PQosPortEgressTagRemarkingEntry
   MAX-ACCESS  not-accessible
   STATUS      current
   DESCRIPTION
       " configure the basic QoS Port Egress Tag Remark Configuration settings for all switch ports. "
   ::= { gs2352pQosPortEgressTagRemarking  1 }

gs2352pQosPortEgressTagRemarkingEntry OBJECT-TYPE
   SYNTAX      GS2352PQosPortEgressTagRemarkingEntry
   MAX-ACCESS  not-accessible
   STATUS      current
   DESCRIPTION
       ""
   INDEX    { gs2352pQosEgressTagRemarkingPort  }
   ::= { gs2352pQosPortEgressTagRemarkingTable 1 }

GS2352PQosPortEgressTagRemarkingEntry ::= SEQUENCE {
   gs2352pQosEgressTagRemarkingPort	                Integer32,
   gs2352pQosEgressTagRemarkingMode	                INTEGER
}

gs2352pQosEgressTagRemarkingPort OBJECT-TYPE
   SYNTAX      Integer32(1..4095)
   MAX-ACCESS  not-accessible
   STATUS      current
   DESCRIPTION
       " port, range : 1 - port number. "
   ::= { gs2352pQosPortEgressTagRemarkingEntry 1 }

gs2352pQosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2352pQosPortEgressTagRemarkingEntry 2 }


gs2352pQosPortEgressTagRemarkingDefTable OBJECT-TYPE
   SYNTAX      SEQUENCE OF GS2352PQosPortEgressTagRemarkingDefEntry
   MAX-ACCESS  not-accessible
   STATUS      current
   DESCRIPTION
       " configure the basic QoS Port Egress Tag Remark Configuration settings for all switch ports. "
   ::= { gs2352pQosPortEgressTagRemarking  2 }

gs2352pQosPortEgressTagRemarkingDefEntry OBJECT-TYPE
   SYNTAX      GS2352PQosPortEgressTagRemarkingDefEntry
   MAX-ACCESS  not-accessible
   STATUS      current
   DESCRIPTION
       ""
   INDEX    { gs2352pQosEgressTagRemarkingDefPort  }
   ::= { gs2352pQosPortEgressTagRemarkingDefTable 1 }

GS2352PQosPortEgressTagRemarkingDefEntry ::= SEQUENCE {
   gs2352pQosEgressTagRemarkingDefPort	            Integer32,
   gs2352pQosEgressTagRemarkingDefPCP	            Integer32,
   gs2352pQosEgressTagRemarkingDefDEI	            INTEGER
}

gs2352pQosEgressTagRemarkingDefPort OBJECT-TYPE
   SYNTAX      Integer32(1..4095)
   MAX-ACCESS  not-accessible
   STATUS      current
   DESCRIPTION
       " port, range : 1 - port number. "
   ::= { gs2352pQosPortEgressTagRemarkingDefEntry 1 }

gs2352pQosEgressTagRemarkingDefPCP OBJECT-TYPE
   SYNTAX      Integer32(0..7)
   MAX-ACCESS  read-write
   STATUS      current
   DESCRIPTION
       " Controls the default PCP
       Range : 0-7"
   ::= { gs2352pQosPortEgressTagRemarkingDefEntry 2 }

gs2352pQosEgressTagRemarkingDefDEI OBJECT-TYPE
   SYNTAX      INTEGER { disable(0), enable(1) }
   MAX-ACCESS  read-write
   STATUS      current
   DESCRIPTION
       " controls the DEI
       Range 0-1"
   ::= { gs2352pQosPortEgressTagRemarkingDefEntry 3 }


gs2352pQosPortEgressTagRemarkingMapDPTable OBJECT-TYPE
   SYNTAX      SEQUENCE OF GS2352PQosPortEgressTagRemarkingMapDPEntry
   MAX-ACCESS  not-accessible
   STATUS      current
   DESCRIPTION
       " Show Qos Port Egress Tag Remarking Map DP. "
   ::= { gs2352pQosPortEgressTagRemarking 3 }

gs2352pQosPortEgressTagRemarkingMapDPEntry OBJECT-TYPE
   SYNTAX      GS2352PQosPortEgressTagRemarkingMapDPEntry
   MAX-ACCESS  not-accessible
   STATUS      current
   DESCRIPTION
       ""
   INDEX    { gs2352pQosPortEgressTagRemarkingDPPort, gs2352pQosPortEgressTagRemarkingClassifiedDPLevel}
   ::= { gs2352pQosPortEgressTagRemarkingMapDPTable 1 }

GS2352PQosPortEgressTagRemarkingMapDPEntry ::= SEQUENCE {
   gs2352pQosPortEgressTagRemarkingDPPort				Integer32,
   gs2352pQosPortEgressTagRemarkingClassifiedDPLevel		Integer32,
   gs2352pQosPortEgressTagRemarkingDPLevel			INTEGER
}

gs2352pQosPortEgressTagRemarkingDPPort OBJECT-TYPE
   SYNTAX      Integer32(1..4095)
   MAX-ACCESS  not-accessible
   STATUS      current
   DESCRIPTION
       " port, range : 1 - port number. "
   ::= { gs2352pQosPortEgressTagRemarkingMapDPEntry 1 }

gs2352pQosPortEgressTagRemarkingClassifiedDPLevel OBJECT-TYPE
   SYNTAX      Integer32(1..4)
   MAX-ACCESS  not-accessible
   STATUS      current
   DESCRIPTION
       " range: 1-4. "
   ::= { gs2352pQosPortEgressTagRemarkingMapDPEntry 2 }
   
gs2352pQosPortEgressTagRemarkingDPLevel OBJECT-TYPE
   SYNTAX      INTEGER { disable(0), enable(1) }
   MAX-ACCESS  read-write
   STATUS      current
   DESCRIPTION
       " range: 0-1.  "
   ::= { gs2352pQosPortEgressTagRemarkingMapDPEntry 3 }

gs2352pQosPortEgressTagRemarkingMapTable OBJECT-TYPE
   SYNTAX      SEQUENCE OF GS2352PQosPortEgressTagRemarkingMapEntry
   MAX-ACCESS  not-accessible
   STATUS      current
   DESCRIPTION
       " Show Qos Port Egress Tag Remarking Map. "
   ::= { gs2352pQosPortEgressTagRemarking 4 }

gs2352pQosPortEgressTagRemarkingMapEntry OBJECT-TYPE
   SYNTAX      GS2352PQosPortEgressTagRemarkingMapEntry
   MAX-ACCESS  not-accessible
   STATUS      current
   DESCRIPTION
       ""
   INDEX    { gs2352pQosPortEgressTagRemarkingMapPort, gs2352pQosTagRemarkingQoSClass, gs2352pQosTagRemarkingDPLevel  }
   ::= { gs2352pQosPortEgressTagRemarkingMapTable 1 }

GS2352PQosPortEgressTagRemarkingMapEntry ::= SEQUENCE {
   gs2352pQosPortEgressTagRemarkingMapPort	Integer32,
   gs2352pQosTagRemarkingQoSClass			INTEGER,
   gs2352pQosTagRemarkingDPLevel			INTEGER,
   gs2352pQosTagRemarkingPCP			Integer32,
   gs2352pQosTagRemarkingDEI			INTEGER
}

gs2352pQosPortEgressTagRemarkingMapPort OBJECT-TYPE
   SYNTAX      Integer32(1..4095)
   MAX-ACCESS  not-accessible
   STATUS      current
   DESCRIPTION
       " port, range : 1 - port number. "
   ::= { gs2352pQosPortEgressTagRemarkingMapEntry 1 }

gs2352pQosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8, 
         QoS Class0: 1, QoS Class1: 2...  "
   ::= { gs2352pQosPortEgressTagRemarkingMapEntry 2 }

gs2352pQosTagRemarkingDPLevel OBJECT-TYPE
   SYNTAX      INTEGER { level0(1), level1(2) }
   MAX-ACCESS  not-accessible
   STATUS      current
   DESCRIPTION
       " range: 1-2,
         DP Level0: 1, DP Level1: 2. "
   ::= { gs2352pQosPortEgressTagRemarkingMapEntry 3 }

gs2352pQosTagRemarkingPCP OBJECT-TYPE
   SYNTAX      Integer32(0..7)
   MAX-ACCESS  read-write
   STATUS      current
   DESCRIPTION
       " range: 0-7.  "
   ::= { gs2352pQosPortEgressTagRemarkingMapEntry 4 }
   
gs2352pQosTagRemarkingDEI OBJECT-TYPE
   SYNTAX      INTEGER (0|1)
   MAX-ACCESS  read-write
   STATUS      current
   DESCRIPTION
       " range: 0-1.  "
   ::= { gs2352pQosPortEgressTagRemarkingMapEntry 5 }


gs2352pQosPortDSCPTable OBJECT-TYPE
   SYNTAX      SEQUENCE OF GS2352PQosPortDSCPEntry
   MAX-ACCESS  not-accessible
   STATUS      current
   DESCRIPTION
       " configure the basic QoS Port DSCP Configuration settings for all switch ports. "
   ::= { gs2352pQos  5 }

gs2352pQosPortDSCPEntry OBJECT-TYPE
   SYNTAX      GS2352PQosPortDSCPEntry
   MAX-ACCESS  not-accessible
   STATUS      current
   DESCRIPTION
       ""
   INDEX    { gs2352pQosPortDSCPPort  }
   ::= { gs2352pQosPortDSCPTable 1 }

GS2352PQosPortDSCPEntry ::= SEQUENCE {
   gs2352pQosPortDSCPPort	                Integer32,
   gs2352pQosPortDSCPIngressTranslate     INTEGER,
   gs2352pQosPortDSCPIngressClassify	INTEGER,
   gs2352pQosPortDSCPEgressRewrite        INTEGER
}

gs2352pQosPortDSCPPort OBJECT-TYPE
   SYNTAX      Integer32(1..4095)
   MAX-ACCESS  not-accessible
   STATUS      current
   DESCRIPTION
       " port, range : 1 - port number. "
   ::= { gs2352pQosPortDSCPEntry 1 }

gs2352pQosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2352pQosPortDSCPEntry 2 }

gs2352pQosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2352pQosPortDSCPEntry 3 }

gs2352pQosPortDSCPEgressRewrite OBJECT-TYPE
   SYNTAX      INTEGER { disable(0), enable(1), remap(2) }
   MAX-ACCESS  read-write
   STATUS      current
   DESCRIPTION
       " Configure the port egress rewriting mode.
         range: 0-2
         0: Disable,No Egress rewrite.
         1: Enable, Rewrite enabled without remapping.
         2: Remap , DSCP from analyzer is remapped and frame is remarked with
            remapped DSCP value.
         default: disable. "
   ::= { gs2352pQosPortDSCPEntry 4 }

gs2352pQosDSCPTable OBJECT-TYPE
   SYNTAX      SEQUENCE OF GS2352PQosDSCPEntry
   MAX-ACCESS  not-accessible
   STATUS      current
   DESCRIPTION
       " configure the basic QoS DSCP based QoS Ingress Classification settings for all switches. "
   ::= { gs2352pQos  6 }

gs2352pQosDSCPEntry OBJECT-TYPE
   SYNTAX      GS2352PQosDSCPEntry
   MAX-ACCESS  not-accessible
   STATUS      current
   DESCRIPTION
       ""
   INDEX    { gs2352pQosDSCPList  }
   ::= { gs2352pQosDSCPTable 1 }

GS2352PQosDSCPEntry ::= SEQUENCE {
   gs2352pQosDSCPList       Integer32,
   gs2352pQosDSCP           DisplayString,
   gs2352pQosDSCPTrust      INTEGER,
   gs2352pQosDSCPQosClass	  Integer32,
   gs2352pQosDSCPDPL	  INTEGER
}

gs2352pQosDSCPList OBJECT-TYPE
   SYNTAX      Integer32(1..64)
   MAX-ACCESS  not-accessible
   STATUS      current
   DESCRIPTION
      " DSCP mapping table index(1-64). "
   ::= { gs2352pQosDSCPEntry 1 }

gs2352pQosDSCP OBJECT-TYPE
   SYNTAX      DisplayString
   MAX-ACCESS  read-only
   STATUS      current
   DESCRIPTION
      "Maximum number of supported DSCP values are 64."
   ::= { gs2352pQosDSCPEntry 2 }

gs2352pQosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2352pQosDSCPEntry 3 }

gs2352pQosDSCPQosClass OBJECT-TYPE
   SYNTAX      Integer32(0..7)
   MAX-ACCESS  read-write
   STATUS      current
   DESCRIPTION
      " QoS class.
        range: 0-7,
        default: 0. "
   ::= { gs2352pQosDSCPEntry 4 }

gs2352pQosDSCPDPL OBJECT-TYPE
   SYNTAX      INTEGER(0..3)
   MAX-ACCESS  read-write
   STATUS      current
   DESCRIPTION
      " Drop Precedence Level.
        range: 0-3,
        default: disable. "
   ::= { gs2352pQosDSCPEntry 5 }


gs2352pQosDSCPTranslationTable OBJECT-TYPE
   SYNTAX      SEQUENCE OF GS2352PQosDSCPTranslationEntry
   MAX-ACCESS  not-accessible
   STATUS      current
   DESCRIPTION
       "  configure the basic QoS DSCP Translation settings for all switches. "
   ::= { gs2352pQos  7 }

gs2352pQosDSCPTranslationEntry OBJECT-TYPE
   SYNTAX      GS2352PQosDSCPTranslationEntry
   MAX-ACCESS  not-accessible
   STATUS      current
   DESCRIPTION
       ""
   INDEX    { gs2352pQosDSCPTranslationList  }
   ::= { gs2352pQosDSCPTranslationTable 1 }

GS2352PQosDSCPTranslationEntry ::= SEQUENCE {
   gs2352pQosDSCPTranslationList                 Integer32,
   gs2352pQosDSCPTranslationDSCPBasedId          DisplayString,
   gs2352pQosDSCPTranslationIngressTranslate     Integer32,
   gs2352pQosDSCPTranslationIngressClassify      INTEGER,
   gs2352pQosDSCPTranslationEgressRemap          Integer32
}

gs2352pQosDSCPTranslationList OBJECT-TYPE
   SYNTAX      Integer32(1..64)
   MAX-ACCESS  not-accessible
   STATUS      current
   DESCRIPTION
      " DSCP translation table index(1-64). "
   ::= { gs2352pQosDSCPTranslationEntry 1 }

gs2352pQosDSCPTranslationDSCPBasedId OBJECT-TYPE
   SYNTAX      DisplayString
   MAX-ACCESS  read-write
   STATUS      current
   DESCRIPTION
      " Configure global ingress DSCP translation table. "
   ::= { gs2352pQosDSCPTranslationEntry 2 }

gs2352pQosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2352pQosDSCPTranslationEntry 3 }

gs2352pQosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2352pQosDSCPTranslationEntry 4 }

gs2352pQosDSCPTranslationEgressRemap OBJECT-TYPE
   SYNTAX      Integer32(0..63)
   MAX-ACCESS  read-write
   STATUS      current
   DESCRIPTION
      " Select the DSCP value from select menu to which you want to remap.
        range: 0-63,
        default: 0. "
   ::= { gs2352pQosDSCPTranslationEntry 5 }


gs2352pQosDSCPClassificationTable OBJECT-TYPE
   SYNTAX      SEQUENCE OF GS2352PQosDSCPClassificationEntry
   MAX-ACCESS  not-accessible
   STATUS      current
   DESCRIPTION
       "   configure the mapping of QoS class  to DSCP value. "
   ::= { gs2352pQos  8 }

gs2352pQosDSCPClassificationEntry OBJECT-TYPE
   SYNTAX      GS2352PQosDSCPClassificationEntry
   MAX-ACCESS  not-accessible
   STATUS      current
   DESCRIPTION
       ""
   INDEX    { gs2352pQosDSCPClassificationQoSClass  }
   ::= { gs2352pQosDSCPClassificationTable 1 }

GS2352PQosDSCPClassificationEntry ::= SEQUENCE {
   gs2352pQosDSCPClassificationQoSClass   INTEGER,
   gs2352pQosDSCPClassificationDSCP       Integer32
}

gs2352pQosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2352pQosDSCPClassificationEntry 1 }

gs2352pQosDSCPClassificationDSCP OBJECT-TYPE
   SYNTAX      Integer32(0..63)
   MAX-ACCESS  read-write
   STATUS      current
   DESCRIPTION
      " Select the classified DSCP value.
        range: 0-63,
        default: 0. "
   ::= { gs2352pQosDSCPClassificationEntry 3 }

gs2352pQosControlList                                         OBJECT IDENTIFIER ::= { gs2352pQos 9 }

gs2352pQosQceCreate OBJECT-TYPE
   SYNTAX       INTEGER { none(0), create(1) }
   MAX-ACCESS   read-write
   STATUS       current
   DESCRIPTION
       "default: 0
        0 : None  (read only)
        1 : Create an Qos entry"
   ::= { gs2352pQosControlList 1 }

gs2352pQosQceTable OBJECT-TYPE
   SYNTAX      SEQUENCE OF GS2352PQosQceEntry
   MAX-ACCESS  not-accessible
   STATUS      current
   DESCRIPTION
       " Create Qos QCE entry. "
   ::= { gs2352pQosControlList 2 }

gs2352pQosQceEntry OBJECT-TYPE
   SYNTAX      GS2352PQosQceEntry
   MAX-ACCESS  not-accessible
   STATUS      current
   DESCRIPTION
       ""
   INDEX    { gs2352pQosQceIndex  }
   ::= { gs2352pQosQceTable 1 }

GS2352PQosQceEntry ::= SEQUENCE {
   gs2352pQosQceIndex                Integer32,
   gs2352pQosQceID                   Integer32,
   gs2352pQosQceNextID               Integer32,
   gs2352pQosQcePortMembers          DisplayString,
   
   gs2352pQosQceTag                  DisplayString,
   gs2352pQosQceVID                  DisplayString,
   gs2352pQosPCP                     DisplayString,
   gs2352pQosDEI                     DisplayString,
   gs2352pQosSMAC                    DisplayString,
   gs2352pQosDMACType                DisplayString,
   gs2352pQosFrameType               INTEGER,
   
   gs2352pQosMacEtherType            DisplayString,
   
   gs2352pQosLLCSSAPAddr             DisplayString,
   gs2352pQosLLCDSAPAddr             DisplayString,
   gs2352pQosLLCControl              DisplayString,
   
   gs2352pQosSNAPPID                 DisplayString,
   
   gs2352pQosIpv4Protocol            DisplayString,
   gs2352pQosIpv4ProtocolValue       Integer32,
   gs2352pQosIpv4ProtocolUDPSport    DisplayString,
   gs2352pQosIpv4ProtocolUDPDport    DisplayString,
   gs2352pQosIpv4ProtocolTCPSport    DisplayString,
   gs2352pQosIpv4ProtocolTCPDport    DisplayString,
   gs2352pQosIpv4SourceIp            DisplayString,
   gs2352pQosIpv4SourceMask          DisplayString,
   gs2352pQosIpv4IPFragment          INTEGER,
   gs2352pQosIpv4DSCP                DisplayString,


   gs2352pQosIpv6Protocol            DisplayString,
   gs2352pQosIpv6ProtocolValue       Integer32,
   gs2352pQosIpv6ProtocolUDPSport    DisplayString,
   gs2352pQosIpv6ProtocolUDPDport    DisplayString,
   gs2352pQosIpv6ProtocolTCPSport    DisplayString,
   gs2352pQosIpv6ProtocolTCPDport    DisplayString,
   gs2352pQosIpv6SourceIp            DisplayString,
   gs2352pQosIpv6SourceMask          DisplayString,
   gs2352pQosIpv6DSCP                DisplayString,
   
   gs2352pQosActionClass             Integer32,
   gs2352pQosActionDPL               INTEGER,
   gs2352pQosActionDSCP              Integer32,
   gs2352pQosQceRowStatus            INTEGER
}

gs2352pQosQceIndex OBJECT-TYPE
   SYNTAX      Integer32(1..256)
   MAX-ACCESS  not-accessible
   STATUS      current
   DESCRIPTION
       " "
   ::= { gs2352pQosQceEntry 1 }

gs2352pQosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2352pQosQceEntry 2 }

gs2352pQosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2352pQosQceEntry 3 }

gs2352pQosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2352pQosQceEntry 4 }

gs2352pQosQceTag OBJECT-TYPE
   SYNTAX      DisplayString
   MAX-ACCESS  read-write
   STATUS      current
   DESCRIPTION
       " Value of Tag field can be 'Any', 'Untag' or 'Tag'. "
   ::= { gs2352pQosQceEntry 5 }

gs2352pQosQceVID OBJECT-TYPE
   SYNTAX      DisplayString
   MAX-ACCESS  read-write
   STATUS      current
   DESCRIPTION
       " Valid value of VLAN ID can be any value in 'Specific 1~4094' or 'range 1-4094' or 'Any'. "
   ::= { gs2352pQosQceEntry 6 }

gs2352pQosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2352pQosQceEntry 7 }

gs2352pQosDEI OBJECT-TYPE
   SYNTAX      DisplayString
   MAX-ACCESS  read-write
   STATUS      current
   DESCRIPTION
       " Drop Eligible Indicator: Valid value of DEI can be any of values between 0, 1 or 'Any'. "
   ::= { gs2352pQosQceEntry 8 }

gs2352pQosSMAC  OBJECT-TYPE
   SYNTAX      DisplayString
   MAX-ACCESS  read-write
   STATUS      current
   DESCRIPTION
       "  Source MAC address: 24 MS bits OUI(00-00-00 ~ FF-FF-FF) or 'Any'. "
   ::= { gs2352pQosQceEntry 9 }

gs2352pQosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2352pQosQceEntry 10 }

gs2352pQosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2352pQosQceEntry 11 }

gs2352pQosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2352pQosQceEntry 12 }

gs2352pQosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2352pQosQceEntry 13 }

gs2352pQosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2352pQosQceEntry 14 }

gs2352pQosLLCControl OBJECT-TYPE
   SYNTAX      DisplayString
   MAX-ACCESS  read-write
   STATUS      current
   DESCRIPTION
       " Valid Control field can vary from 0x00 to 0xFF or 'Any',
         range: 00-FF,
         default: Any. "
   ::= { gs2352pQosQceEntry 15 }

gs2352pQosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2352pQosQceEntry 16 }

gs2352pQosIpv4Protocol OBJECT-TYPE
   SYNTAX      DisplayString
   MAX-ACCESS  read-write
   STATUS      current
   DESCRIPTION
       " IP protocol number: (Other, TCP or UDP) or 'Any'. "
   ::= { gs2352pQosQceEntry 17 }

gs2352pQosIpv4ProtocolValue  OBJECT-TYPE
   SYNTAX      Integer32(0..255)
   MAX-ACCESS  read-write
   STATUS      current
   DESCRIPTION
       " Ipv4 Protocol is Other.
         range: 0-255
         default: 0. "
   ::= { gs2352pQosQceEntry 18 }

gs2352pQosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2352pQosQceEntry 19 }

gs2352pQosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2352pQosQceEntry 20 }

gs2352pQosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2352pQosQceEntry 21 }

gs2352pQosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2352pQosQceEntry 22 }

gs2352pQosIpv4SourceIp OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223."
   ::= { gs2352pQosQceEntry 23 }

gs2352pQosIpv4SourceMask OBJECT-TYPE
   SYNTAX      DisplayString
   MAX-ACCESS  read-write
   STATUS      current
   DESCRIPTION
       " Specific Source IP address in mask format or value 0.0.0.0 is 'Any'. "
   ::= { gs2352pQosQceEntry 24 }

gs2352pQosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2352pQosQceEntry 25 }

gs2352pQosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2352pQosQceEntry 26 }

gs2352pQosIpv6Protocol OBJECT-TYPE
   SYNTAX      DisplayString
   MAX-ACCESS  read-write
   STATUS      current
   DESCRIPTION
       " IP protocol number: (Other, TCP or UDP) or 'Any'. "
   ::= { gs2352pQosQceEntry 27 }

gs2352pQosIpv6ProtocolValue OBJECT-TYPE
   SYNTAX      Integer32(0..255)
   MAX-ACCESS  read-write
   STATUS      current
   DESCRIPTION
       " when IPv6 protocol is Other ,
         range: 0-255. "
   ::= { gs2352pQosQceEntry 28 }

gs2352pQosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2352pQosQceEntry 29 }

gs2352pQosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2352pQosQceEntry 30 }

gs2352pQosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2352pQosQceEntry 31 }


gs2352pQosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2352pQosQceEntry 32 }

gs2352pQosIpv6SourceIp OBJECT-TYPE
   SYNTAX      DisplayString
   MAX-ACCESS  read-write
   STATUS      current
   DESCRIPTION
       " IPv6 source address: (a.b.c.d) or value 0.0.0.0 is 'Any', 32 LS bits. "
   ::= { gs2352pQosQceEntry 33 }

gs2352pQosIpv6SourceMask OBJECT-TYPE
   SYNTAX      DisplayString
   MAX-ACCESS  read-write
   STATUS      current
   DESCRIPTION
       " IPv6 mask address: (a.b.c.d) or value 0.0.0.0 is 'Any', 32 LS bits. "
   ::= { gs2352pQosQceEntry 34 }

gs2352pQosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2352pQosQceEntry 35 }

gs2352pQosActionClass  OBJECT-TYPE
   SYNTAX      Integer32(0..8)
   MAX-ACCESS  read-write
   STATUS      current
   DESCRIPTION
       " QoS class: (0-7) or 8: Default."
   ::= { gs2352pQosQceEntry 36 }

gs2352pQosActionDPL OBJECT-TYPE
   SYNTAX      INTEGER (0..4)
   MAX-ACCESS  read-write
   STATUS      current
   DESCRIPTION
       " DP Valid Drop Precedence Level can be (0-3) or 4: Default. "
   ::= { gs2352pQosQceEntry 37 }

gs2352pQosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2352pQosQceEntry 38 }

gs2352pQosQceRowStatus OBJECT-TYPE
   SYNTAX      INTEGER { active(1), notInservice(2), destroy(4) }
   MAX-ACCESS  read-write
   STATUS      current
   DESCRIPTION
       "  1: active 2: notInservice 4: destroy"
   ::= { gs2352pQosQceEntry 39 }

gs2352pQosQceMoveID OBJECT-TYPE
   SYNTAX       Integer32(0..256)
   MAX-ACCESS   read-write
   STATUS       current
   DESCRIPTION
       " Move Qos,
         default: 0
         Qos ID must be exist.
         range : 0 - 256."
   ::= { gs2352pQosControlList 3 }

gs2352pQosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2352pQosControlList 4 }


gs2352pQosQCLStatusTable OBJECT-TYPE
   SYNTAX      SEQUENCE OF GS2352PQosQCLStatusEntry
   MAX-ACCESS  not-accessible
   STATUS      current
   DESCRIPTION
       "  configure the basic QoS DSCP Translation settings for all switches. "
   ::= { gs2352pQos  10 }

gs2352pQosQCLStatusEntry OBJECT-TYPE
   SYNTAX      GS2352PQosQCLStatusEntry
   MAX-ACCESS  not-accessible
   STATUS      current
   DESCRIPTION
       ""
   INDEX    { gs2352pQosQCLStatusList  }
   ::= { gs2352pQosQCLStatusTable 1 }

GS2352PQosQCLStatusEntry ::= SEQUENCE {
   gs2352pQosQCLStatusList               Integer32,
   gs2352pQosQCLStatusUser               DisplayString,
   gs2352pQosQCLStatusQCEId              DisplayString,
   gs2352pQosQCLStatusFrameType          DisplayString,
   gs2352pQosQCLStatusPortlist           DisplayString,
   gs2352pQosQCLStatusActionClass	       DisplayString,
   gs2352pQosQCLStatusActionDPL	       DisplayString,
   gs2352pQosQCLStatusActionDSCP	       DisplayString,
   gs2352pQosQCLStatusActionConflict     DisplayString
}

gs2352pQosQCLStatusList OBJECT-TYPE
   SYNTAX      Integer32(1..4095)
   MAX-ACCESS  not-accessible
   STATUS      current
   DESCRIPTION
       " QCL table index. "
   ::= { gs2352pQosQCLStatusEntry 1}
   
gs2352pQosQCLStatusUser OBJECT-TYPE
   SYNTAX      DisplayString
   MAX-ACCESS  read-only
   STATUS      current
   DESCRIPTION
       " Indicates the QCL user. "
   ::= { gs2352pQosQCLStatusEntry 2 }

gs2352pQosQCLStatusQCEId OBJECT-TYPE
   SYNTAX      DisplayString
   MAX-ACCESS  read-only
   STATUS      current
   DESCRIPTION
      " Indicates the index of QCE. "
   ::= { gs2352pQosQCLStatusEntry 3}

gs2352pQosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2352pQosQCLStatusEntry 4}

gs2352pQosQCLStatusPortlist OBJECT-TYPE
   SYNTAX      DisplayString
   MAX-ACCESS  read-only
   STATUS      current
   DESCRIPTION
       " Indicates the list of ports configured with the QCE. "
   ::= { gs2352pQosQCLStatusEntry 5}

gs2352pQosQCLStatusActionClass OBJECT-TYPE
   SYNTAX      DisplayString
   MAX-ACCESS  read-only
   STATUS      current
   DESCRIPTION
       " Classified QoS class; if a frame matches the QCE it will be put in the
       queue. "
   ::= { gs2352pQosQCLStatusEntry 6}

gs2352pQosQCLStatusActionDPL OBJECT-TYPE
   SYNTAX      DisplayString
   MAX-ACCESS  read-only
   STATUS      current
   DESCRIPTION
       " Drop Precedence Level; if a frame matches the QCE then DP level will
       set to value displayed under DPL column."
   ::= { gs2352pQosQCLStatusEntry 7}

gs2352pQosQCLStatusActionDSCP OBJECT-TYPE
   SYNTAX      DisplayString
   MAX-ACCESS  read-only
   STATUS      current
   DESCRIPTION
       " If a frame matches the QCE then DSCP will be classified with the value
       displayed under DSCP column."
   ::= { gs2352pQosQCLStatusEntry 8}

gs2352pQosQCLStatusActionConflict OBJECT-TYPE
   SYNTAX      DisplayString
   MAX-ACCESS  read-only
   STATUS      current
   DESCRIPTION
       " If a frame matches the QCE then DSCP will be classified with the value
        displayed under DSCP column. "
   ::= { gs2352pQosQCLStatusEntry 9}


gs2352pQosStormControl                                           OBJECT IDENTIFIER ::= { gs2352pQos 11 }

gs2352pQosStormControlTable OBJECT-TYPE
   SYNTAX      SEQUENCE OF GS2352PQosStormControlEntry
   MAX-ACCESS  not-accessible
   STATUS      current
   DESCRIPTION
       "  configure the basic QoS DSCP Translation settings for all switches. "
   ::= { gs2352pQosStormControl  1 }

gs2352pQosStormControlEntry OBJECT-TYPE
   SYNTAX      GS2352PQosStormControlEntry
   MAX-ACCESS  not-accessible
   STATUS      current
   DESCRIPTION
       ""
   INDEX    { gs2352pQosStormControlPort  }
   ::= { gs2352pQosStormControlTable 1 }

GS2352PQosStormControlEntry ::= SEQUENCE {
   gs2352pQosStormControlPort                    Integer32,
   gs2352pQosStormControlUnicastEnabled          INTEGER,
   gs2352pQosStormControlUnicastRate             Integer32,
   gs2352pQosStormControlUnicastUnit             INTEGER,
   gs2352pQosStormControlBroadcastEnabled        INTEGER,
   gs2352pQosStormControlBroadcastRate           Integer32,
   gs2352pQosStormControlBroadcastUnit           INTEGER,
   gs2352pQosStormControlUnknownEnabled          INTEGER,
   gs2352pQosStormControlUnknownRate             Integer32,
   gs2352pQosStormControlUnknownUnit             INTEGER
}

gs2352pQosStormControlPort OBJECT-TYPE
   SYNTAX      Integer32(1..4095)
   MAX-ACCESS  not-accessible
   STATUS      current
   DESCRIPTION
       " port, range : 1 - port number. "
   ::= { gs2352pQosStormControlEntry 1 }

gs2352pQosStormControlUnicastEnabled OBJECT-TYPE
   SYNTAX      INTEGER { disable(0), enable(1) }
   MAX-ACCESS  read-write
   STATUS      current
   DESCRIPTION
      " Controls whether the storm control is enabled on this switch port.
        0: disable,
        1: enable,
        default: disable. "
   ::= { gs2352pQosStormControlEntry 2 }

gs2352pQosStormControlUnicastRate OBJECT-TYPE
   SYNTAX      Integer32(100..10000000)
   MAX-ACCESS  read-write
   STATUS      current
   DESCRIPTION
       " Controls the rate for the unicast storm control.
         range: 100-10000000(kbps/fps),
         default: 500(kbps).  "
   ::= { gs2352pQosStormControlEntry 3 }

gs2352pQosStormControlUnicastUnit OBJECT-TYPE
   SYNTAX      INTEGER { kbps(0), fps(1) }
   MAX-ACCESS  read-write
   STATUS      current
   DESCRIPTION
       " Controls the unit of measure for the unicast storm control rate.
         0: kbps,
         1: fps,
         default: kbps. "
   ::= { gs2352pQosStormControlEntry 4 }

gs2352pQosStormControlBroadcastEnabled OBJECT-TYPE
   SYNTAX      INTEGER { disable(0), enable(1) }
   MAX-ACCESS  read-write
   STATUS      current
   DESCRIPTION
      " Controls whether the storm control is enabled on this switch port.
        0: disable,
        1: enable,
        default: disable. "
   ::= { gs2352pQosStormControlEntry 5 }

gs2352pQosStormControlBroadcastRate OBJECT-TYPE
   SYNTAX      Integer32(100..10000000)
   MAX-ACCESS  read-write
   STATUS      current
   DESCRIPTION
       " Controls the rate for the broadcast storm control.
         range: 100-10000000(kbps/fps),
         default: 500(kbps).  "
   ::= { gs2352pQosStormControlEntry 6 }

gs2352pQosStormControlBroadcastUnit OBJECT-TYPE
   SYNTAX      INTEGER { kbps(0), fps(1) }
   MAX-ACCESS  read-write
   STATUS      current
   DESCRIPTION
       " Controls the unit of measure for the broadcast storm control rate.
         0: kbps,
         1: fps,
         default: kbps. "
   ::= { gs2352pQosStormControlEntry 7 }

gs2352pQosStormControlUnknownEnabled OBJECT-TYPE
   SYNTAX      INTEGER { disable(0), enable(1) }
   MAX-ACCESS  read-write
   STATUS      current
   DESCRIPTION
      " Controls whether the storm control is enabled on this switch port.
        0: disable,
        1: enable,
        default: disable. "
   ::= { gs2352pQosStormControlEntry 8 }

gs2352pQosStormControlUnknownRate OBJECT-TYPE
   SYNTAX      Integer32(100..10000000)
   MAX-ACCESS  read-write
   STATUS      current
   DESCRIPTION
       " Controls the rate for the multicast storm control.
         range: 100-10000000(kbps/fps),
         default: 500(kbps).  "
   ::= { gs2352pQosStormControlEntry 9 }

gs2352pQosStormControlUnknownUnit OBJECT-TYPE
   SYNTAX      INTEGER { kbps(0), fps(1) }
   MAX-ACCESS  read-write
   STATUS      current
   DESCRIPTION
       " Controls the unit of measure for the multicast storm control rate.
         0: kbps,
         1: fps,
         default: kbps. "
   ::= { gs2352pQosStormControlEntry 10 }


gs2352pQosWREDTable OBJECT-TYPE
   SYNTAX      SEQUENCE OF GS2352PQosWREDEntry
   MAX-ACCESS  not-accessible
   STATUS      current
   DESCRIPTION
       " configure the Random Early Detection (RED) settings for queue. "
   ::= { gs2352pQos  12 }

gs2352pQosWREDEntry OBJECT-TYPE
   SYNTAX      GS2352PQosWREDEntry
   MAX-ACCESS  not-accessible
   STATUS      current
   DESCRIPTION
       ""
   INDEX    { gs2352pQosWREDQueueList  }
   ::= { gs2352pQosWREDTable 1 }

GS2352PQosWREDEntry ::= SEQUENCE {
   gs2352pQosWREDQueueList       Integer32,
   gs2352pQosWREDQueue           INTEGER,
   gs2352pQosWREDMinThreshold    Integer32,
   gs2352pQosWREDMaxDP1          Integer32,
   gs2352pQosWREDMaxDP2          Integer32,
   gs2352pQosWREDMaxDP3          Integer32
}

gs2352pQosWREDQueueList OBJECT-TYPE
   SYNTAX      Integer32(1..6)
   MAX-ACCESS   not-accessible
   STATUS      current
   DESCRIPTION
       " The queue number (QoS class) for which the configuration below applies.
       Index 1~6 mean Queue 0~5."
   ::= { gs2352pQosWREDEntry 1 }

gs2352pQosWREDQueue OBJECT-TYPE
   SYNTAX      INTEGER { disable(0), enable(1) }
   MAX-ACCESS  read-write
   STATUS      current
   DESCRIPTION
       " Controls whether RED(Random Early Detection) for this queue.
         0: Disable,
         1: Enable,
         default: Disable. "
   ::= { gs2352pQosWREDEntry 2 }

gs2352pQosWREDMinThreshold OBJECT-TYPE
   SYNTAX      Integer32(0..100)
   MAX-ACCESS  read-write
   STATUS      current
   DESCRIPTION
       " Controls the lower RED(Random Early Detection) threshold.
       If the average queue filling level is below this threshold, the drop
       probability is zero.
         range: 0-100"
   ::= { gs2352pQosWREDEntry 3 }

gs2352pQosWREDMaxDP1 OBJECT-TYPE
   SYNTAX      Integer32(0..100)
   MAX-ACCESS  read-write
   STATUS      current
   DESCRIPTION
       " Controls the drop probability for frames marked with Drop Precedence
       Level 1 when the average queue filling level is 100%.
         range: 0-100,
         default: 1. "
   ::= { gs2352pQosWREDEntry 4 }

gs2352pQosWREDMaxDP2 OBJECT-TYPE
   SYNTAX      Integer32(0..100)
   MAX-ACCESS  read-write
   STATUS      current
   DESCRIPTION
       " Controls the drop probability for frames marked with Drop Precedence
       Level 2 when the average queue filling level is 100%.
         range: 0-100,
         default: 5. "
   ::= { gs2352pQosWREDEntry 5 }

gs2352pQosWREDMaxDP3 OBJECT-TYPE
   SYNTAX      Integer32(0..100)
   MAX-ACCESS  read-write
   STATUS      current
   DESCRIPTION
       " Controls the drop probability for frames marked with Drop Precedence
       Level 3 when the average queue filling level is 100%.
         range: 0-100,
         default: 10. "
   ::= { gs2352pQosWREDEntry 6 }

gs2352pVlan                                                           OBJECT IDENTIFIER ::= { gs2352pConfiguration 15 }

gs2352pVlanPorts                                                      OBJECT IDENTIFIER ::= { gs2352pVlan 1 }

gs2352pVlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2352pVlanPorts 1 }

gs2352pVlanPortsTable OBJECT-TYPE
   SYNTAX      SEQUENCE OF GS2352PVlanPortsEntry
   MAX-ACCESS  not-accessible
   STATUS      current
   DESCRIPTION
       " Configure Vlan ports Configuration mode. "
   ::= { gs2352pVlanPorts 2 }

gs2352pVlanPortsEntry OBJECT-TYPE
   SYNTAX      GS2352PVlanPortsEntry
   MAX-ACCESS  not-accessible
   STATUS      current
   DESCRIPTION
       ""
   INDEX    { gs2352pVlanPortsPort  }
   ::= { gs2352pVlanPortsTable 1 }

GS2352PVlanPortsEntry ::= SEQUENCE {
   gs2352pVlanPortsPort	         Integer32,
   gs2352pVlanPortsNativeVLAN     Integer32,
   gs2352pVlanPortsFrameType      INTEGER,
   gs2352pVlanPortsIngressFilter  INTEGER,
   gs2352pVlanPortsEgressRule     INTEGER,
   gs2352pVlanPortsPortType       INTEGER
}

gs2352pVlanPortsPort OBJECT-TYPE
   SYNTAX      Integer32(1..4094)
   MAX-ACCESS  not-accessible
   STATUS      current
   DESCRIPTION
       " port, range : 1 - port number. "
   ::= { gs2352pVlanPortsEntry 1 }

gs2352pVlanPortsNativeVLAN OBJECT-TYPE
   SYNTAX      Integer32(1..4094)
   MAX-ACCESS  read-write
   STATUS      current
   DESCRIPTION
       "Configure native VLAN ID.
        range: 1-4094,
        default: 1. "
   ::= { gs2352pVlanPortsEntry 2 }

gs2352pVlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2352pVlanPortsEntry 3 }

gs2352pVlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2352pVlanPortsEntry 4 }

gs2352pVlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2352pVlanPortsEntry 5 }

gs2352pVlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2352pVlanPortsEntry 6 }

gs2352pVlanPrivateVLAN                                                              OBJECT IDENTIFIER ::= { gs2352pVlan 2 }

gs2352pVlanPortIsolationTable OBJECT-TYPE
   SYNTAX      SEQUENCE OF Gs2352pVlanPortIsolationEntry
   MAX-ACCESS  not-accessible
   STATUS      current
   DESCRIPTION
       " Configure Vlan Port Isolation Configuration. "
   ::= { gs2352pVlanPrivateVLAN 2 }

gs2352pVlanPortIsolationEntry OBJECT-TYPE
   SYNTAX      Gs2352pVlanPortIsolationEntry
   MAX-ACCESS  not-accessible
   STATUS      current
   DESCRIPTION
       ""
   INDEX    { gs2352pVlanPortIsolationPort  }
   ::= { gs2352pVlanPortIsolationTable 1 }

Gs2352pVlanPortIsolationEntry ::= SEQUENCE {
   gs2352pVlanPortIsolationPort Integer32,
   gs2352pVlanPortIsolation     INTEGER
}

gs2352pVlanPortIsolationPort OBJECT-TYPE
   SYNTAX      Integer32(1..4094)
   MAX-ACCESS  not-accessible
   STATUS      current
   DESCRIPTION
       " port, range : 1 - port number. "
   ::= { gs2352pVlanPortIsolationEntry 1 }

gs2352pVlanPortIsolation OBJECT-TYPE
   SYNTAX      INTEGER{ disable(0), enable(1) }
   MAX-ACCESS  read-write
   STATUS      current
   DESCRIPTION
       "default: 0
        0:disable
        1:enable"
   ::= { gs2352pVlanPortIsolationEntry 2 }


gs2352pMACbasedVLAN                                                      OBJECT IDENTIFIER ::= { gs2352pVlan 3 }

gs2352pMACbasedVLANConf                                                      OBJECT IDENTIFIER ::= { gs2352pMACbasedVLAN 1 }

gs2352pMACbasedVLANConfCreate OBJECT-TYPE
   SYNTAX       Integer32
   MAX-ACCESS   read-write
   STATUS       current
   DESCRIPTION
       "default: 0
       0 : None  (read only) 1 : Create MAC base vlan"
   ::= { gs2352pMACbasedVLANConf 1 }

gs2352pMACbasedVLANConfTable OBJECT-TYPE
   SYNTAX      SEQUENCE OF Gs2352pMACbasedVLANConfEntry
   MAX-ACCESS  not-accessible
   STATUS      current
   DESCRIPTION
       " Configure Vlan Port Isolation Configuration. "
   ::= { gs2352pMACbasedVLANConf 2 }

gs2352pMACbasedVLANConfEntry OBJECT-TYPE
   SYNTAX      Gs2352pMACbasedVLANConfEntry
   MAX-ACCESS  not-accessible
   STATUS      current
   DESCRIPTION
       ""
   INDEX    { gs2352pMACbasedVLANIndex  }
   ::= { gs2352pMACbasedVLANConfTable 1 }

Gs2352pMACbasedVLANConfEntry ::= SEQUENCE {
   gs2352pMACbasedVLANIndex         Integer32,
   gs2352pMACbasedVLANMACAddress    MacAddress,
   gs2352pMACbasedVLANID            Integer32,
   gs2352pMACbasedMemberships       DisplayString,
   gs2352pMACbaseRowStatus          INTEGER
}

gs2352pMACbasedVLANIndex OBJECT-TYPE
   SYNTAX      Integer32(1..256)
   MAX-ACCESS  read-write
   STATUS      current
   DESCRIPTION
       "Indicates the VLAN ID. "
   ::= { gs2352pMACbasedVLANConfEntry 1 }

gs2352pMACbasedVLANMACAddress OBJECT-TYPE
   SYNTAX      MacAddress
   MAX-ACCESS  read-write
   STATUS      current
   DESCRIPTION
       "Indicates the MAC address.
       The CreateEntry can be modify, the other entry can't be modify."
   ::= { gs2352pMACbasedVLANConfEntry 2 }

gs2352pMACbasedVLANID OBJECT-TYPE
   SYNTAX      Integer32(1..4094)
   MAX-ACCESS  read-write
   STATUS      current
   DESCRIPTION
       "Indicates the VLAN ID. "
   ::= { gs2352pMACbasedVLANConfEntry 3 }

gs2352pMACbasedMemberships OBJECT-TYPE
   SYNTAX      DisplayString
   MAX-ACCESS  read-write
   STATUS      current
   DESCRIPTION
       "The ports are displayed for each MAC-based VLAN entry.
        To include the port in a MAC-based VLAN"
   ::= { gs2352pMACbasedVLANConfEntry 4 }


gs2352pMACbaseRowStatus OBJECT-TYPE
   SYNTAX      INTEGER { active(1), notInservice(2), destroy(4)}
   MAX-ACCESS  read-write
   STATUS      current
   DESCRIPTION
       "1: active
        2: notInservice
        4: destroy"
   ::= { gs2352pMACbasedVLANConfEntry 5 }

gs2352pIGMPSnooping                                                           OBJECT IDENTIFIER ::= { gs2352pConfiguration 16 }

gs2352pIGMPSnoopingBasic                                                      OBJECT IDENTIFIER ::= { gs2352pIGMPSnooping 1 }

gs2352pIGMPSnoopingEnable  OBJECT-TYPE
   SYNTAX      INTEGER { disable(0), enable(1) }
   MAX-ACCESS  read-write
   STATUS      current
   DESCRIPTION
       "Enable/Disable the Global IGMP Snooping"
   ::= { gs2352pIGMPSnoopingBasic 1 }

gs2352pIGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2352pIGMPSnoopingBasic 2 }

gs2352pIGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2352pIGMPSnoopingBasic 3 }
   
gs2352pIGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2352pIGMPSnoopingBasic 4 }

gs2352pIGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2352pIGMPSnoopingBasic 5 }

gs2352pIGMPSnoopingPortRelatedTable OBJECT-TYPE
   SYNTAX      SEQUENCE OF Gs2352pIGMPSnoopingPortRelatedEntry
   MAX-ACCESS  not-accessible
   STATUS      current
   DESCRIPTION
       " Configure IGMP Snooping Port Related Configuration. "
   ::= { gs2352pIGMPSnoopingBasic 6 }

gs2352pIGMPSnoopingPortRelatedEntry OBJECT-TYPE
   SYNTAX      Gs2352pIGMPSnoopingPortRelatedEntry
   MAX-ACCESS  not-accessible
   STATUS      current
   DESCRIPTION
       ""
   INDEX    { ifIndex  }
   ::= { gs2352pIGMPSnoopingPortRelatedTable 1 }

Gs2352pIGMPSnoopingPortRelatedEntry ::= SEQUENCE {
   gs2352pIGMPSnoopingRouterPort	INTEGER,
   gs2352pIGMPSnoopingFastLeave  	INTEGER,
   gs2352pIGMPSnoopingThrottling    Integer32
}

gs2352pIGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2352pIGMPSnoopingPortRelatedEntry 1 }

gs2352pIGMPSnoopingFastLeave OBJECT-TYPE
   SYNTAX      INTEGER { disable(0), enable(1) }
   MAX-ACCESS  read-write
   STATUS      current
   DESCRIPTION
       "Enable/Disable the fast leave on the port. "
   ::= { gs2352pIGMPSnoopingPortRelatedEntry 2 }
   
gs2352pIGMPSnoopingThrottling OBJECT-TYPE
   SYNTAX      Integer32(0..10)
   MAX-ACCESS  read-write
   STATUS      current
   DESCRIPTION
       "Enable to limit the number of multicast groups to which a switch port can belong.
       0: unlimited"
   ::= { gs2352pIGMPSnoopingPortRelatedEntry 3 }
   
gs2352pIGMPSnoopingVLANTable OBJECT-TYPE
   SYNTAX      SEQUENCE OF Gs2352pIGMPSnoopingVLANEntry
   MAX-ACCESS  not-accessible
   STATUS      current
   DESCRIPTION
       " Configure IGMP Snooping Vlan Configuration. "
   ::= { gs2352pIGMPSnooping 2 }

gs2352pIGMPSnoopingVLANEntry OBJECT-TYPE
   SYNTAX      Gs2352pIGMPSnoopingVLANEntry
   MAX-ACCESS  not-accessible
   STATUS      current
   DESCRIPTION
       ""
   INDEX    { gs2352pIGMPSnoopingVLANID  }
   ::= { gs2352pIGMPSnoopingVLANTable 1 }

Gs2352pIGMPSnoopingVLANEntry ::= SEQUENCE {
   gs2352pIGMPSnoopingVLANID        	Integer32,
   gs2352pIGMPSnoopingVLANEnable    	INTEGER,
   gs2352pIGMPSnoopingVLANIGMPQuerier   INTEGER,
   gs2352pIGMPSnoopingVLANCompatibility INTEGER,
   gs2352pIGMPSnoopingVLANRV        	Integer32,
   gs2352pIGMPSnoopingVLANQI      	    Integer32,
   gs2352pIGMPSnoopingVLANQRI   	    Integer32,
   gs2352pIGMPSnoopingVLANLLQI   	    Integer32,
   gs2352pIGMPSnoopingVLANURI    	    Integer32
}

gs2352pIGMPSnoopingVLANID OBJECT-TYPE
   SYNTAX      Integer32(1..4095)
   MAX-ACCESS  read-write
   STATUS      current
   DESCRIPTION
       "The VLAN ID of the entry"
   ::= { gs2352pIGMPSnoopingVLANEntry 1 }

gs2352pIGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2352pIGMPSnoopingVLANEntry 2 }

gs2352pIGMPSnoopingVLANIGMPQuerier OBJECT-TYPE
   SYNTAX      INTEGER { disable(0), enable(1) }
   MAX-ACCESS  read-write
   STATUS      current
   DESCRIPTION
       "Enable/Disable the IGMP Querier in the VLAN. "
   ::= { gs2352pIGMPSnoopingVLANEntry 3 }

gs2352pIGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2352pIGMPSnoopingVLANEntry 4 }
   
gs2352pIGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2352pIGMPSnoopingVLANEntry 5 }
   
gs2352pIGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2352pIGMPSnoopingVLANEntry 6 }
   
gs2352pIGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2352pIGMPSnoopingVLANEntry 7 }
   
gs2352pIGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2352pIGMPSnoopingVLANEntry 8 }

gs2352pIGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2352pIGMPSnoopingVLANEntry 9 }

gs2352pIGMPSnoopingPortGroupFiltering                                                      OBJECT IDENTIFIER ::= { gs2352pIGMPSnooping 3 }

gs2352pIGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2352pIGMPSnoopingPortGroupFiltering 1 }

gs2352pIGMPSnoopingPortGroupFilteringTable OBJECT-TYPE
   SYNTAX      SEQUENCE OF Gs2352pIGMPSnoopingPortGroupFilteringEntry
   MAX-ACCESS  not-accessible
   STATUS      current
   DESCRIPTION
       " Configure IGMP Snooping port group filtering. "
   ::= { gs2352pIGMPSnoopingPortGroupFiltering 2 }

gs2352pIGMPSnoopingPortGroupFilteringEntry OBJECT-TYPE
   SYNTAX      Gs2352pIGMPSnoopingPortGroupFilteringEntry
   MAX-ACCESS  not-accessible
   STATUS      current
   DESCRIPTION
       ""
   INDEX    { gs2352pIGMPSnoopingPortGroupFilteringIndex  }
   ::= { gs2352pIGMPSnoopingPortGroupFilteringTable 1 }

Gs2352pIGMPSnoopingPortGroupFilteringEntry ::= SEQUENCE {
   gs2352pIGMPSnoopingPortGroupFilteringIndex         Integer32,
   gs2352pIGMPSnoopingPortGroupFilteringPort          Integer32,
   gs2352pIGMPSnoopingPortGroupFilteringGroups        DisplayString,
   gs2352pIGMPSnoopingPortGroupFilteringRowStatus     INTEGER
}

gs2352pIGMPSnoopingPortGroupFilteringIndex OBJECT-TYPE
   SYNTAX      Integer32(1..65535)
   MAX-ACCESS  not-accessible
   STATUS      current
   DESCRIPTION
       "IGMP Snooping Port Group Filtering Configuration Index. "
   ::= { gs2352pIGMPSnoopingPortGroupFilteringEntry 1 }

gs2352pIGMPSnoopingPortGroupFilteringPort OBJECT-TYPE
   SYNTAX      Integer32(1..65535)
   MAX-ACCESS  read-write
   STATUS      current
   DESCRIPTION
       "The logical port for the settings. "
   ::= { gs2352pIGMPSnoopingPortGroupFilteringEntry 2 }

gs2352pIGMPSnoopingPortGroupFilteringGroups OBJECT-TYPE
   SYNTAX      DisplayString
   MAX-ACCESS  read-write
   STATUS      current
   DESCRIPTION
       "The IP Multicast Group that will be filtered. "
   ::= { gs2352pIGMPSnoopingPortGroupFilteringEntry 3 }

gs2352pIGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2352pIGMPSnoopingPortGroupFilteringEntry 4 }

gs2352pIGMPSnoopingStatus                                                      OBJECT IDENTIFIER ::= { gs2352pIGMPSnooping 4 }

gs2352pIGMPSnoopingstatisticClear OBJECT-TYPE
   SYNTAX      INTEGER { none(0), clear(1)}
   MAX-ACCESS  read-write
   STATUS      current
   DESCRIPTION
       "Clears all Statistics counters."
   ::= { gs2352pIGMPSnoopingStatus 1 }


gs2352pIGMPSnoopingstatisticTable OBJECT-TYPE
   SYNTAX      SEQUENCE OF Gs2352pIGMPSnoopingstatisticEntry
   MAX-ACCESS  not-accessible
   STATUS      current
   DESCRIPTION
       " Configure Vlan Port Isolation Configuration. "
   ::= { gs2352pIGMPSnoopingStatus 2 }

gs2352pIGMPSnoopingstatisticEntry OBJECT-TYPE
   SYNTAX      Gs2352pIGMPSnoopingstatisticEntry
   MAX-ACCESS  not-accessible
   STATUS      current
   DESCRIPTION
       ""
   INDEX    { gs2352pIGMPSnoopingstatisticVLANID  }
   ::= { gs2352pIGMPSnoopingstatisticTable 1 }

Gs2352pIGMPSnoopingstatisticEntry ::= SEQUENCE {
   gs2352pIGMPSnoopingstatisticVLANID              Integer32,
   gs2352pIGMPSnoopingstatisticQuerierVersion      DisplayString,
   gs2352pIGMPSnoopingstatisticHostVersion         DisplayString,
   gs2352pIGMPSnoopingstatisticQuerierStatus       DisplayString,
   gs2352pIGMPSnoopingstatisticQueriesTransmitted  Counter32,
   gs2352pIGMPSnoopingstatisticQueriesReceived     Counter32,
   gs2352pIGMPSnoopingstatisticV1ReportsReceived   Counter32,
   gs2352pIGMPSnoopingstatisticV2ReportsReceived   Counter32,
   gs2352pIGMPSnoopingstatisticV3ReportsReceived   Counter32,
   gs2352pIGMPSnoopingstatisticV2LeavesReceived    Counter32
}


gs2352pIGMPSnoopingstatisticVLANID OBJECT-TYPE
   SYNTAX      Integer32(1..4095)
   MAX-ACCESS  read-only
   STATUS      current
   DESCRIPTION
       "The VLAN ID of the entry. "
   ::= { gs2352pIGMPSnoopingstatisticEntry 1 }

gs2352pIGMPSnoopingstatisticQuerierVersion OBJECT-TYPE
   SYNTAX      DisplayString
   MAX-ACCESS  read-only
   STATUS      current
   DESCRIPTION
       "Working Querier Version currently. "
   ::= { gs2352pIGMPSnoopingstatisticEntry 2 }
   
gs2352pIGMPSnoopingstatisticHostVersion OBJECT-TYPE
   SYNTAX      DisplayString
   MAX-ACCESS  read-only
   STATUS      current
   DESCRIPTION
       "Working Host Version currently. "
   ::= { gs2352pIGMPSnoopingstatisticEntry 3 }

gs2352pIGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2352pIGMPSnoopingstatisticEntry 4 }

gs2352pIGMPSnoopingstatisticQueriesTransmitted OBJECT-TYPE
   SYNTAX      Counter32
   MAX-ACCESS  read-only
   STATUS      current
   DESCRIPTION
       "The number of Transmitted Queries. "
   ::= { gs2352pIGMPSnoopingstatisticEntry 5 }

gs2352pIGMPSnoopingstatisticQueriesReceived OBJECT-TYPE
   SYNTAX      Counter32
   MAX-ACCESS  read-only
   STATUS      current
   DESCRIPTION
       "The number of Received Queries. "
   ::= { gs2352pIGMPSnoopingstatisticEntry 6 }

gs2352pIGMPSnoopingstatisticV1ReportsReceived OBJECT-TYPE
   SYNTAX      Counter32
   MAX-ACCESS  read-only
   STATUS      current
   DESCRIPTION
       "The number of Received V1 Reports. "
   ::= { gs2352pIGMPSnoopingstatisticEntry 7 }

gs2352pIGMPSnoopingstatisticV2ReportsReceived OBJECT-TYPE
   SYNTAX      Counter32
   MAX-ACCESS  read-only
   STATUS      current
   DESCRIPTION
       "The number of Received V2 Reports. "
   ::= { gs2352pIGMPSnoopingstatisticEntry 8 }

gs2352pIGMPSnoopingstatisticV3ReportsReceived OBJECT-TYPE
   SYNTAX      Counter32
   MAX-ACCESS  read-only
   STATUS      current
   DESCRIPTION
       "The number of Received V3 Reports. "
   ::= { gs2352pIGMPSnoopingstatisticEntry 9 }

gs2352pIGMPSnoopingstatisticV2LeavesReceived OBJECT-TYPE
   SYNTAX      Counter32
   MAX-ACCESS  read-only
   STATUS      current
   DESCRIPTION
       "The number of Received V2 Leaves. "
   ::= { gs2352pIGMPSnoopingstatisticEntry 10 }

gs2352pIGMPSnoopingRouterPortTable OBJECT-TYPE
   SYNTAX      SEQUENCE OF Gs2352pIGMPSnoopingRouterPortEntry
   MAX-ACCESS  not-accessible
   STATUS      current
   DESCRIPTION
       " Configure Vlan Port Isolation Configuration. "
   ::= { gs2352pIGMPSnoopingStatus 3 }

gs2352pIGMPSnoopingRouterPortEntry OBJECT-TYPE
   SYNTAX      Gs2352pIGMPSnoopingRouterPortEntry
   MAX-ACCESS  not-accessible
   STATUS      current
   DESCRIPTION
       ""
   INDEX    { ifIndex  }
   ::= { gs2352pIGMPSnoopingRouterPortTable 1 }

Gs2352pIGMPSnoopingRouterPortEntry ::= SEQUENCE {
   gs2352pIGMPSnoopingRouterPortStatus            DisplayString
}

gs2352pIGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2352pIGMPSnoopingRouterPortEntry 1 }

gs2352pIGMPSnoopingGroupsTable OBJECT-TYPE
   SYNTAX      SEQUENCE OF Gs2352pIGMPSnoopingGroupsEntry
   MAX-ACCESS  not-accessible
   STATUS      current
   DESCRIPTION
       "IGMP Snooping Groups Information . "
   ::= { gs2352pIGMPSnooping 5 }

gs2352pIGMPSnoopingGroupsEntry OBJECT-TYPE
   SYNTAX      Gs2352pIGMPSnoopingGroupsEntry
   MAX-ACCESS  not-accessible
   STATUS      current
   DESCRIPTION
       ""
   INDEX    { gs2352pIGMPSnoopingGroupsIndex  }
   ::= { gs2352pIGMPSnoopingGroupsTable 1 }

Gs2352pIGMPSnoopingGroupsEntry ::= SEQUENCE {
   gs2352pIGMPSnoopingGroupsIndex          Integer32,
   gs2352pIGMPSnoopingGroupsVLANID         Integer32,
   gs2352pIGMPSnoopingGroups               InetAddress,
   gs2352pIGMPSnoopingGroupsMemberships    DisplayString
}

gs2352pIGMPSnoopingGroupsIndex OBJECT-TYPE
   SYNTAX      Integer32(1..65535)
   MAX-ACCESS  not-accessible
   STATUS      current
   DESCRIPTION
       "IGMP Snooping Groups Index"
   ::= { gs2352pIGMPSnoopingGroupsEntry 1 }

gs2352pIGMPSnoopingGroupsVLANID OBJECT-TYPE
   SYNTAX      Integer32(1..4095)
   MAX-ACCESS  read-only
   STATUS      current
   DESCRIPTION
       "VLAN ID of the group. "
   ::= { gs2352pIGMPSnoopingGroupsEntry 2 }

gs2352pIGMPSnoopingGroups OBJECT-TYPE
   SYNTAX      DisplayString
   MAX-ACCESS  read-only
   STATUS      current
   DESCRIPTION
       "Group address of the group displayed."
   ::= { gs2352pIGMPSnoopingGroupsEntry 3 }

gs2352pIGMPSnoopingGroupsMemberships OBJECT-TYPE
   SYNTAX      DisplayString
   MAX-ACCESS  read-only
   STATUS      current
   DESCRIPTION
       "Ports under this group."
   ::= { gs2352pIGMPSnoopingGroupsEntry 4 }
   
gs2352pIGMPSnoopingSSMTable OBJECT-TYPE
   SYNTAX      SEQUENCE OF Gs2352pIGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2352pIGMPSnooping 6 }

gs2352pIGMPSnoopingSSMEntry OBJECT-TYPE
   SYNTAX      Gs2352pIGMPSnoopingSSMEntry
   MAX-ACCESS  not-accessible
   STATUS      current
   DESCRIPTION
       ""
   INDEX    { gs2352pIGMPSnoopingSSMIndex  }
   ::= { gs2352pIGMPSnoopingSSMTable 1 }

Gs2352pIGMPSnoopingSSMEntry ::= SEQUENCE {
   gs2352pIGMPSnoopingSSMIndex          Integer32,
   gs2352pIGMPSnoopingSSMVLANID         Integer32,
   gs2352pIGMPSnoopingSSMGroup          DisplayString,
   gs2352pIGMPSnoopingSSMPort           Integer32,
   gs2352pIGMPSnoopingSSMMode           DisplayString,
   gs2352pIGMPSnoopingSSMSourceAddress  DisplayString,
   gs2352pIGMPSnoopingSSMType           DisplayString
}

gs2352pIGMPSnoopingSSMIndex OBJECT-TYPE
   SYNTAX      Integer32(1..65535)
   MAX-ACCESS  not-accessible
   STATUS      current
   DESCRIPTION
       "IGMP Snooping SSM Index"
   ::= { gs2352pIGMPSnoopingSSMEntry 1 }

gs2352pIGMPSnoopingSSMVLANID OBJECT-TYPE
   SYNTAX      Integer32(1..4095)
   MAX-ACCESS  read-only
   STATUS      current
   DESCRIPTION
       "VLAN ID of the group. "
   ::= { gs2352pIGMPSnoopingSSMEntry 2 }

gs2352pIGMPSnoopingSSMGroup OBJECT-TYPE
   SYNTAX      DisplayString
   MAX-ACCESS  read-only
   STATUS      current
   DESCRIPTION
       "Group address of the group displayed."
   ::= { gs2352pIGMPSnoopingSSMEntry 3 }

gs2352pIGMPSnoopingSSMPort OBJECT-TYPE
   SYNTAX      Integer32(1..65535)
   MAX-ACCESS  read-only
   STATUS      current
   DESCRIPTION
       "Ports under this group."
   ::= { gs2352pIGMPSnoopingSSMEntry 4 }
   
gs2352pIGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2352pIGMPSnoopingSSMEntry 5 }
   
gs2352pIGMPSnoopingSSMSourceAddress OBJECT-TYPE
   SYNTAX      DisplayString
   MAX-ACCESS  read-only
   STATUS      current
   DESCRIPTION
       "IP Address of the source. Currently, system limits the total number of
       IP source addresses for filtering to be 128."
   ::= { gs2352pIGMPSnoopingSSMEntry 6 }

gs2352pIGMPSnoopingSSMType OBJECT-TYPE
   SYNTAX      DisplayString
   MAX-ACCESS  read-only
   STATUS      current
   DESCRIPTION
       "Indicates the Type. It can be either Allow or Deny."
   ::= { gs2352pIGMPSnoopingSSMEntry 7 }   
   
gs2352pMLDSnooping                                                           OBJECT IDENTIFIER ::= { gs2352pConfiguration 17 }

gs2352pMLDSnoopingBasic                                                      OBJECT IDENTIFIER ::= { gs2352pMLDSnooping 1 }

gs2352pMLDSnoopingEnable  OBJECT-TYPE
   SYNTAX      INTEGER { disable(0), enable(1) }
   MAX-ACCESS  read-write
   STATUS      current
   DESCRIPTION
       "Enable/Disable the Global MLD Snooping"
   ::= { gs2352pMLDSnoopingBasic 1 }

gs2352pMLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2352pMLDSnoopingBasic 2 }

gs2352pMLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2352pMLDSnoopingBasic 3 }
   
gs2352pMLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2352pMLDSnoopingBasic 4 }

gs2352pMLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2352pMLDSnoopingBasic 5 }

gs2352pMLDSnoopingPortRelatedTable OBJECT-TYPE
   SYNTAX      SEQUENCE OF Gs2352pMLDSnoopingPortRelatedEntry
   MAX-ACCESS  not-accessible
   STATUS      current
   DESCRIPTION
       " Configure MLD Snooping Port Related Configuration. "
   ::= { gs2352pMLDSnoopingBasic 6 }

gs2352pMLDSnoopingPortRelatedEntry OBJECT-TYPE
   SYNTAX      Gs2352pMLDSnoopingPortRelatedEntry
   MAX-ACCESS  not-accessible
   STATUS      current
   DESCRIPTION
       ""
   INDEX    { ifIndex  }
   ::= { gs2352pMLDSnoopingPortRelatedTable 1 }

Gs2352pMLDSnoopingPortRelatedEntry ::= SEQUENCE {
   gs2352pMLDSnoopingRouterPort	INTEGER,
   gs2352pMLDSnoopingFastLeave  	INTEGER,
   gs2352pMLDSnoopingThrottling    Integer32
}

gs2352pMLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2352pMLDSnoopingPortRelatedEntry 1 }

gs2352pMLDSnoopingFastLeave OBJECT-TYPE
   SYNTAX      INTEGER { disable(0), enable(1) }
   MAX-ACCESS  read-write
   STATUS      current
   DESCRIPTION
       "Enable/Disable the fast leave on the port. "
   ::= { gs2352pMLDSnoopingPortRelatedEntry 2 }
   
gs2352pMLDSnoopingThrottling OBJECT-TYPE
   SYNTAX      Integer32(0..10)
   MAX-ACCESS  read-write
   STATUS      current
   DESCRIPTION
       "Enable to limit the number of multicast groups to which a switch port can belong.
       0: unlimited"
   ::= { gs2352pMLDSnoopingPortRelatedEntry 3 }
   
gs2352pMLDSnoopingVLANTable OBJECT-TYPE
   SYNTAX      SEQUENCE OF Gs2352pMLDSnoopingVLANEntry
   MAX-ACCESS  not-accessible
   STATUS      current
   DESCRIPTION
       " Configure MLD Snooping Vlan Configuration. "
   ::= { gs2352pMLDSnooping 2 }

gs2352pMLDSnoopingVLANEntry OBJECT-TYPE
   SYNTAX      Gs2352pMLDSnoopingVLANEntry
   MAX-ACCESS  not-accessible
   STATUS      current
   DESCRIPTION
       ""
   INDEX    { gs2352pMLDSnoopingVLANID  }
   ::= { gs2352pMLDSnoopingVLANTable 1 }

Gs2352pMLDSnoopingVLANEntry ::= SEQUENCE {
   gs2352pMLDSnoopingVLANID        	Integer32,
   gs2352pMLDSnoopingVLANEnable    	INTEGER,
   gs2352pMLDSnoopingVLANIGMPQuerier   INTEGER,
   gs2352pMLDSnoopingVLANCompatibility INTEGER,
   gs2352pMLDSnoopingVLANRV        	Integer32,
   gs2352pMLDSnoopingVLANQI      	    Integer32,
   gs2352pMLDSnoopingVLANQRI   	    Integer32,
   gs2352pMLDSnoopingVLANLLQI   	    Integer32,
   gs2352pMLDSnoopingVLANURI    	    Integer32
}

gs2352pMLDSnoopingVLANID OBJECT-TYPE
   SYNTAX      Integer32(1..4095)
   MAX-ACCESS  read-write
   STATUS      current
   DESCRIPTION
       "The VLAN ID of the entry"
   ::= { gs2352pMLDSnoopingVLANEntry 1 }

gs2352pMLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2352pMLDSnoopingVLANEntry 2 }

gs2352pMLDSnoopingVLANIGMPQuerier OBJECT-TYPE
   SYNTAX      INTEGER { disable(0), enable(1) }
   MAX-ACCESS  read-write
   STATUS      current
   DESCRIPTION
       "Enable/Disable the MLD Querier in the VLAN. "
   ::= { gs2352pMLDSnoopingVLANEntry 3 }

gs2352pMLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2352pMLDSnoopingVLANEntry 4 }
   
gs2352pMLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2352pMLDSnoopingVLANEntry 5 }
   
gs2352pMLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2352pMLDSnoopingVLANEntry 6 }
   
gs2352pMLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2352pMLDSnoopingVLANEntry 7 }
   
gs2352pMLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2352pMLDSnoopingVLANEntry 8 }

gs2352pMLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2352pMLDSnoopingVLANEntry 9 }

gs2352pMLDSnoopingPortGroupFiltering                                                      OBJECT IDENTIFIER ::= { gs2352pMLDSnooping 3 }

gs2352pMLDSnoopingPortGroupFilteringCreate OBJECT-TYPE
   SYNTAX       Integer32
   MAX-ACCESS   read-write
   STATUS       current
   DESCRIPTION
       "default: 0
       0 : None  (read only) 1 : Create MLD Snooping Port Group Filtering "
   ::= { gs2352pMLDSnoopingPortGroupFiltering 1 }

gs2352pMLDSnoopingPortGroupFilteringTable OBJECT-TYPE
   SYNTAX      SEQUENCE OF Gs2352pMLDSnoopingPortGroupFilteringEntry
   MAX-ACCESS  not-accessible
   STATUS      current
   DESCRIPTION
       " Configure MLD Snooping port group filtering. "
   ::= { gs2352pMLDSnoopingPortGroupFiltering 2 }

gs2352pMLDSnoopingPortGroupFilteringEntry OBJECT-TYPE
   SYNTAX      Gs2352pMLDSnoopingPortGroupFilteringEntry
   MAX-ACCESS  not-accessible
   STATUS      current
   DESCRIPTION
       ""
   INDEX    { gs2352pMLDSnoopingPortGroupFilteringIndex  }
   ::= { gs2352pMLDSnoopingPortGroupFilteringTable 1 }

Gs2352pMLDSnoopingPortGroupFilteringEntry ::= SEQUENCE {
   gs2352pMLDSnoopingPortGroupFilteringIndex         Integer32,
   gs2352pMLDSnoopingPortGroupFilteringPort          Integer32,
   gs2352pMLDSnoopingPortGroupFilteringGroups        DisplayString,
   gs2352pMLDSnoopingPortGroupFilteringRowStatus     INTEGER
}

gs2352pMLDSnoopingPortGroupFilteringIndex OBJECT-TYPE
   SYNTAX      Integer32(1..65535)
   MAX-ACCESS  not-accessible
   STATUS      current
   DESCRIPTION
       "MLD Snooping Port Group Filtering Configuration Index. "
   ::= { gs2352pMLDSnoopingPortGroupFilteringEntry 1 }

gs2352pMLDSnoopingPortGroupFilteringPort OBJECT-TYPE
   SYNTAX      Integer32(1..65535)
   MAX-ACCESS  read-write
   STATUS      current
   DESCRIPTION
       "The logical port for the settings. "
   ::= { gs2352pMLDSnoopingPortGroupFilteringEntry 2 }

gs2352pMLDSnoopingPortGroupFilteringGroups OBJECT-TYPE
   SYNTAX      DisplayString
   MAX-ACCESS  read-write
   STATUS      current
   DESCRIPTION
       "The IP Multicast Group that will be filtered. "
   ::= { gs2352pMLDSnoopingPortGroupFilteringEntry 3 }

gs2352pMLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2352pMLDSnoopingPortGroupFilteringEntry 4 }

gs2352pMLDSnoopingStatus                                                      OBJECT IDENTIFIER ::= { gs2352pMLDSnooping 4 }

gs2352pMLDSnoopingstatisticClear OBJECT-TYPE
   SYNTAX      INTEGER { none(0), clear(1)}
   MAX-ACCESS  read-write
   STATUS      current
   DESCRIPTION
       "Clears all Statistics counters."
   ::= { gs2352pMLDSnoopingStatus 1 }


gs2352pMLDSnoopingstatisticTable OBJECT-TYPE
   SYNTAX      SEQUENCE OF Gs2352pMLDSnoopingstatisticEntry
   MAX-ACCESS  not-accessible
   STATUS      current
   DESCRIPTION
       " Configure Vlan Port Isolation Configuration. "
   ::= { gs2352pMLDSnoopingStatus 2 }

gs2352pMLDSnoopingstatisticEntry OBJECT-TYPE
   SYNTAX      Gs2352pMLDSnoopingstatisticEntry
   MAX-ACCESS  not-accessible
   STATUS      current
   DESCRIPTION
       ""
   INDEX    { gs2352pMLDSnoopingstatisticVLANID  }
   ::= { gs2352pMLDSnoopingstatisticTable 1 }

Gs2352pMLDSnoopingstatisticEntry ::= SEQUENCE {
   gs2352pMLDSnoopingstatisticVLANID              Integer32,
   gs2352pMLDSnoopingstatisticQuerierVersion      DisplayString,
   gs2352pMLDSnoopingstatisticHostVersion         DisplayString,
   gs2352pMLDSnoopingstatisticQuerierStatus       DisplayString,
   gs2352pMLDSnoopingstatisticQueriesTransmitted  Counter32,
   gs2352pMLDSnoopingstatisticQueriesReceived     Counter32,
   gs2352pMLDSnoopingstatisticV1ReportsReceived   Counter32,
   gs2352pMLDSnoopingstatisticV2ReportsReceived   Counter32,
   gs2352pMLDSnoopingstatisticV1LeavesReceived    Counter32
}


gs2352pMLDSnoopingstatisticVLANID OBJECT-TYPE
   SYNTAX      Integer32(1..4095)
   MAX-ACCESS  read-only
   STATUS      current
   DESCRIPTION
       "The VLAN ID of the entry. "
   ::= { gs2352pMLDSnoopingstatisticEntry 1 }

gs2352pMLDSnoopingstatisticQuerierVersion OBJECT-TYPE
   SYNTAX      DisplayString
   MAX-ACCESS  read-only
   STATUS      current
   DESCRIPTION
       "Working Querier Version currently. "
   ::= { gs2352pMLDSnoopingstatisticEntry 2 }
   
gs2352pMLDSnoopingstatisticHostVersion OBJECT-TYPE
   SYNTAX      DisplayString
   MAX-ACCESS  read-only
   STATUS      current
   DESCRIPTION
       "Working Host Version currently. "
   ::= { gs2352pMLDSnoopingstatisticEntry 3 }

gs2352pMLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2352pMLDSnoopingstatisticEntry 4 }

gs2352pMLDSnoopingstatisticQueriesTransmitted OBJECT-TYPE
   SYNTAX      Counter32
   MAX-ACCESS  read-only
   STATUS      current
   DESCRIPTION
       "The number of Transmitted Queries. "
   ::= { gs2352pMLDSnoopingstatisticEntry 5 }

gs2352pMLDSnoopingstatisticQueriesReceived OBJECT-TYPE
   SYNTAX      Counter32
   MAX-ACCESS  read-only
   STATUS      current
   DESCRIPTION
       "The number of Received Queries. "
   ::= { gs2352pMLDSnoopingstatisticEntry 6 }

gs2352pMLDSnoopingstatisticV1ReportsReceived OBJECT-TYPE
   SYNTAX      Counter32
   MAX-ACCESS  read-only
   STATUS      current
   DESCRIPTION
       "The number of Received V1 Reports. "
   ::= { gs2352pMLDSnoopingstatisticEntry 7 }

gs2352pMLDSnoopingstatisticV2ReportsReceived OBJECT-TYPE
   SYNTAX      Counter32
   MAX-ACCESS  read-only
   STATUS      current
   DESCRIPTION
       "The number of Received V2 Reports. "
   ::= { gs2352pMLDSnoopingstatisticEntry 8 }

gs2352pMLDSnoopingstatisticV1LeavesReceived OBJECT-TYPE
   SYNTAX      Counter32
   MAX-ACCESS  read-only
   STATUS      current
   DESCRIPTION
       "The number of Received V1 Leaves. "
   ::= { gs2352pMLDSnoopingstatisticEntry 9 }

gs2352pMLDSnoopingRouterPortTable OBJECT-TYPE
   SYNTAX      SEQUENCE OF Gs2352pMLDSnoopingRouterPortEntry
   MAX-ACCESS  not-accessible
   STATUS      current
   DESCRIPTION
       " Configure Vlan Port Isolation Configuration. "
   ::= { gs2352pMLDSnoopingStatus 3 }

gs2352pMLDSnoopingRouterPortEntry OBJECT-TYPE
   SYNTAX      Gs2352pMLDSnoopingRouterPortEntry
   MAX-ACCESS  not-accessible
   STATUS      current
   DESCRIPTION
       ""
   INDEX    { ifIndex  }
   ::= { gs2352pMLDSnoopingRouterPortTable 1 }

Gs2352pMLDSnoopingRouterPortEntry ::= SEQUENCE {
   gs2352pMLDSnoopingRouterPortStatus            DisplayString
}

gs2352pMLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2352pMLDSnoopingRouterPortEntry 1 }

gs2352pMLDSnoopingGroupsTable OBJECT-TYPE
   SYNTAX      SEQUENCE OF Gs2352pMLDSnoopingGroupsEntry
   MAX-ACCESS  not-accessible
   STATUS      current
   DESCRIPTION
       "MLD Snooping Groups Information . "
   ::= { gs2352pMLDSnooping 5 }

gs2352pMLDSnoopingGroupsEntry OBJECT-TYPE
   SYNTAX      Gs2352pMLDSnoopingGroupsEntry
   MAX-ACCESS  not-accessible
   STATUS      current
   DESCRIPTION
       ""
   INDEX    { gs2352pMLDSnoopingGroupsIndex  }
   ::= { gs2352pMLDSnoopingGroupsTable 1 }

Gs2352pMLDSnoopingGroupsEntry ::= SEQUENCE {
   gs2352pMLDSnoopingGroupsIndex          Integer32,
   gs2352pMLDSnoopingGroupsVLANID         Integer32,
   gs2352pMLDSnoopingGroups               InetAddress,
   gs2352pMLDSnoopingGroupsMemberships    DisplayString
}

gs2352pMLDSnoopingGroupsIndex OBJECT-TYPE
   SYNTAX      Integer32(1..65535)
   MAX-ACCESS  not-accessible
   STATUS      current
   DESCRIPTION
       "MLD Snooping Groups Index"
   ::= { gs2352pMLDSnoopingGroupsEntry 1 }

gs2352pMLDSnoopingGroupsVLANID OBJECT-TYPE
   SYNTAX      Integer32(1..4095)
   MAX-ACCESS  read-only
   STATUS      current
   DESCRIPTION
       "VLAN ID of the group. "
   ::= { gs2352pMLDSnoopingGroupsEntry 2 }

gs2352pMLDSnoopingGroups OBJECT-TYPE
   SYNTAX      DisplayString
   MAX-ACCESS  read-only
   STATUS      current
   DESCRIPTION
       "Group address of the group displayed."
   ::= { gs2352pMLDSnoopingGroupsEntry 3 }

gs2352pMLDSnoopingGroupsMemberships OBJECT-TYPE
   SYNTAX      DisplayString
   MAX-ACCESS  read-only
   STATUS      current
   DESCRIPTION
       "Ports under this group."
   ::= { gs2352pMLDSnoopingGroupsEntry 4 }
   
gs2352pMLDSnoopingSSMTable OBJECT-TYPE
   SYNTAX      SEQUENCE OF Gs2352pMLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2352pMLDSnooping 6 }

gs2352pMLDSnoopingSSMEntry OBJECT-TYPE
   SYNTAX      Gs2352pMLDSnoopingSSMEntry
   MAX-ACCESS  not-accessible
   STATUS      current
   DESCRIPTION
       ""
   INDEX    { gs2352pMLDSnoopingSSMIndex  }
   ::= { gs2352pMLDSnoopingSSMTable 1 }

Gs2352pMLDSnoopingSSMEntry ::= SEQUENCE {
   gs2352pMLDSnoopingSSMIndex          Integer32,
   gs2352pMLDSnoopingSSMVLANID         Integer32,
   gs2352pMLDSnoopingSSMGroup          DisplayString,
   gs2352pMLDSnoopingSSMPort           Integer32,
   gs2352pMLDSnoopingSSMMode           DisplayString,
   gs2352pMLDSnoopingSSMSourceAddress  DisplayString,
   gs2352pMLDSnoopingSSMType           DisplayString
}

gs2352pMLDSnoopingSSMIndex OBJECT-TYPE
   SYNTAX      Integer32(1..65535)
   MAX-ACCESS  not-accessible
   STATUS      current
   DESCRIPTION
       "MLD Snooping SSM Index"
   ::= { gs2352pMLDSnoopingSSMEntry 1 }

gs2352pMLDSnoopingSSMVLANID OBJECT-TYPE
   SYNTAX      Integer32(1..4095)
   MAX-ACCESS  read-only
   STATUS      current
   DESCRIPTION
       "VLAN ID of the group. "
   ::= { gs2352pMLDSnoopingSSMEntry 2 }

gs2352pMLDSnoopingSSMGroup OBJECT-TYPE
   SYNTAX      DisplayString
   MAX-ACCESS  read-only
   STATUS      current
   DESCRIPTION
       "Group address of the group displayed."
   ::= { gs2352pMLDSnoopingSSMEntry 3 }

gs2352pMLDSnoopingSSMPort OBJECT-TYPE
   SYNTAX      Integer32(1..65535)
   MAX-ACCESS  read-only
   STATUS      current
   DESCRIPTION
       "Ports under this group."
   ::= { gs2352pMLDSnoopingSSMEntry 4 }
   
gs2352pMLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2352pMLDSnoopingSSMEntry 5 }
   
gs2352pMLDSnoopingSSMSourceAddress OBJECT-TYPE
   SYNTAX      DisplayString
   MAX-ACCESS  read-only
   STATUS      current
   DESCRIPTION
       "IP Address of the source. Currently, system limits the total number of
       IP source addresses for filtering to be 128."
   ::= { gs2352pMLDSnoopingSSMEntry 6 }

gs2352pMLDSnoopingSSMType OBJECT-TYPE
   SYNTAX      DisplayString
   MAX-ACCESS  read-only
   STATUS      current
   DESCRIPTION
       "Indicates the Type. It can be either Allow or Deny."
   ::= { gs2352pMLDSnoopingSSMEntry 7 }      
   

gs2352pMVR                                                                   OBJECT IDENTIFIER ::= { gs2352pConfiguration 18 }

gs2352pMVRConfiguration                                                      OBJECT IDENTIFIER ::= { gs2352pMVR 1 }

gs2352pMVRMode  OBJECT-TYPE
   SYNTAX      INTEGER { disable(0), enable(1) }
   MAX-ACCESS  read-write
   STATUS      current
   DESCRIPTION
       "Enable/Disable the Global MVR. "
   ::= { gs2352pMVRConfiguration 1 }

gs2352pMVRVLANId  OBJECT-TYPE
   SYNTAX      Integer32(1..4094)
   MAX-ACCESS  read-write
   STATUS      current
   DESCRIPTION
       "Specify the Multicast VLAN ID. "
   ::= { gs2352pMVRConfiguration 2 }

gs2352pMVRPortConfigurationTable OBJECT-TYPE
   SYNTAX      SEQUENCE OF Gs2352pMVRPortConfigurationEntry
   MAX-ACCESS  not-accessible
   STATUS      current
   DESCRIPTION
       " Configure MVR Port Configuration. "
   ::= { gs2352pMVRConfiguration 3 }

gs2352pMVRPortConfigurationEntry OBJECT-TYPE
   SYNTAX      Gs2352pMVRPortConfigurationEntry
   MAX-ACCESS  not-accessible
   STATUS      current
   DESCRIPTION
       ""
   INDEX    { ifIndex  }
   ::= { gs2352pMVRPortConfigurationTable 1 }

Gs2352pMVRPortConfigurationEntry ::= SEQUENCE {
   gs2352pMVRPortConfigurationMode	INTEGER,
   gs2352pMVRPortConfigurationType  	INTEGER,
   gs2352pMVRPortConfigurationImmediateLeave    INTEGER
}

gs2352pMVRPortConfigurationMode OBJECT-TYPE
   SYNTAX      INTEGER { disable(0), enable(1) }
   MAX-ACCESS  read-write
   STATUS      current
   DESCRIPTION
       "Enable MVR on the port. "
   ::= { gs2352pMVRPortConfigurationEntry 1 }

gs2352pMVRPortConfigurationType OBJECT-TYPE
   SYNTAX      INTEGER { receiver(0), source(1) }
   MAX-ACCESS  read-write
   STATUS      current
   DESCRIPTION
       "Specify the MVR port type on the port. "
   ::= { gs2352pMVRPortConfigurationEntry 2 }
   
gs2352pMVRPortConfigurationImmediateLeave OBJECT-TYPE
   SYNTAX      INTEGER { disable(0), enable(1) }
   MAX-ACCESS  read-write
   STATUS      current
   DESCRIPTION
       "Enable the fast leave on the port. "
   ::= { gs2352pMVRPortConfigurationEntry 3 }
      

gs2352pMVRPortGroupFiltering                                                      OBJECT IDENTIFIER ::= { gs2352pMVR 2 }

gs2352pMVRPortGroupFilteringCreate OBJECT-TYPE
   SYNTAX       Integer32
   MAX-ACCESS   read-write
   STATUS       current
   DESCRIPTION
       "default: 0
       0 : None  (read only) 1 : Create MLD Snooping Port Group Filtering "
   ::= { gs2352pMVRPortGroupFiltering 1 }

gs2352pMVRPortGroupFilteringTable OBJECT-TYPE
   SYNTAX      SEQUENCE OF Gs2352pMVRPortGroupFilteringEntry
   MAX-ACCESS  not-accessible
   STATUS      current
   DESCRIPTION
       " Configure MVR port group filtering. "
   ::= { gs2352pMVRPortGroupFiltering 2 }

gs2352pMVRPortGroupFilteringEntry OBJECT-TYPE
   SYNTAX      Gs2352pMVRPortGroupFilteringEntry
   MAX-ACCESS  not-accessible
   STATUS      current
   DESCRIPTION
       ""
   INDEX    { gs2352pMVRPortGroupFilteringIndex  }
   ::= { gs2352pMVRPortGroupFilteringTable 1 }

Gs2352pMVRPortGroupFilteringEntry ::= SEQUENCE {
   gs2352pMVRPortGroupFilteringIndex         Integer32,
   gs2352pMVRPortGroupFilteringPort          Integer32,
   gs2352pMVRPortGroupFilteringStartGroups   DisplayString,
   gs2352pMVRPortGroupFilteringEndGroups     DisplayString,
   gs2352pMVRPortGroupFilteringRowStatus     INTEGER
}

gs2352pMVRPortGroupFilteringIndex OBJECT-TYPE
   SYNTAX      Integer32(1..65535)
   MAX-ACCESS  not-accessible
   STATUS      current
   DESCRIPTION
       "MVR Port Group Filtering Configuration Index. "
   ::= { gs2352pMVRPortGroupFilteringEntry 1 }

gs2352pMVRPortGroupFilteringPort OBJECT-TYPE
   SYNTAX      Integer32(1..65535)
   MAX-ACCESS  read-write
   STATUS      current
   DESCRIPTION
       "The logical port for the settings. "
   ::= { gs2352pMVRPortGroupFilteringEntry 2 }

gs2352pMVRPortGroupFilteringStartGroups OBJECT-TYPE
   SYNTAX      DisplayString
   MAX-ACCESS  read-write
   STATUS      current
   DESCRIPTION
       "The IP Multicast Group that will be allowed. "
   ::= { gs2352pMVRPortGroupFilteringEntry 3 }

gs2352pMVRPortGroupFilteringEndGroups OBJECT-TYPE
   SYNTAX      DisplayString
   MAX-ACCESS  read-write
   STATUS      current
   DESCRIPTION
       "The IP Multicast Group that will be allowed. "
   ::= { gs2352pMVRPortGroupFilteringEntry 4 }   

gs2352pMVRPortGroupFilteringRowStatus OBJECT-TYPE
   SYNTAX      INTEGER { active(1), notInservice(2), destroy(4)}
   MAX-ACCESS  read-write
   STATUS      current
   DESCRIPTION
       "1: active
        2: notInservice
        4: destroy"
   ::= { gs2352pMVRPortGroupFilteringEntry 5 }

gs2352pMVRGroupsTable OBJECT-TYPE
   SYNTAX      SEQUENCE OF Gs2352pMVRGroupsEntry
   MAX-ACCESS  not-accessible
   STATUS      current
   DESCRIPTION
       "MVR Groups Information . "
   ::= { gs2352pMVR 3 }

gs2352pMVRGroupsEntry OBJECT-TYPE
   SYNTAX      Gs2352pMVRGroupsEntry
   MAX-ACCESS  not-accessible
   STATUS      current
   DESCRIPTION
       ""
   INDEX    { gs2352pMVRGroupsIndex  }
   ::= { gs2352pMVRGroupsTable 1 }

Gs2352pMVRGroupsEntry ::= SEQUENCE {
   gs2352pMVRGroupsIndex          Integer32,
   gs2352pMVRGroupsVLANID         Integer32,
   gs2352pMVRGroups               InetAddress,
   gs2352pMVRGroupsMemberships    DisplayString
}

gs2352pMVRGroupsIndex OBJECT-TYPE
   SYNTAX      Integer32(1..65535)
   MAX-ACCESS  not-accessible
   STATUS      current
   DESCRIPTION
       "MVR Groups Index"
   ::= { gs2352pMVRGroupsEntry 1 }

gs2352pMVRGroupsVLANID OBJECT-TYPE
   SYNTAX      Integer32(1..4095)
   MAX-ACCESS  read-only
   STATUS      current
   DESCRIPTION
       "VLAN ID of the group. "
   ::= { gs2352pMVRGroupsEntry 2 }

gs2352pMVRGroups OBJECT-TYPE
   SYNTAX      DisplayString
   MAX-ACCESS  read-only
   STATUS      current
   DESCRIPTION
       "Group address of the group displayed."
   ::= { gs2352pMVRGroupsEntry 3 }

gs2352pMVRGroupsMemberships OBJECT-TYPE
   SYNTAX      DisplayString
   MAX-ACCESS  read-only
   STATUS      current
   DESCRIPTION
       "Ports under this group."
   ::= { gs2352pMVRGroupsEntry 4 }
            

gs2352pMVRStatus                                                      OBJECT IDENTIFIER ::= { gs2352pMVR 4 }

gs2352pMVRstatisticClear OBJECT-TYPE
   SYNTAX      INTEGER { none(0), clear(1)}
   MAX-ACCESS  read-write
   STATUS      current
   DESCRIPTION
       "Clears all Statistics counters."
   ::= { gs2352pMVRStatus 1 }

gs2352pMVRstatisticVLANID OBJECT-TYPE
   SYNTAX      Integer32(1..4095)
   MAX-ACCESS  read-only
   STATUS      current
   DESCRIPTION
       "The VLAN ID of the entry. "
   ::= { gs2352pMVRStatus 2 }

gs2352pMVRstatisticV1ReportsReceived OBJECT-TYPE
   SYNTAX      Counter32
   MAX-ACCESS  read-only
   STATUS      current
   DESCRIPTION
       "The number of Received V1 Reports. "
   ::= { gs2352pMVRStatus 3 }

gs2352pMVRstatisticV2ReportsReceived OBJECT-TYPE
   SYNTAX      Counter32
   MAX-ACCESS  read-only
   STATUS      current
   DESCRIPTION
       "The number of Received V2 Reports. "
   ::= { gs2352pMVRStatus 4 }
   
gs2352pMVRstatisticV3ReportsReceived OBJECT-TYPE
   SYNTAX      Counter32
   MAX-ACCESS  read-only
   STATUS      current
   DESCRIPTION
       "The number of Received V3 Reports. "
   ::= { gs2352pMVRStatus 5 }

gs2352pMVRstatisticV2LeavesReceived OBJECT-TYPE
   SYNTAX      Counter32
   MAX-ACCESS  read-only
   STATUS      current
   DESCRIPTION
       "The number of Received V2 Leaves. "
   ::= { gs2352pMVRStatus 6 }

gs2352pLACP                                                     OBJECT IDENTIFIER ::= { gs2352pConfiguration 19 }

gs2352pLACPConf                                                 OBJECT IDENTIFIER ::= { gs2352pLACP 1 }

gs2352pLACPPortConfigurationTable OBJECT-TYPE
   SYNTAX      SEQUENCE OF Gs2352pLACPPortConfigurationEntry
   MAX-ACCESS  not-accessible
   STATUS      current
   DESCRIPTION
       " "
   ::= { gs2352pLACPConf 1 }

gs2352pLACPPortConfigurationEntry OBJECT-TYPE
   SYNTAX      Gs2352pLACPPortConfigurationEntry
   MAX-ACCESS  not-accessible
   STATUS      current
   DESCRIPTION
       ""
   INDEX    { gs2352pLACPPortConfigurationPort  }
   ::= { gs2352pLACPPortConfigurationTable 1 }
   
Gs2352pLACPPortConfigurationEntry ::= SEQUENCE {
    gs2352pLACPPortConfigurationPort         Integer32,
    gs2352pLACPPortConfigurationMode         INTEGER,
    gs2352pLACPPortConfigurationKey          Integer32,
    gs2352pLACPPortConfigurationRole         INTEGER
}

gs2352pLACPPortConfigurationPort OBJECT-TYPE
   SYNTAX      Integer32(1..4095)
   MAX-ACCESS  not-accessible
   STATUS      current
   DESCRIPTION
       " "
   ::= { gs2352pLACPPortConfigurationEntry 1 }

gs2352pLACPPortConfigurationMode OBJECT-TYPE
   SYNTAX      INTEGER { disable(0), enable(1) }
   MAX-ACCESS  read-write
   STATUS      current
   DESCRIPTION
       "Enable/Disable LACP Mode."
   ::= { gs2352pLACPPortConfigurationEntry 2 }
   
gs2352pLACPPortConfigurationKey OBJECT-TYPE
   SYNTAX      Integer32(0..65535)
   MAX-ACCESS  read-write
   STATUS      current
   DESCRIPTION
       "LACP key : 1-65535. 0 : Auto"
   ::= { gs2352pLACPPortConfigurationEntry 3 }
   
gs2352pLACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2352pLACPPortConfigurationEntry 4 }

gs2352pLACPSystemStatusTable OBJECT-TYPE
   SYNTAX      SEQUENCE OF Gs2352pLACPSystemStatusEntry
   MAX-ACCESS  not-accessible
   STATUS      current
   DESCRIPTION
       " "
   ::= { gs2352pLACP 2 }

gs2352pLACPSystemStatusEntry OBJECT-TYPE
   SYNTAX      Gs2352pLACPSystemStatusEntry
   MAX-ACCESS  not-accessible
   STATUS      current
   DESCRIPTION
       ""
   INDEX    { gs2352pLACPSystemStatusIndex  }
   ::= { gs2352pLACPSystemStatusTable 1 }

Gs2352pLACPSystemStatusEntry ::= SEQUENCE {
   gs2352pLACPSystemStatusIndex             Integer32,
   gs2352pLACPSystemStatusAggrID            DisplayString,
   gs2352pLACPSystemStatusPartnerSystemID   MacAddress,
   gs2352pLACPSystemStatusPartnerKey        DisplayString,
   gs2352pLACPSystemStatusLastchanged       DisplayString,
   gs2352pLACPSystemStatusLocalPorts        DisplayString
}

gs2352pLACPSystemStatusIndex OBJECT-TYPE
   SYNTAX      Integer32(1..12)
   MAX-ACCESS  not-accessible
   STATUS      current
   DESCRIPTION
       " "
   ::= { gs2352pLACPSystemStatusEntry 1 }

gs2352pLACPSystemStatusAggrID OBJECT-TYPE
   SYNTAX      DisplayString
   MAX-ACCESS  read-only
   STATUS      current
   DESCRIPTION
       "The Aggregation ID associated with this aggregation instance."
   ::= { gs2352pLACPSystemStatusEntry 2 }
   
gs2352pLACPSystemStatusPartnerSystemID OBJECT-TYPE
   SYNTAX      MacAddress
   MAX-ACCESS  read-only
   STATUS      current
   DESCRIPTION
       "The system ID (MAC address) of the aggregation partner."
   ::= { gs2352pLACPSystemStatusEntry 3 }

gs2352pLACPSystemStatusPartnerKey OBJECT-TYPE
   SYNTAX      DisplayString
   MAX-ACCESS  read-only
   STATUS      current
   DESCRIPTION
       " The Key that the partner has assigned to this aggregation ID. "
   ::= { gs2352pLACPSystemStatusEntry 4 }

gs2352pLACPSystemStatusLastchanged OBJECT-TYPE
   SYNTAX      DisplayString
   MAX-ACCESS  read-only
   STATUS      current
   DESCRIPTION
       " The time since this aggregation changed. "
   ::= { gs2352pLACPSystemStatusEntry 5 }
   
gs2352pLACPSystemStatusLocalPorts OBJECT-TYPE
   SYNTAX      DisplayString
   MAX-ACCESS  read-only
   STATUS      current
   DESCRIPTION
       " Shows which ports are a part of this aggregation for this switch. "
   ::= { gs2352pLACPSystemStatusEntry 6 }

gs2352pLACPStatusTable OBJECT-TYPE
   SYNTAX      SEQUENCE OF Gs2352pLACPStatusEntry
   MAX-ACCESS  not-accessible
   STATUS      current
   DESCRIPTION
       " "
   ::= { gs2352pLACP 3 }

gs2352pLACPStatusEntry OBJECT-TYPE
   SYNTAX      Gs2352pLACPStatusEntry
   MAX-ACCESS  not-accessible
   STATUS      current
   DESCRIPTION
       ""
   INDEX    { gs2352pLACPStatusPort  }
   ::= { gs2352pLACPStatusTable 1 }

Gs2352pLACPStatusEntry ::= SEQUENCE {
   gs2352pLACPStatusPort                Integer32,
   gs2352pLACPStatusLACP                DisplayString,
   gs2352pLACPStatusKey                 DisplayString,
   gs2352pLACPStatusAggrID              DisplayString,
   gs2352pLACPStatusPartnerSystemID     DisplayString,
   gs2352pLACPStatusPartnerPort         DisplayString
}

gs2352pLACPStatusPort OBJECT-TYPE
   SYNTAX      Integer32(1..4095)
   MAX-ACCESS  not-accessible
   STATUS      current
   DESCRIPTION
       " "
   ::= { gs2352pLACPStatusEntry 1 }

gs2352pLACPStatusLACP OBJECT-TYPE
   SYNTAX      DisplayString
   MAX-ACCESS  read-only
   STATUS      current
   DESCRIPTION
       "Enabled means that LACP is enabled and the port link is up. 
        Disabled means that LACP is not enabled or that the port link is down. 
        Backup means that the port could not join the aggregation group but will join if other port leaves. 
        Meanwhile it's LACP status is disabled."
   ::= { gs2352pLACPStatusEntry 2 }
   
gs2352pLACPStatusKey OBJECT-TYPE
   SYNTAX      DisplayString
   MAX-ACCESS  read-only
   STATUS      current
   DESCRIPTION
       "The key assigned to this port. Only ports with the same key can aggregate together."
   ::= { gs2352pLACPStatusEntry 3 }

gs2352pLACPStatusAggrID	 OBJECT-TYPE
   SYNTAX      DisplayString
   MAX-ACCESS  read-only
   STATUS      current
   DESCRIPTION
       " The Aggregation ID assigned to this aggregation group. "
   ::= { gs2352pLACPStatusEntry 4 }

gs2352pLACPStatusPartnerSystemID OBJECT-TYPE
   SYNTAX      DisplayString
   MAX-ACCESS  read-only
   STATUS      current
   DESCRIPTION
       " The partner's System ID. "
   ::= { gs2352pLACPStatusEntry 5 }
   
gs2352pLACPStatusPartnerPort OBJECT-TYPE
   SYNTAX      DisplayString
   MAX-ACCESS  read-only
   STATUS      current
   DESCRIPTION
       " The partner's port number connected to this port. "
   ::= { gs2352pLACPStatusEntry 6 }


gs2352pLACPStatisticsTable OBJECT-TYPE
   SYNTAX      SEQUENCE OF Gs2352pLACPStatisticsEntry
   MAX-ACCESS  not-accessible
   STATUS      current
   DESCRIPTION
       " "
   ::= { gs2352pLACP 4 }

gs2352pLACPStatisticsEntry OBJECT-TYPE
   SYNTAX      Gs2352pLACPStatisticsEntry
   MAX-ACCESS  not-accessible
   STATUS      current
   DESCRIPTION
       ""
   INDEX    { gs2352pLACPStatisticsPort  }
   ::= { gs2352pLACPStatisticsTable 1 }

Gs2352pLACPStatisticsEntry ::= SEQUENCE {
   gs2352pLACPStatisticsPort        Integer32,
   gs2352pLACPReceived              Counter32,
   gs2352pLACPTransmitted           Counter32,
   gs2352pLACPDiscardedUnknown      Counter32,
   gs2352pLACPDiscardedIllegal      Counter32
}

gs2352pLACPStatisticsPort OBJECT-TYPE
   SYNTAX      Integer32(1..4095)
   MAX-ACCESS  not-accessible
   STATUS      current
   DESCRIPTION
       " "
   ::= { gs2352pLACPStatisticsEntry 1 }
   
gs2352pLACPReceived OBJECT-TYPE
   SYNTAX      Counter32
   MAX-ACCESS  read-only
   STATUS      current
   DESCRIPTION
       "Shows how many LACP frames have been received at each port. "
   ::= { gs2352pLACPStatisticsEntry 2 }

gs2352pLACPTransmitted OBJECT-TYPE
   SYNTAX      Counter32
   MAX-ACCESS  read-only
   STATUS      current
   DESCRIPTION
       " Shows how many LACP frames have been sent from each port. "
   ::= { gs2352pLACPStatisticsEntry 3 }

gs2352pLACPDiscardedUnknown OBJECT-TYPE
   SYNTAX      Counter32
   MAX-ACCESS  read-only
   STATUS      current
   DESCRIPTION
       " Shows how many unknown LACP frames have been discarded at each port. "
   ::= { gs2352pLACPStatisticsEntry 4 }
   
gs2352pLACPDiscardedIllegal OBJECT-TYPE
   SYNTAX      Counter32
   MAX-ACCESS  read-only
   STATUS      current
   DESCRIPTION
       " Shows how many illegal LACP frames have been discarded at each port. "
   ::= { gs2352pLACPStatisticsEntry 5 }
   
gs2352pLACPStatisticsClear OBJECT-TYPE
   SYNTAX      INTEGER { none(0), clear(1) }
   MAX-ACCESS  read-write
   STATUS      current
   DESCRIPTION
       "default: 0
       0: none
       1: clear"
   ::= { gs2352pLACP 5 }
   
gs2352pSTP                                                     OBJECT IDENTIFIER ::= { gs2352pConfiguration 20 }

gs2352pSTPBridgeBasicConf                                                 OBJECT IDENTIFIER ::= { gs2352pSTP 1 }

gs2352pSTPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2352pSTPBridgeBasicConf 1 }

gs2352pSTPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2352pSTPBridgeBasicConf 2 }
   
gs2352pSTPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2352pSTPBridgeBasicConf 3 }
   
gs2352pSTPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2352pSTPBridgeBasicConf 4 }
   
gs2352pSTPBridgeMaximumHopCount OBJECT-TYPE
   SYNTAX      Integer32(6..40)
   MAX-ACCESS  read-write
   STATUS      current
   DESCRIPTION
       " Maximum Hop Count default: 20, range: 6 - 40."
   ::= { gs2352pSTPBridgeBasicConf 5 }
   
gs2352pSTPBridgeTransmitHoldCount OBJECT-TYPE
   SYNTAX      Integer32(1..10)
   MAX-ACCESS  read-write
   STATUS      current
   DESCRIPTION
       " Transmit Hold Count default: 6, range: 1 - 10."
   ::= { gs2352pSTPBridgeBasicConf 6 }
   
gs2352pSTPBridgeAdvancedConf                                                 OBJECT IDENTIFIER ::= { gs2352pSTP 2 }

gs2352pSTPBridgeEdgePortBPDUFiltering OBJECT-TYPE
   SYNTAX      INTEGER { disable(0), enable(1) }
   MAX-ACCESS  read-write
   STATUS      current
   DESCRIPTION
       " default: 0,
        0: disable
        1: enable"
   ::= { gs2352pSTPBridgeAdvancedConf 1 }
   
gs2352pSTPBridgeEdgePortBPDUGuard OBJECT-TYPE
   SYNTAX      INTEGER { disable(0), enable(1) }
   MAX-ACCESS  read-write
   STATUS      current
   DESCRIPTION
       " default: 0,
        0: disable
        1: enable"
   ::= { gs2352pSTPBridgeAdvancedConf 2 }
   
gs2352pSTPBridgePortErrorRecoveryTimeout OBJECT-TYPE
   SYNTAX      Integer32(0..86400)
   MAX-ACCESS  read-write
   STATUS      current
   DESCRIPTION
       " Port Error Recovery Timeout disable: 0, range: 30 - 86400."
   ::= { gs2352pSTPBridgeAdvancedConf 3 }
   
gs2352pSTPMSTIConf                                                 OBJECT IDENTIFIER ::= { gs2352pSTP 3 }
   
gs2352pSTPMSTIConfigurationName OBJECT-TYPE
   SYNTAX      DisplayString (SIZE (1..32))
   MAX-ACCESS  read-write
   STATUS      current
   DESCRIPTION
       "A text string up to 32 characters long."
   ::= { gs2352pSTPMSTIConf 1 }
   
gs2352pSTPMSTIConfigurationRevision   OBJECT-TYPE
   SYNTAX      Integer32(0..65535)
   MAX-ACCESS  read-write
   STATUS      current
   DESCRIPTION
       " Configuration Revision default: 0, range: 0 - 65535."
   ::= { gs2352pSTPMSTIConf 2 }
   
gs2352pSTPMSTIMappingConf                                                 OBJECT IDENTIFIER ::= { gs2352pSTP 4 }
   
gs2352pSTPMSTI1VLANsMapped OBJECT-TYPE
   SYNTAX      DisplayString (SIZE (1..4096))
   MAX-ACCESS  read-write
   STATUS      current
   DESCRIPTION
       "The list of VLANs mapped to the MSTI1. 
       The VLANs must be separated with comma or space. 
       An unused MSTI should just be left empty. "
   ::= { gs2352pSTPMSTIMappingConf 1 }

gs2352pSTPMSTI2VLANsMapped OBJECT-TYPE
   SYNTAX      DisplayString (SIZE (1..4096))
   MAX-ACCESS  read-write
   STATUS      current
   DESCRIPTION
       "The list of VLANs mapped to the MSTI2. 
       The VLANs must be separated with comma or space. 
       An unused MSTI should just be left empty. "
   ::= { gs2352pSTPMSTIMappingConf 2 }
   
gs2352pSTPMSTI3VLANsMapped OBJECT-TYPE
   SYNTAX      DisplayString (SIZE (1..4096))
   MAX-ACCESS  read-write
   STATUS      current
   DESCRIPTION
       "The list of VLANs mapped to the MSTI3. 
       The VLANs must be separated with comma or space. 
       An unused MSTI should just be left empty. "
   ::= { gs2352pSTPMSTIMappingConf 3 }
   
gs2352pSTPMSTI4VLANsMapped OBJECT-TYPE
   SYNTAX      DisplayString (SIZE (1..4096))
   MAX-ACCESS  read-write
   STATUS      current
   DESCRIPTION
       "The list of VLANs mapped to the MSTI4. 
       The VLANs must be separated with comma or space. 
       An unused MSTI should just be left empty. "
   ::= { gs2352pSTPMSTIMappingConf 4 }
   
gs2352pSTPMSTI5VLANsMapped OBJECT-TYPE
   SYNTAX      DisplayString (SIZE (1..4096))
   MAX-ACCESS  read-write
   STATUS      current
   DESCRIPTION
       "The list of VLANs mapped to the MSTI5. 
       The VLANs must be separated with comma or space. 
       An unused MSTI should just be left empty. "
   ::= { gs2352pSTPMSTIMappingConf 5 }

gs2352pSTPMSTI6VLANsMapped OBJECT-TYPE
   SYNTAX      DisplayString (SIZE (1..4096))
   MAX-ACCESS  read-write
   STATUS      current
   DESCRIPTION
       "The list of VLANs mapped to the MSTI6. 
       The VLANs must be separated with comma or space. 
       An unused MSTI should just be left empty. "
   ::= { gs2352pSTPMSTIMappingConf 6 }
   
gs2352pSTPMSTI7VLANsMapped OBJECT-TYPE
   SYNTAX      DisplayString (SIZE (1..4096))
   MAX-ACCESS  read-write
   STATUS      current
   DESCRIPTION
       "The list of VLANs mapped to the MSTI7. 
       The VLANs must be separated with comma or space. 
       An unused MSTI should just be left empty. "
   ::= { gs2352pSTPMSTIMappingConf 7 }
   
gs2352pSTPMSTIPriority                                                 OBJECT IDENTIFIER ::= { gs2352pSTP 5 }
   
gs2352pSTPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352pSTPMSTIPriority 1 }
   
gs2352pSTPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352pSTPMSTIPriority 2 }
   
gs2352pSTPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352pSTPMSTIPriority 3 }
   
gs2352pSTPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352pSTPMSTIPriority 4 }
   
gs2352pSTPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352pSTPMSTIPriority 5 }
   
gs2352pSTPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352pSTPMSTIPriority 6 }

gs2352pSTPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352pSTPMSTIPriority 7 }  

gs2352pSTPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2352pSTPMSTIPriority 8 }
   
gs2352pSTPCISTPort                                                          OBJECT IDENTIFIER ::= { gs2352pSTP 6 }

gs2352pSTPCISTAggregatedPort                                                OBJECT IDENTIFIER ::= { gs2352pSTPCISTPort 1 }
   
gs2352pSTPCISTAggregatedPortSTPEnabled OBJECT-TYPE
   SYNTAX      INTEGER { disable(0), enable(1) }
   MAX-ACCESS  read-write
   STATUS      current
   DESCRIPTION
       " default: 0,
        0: disable
        1: enable"
   ::= { gs2352pSTPCISTAggregatedPort 1 }
   
gs2352pSTPCISTAggregatedPortPathCost OBJECT-TYPE
   SYNTAX      Integer32(0..200000000)
   MAX-ACCESS  read-write
   STATUS      current
   DESCRIPTION
       " Auto: 0,
        Specific Path Cost range: 1 - 200000000."
   ::= { gs2352pSTPCISTAggregatedPort 2 }
   
gs2352pSTPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2352pSTPCISTAggregatedPort 3 }
   
gs2352pSTPCISTAggregatedPortAdminEdge OBJECT-TYPE
   SYNTAX      INTEGER { non-edge(0), edge(1) }
   MAX-ACCESS  read-write
   STATUS      current
   DESCRIPTION
       " default: 0,
        0: non-edge
        1: edge"
   ::= { gs2352pSTPCISTAggregatedPort 4 }

gs2352pSTPCISTAggregatedPortAutoEdge OBJECT-TYPE
   SYNTAX      INTEGER { disable(0), enable(1) }
   MAX-ACCESS  read-write
   STATUS      current
   DESCRIPTION
       " default: 1,
        0: disable
        1: enable"
   ::= { gs2352pSTPCISTAggregatedPort 5 }
   
gs2352pSTPCISTAggregatedPortRestrictedRole OBJECT-TYPE
   SYNTAX      INTEGER { disable(0), enable(1) }
   MAX-ACCESS  read-write
   STATUS      current
   DESCRIPTION
       " default: 0,
        0: disable
        1: enable"
   ::= { gs2352pSTPCISTAggregatedPort 6 }
   
gs2352pSTPCISTAggregatedPortRestrictedTCN OBJECT-TYPE
   SYNTAX      INTEGER { disable(0), enable(1) }
   MAX-ACCESS  read-write
   STATUS      current
   DESCRIPTION
       " default: 0,
        0: disable
        1: enable"
   ::= { gs2352pSTPCISTAggregatedPort 7 }
   
gs2352pSTPCISTAggregatedPortBPDUGuard OBJECT-TYPE
   SYNTAX      INTEGER { disable(0), enable(1) }
   MAX-ACCESS  read-write
   STATUS      current
   DESCRIPTION
       " default: 0,
        0: disable
        1: enable"
   ::= { gs2352pSTPCISTAggregatedPort 8 }
   
gs2352pSTPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2352pSTPCISTAggregatedPort 9 }
   
gs2352pSTPCISTNormalPortTable OBJECT-TYPE
   SYNTAX      SEQUENCE OF Gs2352pSTPCISTNormalPortEntry
   MAX-ACCESS  not-accessible
   STATUS      current
   DESCRIPTION
       " Show CIST Normal Port Configurations. "
   ::= { gs2352pSTPCISTPort 2 }

gs2352pSTPCISTNormalPortEntry OBJECT-TYPE
   SYNTAX      Gs2352pSTPCISTNormalPortEntry
   MAX-ACCESS  not-accessible
   STATUS      current
   DESCRIPTION
       ""
   INDEX    { gs2352pSTPCISTNormalPortConfPort  }
   ::= { gs2352pSTPCISTNormalPortTable 1 }

Gs2352pSTPCISTNormalPortEntry ::= SEQUENCE {
   gs2352pSTPCISTNormalPortConfPort         Integer32,
   gs2352pSTPCISTNormalPortSTPEnabled       INTEGER,
   gs2352pSTPCISTNormalPortPathCost         Integer32,
   gs2352pSTPCISTNormalPortPriority         Integer32,
   gs2352pSTPCISTNormalPortAdminEdge        INTEGER,
   gs2352pSTPCISTNormalPortAutoEdge         INTEGER,
   gs2352pSTPCISTNormalPortRestrictedRole   INTEGER,
   gs2352pSTPCISTNormalPortRestrictedTCN    INTEGER,
   gs2352pSTPCISTNormalPortBPDUGuard        INTEGER,
   gs2352pSTPCISTNormalPortPointtoPoint     INTEGER
}

gs2352pSTPCISTNormalPortConfPort OBJECT-TYPE
   SYNTAX      Integer32(1..4095)
   MAX-ACCESS  not-accessible
   STATUS      current
   DESCRIPTION
       " port, range : 1 - port number. "
   ::= { gs2352pSTPCISTNormalPortEntry 1 }
   
gs2352pSTPCISTNormalPortSTPEnabled OBJECT-TYPE
   SYNTAX      INTEGER { disable(0), enable(1) }
   MAX-ACCESS  read-write
   STATUS      current
   DESCRIPTION
       " default: 0,
        0: disable
        1: enable"
   ::= { gs2352pSTPCISTNormalPortEntry 2 }
   
gs2352pSTPCISTNormalPortPathCost OBJECT-TYPE
   SYNTAX      Integer32(0..200000000)
   MAX-ACCESS  read-write
   STATUS      current
   DESCRIPTION
       " Auto: 0,
        Specific Path Cost range: 1 - 200000000."
   ::= { gs2352pSTPCISTNormalPortEntry 3 }
   
gs2352pSTPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2352pSTPCISTNormalPortEntry 4 }
   
gs2352pSTPCISTNormalPortAdminEdge OBJECT-TYPE
   SYNTAX      INTEGER { non-edge(0), edge(1) }
   MAX-ACCESS  read-write
   STATUS      current
   DESCRIPTION
       " default: 0,
        0: non-edge
        1: edge"
   ::= { gs2352pSTPCISTNormalPortEntry 5 }
   
gs2352pSTPCISTNormalPortAutoEdge OBJECT-TYPE
   SYNTAX      INTEGER { disable(0), enable(1) }
   MAX-ACCESS  read-write
   STATUS      current
   DESCRIPTION
       " default: 1,
        0: disable
        1: enable"
   ::= { gs2352pSTPCISTNormalPortEntry 6 }
   
gs2352pSTPCISTNormalPortRestrictedRole OBJECT-TYPE
   SYNTAX      INTEGER { disable(0), enable(1) }
   MAX-ACCESS  read-write
   STATUS      current
   DESCRIPTION
       " default: 0,
        0: disable
        1: enable"
   ::= { gs2352pSTPCISTNormalPortEntry 7 }
   
gs2352pSTPCISTNormalPortRestrictedTCN OBJECT-TYPE
   SYNTAX      INTEGER { disable(0), enable(1) }
   MAX-ACCESS  read-write
   STATUS      current
   DESCRIPTION
       " default: 0,
        0: disable
        1: enable"
   ::= { gs2352pSTPCISTNormalPortEntry 8 }
   
gs2352pSTPCISTNormalPortBPDUGuard OBJECT-TYPE
   SYNTAX      INTEGER { disable(0), enable(1) }
   MAX-ACCESS  read-write
   STATUS      current
   DESCRIPTION
       " default: 0,
        0: disable
        1: enable"
   ::= { gs2352pSTPCISTNormalPortEntry 9 }
   
gs2352pSTPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2352pSTPCISTNormalPortEntry 10 }
   

gs2352pSTPMSTIPort                                                          OBJECT IDENTIFIER ::= { gs2352pSTP 7 }

gs2352pSTPMSTI1Port                                                         OBJECT IDENTIFIER ::= { gs2352pSTPMSTIPort 1 }

gs2352pSTPMSTI1AggregatedPort                                                OBJECT IDENTIFIER ::= { gs2352pSTPMSTI1Port 1 }
      
gs2352pSTPMSTI1AggregatedPortPathCost OBJECT-TYPE
   SYNTAX      Integer32(0..200000000)
   MAX-ACCESS  read-write
   STATUS      current
   DESCRIPTION
       " Auto: 0,
        Specific Path Cost range: 1 - 200000000."
   ::= { gs2352pSTPMSTI1AggregatedPort 1 }
   
gs2352pSTPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI1AggregatedPort 2 }
   
gs2352pSTPMSTI1NormalPortTable OBJECT-TYPE
   SYNTAX      SEQUENCE OF Gs2352pSTPMSTI1NormalPortEntry
   MAX-ACCESS  not-accessible
   STATUS      current
   DESCRIPTION
       " Show MSTI1 Normal Port Configurations. "
   ::= { gs2352pSTPMSTI1Port 2 }

gs2352pSTPMSTI1NormalPortEntry OBJECT-TYPE
   SYNTAX      Gs2352pSTPMSTI1NormalPortEntry
   MAX-ACCESS  not-accessible
   STATUS      current
   DESCRIPTION
       ""
   INDEX    { gs2352pSTPMSTI1NormalPortConfPort  }
   ::= { gs2352pSTPMSTI1NormalPortTable 1 }

Gs2352pSTPMSTI1NormalPortEntry ::= SEQUENCE {
   gs2352pSTPMSTI1NormalPortConfPort         Integer32,
   gs2352pSTPMSTI1NormalPortPathCost         Integer32,
   gs2352pSTPMSTI1NormalPortPriority         Integer32
}

gs2352pSTPMSTI1NormalPortConfPort OBJECT-TYPE
   SYNTAX      Integer32(1..4095)
   MAX-ACCESS  not-accessible
   STATUS      current
   DESCRIPTION
       " port, range : 1 - port number. "
   ::= { gs2352pSTPMSTI1NormalPortEntry 1 }
   
gs2352pSTPMSTI1NormalPortPathCost OBJECT-TYPE
   SYNTAX      Integer32(0..200000000)
   MAX-ACCESS  read-write
   STATUS      current
   DESCRIPTION
       " Auto: 0,
        Specific Path Cost range: 1 - 200000000."
   ::= { gs2352pSTPMSTI1NormalPortEntry 2 }
   
gs2352pSTPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI1NormalPortEntry 3 }

gs2352pSTPMSTI2Port                                                          OBJECT IDENTIFIER ::= { gs2352pSTPMSTIPort 2 }

gs2352pSTPMSTI2AggregatedPort                                                OBJECT IDENTIFIER ::= { gs2352pSTPMSTI2Port 1 }
      
gs2352pSTPMSTI2AggregatedPortPathCost OBJECT-TYPE
   SYNTAX      Integer32(0..200000000)
   MAX-ACCESS  read-write
   STATUS      current
   DESCRIPTION
       " Auto: 0,
        Specific Path Cost range: 1 - 200000000."
   ::= { gs2352pSTPMSTI2AggregatedPort 1 }
   
gs2352pSTPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI2AggregatedPort 2 }
   
gs2352pSTPMSTI2NormalPortTable OBJECT-TYPE
   SYNTAX      SEQUENCE OF Gs2352pSTPMSTI2NormalPortEntry
   MAX-ACCESS  not-accessible
   STATUS      current
   DESCRIPTION
       " Show MSTI2 Normal Port Configurations. "
   ::= { gs2352pSTPMSTI2Port 2 }

gs2352pSTPMSTI2NormalPortEntry OBJECT-TYPE
   SYNTAX      Gs2352pSTPMSTI2NormalPortEntry
   MAX-ACCESS  not-accessible
   STATUS      current
   DESCRIPTION
       ""
   INDEX    { gs2352pSTPMSTI2NormalPortConfPort  }
   ::= { gs2352pSTPMSTI2NormalPortTable 1 }

Gs2352pSTPMSTI2NormalPortEntry ::= SEQUENCE {
   gs2352pSTPMSTI2NormalPortConfPort         Integer32,
   gs2352pSTPMSTI2NormalPortPathCost         Integer32,
   gs2352pSTPMSTI2NormalPortPriority         Integer32
}

gs2352pSTPMSTI2NormalPortConfPort OBJECT-TYPE
   SYNTAX      Integer32(1..4095)
   MAX-ACCESS  not-accessible
   STATUS      current
   DESCRIPTION
       " port, range : 1 - port number. "
   ::= { gs2352pSTPMSTI2NormalPortEntry 1 }
   
gs2352pSTPMSTI2NormalPortPathCost OBJECT-TYPE
   SYNTAX      Integer32(0..200000000)
   MAX-ACCESS  read-write
   STATUS      current
   DESCRIPTION
       " Auto: 0,
        Specific Path Cost range: 1 - 200000000."
   ::= { gs2352pSTPMSTI2NormalPortEntry 2 }
   
gs2352pSTPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI2NormalPortEntry 3 }
   
gs2352pSTPMSTI3Port                                                          OBJECT IDENTIFIER ::= { gs2352pSTPMSTIPort 3 }

gs2352pSTPMSTI3AggregatedPort                                                OBJECT IDENTIFIER ::= { gs2352pSTPMSTI3Port 1 }
      
gs2352pSTPMSTI3AggregatedPortPathCost OBJECT-TYPE
   SYNTAX      Integer32(0..200000000)
   MAX-ACCESS  read-write
   STATUS      current
   DESCRIPTION
       " Auto: 0,
        Specific Path Cost range: 1 - 200000000."
   ::= { gs2352pSTPMSTI3AggregatedPort 1 }
   
gs2352pSTPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI3AggregatedPort 2 }
   
gs2352pSTPMSTI3NormalPortTable OBJECT-TYPE
   SYNTAX      SEQUENCE OF Gs2352pSTPMSTI3NormalPortEntry
   MAX-ACCESS  not-accessible
   STATUS      current
   DESCRIPTION
       " Show MSTI3 Normal Port Configurations. "
   ::= { gs2352pSTPMSTI3Port 2 }

gs2352pSTPMSTI3NormalPortEntry OBJECT-TYPE
   SYNTAX      Gs2352pSTPMSTI3NormalPortEntry
   MAX-ACCESS  not-accessible
   STATUS      current
   DESCRIPTION
       ""
   INDEX    { gs2352pSTPMSTI3NormalPortConfPort  }
   ::= { gs2352pSTPMSTI3NormalPortTable 1 }

Gs2352pSTPMSTI3NormalPortEntry ::= SEQUENCE {
   gs2352pSTPMSTI3NormalPortConfPort         Integer32,
   gs2352pSTPMSTI3NormalPortPathCost         Integer32,
   gs2352pSTPMSTI3NormalPortPriority         Integer32
}

gs2352pSTPMSTI3NormalPortConfPort OBJECT-TYPE
   SYNTAX      Integer32(1..4095)
   MAX-ACCESS  not-accessible
   STATUS      current
   DESCRIPTION
       " port, range : 1 - port number. "
   ::= { gs2352pSTPMSTI3NormalPortEntry 1 }
   
gs2352pSTPMSTI3NormalPortPathCost OBJECT-TYPE
   SYNTAX      Integer32(0..200000000)
   MAX-ACCESS  read-write
   STATUS      current
   DESCRIPTION
       " Auto: 0,
        Specific Path Cost range: 1 - 200000000."
   ::= { gs2352pSTPMSTI3NormalPortEntry 2 }
   
gs2352pSTPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI3NormalPortEntry 3 }
   
gs2352pSTPMSTI4Port                                                          OBJECT IDENTIFIER ::= { gs2352pSTPMSTIPort 4 }

gs2352pSTPMSTI4AggregatedPort                                                OBJECT IDENTIFIER ::= { gs2352pSTPMSTI4Port 1 }
      
gs2352pSTPMSTI4AggregatedPortPathCost OBJECT-TYPE
   SYNTAX      Integer32(0..200000000)
   MAX-ACCESS  read-write
   STATUS      current
   DESCRIPTION
       " Auto: 0,
        Specific Path Cost range: 1 - 200000000."
   ::= { gs2352pSTPMSTI4AggregatedPort 1 }
   
gs2352pSTPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI4AggregatedPort 2 }
   
gs2352pSTPMSTI4NormalPortTable OBJECT-TYPE
   SYNTAX      SEQUENCE OF Gs2352pSTPMSTI4NormalPortEntry
   MAX-ACCESS  not-accessible
   STATUS      current
   DESCRIPTION
       " Show MSTI4 Normal Port Configurations. "
   ::= { gs2352pSTPMSTI4Port 2 }

gs2352pSTPMSTI4NormalPortEntry OBJECT-TYPE
   SYNTAX      Gs2352pSTPMSTI4NormalPortEntry
   MAX-ACCESS  not-accessible
   STATUS      current
   DESCRIPTION
       ""
   INDEX    { gs2352pSTPMSTI4NormalPortConfPort  }
   ::= { gs2352pSTPMSTI4NormalPortTable 1 }

Gs2352pSTPMSTI4NormalPortEntry ::= SEQUENCE {
   gs2352pSTPMSTI4NormalPortConfPort         Integer32,
   gs2352pSTPMSTI4NormalPortPathCost         Integer32,
   gs2352pSTPMSTI4NormalPortPriority         Integer32
}

gs2352pSTPMSTI4NormalPortConfPort OBJECT-TYPE
   SYNTAX      Integer32(1..4095)
   MAX-ACCESS  not-accessible
   STATUS      current
   DESCRIPTION
       " port, range : 1 - port number. "
   ::= { gs2352pSTPMSTI4NormalPortEntry 1 }
   
gs2352pSTPMSTI4NormalPortPathCost OBJECT-TYPE
   SYNTAX      Integer32(0..200000000)
   MAX-ACCESS  read-write
   STATUS      current
   DESCRIPTION
       " Auto: 0,
        Specific Path Cost range: 1 - 200000000."
   ::= { gs2352pSTPMSTI4NormalPortEntry 2 }
   
gs2352pSTPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI4NormalPortEntry 3 }
   
gs2352pSTPMSTI5Port                                                          OBJECT IDENTIFIER ::= { gs2352pSTPMSTIPort 5 }

gs2352pSTPMSTI5AggregatedPort                                                OBJECT IDENTIFIER ::= { gs2352pSTPMSTI5Port 1 }
      
gs2352pSTPMSTI5AggregatedPortPathCost OBJECT-TYPE
   SYNTAX      Integer32(0..200000000)
   MAX-ACCESS  read-write
   STATUS      current
   DESCRIPTION
       " Auto: 0,
        Specific Path Cost range: 1 - 200000000."
   ::= { gs2352pSTPMSTI5AggregatedPort 1 }
   
gs2352pSTPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI5AggregatedPort 2 }
   
gs2352pSTPMSTI5NormalPortTable OBJECT-TYPE
   SYNTAX      SEQUENCE OF Gs2352pSTPMSTI5NormalPortEntry
   MAX-ACCESS  not-accessible
   STATUS      current
   DESCRIPTION
       " Show MSTI5 Normal Port Configurations. "
   ::= { gs2352pSTPMSTI5Port 2 }

gs2352pSTPMSTI5NormalPortEntry OBJECT-TYPE
   SYNTAX      Gs2352pSTPMSTI5NormalPortEntry
   MAX-ACCESS  not-accessible
   STATUS      current
   DESCRIPTION
       ""
   INDEX    { gs2352pSTPMSTI5NormalPortConfPort  }
   ::= { gs2352pSTPMSTI5NormalPortTable 1 }

Gs2352pSTPMSTI5NormalPortEntry ::= SEQUENCE {
   gs2352pSTPMSTI5NormalPortConfPort         Integer32,
   gs2352pSTPMSTI5NormalPortPathCost         Integer32,
   gs2352pSTPMSTI5NormalPortPriority         Integer32
}

gs2352pSTPMSTI5NormalPortConfPort OBJECT-TYPE
   SYNTAX      Integer32(1..4095)
   MAX-ACCESS  not-accessible
   STATUS      current
   DESCRIPTION
       " port, range : 1 - port number. "
   ::= { gs2352pSTPMSTI5NormalPortEntry 1 }
   
gs2352pSTPMSTI5NormalPortPathCost OBJECT-TYPE
   SYNTAX      Integer32(0..200000000)
   MAX-ACCESS  read-write
   STATUS      current
   DESCRIPTION
       " Auto: 0,
        Specific Path Cost range: 1 - 200000000."
   ::= { gs2352pSTPMSTI5NormalPortEntry 2 }
   
gs2352pSTPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI5NormalPortEntry 3 }
   
gs2352pSTPMSTI6Port                                                          OBJECT IDENTIFIER ::= { gs2352pSTPMSTIPort 6 }

gs2352pSTPMSTI6AggregatedPort                                                OBJECT IDENTIFIER ::= { gs2352pSTPMSTI6Port 1 }
      
gs2352pSTPMSTI6AggregatedPortPathCost OBJECT-TYPE
   SYNTAX      Integer32(0..200000000)
   MAX-ACCESS  read-write
   STATUS      current
   DESCRIPTION
       " Auto: 0,
        Specific Path Cost range: 1 - 200000000."
   ::= { gs2352pSTPMSTI6AggregatedPort 1 }
   
gs2352pSTPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI6AggregatedPort 2 }
   
gs2352pSTPMSTI6NormalPortTable OBJECT-TYPE
   SYNTAX      SEQUENCE OF Gs2352pSTPMSTI6NormalPortEntry
   MAX-ACCESS  not-accessible
   STATUS      current
   DESCRIPTION
       " Show MSTI6 Normal Port Configurations. "
   ::= { gs2352pSTPMSTI6Port 2 }

gs2352pSTPMSTI6NormalPortEntry OBJECT-TYPE
   SYNTAX      Gs2352pSTPMSTI6NormalPortEntry
   MAX-ACCESS  not-accessible
   STATUS      current
   DESCRIPTION
       ""
   INDEX    { gs2352pSTPMSTI6NormalPortConfPort  }
   ::= { gs2352pSTPMSTI6NormalPortTable 1 }

Gs2352pSTPMSTI6NormalPortEntry ::= SEQUENCE {
   gs2352pSTPMSTI6NormalPortConfPort         Integer32,
   gs2352pSTPMSTI6NormalPortPathCost         Integer32,
   gs2352pSTPMSTI6NormalPortPriority         Integer32
}

gs2352pSTPMSTI6NormalPortConfPort OBJECT-TYPE
   SYNTAX      Integer32(1..4095)
   MAX-ACCESS  not-accessible
   STATUS      current
   DESCRIPTION
       " port, range : 1 - port number. "
   ::= { gs2352pSTPMSTI6NormalPortEntry 1 }
   
gs2352pSTPMSTI6NormalPortPathCost OBJECT-TYPE
   SYNTAX      Integer32(0..200000000)
   MAX-ACCESS  read-write
   STATUS      current
   DESCRIPTION
       " Auto: 0,
        Specific Path Cost range: 1 - 200000000."
   ::= { gs2352pSTPMSTI6NormalPortEntry 2 }
   
gs2352pSTPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI6NormalPortEntry 3 }
   
gs2352pSTPMSTI7Port                                                          OBJECT IDENTIFIER ::= { gs2352pSTPMSTIPort 7 }

gs2352pSTPMSTI7AggregatedPort                                                OBJECT IDENTIFIER ::= { gs2352pSTPMSTI7Port 1 }
      
gs2352pSTPMSTI7AggregatedPortPathCost OBJECT-TYPE
   SYNTAX      Integer32(0..200000000)
   MAX-ACCESS  read-write
   STATUS      current
   DESCRIPTION
       " Auto: 0,
        Specific Path Cost range: 1 - 200000000."
   ::= { gs2352pSTPMSTI7AggregatedPort 1 }
   
gs2352pSTPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI7AggregatedPort 2 }
   
gs2352pSTPMSTI7NormalPortTable OBJECT-TYPE
   SYNTAX      SEQUENCE OF Gs2352pSTPMSTI7NormalPortEntry
   MAX-ACCESS  not-accessible
   STATUS      current
   DESCRIPTION
       " Show MSTI7 Normal Port Configurations. "
   ::= { gs2352pSTPMSTI7Port 2 }

gs2352pSTPMSTI7NormalPortEntry OBJECT-TYPE
   SYNTAX      Gs2352pSTPMSTI7NormalPortEntry
   MAX-ACCESS  not-accessible
   STATUS      current
   DESCRIPTION
       ""
   INDEX    { gs2352pSTPMSTI7NormalPortConfPort  }
   ::= { gs2352pSTPMSTI7NormalPortTable 1 }

Gs2352pSTPMSTI7NormalPortEntry ::= SEQUENCE {
   gs2352pSTPMSTI7NormalPortConfPort         Integer32,
   gs2352pSTPMSTI7NormalPortPathCost         Integer32,
   gs2352pSTPMSTI7NormalPortPriority         Integer32
}

gs2352pSTPMSTI7NormalPortConfPort OBJECT-TYPE
   SYNTAX      Integer32(1..4095)
   MAX-ACCESS  not-accessible
   STATUS      current
   DESCRIPTION
       " port, range : 1 - port number. "
   ::= { gs2352pSTPMSTI7NormalPortEntry 1 }
   
gs2352pSTPMSTI7NormalPortPathCost OBJECT-TYPE
   SYNTAX      Integer32(0..200000000)
   MAX-ACCESS  read-write
   STATUS      current
   DESCRIPTION
       " Auto: 0,
        Specific Path Cost range: 1 - 200000000."
   ::= { gs2352pSTPMSTI7NormalPortEntry 2 }
   
gs2352pSTPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2352pSTPMSTI7NormalPortEntry 3 }
   

gs2352pSTPBridgeStatus                                                      OBJECT IDENTIFIER ::= { gs2352pSTP 8 }

gs2352pCISTBridgeSTP                                                        OBJECT IDENTIFIER ::= { gs2352pSTPBridgeStatus 1 }

gs2352pCISTBridgeSTPStatus                                                  OBJECT IDENTIFIER ::= { gs2352pCISTBridgeSTP 1 }
      
gs2352pCISTBridgeInstance OBJECT-TYPE
   SYNTAX       DisplayString
   MAX-ACCESS   read-only
   STATUS       current
   DESCRIPTION
       "The Bridge instance - CIST, MST1, ..."
   ::= { gs2352pCISTBridgeSTPStatus 1 }
   
gs2352pCISTBridgeID OBJECT-TYPE
   SYNTAX       DisplayString
   MAX-ACCESS   read-only
   STATUS       current
   DESCRIPTION
       "The Bridge ID of this Bridge instance."
   ::= { gs2352pCISTBridgeSTPStatus 2 }
   
gs2352pCISTRootID OBJECT-TYPE
   SYNTAX       DisplayString
   MAX-ACCESS   read-only
   STATUS       current
   DESCRIPTION
       "The Bridge ID of the currently elected root bridge."
   ::= { gs2352pCISTBridgeSTPStatus 3 }
   
gs2352pCISTRootPort OBJECT-TYPE
   SYNTAX       DisplayString
   MAX-ACCESS   read-only
   STATUS       current
   DESCRIPTION
       "The switch port currently assigned the root port role."
   ::= { gs2352pCISTBridgeSTPStatus 4 }

gs2352pCISTRootCost OBJECT-TYPE
   SYNTAX       Integer32(0..200000000)
   MAX-ACCESS   read-only
   STATUS       current
   DESCRIPTION
       "Root Path Cost."
   ::= { gs2352pCISTBridgeSTPStatus 5 }
   
gs2352pCISTRegionalRoot OBJECT-TYPE
   SYNTAX       DisplayString
   MAX-ACCESS   read-only
   STATUS       current
   DESCRIPTION
       "The Bridge ID of the currently elected regional root bridge, inside the MSTP region of this bridge."
   ::= { gs2352pCISTBridgeSTPStatus 6 }
   
gs2352pCISTInternalRootCost OBJECT-TYPE
   SYNTAX       Integer32(0..200000000)
   MAX-ACCESS   read-only
   STATUS       current
   DESCRIPTION
       "The Regional Root Path Cost."
   ::= { gs2352pCISTBridgeSTPStatus 7 }

gs2352pCISTTopologyFlag OBJECT-TYPE
   SYNTAX       DisplayString
   MAX-ACCESS   read-only
   STATUS       current
   DESCRIPTION
       "The current state of the Topology Change Flag of this Bridge instance."
   ::= { gs2352pCISTBridgeSTPStatus 8 }

gs2352pCISTTopologyChangeCount OBJECT-TYPE
   SYNTAX       Counter32
   MAX-ACCESS   read-only
   STATUS       current
   DESCRIPTION
       "The number of times where the topology change flag has been set."
   ::= { gs2352pCISTBridgeSTPStatus 9 }
   
gs2352pCISTTopologyChangeLast OBJECT-TYPE
   SYNTAX       DisplayString
   MAX-ACCESS   read-only
   STATUS       current
   DESCRIPTION
       "The time passed since the Topology Flag was last set."
   ::= { gs2352pCISTBridgeSTPStatus 10 }
   
gs2352pCISTPortStateTable OBJECT-TYPE
   SYNTAX      SEQUENCE OF Gs2352pCISTPortStateEntry
   MAX-ACCESS  not-accessible
   STATUS      current
   DESCRIPTION
       " Show CIST Ports and Aggregations State Configurations. "
   ::= { gs2352pCISTBridgeSTP 2 }

gs2352pCISTPortStateEntry OBJECT-TYPE
   SYNTAX      Gs2352pCISTPortStateEntry
   MAX-ACCESS  not-accessible
   STATUS      current
   DESCRIPTION
       ""
   INDEX    { gs2352pCISTPortStateIndex  }
   ::= { gs2352pCISTPortStateTable 1 }

Gs2352pCISTPortStateEntry ::= SEQUENCE {
   gs2352pCISTPortStateIndex        Integer32,
   gs2352pCISTPortStatePort         DisplayString,
   gs2352pCISTPortStatePortID       DisplayString,
   gs2352pCISTPortStateRole         DisplayString,
   gs2352pCISTPortStateState        DisplayString,
   gs2352pCISTPortStatePathCost     Integer32,
   gs2352pCISTPortStateEdge         DisplayString,
   gs2352pCISTPortStatePoint2Point  DisplayString,
   gs2352pCISTPortStateUptime       DisplayString
}

gs2352pCISTPortStateIndex OBJECT-TYPE
   SYNTAX      Integer32(1..4095)
   MAX-ACCESS  not-accessible
   STATUS      current
   DESCRIPTION
       "table index."
   ::= { gs2352pCISTPortStateEntry 1 }
   
gs2352pCISTPortStatePort OBJECT-TYPE
   SYNTAX      DisplayString
   MAX-ACCESS  read-only
   STATUS      current
   DESCRIPTION
       "The switch port number of the logical STP port."
   ::= { gs2352pCISTPortStateEntry 2 }
   
gs2352pCISTPortStatePortID OBJECT-TYPE
   SYNTAX      DisplayString
   MAX-ACCESS  read-only
   STATUS      current
   DESCRIPTION
       "The port id as used by the STP protocol. 
        This is the priority part and the logical port index of the bridge port."
   ::= { gs2352pCISTPortStateEntry 3 }
   
gs2352pCISTPortStateRole OBJECT-TYPE
   SYNTAX      DisplayString
   MAX-ACCESS  read-only
   STATUS      current
   DESCRIPTION
       "The current STP port role."
   ::= { gs2352pCISTPortStateEntry 4 }
   
gs2352pCISTPortStateState OBJECT-TYPE
   SYNTAX      DisplayString
   MAX-ACCESS  read-only
   STATUS      current
   DESCRIPTION
       "The current STP port state."
   ::= { gs2352pCISTPortStateEntry 5 }
   
gs2352pCISTPortStatePathCost OBJECT-TYPE
   SYNTAX      Integer32(0..200000000)
   MAX-ACCESS  read-only
   STATUS      current
   DESCRIPTION
       "The current STP port path cost."
   ::= { gs2352pCISTPortStateEntry 6 }
   
gs2352pCISTPortStateEdge OBJECT-TYPE
   SYNTAX      DisplayString
   MAX-ACCESS  read-only
   STATUS      current
   DESCRIPTION
       "The current STP port Edge Flag."
   ::= { gs2352pCISTPortStateEntry 7 }
   
gs2352pCISTPortStatePoint2Point OBJECT-TYPE
   SYNTAX      DisplayString
   MAX-ACCESS  read-only
   STATUS      current
   DESCRIPTION
       "The current STP port point-to-point flag."
   ::= { gs2352pCISTPortStateEntry 8 }
   
gs2352pCISTPortStateUptime OBJECT-TYPE
   SYNTAX      DisplayString
   MAX-ACCESS  read-only
   STATUS      current
   DESCRIPTION
       "The time since the bridge port was last initialized."
   ::= { gs2352pCISTPortStateEntry 9 }
   
gs2352pMSTI1BridgeSTP                                                        OBJECT IDENTIFIER ::= { gs2352pSTPBridgeStatus 2 }

gs2352pMSTI1BridgeSTPStatus                                                  OBJECT IDENTIFIER ::= { gs2352pMSTI1BridgeSTP 1 }
      
gs2352pMSTI1BridgeInstance OBJECT-TYPE
   SYNTAX       DisplayString
   MAX-ACCESS   read-only
   STATUS       current
   DESCRIPTION
       "The Bridge instance - CIST, MST1, ..."
   ::= { gs2352pMSTI1BridgeSTPStatus 1 }
   
gs2352pMSTI1BridgeID OBJECT-TYPE
   SYNTAX       DisplayString
   MAX-ACCESS   read-only
   STATUS       current
   DESCRIPTION
       "The Bridge ID of this Bridge instance."
   ::= { gs2352pMSTI1BridgeSTPStatus 2 }
   
gs2352pMSTI1RootID OBJECT-TYPE
   SYNTAX       DisplayString
   MAX-ACCESS   read-only
   STATUS       current
   DESCRIPTION
       "The Bridge ID of the currently elected root bridge."
   ::= { gs2352pMSTI1BridgeSTPStatus 3 }
   
gs2352pMSTI1RootPort OBJECT-TYPE
   SYNTAX       DisplayString
   MAX-ACCESS   read-only
   STATUS       current
   DESCRIPTION
       "The switch port currently assigned the root port role."
   ::= { gs2352pMSTI1BridgeSTPStatus 4 }

gs2352pMSTI1RootCost OBJECT-TYPE
   SYNTAX       Integer32(0..200000000)
   MAX-ACCESS   read-only
   STATUS       current
   DESCRIPTION
       "Root Path Cost."
   ::= { gs2352pMSTI1BridgeSTPStatus 5 }

gs2352pMSTI1TopologyFlag OBJECT-TYPE
   SYNTAX       DisplayString
   MAX-ACCESS   read-only
   STATUS       current
   DESCRIPTION
       "The current state of the Topology Change Flag of this Bridge instance."
   ::= { gs2352pMSTI1BridgeSTPStatus 8 }

gs2352pMSTI1TopologyChangeCount OBJECT-TYPE
   SYNTAX       Counter32
   MAX-ACCESS   read-only
   STATUS       current
   DESCRIPTION
       "The number of times where the topology change flag has been set."
   ::= { gs2352pMSTI1BridgeSTPStatus 9 }
   
gs2352pMSTI1TopologyChangeLast OBJECT-TYPE
   SYNTAX       DisplayString
   MAX-ACCESS   read-only
   STATUS       current
   DESCRIPTION
       "The time passed since the Topology Flag was last set."
   ::= { gs2352pMSTI1BridgeSTPStatus 10 }
   
gs2352pMSTI1PortStateTable OBJECT-TYPE
   SYNTAX      SEQUENCE OF Gs2352pMSTI1PortStateEntry
   MAX-ACCESS  not-accessible
   STATUS      current
   DESCRIPTION
       " Show MSTI1 Ports and Aggregations State Configurations. "
   ::= { gs2352pMSTI1BridgeSTP 2 }

gs2352pMSTI1PortStateEntry OBJECT-TYPE
   SYNTAX      Gs2352pMSTI1PortStateEntry
   MAX-ACCESS  not-accessible
   STATUS      current
   DESCRIPTION
       ""
   INDEX    { gs2352pMSTI1PortStateIndex  }
   ::= { gs2352pMSTI1PortStateTable 1 }

Gs2352pMSTI1PortStateEntry ::= SEQUENCE {
   gs2352pMSTI1PortStateIndex        Integer32,
   gs2352pMSTI1PortStatePort         DisplayString,
   gs2352pMSTI1PortStatePortID       DisplayString,
   gs2352pMSTI1PortStateRole         DisplayString,
   gs2352pMSTI1PortStateState        DisplayString,
   gs2352pMSTI1PortStatePathCost     Integer32,
   gs2352pMSTI1PortStateEdge         DisplayString,
   gs2352pMSTI1PortStatePoint2Point  DisplayString,
   gs2352pMSTI1PortStateUptime       DisplayString
}

gs2352pMSTI1PortStateIndex OBJECT-TYPE
   SYNTAX      Integer32(1..4095)
   MAX-ACCESS  not-accessible
   STATUS      current
   DESCRIPTION
       "table index."
   ::= { gs2352pMSTI1PortStateEntry 1 }
   
gs2352pMSTI1PortStatePort OBJECT-TYPE
   SYNTAX      DisplayString
   MAX-ACCESS  read-only
   STATUS      current
   DESCRIPTION
       "The switch port number of the logical STP port."
   ::= { gs2352pMSTI1PortStateEntry 2 }
   
gs2352pMSTI1PortStatePortID OBJECT-TYPE
   SYNTAX      DisplayString
   MAX-ACCESS  read-only
   STATUS      current
   DESCRIPTION
       "The port id as used by the STP protocol. 
        This is the priority part and the logical port index of the bridge port."
   ::= { gs2352pMSTI1PortStateEntry 3 }
   
gs2352pMSTI1PortStateRole OBJECT-TYPE
   SYNTAX      DisplayString
   MAX-ACCESS  read-only
   STATUS      current
   DESCRIPTION
       "The current STP port role."
   ::= { gs2352pMSTI1PortStateEntry 4 }
   
gs2352pMSTI1PortStateState OBJECT-TYPE
   SYNTAX      DisplayString
   MAX-ACCESS  read-only
   STATUS      current
   DESCRIPTION
       "The current STP port state."
   ::= { gs2352pMSTI1PortStateEntry 5 }
   
gs2352pMSTI1PortStatePathCost OBJECT-TYPE
   SYNTAX      Integer32(0..200000000)
   MAX-ACCESS  read-only
   STATUS      current
   DESCRIPTION
       "The current STP port path cost."
   ::= { gs2352pMSTI1PortStateEntry 6 }
   
gs2352pMSTI1PortStateEdge OBJECT-TYPE
   SYNTAX      DisplayString
   MAX-ACCESS  read-only
   STATUS      current
   DESCRIPTION
       "The current STP port Edge Flag."
   ::= { gs2352pMSTI1PortStateEntry 7 }
   
gs2352pMSTI1PortStatePoint2Point OBJECT-TYPE
   SYNTAX      DisplayString
   MAX-ACCESS  read-only
   STATUS      current
   DESCRIPTION
       "The current STP port point-to-point flag."
   ::= { gs2352pMSTI1PortStateEntry 8 }
   
gs2352pMSTI1PortStateUptime OBJECT-TYPE
   SYNTAX      DisplayString
   MAX-ACCESS  read-only
   STATUS      current
   DESCRIPTION
       "The time since the bridge port was last initialized."
   ::= { gs2352pMSTI1PortStateEntry 9 }
   
gs2352pMSTI2BridgeSTP                                                        OBJECT IDENTIFIER ::= { gs2352pSTPBridgeStatus 3 }

gs2352pMSTI2BridgeSTPStatus                                                  OBJECT IDENTIFIER ::= { gs2352pMSTI2BridgeSTP 1 }
      
gs2352pMSTI2BridgeInstance OBJECT-TYPE
   SYNTAX       DisplayString
   MAX-ACCESS   read-only
   STATUS       current
   DESCRIPTION
       "The Bridge instance - CIST, MST1, ..."
   ::= { gs2352pMSTI2BridgeSTPStatus 1 }
   
gs2352pMSTI2BridgeID OBJECT-TYPE
   SYNTAX       DisplayString
   MAX-ACCESS   read-only
   STATUS       current
   DESCRIPTION
       "The Bridge ID of this Bridge instance."
   ::= { gs2352pMSTI2BridgeSTPStatus 2 }
   
gs2352pMSTI2RootID OBJECT-TYPE
   SYNTAX       DisplayString
   MAX-ACCESS   read-only
   STATUS       current
   DESCRIPTION
       "The Bridge ID of the currently elected root bridge."
   ::= { gs2352pMSTI2BridgeSTPStatus 3 }
   
gs2352pMSTI2RootPort OBJECT-TYPE
   SYNTAX       DisplayString
   MAX-ACCESS   read-only
   STATUS       current
   DESCRIPTION
       "The switch port currently assigned the root port role."
   ::= { gs2352pMSTI2BridgeSTPStatus 4 }

gs2352pMSTI2RootCost OBJECT-TYPE
   SYNTAX       Integer32(0..200000000)
   MAX-ACCESS   read-only
   STATUS       current
   DESCRIPTION
       "Root Path Cost."
   ::= { gs2352pMSTI2BridgeSTPStatus 5 }

gs2352pMSTI2TopologyFlag OBJECT-TYPE
   SYNTAX       DisplayString
   MAX-ACCESS   read-only
   STATUS       current
   DESCRIPTION
       "The current state of the Topology Change Flag of this Bridge instance."
   ::= { gs2352pMSTI2BridgeSTPStatus 8 }

gs2352pMSTI2TopologyChangeCount OBJECT-TYPE
   SYNTAX       Counter32
   MAX-ACCESS   read-only
   STATUS       current
   DESCRIPTION
       "The number of times where the topology change flag has been set."
   ::= { gs2352pMSTI2BridgeSTPStatus 9 }
   
gs2352pMSTI2TopologyChangeLast OBJECT-TYPE
   SYNTAX       DisplayString
   MAX-ACCESS   read-only
   STATUS       current
   DESCRIPTION
       "The time passed since the Topology Flag was last set."
   ::= { gs2352pMSTI2BridgeSTPStatus 10 }
   
gs2352pMSTI2PortStateTable OBJECT-TYPE
   SYNTAX      SEQUENCE OF Gs2352pMSTI2PortStateEntry
   MAX-ACCESS  not-accessible
   STATUS      current
   DESCRIPTION
       " Show MSTI2 Ports and Aggregations State Configurations. "
   ::= { gs2352pMSTI2BridgeSTP 2 }

gs2352pMSTI2PortStateEntry OBJECT-TYPE
   SYNTAX      Gs2352pMSTI2PortStateEntry
   MAX-ACCESS  not-accessible
   STATUS      current
   DESCRIPTION
       ""
   INDEX    { gs2352pMSTI2PortStateIndex  }
   ::= { gs2352pMSTI2PortStateTable 1 }

Gs2352pMSTI2PortStateEntry ::= SEQUENCE {
   gs2352pMSTI2PortStateIndex        Integer32,
   gs2352pMSTI2PortStatePort         DisplayString,
   gs2352pMSTI2PortStatePortID       DisplayString,
   gs2352pMSTI2PortStateRole         DisplayString,
   gs2352pMSTI2PortStateState        DisplayString,
   gs2352pMSTI2PortStatePathCost     Integer32,
   gs2352pMSTI2PortStateEdge         DisplayString,
   gs2352pMSTI2PortStatePoint2Point  DisplayString,
   gs2352pMSTI2PortStateUptime       DisplayString
}

gs2352pMSTI2PortStateIndex OBJECT-TYPE
   SYNTAX      Integer32(1..4095)
   MAX-ACCESS  not-accessible
   STATUS      current
   DESCRIPTION
       "table index."
   ::= { gs2352pMSTI2PortStateEntry 1 }
   
gs2352pMSTI2PortStatePort OBJECT-TYPE
   SYNTAX      DisplayString
   MAX-ACCESS  read-only
   STATUS      current
   DESCRIPTION
       "The switch port number of the logical STP port."
   ::= { gs2352pMSTI2PortStateEntry 2 }
   
gs2352pMSTI2PortStatePortID OBJECT-TYPE
   SYNTAX      DisplayString
   MAX-ACCESS  read-only
   STATUS      current
   DESCRIPTION
       "The port id as used by the STP protocol. 
        This is the priority part and the logical port index of the bridge port."
   ::= { gs2352pMSTI2PortStateEntry 3 }
   
gs2352pMSTI2PortStateRole OBJECT-TYPE
   SYNTAX      DisplayString
   MAX-ACCESS  read-only
   STATUS      current
   DESCRIPTION
       "The current STP port role."
   ::= { gs2352pMSTI2PortStateEntry 4 }
   
gs2352pMSTI2PortStateState OBJECT-TYPE
   SYNTAX      DisplayString
   MAX-ACCESS  read-only
   STATUS      current
   DESCRIPTION
       "The current STP port state."
   ::= { gs2352pMSTI2PortStateEntry 5 }
   
gs2352pMSTI2PortStatePathCost OBJECT-TYPE
   SYNTAX      Integer32(0..200000000)
   MAX-ACCESS  read-only
   STATUS      current
   DESCRIPTION
       "The current STP port path cost."
   ::= { gs2352pMSTI2PortStateEntry 6 }
   
gs2352pMSTI2PortStateEdge OBJECT-TYPE
   SYNTAX      DisplayString
   MAX-ACCESS  read-only
   STATUS      current
   DESCRIPTION
       "The current STP port Edge Flag."
   ::= { gs2352pMSTI2PortStateEntry 7 }
   
gs2352pMSTI2PortStatePoint2Point OBJECT-TYPE
   SYNTAX      DisplayString
   MAX-ACCESS  read-only
   STATUS      current
   DESCRIPTION
       "The current STP port point-to-point flag."
   ::= { gs2352pMSTI2PortStateEntry 8 }
   
gs2352pMSTI2PortStateUptime OBJECT-TYPE
   SYNTAX      DisplayString
   MAX-ACCESS  read-only
   STATUS      current
   DESCRIPTION
       "The time since the bridge port was last initialized."
   ::= { gs2352pMSTI2PortStateEntry 9 }

gs2352pMSTI3BridgeSTP                                                        OBJECT IDENTIFIER ::= { gs2352pSTPBridgeStatus 4 }

gs2352pMSTI3BridgeSTPStatus                                                  OBJECT IDENTIFIER ::= { gs2352pMSTI3BridgeSTP 1 }
      
gs2352pMSTI3BridgeInstance OBJECT-TYPE
   SYNTAX       DisplayString
   MAX-ACCESS   read-only
   STATUS       current
   DESCRIPTION
       "The Bridge instance - CIST, MST1, ..."
   ::= { gs2352pMSTI3BridgeSTPStatus 1 }
   
gs2352pMSTI3BridgeID OBJECT-TYPE
   SYNTAX       DisplayString
   MAX-ACCESS   read-only
   STATUS       current
   DESCRIPTION
       "The Bridge ID of this Bridge instance."
   ::= { gs2352pMSTI3BridgeSTPStatus 2 }
   
gs2352pMSTI3RootID OBJECT-TYPE
   SYNTAX       DisplayString
   MAX-ACCESS   read-only
   STATUS       current
   DESCRIPTION
       "The Bridge ID of the currently elected root bridge."
   ::= { gs2352pMSTI3BridgeSTPStatus 3 }
   
gs2352pMSTI3RootPort OBJECT-TYPE
   SYNTAX       DisplayString
   MAX-ACCESS   read-only
   STATUS       current
   DESCRIPTION
       "The switch port currently assigned the root port role."
   ::= { gs2352pMSTI3BridgeSTPStatus 4 }

gs2352pMSTI3RootCost OBJECT-TYPE
   SYNTAX       Integer32(0..200000000)
   MAX-ACCESS   read-only
   STATUS       current
   DESCRIPTION
       "Root Path Cost."
   ::= { gs2352pMSTI3BridgeSTPStatus 5 }

gs2352pMSTI3TopologyFlag OBJECT-TYPE
   SYNTAX       DisplayString
   MAX-ACCESS   read-only
   STATUS       current
   DESCRIPTION
       "The current state of the Topology Change Flag of this Bridge instance."
   ::= { gs2352pMSTI3BridgeSTPStatus 8 }

gs2352pMSTI3TopologyChangeCount OBJECT-TYPE
   SYNTAX       Counter32
   MAX-ACCESS   read-only
   STATUS       current
   DESCRIPTION
       "The number of times where the topology change flag has been set."
   ::= { gs2352pMSTI3BridgeSTPStatus 9 }
   
gs2352pMSTI3TopologyChangeLast OBJECT-TYPE
   SYNTAX       DisplayString
   MAX-ACCESS   read-only
   STATUS       current
   DESCRIPTION
       "The time passed since the Topology Flag was last set."
   ::= { gs2352pMSTI3BridgeSTPStatus 10 }
   
gs2352pMSTI3PortStateTable OBJECT-TYPE
   SYNTAX      SEQUENCE OF Gs2352pMSTI3PortStateEntry
   MAX-ACCESS  not-accessible
   STATUS      current
   DESCRIPTION
       " Show MSTI3 Ports and Aggregations State Configurations. "
   ::= { gs2352pMSTI3BridgeSTP 2 }

gs2352pMSTI3PortStateEntry OBJECT-TYPE
   SYNTAX      Gs2352pMSTI3PortStateEntry
   MAX-ACCESS  not-accessible
   STATUS      current
   DESCRIPTION
       ""
   INDEX    { gs2352pMSTI3PortStateIndex  }
   ::= { gs2352pMSTI3PortStateTable 1 }

Gs2352pMSTI3PortStateEntry ::= SEQUENCE {
   gs2352pMSTI3PortStateIndex        Integer32,
   gs2352pMSTI3PortStatePort         DisplayString,
   gs2352pMSTI3PortStatePortID       DisplayString,
   gs2352pMSTI3PortStateRole         DisplayString,
   gs2352pMSTI3PortStateState        DisplayString,
   gs2352pMSTI3PortStatePathCost     Integer32,
   gs2352pMSTI3PortStateEdge         DisplayString,
   gs2352pMSTI3PortStatePoint2Point  DisplayString,
   gs2352pMSTI3PortStateUptime       DisplayString
}

gs2352pMSTI3PortStateIndex OBJECT-TYPE
   SYNTAX      Integer32(1..4095)
   MAX-ACCESS  not-accessible
   STATUS      current
   DESCRIPTION
       "table index."
   ::= { gs2352pMSTI3PortStateEntry 1 }
   
gs2352pMSTI3PortStatePort OBJECT-TYPE
   SYNTAX      DisplayString
   MAX-ACCESS  read-only
   STATUS      current
   DESCRIPTION
       "The switch port number of the logical STP port."
   ::= { gs2352pMSTI3PortStateEntry 2 }
   
gs2352pMSTI3PortStatePortID OBJECT-TYPE
   SYNTAX      DisplayString
   MAX-ACCESS  read-only
   STATUS      current
   DESCRIPTION
       "The port id as used by the STP protocol. 
        This is the priority part and the logical port index of the bridge port."
   ::= { gs2352pMSTI3PortStateEntry 3 }
   
gs2352pMSTI3PortStateRole OBJECT-TYPE
   SYNTAX      DisplayString
   MAX-ACCESS  read-only
   STATUS      current
   DESCRIPTION
       "The current STP port role."
   ::= { gs2352pMSTI3PortStateEntry 4 }
   
gs2352pMSTI3PortStateState OBJECT-TYPE
   SYNTAX      DisplayString
   MAX-ACCESS  read-only
   STATUS      current
   DESCRIPTION
       "The current STP port state."
   ::= { gs2352pMSTI3PortStateEntry 5 }
   
gs2352pMSTI3PortStatePathCost OBJECT-TYPE
   SYNTAX      Integer32(0..200000000)
   MAX-ACCESS  read-only
   STATUS      current
   DESCRIPTION
       "The current STP port path cost."
   ::= { gs2352pMSTI3PortStateEntry 6 }
   
gs2352pMSTI3PortStateEdge OBJECT-TYPE
   SYNTAX      DisplayString
   MAX-ACCESS  read-only
   STATUS      current
   DESCRIPTION
       "The current STP port Edge Flag."
   ::= { gs2352pMSTI3PortStateEntry 7 }
   
gs2352pMSTI3PortStatePoint2Point OBJECT-TYPE
   SYNTAX      DisplayString
   MAX-ACCESS  read-only
   STATUS      current
   DESCRIPTION
       "The current STP port point-to-point flag."
   ::= { gs2352pMSTI3PortStateEntry 8 }
   
gs2352pMSTI3PortStateUptime OBJECT-TYPE
   SYNTAX      DisplayString
   MAX-ACCESS  read-only
   STATUS      current
   DESCRIPTION
       "The time since the bridge port was last initialized."
   ::= { gs2352pMSTI3PortStateEntry 9 }
   
gs2352pMSTI4BridgeSTP                                                        OBJECT IDENTIFIER ::= { gs2352pSTPBridgeStatus 5 }

gs2352pMSTI4BridgeSTPStatus                                                  OBJECT IDENTIFIER ::= { gs2352pMSTI4BridgeSTP 1 }
      
gs2352pMSTI4BridgeInstance OBJECT-TYPE
   SYNTAX       DisplayString
   MAX-ACCESS   read-only
   STATUS       current
   DESCRIPTION
       "The Bridge instance - CIST, MST1, ..."
   ::= { gs2352pMSTI4BridgeSTPStatus 1 }
   
gs2352pMSTI4BridgeID OBJECT-TYPE
   SYNTAX       DisplayString
   MAX-ACCESS   read-only
   STATUS       current
   DESCRIPTION
       "The Bridge ID of this Bridge instance."
   ::= { gs2352pMSTI4BridgeSTPStatus 2 }
   
gs2352pMSTI4RootID OBJECT-TYPE
   SYNTAX       DisplayString
   MAX-ACCESS   read-only
   STATUS       current
   DESCRIPTION
       "The Bridge ID of the currently elected root bridge."
   ::= { gs2352pMSTI4BridgeSTPStatus 3 }
   
gs2352pMSTI4RootPort OBJECT-TYPE
   SYNTAX       DisplayString
   MAX-ACCESS   read-only
   STATUS       current
   DESCRIPTION
       "The switch port currently assigned the root port role."
   ::= { gs2352pMSTI4BridgeSTPStatus 4 }

gs2352pMSTI4RootCost OBJECT-TYPE
   SYNTAX       Integer32(0..200000000)
   MAX-ACCESS   read-only
   STATUS       current
   DESCRIPTION
       "Root Path Cost."
   ::= { gs2352pMSTI4BridgeSTPStatus 5 }

gs2352pMSTI4TopologyFlag OBJECT-TYPE
   SYNTAX       DisplayString
   MAX-ACCESS   read-only
   STATUS       current
   DESCRIPTION
       "The current state of the Topology Change Flag of this Bridge instance."
   ::= { gs2352pMSTI4BridgeSTPStatus 8 }

gs2352pMSTI4TopologyChangeCount OBJECT-TYPE
   SYNTAX       Counter32
   MAX-ACCESS   read-only
   STATUS       current
   DESCRIPTION
       "The number of times where the topology change flag has been set."
   ::= { gs2352pMSTI4BridgeSTPStatus 9 }
   
gs2352pMSTI4TopologyChangeLast OBJECT-TYPE
   SYNTAX       DisplayString
   MAX-ACCESS   read-only
   STATUS       current
   DESCRIPTION
       "The time passed since the Topology Flag was last set."
   ::= { gs2352pMSTI4BridgeSTPStatus 10 }
   
gs2352pMSTI4PortStateTable OBJECT-TYPE
   SYNTAX      SEQUENCE OF Gs2352pMSTI4PortStateEntry
   MAX-ACCESS  not-accessible
   STATUS      current
   DESCRIPTION
       " Show MSTI4 Ports and Aggregations State Configurations. "
   ::= { gs2352pMSTI4BridgeSTP 2 }

gs2352pMSTI4PortStateEntry OBJECT-TYPE
   SYNTAX      Gs2352pMSTI4PortStateEntry
   MAX-ACCESS  not-accessible
   STATUS      current
   DESCRIPTION
       ""
   INDEX    { gs2352pMSTI4PortStateIndex  }
   ::= { gs2352pMSTI4PortStateTable 1 }

Gs2352pMSTI4PortStateEntry ::= SEQUENCE {
   gs2352pMSTI4PortStateIndex        Integer32,
   gs2352pMSTI4PortStatePort         DisplayString,
   gs2352pMSTI4PortStatePortID       DisplayString,
   gs2352pMSTI4PortStateRole         DisplayString,
   gs2352pMSTI4PortStateState        DisplayString,
   gs2352pMSTI4PortStatePathCost     Integer32,
   gs2352pMSTI4PortStateEdge         DisplayString,
   gs2352pMSTI4PortStatePoint2Point  DisplayString,
   gs2352pMSTI4PortStateUptime       DisplayString
}

gs2352pMSTI4PortStateIndex OBJECT-TYPE
   SYNTAX      Integer32(1..4095)
   MAX-ACCESS  not-accessible
   STATUS      current
   DESCRIPTION
       "table index."
   ::= { gs2352pMSTI4PortStateEntry 1 }
   
gs2352pMSTI4PortStatePort OBJECT-TYPE
   SYNTAX      DisplayString
   MAX-ACCESS  read-only
   STATUS      current
   DESCRIPTION
       "The switch port number of the logical STP port."
   ::= { gs2352pMSTI4PortStateEntry 2 }
   
gs2352pMSTI4PortStatePortID OBJECT-TYPE
   SYNTAX      DisplayString
   MAX-ACCESS  read-only
   STATUS      current
   DESCRIPTION
       "The port id as used by the STP protocol. 
        This is the priority part and the logical port index of the bridge port."
   ::= { gs2352pMSTI4PortStateEntry 3 }
   
gs2352pMSTI4PortStateRole OBJECT-TYPE
   SYNTAX      DisplayString
   MAX-ACCESS  read-only
   STATUS      current
   DESCRIPTION
       "The current STP port role."
   ::= { gs2352pMSTI4PortStateEntry 4 }
   
gs2352pMSTI4PortStateState OBJECT-TYPE
   SYNTAX      DisplayString
   MAX-ACCESS  read-only
   STATUS      current
   DESCRIPTION
       "The current STP port state."
   ::= { gs2352pMSTI4PortStateEntry 5 }
   
gs2352pMSTI4PortStatePathCost OBJECT-TYPE
   SYNTAX      Integer32(0..200000000)
   MAX-ACCESS  read-only
   STATUS      current
   DESCRIPTION
       "The current STP port path cost."
   ::= { gs2352pMSTI4PortStateEntry 6 }
   
gs2352pMSTI4PortStateEdge OBJECT-TYPE
   SYNTAX      DisplayString
   MAX-ACCESS  read-only
   STATUS      current
   DESCRIPTION
       "The current STP port Edge Flag."
   ::= { gs2352pMSTI4PortStateEntry 7 }
   
gs2352pMSTI4PortStatePoint2Point OBJECT-TYPE
   SYNTAX      DisplayString
   MAX-ACCESS  read-only
   STATUS      current
   DESCRIPTION
       "The current STP port point-to-point flag."
   ::= { gs2352pMSTI4PortStateEntry 8 }
   
gs2352pMSTI4PortStateUptime OBJECT-TYPE
   SYNTAX      DisplayString
   MAX-ACCESS  read-only
   STATUS      current
   DESCRIPTION
       "The time since the bridge port was last initialized."
   ::= { gs2352pMSTI4PortStateEntry 9 }
   
gs2352pMSTI5BridgeSTP                                                        OBJECT IDENTIFIER ::= { gs2352pSTPBridgeStatus 6 }

gs2352pMSTI5BridgeSTPStatus                                                  OBJECT IDENTIFIER ::= { gs2352pMSTI5BridgeSTP 1 }
      
gs2352pMSTI5BridgeInstance OBJECT-TYPE
   SYNTAX       DisplayString
   MAX-ACCESS   read-only
   STATUS       current
   DESCRIPTION
       "The Bridge instance - CIST, MST1, ..."
   ::= { gs2352pMSTI5BridgeSTPStatus 1 }
   
gs2352pMSTI5BridgeID OBJECT-TYPE
   SYNTAX       DisplayString
   MAX-ACCESS   read-only
   STATUS       current
   DESCRIPTION
       "The Bridge ID of this Bridge instance."
   ::= { gs2352pMSTI5BridgeSTPStatus 2 }
   
gs2352pMSTI5RootID OBJECT-TYPE
   SYNTAX       DisplayString
   MAX-ACCESS   read-only
   STATUS       current
   DESCRIPTION
       "The Bridge ID of the currently elected root bridge."
   ::= { gs2352pMSTI5BridgeSTPStatus 3 }
   
gs2352pMSTI5RootPort OBJECT-TYPE
   SYNTAX       DisplayString
   MAX-ACCESS   read-only
   STATUS       current
   DESCRIPTION
       "The switch port currently assigned the root port role."
   ::= { gs2352pMSTI5BridgeSTPStatus 4 }

gs2352pMSTI5RootCost OBJECT-TYPE
   SYNTAX       Integer32(0..200000000)
   MAX-ACCESS   read-only
   STATUS       current
   DESCRIPTION
       "Root Path Cost."
   ::= { gs2352pMSTI5BridgeSTPStatus 5 }

gs2352pMSTI5TopologyFlag OBJECT-TYPE
   SYNTAX       DisplayString
   MAX-ACCESS   read-only
   STATUS       current
   DESCRIPTION
       "The current state of the Topology Change Flag of this Bridge instance."
   ::= { gs2352pMSTI5BridgeSTPStatus 8 }

gs2352pMSTI5TopologyChangeCount OBJECT-TYPE
   SYNTAX       Counter32
   MAX-ACCESS   read-only
   STATUS       current
   DESCRIPTION
       "The number of times where the topology change flag has been set."
   ::= { gs2352pMSTI5BridgeSTPStatus 9 }
   
gs2352pMSTI5TopologyChangeLast OBJECT-TYPE
   SYNTAX       DisplayString
   MAX-ACCESS   read-only
   STATUS       current
   DESCRIPTION
       "The time passed since the Topology Flag was last set."
   ::= { gs2352pMSTI5BridgeSTPStatus 10 }
   
gs2352pMSTI5PortStateTable OBJECT-TYPE
   SYNTAX      SEQUENCE OF Gs2352pMSTI5PortStateEntry
   MAX-ACCESS  not-accessible
   STATUS      current
   DESCRIPTION
       " Show MSTI5 Ports and Aggregations State Configurations. "
   ::= { gs2352pMSTI5BridgeSTP 2 }

gs2352pMSTI5PortStateEntry OBJECT-TYPE
   SYNTAX      Gs2352pMSTI5PortStateEntry
   MAX-ACCESS  not-accessible
   STATUS      current
   DESCRIPTION
       ""
   INDEX    { gs2352pMSTI5PortStateIndex  }
   ::= { gs2352pMSTI5PortStateTable 1 }

Gs2352pMSTI5PortStateEntry ::= SEQUENCE {
   gs2352pMSTI5PortStateIndex        Integer32,
   gs2352pMSTI5PortStatePort         DisplayString,
   gs2352pMSTI5PortStatePortID       DisplayString,
   gs2352pMSTI5PortStateRole         DisplayString,
   gs2352pMSTI5PortStateState        DisplayString,
   gs2352pMSTI5PortStatePathCost     Integer32,
   gs2352pMSTI5PortStateEdge         DisplayString,
   gs2352pMSTI5PortStatePoint2Point  DisplayString,
   gs2352pMSTI5PortStateUptime       DisplayString
}

gs2352pMSTI5PortStateIndex OBJECT-TYPE
   SYNTAX      Integer32(1..4095)
   MAX-ACCESS  not-accessible
   STATUS      current
   DESCRIPTION
       "table index."
   ::= { gs2352pMSTI5PortStateEntry 1 }
   
gs2352pMSTI5PortStatePort OBJECT-TYPE
   SYNTAX      DisplayString
   MAX-ACCESS  read-only
   STATUS      current
   DESCRIPTION
       "The switch port number of the logical STP port."
   ::= { gs2352pMSTI5PortStateEntry 2 }
   
gs2352pMSTI5PortStatePortID OBJECT-TYPE
   SYNTAX      DisplayString
   MAX-ACCESS  read-only
   STATUS      current
   DESCRIPTION
       "The port id as used by the STP protocol. 
        This is the priority part and the logical port index of the bridge port."
   ::= { gs2352pMSTI5PortStateEntry 3 }
   
gs2352pMSTI5PortStateRole OBJECT-TYPE
   SYNTAX      DisplayString
   MAX-ACCESS  read-only
   STATUS      current
   DESCRIPTION
       "The current STP port role."
   ::= { gs2352pMSTI5PortStateEntry 4 }
   
gs2352pMSTI5PortStateState OBJECT-TYPE
   SYNTAX      DisplayString
   MAX-ACCESS  read-only
   STATUS      current
   DESCRIPTION
       "The current STP port state."
   ::= { gs2352pMSTI5PortStateEntry 5 }
   
gs2352pMSTI5PortStatePathCost OBJECT-TYPE
   SYNTAX      Integer32(0..200000000)
   MAX-ACCESS  read-only
   STATUS      current
   DESCRIPTION
       "The current STP port path cost."
   ::= { gs2352pMSTI5PortStateEntry 6 }
   
gs2352pMSTI5PortStateEdge OBJECT-TYPE
   SYNTAX      DisplayString
   MAX-ACCESS  read-only
   STATUS      current
   DESCRIPTION
       "The current STP port Edge Flag."
   ::= { gs2352pMSTI5PortStateEntry 7 }
   
gs2352pMSTI5PortStatePoint2Point OBJECT-TYPE
   SYNTAX      DisplayString
   MAX-ACCESS  read-only
   STATUS      current
   DESCRIPTION
       "The current STP port point-to-point flag."
   ::= { gs2352pMSTI5PortStateEntry 8 }
   
gs2352pMSTI5PortStateUptime OBJECT-TYPE
   SYNTAX      DisplayString
   MAX-ACCESS  read-only
   STATUS      current
   DESCRIPTION
       "The time since the bridge port was last initialized."
   ::= { gs2352pMSTI5PortStateEntry 9 }
   
gs2352pMSTI6BridgeSTP                                                        OBJECT IDENTIFIER ::= { gs2352pSTPBridgeStatus 7 }

gs2352pMSTI6BridgeSTPStatus                                                  OBJECT IDENTIFIER ::= { gs2352pMSTI6BridgeSTP 1 }
      
gs2352pMSTI6BridgeInstance OBJECT-TYPE
   SYNTAX       DisplayString
   MAX-ACCESS   read-only
   STATUS       current
   DESCRIPTION
       "The Bridge instance - CIST, MST1, ..."
   ::= { gs2352pMSTI6BridgeSTPStatus 1 }
   
gs2352pMSTI6BridgeID OBJECT-TYPE
   SYNTAX       DisplayString
   MAX-ACCESS   read-only
   STATUS       current
   DESCRIPTION
       "The Bridge ID of this Bridge instance."
   ::= { gs2352pMSTI6BridgeSTPStatus 2 }
   
gs2352pMSTI6RootID OBJECT-TYPE
   SYNTAX       DisplayString
   MAX-ACCESS   read-only
   STATUS       current
   DESCRIPTION
       "The Bridge ID of the currently elected root bridge."
   ::= { gs2352pMSTI6BridgeSTPStatus 3 }
   
gs2352pMSTI6RootPort OBJECT-TYPE
   SYNTAX       DisplayString
   MAX-ACCESS   read-only
   STATUS       current
   DESCRIPTION
       "The switch port currently assigned the root port role."
   ::= { gs2352pMSTI6BridgeSTPStatus 4 }

gs2352pMSTI6RootCost OBJECT-TYPE
   SYNTAX       Integer32(0..200000000)
   MAX-ACCESS   read-only
   STATUS       current
   DESCRIPTION
       "Root Path Cost."
   ::= { gs2352pMSTI6BridgeSTPStatus 5 }

gs2352pMSTI6TopologyFlag OBJECT-TYPE
   SYNTAX       DisplayString
   MAX-ACCESS   read-only
   STATUS       current
   DESCRIPTION
       "The current state of the Topology Change Flag of this Bridge instance."
   ::= { gs2352pMSTI6BridgeSTPStatus 8 }

gs2352pMSTI6TopologyChangeCount OBJECT-TYPE
   SYNTAX       Counter32
   MAX-ACCESS   read-only
   STATUS       current
   DESCRIPTION
       "The number of times where the topology change flag has been set."
   ::= { gs2352pMSTI6BridgeSTPStatus 9 }
   
gs2352pMSTI6TopologyChangeLast OBJECT-TYPE
   SYNTAX       DisplayString
   MAX-ACCESS   read-only
   STATUS       current
   DESCRIPTION
       "The time passed since the Topology Flag was last set."
   ::= { gs2352pMSTI6BridgeSTPStatus 10 }
   
gs2352pMSTI6PortStateTable OBJECT-TYPE
   SYNTAX      SEQUENCE OF Gs2352pMSTI6PortStateEntry
   MAX-ACCESS  not-accessible
   STATUS      current
   DESCRIPTION
       " Show MSTI6 Ports and Aggregations State Configurations. "
   ::= { gs2352pMSTI6BridgeSTP 2 }

gs2352pMSTI6PortStateEntry OBJECT-TYPE
   SYNTAX      Gs2352pMSTI6PortStateEntry
   MAX-ACCESS  not-accessible
   STATUS      current
   DESCRIPTION
       ""
   INDEX    { gs2352pMSTI6PortStateIndex  }
   ::= { gs2352pMSTI6PortStateTable 1 }

Gs2352pMSTI6PortStateEntry ::= SEQUENCE {
   gs2352pMSTI6PortStateIndex        Integer32,
   gs2352pMSTI6PortStatePort         DisplayString,
   gs2352pMSTI6PortStatePortID       DisplayString,
   gs2352pMSTI6PortStateRole         DisplayString,
   gs2352pMSTI6PortStateState        DisplayString,
   gs2352pMSTI6PortStatePathCost     Integer32,
   gs2352pMSTI6PortStateEdge         DisplayString,
   gs2352pMSTI6PortStatePoint2Point  DisplayString,
   gs2352pMSTI6PortStateUptime       DisplayString
}

gs2352pMSTI6PortStateIndex OBJECT-TYPE
   SYNTAX      Integer32(1..4095)
   MAX-ACCESS  not-accessible
   STATUS      current
   DESCRIPTION
       "table index."
   ::= { gs2352pMSTI6PortStateEntry 1 }
   
gs2352pMSTI6PortStatePort OBJECT-TYPE
   SYNTAX      DisplayString
   MAX-ACCESS  read-only
   STATUS      current
   DESCRIPTION
       "The switch port number of the logical STP port."
   ::= { gs2352pMSTI6PortStateEntry 2 }
   
gs2352pMSTI6PortStatePortID OBJECT-TYPE
   SYNTAX      DisplayString
   MAX-ACCESS  read-only
   STATUS      current
   DESCRIPTION
       "The port id as used by the STP protocol. 
        This is the priority part and the logical port index of the bridge port."
   ::= { gs2352pMSTI6PortStateEntry 3 }
   
gs2352pMSTI6PortStateRole OBJECT-TYPE
   SYNTAX      DisplayString
   MAX-ACCESS  read-only
   STATUS      current
   DESCRIPTION
       "The current STP port role."
   ::= { gs2352pMSTI6PortStateEntry 4 }
   
gs2352pMSTI6PortStateState OBJECT-TYPE
   SYNTAX      DisplayString
   MAX-ACCESS  read-only
   STATUS      current
   DESCRIPTION
       "The current STP port state."
   ::= { gs2352pMSTI6PortStateEntry 5 }
   
gs2352pMSTI6PortStatePathCost OBJECT-TYPE
   SYNTAX      Integer32(0..200000000)
   MAX-ACCESS  read-only
   STATUS      current
   DESCRIPTION
       "The current STP port path cost."
   ::= { gs2352pMSTI6PortStateEntry 6 }
   
gs2352pMSTI6PortStateEdge OBJECT-TYPE
   SYNTAX      DisplayString
   MAX-ACCESS  read-only
   STATUS      current
   DESCRIPTION
       "The current STP port Edge Flag."
   ::= { gs2352pMSTI6PortStateEntry 7 }
   
gs2352pMSTI6PortStatePoint2Point OBJECT-TYPE
   SYNTAX      DisplayString
   MAX-ACCESS  read-only
   STATUS      current
   DESCRIPTION
       "The current STP port point-to-point flag."
   ::= { gs2352pMSTI6PortStateEntry 8 }
   
gs2352pMSTI6PortStateUptime OBJECT-TYPE
   SYNTAX      DisplayString
   MAX-ACCESS  read-only
   STATUS      current
   DESCRIPTION
       "The time since the bridge port was last initialized."
   ::= { gs2352pMSTI6PortStateEntry 9 }
   
gs2352pMSTI7BridgeSTP                                                        OBJECT IDENTIFIER ::= { gs2352pSTPBridgeStatus 8 }

gs2352pMSTI7BridgeSTPStatus                                                  OBJECT IDENTIFIER ::= { gs2352pMSTI7BridgeSTP 1 }
      
gs2352pMSTI7BridgeInstance OBJECT-TYPE
   SYNTAX       DisplayString
   MAX-ACCESS   read-only
   STATUS       current
   DESCRIPTION
       "The Bridge instance - CIST, MST1, ..."
   ::= { gs2352pMSTI7BridgeSTPStatus 1 }
   
gs2352pMSTI7BridgeID OBJECT-TYPE
   SYNTAX       DisplayString
   MAX-ACCESS   read-only
   STATUS       current
   DESCRIPTION
       "The Bridge ID of this Bridge instance."
   ::= { gs2352pMSTI7BridgeSTPStatus 2 }
   
gs2352pMSTI7RootID OBJECT-TYPE
   SYNTAX       DisplayString
   MAX-ACCESS   read-only
   STATUS       current
   DESCRIPTION
       "The Bridge ID of the currently elected root bridge."
   ::= { gs2352pMSTI7BridgeSTPStatus 3 }
   
gs2352pMSTI7RootPort OBJECT-TYPE
   SYNTAX       DisplayString
   MAX-ACCESS   read-only
   STATUS       current
   DESCRIPTION
       "The switch port currently assigned the root port role."
   ::= { gs2352pMSTI7BridgeSTPStatus 4 }

gs2352pMSTI7RootCost OBJECT-TYPE
   SYNTAX       Integer32(0..200000000)
   MAX-ACCESS   read-only
   STATUS       current
   DESCRIPTION
       "Root Path Cost."
   ::= { gs2352pMSTI7BridgeSTPStatus 5 }

gs2352pMSTI7TopologyFlag OBJECT-TYPE
   SYNTAX       DisplayString
   MAX-ACCESS   read-only
   STATUS       current
   DESCRIPTION
       "The current state of the Topology Change Flag of this Bridge instance."
   ::= { gs2352pMSTI7BridgeSTPStatus 8 }

gs2352pMSTI7TopologyChangeCount OBJECT-TYPE
   SYNTAX       Counter32
   MAX-ACCESS   read-only
   STATUS       current
   DESCRIPTION
       "The number of times where the topology change flag has been set."
   ::= { gs2352pMSTI7BridgeSTPStatus 9 }
   
gs2352pMSTI7TopologyChangeLast OBJECT-TYPE
   SYNTAX       DisplayString
   MAX-ACCESS   read-only
   STATUS       current
   DESCRIPTION
       "The time passed since the Topology Flag was last set."
   ::= { gs2352pMSTI7BridgeSTPStatus 10 }
   
gs2352pMSTI7PortStateTable OBJECT-TYPE
   SYNTAX      SEQUENCE OF Gs2352pMSTI7PortStateEntry
   MAX-ACCESS  not-accessible
   STATUS      current
   DESCRIPTION
       " Show MSTI7 Ports and Aggregations State Configurations. "
   ::= { gs2352pMSTI7BridgeSTP 2 }

gs2352pMSTI7PortStateEntry OBJECT-TYPE
   SYNTAX      Gs2352pMSTI7PortStateEntry
   MAX-ACCESS  not-accessible
   STATUS      current
   DESCRIPTION
       ""
   INDEX    { gs2352pMSTI7PortStateIndex  }
   ::= { gs2352pMSTI7PortStateTable 1 }

Gs2352pMSTI7PortStateEntry ::= SEQUENCE {
   gs2352pMSTI7PortStateIndex        Integer32,
   gs2352pMSTI7PortStatePort         DisplayString,
   gs2352pMSTI7PortStatePortID       DisplayString,
   gs2352pMSTI7PortStateRole         DisplayString,
   gs2352pMSTI7PortStateState        DisplayString,
   gs2352pMSTI7PortStatePathCost     Integer32,
   gs2352pMSTI7PortStateEdge         DisplayString,
   gs2352pMSTI7PortStatePoint2Point  DisplayString,
   gs2352pMSTI7PortStateUptime       DisplayString
}

gs2352pMSTI7PortStateIndex OBJECT-TYPE
   SYNTAX      Integer32(1..4095)
   MAX-ACCESS  not-accessible
   STATUS      current
   DESCRIPTION
       "table index."
   ::= { gs2352pMSTI7PortStateEntry 1 }
   
gs2352pMSTI7PortStatePort OBJECT-TYPE
   SYNTAX      DisplayString
   MAX-ACCESS  read-only
   STATUS      current
   DESCRIPTION
       "The switch port number of the logical STP port."
   ::= { gs2352pMSTI7PortStateEntry 2 }
   
gs2352pMSTI7PortStatePortID OBJECT-TYPE
   SYNTAX      DisplayString
   MAX-ACCESS  read-only
   STATUS      current
   DESCRIPTION
       "The port id as used by the STP protocol. 
        This is the priority part and the logical port index of the bridge port."
   ::= { gs2352pMSTI7PortStateEntry 3 }
   
gs2352pMSTI7PortStateRole OBJECT-TYPE
   SYNTAX      DisplayString
   MAX-ACCESS  read-only
   STATUS      current
   DESCRIPTION
       "The current STP port role."
   ::= { gs2352pMSTI7PortStateEntry 4 }
   
gs2352pMSTI7PortStateState OBJECT-TYPE
   SYNTAX      DisplayString
   MAX-ACCESS  read-only
   STATUS      current
   DESCRIPTION
       "The current STP port state."
   ::= { gs2352pMSTI7PortStateEntry 5 }
   
gs2352pMSTI7PortStatePathCost OBJECT-TYPE
   SYNTAX      Integer32(0..200000000)
   MAX-ACCESS  read-only
   STATUS      current
   DESCRIPTION
       "The current STP port path cost."
   ::= { gs2352pMSTI7PortStateEntry 6 }
   
gs2352pMSTI7PortStateEdge OBJECT-TYPE
   SYNTAX      DisplayString
   MAX-ACCESS  read-only
   STATUS      current
   DESCRIPTION
       "The current STP port Edge Flag."
   ::= { gs2352pMSTI7PortStateEntry 7 }
   
gs2352pMSTI7PortStatePoint2Point OBJECT-TYPE
   SYNTAX      DisplayString
   MAX-ACCESS  read-only
   STATUS      current
   DESCRIPTION
       "The current STP port point-to-point flag."
   ::= { gs2352pMSTI7PortStateEntry 8 }
   
gs2352pMSTI7PortStateUptime OBJECT-TYPE
   SYNTAX      DisplayString
   MAX-ACCESS  read-only
   STATUS      current
   DESCRIPTION
       "The time since the bridge port was last initialized."
   ::= { gs2352pMSTI7PortStateEntry 9 }
   
gs2352pSTPPortStatusTable OBJECT-TYPE
   SYNTAX      SEQUENCE OF Gs2352pSTPPortStatusEntry
   MAX-ACCESS  not-accessible
   STATUS      current
   DESCRIPTION
       " Show STP Port Status."
   ::= { gs2352pSTP 9 }

gs2352pSTPPortStatusEntry OBJECT-TYPE
   SYNTAX      Gs2352pSTPPortStatusEntry
   MAX-ACCESS  not-accessible
   STATUS      current
   DESCRIPTION
       ""
   INDEX    { gs2352pSTPPortStatusPort  }
   ::= { gs2352pSTPPortStatusTable 1 }

Gs2352pSTPPortStatusEntry ::= SEQUENCE {
   gs2352pSTPPortStatusPort         Integer32,
   gs2352pSTPPortStatusCISTRole     DisplayString,
   gs2352pSTPPortStatusCISTState    DisplayString,
   gs2352pSTPPortStatusUptime       DisplayString
}

gs2352pSTPPortStatusPort OBJECT-TYPE
   SYNTAX      Integer32(1..4095)
   MAX-ACCESS  not-accessible
   STATUS      current
   DESCRIPTION
       " port, range : 1 - port number. "
   ::= { gs2352pSTPPortStatusEntry 1 }

gs2352pSTPPortStatusCISTRole OBJECT-TYPE
   SYNTAX      DisplayString
   MAX-ACCESS  read-only
   STATUS      current
   DESCRIPTION
       " The current STP port role of the CIST port. "
   ::= { gs2352pSTPPortStatusEntry 2 }

gs2352pSTPPortStatusCISTState OBJECT-TYPE
   SYNTAX      DisplayString
   MAX-ACCESS  read-only
   STATUS      current
   DESCRIPTION
       " The current STP port state of the CIST port. "
   ::= { gs2352pSTPPortStatusEntry 3 }

gs2352pSTPPortStatusUptime OBJECT-TYPE
   SYNTAX      DisplayString
   MAX-ACCESS  read-only
   STATUS      current
   DESCRIPTION
       " The time since the bridge port was last initialized. "
   ::= { gs2352pSTPPortStatusEntry 4 }
   
gs2352pSTPPortStatisticsTable OBJECT-TYPE
   SYNTAX      SEQUENCE OF Gs2352pSTPPortStatisticsEntry
   MAX-ACCESS  not-accessible
   STATUS      current
   DESCRIPTION
       " Show STP Port Statistics."
   ::= { gs2352pSTP 10 }

gs2352pSTPPortStatisticsEntry OBJECT-TYPE
   SYNTAX      Gs2352pSTPPortStatisticsEntry
   MAX-ACCESS  not-accessible
   STATUS      current
   DESCRIPTION
       ""
   INDEX    { gs2352pSTPStatisticsIndex  }
   ::= { gs2352pSTPPortStatisticsTable 1 }

Gs2352pSTPPortStatisticsEntry ::= SEQUENCE {
   gs2352pSTPStatisticsIndex            Integer32,
   gs2352pSTPStatisticsPort             DisplayString,
   gs2352pSTPStatisticsTxMSTP           Counter32,
   gs2352pSTPStatisticsTxRSTP           Counter32,
   gs2352pSTPStatisticsTxSTP            Counter32,
   gs2352pSTPStatisticsTxTCN            Counter32,
   gs2352pSTPStatisticsRxMSTP           Counter32,
   gs2352pSTPStatisticsRxRSTP           Counter32,
   gs2352pSTPStatisticsRxSTP            Counter32,
   gs2352pSTPStatisticsRxTCN            Counter32,
   gs2352pSTPStatisticsDiscardedUnknown Counter32,
   gs2352pSTPStatisticsDiscardedIllegal Counter32
}

gs2352pSTPStatisticsIndex OBJECT-TYPE
   SYNTAX      Integer32(1..4095)
   MAX-ACCESS  not-accessible
   STATUS      current
   DESCRIPTION
       "table index."
   ::= { gs2352pSTPPortStatisticsEntry 1 }
   
gs2352pSTPStatisticsPort OBJECT-TYPE
   SYNTAX      DisplayString
   MAX-ACCESS  not-accessible
   STATUS      current
   DESCRIPTION
       " port, range : 1 - port number. "
   ::= { gs2352pSTPPortStatisticsEntry 2 }

gs2352pSTPStatisticsTxMSTP OBJECT-TYPE
   SYNTAX      Counter32
   MAX-ACCESS  read-only
   STATUS      current
   DESCRIPTION
       " The number of MSTP Configuration BPDU's received/transmitted on the port."
   ::= { gs2352pSTPPortStatisticsEntry 3 }

gs2352pSTPStatisticsTxRSTP OBJECT-TYPE
   SYNTAX      Counter32
   MAX-ACCESS  read-only
   STATUS      current
   DESCRIPTION
       " The number of RSTP Configuration BPDU's received/transmitted on the port. "
   ::= { gs2352pSTPPortStatisticsEntry 4 }

gs2352pSTPStatisticsTxSTP OBJECT-TYPE
   SYNTAX      Counter32
   MAX-ACCESS  read-only
   STATUS      current
   DESCRIPTION
       " The number of legacy STP Configuration BPDU's received/transmitted on the port. "
   ::= { gs2352pSTPPortStatisticsEntry 5 }

gs2352pSTPStatisticsTxTCN OBJECT-TYPE
   SYNTAX      Counter32
   MAX-ACCESS  read-only
   STATUS      current
   DESCRIPTION
       " The number of Topology Change Notification BPDU's received/transmitted on the port. "
   ::= { gs2352pSTPPortStatisticsEntry 6 }
   
gs2352pSTPStatisticsRxMSTP OBJECT-TYPE
   SYNTAX      Counter32
   MAX-ACCESS  read-only
   STATUS      current
   DESCRIPTION
       " The number of MSTP Configuration BPDU's received/transmitted on the port."
   ::= { gs2352pSTPPortStatisticsEntry 7 }

gs2352pSTPStatisticsRxRSTP OBJECT-TYPE
   SYNTAX      Counter32
   MAX-ACCESS  read-only
   STATUS      current
   DESCRIPTION
       " The number of RSTP Configuration BPDU's received/transmitted on the port. "
   ::= { gs2352pSTPPortStatisticsEntry 8 }

gs2352pSTPStatisticsRxSTP OBJECT-TYPE
   SYNTAX      Counter32
   MAX-ACCESS  read-only
   STATUS      current
   DESCRIPTION
       " The number of legacy STP Configuration BPDU's received/transmitted on the port. "
   ::= { gs2352pSTPPortStatisticsEntry 9 }

gs2352pSTPStatisticsRxTCN OBJECT-TYPE
   SYNTAX      Counter32
   MAX-ACCESS  read-only
   STATUS      current
   DESCRIPTION
       " The number of Topology Change Notification BPDU's received/transmitted on the port. "
   ::= { gs2352pSTPPortStatisticsEntry 10 }

gs2352pSTPStatisticsDiscardedUnknown OBJECT-TYPE
   SYNTAX      Counter32
   MAX-ACCESS  read-only
   STATUS      current
   DESCRIPTION
       " The number of unknown Spanning Tree BPDU's received and discarded on the port. "
   ::= { gs2352pSTPPortStatisticsEntry 11 }
   
gs2352pSTPStatisticsDiscardedIllegal OBJECT-TYPE
   SYNTAX      Counter32
   MAX-ACCESS  read-only
   STATUS      current
   DESCRIPTION
       " The number of illegal Spanning Tree BPDU's received and discarded on the port. "
   ::= { gs2352pSTPPortStatisticsEntry 12 }


gs2352pFilteringDataBase                                                  OBJECT IDENTIFIER ::= { gs2352pConfiguration 21 }

gs2352pFilteringDataBaseConfig                                            OBJECT IDENTIFIER ::= { gs2352pFilteringDataBase 1 }

gs2352pFilteringDataBaseAgingTime OBJECT-TYPE
   SYNTAX      Integer32(0..1000000)
   MAX-ACCESS  read-write
   STATUS      current
   DESCRIPTION
       "Configure aging time by entering a value here in seconds.
        default: 300,
        range: 10-1000000. 
        Disable automatic aging : 0."
   ::= { gs2352pFilteringDataBaseConfig 1 }

gs2352pFilteringDataBaseConfigTable OBJECT-TYPE
   SYNTAX      SEQUENCE OF GS2352PFilteringDataBaseConfigEntry
   MAX-ACCESS  not-accessible
   STATUS      current
   DESCRIPTION
       " "
   ::= { gs2352pFilteringDataBaseConfig 2 }

gs2352pFilteringDataBaseConfigEntry OBJECT-TYPE
   SYNTAX      GS2352PFilteringDataBaseConfigEntry
   MAX-ACCESS  not-accessible
   STATUS      current
   DESCRIPTION
       ""
   INDEX    { gs2352pFilteringDataBaseConfigPort  }
   ::= { gs2352pFilteringDataBaseConfigTable 1 }
   
GS2352PFilteringDataBaseConfigEntry ::= SEQUENCE {
   gs2352pFilteringDataBaseConfigPort        Integer32,
   gs2352pFilteringDataBaseConfigLearning    INTEGER
}

gs2352pFilteringDataBaseConfigPort OBJECT-TYPE
   SYNTAX      Integer32(1..4095)
   MAX-ACCESS  not-accessible
   STATUS      current
   DESCRIPTION
       " "
   ::= { gs2352pFilteringDataBaseConfigEntry 1 }

gs2352pFilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2352pFilteringDataBaseConfigEntry 2 }


gs2352pFilteringDataBaseStaticMAC                                OBJECT IDENTIFIER ::= { gs2352pFilteringDataBaseConfig 3 }

gs2352pFilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2352pFilteringDataBaseStaticMAC 1 }

gs2352pFilteringDataBaseStaticMACTable OBJECT-TYPE
   SYNTAX      SEQUENCE OF GS2352PFilteringDataBaseStaticMACEntry
   MAX-ACCESS  not-accessible
   STATUS      current
   DESCRIPTION
       " "
   ::= { gs2352pFilteringDataBaseStaticMAC 2 }

gs2352pFilteringDataBaseStaticMACEntry OBJECT-TYPE
   SYNTAX      GS2352PFilteringDataBaseStaticMACEntry
   MAX-ACCESS  not-accessible
   STATUS      current
   DESCRIPTION
       ""
   INDEX    { gs2352pFilteringDataBaseStaticMACIndex  }
   ::= { gs2352pFilteringDataBaseStaticMACTable 1 }

GS2352PFilteringDataBaseStaticMACEntry ::= SEQUENCE {
   gs2352pFilteringDataBaseStaticMACIndex	    Integer32,
   gs2352pFilteringDataBaseStaticMACVLANId	    Integer32,
   gs2352pFilteringDataBaseStaticMACAddress      MacAddress,
   gs2352pFilteringDataBaseStaticMACPortMembers  DisplayString,
   gs2352pFilteringDataBaseStaticMACRowStatus	INTEGER
}

gs2352pFilteringDataBaseStaticMACIndex OBJECT-TYPE
   SYNTAX      Integer32(1..4095)
   MAX-ACCESS  not-accessible
   STATUS      current
   DESCRIPTION
       " "
   ::= { gs2352pFilteringDataBaseStaticMACEntry 1 }

gs2352pFilteringDataBaseStaticMACVLANId OBJECT-TYPE
   SYNTAX      Integer32(1..4094)
   MAX-ACCESS  read-write
   STATUS      current
   DESCRIPTION
       " VLAN ID, range: 1 - 4094. "
   ::= { gs2352pFilteringDataBaseStaticMACEntry 2 }

gs2352pFilteringDataBaseStaticMACAddress OBJECT-TYPE
   SYNTAX      MacAddress
   MAX-ACCESS  read-write
   STATUS      current
   DESCRIPTION
       " MAC address, format 0a 1b 2c 3d 4e 5f "
   ::= { gs2352pFilteringDataBaseStaticMACEntry 3 }

gs2352pFilteringDataBaseStaticMACPortMembers OBJECT-TYPE
   SYNTAX      DisplayString
   MAX-ACCESS  read-write
   STATUS      current
   DESCRIPTION
       "To include the ports in a Static MAC Table"
   ::= { gs2352pFilteringDataBaseStaticMACEntry 4 }

gs2352pFilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2352pFilteringDataBaseStaticMACEntry 5 }
   

gs2352pFilteringDataBaseDynamicMACTable OBJECT-TYPE
   SYNTAX      SEQUENCE OF GS2352PFilteringDataBaseDynamicMACEntry
   MAX-ACCESS  not-accessible
   STATUS      current
   DESCRIPTION
       " "
   ::= { gs2352pFilteringDataBaseConfig 4 }

gs2352pFilteringDataBaseDynamicMACEntry OBJECT-TYPE
   SYNTAX      GS2352PFilteringDataBaseDynamicMACEntry
   MAX-ACCESS  not-accessible
   STATUS      current
   DESCRIPTION
       ""
   INDEX    { gs2352pFilteringDataBaseDynamicMACIndex  }
   ::= { gs2352pFilteringDataBaseDynamicMACTable 1 }
   
GS2352PFilteringDataBaseDynamicMACEntry ::= SEQUENCE {
   gs2352pFilteringDataBaseDynamicMACIndex	    Integer32,
   gs2352pFilteringDataBaseDynamicMACType	    INTEGER,
   gs2352pFilteringDataBaseDynamicMACVLAN	    Integer32,
   gs2352pFilteringDataBaseDynamicMACAddress     MacAddress,
   gs2352pFilteringDataBaseDynamicPortMembers    DisplayString
}

gs2352pFilteringDataBaseDynamicMACIndex OBJECT-TYPE
   SYNTAX      Integer32(1..4095)
   MAX-ACCESS  not-accessible
   STATUS      current
   DESCRIPTION
       " "
   ::= { gs2352pFilteringDataBaseDynamicMACEntry 1 }

gs2352pFilteringDataBaseDynamicMACType OBJECT-TYPE
   SYNTAX      INTEGER { dynamic(0), static(1) }
   MAX-ACCESS  read-only
   STATUS      current
   DESCRIPTION
       "Indicates whether the entry is a static or a dynamic entry."
   ::= { gs2352pFilteringDataBaseDynamicMACEntry 2 }

gs2352pFilteringDataBaseDynamicMACVLAN OBJECT-TYPE
   SYNTAX      Integer32(1..4094)
   MAX-ACCESS  read-only
   STATUS      current
   DESCRIPTION
       "The VLAN ID of the entry."
   ::= { gs2352pFilteringDataBaseDynamicMACEntry 3 }

gs2352pFilteringDataBaseDynamicMACAddress OBJECT-TYPE
   SYNTAX      MacAddress
   MAX-ACCESS  read-only
   STATUS      current
   DESCRIPTION
       "The MAC address of the entry."
   ::= { gs2352pFilteringDataBaseDynamicMACEntry 4 }
   
gs2352pFilteringDataBaseDynamicPortMembers OBJECT-TYPE
   SYNTAX      DisplayString
   MAX-ACCESS  read-only
   STATUS      current
   DESCRIPTION
       "The ports that are members of the entry."
   ::= { gs2352pFilteringDataBaseDynamicMACEntry 5 } 


gs2352pSFlowAgent                                                  OBJECT IDENTIFIER ::= { gs2352pConfiguration 22 }

gs2352pSFlowAgentCollector                                            OBJECT IDENTIFIER ::= { gs2352pSFlowAgent 1 }

gs2352pSFlowAgentReceiverMode OBJECT-TYPE
   SYNTAX      INTEGER { disable(0), enable(1) }
   MAX-ACCESS  read-write
   STATUS      current
   DESCRIPTION
       "default: 0
       0: disable
       1: enable "
   ::= { gs2352pSFlowAgentCollector 1 }


gs2352pLMC                                                   OBJECT IDENTIFIER ::= { gs2352pConfiguration 1500 }

gs2352pLMCOperating OBJECT-TYPE
   SYNTAX      INTEGER { disabled(0), enabled(1), try(2) }
   MAX-ACCESS  read-write
   STATUS      current
   DESCRIPTION
       "0: disabled
        1: enabled
        2: try"
   ::= { gs2352pLMC 1 }

gs2352pLMCConfigViaDhcp OBJECT-TYPE
   SYNTAX      INTEGER { disabled(0), enabled(1) }
   MAX-ACCESS  read-write
   STATUS      current
   DESCRIPTION
       "0: disabled
        1: enabled"
   ::= { gs2352pLMC 2 }

gs2352pLMCDomain OBJECT-TYPE
   SYNTAX      DisplayString(SIZE(0..255))
   MAX-ACCESS  read-write
   STATUS      current
   DESCRIPTION
       "0: disabled
        1: enabled"
   ::= { gs2352pLMC 3 }

gs2352pLMCDhcpClientAutoRenew OBJECT-TYPE
   SYNTAX      INTEGER { disabled(0), enabled(1) }
   MAX-ACCESS  read-write
   STATUS      current
   DESCRIPTION
       "0: disabled
        1: enabled"
   ::= { gs2352pLMC 4 }


gs2352pLMCZeroTouchSupport OBJECT-TYPE
   SYNTAX      INTEGER { No(0), Yes(1) }
   MAX-ACCESS  read-only
   STATUS      current
   DESCRIPTION
       "0: No
        1: Yes"
   ::= { gs2352pLMC 50 }   
   
gs2352pLMCPairingTokenPresent OBJECT-TYPE
   SYNTAX      INTEGER { No(0), Yes(1) }
   MAX-ACCESS  read-only
   STATUS      current
   DESCRIPTION
       "0: No
        1: Yes"
   ::= { gs2352pLMC 51 }
   
gs2352pLMCClientStatus OBJECT-TYPE
   SYNTAX      DisplayString
   MAX-ACCESS  read-only
   STATUS      current
   DESCRIPTION
           ""
   ::= { gs2352pLMC  52 }
   
   
gs2352pLMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2352pLMC  53 }
   
gs2352pLMCControlStatus OBJECT-TYPE
   SYNTAX      INTEGER {Disabled(2), Operating(4)}
   MAX-ACCESS  read-only
   STATUS      current
   DESCRIPTION
           "2: Disabled
            4: Operating"
   ::= { gs2352pLMC  54 }          
   
gs2352pLMCMonitoringStatus OBJECT-TYPE
   SYNTAX      INTEGER {Disabled(2), Operating(4)}
   MAX-ACCESS  read-only
   STATUS      current
   DESCRIPTION
           "2: Disabled
            4: Operating"
   ::= { gs2352pLMC  55 }
   
gs2352pLMCConfigurationSource OBJECT-TYPE
   SYNTAX      DisplayString
   MAX-ACCESS  read-only
   STATUS      current
   DESCRIPTION
           ""
   ::= { gs2352pLMC  56 }
   
gs2352pLMCConfigModified OBJECT-TYPE
   SYNTAX      INTEGER { No(0), Yes(1) }
   MAX-ACCESS  read-only
   STATUS      current
   DESCRIPTION
       "0: No
        1: Yes"
   ::= { gs2352pLMC 57 }
   
gs2352pLMCDeviceID OBJECT-TYPE
   SYNTAX      DisplayString
   MAX-ACCESS  read-only
   STATUS      current
   DESCRIPTION
           ""
   ::= { gs2352pLMC  58 }
   
gs2352pLMCRoundTripTime OBJECT-TYPE
   SYNTAX      INTEGER
   MAX-ACCESS  read-only
   STATUS      current
   DESCRIPTION
           ""
   ::= { gs2352pLMC  100 }
----------------------------------------------------------------------------------------------------------------------------
gs2352pSecurity                                              OBJECT IDENTIFIER ::= { lancomGS2352P 3 }

gs2352pIPSourceGuard                                         OBJECT IDENTIFIER ::= { gs2352pSecurity 1 }

gs2352pIPSourceGuardConf                                     OBJECT IDENTIFIER ::= { gs2352pIPSourceGuard 1 }

gs2352pIPSourceGuardMode OBJECT-TYPE
   SYNTAX      INTEGER { disable(0), enable(1) }
   MAX-ACCESS  read-write
   STATUS      current
   DESCRIPTION
       " default:  0
        0: disable
        1: enable"
   ::= { gs2352pIPSourceGuardConf 1 }

gs2352pIPSourceGuardPortConfigTable OBJECT-TYPE
   SYNTAX      SEQUENCE OF GS2352PIPSourceGuardPortConfigEntry
   MAX-ACCESS  not-accessible
   STATUS      current
   DESCRIPTION
       " "
   ::= { gs2352pIPSourceGuardConf 2 }

gs2352pIPSourceGuardPortConfigEntry OBJECT-TYPE
   SYNTAX      GS2352PIPSourceGuardPortConfigEntry
   MAX-ACCESS  not-accessible
   STATUS      current
   DESCRIPTION
       ""
   INDEX    { gs2352pIPSourceGuardPortConfigPort  }
   ::= { gs2352pIPSourceGuardPortConfigTable 1 }

GS2352PIPSourceGuardPortConfigEntry ::= SEQUENCE {
   gs2352pIPSourceGuardPortConfigPort               Integer32,
   gs2352pIPSourceGuardPortConfigMode               INTEGER,
   gs2352pIPSourceGuardPortMaxDynamicClients        Integer32
}

gs2352pIPSourceGuardPortConfigPort OBJECT-TYPE
   SYNTAX      Integer32(1..4095)
   MAX-ACCESS  not-accessible
   STATUS      current
   DESCRIPTION
       " "
   ::= { gs2352pIPSourceGuardPortConfigEntry 1 }

gs2352pIPSourceGuardPortConfigMode OBJECT-TYPE
   SYNTAX      INTEGER { disable(0), enable(1) }
   MAX-ACCESS  read-write
   STATUS      current
   DESCRIPTION
       "default: 0
       0:disable
       1:enable "
   ::= { gs2352pIPSourceGuardPortConfigEntry 2 }

gs2352pIPSourceGuardPortMaxDynamicClients OBJECT-TYPE
   SYNTAX      Integer32(0..2|99)
   MAX-ACCESS  read-write
   STATUS      current
   DESCRIPTION
       "default: 99
       0~2: Max Dynamic clients
       99:Unlimited "
   ::= { gs2352pIPSourceGuardPortConfigEntry 3 }


gs2352pIPSourceGuardStatic                                OBJECT IDENTIFIER ::= { gs2352pIPSourceGuard 2 }

gs2352pIPSourceGuardStaticCreate OBJECT-TYPE
   SYNTAX       INTEGER { none(0), create(1) }
   MAX-ACCESS   read-write
   STATUS       current
   DESCRIPTION
       "default: 0
        0 : None  (read only)
        1 : Create a IP Source Guard"
   ::= { gs2352pIPSourceGuardStatic 1 }

gs2352pIPSourceGuardStaticTable OBJECT-TYPE
   SYNTAX      SEQUENCE OF GS2352PIPSourceGuardStaticEntry
   MAX-ACCESS  not-accessible
   STATUS      current
   DESCRIPTION
       " "
   ::= { gs2352pIPSourceGuardStatic 2 }

gs2352pIPSourceGuardStaticEntry OBJECT-TYPE
   SYNTAX      GS2352PIPSourceGuardStaticEntry
   MAX-ACCESS  not-accessible
   STATUS      current
   DESCRIPTION
       ""
   INDEX    { gs2352pIPSourceGuardStaticIndex  }
   ::= { gs2352pIPSourceGuardStaticTable 1 }

GS2352PIPSourceGuardStaticEntry ::= SEQUENCE {
   gs2352pIPSourceGuardStaticIndex         Integer32,
   gs2352pIPSourceGuardStaticPort          Integer32,
   gs2352pIPSourceGuardStaticVLANId        Integer32,
   gs2352pIPSourceGuardStaticIPAddress     IpAddress,
   gs2352pIPSourceGuardStaticMACAddress    MacAddress,
   gs2352pIPSourceGuardStaticRowStatus     INTEGER
}

gs2352pIPSourceGuardStaticIndex OBJECT-TYPE
   SYNTAX      Integer32(1..28)
   MAX-ACCESS  not-accessible
   STATUS      current
   DESCRIPTION
       " "
   ::= { gs2352pIPSourceGuardStaticEntry 1 }

gs2352pIPSourceGuardStaticPort OBJECT-TYPE
   SYNTAX      Integer32(1..4095)
   MAX-ACCESS  read-write
   STATUS      current
   DESCRIPTION
       " Port, range: 1 - port number. "
   ::= { gs2352pIPSourceGuardStaticEntry 2 }

gs2352pIPSourceGuardStaticVLANId OBJECT-TYPE
   SYNTAX      Integer32(1..4094)
   MAX-ACCESS  read-write
   STATUS      current
   DESCRIPTION
       " VLAN ID, range: 1 - 4094. "
   ::= { gs2352pIPSourceGuardStaticEntry 3 }

gs2352pIPSourceGuardStaticIPAddress OBJECT-TYPE
   SYNTAX      IpAddress
   MAX-ACCESS  read-write
   STATUS      current
   DESCRIPTION
       " IP address allowed for doing IP source guard. "
   ::= { gs2352pIPSourceGuardStaticEntry 4 }

gs2352pIPSourceGuardStaticMACAddress OBJECT-TYPE
   SYNTAX      MacAddress
   MAX-ACCESS  read-write
   STATUS      current
   DESCRIPTION
       " Allowed Source MAC address, format 0a 1b 2c 3d 4e 5f "
   ::= { gs2352pIPSourceGuardStaticEntry 5 }

gs2352pIPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2352pIPSourceGuardStaticEntry 6 }

gs2352pIPSourceGuardDynamicTable OBJECT-TYPE
   SYNTAX      SEQUENCE OF GS2352PIPSourceGuardDynamicEntry
   MAX-ACCESS  not-accessible
   STATUS      current
   DESCRIPTION
       " "
   ::= { gs2352pIPSourceGuard 3 }

gs2352pIPSourceGuardDynamicEntry OBJECT-TYPE
   SYNTAX      GS2352PIPSourceGuardDynamicEntry
   MAX-ACCESS  not-accessible
   STATUS      current
   DESCRIPTION
       ""
   INDEX    { gs2352pIPSourceGuardDynamicIndex  }
   ::= { gs2352pIPSourceGuardDynamicTable 1 }

GS2352PIPSourceGuardDynamicEntry ::= SEQUENCE {
   gs2352pIPSourceGuardDynamicIndex          Integer32,
   gs2352pIPSourceGuardDynamicPort           Integer32,
   gs2352pIPSourceGuardDynamicVLANId         Integer32,
   gs2352pIPSourceGuardDynamicIPAddress      IpAddress,
   gs2352pIPSourceGuardDynamicMACAddress     MacAddress
}

gs2352pIPSourceGuardDynamicIndex OBJECT-TYPE
   SYNTAX      Integer32(1..4095)
   MAX-ACCESS  not-accessible
   STATUS      current
   DESCRIPTION
       " "
   ::= { gs2352pIPSourceGuardDynamicEntry 1 }

gs2352pIPSourceGuardDynamicPort OBJECT-TYPE
   SYNTAX      Integer32(1..10)
   MAX-ACCESS  read-only
   STATUS      current
   DESCRIPTION
       " "
   ::= { gs2352pIPSourceGuardDynamicEntry 2 }

gs2352pIPSourceGuardDynamicVLANId OBJECT-TYPE
   SYNTAX      Integer32(1..4094)
   MAX-ACCESS  read-only
   STATUS      current
   DESCRIPTION
       " "
   ::= { gs2352pIPSourceGuardDynamicEntry 3 }

gs2352pIPSourceGuardDynamicIPAddress OBJECT-TYPE
   SYNTAX      IpAddress
   MAX-ACCESS  read-only
   STATUS      current
   DESCRIPTION
       " "
   ::= { gs2352pIPSourceGuardDynamicEntry 4 }

gs2352pIPSourceGuardDynamicMACAddress OBJECT-TYPE
   SYNTAX      MacAddress
   MAX-ACCESS  read-only
   STATUS      current
   DESCRIPTION
       " "
   ::= { gs2352pIPSourceGuardDynamicEntry 5 }

gs2352pARPInspection                                         OBJECT IDENTIFIER ::= { gs2352pSecurity 2 }

gs2352pARPInspectionConf                                     OBJECT IDENTIFIER ::= { gs2352pARPInspection 1 }

gs2352pARPInspectionConfMode OBJECT-TYPE
   SYNTAX      INTEGER { disable(0), enable(1) }
   MAX-ACCESS  read-write
   STATUS      current
   DESCRIPTION
       "default: 0
        0: disable
        1: enable"
   ::= { gs2352pARPInspectionConf 1 }

gs2352pARPInspectionConfTable OBJECT-TYPE
   SYNTAX      SEQUENCE OF GS2352PARPInspectionConfEntry
   MAX-ACCESS  not-accessible
   STATUS      current
   DESCRIPTION
       " "
   ::= { gs2352pARPInspectionConf 2 }

gs2352pARPInspectionConfEntry OBJECT-TYPE
   SYNTAX      GS2352PARPInspectionConfEntry
   MAX-ACCESS  not-accessible
   STATUS      current
   DESCRIPTION
       ""
   INDEX    { gs2352pARPInspectionConfPortIndex  }
   ::= { gs2352pARPInspectionConfTable 1 }

GS2352PARPInspectionConfEntry ::= SEQUENCE {
   gs2352pARPInspectionConfPortIndex	Integer32,
   gs2352pARPInspectionConfPortMode	INTEGER
}

gs2352pARPInspectionConfPortIndex OBJECT-TYPE
   SYNTAX      Integer32(1..4095)
   MAX-ACCESS  not-accessible
   STATUS      current
   DESCRIPTION
       " "
   ::= { gs2352pARPInspectionConfEntry 1 }

gs2352pARPInspectionConfPortMode OBJECT-TYPE
   SYNTAX      INTEGER { disable(0), enable(1) }
   MAX-ACCESS  read-write
   STATUS      current
   DESCRIPTION
       "default: 0
        0: disable
        1: enable"
   ::= { gs2352pARPInspectionConfEntry 2 }


gs2352pARPInspectionStatic                                OBJECT IDENTIFIER ::= { gs2352pARPInspection 2 }

gs2352pARPInspectionStaticCreate OBJECT-TYPE
   SYNTAX      INTEGER { none(0), create(1) }
   MAX-ACCESS  read-write
   STATUS      current
   DESCRIPTION
       "default: 0
        0: none
        1: create"
   ::= { gs2352pARPInspectionStatic 1 }

gs2352pARPInspectionStaticTable OBJECT-TYPE
   SYNTAX      SEQUENCE OF GS2352PARPInspectionStaticEntry
   MAX-ACCESS  not-accessible
   STATUS      current
   DESCRIPTION
       " "
   ::= { gs2352pARPInspectionStatic 2 }

gs2352pARPInspectionStaticEntry OBJECT-TYPE
   SYNTAX      GS2352PARPInspectionStaticEntry
   MAX-ACCESS  not-accessible
   STATUS      current
   DESCRIPTION
       ""
   INDEX    { gs2352pARPInspectionStaticIndex  }
   ::= { gs2352pARPInspectionStaticTable 1 }

GS2352PARPInspectionStaticEntry ::= SEQUENCE {
   gs2352pARPInspectionStaticIndex       Integer32,
   gs2352pARPInspectionStaticPort        Integer32,
   gs2352pARPInspectionStaticVLANId      Integer32,
   gs2352pARPInspectionStaticIPAddress   IpAddress,
   gs2352pARPInspectionStaticMACAddress  MacAddress,
   gs2352pARPInspectionStaticRowStatus   INTEGER
}

gs2352pARPInspectionStaticIndex OBJECT-TYPE
   SYNTAX      Integer32(1..4095)
   MAX-ACCESS  not-accessible
   STATUS      current
   DESCRIPTION
       ""
   ::= { gs2352pARPInspectionStaticEntry 1 }

gs2352pARPInspectionStaticPort OBJECT-TYPE
   SYNTAX      Integer32(1..4095)
   MAX-ACCESS  read-write
   STATUS      current
   DESCRIPTION
       " Port, range: 1 - port number. "
   ::= { gs2352pARPInspectionStaticEntry 2 }

gs2352pARPInspectionStaticVLANId OBJECT-TYPE
   SYNTAX      Integer32(1..4094)
   MAX-ACCESS  read-write
   STATUS      current
   DESCRIPTION
       " VLAN ID, range: 1 - 4094. "
   ::= { gs2352pARPInspectionStaticEntry 3 }

gs2352pARPInspectionStaticIPAddress OBJECT-TYPE
   SYNTAX      IpAddress
   MAX-ACCESS  read-write
   STATUS      current
   DESCRIPTION
       " IP address allowed for doing ARP request. "
   ::= { gs2352pARPInspectionStaticEntry 4 }

gs2352pARPInspectionStaticMACAddress OBJECT-TYPE
   SYNTAX      MacAddress
   MAX-ACCESS  read-write
   STATUS      current
   DESCRIPTION
       " Allowed Source MAC address in ARP request packets, format 0a 1b 2c 3d 4e 5f "
   ::= { gs2352pARPInspectionStaticEntry 5 }

gs2352pARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2352pARPInspectionStaticEntry 6 }

gs2352pARPInspectionDynamicTable OBJECT-TYPE
   SYNTAX      SEQUENCE OF GS2352PARPInspectionDynamicEntry
   MAX-ACCESS  not-accessible
   STATUS      current
   DESCRIPTION
       " "
   ::= { gs2352pARPInspection 3 }

gs2352pARPInspectionDynamicEntry OBJECT-TYPE
   SYNTAX      GS2352PARPInspectionDynamicEntry
   MAX-ACCESS  not-accessible
   STATUS      current
   DESCRIPTION
       ""
   INDEX    { gs2352pARPInspectionDynamicIndex  }
   ::= { gs2352pARPInspectionDynamicTable 1 }

GS2352PARPInspectionDynamicEntry ::= SEQUENCE {
   gs2352pARPInspectionDynamicIndex          Integer32,
   gs2352pARPInspectionDynamicPort           Integer32,
   gs2352pARPInspectionDynamicVLANId         Integer32,
   gs2352pARPInspectionDynamicIPAddress      IpAddress,
   gs2352pARPInspectionDynamicMACAddress     MacAddress
}

gs2352pARPInspectionDynamicIndex OBJECT-TYPE
   SYNTAX      Integer32(1..4095)
   MAX-ACCESS  not-accessible
   STATUS      current
   DESCRIPTION
       " "
   ::= { gs2352pARPInspectionDynamicEntry 1 }

gs2352pARPInspectionDynamicPort OBJECT-TYPE
   SYNTAX      Integer32(1..4095)
   MAX-ACCESS  read-only
   STATUS      current
   DESCRIPTION
       ""
   ::= { gs2352pARPInspectionDynamicEntry 2 }

gs2352pARPInspectionDynamicVLANId OBJECT-TYPE
   SYNTAX      Integer32(1..4094)
   MAX-ACCESS  read-only
   STATUS      current
   DESCRIPTION
       ""
   ::= { gs2352pARPInspectionDynamicEntry 3 }

gs2352pARPInspectionDynamicIPAddress OBJECT-TYPE
   SYNTAX      IpAddress
   MAX-ACCESS  read-only
   STATUS      current
   DESCRIPTION
       ""
   ::= { gs2352pARPInspectionDynamicEntry 4 }

gs2352pARPInspectionDynamicMACAddress OBJECT-TYPE
   SYNTAX      MacAddress
   MAX-ACCESS  read-only
   STATUS      current
   DESCRIPTION
       ""
   ::= { gs2352pARPInspectionDynamicEntry 5 }

gs2352pARPStaticGatewayCtrl	                                OBJECT IDENTIFIER ::= { gs2352pARPInspection 6 }

gs2352pARPStaticGatewayCtrlSystemConf                                      OBJECT IDENTIFIER ::= { gs2352pARPStaticGatewayCtrl 1 }

gs2352pARPStaticGatewayCtrlMode OBJECT-TYPE
   SYNTAX      INTEGER { disable(0), enable(1) }
   MAX-ACCESS  read-write
   STATUS      current
   DESCRIPTION
       "default: 0
       0: disable
       1: enable "
   ::= { gs2352pARPStaticGatewayCtrlSystemConf 1 }

gs2352pARPStaticGatewayCtrlCreate OBJECT-TYPE
   SYNTAX      INTEGER { none(0), create(1) }
   MAX-ACCESS  read-write
   STATUS      current
   DESCRIPTION
       "default: 0
        0: none
        1: create"
   ::= { gs2352pARPStaticGatewayCtrl 2 }

gs2352pARPStaticGatewayCtrlTable OBJECT-TYPE
   SYNTAX      SEQUENCE OF GS2352PARPStaticGatewayCtrlEntry
   MAX-ACCESS  not-accessible
   STATUS      current
   DESCRIPTION
       " "
   ::= { gs2352pARPStaticGatewayCtrl 3 }

gs2352pARPStaticGatewayCtrlEntry OBJECT-TYPE
   SYNTAX      GS2352PARPStaticGatewayCtrlEntry
   MAX-ACCESS  not-accessible
   STATUS      current
   DESCRIPTION
       ""
   INDEX    { gs2352pARPStaticGatewayCtrlIndex  }
   ::= { gs2352pARPStaticGatewayCtrlTable 1 }

GS2352PARPStaticGatewayCtrlEntry ::= SEQUENCE {
   gs2352pARPStaticGatewayCtrlIndex       Integer32,
   gs2352pARPStaticGatewayCtrlIPAddress   IpAddress,
   gs2352pARPStaticGatewayCtrlMACAddress  MacAddress,
   gs2352pARPStaticGatewayCtrlPort        Integer32,
   gs2352pARPStaticGatewayCtrlAction      INTEGER,
   gs2352pARPStaticGatewayCtrlState       DisplayString,
   gs2352pARPStaticGatewayCtrlReOpen      INTEGER,
   gs2352pARPStaticGatewayCtrlRowStatus   INTEGER
}

gs2352pARPStaticGatewayCtrlIndex OBJECT-TYPE
   SYNTAX      Integer32(1..4)
   MAX-ACCESS  not-accessible
   STATUS      current
   DESCRIPTION
       ""
   ::= { gs2352pARPStaticGatewayCtrlEntry 1 }

gs2352pARPStaticGatewayCtrlIPAddress OBJECT-TYPE
   SYNTAX      IpAddress
   MAX-ACCESS  read-write
   STATUS      current
   DESCRIPTION
       " Source IP address. "
   ::= { gs2352pARPStaticGatewayCtrlEntry 2 }

gs2352pARPStaticGatewayCtrlMACAddress OBJECT-TYPE
   SYNTAX      MacAddress
   MAX-ACCESS  read-write
   STATUS      current
   DESCRIPTION
       " Source MAC address , format 0a 1b 2c 3d 4e 5f "
   ::= { gs2352pARPStaticGatewayCtrlEntry 3 }

gs2352pARPStaticGatewayCtrlPort OBJECT-TYPE
   SYNTAX      Integer32(1..4095)
   MAX-ACCESS  read-write
   STATUS      current
   DESCRIPTION
       " Port, range: 1 - port number. "
   ::= { gs2352pARPStaticGatewayCtrlEntry 4 }

gs2352pARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2352pARPStaticGatewayCtrlEntry 5 }

gs2352pARPStaticGatewayCtrlState OBJECT-TYPE
   SYNTAX      DisplayString
   MAX-ACCESS  read-only
   STATUS      current
   DESCRIPTION
       ""
   ::= { gs2352pARPStaticGatewayCtrlEntry 6 }

gs2352pARPStaticGatewayCtrlReOpen OBJECT-TYPE
   SYNTAX      INTEGER { none(0), reopen(1) }
   MAX-ACCESS  read-write
   STATUS      current
   DESCRIPTION
       "default: 0
       0: none
       1: reopen"
   ::= { gs2352pARPStaticGatewayCtrlEntry 7 }  
   
gs2352pARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2352pARPStaticGatewayCtrlEntry 8 }

gs2352pARPSpoofingPrevention	                                OBJECT IDENTIFIER ::= { gs2352pARPInspection 7 }

gs2352pARPSpoofingPreventionSystemConf                                      OBJECT IDENTIFIER ::= { gs2352pARPSpoofingPrevention 1 }

gs2352pARPSpoofingPreventionMode OBJECT-TYPE
   SYNTAX      INTEGER { disable(0), enable(1) }
   MAX-ACCESS  read-write
   STATUS      current
   DESCRIPTION
       "default: 0
       0: disable
       1: enable "
   ::= { gs2352pARPSpoofingPreventionSystemConf 1 }

gs2352pARPSpoofingPreventionTable OBJECT-TYPE
   SYNTAX      SEQUENCE OF GS2352PARPSpoofingPreventionEntry
   MAX-ACCESS  not-accessible
   STATUS      current
   DESCRIPTION
       " "
   ::= { gs2352pARPSpoofingPrevention 2 }

gs2352pARPSpoofingPreventionEntry OBJECT-TYPE
   SYNTAX      GS2352PARPSpoofingPreventionEntry
   MAX-ACCESS  not-accessible
   STATUS      current
   DESCRIPTION
       ""
   INDEX    { gs2352pARPSpoofingPreventionPort  }
   ::= { gs2352pARPSpoofingPreventionTable 1 }

GS2352PARPSpoofingPreventionEntry ::= SEQUENCE {
   gs2352pARPSpoofingPreventionPort           Integer32,
   gs2352pARPSpoofingPreventionPortMode       INTEGER,
   gs2352pARPSpoofingPreventionPortLimit      Integer32,
   gs2352pARPSpoofingPreventionPortAction     INTEGER,
   gs2352pARPSpoofingPreventionPortState      DisplayString,
   gs2352pARPSpoofingPreventionPortReOpen     INTEGER
}

gs2352pARPSpoofingPreventionPort OBJECT-TYPE
   SYNTAX      Integer32(1..4095)
   MAX-ACCESS  not-accessible
   STATUS      current
   DESCRIPTION
       " "
   ::= { gs2352pARPSpoofingPreventionEntry 1 }

gs2352pARPSpoofingPreventionPortMode OBJECT-TYPE
   SYNTAX      INTEGER { disable(0), enable(1) }
   MAX-ACCESS  read-write
   STATUS      current
   DESCRIPTION
       "default: 0
       0: disable
       1: enable"
   ::= { gs2352pARPSpoofingPreventionEntry 2 }

gs2352pARPSpoofingPreventionPortLimit OBJECT-TYPE
   SYNTAX      Integer32(1..100)
   MAX-ACCESS  read-write
   STATUS      current
   DESCRIPTION
       "default: 1, range: 1-100"
   ::= { gs2352pARPSpoofingPreventionEntry 3 }

gs2352pARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2352pARPSpoofingPreventionEntry 4 }

gs2352pARPSpoofingPreventionPortState OBJECT-TYPE
   SYNTAX      DisplayString
   MAX-ACCESS  read-only
   STATUS      current
   DESCRIPTION
       ""
   ::= { gs2352pARPSpoofingPreventionEntry 5 }

gs2352pARPSpoofingPreventionPortReOpen OBJECT-TYPE
   SYNTAX      INTEGER { none(0), reopen(1) }
   MAX-ACCESS  read-write
   STATUS      current
   DESCRIPTION
       "default: 0
       0: none
       1: reopen"
   ::= { gs2352pARPSpoofingPreventionEntry 6 }  

gs2352pARPIPDoSPrevention	                                OBJECT IDENTIFIER ::= { gs2352pARPInspection 8 }

gs2352pARPIPDoSPreventionTCPMode OBJECT-TYPE
   SYNTAX      INTEGER { disable(0), enable(1) }
   MAX-ACCESS  read-write
   STATUS      current
   DESCRIPTION
       "default: 0
       0: disable
       1: enable "
   ::= { gs2352pARPIPDoSPrevention 1 }

gs2352pARPIPDoSPreventionUDPMode OBJECT-TYPE
   SYNTAX      INTEGER { disable(0), enable(1) }
   MAX-ACCESS  read-write
   STATUS      current
   DESCRIPTION
       "default: 0
       0: disable
       1: enable "
   ::= { gs2352pARPIPDoSPrevention 2 }
   
gs2352pARPIPDoSPreventionICMPMode OBJECT-TYPE
   SYNTAX      INTEGER { disable(0), enable(1) }
   MAX-ACCESS  read-write
   STATUS      current
   DESCRIPTION
       "default: 0
       0: disable
       1: enable "
   ::= { gs2352pARPIPDoSPrevention 3 }   

gs2352pARPIPDoSPreventionServerPort1 OBJECT-TYPE
   SYNTAX      Integer32(0..4094)
   MAX-ACCESS  read-write
   STATUS      current
   DESCRIPTION
       " Port, range: 0 - port number. 0: none. "
   ::= { gs2352pARPIPDoSPrevention 4 }  

gs2352pARPIPDoSPreventionServerPort2 OBJECT-TYPE
   SYNTAX      Integer32(0..4094)
   MAX-ACCESS  read-write
   STATUS      current
   DESCRIPTION
       " Port, range: 0 - port number. 0: none. "
   ::= { gs2352pARPIPDoSPrevention 5 }  
   
gs2352pARPIPDoSPreventionServerPort3 OBJECT-TYPE
   SYNTAX      Integer32(0..4094)
   MAX-ACCESS  read-write
   STATUS      current
   DESCRIPTION
       " Port, range: 0 - port number. 0: none. "
   ::= { gs2352pARPIPDoSPrevention 6 }  
   
gs2352pARPIPDoSPreventionServerPort4 OBJECT-TYPE
   SYNTAX      Integer32(0..4094)
   MAX-ACCESS  read-write
   STATUS      current
   DESCRIPTION
       " Port, range: 0 - port number. 0: none. "
   ::= { gs2352pARPIPDoSPrevention 7 }        

gs2352pDHCPSnooping                                          OBJECT IDENTIFIER ::= { gs2352pSecurity 3 }

gs2352pDHCPSnoopingConf                                          OBJECT IDENTIFIER ::= { gs2352pDHCPSnooping 1 }

gs2352pDHCPSnoopingMode OBJECT-TYPE
   SYNTAX      INTEGER { disable(0), enable(1) }
   MAX-ACCESS  read-write
   STATUS      current
   DESCRIPTION
       "default: 0
       0: disable
       1: enable"
   ::= { gs2352pDHCPSnoopingConf 1 }

gs2352pDHCPSnoopingPortModeConfigurationTable OBJECT-TYPE
   SYNTAX      SEQUENCE OF GS2352PDHCPSnoopingPortModeConfigurationEntry
   MAX-ACCESS  not-accessible
   STATUS      current
   DESCRIPTION
       " "
   ::= { gs2352pDHCPSnoopingConf 2 }

gs2352pDHCPSnoopingPortModeConfigurationEntry OBJECT-TYPE
   SYNTAX      GS2352PDHCPSnoopingPortModeConfigurationEntry
   MAX-ACCESS  not-accessible
   STATUS      current
   DESCRIPTION
       ""
   INDEX    { gs2352pDHCPSnoopingPortModeConfigurationPort  }
   ::= { gs2352pDHCPSnoopingPortModeConfigurationTable 1 }
   
GS2352PDHCPSnoopingPortModeConfigurationEntry ::= SEQUENCE {
   gs2352pDHCPSnoopingPortModeConfigurationPort	Integer32,
   gs2352pDHCPSnoopingPortModeConfigurationMode	INTEGER
}

gs2352pDHCPSnoopingPortModeConfigurationPort OBJECT-TYPE
   SYNTAX      Integer32(1..4095)
   MAX-ACCESS  not-accessible
   STATUS      current
   DESCRIPTION
       " "
   ::= { gs2352pDHCPSnoopingPortModeConfigurationEntry 1 }

gs2352pDHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2352pDHCPSnoopingPortModeConfigurationEntry 2 }

gs2352pDHCPSnoopingStatisticsTable OBJECT-TYPE
   SYNTAX      SEQUENCE OF GS2352PDHCPSnoopingStatisticsEntry
   MAX-ACCESS  not-accessible
   STATUS      current
   DESCRIPTION
       " "
   ::= { gs2352pDHCPSnooping 2 }

gs2352pDHCPSnoopingStatisticsEntry OBJECT-TYPE
   SYNTAX      GS2352PDHCPSnoopingStatisticsEntry
   MAX-ACCESS  not-accessible
   STATUS      current
   DESCRIPTION
       ""
   INDEX    { gs2352pDHCPSnoopingStatisticsPort  }
   ::= { gs2352pDHCPSnoopingStatisticsTable 1 }

GS2352PDHCPSnoopingStatisticsEntry ::= SEQUENCE {
   gs2352pDHCPSnoopingStatisticsPort         Integer32,
   gs2352pDHCPSnoopingStatisticsClear        INTEGER,
   gs2352pDHCPSnoopingRxDiscover             Counter32,
   gs2352pDHCPSnoopingRxOffer                Counter32,
   gs2352pDHCPSnoopingRxRequest              Counter32,
   gs2352pDHCPSnoopingRxDecline              Counter32,
   gs2352pDHCPSnoopingRxACK                  Counter32,
   gs2352pDHCPSnoopingRxNAK                  Counter32,
   gs2352pDHCPSnoopingRxRelease              Counter32,
   gs2352pDHCPSnoopingRxInform               Counter32,
   gs2352pDHCPSnoopingRxLeaseQuery           Counter32,
   gs2352pDHCPSnoopingRxLeaseUnassigned      Counter32,
   gs2352pDHCPSnoopingRxLeaseUnknown         Counter32,
   gs2352pDHCPSnoopingRxLeaseActive          Counter32,
   gs2352pDHCPSnoopingTxDiscover             Counter32,
   gs2352pDHCPSnoopingTxOffer                Counter32,
   gs2352pDHCPSnoopingTxRequest              Counter32,
   gs2352pDHCPSnoopingTxDecline              Counter32,
   gs2352pDHCPSnoopingTxACK                  Counter32,
   gs2352pDHCPSnoopingTxNAK                  Counter32,
   gs2352pDHCPSnoopingTxRelease              Counter32,
   gs2352pDHCPSnoopingTxInform               Counter32,
   gs2352pDHCPSnoopingTxLeaseQuery           Counter32,
   gs2352pDHCPSnoopingTxLeaseUnassigned      Counter32,
   gs2352pDHCPSnoopingTxLeaseUnknown         Counter32,
   gs2352pDHCPSnoopingTxLeaseActive          Counter32
}

gs2352pDHCPSnoopingStatisticsPort OBJECT-TYPE
   SYNTAX      Integer32(1..4095)
   MAX-ACCESS  not-accessible
   STATUS      current
   DESCRIPTION
       " "
   ::= { gs2352pDHCPSnoopingStatisticsEntry 1 }

gs2352pDHCPSnoopingStatisticsClear OBJECT-TYPE
   SYNTAX      INTEGER { none(0), clear(1) }
   MAX-ACCESS  read-write
   STATUS      current
   DESCRIPTION
       "default: 0
       0: none
       1: clear"
   ::= { gs2352pDHCPSnoopingStatisticsEntry 2 }
   
gs2352pDHCPSnoopingRxDiscover OBJECT-TYPE
   SYNTAX      Counter32
   MAX-ACCESS  read-only
   STATUS      current
   DESCRIPTION
       " "
   ::= { gs2352pDHCPSnoopingStatisticsEntry 3 }

gs2352pDHCPSnoopingRxOffer OBJECT-TYPE
   SYNTAX      Counter32
   MAX-ACCESS  read-only
   STATUS      current
   DESCRIPTION
       " "
   ::= { gs2352pDHCPSnoopingStatisticsEntry 4 }

gs2352pDHCPSnoopingRxRequest OBJECT-TYPE
   SYNTAX      Counter32
   MAX-ACCESS  read-only
   STATUS      current
   DESCRIPTION
       " "
   ::= { gs2352pDHCPSnoopingStatisticsEntry 5 }

gs2352pDHCPSnoopingRxDecline OBJECT-TYPE
   SYNTAX      Counter32
   MAX-ACCESS  read-only
   STATUS      current
   DESCRIPTION
       " "
   ::= { gs2352pDHCPSnoopingStatisticsEntry 6 }

gs2352pDHCPSnoopingRxACK OBJECT-TYPE
   SYNTAX      Counter32
   MAX-ACCESS  read-only
   STATUS      current
   DESCRIPTION
       " "
   ::= { gs2352pDHCPSnoopingStatisticsEntry 7 }

gs2352pDHCPSnoopingRxNAK OBJECT-TYPE
   SYNTAX      Counter32
   MAX-ACCESS  read-only
   STATUS      current
   DESCRIPTION
       " "
   ::= { gs2352pDHCPSnoopingStatisticsEntry 8 }   

gs2352pDHCPSnoopingRxRelease OBJECT-TYPE
   SYNTAX      Counter32
   MAX-ACCESS  read-only
   STATUS      current
   DESCRIPTION
       " "
   ::= { gs2352pDHCPSnoopingStatisticsEntry 9 }

gs2352pDHCPSnoopingRxInform OBJECT-TYPE
   SYNTAX      Counter32
   MAX-ACCESS  read-only
   STATUS      current
   DESCRIPTION
       " "
   ::= { gs2352pDHCPSnoopingStatisticsEntry 10 }

gs2352pDHCPSnoopingRxLeaseQuery OBJECT-TYPE
   SYNTAX      Counter32
   MAX-ACCESS  read-only
   STATUS      current
   DESCRIPTION
       " "
   ::= { gs2352pDHCPSnoopingStatisticsEntry 11 }

gs2352pDHCPSnoopingRxLeaseUnassigned OBJECT-TYPE
   SYNTAX      Counter32
   MAX-ACCESS  read-only
   STATUS      current
   DESCRIPTION
       " "
   ::= { gs2352pDHCPSnoopingStatisticsEntry 12 }

gs2352pDHCPSnoopingRxLeaseUnknown OBJECT-TYPE
   SYNTAX      Counter32
   MAX-ACCESS  read-only
   STATUS      current
   DESCRIPTION
       " "
   ::= { gs2352pDHCPSnoopingStatisticsEntry 13 }

gs2352pDHCPSnoopingRxLeaseActive OBJECT-TYPE
   SYNTAX      Counter32
   MAX-ACCESS  read-only
   STATUS      current
   DESCRIPTION
       " "
   ::= { gs2352pDHCPSnoopingStatisticsEntry 14 }

gs2352pDHCPSnoopingTxDiscover OBJECT-TYPE
   SYNTAX      Counter32
   MAX-ACCESS  read-only
   STATUS      current
   DESCRIPTION
       " "
   ::= { gs2352pDHCPSnoopingStatisticsEntry 15 }

gs2352pDHCPSnoopingTxOffer OBJECT-TYPE
   SYNTAX      Counter32
   MAX-ACCESS  read-only
   STATUS      current
   DESCRIPTION
       " "
   ::= { gs2352pDHCPSnoopingStatisticsEntry 16 }

gs2352pDHCPSnoopingTxRequest OBJECT-TYPE
   SYNTAX      Counter32
   MAX-ACCESS  read-only
   STATUS      current
   DESCRIPTION
       " "
   ::= { gs2352pDHCPSnoopingStatisticsEntry 17 }

gs2352pDHCPSnoopingTxDecline OBJECT-TYPE
   SYNTAX      Counter32
   MAX-ACCESS  read-only
   STATUS      current
   DESCRIPTION
       " "
   ::= { gs2352pDHCPSnoopingStatisticsEntry 18 }

gs2352pDHCPSnoopingTxACK OBJECT-TYPE
   SYNTAX      Counter32
   MAX-ACCESS  read-only
   STATUS      current
   DESCRIPTION
       " "
   ::= { gs2352pDHCPSnoopingStatisticsEntry 19 }

gs2352pDHCPSnoopingTxNAK OBJECT-TYPE
   SYNTAX      Counter32
   MAX-ACCESS  read-only
   STATUS      current
   DESCRIPTION
       " "
   ::= { gs2352pDHCPSnoopingStatisticsEntry 20 }   

gs2352pDHCPSnoopingTxRelease OBJECT-TYPE
   SYNTAX      Counter32
   MAX-ACCESS  read-only
   STATUS      current
   DESCRIPTION
       " "
   ::= { gs2352pDHCPSnoopingStatisticsEntry 21 }

gs2352pDHCPSnoopingTxInform OBJECT-TYPE
   SYNTAX      Counter32
   MAX-ACCESS  read-only
   STATUS      current
   DESCRIPTION
       " "
   ::= { gs2352pDHCPSnoopingStatisticsEntry 22 }

gs2352pDHCPSnoopingTxLeaseQuery OBJECT-TYPE
   SYNTAX      Counter32
   MAX-ACCESS  read-only
   STATUS      current
   DESCRIPTION
       " "
   ::= { gs2352pDHCPSnoopingStatisticsEntry 23 }

gs2352pDHCPSnoopingTxLeaseUnassigned OBJECT-TYPE
   SYNTAX      Counter32
   MAX-ACCESS  read-only
   STATUS      current
   DESCRIPTION
       " "
   ::= { gs2352pDHCPSnoopingStatisticsEntry 24 }

gs2352pDHCPSnoopingTxLeaseUnknown OBJECT-TYPE
   SYNTAX      Counter32
   MAX-ACCESS  read-only
   STATUS      current
   DESCRIPTION
       " "
   ::= { gs2352pDHCPSnoopingStatisticsEntry 25 }

gs2352pDHCPSnoopingTxLeaseActive OBJECT-TYPE
   SYNTAX      Counter32
   MAX-ACCESS  read-only
   STATUS      current
   DESCRIPTION
       " "
   ::= { gs2352pDHCPSnoopingStatisticsEntry 26 }


gs2352pDHCPRelay                                             OBJECT IDENTIFIER ::= { gs2352pSecurity 4 }

gs2352pDHCPRelayConfiguration                                         OBJECT IDENTIFIER ::= { gs2352pDHCPRelay 1 }

gs2352pDHCPRelayMode OBJECT-TYPE
   SYNTAX      INTEGER { disable(0), enable(1) }
   MAX-ACCESS  read-write
   STATUS      current
   DESCRIPTION
       "default: 0
       0: disable
       1: enable 
       We need at least one server"
   ::= { gs2352pDHCPRelayConfiguration 1 }

gs2352pDHCPRelayServer OBJECT-TYPE
   SYNTAX      IpAddress
   MAX-ACCESS  read-write
   STATUS      current
   DESCRIPTION
       " "
   ::= { gs2352pDHCPRelayConfiguration 2 }

gs2352pDHCPRelayInformationMode OBJECT-TYPE
   SYNTAX      INTEGER { disable(0), enable(1) }
   MAX-ACCESS  read-write
   STATUS      current
   DESCRIPTION
       "default: 0
       0: disable
       1: enable "
   ::= { gs2352pDHCPRelayConfiguration 3 }

gs2352pDHCPRelayInformationPolicy OBJECT-TYPE
   SYNTAX      INTEGER { replace(0), keep(1), drop(2) }
   MAX-ACCESS  read-write
   STATUS      current
   DESCRIPTION
       "default: 0
       0: replace
       1: keep
       2: drop "
   ::= { gs2352pDHCPRelayConfiguration 4 }

gs2352pDHCPRelayInformationCustom OBJECT-TYPE
   SYNTAX      DisplayString(SIZE(0..32))
   MAX-ACCESS  read-write
   STATUS      current
   DESCRIPTION
       "DHCP Option 82 Circuit ID custom information"
   ::= { gs2352pDHCPRelayConfiguration 1500 }

gs2352pDHCPRelayConfigurationGateways                                          OBJECT IDENTIFIER ::= { gs2352pDHCPRelayConfiguration 5 }

gs2352pDHCPRelayConfigurationGatewaysCreate OBJECT-TYPE
   SYNTAX       INTEGER { none(0), create(1) }
   MAX-ACCESS   read-write
   STATUS       current
   DESCRIPTION
       "default: 0
        0 : None  (read only)
        1 : Create entry"
   ::= { gs2352pDHCPRelayConfigurationGateways 1 }

gs2352pDHCPRelayConfigurationGatewaysTable OBJECT-TYPE
   SYNTAX      SEQUENCE OF Gs2352pDHCPRelayConfigurationGatewaysEntry
   MAX-ACCESS  not-accessible
   STATUS      current
   DESCRIPTION
       " Create DHCP Relay Gateway IP address entry."
   ::= { gs2352pDHCPRelayConfigurationGateways 2 }

gs2352pDHCPRelayConfigurationGatewaysEntry OBJECT-TYPE
   SYNTAX      Gs2352pDHCPRelayConfigurationGatewaysEntry
   MAX-ACCESS  not-accessible
   STATUS      current
   DESCRIPTION
       ""
   INDEX    { gs2352pDHCPRelayConfigurationGatewaysIndex  }
   ::= { gs2352pDHCPRelayConfigurationGatewaysTable 1 }

Gs2352pDHCPRelayConfigurationGatewaysEntry ::= SEQUENCE {
   gs2352pDHCPRelayConfigurationGatewaysIndex           Integer32,
   gs2352pDHCPRelayConfigurationGatewaysVLANId          Integer32,
   gs2352pDHCPRelayConfigurationGatewaysIP              IpAddress,
   gs2352pDHCPRelayConfigurationGatewaysRowStatus       INTEGER
}

gs2352pDHCPRelayConfigurationGatewaysIndex OBJECT-TYPE
   SYNTAX      Integer32(1..6)
   MAX-ACCESS  not-accessible
   STATUS      current
   DESCRIPTION
       " "
   ::= { gs2352pDHCPRelayConfigurationGatewaysEntry 1 }

gs2352pDHCPRelayConfigurationGatewaysVLANId OBJECT-TYPE
   SYNTAX      Integer32(1..4094)
   MAX-ACCESS  read-write
   STATUS      current
   DESCRIPTION
       " VLAN ID "
   ::= { gs2352pDHCPRelayConfigurationGatewaysEntry 2 }

gs2352pDHCPRelayConfigurationGatewaysIP OBJECT-TYPE
   SYNTAX      IpAddress
   MAX-ACCESS  read-write
   STATUS      current
   DESCRIPTION
       "DHCP GIADDR address."
   ::= { gs2352pDHCPRelayConfigurationGatewaysEntry 3 }
   
gs2352pDHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2352pDHCPRelayConfigurationGatewaysEntry 4 }


gs2352pDHCPRelayStatistics                                   OBJECT IDENTIFIER ::= { gs2352pDHCPRelay 2 }

gs2352pDHCPRelayServerStatistics                                   OBJECT IDENTIFIER ::= { gs2352pDHCPRelayStatistics 1 }

gs2352pServerStatTransmitToServer OBJECT-TYPE
   SYNTAX      Counter32
   MAX-ACCESS  read-only
   STATUS      current
   DESCRIPTION
       " "
   ::= { gs2352pDHCPRelayServerStatistics 1 }

gs2352pServerStatTransmitError OBJECT-TYPE
   SYNTAX      Counter32
   MAX-ACCESS  read-only
   STATUS      current
   DESCRIPTION
       " "
   ::= { gs2352pDHCPRelayServerStatistics 2 }

gs2352pServerStatReceiveFromServer OBJECT-TYPE
   SYNTAX      Counter32
   MAX-ACCESS  read-only
   STATUS      current
   DESCRIPTION
       " "
   ::= { gs2352pDHCPRelayServerStatistics 3 }

gs2352pServerStatReceiveMissingAgentOption OBJECT-TYPE
   SYNTAX      Counter32
   MAX-ACCESS  read-only
   STATUS      current
   DESCRIPTION
       " "
   ::= { gs2352pDHCPRelayServerStatistics 4 }

gs2352pServerStatReceiveMissingCircuitID OBJECT-TYPE
   SYNTAX      Counter32
   MAX-ACCESS  read-only
   STATUS      current
   DESCRIPTION
       " "
   ::= { gs2352pDHCPRelayServerStatistics 5 }

gs2352pServerStatReceiveMissingRemoteID OBJECT-TYPE
   SYNTAX      Counter32
   MAX-ACCESS  read-only
   STATUS      current
   DESCRIPTION
       " "
   ::= { gs2352pDHCPRelayServerStatistics 6 }

gs2352pServerStatReceiveBadCircuitID OBJECT-TYPE
   SYNTAX      Counter32
   MAX-ACCESS  read-only
   STATUS      current
   DESCRIPTION
       " "
   ::= { gs2352pDHCPRelayServerStatistics 7 }

gs2352pServerStatReceiveBadRemoteID OBJECT-TYPE
   SYNTAX      Counter32
   MAX-ACCESS  read-only
   STATUS      current
   DESCRIPTION
       " "
   ::= { gs2352pDHCPRelayServerStatistics 8 }

gs2352pDHCPRelayClientStatistics                                   OBJECT IDENTIFIER ::= { gs2352pDHCPRelayStatistics 2 }

gs2352pClientStatTransmitToClient OBJECT-TYPE
   SYNTAX      Counter32
   MAX-ACCESS  read-only
   STATUS      current
   DESCRIPTION
       " "
   ::= { gs2352pDHCPRelayClientStatistics 1 }

gs2352pClientStatTransmitError OBJECT-TYPE
   SYNTAX      Counter32
   MAX-ACCESS  read-only
   STATUS      current
   DESCRIPTION
       " "
   ::= { gs2352pDHCPRelayClientStatistics 2 }

gs2352pClientStatReceivefromClient OBJECT-TYPE
   SYNTAX      Counter32
   MAX-ACCESS  read-only
   STATUS      current
   DESCRIPTION
       " "
   ::= { gs2352pDHCPRelayClientStatistics 3 }

gs2352pClientStatReceiveAgentOption OBJECT-TYPE
   SYNTAX      Counter32
   MAX-ACCESS  read-only
   STATUS      current
   DESCRIPTION
       " "
   ::= { gs2352pDHCPRelayClientStatistics 4 }

gs2352pClientStatReplaceAgentOption OBJECT-TYPE
   SYNTAX      Counter32
   MAX-ACCESS  read-only
   STATUS      current
   DESCRIPTION
       " "
   ::= { gs2352pDHCPRelayClientStatistics 5 }

gs2352pClientStatKeepAgentOption OBJECT-TYPE
   SYNTAX      Counter32
   MAX-ACCESS  read-only
   STATUS      current
   DESCRIPTION
       " "
   ::= { gs2352pDHCPRelayClientStatistics 6 }

gs2352pClientStatDropAgentOption OBJECT-TYPE
   SYNTAX      Counter32
   MAX-ACCESS  read-only
   STATUS      current
   DESCRIPTION
       " "
   ::= { gs2352pDHCPRelayClientStatistics 7 }

gs2352pPortSecurity                                          OBJECT IDENTIFIER ::= { gs2352pSecurity 5 }

gs2352pPortSecLimitCtrl                                      OBJECT IDENTIFIER ::= { gs2352pPortSecurity 1 }

gs2352pPortSecLimitCtrlSystemConf                                      OBJECT IDENTIFIER ::= { gs2352pPortSecLimitCtrl 1 }

gs2352pPortSecurityMode OBJECT-TYPE
   SYNTAX      INTEGER { disable(0), enable(1) }
   MAX-ACCESS  read-write
   STATUS      current
   DESCRIPTION
       "default: 0
       0: disable
       1: enable "
   ::= { gs2352pPortSecLimitCtrlSystemConf 1 }

gs2352pPortSecurityAging OBJECT-TYPE
   SYNTAX      INTEGER { disable(0), enable(1) }
   MAX-ACCESS  read-write
   STATUS      current
   DESCRIPTION
       "default: 0
       0: disable
       1: enable "
   ::= { gs2352pPortSecLimitCtrlSystemConf 2 }

gs2352pPortSecurityAgingPeriod OBJECT-TYPE
   SYNTAX      INTEGER(10..10000000)
   MAX-ACCESS  read-write
   STATUS      current
   DESCRIPTION
       "default: 3600, range: 10-10000000 "
   ::= { gs2352pPortSecLimitCtrlSystemConf 3 }

gs2352pPortSecLimitCtrlTable OBJECT-TYPE
   SYNTAX      SEQUENCE OF GS2352PPortSecLimitCtrlEntry
   MAX-ACCESS  not-accessible
   STATUS      current
   DESCRIPTION
       " "
   ::= { gs2352pPortSecLimitCtrl 2 }

gs2352pPortSecLimitCtrlEntry OBJECT-TYPE
   SYNTAX      GS2352PPortSecLimitCtrlEntry
   MAX-ACCESS  not-accessible
   STATUS      current
   DESCRIPTION
       ""
   INDEX    { gs2352pPortSecLimitCtrlPort  }
   ::= { gs2352pPortSecLimitCtrlTable 1 }

GS2352PPortSecLimitCtrlEntry ::= SEQUENCE {
   gs2352pPortSecLimitCtrlPort           Integer32,
   gs2352pPortSecLimitCtrlPortMode       INTEGER,
   gs2352pPortSecLimitCtrlPortLimit      Integer32,
   gs2352pPortSecLimitCtrlPortAction     INTEGER,
   gs2352pPortSecLimitCtrlPortState      DisplayString,
   gs2352pPortSecLimitCtrlPortReOpen     INTEGER
}

gs2352pPortSecLimitCtrlPort OBJECT-TYPE
   SYNTAX      Integer32(1..4095)
   MAX-ACCESS  not-accessible
   STATUS      current
   DESCRIPTION
       " "
   ::= { gs2352pPortSecLimitCtrlEntry 1 }

gs2352pPortSecLimitCtrlPortMode OBJECT-TYPE
   SYNTAX      INTEGER { disable(0), enable(1) }
   MAX-ACCESS  read-write
   STATUS      current
   DESCRIPTION
       "default: 0
       0: disable
       1: enable"
   ::= { gs2352pPortSecLimitCtrlEntry 2 }

gs2352pPortSecLimitCtrlPortLimit OBJECT-TYPE
   SYNTAX      Integer32(1..1024)
   MAX-ACCESS  read-write
   STATUS      current
   DESCRIPTION
       "default: 4, range: 1-1024"
   ::= { gs2352pPortSecLimitCtrlEntry 3 }

gs2352pPortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2352pPortSecLimitCtrlEntry 4 }

gs2352pPortSecLimitCtrlPortState OBJECT-TYPE
   SYNTAX      DisplayString
   MAX-ACCESS  read-only
   STATUS      current
   DESCRIPTION
       ""
   ::= { gs2352pPortSecLimitCtrlEntry 5 }

gs2352pPortSecLimitCtrlPortReOpen OBJECT-TYPE
   SYNTAX      INTEGER { none(0), reopen(1) }
   MAX-ACCESS  read-write
   STATUS      current
   DESCRIPTION
       "default: 0
       0: none
       1: reopen"
   ::= { gs2352pPortSecLimitCtrlEntry 6 }

gs2352pPortSecSwitchStatusTable OBJECT-TYPE
   SYNTAX      SEQUENCE OF GS2352PPortSecSwitchStatusEntry
   MAX-ACCESS  not-accessible
   STATUS      current
   DESCRIPTION
       " "
   ::= { gs2352pPortSecurity 2 }

gs2352pPortSecSwitchStatusEntry OBJECT-TYPE
   SYNTAX      GS2352PPortSecSwitchStatusEntry
   MAX-ACCESS  not-accessible
   STATUS      current
   DESCRIPTION
       ""
   INDEX    { gs2352pPortSecSwitchStatusPort  }
   ::= { gs2352pPortSecSwitchStatusTable 1 }

GS2352PPortSecSwitchStatusEntry ::= SEQUENCE {
   gs2352pPortSecSwitchStatusPort                Integer32,
   gs2352pPortSecSwitchStatusUsers               DisplayString,
   gs2352pPortSecSwitchStatusState               DisplayString,
   gs2352pPortSecSwitchStatusMACCountCurrent     Integer32,
   gs2352pPortSecSwitchStatusMACCountLimit       Integer32
}

gs2352pPortSecSwitchStatusPort OBJECT-TYPE
   SYNTAX      Integer32(1..4095)
   MAX-ACCESS  not-accessible
   STATUS      current
   DESCRIPTION
       " "
   ::= { gs2352pPortSecSwitchStatusEntry 1 }

gs2352pPortSecSwitchStatusUsers OBJECT-TYPE
   SYNTAX      DisplayString
   MAX-ACCESS  read-only
   STATUS      current
   DESCRIPTION
       " Users Abbr: L = Limit Control, 8 = 802.1X, D = DHCP Snooping, V = Voice VLAN, 
         '-' means that the corresponding user module is not enabled. "
   ::= { gs2352pPortSecSwitchStatusEntry 2 }

gs2352pPortSecSwitchStatusState OBJECT-TYPE
   SYNTAX      DisplayString
   MAX-ACCESS  read-only
   STATUS      current
   DESCRIPTION
       " Shows the current state of the port : Disabled, Ready, Limit Reached, Shutdown. "
   ::= { gs2352pPortSecSwitchStatusEntry 3 }

gs2352pPortSecSwitchStatusMACCountCurrent OBJECT-TYPE
   SYNTAX      Integer32(1..4095)
   MAX-ACCESS  read-only
   STATUS      current
   DESCRIPTION
       ""
   ::= { gs2352pPortSecSwitchStatusEntry 4 }

gs2352pPortSecSwitchStatusMACCountLimit OBJECT-TYPE
   SYNTAX      Integer32(1..4095)
   MAX-ACCESS  read-only
   STATUS      current
   DESCRIPTION
       ""
   ::= { gs2352pPortSecSwitchStatusEntry 5 }

gs2352pPortSecPortStatus                                      OBJECT IDENTIFIER ::= { gs2352pPortSecurity 3 }

gs2352pPortSecPortStatusPort OBJECT-TYPE
   SYNTAX       Integer32(1..4095)
   MAX-ACCESS   read-write
   STATUS       current
   DESCRIPTION
       "port number
        default: 1
        range: 1 - port number."
   ::= { gs2352pPortSecPortStatus 1 }

gs2352pPortSecPortStatusTable OBJECT-TYPE
   SYNTAX      SEQUENCE OF GS2352PPortSecPortStatusEntry
   MAX-ACCESS  not-accessible
   STATUS      current
   DESCRIPTION
      " "
   ::= { gs2352pPortSecPortStatus 2 }
       
gs2352pPortSecPortStatusEntry OBJECT-TYPE
   SYNTAX      GS2352PPortSecPortStatusEntry
   MAX-ACCESS  not-accessible
   STATUS      current
   DESCRIPTION
       ""
   INDEX    { gs2352pPortSecPortStatusIndex  }
   ::= { gs2352pPortSecPortStatusTable 1 }       

GS2352PPortSecPortStatusEntry ::= SEQUENCE {
   gs2352pPortSecPortStatusIndex              Integer32,
   gs2352pPortSecPortStatusMACAddress         MacAddress,
   gs2352pPortSecPortStatusVLANId             Integer32,
   gs2352pPortSecPortStatusState              DisplayString,
   gs2352pPortSecPortStatusTimeOfAddition     DisplayString,
   gs2352pPortSecPortStatusAgeAndHold         DisplayString
}

gs2352pPortSecPortStatusIndex OBJECT-TYPE
   SYNTAX      Integer32(1..4095)
   MAX-ACCESS  not-accessible
   STATUS      current
   DESCRIPTION
       " "
   ::= { gs2352pPortSecPortStatusEntry 1 }

gs2352pPortSecPortStatusMACAddress OBJECT-TYPE
   SYNTAX      MacAddress
   MAX-ACCESS  read-only
   STATUS      current
   DESCRIPTION
       " "
   ::= { gs2352pPortSecPortStatusEntry 2 }

gs2352pPortSecPortStatusVLANId OBJECT-TYPE
   SYNTAX      Integer32(1..4094)
   MAX-ACCESS  read-only
   STATUS      current
   DESCRIPTION
       " "
   ::= { gs2352pPortSecPortStatusEntry 3 }

gs2352pPortSecPortStatusState OBJECT-TYPE
   SYNTAX      DisplayString
   MAX-ACCESS  read-only
   STATUS      current
   DESCRIPTION
       "Blocked / Forwarding "
   ::= { gs2352pPortSecPortStatusEntry 4 }

gs2352pPortSecPortStatusTimeOfAddition OBJECT-TYPE
   SYNTAX      DisplayString
   MAX-ACCESS  read-only
   STATUS      current
   DESCRIPTION
       " "
   ::= { gs2352pPortSecPortStatusEntry 5 }

gs2352pPortSecPortStatusAgeAndHold OBJECT-TYPE
   SYNTAX      DisplayString
   MAX-ACCESS  read-only
   STATUS      current
   DESCRIPTION
       " "
   ::= { gs2352pPortSecPortStatusEntry 6 }       
       

gs2352pAccessManagement                                      OBJECT IDENTIFIER ::= { gs2352pSecurity 6 }

gs2352pAccessMgtConf                                         OBJECT IDENTIFIER ::= { gs2352pAccessManagement 1 }

gs2352pAccessMgtConfMode OBJECT-TYPE
   SYNTAX      INTEGER { disable(0), enable(1) }
   MAX-ACCESS  read-write
   STATUS      current
   DESCRIPTION
       "default: 0
       0: disable
       1: enable "
   ::= { gs2352pAccessMgtConf 1 }

gs2352pAccessMgtConfCreate OBJECT-TYPE
   SYNTAX      INTEGER { none(0), create(1) }
   MAX-ACCESS  read-write
   STATUS      current
   DESCRIPTION
       "default: 0
       0: none
       1: create "
   ::= { gs2352pAccessMgtConf 2 }

gs2352pAccessMgtConfTable OBJECT-TYPE
   SYNTAX      SEQUENCE OF GS2352PAccessMgtConfEntry
   MAX-ACCESS  not-accessible
   STATUS      current
   DESCRIPTION
       " "
   ::= { gs2352pAccessMgtConf 3 }

gs2352pAccessMgtConfEntry OBJECT-TYPE
   SYNTAX      GS2352PAccessMgtConfEntry
   MAX-ACCESS  not-accessible
   STATUS      current
   DESCRIPTION
       ""
   INDEX    { gs2352pAccessMgtIndex  }
   ::= { gs2352pAccessMgtConfTable 1 }
   
GS2352PAccessMgtConfEntry ::= SEQUENCE {
   gs2352pAccessMgtIndex             Integer32,
   gs2352pAccessMgtAddresstype       INTEGER,
   gs2352pAccessMgtStartIpAddress    DisplayString,
   gs2352pAccessMgtEndIpAddress      DisplayString,
   gs2352pAccessMgtHttpHttps         INTEGER,
   gs2352pAccessMgtSNMP              INTEGER,
   gs2352pAccessMgtTelnetSSH         INTEGER,
   gs2352pAccessMgtRowStatus         INTEGER
}

gs2352pAccessMgtIndex OBJECT-TYPE
   SYNTAX      Integer32(1..16)
   MAX-ACCESS  read-write
   STATUS      current
   DESCRIPTION
       "Set Access Management config index
        range : 1-16."
   ::= { gs2352pAccessMgtConfEntry 1 }

gs2352pAccessMgtAddresstype OBJECT-TYPE
   SYNTAX      INTEGER { ipv4(0), ipv6(1) }
   MAX-ACCESS  read-write
   STATUS      current
   DESCRIPTION
       "0: ipv4
        1: ipv6 "
   ::= { gs2352pAccessMgtConfEntry 2 }
   
gs2352pAccessMgtStartIpAddress OBJECT-TYPE
   SYNTAX      DisplayString
   MAX-ACCESS  read-write
   STATUS      current
   DESCRIPTION
       " Start IP address. 
         IP address doesn't allowed all zero or all 'ff'H."
   ::= { gs2352pAccessMgtConfEntry 3 }
   
gs2352pAccessMgtEndIpAddress OBJECT-TYPE
   SYNTAX      DisplayString
   MAX-ACCESS  read-write
   STATUS      current
   DESCRIPTION
       " End IP address. 
         IP address doesn't allowed all zero or all 'ff'H.
         End ip address is not less than start ip address."
   ::= { gs2352pAccessMgtConfEntry 4 }

gs2352pAccessMgtHttpHttps OBJECT-TYPE
   SYNTAX      INTEGER { disable(0), enable(1) }
   MAX-ACCESS  read-write
   STATUS      current
   DESCRIPTION
       "default: 0
       0: disable
       1: enable "
   ::= { gs2352pAccessMgtConfEntry 5 }

gs2352pAccessMgtSNMP OBJECT-TYPE
   SYNTAX      INTEGER { disable(0), enable(1) }
   MAX-ACCESS  read-write
   STATUS      current
   DESCRIPTION
       "default: 0
       0: disable
       1: enable "
   ::= { gs2352pAccessMgtConfEntry 6 }

gs2352pAccessMgtTelnetSSH OBJECT-TYPE
   SYNTAX      INTEGER { disable(0), enable(1) }
   MAX-ACCESS  read-write
   STATUS      current
   DESCRIPTION
       "default: 0
       0: disable
       1: enable "
   ::= { gs2352pAccessMgtConfEntry 7 }

gs2352pAccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2352pAccessMgtConfEntry 8 }

gs2352pAccessMgtStatistics                                   OBJECT IDENTIFIER ::= { gs2352pAccessManagement 2 }

gs2352pHttpReceivedPkts OBJECT-TYPE
   SYNTAX      Counter32
   MAX-ACCESS  read-only
   STATUS      current
   DESCRIPTION
       " "
   ::= { gs2352pAccessMgtStatistics 1 }

gs2352pHttpAllowedPkts OBJECT-TYPE
   SYNTAX      Counter32
   MAX-ACCESS  read-only
   STATUS      current
   DESCRIPTION
       " "
   ::= { gs2352pAccessMgtStatistics 2 }

gs2352pHttpDiscardedPkts OBJECT-TYPE
   SYNTAX      Counter32
   MAX-ACCESS  read-only
   STATUS      current
   DESCRIPTION
       " "
   ::= { gs2352pAccessMgtStatistics 3 }

gs2352pHttpsReceivedPkts OBJECT-TYPE
   SYNTAX      Counter32
   MAX-ACCESS  read-only
   STATUS      current
   DESCRIPTION
       " "
   ::= { gs2352pAccessMgtStatistics 4 }

gs2352pHttpsAllowedPkts OBJECT-TYPE
   SYNTAX      Counter32
   MAX-ACCESS  read-only
   STATUS      current
   DESCRIPTION
       " "
   ::= { gs2352pAccessMgtStatistics 5 }

gs2352pHttpsDiscardedPkts OBJECT-TYPE
   SYNTAX      Counter32
   MAX-ACCESS  read-only
   STATUS      current
   DESCRIPTION
       " "
   ::= { gs2352pAccessMgtStatistics 6 }

gs2352pSnmpReceivedPkts OBJECT-TYPE
   SYNTAX      Counter32
   MAX-ACCESS  read-only
   STATUS      current
   DESCRIPTION
       " "
   ::= { gs2352pAccessMgtStatistics 7 }

gs2352pSnmpAllowedPkts OBJECT-TYPE
   SYNTAX      Counter32
   MAX-ACCESS  read-only
   STATUS      current
   DESCRIPTION
       " "
   ::= { gs2352pAccessMgtStatistics 8 }

gs2352pSnmpDiscardedPkts OBJECT-TYPE
   SYNTAX      Counter32
   MAX-ACCESS  read-only
   STATUS      current
   DESCRIPTION
       " "
   ::= { gs2352pAccessMgtStatistics 9 }

gs2352pTelnetReceivedPkts OBJECT-TYPE
   SYNTAX      Counter32
   MAX-ACCESS  read-only
   STATUS      current
   DESCRIPTION
       " "
   ::= { gs2352pAccessMgtStatistics 10 }

gs2352pTelnetAllowedPkts OBJECT-TYPE
   SYNTAX      Counter32
   MAX-ACCESS  read-only
   STATUS      current
   DESCRIPTION
       " "
   ::= { gs2352pAccessMgtStatistics 11 }

gs2352pTelnetDiscardedPkts OBJECT-TYPE
   SYNTAX      Counter32
   MAX-ACCESS  read-only
   STATUS      current
   DESCRIPTION
       " "
   ::= { gs2352pAccessMgtStatistics 12 }

gs2352pSSHReceivedPkts OBJECT-TYPE
   SYNTAX      Counter32
   MAX-ACCESS  read-only
   STATUS      current
   DESCRIPTION
       " "
   ::= { gs2352pAccessMgtStatistics 13 }

gs2352pSSHAllowedPkts OBJECT-TYPE
   SYNTAX      Counter32
   MAX-ACCESS  read-only
   STATUS      current
   DESCRIPTION
       " "
   ::= { gs2352pAccessMgtStatistics 14 }

gs2352pSSHDiscardedPkts OBJECT-TYPE
   SYNTAX      Counter32
   MAX-ACCESS  read-only
   STATUS      current
   DESCRIPTION
       " "
   ::= { gs2352pAccessMgtStatistics 15 }

gs2352pAccessMgtStatisticsClearAll OBJECT-TYPE
   SYNTAX      INTEGER { none(0), clear(1) }
   MAX-ACCESS  read-write
   STATUS      current
   DESCRIPTION
       "0: none
        1: clear"
   ::= { gs2352pAccessMgtStatistics 16 }

gs2352pSSH                                                   OBJECT IDENTIFIER ::= { gs2352pSecurity 7 }

gs2352pSSHMode OBJECT-TYPE
   SYNTAX      INTEGER { disable(0), enable(1) }
   MAX-ACCESS  read-write
   STATUS      current
   DESCRIPTION
       "default: 1
        0: disable
        1: enable"
   ::= { gs2352pSSH 1 }

gs2352pHTTPS                                                 OBJECT IDENTIFIER ::= { gs2352pSecurity 8 }

gs2352pHTTPSMode OBJECT-TYPE
   SYNTAX      INTEGER { disable(0), enable(1) }
   MAX-ACCESS  read-write
   STATUS      current
   DESCRIPTION
       "default: 1
        0: disable
        1: enable"
   ::= { gs2352pHTTPS 1 }

gs2352pHTTPSAutoRedirect OBJECT-TYPE
   SYNTAX      INTEGER { disable(0), enable(1) }
   MAX-ACCESS  read-write
   STATUS      current
   DESCRIPTION
       "default: 0
        0: disable
        1: enable"
   ::= { gs2352pHTTPS 2 }

gs2352pHTTPSCertRenew OBJECT-TYPE
   SYNTAX      INTEGER { doNothing(0), renew(1) }
   MAX-ACCESS  read-write
   STATUS      current
   DESCRIPTION
       "default: 0 ,
        0: doNothing
        1: renew"
   ::= { gs2352pHTTPS 3 }

gs2352pHTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2352pHTTPS 4 }

gs2352pHTTPMode OBJECT-TYPE
   SYNTAX      INTEGER { disable(0), enable(1) }
   MAX-ACCESS  read-write
   STATUS      current
   DESCRIPTION
       "default: 1
        0: disable
        1: enable"
   ::= { gs2352pHTTPS 5 }

gs2352pAuthMethod                                            OBJECT IDENTIFIER ::= { gs2352pSecurity 9 }

gs2352pConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352pAuthMethod 1 }

gs2352pConsoleFallback OBJECT-TYPE
   SYNTAX      INTEGER { disable(0), enable(1) }
   MAX-ACCESS  read-write
   STATUS      current
   DESCRIPTION
       "default: 0
        0:disable
        1:enable"
   ::= { gs2352pAuthMethod 2 }

gs2352pTelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352pAuthMethod 3 }

gs2352pTelnetFallback OBJECT-TYPE
   SYNTAX      INTEGER { disable(0), enable(1) }
   MAX-ACCESS  read-write
   STATUS      current
   DESCRIPTION
       "default: 0
        0:disable
        1:enable"
   ::= { gs2352pAuthMethod 4 }

gs2352pSshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352pAuthMethod 5 }

gs2352pSshFallback OBJECT-TYPE
   SYNTAX      INTEGER { disable(0), enable(1) }
   MAX-ACCESS  read-write
   STATUS      current
   DESCRIPTION
       "default: 0
        0:disable
        1:enable"
   ::= { gs2352pAuthMethod 6 }

gs2352pTftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352pAuthMethod 9 }

gs2352pTftpFallback OBJECT-TYPE
   SYNTAX      INTEGER { disable(0), enable(1) }
   MAX-ACCESS  read-write
   STATUS      current
   DESCRIPTION
       "default: 0
        0:disable
        1:enable"
   ::= { gs2352pAuthMethod 10 }
   
gs2352pLoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2352pAuthMethod 11 }

gs2352pLockMinutes OBJECT-TYPE
   SYNTAX      Integer32(1..99)
   MAX-ACCESS  read-write
   STATUS      current
   DESCRIPTION
       "Lock time to login failures trigger.
        range: 1-99.
        default: 5."
   ::= { gs2352pAuthMethod 12 }

gs2352pHttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352pAuthMethod 13 }

gs2352pHttpFallback OBJECT-TYPE
   SYNTAX      INTEGER { disable(0), enable(1) }
   MAX-ACCESS  read-write
   STATUS      current
   DESCRIPTION
       "default: 0
        0:disable
        1:enable"
   ::= { gs2352pAuthMethod 14 }

gs2352pHttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2352pAuthMethod 15 }

gs2352pHttpsFallback OBJECT-TYPE
   SYNTAX      INTEGER { disable(0), enable(1) }
   MAX-ACCESS  read-write
   STATUS      current
   DESCRIPTION
       "default: 0
        0:disable
        1:enable"
   ::= { gs2352pAuthMethod 16 }


gs2352pAAA                                              OBJECT IDENTIFIER ::= { gs2352pSecurity 10 }

gs2352pAAACommonServer                                  OBJECT IDENTIFIER ::= { gs2352pAAA 1 }

gs2352pAAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2352pAAACommonServer 1 }

gs2352pAAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2352pAAACommonServer 2 }

gs2352pAAATACACSPlusAuthAndAccounting                  OBJECT IDENTIFIER ::= { gs2352pAAA 2 }

gs2352pAAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2352pAAATACACSPlusAuthAndAccounting 1 }

gs2352pAAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2352pAAATACACSPlusAuthAndAccounting 2 }

gs2352pAAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2352pAAATACACSPlusAuthAndAccounting 3 }

gs2352pRADIUSAuthenticationServerTable OBJECT-TYPE
   SYNTAX      SEQUENCE OF Gs2352pRADIUSAuthenticationServerEntry
   MAX-ACCESS  not-accessible
   STATUS      current
   DESCRIPTION
       " "
   ::= { gs2352pAAA 3 }

gs2352pRADIUSAuthenticationServerEntry OBJECT-TYPE
   SYNTAX      Gs2352pRADIUSAuthenticationServerEntry
   MAX-ACCESS  not-accessible
   STATUS      current
   DESCRIPTION
       ""
   INDEX    { gs2352pRADIUSAuthenticationServerIndex  }
   ::= { gs2352pRADIUSAuthenticationServerTable 1 }

Gs2352pRADIUSAuthenticationServerEntry ::= SEQUENCE {
   gs2352pRADIUSAuthenticationServerIndex     Integer32,
   gs2352pRADIUSAuthenticationServerEnable    INTEGER,
   gs2352pRADIUSAuthenticationServerIP        DisplayString,
   gs2352pRADIUSAuthenticationServerPort      Integer32,
   gs2352pRADIUSAuthenticationServerSecret    DisplayString
}

gs2352pRADIUSAuthenticationServerIndex OBJECT-TYPE
   SYNTAX      Integer32(1..5)
   MAX-ACCESS  not-accessible
   STATUS      current
   DESCRIPTION
       "RADIUS Authentication Server index
        range : 1-5."
   ::= { gs2352pRADIUSAuthenticationServerEntry 1 }

gs2352pRADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2352pRADIUSAuthenticationServerEntry 2 }

gs2352pRADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2352pRADIUSAuthenticationServerEntry 3 }

gs2352pRADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2352pRADIUSAuthenticationServerEntry 4 }

gs2352pRADIUSAuthenticationServerSecret OBJECT-TYPE
   SYNTAX      DisplayString
   MAX-ACCESS  read-write
   STATUS      current
   DESCRIPTION
       "The secret - up to 64 characters long - shared between the RADIUS Authentication Server and the switch. "
   ::= { gs2352pRADIUSAuthenticationServerEntry 5 }
   

gs2352pRADIUSAccountingServerTable OBJECT-TYPE
   SYNTAX      SEQUENCE OF Gs2352pRADIUSAccountingServerEntry
   MAX-ACCESS  not-accessible
   STATUS      current
   DESCRIPTION
       " "
   ::= { gs2352pAAA 4 }

gs2352pRADIUSAccountingServerEntry OBJECT-TYPE
   SYNTAX      Gs2352pRADIUSAccountingServerEntry
   MAX-ACCESS  not-accessible
   STATUS      current
   DESCRIPTION
       ""
   INDEX    { gs2352pRADIUSAccountingServerIndex  }
   ::= { gs2352pRADIUSAccountingServerTable 1 }

Gs2352pRADIUSAccountingServerEntry ::= SEQUENCE {
   gs2352pRADIUSAccountingServerIndex     Integer32,
   gs2352pRADIUSAccountingServerEnable    INTEGER,
   gs2352pRADIUSAccountingServerIP        DisplayString,
   gs2352pRADIUSAccountingServerPort      Integer32,
   gs2352pRADIUSAccountingServerSecret    DisplayString
}

gs2352pRADIUSAccountingServerIndex OBJECT-TYPE
   SYNTAX      Integer32(1..5)
   MAX-ACCESS  not-accessible
   STATUS      current
   DESCRIPTION
       "RADIUS Accounting Server index
        range : 1-5."
   ::= { gs2352pRADIUSAccountingServerEntry 1 }

gs2352pRADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2352pRADIUSAccountingServerEntry 2 }

gs2352pRADIUSAccountingServerIP OBJECT-TYPE
   SYNTAX      DisplayString
   MAX-ACCESS  read-write
   STATUS      current
   DESCRIPTION
       "The IP address or hostname of the RADIUS Accounting Server.
       IP address is expressed in  dotted decimal notation. "
   ::= { gs2352pRADIUSAccountingServerEntry 3 }

gs2352pRADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2352pRADIUSAccountingServerEntry 4 }

gs2352pRADIUSAccountingServerSecret OBJECT-TYPE
   SYNTAX      DisplayString
   MAX-ACCESS  read-write
   STATUS      current
   DESCRIPTION
       "The secret - up to 64 characters long - shared between the RADIUS Accounting Server and the switch. "
   ::= { gs2352pRADIUSAccountingServerEntry 5 }

gs2352pTACACSPlusAuthenticationServerTable OBJECT-TYPE
   SYNTAX      SEQUENCE OF Gs2352pTACACSPlusAuthenticationServerEntry
   MAX-ACCESS  not-accessible
   STATUS      current
   DESCRIPTION
       " "
   ::= { gs2352pAAA 5 }

gs2352pTACACSPlusAuthenticationServerEntry OBJECT-TYPE
   SYNTAX      Gs2352pTACACSPlusAuthenticationServerEntry
   MAX-ACCESS  not-accessible
   STATUS      current
   DESCRIPTION
       ""
   INDEX    { gs2352pTACACSPlusAuthenticationServerIndex  }
   ::= { gs2352pTACACSPlusAuthenticationServerTable 1 }

Gs2352pTACACSPlusAuthenticationServerEntry ::= SEQUENCE {
   gs2352pTACACSPlusAuthenticationServerIndex     Integer32,
   gs2352pTACACSPlusAuthenticationServerEnable    INTEGER,
   gs2352pTACACSPlusAuthenticationServerIP        DisplayString,
   gs2352pTACACSPlusAuthenticationServerPort      Integer32,
   gs2352pTACACSPlusAuthenticationServerSecret    DisplayString
}

gs2352pTACACSPlusAuthenticationServerIndex OBJECT-TYPE
   SYNTAX      Integer32(1..5)
   MAX-ACCESS  not-accessible
   STATUS      current
   DESCRIPTION
       "TACACSPlus Authentication Server index
        range : 1-5."
   ::= { gs2352pTACACSPlusAuthenticationServerEntry 1 }

gs2352pTACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2352pTACACSPlusAuthenticationServerEntry 2 }

gs2352pTACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2352pTACACSPlusAuthenticationServerEntry 3 }

gs2352pTACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2352pTACACSPlusAuthenticationServerEntry 4 }

gs2352pTACACSPlusAuthenticationServerSecret OBJECT-TYPE
   SYNTAX      DisplayString
   MAX-ACCESS  read-write
   STATUS      current
   DESCRIPTION
       "The secret - up to 64 characters long - shared between the TACACSPlus Authentication Server and the switch. "
   ::= { gs2352pTACACSPlusAuthenticationServerEntry 5 }


gs2352pRADIUSStatisticsTable OBJECT-TYPE
   SYNTAX      SEQUENCE OF Gs2352pRADIUSStatisticsEntry
   MAX-ACCESS  not-accessible
   STATUS      current
   DESCRIPTION
       " "
   ::= { gs2352pAAA 6 }

gs2352pRADIUSStatisticsEntry OBJECT-TYPE
   SYNTAX      Gs2352pRADIUSStatisticsEntry
   MAX-ACCESS  not-accessible
   STATUS      current
   DESCRIPTION
       ""
   INDEX    { gs2352pRADIUSAuthStatisticsServerIndex  }
   ::= { gs2352pRADIUSStatisticsTable 1 }

Gs2352pRADIUSStatisticsEntry ::= SEQUENCE {
   gs2352pRADIUSAuthStatisticsServerIndex                           Integer32,
   gs2352pRADIUSAuthStatisticsRecPktAccessAccepts                   Counter32,
   gs2352pRADIUSAuthStatisticsRecPktAccessRejects                   Counter32,
   gs2352pRADIUSAuthStatisticsRecPktAccessChallenges                Counter32,
   gs2352pRADIUSAuthStatisticsRecPktMalformedAccResponses           Counter32,
   gs2352pRADIUSAuthStatisticsRecPktBadAuthenticators               Counter32,
   gs2352pRADIUSAuthStatisticsRecPktUnknownTypes                    Counter32,
   gs2352pRADIUSAuthStatisticsRecPktDropped                         Counter32,
   gs2352pRADIUSAuthStatisticsTransmitPktAccessRequests             Counter32,
   gs2352pRADIUSAuthStatisticsTransmitPktAccessRetransmissions      Counter32,
   gs2352pRADIUSAuthStatisticsTransmitPktPendingRequests            Counter32,
   gs2352pRADIUSAuthStatisticsTransmitPktTimeouts                   Counter32,
   gs2352pRADIUSAuthIP                                              DisplayString,
   gs2352pRADIUSAuthState                                           DisplayString,
   gs2352pRADIUSAuthRoundTripTime                                   DisplayString,

   gs2352pRADIUSAccountingStatisticsRecPktResponses                 Counter32,
   gs2352pRADIUSAccountingStatisticsRecPktMalformedResponses        Counter32,
   gs2352pRADIUSAccountingStatisticsRecPktBadAuthenticators         Counter32,
   gs2352pRADIUSAccountingStatisticsRecPktUnknownTypes              Counter32,
   gs2352pRADIUSAccountingStatisticsRecPktDropped                   Counter32,
   gs2352pRADIUSAccountingStatisticsTransmitPktRequests             Counter32,
   gs2352pRADIUSAccountingStatisticsTransmitPktRetransmissions      Counter32,
   gs2352pRADIUSAccountingStatisticsTransmitPktPendingRequests      Counter32,
   gs2352pRADIUSAccountingStatisticsTransmitPktTimeouts             Counter32,
   gs2352pRADIUSAccountingIP                                        DisplayString,
   gs2352pRADIUSAccountingState                                     DisplayString,
   gs2352pRADIUSAccountingRoundTripTime                             DisplayString,
   gs2352pRADIUSStatisticsClear                                     INTEGER
}

gs2352pRADIUSAuthStatisticsServerIndex OBJECT-TYPE
   SYNTAX      Integer32(1..5)
   MAX-ACCESS  not-accessible
   STATUS      current
   DESCRIPTION
       "RADIUS Authentication Server index
        range : 1-5."
   ::= { gs2352pRADIUSStatisticsEntry 1 }

gs2352pRADIUSAuthStatisticsRecPktAccessAccepts OBJECT-TYPE
   SYNTAX      Counter32
   MAX-ACCESS  read-only
   STATUS      current
   DESCRIPTION
       "The number of RADIUS Access-Accept packets (valid or invalid) received from the server."
   ::= { gs2352pRADIUSStatisticsEntry 2 }

gs2352pRADIUSAuthStatisticsRecPktAccessRejects OBJECT-TYPE
   SYNTAX      Counter32
   MAX-ACCESS  read-only
   STATUS      current
   DESCRIPTION
       "The number of RADIUS Access-Reject packets (valid or invalid) received from the server."
   ::= { gs2352pRADIUSStatisticsEntry 3 }

gs2352pRADIUSAuthStatisticsRecPktAccessChallenges OBJECT-TYPE
   SYNTAX      Counter32
   MAX-ACCESS  read-only
   STATUS      current
   DESCRIPTION
       "The number of RADIUS Access-Challenge packets (valid or invalid) received from the server. "
   ::= { gs2352pRADIUSStatisticsEntry 4 }

gs2352pRADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2352pRADIUSStatisticsEntry 5 }

gs2352pRADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2352pRADIUSStatisticsEntry 6 }

gs2352pRADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2352pRADIUSStatisticsEntry 7 }

gs2352pRADIUSAuthStatisticsRecPktDropped OBJECT-TYPE
   SYNTAX      Counter32
   MAX-ACCESS  read-only
   STATUS      current
   DESCRIPTION
       "The number of RADIUS packets that were received from the server on the
       authentication port and dropped for some other reason."
   ::= { gs2352pRADIUSStatisticsEntry 8 }

gs2352pRADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2352pRADIUSStatisticsEntry 9 }

gs2352pRADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2352pRADIUSStatisticsEntry 10 }

gs2352pRADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2352pRADIUSStatisticsEntry 11 }

gs2352pRADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2352pRADIUSStatisticsEntry 12 }

gs2352pRADIUSAuthIP OBJECT-TYPE
   SYNTAX      DisplayString
   MAX-ACCESS  read-only
   STATUS      current
   DESCRIPTION
       "IP address and UDP port for the authentication server in question."
   ::= { gs2352pRADIUSStatisticsEntry 13 }

gs2352pRADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2352pRADIUSStatisticsEntry 14 }

gs2352pRADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2352pRADIUSStatisticsEntry 15 }

gs2352pRADIUSAccountingStatisticsRecPktResponses OBJECT-TYPE
   SYNTAX      Counter32
   MAX-ACCESS  read-only
   STATUS      current
   DESCRIPTION
       "The number of RADIUS packets (valid or invalid) received from the server."
   ::= { gs2352pRADIUSStatisticsEntry 16 }

gs2352pRADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2352pRADIUSStatisticsEntry 17 }

gs2352pRADIUSAccountingStatisticsRecPktBadAuthenticators OBJECT-TYPE
   SYNTAX      Counter32
   MAX-ACCESS  read-only
   STATUS      current
   DESCRIPTION
       "The number of RADIUS packets containing invalid authenticators received
       from the server."
   ::= { gs2352pRADIUSStatisticsEntry 18 }

gs2352pRADIUSAccountingStatisticsRecPktUnknownTypes OBJECT-TYPE
   SYNTAX      Counter32
   MAX-ACCESS  read-only
   STATUS      current
   DESCRIPTION
       "The number of RADIUS packets of unknown types that were received from
       the server on the accounting port."
   ::= { gs2352pRADIUSStatisticsEntry 19 }

gs2352pRADIUSAccountingStatisticsRecPktDropped OBJECT-TYPE
   SYNTAX      Counter32
   MAX-ACCESS  read-only
   STATUS      current
   DESCRIPTION
       "The number of RADIUS packets that were received from the server on the
       accounting port and dropped for some other reason."
   ::= { gs2352pRADIUSStatisticsEntry 20 }

gs2352pRADIUSAccountingStatisticsTransmitPktRequests OBJECT-TYPE
   SYNTAX      Counter32
   MAX-ACCESS  read-only
   STATUS      current
   DESCRIPTION
       "The number of RADIUS packets sent to the server. This does not include
       retransmissions."
   ::= { gs2352pRADIUSStatisticsEntry 21 }

gs2352pRADIUSAccountingStatisticsTransmitPktRetransmissions OBJECT-TYPE
   SYNTAX      Counter32
   MAX-ACCESS  read-only
   STATUS      current
   DESCRIPTION
       "The number of RADIUS packets retransmitted to the RADIUS accounting server."
   ::= { gs2352pRADIUSStatisticsEntry 22 }

gs2352pRADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2352pRADIUSStatisticsEntry 23 }

gs2352pRADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2352pRADIUSStatisticsEntry 24 }

gs2352pRADIUSAccountingIP OBJECT-TYPE
   SYNTAX      DisplayString
   MAX-ACCESS  read-only
   STATUS      current
   DESCRIPTION
       "IP address and UDP port for the accounting server in question."
   ::= { gs2352pRADIUSStatisticsEntry 25 }

gs2352pRADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2352pRADIUSStatisticsEntry 26 }
   
gs2352pRADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2352pRADIUSStatisticsEntry 27 }

gs2352pRADIUSStatisticsClear OBJECT-TYPE
   SYNTAX      INTEGER(0|1)
   MAX-ACCESS  read-write
   STATUS      current
   DESCRIPTION
       "Clears the counters for the server.
       read: always 0
       clear: set 1"
   ::= { gs2352pRADIUSStatisticsEntry 28 }

gs2352pNAS                                              OBJECT IDENTIFIER ::= { gs2352pSecurity 11 }

gs2352pNASConfiguration                                 OBJECT IDENTIFIER ::= { gs2352pNAS 1 }

gs2352pNASConfigMode OBJECT-TYPE
   SYNTAX      INTEGER { disable(0), enable(1) }
   MAX-ACCESS  read-write
   STATUS      current
   DESCRIPTION
       "Indicates if NAS is globally enabled or disabled on the switch. 
	    If globally disabled, all ports are allowed forwarding of frames."
   ::= { gs2352pNASConfiguration 1 }

gs2352pNASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication 
		Period. Reauthentication for 802.1X-enabled ports can be used to 
		detect if a new device is plugged into a switch port or if a 
		supplicant is no longer attached. 
		For MAC-based ports, reauthentication is only useful if the RADIUS 
		server configuration has changed. It does not involve communication 
		between the switch and the client, and therefore doesn't imply that 
		a client is still present on a port."
   ::= { gs2352pNASConfiguration 2 }

gs2352pNASConfigReauthPeriod OBJECT-TYPE
   SYNTAX      Integer32(1..3600)
   MAX-ACCESS  read-write
   STATUS      current
   DESCRIPTION
       "Determines the period, in seconds, after which a connected client must 
	    be reauthenticated. This is only active if the Reauthentication Enabled 
		checkbox is checked. 
		range: 1 - 3600 seconds."
   ::= { gs2352pNASConfiguration 3 }

gs2352pNASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2352pNASConfiguration 4 }
   
gs2352pNASConfigAgingPeriod OBJECT-TYPE
   SYNTAX      Integer32(10..1000000)
   MAX-ACCESS  read-write
   STATUS      current
   DESCRIPTION
       "When the NAS module uses the Port Security module to secure MAC addresses, 
	    the Port Security module needs to check for activity on the MAC address 
		in question at regular intervals and free resources if no activity 
		is seen within a given period of time.
		Admin State supported : Single, Multi and MAC-Based Auth. 802.1X.
		range: 10 - 1000000 seconds."
   ::= { gs2352pNASConfiguration 5 }   
   
gs2352pNASConfigHoldTime OBJECT-TYPE
   SYNTAX      Integer32(10..1000000)
   MAX-ACCESS  read-write
   STATUS      current
   DESCRIPTION
       "If a client is denied access - either because the RADIUS server denies
	    the client access or because the RADIUS server request times out 
		- the client is put on hold in the Unauthorized state. The hold timer 
		does not count during an on-going authentication. In MAC-based Auth. 
		mode, the switch will ignore new frames coming from the client during 
		the hold time.
		Admin State supported : Single, Multi and MAC-Based Auth. 802.1X.
		range: 10 - 1000000 seconds."
   ::= { gs2352pNASConfiguration 6 }  

gs2352pNASConfigRADIUSAssignedQoSEnabled OBJECT-TYPE
   SYNTAX      INTEGER { disable(0), enable(1) }
   MAX-ACCESS  read-write
   STATUS      current
   DESCRIPTION
       "RADIUS-assigned QoS provides a means to centrally control the 
	    traffic class to which traffic coming from a successfully authenticated 
		supplicant is assigned on the switch. The RADIUS server must be configured 
		to transmit special RADIUS attributes to take advantage of this feature."
   ::= { gs2352pNASConfiguration 7 }  
 
gs2352pNASConfigRADIUSAssignedVLANEnabled OBJECT-TYPE
   SYNTAX      INTEGER { disable(0), enable(1) }
   MAX-ACCESS  read-write
   STATUS      current
   DESCRIPTION
       "RADIUS-assigned VLAN provides a means to centrally control the VLAN on 
	    which a successfully authenticated supplicant is placed on the switch. 
	    Incoming traffic will be classified to and switched on the RADIUS-assigned 
		VLAN. The RADIUS server must be configured to transmit special RADIUS 
		attributes to take advantage of this feature.When enable, the individual 
		ports' ditto setting determine whether RADIUS-assigned VLAN is enabled 
		on that port. When disable, RADIUS-server assigned VLAN is disabled on 
		all ports. "
   ::= { gs2352pNASConfiguration 8 }    
   
gs2352pNASConfigGuestVLANEnabled OBJECT-TYPE
   SYNTAX      INTEGER { disable(0), enable(1) }
   MAX-ACCESS  read-write
   STATUS      current
   DESCRIPTION
       "A Guest VLAN is a special VLAN - typically with limited network access - 
	   on which 802.1X-unaware clients are placed after a network administrator-defined 
	   timeout. The switch follows a set of rules for entering and leaving the Guest 
	   VLAN as listed below.When enable, the individual ports' ditto setting determines 
	   whether the port can be moved into Guest VLAN. When disable, the ability to 
	   move to the Guest VLAN is disabled on all ports. "
   ::= { gs2352pNASConfiguration 9 } 
   
gs2352pNASConfigGuestVLANID OBJECT-TYPE
   SYNTAX      Integer32(1..4094)
   MAX-ACCESS  read-write
   STATUS      current
   DESCRIPTION
       "This is the value that a port's Port VLAN ID is set to if a port is moved into 
	   the Guest VLAN. It is only changeable if the Guest VLAN option is globally enabled.
	   range: 1 - 4094."
   ::= { gs2352pNASConfiguration 10 }

gs2352pNASConfigMaxReauthCount OBJECT-TYPE
   SYNTAX      Integer32(1..255)
   MAX-ACCESS  read-write
   STATUS      current
   DESCRIPTION
       "The number of times the switch transmits an EAPOL Request Identity frame without 
	   response before considering entering the Guest VLAN is adjusted with this setting. 
	   The value can only be changed if the Guest VLAN option is globally enabled.
	   range: 1 - 255."
   ::= { gs2352pNASConfiguration 11 }

gs2352pNASConfigAllowGuestVLANEAPOLSeen OBJECT-TYPE
   SYNTAX      INTEGER { disable(0), enable(1) }
   MAX-ACCESS  read-write
   STATUS      current
   DESCRIPTION
       "The switch remembers if an EAPOL frame has been received on the port for the 
	   life-time of the port. Once the switch considers whether to enter the Guest VLAN, 
	   it will first check if this option is enabled or disabled. If disabled, the switch 
	   will only enter the Guest VLAN if an EAPOL frame has not been received on the port 
	   for the life-time of the port. If enabled (checked), the switch will consider 
	   entering the Guest VLAN even if an EAPOL frame has been received on the port for 
	   the life-time of the port.The value can only be changed if the Guest VLAN option 
	   is globally enabled."
   ::= { gs2352pNASConfiguration 12 }

gs2352pNASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2352pNASConfiguration 101 }

gs2352pNASPortConfigTable OBJECT-TYPE
   SYNTAX      SEQUENCE OF Gs2352pNASPortConfigEntry
   MAX-ACCESS  not-accessible
   STATUS      current
   DESCRIPTION
       ""
   ::= { gs2352pNASConfiguration 13 }

gs2352pNASPortConfigEntry OBJECT-TYPE
   SYNTAX      Gs2352pNASPortConfigEntry
   MAX-ACCESS  not-accessible
   STATUS      current
   DESCRIPTION
       ""
   INDEX    { gs2352pNASPortConfigPort }
   ::= { gs2352pNASPortConfigTable 1 }

Gs2352pNASPortConfigEntry ::= SEQUENCE {
   gs2352pNASPortConfigPort                       Integer32,
   gs2352pNASPortConfigAdminState                 INTEGER,
   gs2352pNASPortConfigRADIUSAssignedQoSEnabled	  INTEGER,
   gs2352pNASPortConfigRADIUSAssignedVLANEnabled  INTEGER,
   gs2352pNASPortConfigGuestVLANEnabled           INTEGER,   
   gs2352pNASPortConfigFallbackEnabled            INTEGER,   
   gs2352pNASPortConfigPortState                  DisplayString,
   gs2352pNASPortConfigReauthenticate             INTEGER,
   gs2352pNASPortConfigReinitialize               INTEGER
}
  
gs2352pNASPortConfigPort OBJECT-TYPE
   SYNTAX      Integer32(1..255)
   MAX-ACCESS  not-accessible
   STATUS      current
   DESCRIPTION
       " port, range : 1 - port number. "
   ::= { gs2352pNASPortConfigEntry 1 }   
   
gs2352pNASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2352pNASPortConfigEntry 2 }   
   
gs2352pNASPortConfigRADIUSAssignedQoSEnabled OBJECT-TYPE
   SYNTAX      INTEGER { disable(0), enable(1) }
   MAX-ACCESS  read-write
   STATUS      current
   DESCRIPTION
       "When RADIUS-Assigned QoS is both globally enabled and enabled (checked) 
	    on a given port, the switch reacts to QoS Class information carried in 
		the RADIUS Access-Accept packet transmitted by the RADIUS server when a 
		supplicant is successfully authenticated. If present and valid, traffic 
		received on the supplicant's port will be classified to the given QoS Class.
		Admin State supported : Port-based and Single 802.1X and MAC-based Single Auth."
   ::= { gs2352pNASPortConfigEntry 3 }    
   
gs2352pNASPortConfigRADIUSAssignedVLANEnabled OBJECT-TYPE
   SYNTAX      INTEGER { disable(0), enable(1) }
   MAX-ACCESS  read-write
   STATUS      current
   DESCRIPTION
       "When RADIUS-Assigned VLAN is both globally enabled and enabled (checked) 
	   for a given port, the switch reacts to VLAN ID information carried in the 
	   RADIUS Access-Accept packet transmitted by the RADIUS server when a supplicant 
	   is successfully authenticated. If present and valid, the port's Port VLAN ID 
	   will be changed to this VLAN ID, the port will be set to be a member of that 
	   VLAN ID, and the port will be forced into VLAN unaware mode. Once assigned, 
	   all traffic arriving on the port will be classified and switched on the 
	   RADIUS-assigned VLAN ID.
	   Admin State supported : Port-based and Single 802.1X and MAC-based Single Auth."
   ::= { gs2352pNASPortConfigEntry 4 }    
   
gs2352pNASPortConfigGuestVLANEnabled OBJECT-TYPE
   SYNTAX      INTEGER { disable(0), enable(1) }
   MAX-ACCESS  read-write
   STATUS      current
   DESCRIPTION
       "When Guest VLAN is both globally enabled and enabled (checked) for a given port, 
	   the switch considers moving the port into the Guest VLAN according to the rules
	   outlined below.
	   Admin State supported : Port-based , Single and Multi 802.1X."
   ::= { gs2352pNASPortConfigEntry 5 }    
   
gs2352pNASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode 
		and the supplicant is authorized.
		Unauthorized: The port is in Force Unauthorized or a single-supplicant 
		mode and the supplicant is not successfully authorized by the RADIUS server.
		X Auth/Y Unauth: The port is in a multi-supplicant mode. Currently X clients 
		are authorized and Y are unauthorized."
   ::= { gs2352pNASPortConfigEntry 6 }    
   
gs2352pNASPortConfigReauthenticate OBJECT-TYPE
   SYNTAX      INTEGER { doNothing(0), do(1) }
   MAX-ACCESS  read-write
   STATUS      current
   DESCRIPTION
       "Schedules a reauthentication whenever the quiet-period of the port runs out 
	   (EAPOL-based authentication). For MAC-based authentication, reauthentication 
	   will be attempted immediately.The button only has effect for successfully 
	   authenticated clients on the port and will not cause the clients to get 
	   temporarily unauthorized."
   ::= { gs2352pNASPortConfigEntry 7 }    

gs2352pNASPortConfigReinitialize OBJECT-TYPE
   SYNTAX      INTEGER { doNothing(0), do(1) }
   MAX-ACCESS  read-write
   STATUS      current
   DESCRIPTION
       "Forces a reinitialization of the clients on the port and thereby a reauthentication 
	   immediately. The clients will transfer to the unauthorized state while the 
	   reauthentication is in progress."
   ::= { gs2352pNASPortConfigEntry 8 }    

gs2352pNASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2352pNASPortConfigEntry 101 }

gs2352pNASSwitchStatusTable OBJECT-TYPE
   SYNTAX      SEQUENCE OF Gs2352pNASSwitchStatusEntry
   MAX-ACCESS  not-accessible
   STATUS      current
   DESCRIPTION
       ""
   ::= { gs2352pNAS 2 }

gs2352pNASSwitchStatusEntry OBJECT-TYPE
   SYNTAX      Gs2352pNASSwitchStatusEntry
   MAX-ACCESS  not-accessible
   STATUS      current
   DESCRIPTION
       ""
   INDEX    { gs2352pNASPortConfigPort }
   ::= { gs2352pNASSwitchStatusTable 1 }

Gs2352pNASSwitchStatusEntry ::= SEQUENCE {
   gs2352pNASSwitchStatusAdminState 	DisplayString,
   gs2352pNASSwitchStatusPortState		DisplayString,
   gs2352pNASSwitchStatusLastSource		DisplayString,
   gs2352pNASSwitchStatusLastID			DisplayString,
   gs2352pNASSwitchStatusQoSClass		DisplayString,
   gs2352pNASSwitchStatusPortVlanID		DisplayString
}
   
gs2352pNASSwitchStatusAdminState OBJECT-TYPE
   SYNTAX      DisplayString
   MAX-ACCESS  read-only
   STATUS      current
   DESCRIPTION
       "The port's current administrative state. Refer to NAS Admin State for a description of possible values."
   ::= { gs2352pNASSwitchStatusEntry 2 }   
   
gs2352pNASSwitchStatusPortState OBJECT-TYPE
   SYNTAX      DisplayString
   MAX-ACCESS  read-only
   STATUS      current
   DESCRIPTION
       "The current state of the port. Refer to NAS Port State for a description of the individual states."
   ::= { gs2352pNASSwitchStatusEntry 3 }      
   
gs2352pNASSwitchStatusLastSource OBJECT-TYPE
   SYNTAX      DisplayString
   MAX-ACCESS  read-only
   STATUS      current
   DESCRIPTION
       "The source MAC address carried in the most recently received EAPOL frame for EAPOL-based authentication, 
	   and the most recently received frame from a new client for MAC-based authentication."
   ::= { gs2352pNASSwitchStatusEntry 4 }      

gs2352pNASSwitchStatusLastID OBJECT-TYPE
   SYNTAX      DisplayString
   MAX-ACCESS  read-only
   STATUS      current
   DESCRIPTION
       "The user name (supplicant identity) carried in the most recently received Response Identity EAPOL frame 
	   for EAPOL-based authentication, and the source MAC address from the most recently received frame from a 
	   new client for MAC-based authentication."
   ::= { gs2352pNASSwitchStatusEntry 5 }      

gs2352pNASSwitchStatusQoSClass OBJECT-TYPE
   SYNTAX      DisplayString
   MAX-ACCESS  read-only
   STATUS      current
   DESCRIPTION
       "QoS Class assigned to the port by the RADIUS server if enabled."
   ::= { gs2352pNASSwitchStatusEntry 6 } 
   
gs2352pNASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2352pNASSwitchStatusEntry 7 } 

gs2352pNASPortStatus                                 OBJECT IDENTIFIER ::= { gs2352pNAS 3 }
   
gs2352pNASPortStatusCountersTable OBJECT-TYPE
   SYNTAX      SEQUENCE OF Gs2352pNASPortStatusCountersEntry
   MAX-ACCESS  not-accessible
   STATUS      current
   DESCRIPTION
       ""
   ::= { gs2352pNASPortStatus 1 }

gs2352pNASPortStatusCountersEntry OBJECT-TYPE
   SYNTAX      Gs2352pNASPortStatusCountersEntry
   MAX-ACCESS  not-accessible
   STATUS      current
   DESCRIPTION
       ""
   INDEX    { gs2352pNASPortConfigPort }
   ::= { gs2352pNASPortStatusCountersTable 1 }

Gs2352pNASPortStatusCountersEntry ::= SEQUENCE {
   gs2352pNASRxCountersEAPOLTotal  	                  Counter32,
   gs2352pNASRxCountersEAPOLResponseID	              Counter32,
   gs2352pNASRxCountersEAPOLResponses	              Counter32,
   gs2352pNASRxCountersEAPOLStart	                  Counter32,
   gs2352pNASRxCountersEAPOLLogoff                    Counter32,
   gs2352pNASRxCountersEAPOLInvalidType               Counter32,
   gs2352pNASRxCountersEAPOLInvalidLength             Counter32,
   gs2352pNASTxCountersEAPOLTotal                     Counter32,
   gs2352pNASTxCountersEAPOLRequestID                 Counter32,
   gs2352pNASTxCountersEAPOLRequests                  Counter32,
   gs2352pNASRxBackendServerCountersAccessChallenges  Counter32,
   gs2352pNASRxBackendServerCountersOtherRequests     Counter32,
   gs2352pNASRxBackendServerCountersAuthSuccesses     Counter32,
   gs2352pNASRxBackendServerCountersAuthFailures      Counter32,
   gs2352pNASTxBackendServerCountersResponses         Counter32,
   gs2352pNASLastSupplicantInfoMACAddress             DisplayString,
   gs2352pNASLastSupplicantInfoVlanID                 Integer32,
   gs2352pNASLastSupplicantInfoVersion                Integer32,
   gs2352pNASLastSupplicantInfoIdentity               DisplayString,
   gs2352pNASCountersDoClear                          INTEGER
}

gs2352pNASRxCountersEAPOLTotal OBJECT-TYPE
   SYNTAX      Counter32
   MAX-ACCESS  read-only
   STATUS      current
   DESCRIPTION
       "The number of valid EAPOL frames of any type that have been received by the switch."
   ::= { gs2352pNASPortStatusCountersEntry 2 }   

gs2352pNASRxCountersEAPOLResponseID OBJECT-TYPE
   SYNTAX      Counter32
   MAX-ACCESS  read-only
   STATUS      current
   DESCRIPTION
       "The number of valid EAPOL Response Identity frames that have been received by the switch."
   ::= { gs2352pNASPortStatusCountersEntry 3 }   

gs2352pNASRxCountersEAPOLResponses OBJECT-TYPE
   SYNTAX      Counter32
   MAX-ACCESS  read-only
   STATUS      current
   DESCRIPTION
       "The number of valid EAPOL response frames (other than Response Identity frames) 
	   that have been received by the switch."
   ::= { gs2352pNASPortStatusCountersEntry 4 }   

gs2352pNASRxCountersEAPOLStart OBJECT-TYPE
   SYNTAX      Counter32
   MAX-ACCESS  read-only
   STATUS      current
   DESCRIPTION
       "The number of EAPOL Start frames that have been received by the switch."
   ::= { gs2352pNASPortStatusCountersEntry 5 }   

gs2352pNASRxCountersEAPOLLogoff OBJECT-TYPE
   SYNTAX      Counter32
   MAX-ACCESS  read-only
   STATUS      current
   DESCRIPTION
       "The number of valid EAPOL Logoff frames that have been received by the switch."
   ::= { gs2352pNASPortStatusCountersEntry 6 }   

gs2352pNASRxCountersEAPOLInvalidType OBJECT-TYPE
   SYNTAX      Counter32
   MAX-ACCESS  read-only
   STATUS      current
   DESCRIPTION
       "The number of EAPOL frames that have been received by the switch in which 
	   the frame type is not recognized."
   ::= { gs2352pNASPortStatusCountersEntry 7 }   
   
gs2352pNASRxCountersEAPOLInvalidLength OBJECT-TYPE
   SYNTAX      Counter32
   MAX-ACCESS  read-only
   STATUS      current
   DESCRIPTION
       "The number of EAPOL frames that have been received by the switch in which the 
	   Packet Body Length field is invalid."
   ::= { gs2352pNASPortStatusCountersEntry 8 }   
   
gs2352pNASTxCountersEAPOLTotal OBJECT-TYPE
   SYNTAX      Counter32
   MAX-ACCESS  read-only
   STATUS      current
   DESCRIPTION
       "The number of EAPOL frames of any type that have been transmitted by the switch."
   ::= { gs2352pNASPortStatusCountersEntry 9 }   
   
gs2352pNASTxCountersEAPOLRequestID OBJECT-TYPE
   SYNTAX      Counter32
   MAX-ACCESS  read-only
   STATUS      current
   DESCRIPTION
       "The number of EAPOL Request Identity frames that have been transmitted by the switch."
   ::= { gs2352pNASPortStatusCountersEntry 10 }      

gs2352pNASTxCountersEAPOLRequests OBJECT-TYPE
   SYNTAX      Counter32
   MAX-ACCESS  read-only
   STATUS      current
   DESCRIPTION
       "The number of valid EAPOL Request frames (other than Request Identity frames) 
	   that have been transmitted by the switch."
   ::= { gs2352pNASPortStatusCountersEntry 11 }      
   
gs2352pNASRxBackendServerCountersAccessChallenges OBJECT-TYPE
   SYNTAX      Counter32
   MAX-ACCESS  read-only
   STATUS      current
   DESCRIPTION
       "802.1X-based: Counts the number of times that the switch receives the first request 
	   from the backend server following the first response from the supplicant.
	   MAC-based: Counts all Access Challenges received from the backend server for this 
	   port or client."
   ::= { gs2352pNASPortStatusCountersEntry 12 }      

gs2352pNASRxBackendServerCountersOtherRequests OBJECT-TYPE
   SYNTAX      Counter32
   MAX-ACCESS  read-only
   STATUS      current
   DESCRIPTION
       "802.1X-based: Counts the number of times that the switch sends an EAP Request 
	   packet following the first to the supplicant.
	   MAC-based: Not applicable."
   ::= { gs2352pNASPortStatusCountersEntry 13 }      
   
gs2352pNASRxBackendServerCountersAuthSuccesses OBJECT-TYPE
   SYNTAX      Counter32
   MAX-ACCESS  read-only
   STATUS      current
   DESCRIPTION
       "Counts the number of times that the switch receives a success indication. 
	   Indicates that the supplicant/client has successfully authenticated to the 
	   backend server."
   ::= { gs2352pNASPortStatusCountersEntry 14 }      
   
gs2352pNASRxBackendServerCountersAuthFailures OBJECT-TYPE
   SYNTAX      Counter32
   MAX-ACCESS  read-only
   STATUS      current
   DESCRIPTION
       "Counts the number of times that the switch receives a failure message. 
	   This indicates that the supplicant/client has not authenticated to the 
	   backend server. "
   ::= { gs2352pNASPortStatusCountersEntry 15 }      
   
gs2352pNASTxBackendServerCountersResponses OBJECT-TYPE
   SYNTAX      Counter32
   MAX-ACCESS  read-only
   STATUS      current
   DESCRIPTION
       "802.1X-based: Counts the number of times that the switch attempts to 
	   send a supplicant's first response packet to the backend server. Indicates 
	   the switch attempted communication with the backend server. Possible 
	   retransmissions are not counted. 
	   MAC-based: Counts all the backend server packets sent from the switch 
	   towards the backend server for a given port or client. Possible 
	   retransmissions are not counted."
   ::= { gs2352pNASPortStatusCountersEntry 16 }  

gs2352pNASLastSupplicantInfoMACAddress OBJECT-TYPE
   SYNTAX      DisplayString
   MAX-ACCESS  read-only
   STATUS      current
   DESCRIPTION
       "The MAC address of the last supplicant/client."
   ::= { gs2352pNASPortStatusCountersEntry 17 }  

gs2352pNASLastSupplicantInfoVlanID OBJECT-TYPE
   SYNTAX      Integer32
   MAX-ACCESS  read-only
   STATUS      current
   DESCRIPTION
       "The VLAN ID on which the last frame from the last supplicant/client was received."
   ::= { gs2352pNASPortStatusCountersEntry 18 }  
   
gs2352pNASLastSupplicantInfoVersion OBJECT-TYPE
   SYNTAX      Integer32
   MAX-ACCESS  read-only
   STATUS      current
   DESCRIPTION
       "802.1X-based: The protocol version number carried in the most recently 
	   received EAPOL frame. 
	   MAC-based: Not applicable."
   ::= { gs2352pNASPortStatusCountersEntry 19 }  

gs2352pNASLastSupplicantInfoIdentity OBJECT-TYPE
   SYNTAX      DisplayString
   MAX-ACCESS  read-only
   STATUS      current
   DESCRIPTION
       "802.1X-based: The user name (supplicant identity) carried in the most recently received 
	   Response Identity EAPOL frame. 
	   MAC-based: Not applicable."
   ::= { gs2352pNASPortStatusCountersEntry 20 }  

gs2352pNASCountersDoClear OBJECT-TYPE
   SYNTAX      INTEGER { doNothing(0), do(1) }
   MAX-ACCESS  read-write
   STATUS      current
   DESCRIPTION
       "Clear the counters for the selected port."
   ::= { gs2352pNASPortStatusCountersEntry 21 }    

gs2352pNASPortStatusClientsTable OBJECT-TYPE
   SYNTAX      SEQUENCE OF Gs2352pNASPortStatusClientsEntry
   MAX-ACCESS  not-accessible
   STATUS      current
   DESCRIPTION
       ""
   ::= { gs2352pNASPortStatus 2 }

gs2352pNASPortStatusClientsEntry OBJECT-TYPE
   SYNTAX      Gs2352pNASPortStatusClientsEntry
   MAX-ACCESS  not-accessible
   STATUS      current
   DESCRIPTION
       ""
   INDEX    { gs2352pNASPortConfigPort,
		gs2352pNASClientsIndex}
   ::= { gs2352pNASPortStatusClientsTable 1 }

Gs2352pNASPortStatusClientsEntry ::= SEQUENCE {
   gs2352pNASClientsIndex  	                  		    Integer32,
   gs2352pNASClientsIdentity							DisplayString,
   gs2352pNASClientsMACAddress  	                  	DisplayString,
   gs2352pNASClientsVlanID		              			Integer32,
   gs2352pNASClientsState	              				DisplayString,
   gs2352pNASClientsLastAuth	                  		DisplayString,
   gs2352pNASRxClientsEAPOLTotal  	                  	Counter32,
   gs2352pNASRxClientsEAPOLResponseID	              	Counter32,
   gs2352pNASRxClientsEAPOLResponses	              	Counter32,
   gs2352pNASRxClientsEAPOLStart	                  	Counter32,
   gs2352pNASRxClientsEAPOLLogoff                    	Counter32,
   gs2352pNASRxClientsEAPOLInvalidType               	Counter32,
   gs2352pNASRxClientsEAPOLInvalidLength             	Counter32,
   gs2352pNASTxClientsEAPOLTotal                     	Counter32,
   gs2352pNASTxClientsEAPOLRequestID                 	Counter32,
   gs2352pNASTxClientsEAPOLRequests                  	Counter32,
   gs2352pNASRxBackendServerClientsAccessChallenges  	Counter32,
   gs2352pNASRxBackendServerClientsOtherRequests     	Counter32,
   gs2352pNASRxBackendServerClientsAuthSuccesses     	Counter32,
   gs2352pNASRxBackendServerClientsAuthFailures      	Counter32,
   gs2352pNASTxBackendServerClientsResponses         	Counter32
}

gs2352pNASClientsIndex OBJECT-TYPE
   SYNTAX      Integer32(1..255)
   MAX-ACCESS  not-accessible
   STATUS      current
   DESCRIPTION
       "Entry of client table in the port."
   ::= { gs2352pNASPortStatusClientsEntry 1 } 
   
gs2352pNASClientsIdentity OBJECT-TYPE
   SYNTAX      DisplayString
   MAX-ACCESS  read-only
   STATUS      current
   DESCRIPTION
       "Shows the identity of the supplicant, as received in the Response Identity 
	   EAPOL frame.This isn't available for MAC-based Auth."
   ::= { gs2352pNASPortStatusClientsEntry 2 }
   
gs2352pNASClientsMACAddress OBJECT-TYPE
   SYNTAX      DisplayString
   MAX-ACCESS  read-only
   STATUS      current
   DESCRIPTION
       "Multi 802.1X, this column holds the MAC address of the attached supplicant. 
	   MAC-based Auth., this column holds the MAC address of the attached client."
   ::= { gs2352pNASPortStatusClientsEntry 3 }  

gs2352pNASClientsVlanID OBJECT-TYPE
   SYNTAX      Integer32(1..4095)
   MAX-ACCESS  read-only
   STATUS      current
   DESCRIPTION
       "This column holds the VLAN ID that the corresponding client is currently 
	   secured through the Port Security module."
   ::= { gs2352pNASPortStatusClientsEntry 4 }  
   
gs2352pNASClientsState OBJECT-TYPE
   SYNTAX      DisplayString
   MAX-ACCESS  read-only
   STATUS      current
   DESCRIPTION
       "The client can either be authenticated or unauthenticated. In the authenticated 
	   state, it is allowed to forward frames on the port, and in the unauthenticated 
	   state, it is blocked."
   ::= { gs2352pNASPortStatusClientsEntry 5 }  

gs2352pNASClientsLastAuth OBJECT-TYPE
   SYNTAX      DisplayString
   MAX-ACCESS  read-only
   STATUS      current
   DESCRIPTION
       "Shows the date and time of the last authentication of the client."
   ::= { gs2352pNASPortStatusClientsEntry 6 }  
   
gs2352pNASRxClientsEAPOLTotal OBJECT-TYPE
   SYNTAX      Counter32
   MAX-ACCESS  read-only
   STATUS      current
   DESCRIPTION
       "The number of valid EAPOL frames of any type that have been received by the switch."
   ::= { gs2352pNASPortStatusClientsEntry 7 }  

gs2352pNASRxClientsEAPOLResponseID OBJECT-TYPE
   SYNTAX      Counter32
   MAX-ACCESS  read-only
   STATUS      current
   DESCRIPTION
       "The number of valid EAPOL Response Identity frames that have been received by the switch."
   ::= { gs2352pNASPortStatusClientsEntry 8 }   

gs2352pNASRxClientsEAPOLResponses OBJECT-TYPE
   SYNTAX      Counter32
   MAX-ACCESS  read-only
   STATUS      current
   DESCRIPTION
       "The number of valid EAPOL response frames (other than Response Identity frames) 
	   that have been received by the switch."
   ::= { gs2352pNASPortStatusClientsEntry 9 }   

gs2352pNASRxClientsEAPOLStart OBJECT-TYPE
   SYNTAX      Counter32
   MAX-ACCESS  read-only
   STATUS      current
   DESCRIPTION
       "The number of EAPOL Start frames that have been received by the switch."
   ::= { gs2352pNASPortStatusClientsEntry 10 }   

gs2352pNASRxClientsEAPOLLogoff OBJECT-TYPE
   SYNTAX      Counter32
   MAX-ACCESS  read-only
   STATUS      current
   DESCRIPTION
       "The number of valid EAPOL Logoff frames that have been received by the switch."
   ::= { gs2352pNASPortStatusClientsEntry 11 }   

gs2352pNASRxClientsEAPOLInvalidType OBJECT-TYPE
   SYNTAX      Counter32
   MAX-ACCESS  read-only
   STATUS      current
   DESCRIPTION
       "The number of EAPOL frames that have been received by the switch in which 
	   the frame type is not recognized."
   ::= { gs2352pNASPortStatusClientsEntry 12 }   
   
gs2352pNASRxClientsEAPOLInvalidLength OBJECT-TYPE
   SYNTAX      Counter32
   MAX-ACCESS  read-only
   STATUS      current
   DESCRIPTION
       "The number of EAPOL frames that have been received by the switch in which the 
	   Packet Body Length field is invalid."
   ::= { gs2352pNASPortStatusClientsEntry 13 }

gs2352pNASTxClientsEAPOLTotal OBJECT-TYPE
   SYNTAX      Counter32
   MAX-ACCESS  read-only
   STATUS      current
   DESCRIPTION
       "The number of EAPOL frames of any type that have been transmitted by the switch."
   ::= { gs2352pNASPortStatusClientsEntry 14 }   
   
gs2352pNASTxClientsEAPOLRequestID OBJECT-TYPE
   SYNTAX      Counter32
   MAX-ACCESS  read-only
   STATUS      current
   DESCRIPTION
       "The number of EAPOL Request Identity frames that have been transmitted by the switch."
   ::= { gs2352pNASPortStatusClientsEntry 15 }      

gs2352pNASTxClientsEAPOLRequests OBJECT-TYPE
   SYNTAX      Counter32
   MAX-ACCESS  read-only
   STATUS      current
   DESCRIPTION
       "The number of valid EAPOL Request frames (other than Request Identity frames) 
	   that have been transmitted by the switch."
   ::= { gs2352pNASPortStatusClientsEntry 16 }        

gs2352pNASRxBackendServerClientsAccessChallenges OBJECT-TYPE
   SYNTAX      Counter32
   MAX-ACCESS  read-only
   STATUS      current
   DESCRIPTION
       "802.1X-based: Counts the number of times that the switch receives the first request 
	   from the backend server following the first response from the supplicant.
	   MAC-based: Counts all Access Challenges received from the backend server for this 
	   port or client."
   ::= { gs2352pNASPortStatusClientsEntry 17 }      

gs2352pNASRxBackendServerClientsOtherRequests OBJECT-TYPE
   SYNTAX      Counter32
   MAX-ACCESS  read-only
   STATUS      current
   DESCRIPTION
       "802.1X-based: Counts the number of times that the switch sends an EAP Request 
	   packet following the first to the supplicant.
	   MAC-based: Not applicable."
   ::= { gs2352pNASPortStatusClientsEntry 18 }      
   
gs2352pNASRxBackendServerClientsAuthSuccesses OBJECT-TYPE
   SYNTAX      Counter32
   MAX-ACCESS  read-only
   STATUS      current
   DESCRIPTION
       "Counts the number of times that the switch receives a success indication. 
	   Indicates that the supplicant/client has successfully authenticated to the 
	   backend server."
   ::= { gs2352pNASPortStatusClientsEntry 19 }      
   
gs2352pNASRxBackendServerClientsAuthFailures OBJECT-TYPE
   SYNTAX      Counter32
   MAX-ACCESS  read-only
   STATUS      current
   DESCRIPTION
       "Counts the number of times that the switch receives a failure message. 
	   This indicates that the supplicant/client has not authenticated to the 
	   backend server. "
   ::= { gs2352pNASPortStatusClientsEntry 20 }      
   
gs2352pNASTxBackendServerClientsResponses OBJECT-TYPE
   SYNTAX      Counter32
   MAX-ACCESS  read-only
   STATUS      current
   DESCRIPTION
       "802.1X-based: Counts the number of times that the switch attempts to 
	   send a supplicant's first response packet to the backend server. Indicates 
	   the switch attempted communication with the backend server. Possible 
	   retransmissions are not counted. 
	   MAC-based: Counts all the backend server packets sent from the switch 
	   towards the backend server for a given port or client. Possible 
	   retransmissions are not counted."
   ::= { gs2352pNASPortStatusClientsEntry 21 }  


gs2352pMaintenance                                           OBJECT IDENTIFIER ::= { lancomGS2352P 4 }

gs2352pRestartDevice OBJECT-TYPE
   SYNTAX      INTEGER { disable(0), enable(1) }
   MAX-ACCESS  read-write
   STATUS      current
   DESCRIPTION
       "default: 0
        0:none
        1:yes"
   ::= { gs2352pMaintenance 1 }

gs2352pColdRestartDevice OBJECT-TYPE
   SYNTAX      INTEGER { disable(0), enable(1) }
   MAX-ACCESS  read-write
   STATUS      current
   DESCRIPTION
       "default: 0
        0:none
        1:yes"
   ::= { gs2352pMaintenance 1500 }

gs2352pFirmware                                         OBJECT IDENTIFIER ::= { gs2352pMaintenance 2 }

gs2352pFirmwareIpAddress OBJECT-TYPE
   SYNTAX       IpAddress
   MAX-ACCESS   read-write
   STATUS       current
   DESCRIPTION
        "Get/Set the firmware tftp server."
   ::= { gs2352pFirmware 1 }

gs2352pFirmwareFileName OBJECT-TYPE
   SYNTAX       DisplayString
   MAX-ACCESS   read-write
   STATUS       current
   DESCRIPTION
        "Get/Set the path and filename for firmware upgrading."
   ::= { gs2352pFirmware 2 }

gs2352pDoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2352pFirmware 3 }

gs2352pSaveOrRestore                                         OBJECT IDENTIFIER ::= { gs2352pMaintenance 3 }

gs2352pFactoryDefaults OBJECT-TYPE
   SYNTAX      INTEGER { none(0), yes(1) }
   MAX-ACCESS  read-write
   STATUS      current
   DESCRIPTION
       "default: 0
        0:none
        1:yes"
   ::= { gs2352pSaveOrRestore 1 }

gs2352pSaveStart OBJECT-TYPE
   SYNTAX      INTEGER { none(0), yes(1) }
   MAX-ACCESS  read-write
   STATUS      current
   DESCRIPTION
       "default: 0
        0:none
        1:yes"
   ::= { gs2352pSaveOrRestore 2 }

gs2352pSaveUser OBJECT-TYPE
   SYNTAX      INTEGER { none(0), yes(1) }
   MAX-ACCESS  read-write
   STATUS      current
   DESCRIPTION
       "default: 0
        0:none
        1:yes"
   ::= { gs2352pSaveOrRestore 3 }

gs2352pRestoreUser OBJECT-TYPE
   SYNTAX      INTEGER { none(0), yes(1) }
   MAX-ACCESS  read-write
   STATUS      current
   DESCRIPTION
       "default: 0
        0:none
        1:yes"
   ::= { gs2352pSaveOrRestore 4 }


gs2352pExportOrImport                                        OBJECT IDENTIFIER ::= { gs2352pMaintenance 4 }

gs2352pExportIpAddress OBJECT-TYPE
   SYNTAX       IpAddress
   MAX-ACCESS   read-write
   STATUS       current
   DESCRIPTION
        "Get/Set the export tftp server."
   ::= { gs2352pExportOrImport 1 }

gs2352pExportConfigName OBJECT-TYPE
   SYNTAX       DisplayString
   MAX-ACCESS   read-write
   STATUS       current
   DESCRIPTION
       "Get/Set the export file path and name."
   ::= { gs2352pExportOrImport 2 }

gs2352pDoExportConfig OBJECT-TYPE
   SYNTAX       INTEGER{ doNothing(0), do(1) }
   MAX-ACCESS   read-write
   STATUS       current
   DESCRIPTION
        "Do export-config.
         Get this OID always return zero.
         1 - export."
   ::= { gs2352pExportOrImport 3 }

gs2352pImportIpAddress OBJECT-TYPE
   SYNTAX       IpAddress
   MAX-ACCESS   read-write
   STATUS       current
   DESCRIPTION
        "Get/Set the import tftp server."
   ::= { gs2352pExportOrImport 4 }

gs2352pImportConfigName OBJECT-TYPE
   SYNTAX      DisplayString
   MAX-ACCESS  read-write
   STATUS      current
   DESCRIPTION
       "Get/Set the import file path and name."
   ::= { gs2352pExportOrImport 5 }

gs2352pDoImportConfig OBJECT-TYPE
   SYNTAX       INTEGER{ doNothing(0), do(1) }
   MAX-ACCESS   read-write
   STATUS       current
   DESCRIPTION
        "Do export-config.
         Get this OID always return zero.
         1 - import."
   ::= { gs2352pExportOrImport 6 }

gs2352pDiagnostics                                           OBJECT IDENTIFIER ::= { gs2352pMaintenance 5 }

gs2352pPingIpAddress OBJECT-TYPE
   SYNTAX      IpAddress
   MAX-ACCESS  read-write
   STATUS      current
   DESCRIPTION
       " The destination IP Address. "
   ::= { gs2352pDiagnostics 1 }
   
gs2352pPingSize OBJECT-TYPE
   SYNTAX      Integer32(0|60..1400)
   MAX-ACCESS  read-write
   STATUS      current
   DESCRIPTION
       " Size of ICMP echo packet.
         range : 60-1400, default : 64. "
   ::= { gs2352pDiagnostics 2 }   

gs2352pDoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2352pDiagnostics 3 }

gs2352pPingResult OBJECT-TYPE
   SYNTAX      DisplayString
   MAX-ACCESS  read-only
   STATUS      current
   DESCRIPTION
       " Show ping result. "
   ::= { gs2352pDiagnostics 4 }

gs2352pPing6IpAddress OBJECT-TYPE
   SYNTAX      DisplayString
   MAX-ACCESS  read-write
   STATUS      current
   DESCRIPTION
       " The destination IPv6 Address. "
   ::= { gs2352pDiagnostics 5 }
   
gs2352pPing6Size OBJECT-TYPE
   SYNTAX      Integer32(0|60..1400)
   MAX-ACCESS  read-write
   STATUS      current
   DESCRIPTION
       " Size of ICMP echo packet.
         range : 60-1400, default : 64. "
   ::= { gs2352pDiagnostics 6 }   

gs2352pDoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2352pDiagnostics 7 }

gs2352pPing6Result OBJECT-TYPE
   SYNTAX      DisplayString
   MAX-ACCESS  read-only
   STATUS      current
   DESCRIPTION
       " Show ping result. "
   ::= { gs2352pDiagnostics 8 }


gs2352pVeriPHY                                           OBJECT IDENTIFIER ::= { gs2352pDiagnostics 9 }

gs2352pVeriPHYTest OBJECT-TYPE
   SYNTAX      Integer32(1..4095)
   MAX-ACCESS  read-write
   STATUS      current
   DESCRIPTION
       "Run VeriPHY Cable Diagnostics.
        port, range : 0 - port number.
        0 : ALL "
   ::= { gs2352pVeriPHY 1 }

gs2352pVeriPHYTable OBJECT-TYPE
   SYNTAX      SEQUENCE OF GS2352PVeriPHYEntry
   MAX-ACCESS  not-accessible
   STATUS      current
   DESCRIPTION
       " "
   ::= { gs2352pVeriPHY 2 }

gs2352pVeriPHYEntry OBJECT-TYPE
   SYNTAX      GS2352PVeriPHYEntry
   MAX-ACCESS  not-accessible
   STATUS      current
   DESCRIPTION
       ""
   INDEX    { gs2352pVeriPHYPort  }
   ::= { gs2352pVeriPHYTable 1 }

GS2352PVeriPHYEntry ::= SEQUENCE {
   gs2352pVeriPHYPort        Integer32,
   gs2352pVeriPHYPairA       DisplayString,
   gs2352pVeriPHYLengthA     DisplayString,
   gs2352pVeriPHYPairB       DisplayString,
   gs2352pVeriPHYLengthB     DisplayString,
   gs2352pVeriPHYPairC       DisplayString,
   gs2352pVeriPHYLengthC     DisplayString,
   gs2352pVeriPHYPairD       DisplayString,
   gs2352pVeriPHYLengthD     DisplayString
}

gs2352pVeriPHYPort OBJECT-TYPE
   SYNTAX      Integer32(1..4095)
   MAX-ACCESS  not-accessible
   STATUS      current
   DESCRIPTION
       " The length (in meters) of the cable pair. "
   ::= { gs2352pVeriPHYEntry 1 }

gs2352pVeriPHYPairA OBJECT-TYPE
   SYNTAX      DisplayString
   MAX-ACCESS  read-only
   STATUS      current
   DESCRIPTION
       " The status of the cable pair. "
   ::= { gs2352pVeriPHYEntry 2 }

gs2352pVeriPHYLengthA OBJECT-TYPE
   SYNTAX      DisplayString
   MAX-ACCESS  read-only
   STATUS      current
   DESCRIPTION
       " The length (in meters) of the cable pair. "
   ::= { gs2352pVeriPHYEntry 3 }

gs2352pVeriPHYPairB OBJECT-TYPE
   SYNTAX      DisplayString
   MAX-ACCESS  read-only
   STATUS      current
   DESCRIPTION
       " The status of the cable pair. "
   ::= { gs2352pVeriPHYEntry 4 }

gs2352pVeriPHYLengthB OBJECT-TYPE
   SYNTAX      DisplayString
   MAX-ACCESS  read-only
   STATUS      current
   DESCRIPTION
       " The length (in meters) of the cable pair. "
   ::= { gs2352pVeriPHYEntry 5 }

gs2352pVeriPHYPairC OBJECT-TYPE
   SYNTAX      DisplayString
   MAX-ACCESS  read-only
   STATUS      current
   DESCRIPTION
       " The status of the cable pair. "
   ::= { gs2352pVeriPHYEntry 6 }

gs2352pVeriPHYLengthC OBJECT-TYPE
   SYNTAX      DisplayString
   MAX-ACCESS  read-only
   STATUS      current
   DESCRIPTION
       " The length (in meters) of the cable pair. "
   ::= { gs2352pVeriPHYEntry 7 }

gs2352pVeriPHYPairD OBJECT-TYPE
   SYNTAX      DisplayString
   MAX-ACCESS  read-only
   STATUS      current
   DESCRIPTION
       " The status of the cable pair. "
   ::= { gs2352pVeriPHYEntry 8 }

gs2352pVeriPHYLengthD OBJECT-TYPE
   SYNTAX      DisplayString
   MAX-ACCESS  read-only
   STATUS      current
   DESCRIPTION
       " The length (in meters) of the cable pair. "
   ::= { gs2352pVeriPHYEntry 9 }


------------------------------------------------------------------------------------------------------------------
gs2352pTrap                                                  OBJECT IDENTIFIER ::= { lancomGS2352P 5 }

gs2352pTrapEvent                                             OBJECT IDENTIFIER ::= { gs2352pTrap 1 }

gs2352pEmergency NOTIFICATION-TYPE
  OBJECTS   { gs2352pInformation }
  STATUS        current
    DESCRIPTION
        "The severity level is Emergency. The system is unusable."
    ::= { gs2352pTrapEvent 1 }

gs2352pAlert NOTIFICATION-TYPE
  OBJECTS   { gs2352pInformation }
  STATUS        current
    DESCRIPTION
        "The severity level is Alert. The action must be taken immediately."
    ::= { gs2352pTrapEvent 2 }

gs2352pCritical NOTIFICATION-TYPE
  OBJECTS   { gs2352pInformation }
  STATUS        current
    DESCRIPTION
        "The severity level is Critical. Critical conditions."
    ::= { gs2352pTrapEvent 3 }

gs2352pError NOTIFICATION-TYPE
  OBJECTS   { gs2352pInformation }
  STATUS        current
    DESCRIPTION
        "The severity level is Error. Error conditions."
    ::= { gs2352pTrapEvent 4 }

gs2352pWarning NOTIFICATION-TYPE
  OBJECTS   { gs2352pInformation }
  STATUS        current
    DESCRIPTION
        "The severity level is Warning. Warning conditions."
    ::= { gs2352pTrapEvent 5 }

gs2352pNotice NOTIFICATION-TYPE
  OBJECTS   { gs2352pInformation }
  STATUS        current
    DESCRIPTION
        "The severity level is Notice. Normal but significant condition."
    ::= { gs2352pTrapEvent 6 }

gs2352pInformational NOTIFICATION-TYPE
  OBJECTS   { gs2352pInformation }
  STATUS        current
    DESCRIPTION
        "The severity level is Informational. Informational messages."
    ::= { gs2352pTrapEvent 7 }

gs2352pDebug NOTIFICATION-TYPE
  OBJECTS   { gs2352pInformation }
  STATUS        current
    DESCRIPTION
        "The severity level is Debug. debug-level messages."
    ::= { gs2352pTrapEvent 8 }

gs2352pTrapVariable                                          OBJECT IDENTIFIER ::= { gs2352pTrap 2 }

gs2352pInformation OBJECT-TYPE
    SYNTAX      DisplayString
    MAX-ACCESS  read-only
    STATUS      current
    DESCRIPTION
        "Trap information."
    ::= { gs2352pTrapVariable 1 }


END

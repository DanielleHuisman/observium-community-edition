LANCOM-GS2310PPLUS-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2310PPLUS                                                   OBJECT IDENTIFIER ::= { gigabitEthernetSwitches 2312 }

gs2310pplusSystem                                                   OBJECT IDENTIFIER ::= { lancomGS2310PPLUS 1 }

gs2310pplusSystemInformation                                        OBJECT IDENTIFIER ::= { gs2310pplusSystem 1 }

gs2310pplusModelName OBJECT-TYPE
   SYNTAX       DisplayString
   MAX-ACCESS   read-only
   STATUS       current
   DESCRIPTION
       ""
 ::= { gs2310pplusSystemInformation 1 }

gs2310pplusBIOSVersion OBJECT-TYPE
   SYNTAX       DisplayString
   MAX-ACCESS   read-only
   STATUS       current
   DESCRIPTION
       ""
   ::= { gs2310pplusSystemInformation 2 }

gs2310pplusFirmwareVersion OBJECT-TYPE
   SYNTAX       DisplayString
   MAX-ACCESS   read-only
   STATUS       current
   DESCRIPTION
       ""
   ::= { gs2310pplusSystemInformation 3 }

gs2310pplusHardwareMechanicalVersion OBJECT-TYPE
   SYNTAX       DisplayString
   MAX-ACCESS   read-only
   STATUS       current
   DESCRIPTION
       ""
   ::= { gs2310pplusSystemInformation 4 }

gs2310pplusSerialNumber OBJECT-TYPE
   SYNTAX       DisplayString
   MAX-ACCESS   read-only
   STATUS       current
   DESCRIPTION
       ""
   ::= { gs2310pplusSystemInformation 5 }

gs2310pplusHostMACAddress OBJECT-TYPE
   SYNTAX       MacAddress
   MAX-ACCESS   read-only
   STATUS       current
   DESCRIPTION
       ""
   ::= { gs2310pplusSystemInformation 6 }

gs2310pplusConsoleBaudrate OBJECT-TYPE
   SYNTAX       DisplayString
   MAX-ACCESS   read-only
   STATUS       current
   DESCRIPTION
       ""
   ::= { gs2310pplusSystemInformation 7 }

gs2310pplusRAMSize OBJECT-TYPE
   SYNTAX       DisplayString
   MAX-ACCESS   read-only
   STATUS       current
   DESCRIPTION
       ""
   ::= { gs2310pplusSystemInformation 8 }

gs2310pplusFlashSize OBJECT-TYPE
   SYNTAX       DisplayString
   MAX-ACCESS   read-only
   STATUS       current
   DESCRIPTION
       ""
   ::= { gs2310pplusSystemInformation 9 }

gs2310pplusBridgeFDBSize OBJECT-TYPE
   SYNTAX       DisplayString
   MAX-ACCESS   read-only
   STATUS       current
   DESCRIPTION
       ""
   ::= { gs2310pplusSystemInformation 10 }

gs2310pplusTransmitQueue OBJECT-TYPE
   SYNTAX       DisplayString
   MAX-ACCESS   read-only
   STATUS       current
   DESCRIPTION
       ""
   ::= { gs2310pplusSystemInformation 11 }

gs2310pplusMaximumFrameSize OBJECT-TYPE
   SYNTAX       DisplayString
   MAX-ACCESS   read-only
   STATUS       current
   DESCRIPTION
       ""
   ::= { gs2310pplusSystemInformation 12 }

gs2310pplusCPULoad OBJECT-TYPE
   SYNTAX       DisplayString
   MAX-ACCESS   read-only
   STATUS       current
   DESCRIPTION
       ""
   ::= { gs2310pplusSystemInformation 13 }

gs2310pplusSystemDescription OBJECT-TYPE
   SYNTAX       DisplayString
   MAX-ACCESS   read-only
   STATUS       current
   DESCRIPTION
       ""
   ::= { gs2310pplusSystemInformation 21 }
   
gs2310pplusLocation OBJECT-TYPE
   SYNTAX       DisplayString
   MAX-ACCESS   read-only
   STATUS       current
   DESCRIPTION
       ""
   ::= { gs2310pplusSystemInformation 22 }
   
gs2310pplusContact OBJECT-TYPE
   SYNTAX       DisplayString
   MAX-ACCESS   read-only
   STATUS       current
   DESCRIPTION
       ""
   ::= { gs2310pplusSystemInformation 23 }
   
gs2310pplusDeviceName OBJECT-TYPE
   SYNTAX       DisplayString
   MAX-ACCESS   read-only
   STATUS       current
   DESCRIPTION
       ""
   ::= { gs2310pplusSystemInformation 24 }
   
gs2310pplusSystemDate OBJECT-TYPE
   SYNTAX       DisplayString
   MAX-ACCESS   read-only
   STATUS       current
   DESCRIPTION
       ""
   ::= { gs2310pplusSystemInformation 25 }
   
gs2310pplusSystemUptime OBJECT-TYPE
   SYNTAX       DisplayString
   MAX-ACCESS   read-only
   STATUS       current
   DESCRIPTION
       ""
   ::= { gs2310pplusSystemInformation 26 }
   
gs2310pplusSystemIPv4Address OBJECT-TYPE
   SYNTAX       DisplayString
   MAX-ACCESS   read-only
   STATUS       current
   DESCRIPTION
       ""
   ::= { gs2310pplusSystemInformation 27 }

gs2310pplusSystemIPv4SubnetMask OBJECT-TYPE
   SYNTAX       DisplayString
   MAX-ACCESS   read-only
   STATUS       current
   DESCRIPTION
       ""
   ::= { gs2310pplusSystemInformation 28 }
   
gs2310pplusSystemIPv4Gateway OBJECT-TYPE
   SYNTAX       DisplayString
   MAX-ACCESS   read-only
   STATUS       current
   DESCRIPTION
       ""
   ::= { gs2310pplusSystemInformation 29 }

gs2310pplusIPv6LinkLocalAddress OBJECT-TYPE
   SYNTAX       DisplayString
   MAX-ACCESS   read-only
   STATUS       current
   DESCRIPTION
       ""
   ::= { gs2310pplusSystemInformation 30 }

gs2310pplusIPv6Address OBJECT-TYPE
   SYNTAX       DisplayString
   MAX-ACCESS   read-only
   STATUS       current
   DESCRIPTION
       ""
   ::= { gs2310pplusSystemInformation 31 }

gs2310pplusIPv6Prefix OBJECT-TYPE
   SYNTAX       DisplayString
   MAX-ACCESS   read-only
   STATUS       current
   DESCRIPTION
       ""
   ::= { gs2310pplusSystemInformation 32 }
   
gs2310pplusIPv6Gateway OBJECT-TYPE
   SYNTAX       DisplayString
   MAX-ACCESS   read-only
   STATUS       current
   DESCRIPTION
       ""
   ::= { gs2310pplusSystemInformation 33 }

gs2310pplusLargestFreeMemBlock OBJECT-TYPE
   SYNTAX       Integer32
   MAX-ACCESS   read-only
   STATUS       current
   DESCRIPTION
       "Largest free memory block in Kb"
   ::= { gs2310pplusSystemInformation 1500 }   
   
gs2310pplusMemFree  OBJECT-TYPE
   SYNTAX       Integer32
   MAX-ACCESS   read-only
   STATUS       current
   DESCRIPTION
       "Free memory in Kb"
   ::= { gs2310pplusSystemInformation 1501 }


gs2310pplusSystemTime                                            OBJECT IDENTIFIER ::= { gs2310pplusSystem 2 }

gs2310pplusSystemTimeManual                                      OBJECT IDENTIFIER ::= { gs2310pplusSystemTime 1 }

gs2310pplusSystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2310pplusSystemTimeManual 1 }
   
gs2310pplusSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2310pplusSystemTimeManual 2 }

gs2310pplusSystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2310pplusSystemTimeManual 3 }
   
gs2310pplusSystemTimeManualDaylightSavings OBJECT-TYPE
   SYNTAX       INTEGER { disable(0), enable(1) }
   MAX-ACCESS   read-write
   STATUS       current
   DESCRIPTION
       "default: 0,
        0 : Disable,
        1 : Enable."
   ::= { gs2310pplusSystemTimeManual 4 }
   
gs2310pplusSystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2310pplusSystemTimeManual 5 }
   
gs2310pplusSystemTimeManualDaylightSavingsType OBJECT-TYPE
   SYNTAX       INTEGER { byDates(0), recurring(1) }
   MAX-ACCESS   read-write
   STATUS       current
   DESCRIPTION
       "default: 0,
        0 : By dates,
        1 : Recurring."
   ::= { gs2310pplusSystemTimeManual 6 }
   
gs2310pplusSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2310pplusSystemTimeManual 7 }
   
gs2310pplusSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2310pplusSystemTimeManual 8 }

gs2310pplusSystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2310pplusSystemTimeManual 9 }

gs2310pplusSystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2310pplusSystemTimeManual 10 }
   
gs2310pplusSystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2310pplusSystemTimeManual 11 }

gs2310pplusSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2310pplusSystemTimeManual 12 }
   
gs2310pplusSystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2310pplusSystemTimeManual 13 }

gs2310pplusSystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2310pplusSystemTimeManual 14 }
   
gs2310pplusSystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2310pplusSystemTimeManual 15 }

gs2310pplusSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2310pplusSystemTimeManual 16 }

gs2310pplusSystemTimeNTP                                     OBJECT IDENTIFIER ::= { gs2310pplusSystemTime 2 }

gs2310pplusSystemTimeNTPTable OBJECT-TYPE
   SYNTAX      SEQUENCE OF GS2310PPLUSSystemTimeNTPEntry
   MAX-ACCESS  not-accessible
   STATUS      current
   DESCRIPTION
       " "
   ::= { gs2310pplusSystemTimeNTP 1 }

gs2310pplusSystemTimeNTPEntry OBJECT-TYPE
   SYNTAX      GS2310PPLUSSystemTimeNTPEntry
   MAX-ACCESS  not-accessible
   STATUS      current
   DESCRIPTION
       ""
   INDEX    { gs2310pplusSystemTimeNTPIndex  }
   ::= { gs2310pplusSystemTimeNTPTable 1 }

GS2310PPLUSSystemTimeNTPEntry ::= SEQUENCE {
   gs2310pplusSystemTimeNTPIndex             Integer32,
   gs2310pplusSystemTimeNTPServerIPType      INTEGER,
   gs2310pplusSystemTimeNTPServer            DisplayString,
   gs2310pplusSystemTimeNTPCurrentMode       INTEGER
}

gs2310pplusSystemTimeNTPIndex OBJECT-TYPE
   SYNTAX      Integer32(1..5)
   MAX-ACCESS  not-accessible
   STATUS      current
   DESCRIPTION
       " The index of the ntp entry. "
   ::= { gs2310pplusSystemTimeNTPEntry 1 }

gs2310pplusSystemTimeNTPServerIPType OBJECT-TYPE
   SYNTAX       INTEGER { ipv4(0), ipv6(1) }
   MAX-ACCESS   read-write
   STATUS       current
   DESCRIPTION
       "Default: 0,
        0 : IPv4,
        1 : IPv6."
   ::= { gs2310pplusSystemTimeNTPEntry 2 }

gs2310pplusSystemTimeNTPServer OBJECT-TYPE
   SYNTAX       DisplayString
   MAX-ACCESS   read-write
   STATUS       current
   DESCRIPTION
       "Get/Set the NTP Time Server1. You can use the IP address or domain name."
   ::= { gs2310pplusSystemTimeNTPEntry 3 }

gs2310pplusSystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2310pplusSystemTimeNTPEntry 4 }

gs2310pplusSystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2310pplusSystemTimeNTP 2 }
   
gs2310pplusSystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2310pplusSystemTimeNTP 3 }
       

gs2310pplusSystemAccount                                         OBJECT IDENTIFIER ::= { gs2310pplusSystem 3 }

gs2310pplusSystemAccountUsers                                    OBJECT IDENTIFIER ::= { gs2310pplusSystemAccount 1 }

gs2310pplusSystemAccountUserCreate OBJECT-TYPE
   SYNTAX       INTEGER { none(0), create(1) }
   MAX-ACCESS   read-write
   STATUS       current
   DESCRIPTION
       "default: 0
        0 : None  (read only)
        1 : Create a user account"
   ::= { gs2310pplusSystemAccountUsers 1 }

gs2310pplusSystemAccountUsersTable OBJECT-TYPE
   SYNTAX      SEQUENCE OF GS2310PPLUSSystemAccountUsersEntry
   MAX-ACCESS  not-accessible
   STATUS      current
   DESCRIPTION
       " "
   ::= { gs2310pplusSystemAccountUsers 2 }

gs2310pplusSystemAccountUsersEntry OBJECT-TYPE
   SYNTAX      GS2310PPLUSSystemAccountUsersEntry
   MAX-ACCESS  not-accessible
   STATUS      current
   DESCRIPTION
       ""
   INDEX    { gs2310pplusUserIndex  }
   ::= { gs2310pplusSystemAccountUsersTable 1 }


GS2310PPLUSSystemAccountUsersEntry ::= SEQUENCE {
   gs2310pplusUserIndex              Integer32 ,
   gs2310pplusUserName               DisplayString,
   gs2310pplusPassword               DisplayString,
   gs2310pplusUserPrivilegeLevel     Integer32 ,
   gs2310pplusAccountUserRowStatus   INTEGER
}


gs2310pplusUserIndex OBJECT-TYPE
   SYNTAX      Integer32 (1..20)
   MAX-ACCESS  not-accessible
   STATUS      current
   DESCRIPTION
       " "
   ::= { gs2310pplusSystemAccountUsersEntry 1 }

gs2310pplusUserName OBJECT-TYPE
   SYNTAX      DisplayString (SIZE (1..32))
   MAX-ACCESS  read-write
   STATUS      current
   DESCRIPTION
       "Please use a combination of letters, numbers and underscores"
   ::= { gs2310pplusSystemAccountUsersEntry 2 }

gs2310pplusPassword OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2310pplusSystemAccountUsersEntry 3 }

gs2310pplusUserPrivilegeLevel OBJECT-TYPE
   SYNTAX      Integer32 (1..15)
   MAX-ACCESS  read-write
   STATUS      current
   DESCRIPTION
       "default:1 
        User privilege level range : 1 - 15"
   ::= { gs2310pplusSystemAccountUsersEntry 4 }

gs2310pplusAccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2310pplusSystemAccountUsersEntry 5 }

gs2310pplusSystemAccountUsersSuperUserPassword OBJECT-TYPE
   SYNTAX      OCTET STRING (SIZE (0..32))
   MAX-ACCESS read-write
   STATUS      current
   DESCRIPTION
        "Super-User Password"
   ::= { gs2310pplusSystemAccountUsers 1500 }

gs2310pplusSystemAccountEnforcePasswordRules OBJECT-TYPE
   SYNTAX       INTEGER { yes(0), no(1) }
   MAX-ACCESS   read-write
   STATUS       current
   DESCRIPTION
       "default: 0
        0 : Do not enforce rules
        1 : enforce rules"
   ::= { gs2310pplusSystemAccountUsers 1501 }

gs2310pplusSystemAccountPrivilegeLevel                           OBJECT IDENTIFIER ::= { gs2310pplusSystemAccount 2 }

gs2310pplusAccountPrivilegeLevel OBJECT-TYPE
   SYNTAX      Integer32 (1..15)
   MAX-ACCESS  read-write
   STATUS      current
   DESCRIPTION
       "Default:15, Range : 1-15. "
   ::= { gs2310pplusSystemAccountPrivilegeLevel 1 }

gs2310pplusAggregationPrivilegeLevel OBJECT-TYPE
   SYNTAX      Integer32 (1..15)
   MAX-ACCESS  read-write
   STATUS      current
   DESCRIPTION
       "Default:15, Range : 1-15. "
   ::= { gs2310pplusSystemAccountPrivilegeLevel 2 }

gs2310pplusDiagnosticsPrivilegeLevel OBJECT-TYPE
   SYNTAX      Integer32 (1..15)
   MAX-ACCESS  read-write
   STATUS      current
   DESCRIPTION
       "Default:15, Range : 1-15. "
   ::= { gs2310pplusSystemAccountPrivilegeLevel 3 }

gs2310pplusEEEPrivilegeLevel OBJECT-TYPE
   SYNTAX      Integer32 (1..15)
   MAX-ACCESS  read-write
   STATUS      current
   DESCRIPTION
       "Default:15, Range : 1-15. "
   ::= { gs2310pplusSystemAccountPrivilegeLevel 4 }

gs2310pplusEasyportPrivilegeLevel OBJECT-TYPE
   SYNTAX      Integer32 (1..15)
   MAX-ACCESS  read-write
   STATUS      current
   DESCRIPTION
       "Default:15, Range : 1-15. "
   ::= { gs2310pplusSystemAccountPrivilegeLevel 9 }

gs2310pplusGARPPrivilegeLevel OBJECT-TYPE
   SYNTAX      Integer32 (1..15)
   MAX-ACCESS  read-write
   STATUS      current
   DESCRIPTION
       "Default:15, Range : 1-15. "
   ::= { gs2310pplusSystemAccountPrivilegeLevel 10 }

gs2310pplusGVRPPrivilegeLevel OBJECT-TYPE
   SYNTAX      Integer32 (1..15)
   MAX-ACCESS  read-write
   STATUS      current
   DESCRIPTION
       "Default:15, Range : 1-15. "
   ::= { gs2310pplusSystemAccountPrivilegeLevel 11 }

gs2310pplusIPPrivilegeLevel OBJECT-TYPE
   SYNTAX      Integer32 (1..15)
   MAX-ACCESS  read-write
   STATUS      current
   DESCRIPTION
       "Default:15, Range : 1-15. "
   ::= { gs2310pplusSystemAccountPrivilegeLevel 12 }

gs2310pplusIPMCSnoopingPrivilegeLevel OBJECT-TYPE
   SYNTAX      Integer32 (1..15)
   MAX-ACCESS  read-write
   STATUS      current
   DESCRIPTION
       "Default:15, Range : 1-15. "
   ::= { gs2310pplusSystemAccountPrivilegeLevel 13 }

gs2310pplusLACPPrivilegeLevel OBJECT-TYPE
   SYNTAX      Integer32 (1..15)
   MAX-ACCESS  read-write
   STATUS      current
   DESCRIPTION
       "Default:15, Range : 1-15. "
   ::= { gs2310pplusSystemAccountPrivilegeLevel 14 }

gs2310pplusLLDPPrivilegeLevel OBJECT-TYPE
   SYNTAX      Integer32 (1..15)
   MAX-ACCESS  read-write
   STATUS      current
   DESCRIPTION
       "Default:15, Range : 1-15. "
   ::= { gs2310pplusSystemAccountPrivilegeLevel 15 }

gs2310pplusLLDPMEDPrivilegeLevel OBJECT-TYPE
   SYNTAX      Integer32 (1..15)
   MAX-ACCESS  read-write
   STATUS      current
   DESCRIPTION
       "Default:15, Range : 1-15. "
   ::= { gs2310pplusSystemAccountPrivilegeLevel 16 }

gs2310pplusLoopProtectPrivilegeLevel OBJECT-TYPE
   SYNTAX      Integer32 (1..15)
   MAX-ACCESS  read-write
   STATUS      current
   DESCRIPTION
       "Default:15, Range : 1-15. "
   ::= { gs2310pplusSystemAccountPrivilegeLevel 17 }

gs2310pplusMACTablePrivilegeLevel OBJECT-TYPE
   SYNTAX      Integer32 (1..15)
   MAX-ACCESS  read-write
   STATUS      current
   DESCRIPTION
       "Default:15, Range : 1-15. "
   ::= { gs2310pplusSystemAccountPrivilegeLevel 18 }

gs2310pplusMVRPrivilegeLevel OBJECT-TYPE
   SYNTAX      Integer32 (1..15)
   MAX-ACCESS  read-write
   STATUS      current
   DESCRIPTION
       "Default:15, Range : 1-15. "
   ::= { gs2310pplusSystemAccountPrivilegeLevel 22 }

gs2310pplusMaintenancePrivilegeLevel OBJECT-TYPE
   SYNTAX      Integer32 (1..15)
   MAX-ACCESS  read-write
   STATUS      current
   DESCRIPTION
       "Default:15, Range : 1-15. "
   ::= { gs2310pplusSystemAccountPrivilegeLevel 24 }

gs2310pplusMirroringPrivilegeLevel OBJECT-TYPE
   SYNTAX      Integer32 (1..15)
   MAX-ACCESS  read-write
   STATUS      current
   DESCRIPTION
       "Default:15, Range : 1-15. "
   ::= { gs2310pplusSystemAccountPrivilegeLevel 25 }

gs2310pplusPortsPrivilegeLevel OBJECT-TYPE
   SYNTAX      Integer32 (1..15)
   MAX-ACCESS  read-write
   STATUS      current
   DESCRIPTION
       "Default:15, Range : 1-15. "
   ::= { gs2310pplusSystemAccountPrivilegeLevel 27 }

gs2310pplusPrivateVLANsPrivilegeLevel OBJECT-TYPE
   SYNTAX      Integer32 (1..15)
   MAX-ACCESS  read-write
   STATUS      current
   DESCRIPTION
       "Default:15, Range : 1-15. "
   ::= { gs2310pplusSystemAccountPrivilegeLevel 28 }

gs2310pplusQoSPrivilegeLevel OBJECT-TYPE
   SYNTAX      Integer32 (1..15)
   MAX-ACCESS  read-write
   STATUS      current
   DESCRIPTION
       "Default:15, Range : 1-15. "
   ::= { gs2310pplusSystemAccountPrivilegeLevel 29 }

gs2310pplusSFlowPrivilegeLevel OBJECT-TYPE
   SYNTAX      Integer32 (1..15)
   MAX-ACCESS  read-write
   STATUS      current
   DESCRIPTION
       "Default:15, Range : 1-15. "
   ::= { gs2310pplusSystemAccountPrivilegeLevel 30 }

gs2310pplusSMTPPrivilegeLevel OBJECT-TYPE
   SYNTAX      Integer32 (1..15)
   MAX-ACCESS  read-write
   STATUS      current
   DESCRIPTION
       "Default:15, Range : 1-15. "
   ::= { gs2310pplusSystemAccountPrivilegeLevel 31 }

gs2310pplusSNMPPrivilegeLevel OBJECT-TYPE
   SYNTAX      Integer32 (1..15)
   MAX-ACCESS  read-write
   STATUS      current
   DESCRIPTION
       "Default:15, Range : 1-15. "
   ::= { gs2310pplusSystemAccountPrivilegeLevel 32 }

gs2310pplusSecurityPrivilegeLevel OBJECT-TYPE
   SYNTAX      Integer32 (1..15)
   MAX-ACCESS  read-write
   STATUS      current
   DESCRIPTION
       "Default:15, Range : 1-15. "
   ::= { gs2310pplusSystemAccountPrivilegeLevel 33 }

gs2310pplusSingleIPPrivilegeLevel OBJECT-TYPE
   SYNTAX      Integer32 (1..15)
   MAX-ACCESS  read-write
   STATUS      current
   DESCRIPTION
       "Default:15, Range : 1-15. "
   ::= { gs2310pplusSystemAccountPrivilegeLevel 34 }

gs2310pplusSpanningTreePrivilegeLevel OBJECT-TYPE
   SYNTAX      Integer32 (1..15)
   MAX-ACCESS  read-write
   STATUS      current
   DESCRIPTION
       "Default:15, Range : 1-15. "
   ::= { gs2310pplusSystemAccountPrivilegeLevel 35 }

gs2310pplusSystemPrivilegeLevel OBJECT-TYPE
   SYNTAX      Integer32 (1..15)
   MAX-ACCESS  read-write
   STATUS      current
   DESCRIPTION
       "Default:15, Range : 1-15. "
   ::= { gs2310pplusSystemAccountPrivilegeLevel 36 }

gs2310pplusTrapEventPrivilegeLevel OBJECT-TYPE
   SYNTAX      Integer32 (1..15)
   MAX-ACCESS  read-write
   STATUS      current
   DESCRIPTION
       "Default:15, Range : 1-15. "
   ::= { gs2310pplusSystemAccountPrivilegeLevel 37 }

gs2310pplusUPnPPrivilegeLevel OBJECT-TYPE
   SYNTAX      Integer32 (1..15)
   MAX-ACCESS  read-write
   STATUS      current
   DESCRIPTION
       "Default:15, Range : 1-15. "
   ::= { gs2310pplusSystemAccountPrivilegeLevel 38 }

gs2310pplusVCLPrivilegeLevel OBJECT-TYPE
   SYNTAX      Integer32 (1..15)
   MAX-ACCESS  read-write
   STATUS      current
   DESCRIPTION
       "Default:15, Range : 1-15. "
   ::= { gs2310pplusSystemAccountPrivilegeLevel 39 }

gs2310pplusVLANsPrivilegeLevel OBJECT-TYPE
   SYNTAX      Integer32 (1..15)
   MAX-ACCESS  read-write
   STATUS      current
   DESCRIPTION
       "Default:15, Range : 1-15. "
   ::= { gs2310pplusSystemAccountPrivilegeLevel 41 }

gs2310pplusVoiceVLANPrivilegeLevel OBJECT-TYPE
   SYNTAX      Integer32 (1..15)
   MAX-ACCESS  read-write
   STATUS      current
   DESCRIPTION
       "Default:15, Range : 1-15. "
   ::= { gs2310pplusSystemAccountPrivilegeLevel 42 }
   
gs2310pplusPOEPrivilegeLevel OBJECT-TYPE
   SYNTAX      Integer32 (1..15)
   MAX-ACCESS  read-write
   STATUS      current
   DESCRIPTION
       "Default:15, Range : 1-15. "
   ::= { gs2310pplusSystemAccountPrivilegeLevel 43 }

gs2310pplusIP                                                    OBJECT IDENTIFIER ::= { gs2310pplusSystem 4 }

gs2310pplusIPv4                                                  OBJECT IDENTIFIER ::= { gs2310pplusIP 1 }

gs2310pplusIPv4Configured                                                  OBJECT IDENTIFIER ::= { gs2310pplusIPv4 1 }

gs2310pplusIpv4DHCPClient OBJECT-TYPE
   SYNTAX      INTEGER { disable(0), enable(1) }
   MAX-ACCESS  read-write
   STATUS      current
   DESCRIPTION
       "default:0
       0: disable
       1: enable"
   ::= { gs2310pplusIPv4Configured 1 }

gs2310pplusIPv4Address OBJECT-TYPE
   SYNTAX      IpAddress
   MAX-ACCESS  read-write
   STATUS      current
   DESCRIPTION
       ""
   ::= { gs2310pplusIPv4Configured 2 }

gs2310pplusIPv4Mask OBJECT-TYPE
   SYNTAX      IpAddress
   MAX-ACCESS  read-write
   STATUS      current
   DESCRIPTION
       ""
   ::= { gs2310pplusIPv4Configured 3 }

gs2310pplusIPv4Gateway OBJECT-TYPE
   SYNTAX      IpAddress
   MAX-ACCESS  read-write
   STATUS      current
   DESCRIPTION
       ""
   ::= { gs2310pplusIPv4Configured 4 }

gs2310pplusIPv4VLANId OBJECT-TYPE
   SYNTAX      Integer32(1..4094)
   MAX-ACCESS  read-write
   STATUS      current
   DESCRIPTION
       "default:1"
   ::= { gs2310pplusIPv4Configured 5 }

gs2310pplusIPv4DNSServer OBJECT-TYPE
   SYNTAX      IpAddress
   MAX-ACCESS  read-write
   STATUS      current
   DESCRIPTION
       ""
   ::= { gs2310pplusIPv4Configured 6 }

gs2310pplusIPv4DNSProxy OBJECT-TYPE
   SYNTAX      INTEGER { disable(0), enable(1) }
   MAX-ACCESS  read-write
   STATUS      current
   DESCRIPTION
       "0:disable, 1:enable "
   ::= { gs2310pplusIPv4Configured 7 }

gs2310pplusIPv4Current                                                  OBJECT IDENTIFIER ::= { gs2310pplusIPv4 2 }

gs2310pplusIpv4CurrentDHCPClient OBJECT-TYPE
   SYNTAX      INTEGER { none(0), renew(1) }
   MAX-ACCESS  read-write
   STATUS      current
   DESCRIPTION
       "default:0
       0: none (for read)
       1: renew"
   ::= { gs2310pplusIPv4Current 1 }

gs2310pplusIPv4CurrentAddress OBJECT-TYPE
   SYNTAX      IpAddress
   MAX-ACCESS  read-only
   STATUS      current
   DESCRIPTION
       ""
   ::= { gs2310pplusIPv4Current 2 }

gs2310pplusIPv4CurrentMask OBJECT-TYPE
   SYNTAX      IpAddress
   MAX-ACCESS  read-only
   STATUS      current
   DESCRIPTION
       ""
   ::= { gs2310pplusIPv4Current 3 }

gs2310pplusIPv4CurrentGateway OBJECT-TYPE
   SYNTAX      IpAddress
   MAX-ACCESS  read-only
   STATUS      current
   DESCRIPTION
       ""
   ::= { gs2310pplusIPv4Current 4 }

gs2310pplusIPv4CurrentVLANId OBJECT-TYPE
   SYNTAX      Integer32(1..4094)
   MAX-ACCESS  read-only
   STATUS      current
   DESCRIPTION
       "default:1"
   ::= { gs2310pplusIPv4Current 5 }

gs2310pplusIPv4CurrentDNSServer OBJECT-TYPE
   SYNTAX      IpAddress
   MAX-ACCESS  read-only
   STATUS      current
   DESCRIPTION
       ""
   ::= { gs2310pplusIPv4Current 6 }


gs2310pplusIPv6                                                  OBJECT IDENTIFIER ::= { gs2310pplusIP 2 }

gs2310pplusIPv6Configured                                                  OBJECT IDENTIFIER ::= { gs2310pplusIPv6 1 }

gs2310pplusIpv6AutoConfiguration OBJECT-TYPE
   SYNTAX      INTEGER { disable(0), enable(1) }
   MAX-ACCESS  read-write
   STATUS      current
   DESCRIPTION
       "default:0
       0: disable
       1: enable"
   ::= { gs2310pplusIPv6Configured 1 }

gs2310pplusIpv6Address OBJECT-TYPE
   SYNTAX      DisplayString (SIZE (0..30))
   MAX-ACCESS  read-write
   STATUS      current
   DESCRIPTION
       ""
   ::= { gs2310pplusIPv6Configured 2 }

gs2310pplusIpv6Prefix OBJECT-TYPE
   SYNTAX      Integer32 (1..128)
   MAX-ACCESS  read-write
   STATUS      current
   DESCRIPTION
       "default: 96"
   ::= { gs2310pplusIPv6Configured 3 }

gs2310pplusIpv6Gateway OBJECT-TYPE
   SYNTAX      DisplayString (SIZE (0..30))
   MAX-ACCESS  read-write
   STATUS      current
   DESCRIPTION
       " "
   ::= { gs2310pplusIPv6Configured 4 }

gs2310pplusIPv6Current                                                  OBJECT IDENTIFIER ::= { gs2310pplusIPv6 2 }

gs2310pplusIpv6CurrentAutoConfiguration OBJECT-TYPE
   SYNTAX      INTEGER { disable(0), enable(1) }
   MAX-ACCESS  read-only
   STATUS      current
   DESCRIPTION
       "default:0
       0: disable
       1: enable"
   ::= { gs2310pplusIPv6Current 1 }

gs2310pplusIpv6CurrentAddress OBJECT-TYPE
   SYNTAX      DisplayString (SIZE (0..30))
   MAX-ACCESS  read-only
   STATUS      current
   DESCRIPTION
       ""
   ::= { gs2310pplusIPv6Current 2 }


gs2310pplusIpv6CurrentLinkLocalAddress OBJECT-TYPE
   SYNTAX      DisplayString(SIZE (0..30))
   MAX-ACCESS  read-only
   STATUS      current
   DESCRIPTION
       ""
   ::= { gs2310pplusIPv6Current 3 }


gs2310pplusIpv6CurrentPrefix OBJECT-TYPE
   SYNTAX      DisplayString(SIZE (0..64))
   MAX-ACCESS  read-only
   STATUS      current
   DESCRIPTION
       ""
   ::= { gs2310pplusIPv6Current 4 }

gs2310pplusIpv6CurrentGateway OBJECT-TYPE
   SYNTAX      DisplayString (SIZE (0..30))
   MAX-ACCESS  read-only
   STATUS      current
   DESCRIPTION
       " "
   ::= { gs2310pplusIPv6Current 5 }

gs2310pplusSyslog                                                OBJECT IDENTIFIER ::= { gs2310pplusSystem 5 }

gs2310pplusSyslogConf                                            OBJECT IDENTIFIER ::= { gs2310pplusSyslog 1 }

gs2310pplusServerMode OBJECT-TYPE
   SYNTAX      INTEGER { disable(0), enable(1) }
   MAX-ACCESS  read-write
   STATUS      current
   DESCRIPTION
       "default: 0
       0: disable
       1: enable "
   ::= { gs2310pplusSyslogConf 1 }

gs2310pplusServerAddress1 OBJECT-TYPE
   SYNTAX      IpAddress
   MAX-ACCESS  read-write
   STATUS      current
   DESCRIPTION
       " "
   ::= { gs2310pplusSyslogConf 2 }

gs2310pplusServerAddress2 OBJECT-TYPE
   SYNTAX      IpAddress
   MAX-ACCESS  read-write
   STATUS      current
   DESCRIPTION
       " "
   ::= { gs2310pplusSyslogConf 3 }

gs2310pplusSyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2310pplusSyslogConf 4 }

gs2310pplusSyslogDetailedInfo                                    OBJECT IDENTIFIER ::= { gs2310pplusSyslog 2 }

gs2310pplusSyslogDetailedInfoClear OBJECT-TYPE
   SYNTAX      INTEGER { none(0), clear(1) }
   MAX-ACCESS  read-write
   STATUS      current
   DESCRIPTION
      "default: 0
       0 : None  (read only)
       1 : Clear Syslog"
   ::= { gs2310pplusSyslogDetailedInfo 1 }

gs2310pplusSyslogDetailedInfoTable OBJECT-TYPE
  SYNTAX      SEQUENCE OF GS2310PPLUSSyslogDetailedInfoEntry
  MAX-ACCESS  not-accessible
  STATUS      current
  DESCRIPTION
           " "
       ::= { gs2310pplusSyslogDetailedInfo 2 }

gs2310pplusSyslogDetailedInfoEntry OBJECT-TYPE
   SYNTAX      GS2310PPLUSSyslogDetailedInfoEntry
   MAX-ACCESS  not-accessible
   STATUS      current
   DESCRIPTION
           ""
   INDEX    { gs2310pplusSyslogDetailedInfoIndex  }
   ::= { gs2310pplusSyslogDetailedInfoTable 1 }

GS2310PPLUSSyslogDetailedInfoEntry ::= SEQUENCE {
   gs2310pplusSyslogDetailedInfoIndex       Integer32,
   gs2310pplusSyslogDetailedInfoLevel       DisplayString,
   gs2310pplusSyslogDetailedInfoTime        DisplayString,
   gs2310pplusSyslogDetailedInfoMessage     DisplayString
}

gs2310pplusSyslogDetailedInfoIndex OBJECT-TYPE
   SYNTAX      Integer32(1..1024)
   MAX-ACCESS  not-accessible
   STATUS      current
   DESCRIPTION
       " "
   ::= { gs2310pplusSyslogDetailedInfoEntry 1 }
   
gs2310pplusSyslogDetailedInfoLevel OBJECT-TYPE
   SYNTAX      DisplayString
   MAX-ACCESS  read-only
   STATUS      current
   DESCRIPTION
       " "
   ::= { gs2310pplusSyslogDetailedInfoEntry 2 }

gs2310pplusSyslogDetailedInfoTime OBJECT-TYPE
   SYNTAX      DisplayString(SIZE (0..20))
   MAX-ACCESS  read-only
   STATUS      current
   DESCRIPTION
       " "
   ::= { gs2310pplusSyslogDetailedInfoEntry 3 }

gs2310pplusSyslogDetailedInfoMessage OBJECT-TYPE
   SYNTAX      DisplayString
   MAX-ACCESS  read-only
   STATUS      current
   DESCRIPTION
       " "
   ::= { gs2310pplusSyslogDetailedInfoEntry 4 }


gs2310pplusSnmp                                                OBJECT IDENTIFIER ::= { gs2310pplusSystem 6 }

gs2310pplusSnmpConf                                            OBJECT IDENTIFIER ::= { gs2310pplusSnmp 1 }

gs2310pplusGetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2310pplusSnmpConf 1 }

gs2310pplusGetCommunity OBJECT-TYPE
   SYNTAX       DisplayString
   MAX-ACCESS   read-write
   STATUS       current
   DESCRIPTION
       "Get/Set the get-community of the SNMP."
   ::= { gs2310pplusSnmpConf 2 }

gs2310pplusSetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2310pplusSnmpConf 3 }

gs2310pplusSetCommunity OBJECT-TYPE
   SYNTAX       DisplayString
   MAX-ACCESS   read-write
   STATUS       current
   DESCRIPTION
       "Get/Set the set-community of the SNMP."
   ::= { gs2310pplusSnmpConf 4 }

gs2310pplusGetCommunityConfTable OBJECT-TYPE
   SYNTAX      SEQUENCE OF GS2310PPLUSGetCommunityConfEntry
   MAX-ACCESS  not-accessible
   STATUS      current
   DESCRIPTION
       " Show get-community of the SNMP. "
   ::= { gs2310pplusSnmpConf 5 }

gs2310pplusGetCommunityConfEntry OBJECT-TYPE
   SYNTAX      GS2310PPLUSGetCommunityConfEntry
   MAX-ACCESS  not-accessible
   STATUS      current
   DESCRIPTION
       ""
   INDEX    { gs2310pplusCommunityConfIndex  }
   ::= { gs2310pplusGetCommunityConfTable 1 }

GS2310PPLUSGetCommunityConfEntry ::= SEQUENCE {
   gs2310pplusCommunityConfIndex				Integer32,
   gs2310pplusCommunityConfGetCommunity			DisplayString
}

gs2310pplusCommunityConfIndex OBJECT-TYPE
   SYNTAX      Integer32(1..4095)
   MAX-ACCESS  not-accessible
   STATUS      current
   DESCRIPTION
       " index, range : 1 - 5. "
   ::= { gs2310pplusGetCommunityConfEntry 1 }
   
gs2310pplusCommunityConfGetCommunity OBJECT-TYPE
   SYNTAX      DisplayString
   MAX-ACCESS  read-write
   STATUS      current
   DESCRIPTION
       " Get/Set the get-community of the SNMP."
   ::= { gs2310pplusGetCommunityConfEntry 2 }

gs2310pplusTrapHostConfTable OBJECT-TYPE
   SYNTAX      SEQUENCE OF GS2310PPLUSTrapHostConfEntry
   MAX-ACCESS  not-accessible
   STATUS      current
   DESCRIPTION
       "A list of trap host entry. The numbers of entries are given by the value of gs2310pplusTrapHostConfNumber."
   ::= { gs2310pplusSnmpConf 6 }
   
gs2310pplusTrapHostConfEntry OBJECT-TYPE
   SYNTAX      GS2310PPLUSTrapHostConfEntry
   MAX-ACCESS  not-accessible
   STATUS      current
   DESCRIPTION
       "This is the entry information for trap host."
   INDEX    { gs2310pplusTrapHostConfIndex  }
   ::= { gs2310pplusTrapHostConfTable 1 }

GS2310PPLUSTrapHostConfEntry ::= SEQUENCE {
    gs2310pplusTrapHostConfIndex             Integer32,
    gs2310pplusTrapHostConfVersion           INTEGER,
    gs2310pplusTrapHostConfIPType            INTEGER,
    gs2310pplusTrapHostConfIP                DisplayString,
    gs2310pplusTrapHostConfPort              Integer32,
    gs2310pplusTrapHostConfCommunity         DisplayString,
    gs2310pplusTrapHostConfSeverityLevel     INTEGER,
    gs2310pplusTrapHostConfSecurityLevel     INTEGER,
    gs2310pplusTrapHostConfAuthPtc           INTEGER,
    gs2310pplusTrapHostConfAuthPassword      DisplayString,
    gs2310pplusTrapHostConfPrivPtc           INTEGER,
    gs2310pplusTrapHostConfPrivPassword      DisplayString,
    gs2310pplusTrapHostConfCurrentMode       INTEGER
}
   
gs2310pplusTrapHostConfIndex OBJECT-TYPE
   SYNTAX      Integer32(1..6)
   MAX-ACCESS  not-accessible
   STATUS      current
   DESCRIPTION
       " The index of the trap host entry. "
   ::= { gs2310pplusTrapHostConfEntry 1 }

gs2310pplusTrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2310pplusTrapHostConfEntry 2 }

gs2310pplusTrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2310pplusTrapHostConfEntry 3 }

gs2310pplusTrapHostConfIP OBJECT-TYPE
   SYNTAX       DisplayString
   MAX-ACCESS   read-write
   STATUS       current
   DESCRIPTION
       "This is the IP of the trap host."
   ::= { gs2310pplusTrapHostConfEntry 4 }

gs2310pplusTrapHostConfPort OBJECT-TYPE
   SYNTAX       Integer32(1..65535)
   MAX-ACCESS   read-write
   STATUS       current
   DESCRIPTION
       "This is the receiving-port number of the trap host.
        range : 1 - 65535."
   ::= { gs2310pplusTrapHostConfEntry 5 }

gs2310pplusTrapHostConfCommunity OBJECT-TYPE
   SYNTAX       DisplayString (SIZE (1..32))
   MAX-ACCESS   read-write
   STATUS       current
   DESCRIPTION
       "The community/security name for the trap PDU."
   ::= { gs2310pplusTrapHostConfEntry 6 }

gs2310pplusTrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2310pplusTrapHostConfEntry 7 }

gs2310pplusTrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2310pplusTrapHostConfEntry 8 }

gs2310pplusTrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2310pplusTrapHostConfEntry 9 }

gs2310pplusTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2310pplusTrapHostConfEntry 10 }

gs2310pplusTrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2310pplusTrapHostConfEntry 11 }

gs2310pplusTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2310pplusTrapHostConfEntry 12 }

gs2310pplusTrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2310pplusTrapHostConfEntry 13 }


gs2310pplusSnmpSystem                                          OBJECT IDENTIFIER ::= { gs2310pplusSnmp 2 }

gs2310pplusSnmpState OBJECT-TYPE
   SYNTAX       INTEGER { disable(0), enable(1) }
   MAX-ACCESS   read-write
   STATUS       current
   DESCRIPTION
       "Get/Set the state of the SNMP.
        default : 1, 0: disable, 1: enable. "
   ::= { gs2310pplusSnmpSystem 1 }

gs2310pplusSnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2310pplusSnmpSystem 2 }

gs2310pplusSnmpCommunities                                          OBJECT IDENTIFIER ::= { gs2310pplusSnmp 3 }

gs2310pplusSnmpCommunitiesCreate OBJECT-TYPE
   SYNTAX       INTEGER { none(0), create(1) }
   MAX-ACCESS   read-write
   STATUS       current
   DESCRIPTION
       "default: 0
        0 : None  (read only)
        1 : Create entry"
   ::= { gs2310pplusSnmpCommunities 1 }

gs2310pplusSnmpCommunitiesTable OBJECT-TYPE
   SYNTAX      SEQUENCE OF GS2310PPLUSSnmpCommunitiesEntry
   MAX-ACCESS  not-accessible
   STATUS      current
   DESCRIPTION
       " Create SNMPv1/v2 Communities entry."
   ::= { gs2310pplusSnmpCommunities 2 }

gs2310pplusSnmpCommunitiesEntry OBJECT-TYPE
   SYNTAX      GS2310PPLUSSnmpCommunitiesEntry
   MAX-ACCESS  not-accessible
   STATUS      current
   DESCRIPTION
       ""
   INDEX    { gs2310pplusSnmpCommunitiesIndex  }
   ::= { gs2310pplusSnmpCommunitiesTable 1 }

GS2310PPLUSSnmpCommunitiesEntry ::= SEQUENCE {
   gs2310pplusSnmpCommunitiesIndex          Integer32,
   gs2310pplusSnmpCommunitiesCommunity      DisplayString,
   gs2310pplusSnmpCommunitiesUserName       DisplayString,
   gs2310pplusSnmpCommunitiesSourceIP       IpAddress,
   gs2310pplusSnmpCommunitiesSourceMask     IpAddress,
   gs2310pplusSnmpCommunitiesRowStatus      INTEGER
}

gs2310pplusSnmpCommunitiesIndex OBJECT-TYPE
   SYNTAX      Integer32(1..4)
   MAX-ACCESS  not-accessible
   STATUS      current
   DESCRIPTION
       " "
   ::= { gs2310pplusSnmpCommunitiesEntry 1 }

gs2310pplusSnmpCommunitiesCommunity OBJECT-TYPE
   SYNTAX      DisplayString (SIZE (1..32))
   MAX-ACCESS  read-write
   STATUS      current
   DESCRIPTION
       "Up to 32 characters describing Community."
   ::= { gs2310pplusSnmpCommunitiesEntry 2 }

gs2310pplusSnmpCommunitiesUserName OBJECT-TYPE
   SYNTAX      DisplayString (SIZE (1..32))
   MAX-ACCESS  read-write
   STATUS      current
   DESCRIPTION
       " Up to 32 characters describing User Name. "
   ::= { gs2310pplusSnmpCommunitiesEntry 3 }

gs2310pplusSnmpCommunitiesSourceIP OBJECT-TYPE
   SYNTAX      IpAddress
   MAX-ACCESS  read-write
   STATUS      current
   DESCRIPTION
       " SNMP access source ip. "
   ::= { gs2310pplusSnmpCommunitiesEntry 4 }

gs2310pplusSnmpCommunitiesSourceMask OBJECT-TYPE
   SYNTAX      IpAddress
   MAX-ACCESS  read-write
   STATUS      current
   DESCRIPTION
       " SNMP access source address mask. "
   ::= { gs2310pplusSnmpCommunitiesEntry 5 }

gs2310pplusSnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pplusSnmpCommunitiesEntry 6 }


gs2310pplusSnmpUsers                                          OBJECT IDENTIFIER ::= { gs2310pplusSnmp 4 }

gs2310pplusSnmpUsersCreate OBJECT-TYPE
   SYNTAX       INTEGER { none(0), create(1) }
   MAX-ACCESS   read-write
   STATUS       current
   DESCRIPTION
       "default: 0
        0 : None  (read only)
        1 : Create entry"
   ::= { gs2310pplusSnmpUsers 1 }

gs2310pplusSnmpUsersTable OBJECT-TYPE
   SYNTAX      SEQUENCE OF GS2310PPLUSSnmpUsersEntry
   MAX-ACCESS  not-accessible
   STATUS      current
   DESCRIPTION
       " Create SNMPv3 users entry."
   ::= { gs2310pplusSnmpUsers 2 }

gs2310pplusSnmpUsersEntry OBJECT-TYPE
   SYNTAX      GS2310PPLUSSnmpUsersEntry
   MAX-ACCESS  not-accessible
   STATUS      current
   DESCRIPTION
       ""
   INDEX    { gs2310pplusSnmpUsersIndex  }
   ::= { gs2310pplusSnmpUsersTable 1 }

GS2310PPLUSSnmpUsersEntry ::= SEQUENCE {
   gs2310pplusSnmpUsersIndex                    Integer32,
   gs2310pplusSnmpUsersUserName                 DisplayString,
   gs2310pplusSnmpUsersSecurityLevel            INTEGER,
   gs2310pplusSnmpUsersAuthenticationProtocol   INTEGER,
   gs2310pplusSnmpUsersAuthenticationPassword   DisplayString,
   gs2310pplusSnmpUsersPrivacyProtocol          INTEGER,
   gs2310pplusSnmpUsersPrivacyPassword          DisplayString,
   gs2310pplusSnmpUsersRowStatus                INTEGER
}

gs2310pplusSnmpUsersIndex OBJECT-TYPE
   SYNTAX      Integer32(1..10)
   MAX-ACCESS  not-accessible
   STATUS      current
   DESCRIPTION
       " "
   ::= { gs2310pplusSnmpUsersEntry 1 }

gs2310pplusSnmpUsersUserName OBJECT-TYPE
   SYNTAX      DisplayString (SIZE (1..32))
   MAX-ACCESS  read-write
   STATUS      current
   DESCRIPTION
       "Up to 32 characters describing User Name."
   ::= { gs2310pplusSnmpUsersEntry 2 }

gs2310pplusSnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy. 
         3: Authentication and privacy. "
   ::= { gs2310pplusSnmpUsersEntry 3 }

gs2310pplusSnmpUsersAuthenticationProtocol OBJECT-TYPE
   SYNTAX      INTEGER { none(0), md5(1), sha(2) }
   MAX-ACCESS  read-write
   STATUS      current
   DESCRIPTION
       " 0: None.
         1: MD5.
         2: SHA "
   ::= { gs2310pplusSnmpUsersEntry 4 }

gs2310pplusSnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2310pplusSnmpUsersEntry 5 }
   
gs2310pplusSnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2310pplusSnmpUsersEntry 6 }

gs2310pplusSnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2310pplusSnmpUsersEntry 7 }
   
gs2310pplusSnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pplusSnmpUsersEntry 8 }


gs2310pplusSnmpGroups                                          OBJECT IDENTIFIER ::= { gs2310pplusSnmp 5 }

gs2310pplusSnmpGroupsCreate OBJECT-TYPE
   SYNTAX       INTEGER { none(0), create(1) }
   MAX-ACCESS   read-write
   STATUS       current
   DESCRIPTION
       "default: 0
        0 : None  (read only)
        1 : Create entry"
   ::= { gs2310pplusSnmpGroups 1 }

gs2310pplusSnmpGroupsTable OBJECT-TYPE
   SYNTAX      SEQUENCE OF GS2310PPLUSSnmpGroupsEntry
   MAX-ACCESS  not-accessible
   STATUS      current
   DESCRIPTION
       " Create SNMPv3 groups entry."
   ::= { gs2310pplusSnmpGroups 2 }

gs2310pplusSnmpGroupsEntry OBJECT-TYPE
   SYNTAX      GS2310PPLUSSnmpGroupsEntry
   MAX-ACCESS  not-accessible
   STATUS      current
   DESCRIPTION
       ""
   INDEX    { gs2310pplusSnmpGroupsIndex  }
   ::= { gs2310pplusSnmpGroupsTable 1 }

GS2310PPLUSSnmpGroupsEntry ::= SEQUENCE {
   gs2310pplusSnmpGroupsIndex           Integer32,
   gs2310pplusSnmpGroupsSecurityModel   INTEGER,
   gs2310pplusSnmpGroupsSecurityName    DisplayString,
   gs2310pplusSnmpGroupsGroupName       DisplayString,
   gs2310pplusSnmpGroupsRowStatus       INTEGER
}

gs2310pplusSnmpGroupsIndex OBJECT-TYPE
   SYNTAX      Integer32(1..14)
   MAX-ACCESS  not-accessible
   STATUS      current
   DESCRIPTION
       " "
   ::= { gs2310pplusSnmpGroupsEntry 1 }

gs2310pplusSnmpGroupsSecurityModel OBJECT-TYPE
   SYNTAX      INTEGER { v1(1), v2c(2), usm(3) }
   MAX-ACCESS  read-write
   STATUS      current
   DESCRIPTION
       " 1: v1.
         2: v2c. 
         3: usm."
   ::= { gs2310pplusSnmpGroupsEntry 2 }

gs2310pplusSnmpGroupsSecurityName OBJECT-TYPE
   SYNTAX      DisplayString (SIZE (1..32))
   MAX-ACCESS  read-write
   STATUS      current
   DESCRIPTION
       "Up to 32 characters describing User Name."
   ::= { gs2310pplusSnmpGroupsEntry 3 }

gs2310pplusSnmpGroupsGroupName OBJECT-TYPE
   SYNTAX      DisplayString (SIZE (1..32))
   MAX-ACCESS  read-write
   STATUS      current
   DESCRIPTION
       "Up to 32 characters describing Group Name."
   ::= { gs2310pplusSnmpGroupsEntry 4 }
   
gs2310pplusSnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pplusSnmpGroupsEntry 5 }

gs2310pplusSnmpViews                                              OBJECT IDENTIFIER ::= { gs2310pplusSnmp 6 }

gs2310pplusSnmpViewsCreate OBJECT-TYPE
   SYNTAX       INTEGER { none(0), create(1) }
   MAX-ACCESS   read-write
   STATUS       current
   DESCRIPTION
       "default: 0
        0 : None  (read only)
        1 : Create entry"
   ::= { gs2310pplusSnmpViews 1 }

gs2310pplusSnmpViewsTable OBJECT-TYPE
   SYNTAX      SEQUENCE OF GS2310PPLUSSnmpViewsEntry
   MAX-ACCESS  not-accessible
   STATUS      current
   DESCRIPTION
       " Create SNMPv1/v2 Views entry."
   ::= { gs2310pplusSnmpViews 2 }

gs2310pplusSnmpViewsEntry OBJECT-TYPE
   SYNTAX      GS2310PPLUSSnmpViewsEntry
   MAX-ACCESS  not-accessible
   STATUS      current
   DESCRIPTION
       ""
   INDEX    { gs2310pplusSnmpViewsIndex  }
   ::= { gs2310pplusSnmpViewsTable 1 }

GS2310PPLUSSnmpViewsEntry ::= SEQUENCE {
   gs2310pplusSnmpViewsIndex        Integer32,
   gs2310pplusSnmpViewsName         DisplayString,
   gs2310pplusSnmpViewsType         INTEGER,
   gs2310pplusSnmpViewsOIDSubtree   DisplayString,
   gs2310pplusSnmpViewsRowStatus    INTEGER
}
   
gs2310pplusSnmpViewsIndex OBJECT-TYPE
   SYNTAX      Integer32(1..4)
   MAX-ACCESS  not-accessible
   STATUS      current
   DESCRIPTION
       " "
   ::= { gs2310pplusSnmpViewsEntry 1 }

gs2310pplusSnmpViewsName OBJECT-TYPE
   SYNTAX      DisplayString (SIZE (1..32))
   MAX-ACCESS  read-write
   STATUS      current
   DESCRIPTION
       "Up to 32 characters describing view Name."
   ::= { gs2310pplusSnmpViewsEntry 2 }   

gs2310pplusSnmpViewsType OBJECT-TYPE
   SYNTAX      INTEGER { included(1), excluded(2) }
   MAX-ACCESS  read-write
   STATUS      current
   DESCRIPTION
       "1: included, An optional flag to indicate that this view subtree should be included. 
	   2: excluded, An optional flag to indicate that this view subtree should be excluded."
   ::= { gs2310pplusSnmpViewsEntry 3 } 
   
gs2310pplusSnmpViewsOIDSubtree OBJECT-TYPE
   SYNTAX      DisplayString (SIZE (1..128))
   MAX-ACCESS  read-write
   STATUS      current
   DESCRIPTION
       "The OID defining the root of the subtree to add to the named view."
   ::= { gs2310pplusSnmpViewsEntry 4 } 

gs2310pplusSnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pplusSnmpViewsEntry 5 }   


gs2310pplusSnmpAccess                                          OBJECT IDENTIFIER ::= { gs2310pplusSnmp 7 }

gs2310pplusSnmpAccessCreate OBJECT-TYPE
   SYNTAX       INTEGER { none(0), create(1) }
   MAX-ACCESS   read-write
   STATUS       current
   DESCRIPTION
       "default: 0
        0 : None  (read only)
        1 : Create entry"
   ::= { gs2310pplusSnmpAccess 1 }

gs2310pplusSnmpAccessTable OBJECT-TYPE
   SYNTAX      SEQUENCE OF GS2310PPLUSSnmpAccessEntry
   MAX-ACCESS  not-accessible
   STATUS      current
   DESCRIPTION
       " Create SNMPv3 Access entry."
   ::= { gs2310pplusSnmpAccess 2 }

gs2310pplusSnmpAccessEntry OBJECT-TYPE
   SYNTAX      GS2310PPLUSSnmpAccessEntry
   MAX-ACCESS  not-accessible
   STATUS      current
   DESCRIPTION
       ""
   INDEX    { gs2310pplusSnmpAccessIndex  }
   ::= { gs2310pplusSnmpAccessTable 1 }

GS2310PPLUSSnmpAccessEntry ::= SEQUENCE {
   gs2310pplusSnmpAccessIndex             Integer32,
   gs2310pplusSnmpAccessGroupName         DisplayString,
   gs2310pplusSnmpAccessSecurityModel     INTEGER,
   gs2310pplusSnmpAccessSecurityLevel     INTEGER,
   gs2310pplusSnmpAccessReadViewName      DisplayString,
   gs2310pplusSnmpAccessWriteViewName     DisplayString,  
   gs2310pplusSnmpAccessRowStatus         INTEGER
}

gs2310pplusSnmpAccessIndex OBJECT-TYPE
   SYNTAX      Integer32(1..14)
   MAX-ACCESS  not-accessible
   STATUS      current
   DESCRIPTION
       " "
   ::= { gs2310pplusSnmpAccessEntry 1 }

gs2310pplusSnmpAccessGroupName OBJECT-TYPE
   SYNTAX      DisplayString (SIZE (1..32))
   MAX-ACCESS  read-write
   STATUS      current
   DESCRIPTION
       "Up to 32 characters describing Group Name."
   ::= { gs2310pplusSnmpAccessEntry 2 }

gs2310pplusSnmpAccessSecurityModel OBJECT-TYPE
   SYNTAX      INTEGER { any(0), v1(1), v2c(2), usm(3) }
   MAX-ACCESS  read-write
   STATUS      current
   DESCRIPTION
       " 0: any.
         1: v1.
         2: v2c. 
         3: usm."
   ::= { gs2310pplusSnmpAccessEntry 3 }

gs2310pplusSnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy. 
         3: Authentication and privacy. "
   ::= { gs2310pplusSnmpAccessEntry 4 }

gs2310pplusSnmpAccessReadViewName OBJECT-TYPE
   SYNTAX      DisplayString (SIZE (1..32))
   MAX-ACCESS  read-write
   STATUS      current
   DESCRIPTION
       "Up to 32 characters describing Read View Name.
        None is reserved for Empty."
   ::= { gs2310pplusSnmpAccessEntry 5 }
   
gs2310pplusSnmpAccessWriteViewName OBJECT-TYPE
   SYNTAX      DisplayString (SIZE (1..32))
   MAX-ACCESS  read-write
   STATUS      current
   DESCRIPTION
       "Up to 32 characters describing Write View Name.
        None is reserved for Empty."
   ::= { gs2310pplusSnmpAccessEntry 6 }
   
gs2310pplusSnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pplusSnmpAccessEntry 7 }

----------------------------------------------------------------------------------------------------

gs2310pplusConfiguration                                         OBJECT IDENTIFIER ::= { lancomGS2310PPLUS 2 }

gs2310pplusPort                                                  OBJECT IDENTIFIER ::= { gs2310pplusConfiguration 1 }

gs2310pplusPortConfigurationTable OBJECT-TYPE
   SYNTAX      SEQUENCE OF GS2310PPLUSPortConfigurationEntry
   MAX-ACCESS  not-accessible
   STATUS      current
   DESCRIPTION
       " Show port configurations. "
   ::= { gs2310pplusPort 1 }

gs2310pplusPortConfigurationEntry OBJECT-TYPE
   SYNTAX      GS2310PPLUSPortConfigurationEntry
   MAX-ACCESS  not-accessible
   STATUS      current
   DESCRIPTION
       ""
   INDEX    { gs2310pplusPortConfPort  }
   ::= { gs2310pplusPortConfigurationTable 1 }

GS2310PPLUSPortConfigurationEntry ::= SEQUENCE {
   gs2310pplusPortConfPort                     Integer32,
   gs2310pplusPortConfPortMedia                DisplayString,
   gs2310pplusPortConfLink                     DisplayString,
   gs2310pplusPortConfCurrentSpeed             DisplayString,
   gs2310pplusPortConfSpeed                    INTEGER,
   gs2310pplusPortConfCurrentFlowControlRx     INTEGER,
   gs2310pplusPortConfCurrentFlowControlTx     INTEGER,
   gs2310pplusPortConfFlowControl              INTEGER,
   gs2310pplusPortConfMaxFrameSize             Integer32,
   gs2310pplusPortConfExcessiveCollisionMode   INTEGER,
   gs2310pplusPortConfPowerControl             INTEGER,
   gs2310pplusPortConfDescription              DisplayString
}

gs2310pplusPortConfPort OBJECT-TYPE
   SYNTAX      Integer32(1..4095)
   MAX-ACCESS  not-accessible
   STATUS      current
   DESCRIPTION
       " port, range : 1 - port number. "
   ::= { gs2310pplusPortConfigurationEntry 1 }

gs2310pplusPortConfPortMedia OBJECT-TYPE
   SYNTAX      DisplayString(SIZE (1..4))
   MAX-ACCESS  read-only
   STATUS      current
   DESCRIPTION
       " Show port media. "
   ::= { gs2310pplusPortConfigurationEntry 2 }

gs2310pplusPortConfLink OBJECT-TYPE
   SYNTAX      DisplayString(SIZE (2..4))
   MAX-ACCESS  read-only
   STATUS      current
   DESCRIPTION
       " The current link state. "
   ::= { gs2310pplusPortConfigurationEntry 3 }

gs2310pplusPortConfCurrentSpeed OBJECT-TYPE
   SYNTAX      DisplayString(SIZE (6..12))
   MAX-ACCESS  read-only
   STATUS      current
   DESCRIPTION
       " The current link speed of the port. "
   ::= { gs2310pplusPortConfigurationEntry 4 }

gs2310pplusPortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11)
                }
   MAX-ACCESS  read-write
   STATUS      current
   DESCRIPTION
       "default: 1,
        0: disable state, 
        1: auto, 
        2: 10 Half, 
        3: 10 Full, 
        4: 100 Half, 
        5: 100 Full, 
        6: 1G full, 
        only 'Dual Media' port have 7-11 option. 
        Dual Media port default: 7,  
        7: SFP_Auto_AMS, 
        8: 100FX_AMS, 
        9: 1000X_AMS, 
        10: 100FX, 
        11: 1000X "
   ::= { gs2310pplusPortConfigurationEntry 5 }

gs2310pplusPortConfCurrentFlowControlRx OBJECT-TYPE
   SYNTAX      INTEGER { disable(0), enable(1), noSupport(2) }
   MAX-ACCESS  read-only
   STATUS      current
   DESCRIPTION
       "0: disable
        1: enable
        2: no support.  "
   ::= { gs2310pplusPortConfigurationEntry 6 }

gs2310pplusPortConfCurrentFlowControlTx OBJECT-TYPE
   SYNTAX      INTEGER { disable(0), enable(1), noSupport(2) }
   MAX-ACCESS  read-only
   STATUS      current
   DESCRIPTION
       "0: disable
        1: enable
        2: no support.  "
   ::= { gs2310pplusPortConfigurationEntry 7 }

gs2310pplusPortConfFlowControl OBJECT-TYPE
   SYNTAX      INTEGER { disable(0), enable(1), noSupport(2) }
   MAX-ACCESS  read-write
   STATUS      current
   DESCRIPTION
       "default: 0,
        0: disable
        1: enable
        2: no support. "
   ::= { gs2310pplusPortConfigurationEntry 8 }

gs2310pplusPortConfMaxFrameSize OBJECT-TYPE
   SYNTAX      Integer32 (1518..9600)
   MAX-ACCESS  read-write
   STATUS      current
   DESCRIPTION
       "default: 9600 , range : 1518 - 9600 "
   ::= { gs2310pplusPortConfigurationEntry 9 }

gs2310pplusPortConfExcessiveCollisionMode OBJECT-TYPE
   SYNTAX      INTEGER { discard(0), restart(1), noSupport(2) }
   MAX-ACCESS  read-write
   STATUS      current
   DESCRIPTION
       "default: 0,
        Excessive Collision Mode : 
        0: Discard,
        1: Restart, 
        2: no support.
       "
   ::= { gs2310pplusPortConfigurationEntry 10 }

gs2310pplusPortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy, 
        2: Dynamic (perfectReach),
        3: Enable,
        4: no support.
       "
   ::= { gs2310pplusPortConfigurationEntry 11 }

gs2310pplusPortConfDescription OBJECT-TYPE
   SYNTAX      DisplayString
   MAX-ACCESS  read-write
   STATUS      current
   DESCRIPTION
       " Interface specific description.
         Up to 47 characters describing this interface. "
   ::= { gs2310pplusPortConfigurationEntry 12 }


gs2310pplusPortTrafficStatisticsTable OBJECT-TYPE
   SYNTAX      SEQUENCE OF GS2310PPLUSPortTrafficStatisticsEntry
   MAX-ACCESS  not-accessible
   STATUS      current
   DESCRIPTION
       " "
   ::= { gs2310pplusPort 2 }

gs2310pplusPortTrafficStatisticsEntry OBJECT-TYPE
   SYNTAX      GS2310PPLUSPortTrafficStatisticsEntry
   MAX-ACCESS  not-accessible
   STATUS      current
   DESCRIPTION
       ""
   INDEX    { gs2310pplusPortTrafficStatisticsPort  }
   ::= { gs2310pplusPortTrafficStatisticsTable 1 }

GS2310PPLUSPortTrafficStatisticsEntry ::= SEQUENCE {
   gs2310pplusPortTrafficStatisticsPort          Integer32,
   gs2310pplusPortTrafficStatisticsClear         INTEGER,
   gs2310pplusPortTrafficRxPackets               Counter64,
   gs2310pplusPortTrafficRxOctets                Counter64,
   gs2310pplusPortTrafficRxUnicast               Counter64,
   gs2310pplusPortTrafficRxMulticast             Counter64,
   gs2310pplusPortTrafficRxBroadcast             Counter64,
   gs2310pplusPortTrafficRxPause                 Counter64,
   gs2310pplusPortTrafficRx64Bytes               Counter64,
   gs2310pplusPortTrafficRx65to127Bytes          Counter64,
   gs2310pplusPortTrafficRx128to255Bytes         Counter64,
   gs2310pplusPortTrafficRx256to511Bytes         Counter64,
   gs2310pplusPortTrafficRx512to1023Bytes        Counter64,
   gs2310pplusPortTrafficRx1024to1526Bytes       Counter64,
   gs2310pplusPortTrafficRxExceecd1527Bytes      Counter64,
   gs2310pplusPortTrafficRxQ0                    Counter64,
   gs2310pplusPortTrafficRxQ1                    Counter64,
   gs2310pplusPortTrafficRxQ2                    Counter64,
   gs2310pplusPortTrafficRxQ3                    Counter64,
   gs2310pplusPortTrafficRxQ4                    Counter64,
   gs2310pplusPortTrafficRxQ5                    Counter64,
   gs2310pplusPortTrafficRxQ6                    Counter64,
   gs2310pplusPortTrafficRxQ7                    Counter64,
   gs2310pplusPortTrafficRxDrops                 Counter64,
   gs2310pplusPortTrafficRxCRCorAlignment        Counter64,
   gs2310pplusPortTrafficRxUndersize             Counter64,
   gs2310pplusPortTrafficRxOversize              Counter64,
   gs2310pplusPortTrafficRxFragments             Counter64,
   gs2310pplusPortTrafficRxJabber                Counter64,
   gs2310pplusPortTrafficRxFiltered              Counter64,
   gs2310pplusPortTrafficTxPackets               Counter64,
   gs2310pplusPortTrafficTxOctets                Counter64,
   gs2310pplusPortTrafficTxUnicast               Counter64,
   gs2310pplusPortTrafficTxMulticast             Counter64,
   gs2310pplusPortTrafficTxBroadcast             Counter64,
   gs2310pplusPortTrafficTxPause                 Counter64,
   gs2310pplusPortTrafficTx64Bytes               Counter64,
   gs2310pplusPortTrafficTx65to127Bytes          Counter64,
   gs2310pplusPortTrafficTx128to255Bytes         Counter64,
   gs2310pplusPortTrafficTx256to511Bytes         Counter64,
   gs2310pplusPortTrafficTx512to1023Bytes        Counter64,
   gs2310pplusPortTrafficTx1024to1526Bytes       Counter64,
   gs2310pplusPortTrafficTxExceecd1527Bytes      Counter64,
   gs2310pplusPortTrafficTxQ0                    Counter64,
   gs2310pplusPortTrafficTxQ1                    Counter64,
   gs2310pplusPortTrafficTxQ2                    Counter64,
   gs2310pplusPortTrafficTxQ3                    Counter64,
   gs2310pplusPortTrafficTxQ4                    Counter64,
   gs2310pplusPortTrafficTxQ5                    Counter64,
   gs2310pplusPortTrafficTxQ6                    Counter64,
   gs2310pplusPortTrafficTxQ7                    Counter64,
   gs2310pplusPortTrafficTxDrops                 Counter64,
   gs2310pplusPortTrafficTxLateOrExcColl         Counter64
}

gs2310pplusPortTrafficStatisticsPort OBJECT-TYPE
   SYNTAX      Integer32 (1..4095)
   MAX-ACCESS  not-accessible
   STATUS      current
   DESCRIPTION
       " "
   ::= { gs2310pplusPortTrafficStatisticsEntry 1 }

gs2310pplusPortTrafficStatisticsClear OBJECT-TYPE
   SYNTAX      INTEGER { disable(0), enable(1) }
   MAX-ACCESS  read-write
   STATUS      current
   DESCRIPTION
       " "
   ::= { gs2310pplusPortTrafficStatisticsEntry 2 }

gs2310pplusPortTrafficRxPackets OBJECT-TYPE
   SYNTAX      Counter64
   MAX-ACCESS  read-only
   STATUS      current
   DESCRIPTION
       " "
   ::= { gs2310pplusPortTrafficStatisticsEntry 3 }

gs2310pplusPortTrafficRxOctets OBJECT-TYPE
   SYNTAX      Counter64
   MAX-ACCESS  read-only
   STATUS      current
   DESCRIPTION
       " "
   ::= { gs2310pplusPortTrafficStatisticsEntry 4 }

gs2310pplusPortTrafficRxUnicast OBJECT-TYPE
   SYNTAX      Counter64
   MAX-ACCESS  read-only
   STATUS      current
   DESCRIPTION
       " "
   ::= { gs2310pplusPortTrafficStatisticsEntry 5 }

gs2310pplusPortTrafficRxMulticast OBJECT-TYPE
   SYNTAX      Counter64
   MAX-ACCESS  read-only
   STATUS      current
   DESCRIPTION
       " "
   ::= { gs2310pplusPortTrafficStatisticsEntry 6 }

gs2310pplusPortTrafficRxBroadcast OBJECT-TYPE
   SYNTAX      Counter64
   MAX-ACCESS  read-only
   STATUS      current
   DESCRIPTION
       " "
   ::= { gs2310pplusPortTrafficStatisticsEntry 7 }

gs2310pplusPortTrafficRxPause OBJECT-TYPE
   SYNTAX      Counter64
   MAX-ACCESS  read-only
   STATUS      current
   DESCRIPTION
       " "
   ::= { gs2310pplusPortTrafficStatisticsEntry 8 }

gs2310pplusPortTrafficRx64Bytes OBJECT-TYPE
   SYNTAX      Counter64
   MAX-ACCESS  read-only
   STATUS      current
   DESCRIPTION
       " "
   ::= { gs2310pplusPortTrafficStatisticsEntry 9 }

gs2310pplusPortTrafficRx65to127Bytes OBJECT-TYPE
   SYNTAX      Counter64
   MAX-ACCESS  read-only
   STATUS      current
   DESCRIPTION
       " "
   ::= { gs2310pplusPortTrafficStatisticsEntry 10 }

gs2310pplusPortTrafficRx128to255Bytes OBJECT-TYPE
   SYNTAX      Counter64
   MAX-ACCESS  read-only
   STATUS      current
   DESCRIPTION
       " "
   ::= { gs2310pplusPortTrafficStatisticsEntry 11 }

gs2310pplusPortTrafficRx256to511Bytes OBJECT-TYPE
   SYNTAX      Counter64
   MAX-ACCESS  read-only
   STATUS      current
   DESCRIPTION
       " "
   ::= { gs2310pplusPortTrafficStatisticsEntry 12 }

gs2310pplusPortTrafficRx512to1023Bytes OBJECT-TYPE
   SYNTAX      Counter64
   MAX-ACCESS  read-only
   STATUS      current
   DESCRIPTION
       " "
   ::= { gs2310pplusPortTrafficStatisticsEntry 13 }

gs2310pplusPortTrafficRx1024to1526Bytes OBJECT-TYPE
   SYNTAX      Counter64
   MAX-ACCESS  read-only
   STATUS      current
   DESCRIPTION
       " "
   ::= { gs2310pplusPortTrafficStatisticsEntry 14 }

gs2310pplusPortTrafficRxExceecd1527Bytes OBJECT-TYPE
   SYNTAX      Counter64
   MAX-ACCESS  read-only
   STATUS      current
   DESCRIPTION
       " "
   ::= { gs2310pplusPortTrafficStatisticsEntry 15 }

gs2310pplusPortTrafficRxQ0 OBJECT-TYPE
   SYNTAX      Counter64
   MAX-ACCESS  read-only
   STATUS      current
   DESCRIPTION
       " "
   ::= { gs2310pplusPortTrafficStatisticsEntry 16 }

gs2310pplusPortTrafficRxQ1 OBJECT-TYPE
   SYNTAX      Counter64
   MAX-ACCESS  read-only
   STATUS      current
   DESCRIPTION
       " "
   ::= { gs2310pplusPortTrafficStatisticsEntry 17 }

gs2310pplusPortTrafficRxQ2 OBJECT-TYPE
   SYNTAX      Counter64
   MAX-ACCESS  read-only
   STATUS      current
   DESCRIPTION
       " "
   ::= { gs2310pplusPortTrafficStatisticsEntry 18 }

gs2310pplusPortTrafficRxQ3 OBJECT-TYPE
   SYNTAX      Counter64
   MAX-ACCESS  read-only
   STATUS      current
   DESCRIPTION
       " "
   ::= { gs2310pplusPortTrafficStatisticsEntry 19 }

gs2310pplusPortTrafficRxQ4 OBJECT-TYPE
   SYNTAX      Counter64
   MAX-ACCESS  read-only
   STATUS      current
   DESCRIPTION
       " "
   ::= { gs2310pplusPortTrafficStatisticsEntry 20 }

gs2310pplusPortTrafficRxQ5 OBJECT-TYPE
   SYNTAX      Counter64
   MAX-ACCESS  read-only
   STATUS      current
   DESCRIPTION
       " "
   ::= { gs2310pplusPortTrafficStatisticsEntry 21 }

gs2310pplusPortTrafficRxQ6 OBJECT-TYPE
   SYNTAX      Counter64
   MAX-ACCESS  read-only
   STATUS      current
   DESCRIPTION
       " "
   ::= { gs2310pplusPortTrafficStatisticsEntry 22 }

gs2310pplusPortTrafficRxQ7 OBJECT-TYPE
   SYNTAX      Counter64
   MAX-ACCESS  read-only
   STATUS      current
   DESCRIPTION
       " "
   ::= { gs2310pplusPortTrafficStatisticsEntry 23 }

gs2310pplusPortTrafficRxDrops OBJECT-TYPE
   SYNTAX      Counter64
   MAX-ACCESS  read-only
   STATUS      current
   DESCRIPTION
       " "
   ::= { gs2310pplusPortTrafficStatisticsEntry 24 }

gs2310pplusPortTrafficRxCRCorAlignment OBJECT-TYPE
   SYNTAX      Counter64
   MAX-ACCESS  read-only
   STATUS      current
   DESCRIPTION
       " "
   ::= { gs2310pplusPortTrafficStatisticsEntry 25 }

gs2310pplusPortTrafficRxUndersize OBJECT-TYPE
   SYNTAX      Counter64
   MAX-ACCESS  read-only
   STATUS      current
   DESCRIPTION
       " "
   ::= { gs2310pplusPortTrafficStatisticsEntry 26 }

gs2310pplusPortTrafficRxOversize OBJECT-TYPE
   SYNTAX      Counter64
   MAX-ACCESS  read-only
   STATUS      current
   DESCRIPTION
       " "
   ::= { gs2310pplusPortTrafficStatisticsEntry 27 }

gs2310pplusPortTrafficRxFragments OBJECT-TYPE
   SYNTAX      Counter64
   MAX-ACCESS  read-only
   STATUS      current
   DESCRIPTION
       " "
   ::= { gs2310pplusPortTrafficStatisticsEntry 28 }

gs2310pplusPortTrafficRxJabber OBJECT-TYPE
   SYNTAX      Counter64
   MAX-ACCESS  read-only
   STATUS      current
   DESCRIPTION
       " "
   ::= { gs2310pplusPortTrafficStatisticsEntry 29 }

gs2310pplusPortTrafficRxFiltered OBJECT-TYPE
   SYNTAX      Counter64
   MAX-ACCESS  read-only
   STATUS      current
   DESCRIPTION
       " "
   ::= { gs2310pplusPortTrafficStatisticsEntry 30 }

gs2310pplusPortTrafficTxPackets OBJECT-TYPE
   SYNTAX      Counter64
   MAX-ACCESS  read-only
   STATUS      current
   DESCRIPTION
       " "
   ::= { gs2310pplusPortTrafficStatisticsEntry 31 }

gs2310pplusPortTrafficTxOctets OBJECT-TYPE
   SYNTAX      Counter64
   MAX-ACCESS  read-only
   STATUS      current
   DESCRIPTION
       " "
   ::= { gs2310pplusPortTrafficStatisticsEntry 32 }

gs2310pplusPortTrafficTxUnicast OBJECT-TYPE
   SYNTAX      Counter64
   MAX-ACCESS  read-only
   STATUS      current
   DESCRIPTION
       " "
   ::= { gs2310pplusPortTrafficStatisticsEntry 33 }

gs2310pplusPortTrafficTxMulticast OBJECT-TYPE
   SYNTAX      Counter64
   MAX-ACCESS  read-only
   STATUS      current
   DESCRIPTION
       " "
   ::= { gs2310pplusPortTrafficStatisticsEntry 34 }

gs2310pplusPortTrafficTxBroadcast OBJECT-TYPE
   SYNTAX      Counter64
   MAX-ACCESS  read-only
   STATUS      current
   DESCRIPTION
       " "
   ::= { gs2310pplusPortTrafficStatisticsEntry 35 }

gs2310pplusPortTrafficTxPause OBJECT-TYPE
   SYNTAX      Counter64
   MAX-ACCESS  read-only
   STATUS      current
   DESCRIPTION
       " "
   ::= { gs2310pplusPortTrafficStatisticsEntry 36 }

gs2310pplusPortTrafficTx64Bytes OBJECT-TYPE
   SYNTAX      Counter64
   MAX-ACCESS  read-only
   STATUS      current
   DESCRIPTION
       " "
   ::= { gs2310pplusPortTrafficStatisticsEntry 37 }

gs2310pplusPortTrafficTx65to127Bytes OBJECT-TYPE
   SYNTAX      Counter64
   MAX-ACCESS  read-only
   STATUS      current
   DESCRIPTION
       " "
   ::= { gs2310pplusPortTrafficStatisticsEntry 38 }

gs2310pplusPortTrafficTx128to255Bytes OBJECT-TYPE
   SYNTAX      Counter64
   MAX-ACCESS  read-only
   STATUS      current
   DESCRIPTION
       " "
   ::= { gs2310pplusPortTrafficStatisticsEntry 39 }

gs2310pplusPortTrafficTx256to511Bytes OBJECT-TYPE
   SYNTAX      Counter64
   MAX-ACCESS  read-only
   STATUS      current
   DESCRIPTION
       " "
   ::= { gs2310pplusPortTrafficStatisticsEntry 40 }

gs2310pplusPortTrafficTx512to1023Bytes OBJECT-TYPE
   SYNTAX      Counter64
   MAX-ACCESS  read-only
   STATUS      current
   DESCRIPTION
       " "
   ::= { gs2310pplusPortTrafficStatisticsEntry 41 }

gs2310pplusPortTrafficTx1024to1526Bytes OBJECT-TYPE
   SYNTAX      Counter64
   MAX-ACCESS  read-only
   STATUS      current
   DESCRIPTION
       " "
   ::= { gs2310pplusPortTrafficStatisticsEntry 42 }

gs2310pplusPortTrafficTxExceecd1527Bytes OBJECT-TYPE
   SYNTAX      Counter64
   MAX-ACCESS  read-only
   STATUS      current
   DESCRIPTION
       " "
   ::= { gs2310pplusPortTrafficStatisticsEntry 43 }

gs2310pplusPortTrafficTxQ0 OBJECT-TYPE
   SYNTAX      Counter64
   MAX-ACCESS  read-only
   STATUS      current
   DESCRIPTION
       " "
   ::= { gs2310pplusPortTrafficStatisticsEntry 44 }

gs2310pplusPortTrafficTxQ1 OBJECT-TYPE
   SYNTAX      Counter64
   MAX-ACCESS  read-only
   STATUS      current
   DESCRIPTION
       " "
   ::= { gs2310pplusPortTrafficStatisticsEntry 45 }

gs2310pplusPortTrafficTxQ2 OBJECT-TYPE
   SYNTAX      Counter64
   MAX-ACCESS  read-only
   STATUS      current
   DESCRIPTION
       " "
   ::= { gs2310pplusPortTrafficStatisticsEntry 46 }

gs2310pplusPortTrafficTxQ3 OBJECT-TYPE
   SYNTAX      Counter64
   MAX-ACCESS  read-only
   STATUS      current
   DESCRIPTION
       " "
   ::= { gs2310pplusPortTrafficStatisticsEntry 47 }

gs2310pplusPortTrafficTxQ4 OBJECT-TYPE
   SYNTAX      Counter64
   MAX-ACCESS  read-only
   STATUS      current
   DESCRIPTION
       " "
   ::= { gs2310pplusPortTrafficStatisticsEntry 48 }

gs2310pplusPortTrafficTxQ5 OBJECT-TYPE
   SYNTAX      Counter64
   MAX-ACCESS  read-only
   STATUS      current
   DESCRIPTION
       " "
   ::= { gs2310pplusPortTrafficStatisticsEntry 49 }

gs2310pplusPortTrafficTxQ6 OBJECT-TYPE
   SYNTAX      Counter64
   MAX-ACCESS  read-only
   STATUS      current
   DESCRIPTION
       " "
   ::= { gs2310pplusPortTrafficStatisticsEntry 50 }


gs2310pplusPortTrafficTxQ7 OBJECT-TYPE
   SYNTAX      Counter64
   MAX-ACCESS  read-only
   STATUS      current
   DESCRIPTION
       " "
   ::= { gs2310pplusPortTrafficStatisticsEntry 51 }

gs2310pplusPortTrafficTxDrops OBJECT-TYPE
   SYNTAX      Counter64
   MAX-ACCESS  read-only
   STATUS      current
   DESCRIPTION
       " "
   ::= { gs2310pplusPortTrafficStatisticsEntry 52 }

gs2310pplusPortTrafficTxLateOrExcColl OBJECT-TYPE
   SYNTAX      Counter64
   MAX-ACCESS  read-only
   STATUS      current
   DESCRIPTION
       " "
   ::= { gs2310pplusPortTrafficStatisticsEntry 53 }


gs2310pplusPortQoSStatistics                                     OBJECT IDENTIFIER ::= { gs2310pplusPort 3 }

gs2310pplusPortQoSStatisticsClear OBJECT-TYPE
   SYNTAX      INTEGER { none(0), clear(1) }
   MAX-ACCESS  read-only
   STATUS      current
   DESCRIPTION
       "default: 0
       0: none
       1: clear "
   ::= { gs2310pplusPortQoSStatistics 1 }

gs2310pplusPortQoSStatisticsTable OBJECT-TYPE
   SYNTAX      SEQUENCE OF GS2310PPLUSPortQoSStatisticsEntry
   MAX-ACCESS  not-accessible
   STATUS      current
   DESCRIPTION
       " "
   ::= { gs2310pplusPortQoSStatistics 2 }

gs2310pplusPortQoSStatisticsEntry OBJECT-TYPE
   SYNTAX      GS2310PPLUSPortQoSStatisticsEntry
   MAX-ACCESS  not-accessible
   STATUS      current
   DESCRIPTION
       ""
   INDEX    { gs2310pplusPortQoSStatisticsPort  }
   ::= { gs2310pplusPortQoSStatisticsTable 1 }

GS2310PPLUSPortQoSStatisticsEntry ::= SEQUENCE {
   gs2310pplusPortQoSStatisticsPort      Integer32,
   gs2310pplusPortQoSQ0Rx                Counter64,
   gs2310pplusPortQoSQ0Tx                Counter64,
   gs2310pplusPortQoSQ1Rx                Counter64,
   gs2310pplusPortQoSQ1Tx                Counter64,
   gs2310pplusPortQoSQ2Rx                Counter64,
   gs2310pplusPortQoSQ2Tx                Counter64,
   gs2310pplusPortQoSQ3Rx                Counter64,
   gs2310pplusPortQoSQ3Tx                Counter64,
   gs2310pplusPortQoSQ4Rx                Counter64,
   gs2310pplusPortQoSQ4Tx                Counter64,
   gs2310pplusPortQoSQ5Rx                Counter64,
   gs2310pplusPortQoSQ5Tx                Counter64,
   gs2310pplusPortQoSQ6Rx                Counter64,
   gs2310pplusPortQoSQ6Tx                Counter64,
   gs2310pplusPortQoSQ7Rx                Counter64,
   gs2310pplusPortQoSQ7Tx                Counter64
}

gs2310pplusPortQoSStatisticsPort OBJECT-TYPE
   SYNTAX      Integer32(1..4095)
   MAX-ACCESS  not-accessible
   STATUS      current
   DESCRIPTION
       " "
   ::= { gs2310pplusPortQoSStatisticsEntry 1 }

gs2310pplusPortQoSQ0Rx OBJECT-TYPE
   SYNTAX      Counter64
   MAX-ACCESS  read-only
   STATUS      current
   DESCRIPTION
       " "
   ::= { gs2310pplusPortQoSStatisticsEntry 2 }

gs2310pplusPortQoSQ0Tx OBJECT-TYPE
   SYNTAX      Counter64
   MAX-ACCESS  read-only
   STATUS      current
   DESCRIPTION
       " "
   ::= { gs2310pplusPortQoSStatisticsEntry 3 }

gs2310pplusPortQoSQ1Rx OBJECT-TYPE
   SYNTAX      Counter64
   MAX-ACCESS  read-only
   STATUS      current
   DESCRIPTION
       " "
   ::= { gs2310pplusPortQoSStatisticsEntry 4 }

gs2310pplusPortQoSQ1Tx OBJECT-TYPE
   SYNTAX      Counter64
   MAX-ACCESS  read-only
   STATUS      current
   DESCRIPTION
       " "
   ::= { gs2310pplusPortQoSStatisticsEntry 5 }

gs2310pplusPortQoSQ2Rx OBJECT-TYPE
   SYNTAX      Counter64
   MAX-ACCESS  read-only
   STATUS      current
   DESCRIPTION
       " "
   ::= { gs2310pplusPortQoSStatisticsEntry 6 }

gs2310pplusPortQoSQ2Tx OBJECT-TYPE
   SYNTAX      Counter64
   MAX-ACCESS  read-only
   STATUS      current
   DESCRIPTION
       " "
   ::= { gs2310pplusPortQoSStatisticsEntry 7 }

gs2310pplusPortQoSQ3Rx OBJECT-TYPE
   SYNTAX      Counter64
   MAX-ACCESS  read-only
   STATUS      current
   DESCRIPTION
       " "
   ::= { gs2310pplusPortQoSStatisticsEntry 8 }

gs2310pplusPortQoSQ3Tx OBJECT-TYPE
   SYNTAX      Counter64
   MAX-ACCESS  read-only
   STATUS      current
   DESCRIPTION
       " "
   ::= { gs2310pplusPortQoSStatisticsEntry 9 }

gs2310pplusPortQoSQ4Rx OBJECT-TYPE
   SYNTAX      Counter64
   MAX-ACCESS  read-only
   STATUS      current
   DESCRIPTION
       " "
   ::= { gs2310pplusPortQoSStatisticsEntry 10 }

gs2310pplusPortQoSQ4Tx OBJECT-TYPE
   SYNTAX      Counter64
   MAX-ACCESS  read-only
   STATUS      current
   DESCRIPTION
       " "
   ::= { gs2310pplusPortQoSStatisticsEntry 11 }

gs2310pplusPortQoSQ5Rx OBJECT-TYPE
   SYNTAX      Counter64
   MAX-ACCESS  read-only
   STATUS      current
   DESCRIPTION
       " "
   ::= { gs2310pplusPortQoSStatisticsEntry 12 }

gs2310pplusPortQoSQ5Tx OBJECT-TYPE
   SYNTAX      Counter64
   MAX-ACCESS  read-only
   STATUS      current
   DESCRIPTION
       " "
   ::= { gs2310pplusPortQoSStatisticsEntry 13 }

gs2310pplusPortQoSQ6Rx OBJECT-TYPE
   SYNTAX      Counter64
   MAX-ACCESS  read-only
   STATUS      current
   DESCRIPTION
       " "
   ::= { gs2310pplusPortQoSStatisticsEntry 14 }

gs2310pplusPortQoSQ6Tx OBJECT-TYPE
   SYNTAX      Counter64
   MAX-ACCESS  read-only
   STATUS      current
   DESCRIPTION
       " "
   ::= { gs2310pplusPortQoSStatisticsEntry 15 }

gs2310pplusPortQoSQ7Rx OBJECT-TYPE
   SYNTAX      Counter64
   MAX-ACCESS  read-only
   STATUS      current
   DESCRIPTION
       " "
   ::= { gs2310pplusPortQoSStatisticsEntry 16 }

gs2310pplusPortQoSQ7Tx OBJECT-TYPE
   SYNTAX      Counter64
   MAX-ACCESS  read-only
   STATUS      current
   DESCRIPTION
       " "
   ::= { gs2310pplusPortQoSStatisticsEntry 17 }

gs2310pplusSFPInfoTable OBJECT-TYPE
   SYNTAX      SEQUENCE OF GS2310PPLUSSFPInfoEntry
   MAX-ACCESS  not-accessible
   STATUS      current
   DESCRIPTION
       " "
   ::= { gs2310pplusPort 4 }

gs2310pplusSFPInfoEntry OBJECT-TYPE
   SYNTAX      GS2310PPLUSSFPInfoEntry
   MAX-ACCESS  not-accessible
   STATUS      current
   DESCRIPTION
       ""
   INDEX    { gs2310pplusSFPInfoIndex }
   ::= { gs2310pplusSFPInfoTable 1 }

GS2310PPLUSSFPInfoEntry ::= SEQUENCE {
   gs2310pplusSFPInfoIndex               Integer32,
   gs2310pplusSFPInfoPort                DisplayString,
   gs2310pplusSFPConnectorType           DisplayString,
   gs2310pplusSFPFiberType               DisplayString,
   gs2310pplusSFPTxCentralWavelength     DisplayString,
   gs2310pplusSFPBaudRate                DisplayString,
   gs2310pplusSFPVendorOUI               DisplayString,
   gs2310pplusSFPVendorName              DisplayString,
   gs2310pplusSFPVendorPN                DisplayString,
   gs2310pplusSFPVendorRev               DisplayString,
   gs2310pplusSFPVendorSN                DisplayString,
   gs2310pplusSFPDateCode                DisplayString,
   gs2310pplusSFPTemperature             DisplayString,
   gs2310pplusSFPVcc                     DisplayString,
   gs2310pplusSFPMon1Bias                DisplayString,
   gs2310pplusSFPMon2TxPWR               DisplayString,
   gs2310pplusSFPMon3RxPWR               DisplayString
}

gs2310pplusSFPInfoIndex OBJECT-TYPE
   SYNTAX      Integer32(1..4095)
   MAX-ACCESS  not-accessible
   STATUS      current
   DESCRIPTION
       " "
   ::= { gs2310pplusSFPInfoEntry 1 }

gs2310pplusSFPInfoPort OBJECT-TYPE
   SYNTAX      DisplayString
   MAX-ACCESS  read-only
   STATUS      current
   DESCRIPTION
       " "
   ::= { gs2310pplusSFPInfoEntry 2 }

gs2310pplusSFPConnectorType OBJECT-TYPE
   SYNTAX      DisplayString
   MAX-ACCESS  read-only
   STATUS      current
   DESCRIPTION
       " "
   ::= { gs2310pplusSFPInfoEntry 3 }

gs2310pplusSFPFiberType OBJECT-TYPE
   SYNTAX      DisplayString
   MAX-ACCESS  read-only
   STATUS      current
   DESCRIPTION
       " "
   ::= { gs2310pplusSFPInfoEntry 4 }

gs2310pplusSFPTxCentralWavelength OBJECT-TYPE
   SYNTAX      DisplayString
   MAX-ACCESS  read-only
   STATUS      current
   DESCRIPTION
       " "
   ::= { gs2310pplusSFPInfoEntry 5 }

gs2310pplusSFPBaudRate OBJECT-TYPE
   SYNTAX      DisplayString
   MAX-ACCESS  read-only
   STATUS      current
   DESCRIPTION
       " "
   ::= { gs2310pplusSFPInfoEntry 6 }

gs2310pplusSFPVendorOUI OBJECT-TYPE
   SYNTAX      DisplayString
   MAX-ACCESS  read-only
   STATUS      current
   DESCRIPTION
       " "
   ::= { gs2310pplusSFPInfoEntry 7 }

gs2310pplusSFPVendorName OBJECT-TYPE
   SYNTAX      DisplayString
   MAX-ACCESS  read-only
   STATUS      current
   DESCRIPTION
       " "
   ::= { gs2310pplusSFPInfoEntry 8 }

gs2310pplusSFPVendorPN OBJECT-TYPE
   SYNTAX      DisplayString
   MAX-ACCESS  read-only
   STATUS      current
   DESCRIPTION
       " "
   ::= { gs2310pplusSFPInfoEntry 9 }

gs2310pplusSFPVendorRev OBJECT-TYPE
   SYNTAX      DisplayString
   MAX-ACCESS  read-only
   STATUS      current
   DESCRIPTION
       " "
   ::= { gs2310pplusSFPInfoEntry 10 }

gs2310pplusSFPVendorSN OBJECT-TYPE
   SYNTAX      DisplayString
   MAX-ACCESS  read-only
   STATUS      current
   DESCRIPTION
       " "
   ::= { gs2310pplusSFPInfoEntry 11 }

gs2310pplusSFPDateCode OBJECT-TYPE
   SYNTAX      DisplayString
   MAX-ACCESS  read-only
   STATUS      current
   DESCRIPTION
       " "
   ::= { gs2310pplusSFPInfoEntry 12 }

gs2310pplusSFPTemperature OBJECT-TYPE
   SYNTAX      DisplayString
   MAX-ACCESS  read-only
   STATUS      current
   DESCRIPTION
       " "
   ::= { gs2310pplusSFPInfoEntry 13 }

gs2310pplusSFPVcc OBJECT-TYPE
   SYNTAX      DisplayString
   MAX-ACCESS  read-only
   STATUS      current
   DESCRIPTION
       " "
   ::= { gs2310pplusSFPInfoEntry 14 }
   
gs2310pplusSFPMon1Bias OBJECT-TYPE
   SYNTAX      DisplayString
   MAX-ACCESS  read-only
   STATUS      current
   DESCRIPTION
       " "
   ::= { gs2310pplusSFPInfoEntry 15 }
   
gs2310pplusSFPMon2TxPWR OBJECT-TYPE
   SYNTAX      DisplayString
   MAX-ACCESS  read-only
   STATUS      current
   DESCRIPTION
       " "
   ::= { gs2310pplusSFPInfoEntry 16 }

gs2310pplusSFPMon3RxPWR OBJECT-TYPE
   SYNTAX      DisplayString
   MAX-ACCESS  read-only
   STATUS      current
   DESCRIPTION
       " "
   ::= { gs2310pplusSFPInfoEntry 17 }


gs2310pplusPortEEETable OBJECT-TYPE
   SYNTAX      SEQUENCE OF GS2310PPLUSPortEEEEntry
   MAX-ACCESS  not-accessible
   STATUS      current
   DESCRIPTION
      " "
   ::= { gs2310pplusPort 5 }

gs2310pplusPortEEEEntry OBJECT-TYPE
   SYNTAX      GS2310PPLUSPortEEEEntry
   MAX-ACCESS  not-accessible
   STATUS      current
   DESCRIPTION
       ""
   INDEX    { gs2310pplusPortEEEPort }
   ::= { gs2310pplusPortEEETable 1 }

GS2310PPLUSPortEEEEntry ::= SEQUENCE {
   gs2310pplusPortEEEPort		        Integer32,
   gs2310pplusPortEEEMode		        INTEGER,
   gs2310pplusPortEEEUrgentQueue1		INTEGER,
   gs2310pplusPortEEEUrgentQueue2		INTEGER,
   gs2310pplusPortEEEUrgentQueue3		INTEGER,
   gs2310pplusPortEEEUrgentQueue4		INTEGER,
   gs2310pplusPortEEEUrgentQueue5		INTEGER,
   gs2310pplusPortEEEUrgentQueue6		INTEGER,
   gs2310pplusPortEEEUrgentQueue7		INTEGER,
   gs2310pplusPortEEEUrgentQueue8		INTEGER
}

gs2310pplusPortEEEPort OBJECT-TYPE
   SYNTAX      Integer32(1..4095)
   MAX-ACCESS  not-accessible
   STATUS      current
   DESCRIPTION
       " "
   ::= { gs2310pplusPortEEEEntry 1 }

gs2310pplusPortEEEMode OBJECT-TYPE
   SYNTAX      INTEGER { disable(0), enable(1) }
   MAX-ACCESS  read-write
   STATUS      current
   DESCRIPTION
       "default: 0
       0:disable
       1:enable "
   ::= { gs2310pplusPortEEEEntry 2 }

gs2310pplusPortEEEUrgentQueue1 OBJECT-TYPE
   SYNTAX      INTEGER { disable(0), enable(1) }
   MAX-ACCESS  read-write
   STATUS      current
   DESCRIPTION
       "default: 0
       0:disable
       1:enable "
   ::= { gs2310pplusPortEEEEntry 3 }

gs2310pplusPortEEEUrgentQueue2 OBJECT-TYPE
   SYNTAX      INTEGER { disable(0), enable(1) }
   MAX-ACCESS  read-write
   STATUS      current
   DESCRIPTION
       "default: 0
       0:disable
       1:enable "
   ::= { gs2310pplusPortEEEEntry 4 }

gs2310pplusPortEEEUrgentQueue3 OBJECT-TYPE
   SYNTAX      INTEGER { disable(0), enable(1) }
   MAX-ACCESS  read-write
   STATUS      current
   DESCRIPTION
       "default: 0
       0:disable
       1:enable "
   ::= { gs2310pplusPortEEEEntry 5 }

gs2310pplusPortEEEUrgentQueue4 OBJECT-TYPE
   SYNTAX      INTEGER { disable(0), enable(1) }
   MAX-ACCESS  read-write
   STATUS      current
   DESCRIPTION
       "default: 0
       0:disable
       1:enable "
   ::= { gs2310pplusPortEEEEntry 6 }

gs2310pplusPortEEEUrgentQueue5 OBJECT-TYPE
   SYNTAX      INTEGER { disable(0), enable(1) }
   MAX-ACCESS  read-write
   STATUS      current
   DESCRIPTION
       "default: 0
       0:disable
       1:enable "
   ::= { gs2310pplusPortEEEEntry 7 }

gs2310pplusPortEEEUrgentQueue6 OBJECT-TYPE
   SYNTAX      INTEGER { disable(0), enable(1) }
   MAX-ACCESS  read-write
   STATUS      current
   DESCRIPTION
       "default: 0
       0:disable
       1:enable "
   ::= { gs2310pplusPortEEEEntry 8 }

gs2310pplusPortEEEUrgentQueue7 OBJECT-TYPE
   SYNTAX      INTEGER { disable(0), enable(1) }
   MAX-ACCESS  read-write
   STATUS      current
   DESCRIPTION
       "default: 0
       0:disable
       1:enable "
   ::= { gs2310pplusPortEEEEntry 9 }

gs2310pplusPortEEEUrgentQueue8 OBJECT-TYPE
   SYNTAX      INTEGER { disable(0), enable(1) }
   MAX-ACCESS  read-write
   STATUS      current
   DESCRIPTION
       "default: 0
       0:disable
       1:enable "
   ::= { gs2310pplusPortEEEEntry 10 }


gs2310pplusVoiceVLAN                                             OBJECT IDENTIFIER ::= { gs2310pplusConfiguration 2 }

gs2310pplusVoiceVLANConf                                         OBJECT IDENTIFIER ::= { gs2310pplusVoiceVLAN 1 }

gs2310pplusVoiceVLANMode OBJECT-TYPE
   SYNTAX      INTEGER { disable(0), enable(1) }
   MAX-ACCESS  read-write
   STATUS      current
   DESCRIPTION
       " Voice VLAN mode operation.
       default: 0,
       0: disable
       1: enable"
   ::= { gs2310pplusVoiceVLANConf 1 }

gs2310pplusVoiceVLANVLANId OBJECT-TYPE
   SYNTAX      Integer32(1..4094)
   MAX-ACCESS  read-write
   STATUS      current
   DESCRIPTION
       "Voice VLAN ID.
        default: 1000,
        range : 1-4094. "
   ::= { gs2310pplusVoiceVLANConf 2 }

gs2310pplusVoiceVLANAgingTime OBJECT-TYPE
   SYNTAX      Integer32(10..1000000)
   MAX-ACCESS  read-write
   STATUS      current
   DESCRIPTION
       " Voice VLAN secure learning aging time. 
         default: 86400,
         range : 10 - 10000000. "
   ::= { gs2310pplusVoiceVLANConf 3 }

gs2310pplusVoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2310pplusVoiceVLANConf 4 }


gs2310pplusVoiceVLANPortTable OBJECT-TYPE
   SYNTAX      SEQUENCE OF GS2310PPLUSVoiceVLANPortEntry
   MAX-ACCESS  not-accessible
   STATUS      current
   DESCRIPTION
       " Show Voice Vlan configuration. "
   ::= { gs2310pplusVoiceVLANConf 5 }

gs2310pplusVoiceVLANPortEntry OBJECT-TYPE
   SYNTAX      GS2310PPLUSVoiceVLANPortEntry
   MAX-ACCESS  not-accessible
   STATUS      current
   DESCRIPTION
       ""
   INDEX    { gs2310pplusVoiceVLANPort  }
   ::= { gs2310pplusVoiceVLANPortTable 1 }

GS2310PPLUSVoiceVLANPortEntry ::= SEQUENCE {
   gs2310pplusVoiceVLANPort                    Integer32,
   gs2310pplusVoiceVLANPortMode                INTEGER,
   gs2310pplusVoiceVLANPortSecurity            INTEGER,
   gs2310pplusVoiceVLANPortDiscoveryProtocol   INTEGER
}

gs2310pplusVoiceVLANPort OBJECT-TYPE
   SYNTAX      Integer32(1..4095)
   MAX-ACCESS  not-accessible
   STATUS      current
   DESCRIPTION
       " port, range : 1 - port number. "
   ::= { gs2310pplusVoiceVLANPortEntry 1 }

gs2310pplusVoiceVLANPortMode OBJECT-TYPE
   SYNTAX      INTEGER { disable(0), auto(1), forced(2) }
   MAX-ACCESS  read-write
   STATUS      current
   DESCRIPTION
       " Voice VLAN port mode.  
         default: 0,
         0: Disable (Disjoin from Voice VLAN.)
         1: Auto (Enable auto detect mode. It detects whether there is VoIP phone attached to the specific port and configures the Voice VLAN members automatically.)
         2: Forced (Force join to Voice VLAN.)"
   ::= { gs2310pplusVoiceVLANPortEntry 2 }

gs2310pplusVoiceVLANPortSecurity OBJECT-TYPE
   SYNTAX      INTEGER { disable(0), enable(1) }
   MAX-ACCESS  read-write
   STATUS      current
   DESCRIPTION
       " Voice VLAN port security mode. 
         default: 0,
         0: Disable (Disjoin from Voice VLAN.)
         1: enable ( Enable Voice VLAN security mode. When the function is
                     enabled, all non-telephone MAC address in Voice VLAN
                     will be blocked 10 seconds.)"
   ::= { gs2310pplusVoiceVLANPortEntry 3 }

gs2310pplusVoiceVLANPortDiscoveryProtocol OBJECT-TYPE
   SYNTAX      INTEGER { oui(0), lldp(1), both(2) }
   MAX-ACCESS  read-write
   STATUS      current
   DESCRIPTION
       " Voice VLAN port discovery protocol.  
         default: 0
         0: OUI (Detect telephony device by OUI address.)
         1: LLDP (Detect telephony device by LLDP.)
         2: Both (Both OUI and LLDP.) "
   ::= { gs2310pplusVoiceVLANPortEntry 4 }

gs2310pplusVoiceVLANSkipNAS OBJECT-TYPE
   SYNTAX      INTEGER { disable(0), enable(1) }
   MAX-ACCESS  read-write
   STATUS      current
   DESCRIPTION
       " Voice VLAN skip NAS mode. 
         default: 0,
         0: Disable (Do not skip NAS on Voice VLAN.)
         1: enable (Enable skipping of NAS on Voice VLAN. When the function is
                    enabled, authentication through the NAS module is not
                    applied to the Voice VLAN, but clients are allowed without
                    authentication.)"
   ::= { gs2310pplusVoiceVLANPortEntry 5 }


gs2310pplusVoiceVLANOUI                                          OBJECT IDENTIFIER ::= { gs2310pplusVoiceVLAN 2 }

gs2310pplusVoiceVLANOUICreate OBJECT-TYPE
   SYNTAX       INTEGER { none(0), create(1) }
   MAX-ACCESS   read-write
   STATUS       current
   DESCRIPTION
       "default: 0
        0 : None  (read only)
        1 : Create an OUI entry"
   ::= { gs2310pplusVoiceVLANOUI 1 }

gs2310pplusVoiceVLANOUITable OBJECT-TYPE
   SYNTAX      SEQUENCE OF GS2310PPLUSVoiceVLANOUIEntry
   MAX-ACCESS  not-accessible
   STATUS      current
   DESCRIPTION
       " Create Voice VLAN OUI entry. Modify OUI table will
         restart auto detect OUI process. "
   ::= { gs2310pplusVoiceVLANOUI 2 }

gs2310pplusVoiceVLANOUIEntry OBJECT-TYPE
   SYNTAX      GS2310PPLUSVoiceVLANOUIEntry
   MAX-ACCESS  not-accessible
   STATUS      current
   DESCRIPTION
       ""
   INDEX    { gs2310pplusVoiceVLANOUIIndex  }
   ::= { gs2310pplusVoiceVLANOUITable 1 }

GS2310PPLUSVoiceVLANOUIEntry ::= SEQUENCE {
   gs2310pplusVoiceVLANOUIIndex         Integer32,
   gs2310pplusVoiceVLANTelephonyOUI     OCTET STRING,
   gs2310pplusVoiceVLANDescription      DisplayString,
   gs2310pplusVoiceVLANOUIRowStatus     INTEGER
}

gs2310pplusVoiceVLANOUIIndex OBJECT-TYPE
   SYNTAX      Integer32(1..16)
   MAX-ACCESS  not-accessible
   STATUS      current
   DESCRIPTION
       " "
   ::= { gs2310pplusVoiceVLANOUIEntry 1 }

gs2310pplusVoiceVLANTelephonyOUI OBJECT-TYPE
   SYNTAX      OCTET STRING (SIZE (1..32))
   MAX-ACCESS  read-write
   STATUS      current
   DESCRIPTION
       "OUI address, format : 0a 1b 2c "
   ::= { gs2310pplusVoiceVLANOUIEntry 2 }

gs2310pplusVoiceVLANDescription OBJECT-TYPE
   SYNTAX      DisplayString (SIZE (1..32))
   MAX-ACCESS  read-write
   STATUS      current
   DESCRIPTION
       " Up to 32 characters describing OUI address. "
   ::= { gs2310pplusVoiceVLANOUIEntry 3 }

gs2310pplusVoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pplusVoiceVLANOUIEntry 4 }

gs2310pplusGARP                                                   OBJECT IDENTIFIER ::= { gs2310pplusConfiguration 3 }

gs2310pplusGARPConfTable OBJECT-TYPE
   SYNTAX      SEQUENCE OF GS2310PPLUSGARPConfEntry
   MAX-ACCESS  not-accessible
   STATUS      current
   DESCRIPTION
       " "
   ::= { gs2310pplusGARP 1 }

gs2310pplusGARPConfEntry OBJECT-TYPE
   SYNTAX      GS2310PPLUSGARPConfEntry
   MAX-ACCESS  not-accessible
   STATUS      current
   DESCRIPTION
       ""
   INDEX    { gs2310pplusGARPConfPort  }
   ::= { gs2310pplusGARPConfTable 1 }

GS2310PPLUSGARPConfEntry ::= SEQUENCE {
   gs2310pplusGARPConfPort           Integer32,
   gs2310pplusGARPJoinTimer          Integer32,
   gs2310pplusGARPLeaveTimer         Integer32,
   gs2310pplusGARPLeaveAllTimer      Integer32,
   gs2310pplusGARPApplicantion       INTEGER,
   gs2310pplusGARPAttributeType      INTEGER,
   gs2310pplusGARPApplicant          INTEGER
}

gs2310pplusGARPConfPort OBJECT-TYPE
   SYNTAX      Integer32(1..4095)
   MAX-ACCESS  not-accessible
   STATUS      current
   DESCRIPTION
       " "
   ::= { gs2310pplusGARPConfEntry 1 }

gs2310pplusGARPJoinTimer OBJECT-TYPE
   SYNTAX      Integer32(200..1000)
   MAX-ACCESS  read-write
   STATUS      current
   DESCRIPTION
       "default: 200, range : 200 - 1000 "
   ::= { gs2310pplusGARPConfEntry 2 }

gs2310pplusGARPLeaveTimer OBJECT-TYPE
   SYNTAX      Integer32(600..3000)
   MAX-ACCESS  read-write
   STATUS      current
   DESCRIPTION
       "default: 600 , range : 600 - 3000"
   ::= { gs2310pplusGARPConfEntry 3 }

gs2310pplusGARPLeaveAllTimer OBJECT-TYPE
   SYNTAX      Integer32(10000..50000)
   MAX-ACCESS  read-write
   STATUS      current
   DESCRIPTION
       "default: 10000, range : 10000 - 50000 "
   ::= { gs2310pplusGARPConfEntry 4 }

gs2310pplusGARPApplicantion OBJECT-TYPE
   SYNTAX      INTEGER { gvrp(1)}
   MAX-ACCESS  read-write
   STATUS      current
   DESCRIPTION
       "default: 1
       1: GVRP"
   ::= { gs2310pplusGARPConfEntry 5 }

gs2310pplusGARPAttributeType OBJECT-TYPE
   SYNTAX      INTEGER { vlan(1)}
   MAX-ACCESS  read-write
   STATUS      current
   DESCRIPTION
       "default: 1
       1: VLAN"
   ::= { gs2310pplusGARPConfEntry 6 }

gs2310pplusGARPApplicant OBJECT-TYPE
   SYNTAX      INTEGER { participant(0), nonParticipant(1) }
   MAX-ACCESS  read-write
   STATUS      current
   DESCRIPTION
       "default: 0
       0: normal-participant
       1: non-participant"
   ::= { gs2310pplusGARPConfEntry 7 }

gs2310pplusGARPStatisticsTable OBJECT-TYPE
   SYNTAX      SEQUENCE OF GS2310PPLUSGARPStatisticsEntry
   MAX-ACCESS  not-accessible
   STATUS      current
   DESCRIPTION
       " Show the basic GARP port statistics. "
   ::= { gs2310pplusGARP 2 }

gs2310pplusGARPStatisticsEntry OBJECT-TYPE
   SYNTAX      GS2310PPLUSGARPStatisticsEntry
   MAX-ACCESS  not-accessible
   STATUS      current
   DESCRIPTION
       ""
   INDEX    { gs2310pplusGARPStatisticsPort  }
   ::= { gs2310pplusGARPStatisticsTable 1 }

GS2310PPLUSGARPStatisticsEntry ::= SEQUENCE {
   gs2310pplusGARPStatisticsPort             Integer32,
   gs2310pplusGARPStatisticsPeerMAC          DisplayString,
   gs2310pplusGARPStatisticsFailedCount      Counter32
}

gs2310pplusGARPStatisticsPort OBJECT-TYPE
   SYNTAX      Integer32(1..4095)
   MAX-ACCESS  not-accessible
   STATUS      current
   DESCRIPTION
       " port, range : 1 - port number. "
   ::= { gs2310pplusGARPStatisticsEntry 1 }

gs2310pplusGARPStatisticsPeerMAC OBJECT-TYPE
   SYNTAX      DisplayString
   MAX-ACCESS  read-only
   STATUS      current
   DESCRIPTION
       " Peer MAC is MAC address of the neighbour Switch from with GARP frame is received.  "
   ::= { gs2310pplusGARPStatisticsEntry 2 }

gs2310pplusGARPStatisticsFailedCount OBJECT-TYPE
   SYNTAX      Counter32
   MAX-ACCESS  read-only
   STATUS      current
   DESCRIPTION
       " explain Failed count here. "
   ::= { gs2310pplusGARPStatisticsEntry 3 }

gs2310pplusGVRP                                                   OBJECT IDENTIFIER ::= { gs2310pplusConfiguration 4 }

gs2310pplusGVRPConf                                                   OBJECT IDENTIFIER ::= { gs2310pplusGVRP 1 }

gs2310pplusGVRPMode OBJECT-TYPE
   SYNTAX      INTEGER { disable(0), enable(1) }
   MAX-ACCESS  read-write
   STATUS      current
   DESCRIPTION
       "default: 0,
        0: disable, 
        1: enable. "
   ::= { gs2310pplusGVRPConf 1 }

gs2310pplusGVRPConfTable OBJECT-TYPE
   SYNTAX      SEQUENCE OF GS2310PPLUSGVRPConfEntry
   MAX-ACCESS  not-accessible
   STATUS      current
   DESCRIPTION
       " "
   ::= { gs2310pplusGVRPConf 2 }

gs2310pplusGVRPConfEntry OBJECT-TYPE
   SYNTAX      GS2310PPLUSGVRPConfEntry
   MAX-ACCESS  not-accessible
   STATUS      current
   DESCRIPTION
       ""
   INDEX    { gs2310pplusGVRPConfPort  }
   ::= { gs2310pplusGVRPConfTable 1 }

GS2310PPLUSGVRPConfEntry ::= SEQUENCE {
   gs2310pplusGVRPConfPort           Integer32,
   gs2310pplusGVRPConfPortMode       INTEGER,
   gs2310pplusGVRPConfPortRRole      INTEGER
}

gs2310pplusGVRPConfPort OBJECT-TYPE
   SYNTAX      Integer32(1..4095)
   MAX-ACCESS  not-accessible
   STATUS      current
   DESCRIPTION
       " "
   ::= { gs2310pplusGVRPConfEntry 1 }

gs2310pplusGVRPConfPortMode OBJECT-TYPE
   SYNTAX      INTEGER { disable(0), enable(1) }
   MAX-ACCESS  read-write
   STATUS      current
   DESCRIPTION
       "default: 0
       1: enable
       0: disable"
   ::= { gs2310pplusGVRPConfEntry 2 }

gs2310pplusGVRPConfPortRRole OBJECT-TYPE
   SYNTAX      INTEGER { disable(0), enable(1) }
   MAX-ACCESS  read-write
   STATUS      current
   DESCRIPTION
       "default: 0
       1: enable
       0: disable"
   ::= { gs2310pplusGVRPConfEntry 3 }

gs2310pplusGVRPStatisticsTable OBJECT-TYPE
   SYNTAX      SEQUENCE OF GS2310PPLUSGVRPStatisticsEntry
   MAX-ACCESS  not-accessible
   STATUS      current
   DESCRIPTION
       " "
   ::= { gs2310pplusGVRP 2 }

gs2310pplusGVRPStatisticsEntry OBJECT-TYPE
   SYNTAX      GS2310PPLUSGVRPStatisticsEntry
   MAX-ACCESS  not-accessible
   STATUS      current
   DESCRIPTION
       ""
   INDEX    { gs2310pplusGVRPStatisticsPort  }
   ::= { gs2310pplusGVRPStatisticsTable 1 }

GS2310PPLUSGVRPStatisticsEntry ::= SEQUENCE {
   gs2310pplusGVRPStatisticsPort         Integer32,
   gs2310pplusGVRPStatisticsJoinTxCnt    Counter32,
   gs2310pplusGVRPStatisticsLeaveTxCnt   Counter32
}

gs2310pplusGVRPStatisticsPort OBJECT-TYPE
   SYNTAX      Integer32(1..4095)
   MAX-ACCESS  not-accessible
   STATUS      current
   DESCRIPTION
       " "
   ::= { gs2310pplusGVRPStatisticsEntry 1 }

gs2310pplusGVRPStatisticsJoinTxCnt OBJECT-TYPE
   SYNTAX      Counter32
   MAX-ACCESS  read-only
   STATUS      current
   DESCRIPTION
       ""
   ::= { gs2310pplusGVRPStatisticsEntry 2 }

gs2310pplusGVRPStatisticsLeaveTxCnt OBJECT-TYPE
   SYNTAX      Counter32
   MAX-ACCESS  read-only
   STATUS      current
   DESCRIPTION
       ""
   ::= { gs2310pplusGVRPStatisticsEntry 3 }


gs2310pplusMirroring                                             OBJECT IDENTIFIER ::= { gs2310pplusConfiguration 6 }

gs2310pplusPortToMirrorOn OBJECT-TYPE
   SYNTAX      Integer32(0..10)
   MAX-ACCESS  read-write
   STATUS      current
   DESCRIPTION
       "default: 0 
        0: disable,
        range : 1 - port number. "
   ::= { gs2310pplusMirroring 1 }

gs2310pplusMirrorTable OBJECT-TYPE
   SYNTAX      SEQUENCE OF GS2310PPLUSMirrorEntry
   MAX-ACCESS  not-accessible
   STATUS      current
   DESCRIPTION
       " "
   ::= { gs2310pplusMirroring 2 }

gs2310pplusMirrorEntry OBJECT-TYPE
   SYNTAX      GS2310PPLUSMirrorEntry
   MAX-ACCESS  not-accessible
   STATUS      current
   DESCRIPTION
       ""
   INDEX    { gs2310pplusMirrorPort  }
   ::= { gs2310pplusMirrorTable 1 }

GS2310PPLUSMirrorEntry ::= SEQUENCE {
   gs2310pplusMirrorPort		Integer32,
   gs2310pplusMirrorMode		INTEGER
}

gs2310pplusMirrorPort OBJECT-TYPE
   SYNTAX      Integer32(1..4095)
   MAX-ACCESS  not-accessible
   STATUS      current
   DESCRIPTION
       " "
   ::= { gs2310pplusMirrorEntry 1 }

gs2310pplusMirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2310pplusMirrorEntry 2 }

gs2310pplusTrapEventSeverity                                             OBJECT IDENTIFIER ::= { gs2310pplusConfiguration 7 }

gs2310pplusTrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 1 }

gs2310pplusTrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2310pplusTrapEventSeverity 2 }

gs2310pplusTrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 3 }

gs2310pplusTrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pplusTrapEventSeverity 4 }

gs2310pplusTrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pplusTrapEventSeverity 5 }

gs2310pplusTrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 6 }

gs2310pplusTrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 7 }

gs2310pplusTrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 8 }

gs2310pplusTrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 9 }

gs2310pplusTrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pplusTrapEventSeverity 10 }

gs2310pplusTrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 11 }

gs2310pplusTrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 12 }

gs2310pplusTrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 13 }

gs2310pplusTrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 14 }

gs2310pplusTrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2310pplusTrapEventSeverity 15 }

gs2310pplusTrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 16 }

gs2310pplusTrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 17 }

gs2310pplusTrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 18 }

gs2310pplusTrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2310pplusTrapEventSeverity 20 }

gs2310pplusTrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pplusTrapEventSeverity 21 }

gs2310pplusTrapEventSeverityPoEAutoCheck OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pplusTrapEventSeverity 22 }

gs2310pplusTrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pplusTrapEventSeverity 25 }

gs2310pplusTrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pplusTrapEventSeverity 27 }
   
gs2310pplusTrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2310pplusTrapEventSeverity 28 }

gs2310pplusSMTP                                             OBJECT IDENTIFIER ::= { gs2310pplusConfiguration 8 }

gs2310pplusSMTPMailServer OBJECT-TYPE
   SYNTAX      DisplayString
   MAX-ACCESS  read-write
   STATUS      current
   DESCRIPTION
       " Up to 47 characters describing email server. "
   ::= { gs2310pplusSMTP 1 }

gs2310pplusSMTPUserName OBJECT-TYPE
   SYNTAX      DisplayString
   MAX-ACCESS  read-write
   STATUS      current
   DESCRIPTION
       " Up to 47 characters describing user name. "
   ::= { gs2310pplusSMTP 2 }

gs2310pplusSMTPPassword OBJECT-TYPE
   SYNTAX      DisplayString
   MAX-ACCESS  read-write
   STATUS      current
   DESCRIPTION
       " Up to 47 characters describing password. "
   ::= { gs2310pplusSMTP 3 }

gs2310pplusSMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2310pplusSMTP 4 }

gs2310pplusSMTPSender OBJECT-TYPE
   SYNTAX      DisplayString
   MAX-ACCESS  read-write
   STATUS      current
   DESCRIPTION
       " Up to 47 characters describing sender. "
   ::= { gs2310pplusSMTP 5 }

gs2310pplusSMTPReturnPath OBJECT-TYPE
   SYNTAX      DisplayString
   MAX-ACCESS  read-write
   STATUS      current
   DESCRIPTION
       " Up to 47 characters describing return path. "
   ::= { gs2310pplusSMTP 6 }

gs2310pplusSMTPEmailAddress1 OBJECT-TYPE
   SYNTAX      DisplayString
   MAX-ACCESS  read-write
   STATUS      current
   DESCRIPTION
       " Up to 47 characters describing mail address. "
   ::= { gs2310pplusSMTP 7 }

gs2310pplusSMTPEmailAddress2 OBJECT-TYPE
   SYNTAX      DisplayString
   MAX-ACCESS  read-write
   STATUS      current
   DESCRIPTION
       " Up to 47 characters describing mail address. "
   ::= { gs2310pplusSMTP 8 }

gs2310pplusSMTPEmailAddress3 OBJECT-TYPE
   SYNTAX      DisplayString
   MAX-ACCESS  read-write
   STATUS      current
   DESCRIPTION
       " Up to 47 characters describing mail address. "
   ::= { gs2310pplusSMTP 9 }

gs2310pplusSMTPEmailAddress4 OBJECT-TYPE
   SYNTAX      DisplayString
   MAX-ACCESS  read-write
   STATUS      current
   DESCRIPTION
       " Up to 47 characters describing mail address. "
   ::= { gs2310pplusSMTP 10 }

gs2310pplusSMTPEmailAddress5 OBJECT-TYPE
   SYNTAX      DisplayString
   MAX-ACCESS  read-write
   STATUS      current
   DESCRIPTION
       " Up to 47 characters describing mail address. "
   ::= { gs2310pplusSMTP 11 }

gs2310pplusSMTPEmailAddress6 OBJECT-TYPE
   SYNTAX      DisplayString
   MAX-ACCESS  read-write
   STATUS      current
   DESCRIPTION
       " Up to 47 characters describing mail address. "
   ::= { gs2310pplusSMTP 12 }


gs2310pplusACL                                                   OBJECT IDENTIFIER ::= { gs2310pplusConfiguration 9 }

gs2310pplusACLPortsConfTable OBJECT-TYPE
   SYNTAX      SEQUENCE OF GS2310PPLUSACLPortsConfEntry
   MAX-ACCESS  not-accessible
   STATUS      current
   DESCRIPTION
       " "
   ::= { gs2310pplusACL 1 }

gs2310pplusACLPortsConfEntry OBJECT-TYPE
   SYNTAX      GS2310PPLUSACLPortsConfEntry
   MAX-ACCESS  not-accessible
   STATUS      current
   DESCRIPTION
       ""
   INDEX    { gs2310pplusACLPortsConfPort  }
   ::= { gs2310pplusACLPortsConfTable 1 }

GS2310PPLUSACLPortsConfEntry ::= SEQUENCE {
   gs2310pplusACLPortsConfPort               Integer32,
   gs2310pplusACLPortsConfPolicyID           Integer32,
   gs2310pplusACLPortsConfAction             INTEGER,
   gs2310pplusACLPortsConfRateLimiterID      Integer32,
   gs2310pplusACLPortsConfPortRedirect       Integer32,
   gs2310pplusACLPortsConfMirror             INTEGER,
   gs2310pplusACLPortsConfLogging            INTEGER,
   gs2310pplusACLPortsConfShutdown           INTEGER,
   gs2310pplusACLPortsConfState              INTEGER,
   gs2310pplusACLPortsConfCounter            Counter32
}

gs2310pplusACLPortsConfPort OBJECT-TYPE
   SYNTAX      Integer32 (1..4095)
   MAX-ACCESS  not-accessible
   STATUS      current
   DESCRIPTION
       " "
   ::= { gs2310pplusACLPortsConfEntry 1 }

gs2310pplusACLPortsConfPolicyID OBJECT-TYPE
   SYNTAX      Integer32 (0..255)
   MAX-ACCESS  read-write
   STATUS      current
   DESCRIPTION
       "default: 0, range : 0 - 255 "
   ::= { gs2310pplusACLPortsConfEntry 2 }

gs2310pplusACLPortsConfAction OBJECT-TYPE
   SYNTAX      INTEGER { deny(0), permit(1) }
   MAX-ACCESS  read-write
   STATUS      current
   DESCRIPTION
       "default: 1,
        0: Deny
        1: Permit"
   ::= { gs2310pplusACLPortsConfEntry 3 }

gs2310pplusACLPortsConfRateLimiterID OBJECT-TYPE
   SYNTAX      Integer32 (0..12)
   MAX-ACCESS  read-write
   STATUS      current
   DESCRIPTION
       "default: 0,
        0: Disable
        range : 0 - 12 "
   ::= { gs2310pplusACLPortsConfEntry 4 }

gs2310pplusACLPortsConfPortRedirect OBJECT-TYPE
   SYNTAX      Integer32 (0..4095)
   MAX-ACCESS  read-write
   STATUS      current
   DESCRIPTION
       "default: 0
        0: Disable
        range : 0 - end port number "
   ::= { gs2310pplusACLPortsConfEntry 5 }

gs2310pplusACLPortsConfMirror OBJECT-TYPE
   SYNTAX      INTEGER { disable(0), enable(1) }
   MAX-ACCESS  read-write
   STATUS      current
   DESCRIPTION
       "default: 0
        0: Disable
        1: Enable "
   ::= { gs2310pplusACLPortsConfEntry 6 }

gs2310pplusACLPortsConfLogging OBJECT-TYPE
   SYNTAX      INTEGER { disable(0), enable(1) }
   MAX-ACCESS  read-write
   STATUS      current
   DESCRIPTION
       "default: 0
        0: Disable
        1: Enable "
   ::= { gs2310pplusACLPortsConfEntry 7 }

gs2310pplusACLPortsConfShutdown OBJECT-TYPE
   SYNTAX      INTEGER { disable(0), enable(1) }
   MAX-ACCESS  read-write
   STATUS      current
   DESCRIPTION
       "default: 0
        0: Disable
        1: Enable "
   ::= { gs2310pplusACLPortsConfEntry 8 }
   
gs2310pplusACLPortsConfState OBJECT-TYPE
   SYNTAX      INTEGER { disable(0), enable(1) }
   MAX-ACCESS  read-write
   STATUS      current
   DESCRIPTION
       "default: 1
        0: Disable
        1: Enable "
   ::= { gs2310pplusACLPortsConfEntry 9 }

gs2310pplusACLPortsConfCounter OBJECT-TYPE
   SYNTAX      Counter32
   MAX-ACCESS  read-only
   STATUS      current
   DESCRIPTION
       "Counts the number of frames that match this ACE. "
   ::= { gs2310pplusACLPortsConfEntry 10 }


gs2310pplusACLRateLimiterTable OBJECT-TYPE
   SYNTAX      SEQUENCE OF GS2310PPLUSACLRateLimiterEntry
   MAX-ACCESS  not-accessible
   STATUS      current
   DESCRIPTION
       " "
   ::= { gs2310pplusACL 2 }

gs2310pplusACLRateLimiterEntry OBJECT-TYPE
   SYNTAX      GS2310PPLUSACLRateLimiterEntry
   MAX-ACCESS  not-accessible
   STATUS      current
   DESCRIPTION
       ""
   INDEX    { gs2310pplusACLRateLimiterID  }
   ::= { gs2310pplusACLRateLimiterTable 1 }

GS2310PPLUSACLRateLimiterEntry ::= SEQUENCE {
   gs2310pplusACLRateLimiterID       Integer32,
   gs2310pplusACLRateLimiterUnit     INTEGER,
   gs2310pplusACLRateLimiterRate     Integer32
}

gs2310pplusACLRateLimiterID OBJECT-TYPE
   SYNTAX      Integer32 (1..12)
   MAX-ACCESS  not-accessible
   STATUS      current
   DESCRIPTION
       " Rate Limiter ID.
         range : 1-12 "
   ::= { gs2310pplusACLRateLimiterEntry 1 }

gs2310pplusACLRateLimiterUnit OBJECT-TYPE
   SYNTAX      INTEGER { pps(0), kbps(1) }
   MAX-ACCESS  read-write
   STATUS      current
   DESCRIPTION
       "default: 0, 
        0: pps
        1: kbps"
   ::= { gs2310pplusACLRateLimiterEntry 2 }

gs2310pplusACLRateLimiterRate OBJECT-TYPE
   SYNTAX      Integer32(0..3276700)
   MAX-ACCESS  read-write
   STATUS      current
   DESCRIPTION
       "default: 1, 
        range : <0-3276700> pps
                <0-10000> kbps"
   ::= { gs2310pplusACLRateLimiterEntry 3 }


gs2310pplusACLACE                                          OBJECT IDENTIFIER ::= { gs2310pplusACL 3 }

gs2310pplusACLACECreate OBJECT-TYPE
   SYNTAX       INTEGER { none(0), create(1) }
   MAX-ACCESS   read-write
   STATUS       current
   DESCRIPTION
       "default: 0
        0 : None  (read only)
        1 : Create an ACE entry"
   ::= { gs2310pplusACLACE 1 }

gs2310pplusACLACETable OBJECT-TYPE
   SYNTAX      SEQUENCE OF GS2310PPLUSACLACEEntry
   MAX-ACCESS  not-accessible
   STATUS      current
   DESCRIPTION
       " Create ACL ACE entry. "
   ::= { gs2310pplusACLACE 2 }

gs2310pplusACLACEEntry OBJECT-TYPE
   SYNTAX      GS2310PPLUSACLACEEntry
   MAX-ACCESS  not-accessible
   STATUS      current
   DESCRIPTION
       ""
   INDEX    { gs2310pplusACLACEIndex  }
   ::= { gs2310pplusACLACETable 1 }

GS2310PPLUSACLACEEntry ::= SEQUENCE {
   gs2310pplusACLACEIndex                Integer32,
   gs2310pplusACLACEID                   Integer32,
   gs2310pplusACLACENextID               Integer32,
   gs2310pplusACLACEIngressPort          DisplayString,
   gs2310pplusACLACEPortPolicyNumber     Integer32,
   
   gs2310pplusACLACEPortPolicyBitmask    Integer32,
   gs2310pplusACLACEFrameType            INTEGER,
   gs2310pplusACLACEAction               INTEGER,
   gs2310pplusACLACEDenyPortRedirect     DisplayString,
   gs2310pplusACLACELogging              INTEGER,
   
   gs2310pplusACLACEMirror               INTEGER,
   gs2310pplusACLACERateLimiter          Integer32,
   gs2310pplusACLACEShutdown             INTEGER,
   gs2310pplusACLACEVLAN8021QTagged      INTEGER,
   gs2310pplusACLACEVLANTagPriority      Integer32,
   
   gs2310pplusACLACEVLANVID              Integer32,
   gs2310pplusACLACEEtherType            Integer32,
   gs2310pplusACLACESMAC                 DisplayString,
   gs2310pplusACLACEDMACType             INTEGER,
   gs2310pplusACLACEDMAC                 DisplayString,
   
   gs2310pplusACLACEArpOpcode            INTEGER,
   gs2310pplusACLACEArpFlagsRequestReply INTEGER,
   gs2310pplusACLACEArpFlagsArpSmac      INTEGER,
   gs2310pplusACLACEArpFlagsRarpDmac     INTEGER,
   gs2310pplusACLACEArpFlagsLength       INTEGER,
   
   gs2310pplusACLACEArpFlagsIp           INTEGER,
   gs2310pplusACLACEArpFlagsEthernet     INTEGER,
   gs2310pplusACLACESIPType              INTEGER,
   gs2310pplusACLACESIPIPAddress         IpAddress,                      
   gs2310pplusACLACESIPNetworkPrefix     Integer32,
   
   gs2310pplusACLACEDIPType              INTEGER,
   gs2310pplusACLACEDIPIPAddress         IpAddress,                      
   gs2310pplusACLACEDIPNetworkPrefix     Integer32,
   
   gs2310pplusACLACEIPProtocol           Integer32,
   gs2310pplusACLACEIPFlagsTTL           INTEGER,
   gs2310pplusACLACEIPFlagsOptions       INTEGER,
   gs2310pplusACLACEIPFlagsFragment      INTEGER,
   gs2310pplusACLACEICMPType             Integer32,
   
   gs2310pplusACLACEICMPCode             Integer32,
   gs2310pplusACLACESourcePortMin        Integer32,
   gs2310pplusACLACESourcePortMax        Integer32,
   gs2310pplusACLACEDestPortMin          Integer32,
   gs2310pplusACLACEDestPortMax          Integer32,
   
   gs2310pplusACLACETCPFlagsFin          INTEGER,
   gs2310pplusACLACETCPFlagsSyn          INTEGER,
   gs2310pplusACLACETCPFlagsRst          INTEGER,
   gs2310pplusACLACETCPFlagsPsh          INTEGER,
   gs2310pplusACLACETCPFlagsAck          INTEGER,
   
   gs2310pplusACLACETCPFlagsUrg          INTEGER,
   
   gs2310pplusACLACERowStatus            INTEGER
}

gs2310pplusACLACEIndex OBJECT-TYPE
   SYNTAX      Integer32(1..256)
   MAX-ACCESS  not-accessible
   STATUS      current
   DESCRIPTION
       " "
   ::= { gs2310pplusACLACEEntry 1 }

gs2310pplusACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2310pplusACLACEEntry 2 }

gs2310pplusACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2310pplusACLACEEntry 3 }

gs2310pplusACLACEIngressPort OBJECT-TYPE
   SYNTAX      DisplayString
   MAX-ACCESS  read-write
   STATUS      current
   DESCRIPTION
       " Indicates the ingress port of the ACE. Possible values are: 
         All: The ACE will match all ingress port. 
         Port: The ACE will match a specific ingress port.Format: 1,3,6."
   ::= { gs2310pplusACLACEEntry 4 }

gs2310pplusACLACEPortPolicyNumber OBJECT-TYPE
   SYNTAX      Integer32(0..255)
   MAX-ACCESS  read-write
   STATUS      current
   DESCRIPTION
       " policy value.
         range : 0 - 255. "
   ::= { gs2310pplusACLACEEntry 5 }
   
gs2310pplusACLACEPortPolicyBitmask OBJECT-TYPE
   SYNTAX      Integer32(0..255)
   MAX-ACCESS  read-write
   STATUS      current
   DESCRIPTION
       " policy bitmask.
         range : 0 - 255(0xff). "
   ::= { gs2310pplusACLACEEntry 6 }

gs2310pplusACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2310pplusACLACEEntry 7 }

gs2310pplusACLACEAction OBJECT-TYPE
   SYNTAX      INTEGER { deny(0), permit(1) }
   MAX-ACCESS  read-write
   STATUS      current
   DESCRIPTION
       "default: 1,
        0: Deny
        1: Permit"
   ::= { gs2310pplusACLACEEntry 8 }

gs2310pplusACLACEDenyPortRedirect OBJECT-TYPE
   SYNTAX      DisplayString
   MAX-ACCESS  read-write
   STATUS      current
   DESCRIPTION
       " Frames that hit the ACE are redirected to the port number specified here.  
         Disabled: indicates that the port redirect operation is disabled. 
         Port Format: 1,3,6."
   ::= { gs2310pplusACLACEEntry 9 }

gs2310pplusACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2310pplusACLACEEntry 10 }

gs2310pplusACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { gs2310pplusACLACEEntry 11 }

gs2310pplusACLACERateLimiter OBJECT-TYPE
   SYNTAX      Integer32(0..12)
   MAX-ACCESS  read-write
   STATUS      current
   DESCRIPTION
       "default: 0,
        0: Disable
        range : 0 - 12 "
   ::= { gs2310pplusACLACEEntry 12 }

gs2310pplusACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2310pplusACLACEEntry 13 }

gs2310pplusACLACEVLAN8021QTagged OBJECT-TYPE
   SYNTAX      INTEGER { disable(0), enable(1), any(2) }
   MAX-ACCESS  read-write
   STATUS      current
   DESCRIPTION
       "Specify whether frames can hit the action according to the 802.1Q tagged. 
        default: 2,
        0: disable - Untagged frame only.
        1: enable - Tagged frame only.
        2: Any - Any value is allowed. "
   ::= { gs2310pplusACLACEEntry 14 }

gs2310pplusACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2310pplusACLACEEntry 15 }

gs2310pplusACLACEVLANVID OBJECT-TYPE
   SYNTAX      Integer32(0..4094)
   MAX-ACCESS  read-write
   STATUS      current
   DESCRIPTION
       "Specify the VLAN ID filter for this ACE.
        The vid can't be set when 802.1Q Tagged is disabled. 
        default: 0,
        0: Any - No VLAN ID filter is specified.
        range : 0 - 4094 "
   ::= { gs2310pplusACLACEEntry 16 }

gs2310pplusACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2310pplusACLACEEntry 17 }

gs2310pplusACLACESMAC OBJECT-TYPE
   SYNTAX      DisplayString
   MAX-ACCESS  read-write
   STATUS      current
   DESCRIPTION
       " Configure source MAC address for this ACE.
         <mac-address>: A frame that hits this ACE matches this source MAC address value. 
         Any: Don't care."
   ::= { gs2310pplusACLACEEntry 18 }

gs2310pplusACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { gs2310pplusACLACEEntry 19 }

gs2310pplusACLACEDMAC OBJECT-TYPE
   SYNTAX      DisplayString
   MAX-ACCESS  read-write
   STATUS      current
   DESCRIPTION
       " Configure destination MAC address for this ACE. 
         <mac-address>: A frame that hits this ACE matches this destination MAC address value.            
         Any: Don't care.
         Broadcast: Frame must be broadcast.
         Unicast: Frame must be unicast.
         Multicast: Frame must be multicast. "
   ::= { gs2310pplusACLACEEntry 20 }

gs2310pplusACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2310pplusACLACEEntry 21 }

gs2310pplusACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2310pplusACLACEEntry 22 }

gs2310pplusACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2310pplusACLACEEntry 23 }   

gs2310pplusACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2310pplusACLACEEntry 24 }

gs2310pplusACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2310pplusACLACEEntry 25 }

gs2310pplusACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2310pplusACLACEEntry 26 }

gs2310pplusACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2310pplusACLACEEntry 27 }
   
gs2310pplusACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { gs2310pplusACLACEEntry 28 }   
   
gs2310pplusACLACESIPIPAddress OBJECT-TYPE
   SYNTAX      IpAddress
   MAX-ACCESS  read-write
   STATUS      current
   DESCRIPTION
       "A frame that hits this ACE matches this source IP address value."
   ::= { gs2310pplusACLACEEntry 29 }      
   
gs2310pplusACLACESIPNetworkPrefix OBJECT-TYPE
   SYNTAX      Integer32(0..32)
   MAX-ACCESS  read-write
   STATUS      current
   DESCRIPTION
       "Network prefix.
        default: 32,
        0: No data.
        range : 1 - 32"
   ::= { gs2310pplusACLACEEntry 30 }   
   

gs2310pplusACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2310pplusACLACEEntry 32 }   
   
gs2310pplusACLACEDIPIPAddress OBJECT-TYPE
   SYNTAX      IpAddress
   MAX-ACCESS  read-write
   STATUS      current
   DESCRIPTION
       "A frame that hits this ACE matches this destination IP address value."
   ::= { gs2310pplusACLACEEntry 33 }      
   
gs2310pplusACLACEDIPNetworkPrefix OBJECT-TYPE
   SYNTAX      Integer32(0..32)
   MAX-ACCESS  read-write
   STATUS      current
   DESCRIPTION
       "Network prefix.
        default: 32,
        0: No data.
        range : 1 - 32"
   ::= { gs2310pplusACLACEEntry 34 }  
   
   
gs2310pplusACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { gs2310pplusACLACEEntry 36 } 

gs2310pplusACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2310pplusACLACEEntry 37 }   
   
gs2310pplusACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2310pplusACLACEEntry 38 }

gs2310pplusACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2310pplusACLACEEntry 39 }

gs2310pplusACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { gs2310pplusACLACEEntry 40 }   

gs2310pplusACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2310pplusACLACEEntry 41 } 

gs2310pplusACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2310pplusACLACEEntry 42 }     
   
gs2310pplusACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2310pplusACLACEEntry 43 } 
      
gs2310pplusACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { gs2310pplusACLACEEntry 44 }     

gs2310pplusACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { gs2310pplusACLACEEntry 45 }

gs2310pplusACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2310pplusACLACEEntry 46 }

gs2310pplusACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2310pplusACLACEEntry 47 }

gs2310pplusACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2310pplusACLACEEntry 48 }

gs2310pplusACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2310pplusACLACEEntry 49 }

gs2310pplusACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2310pplusACLACEEntry 50 }

gs2310pplusACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2310pplusACLACEEntry 51 }

gs2310pplusACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2310pplusACLACEEntry 66 }


gs2310pplusACLACEClear OBJECT-TYPE
   SYNTAX       INTEGER { noAction(0), clear(1) }
   MAX-ACCESS   read-write
   STATUS       current
   DESCRIPTION
       "default: 0
        0 : No action
        1 : Clear all ACL counters."
   ::= { gs2310pplusACLACE 3 }

gs2310pplusACLACEMoveACEID OBJECT-TYPE
   SYNTAX       Integer32(0..256)
   MAX-ACCESS   read-write
   STATUS       current
   DESCRIPTION
       "Move ACE,
        default: 0
        ACE ID must be exist.
        range : 1 - 256."
   ::= { gs2310pplusACLACE 4 }

gs2310pplusACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2310pplusACLACE 5 }

gs2310pplusACLACEStatusTable OBJECT-TYPE
   SYNTAX      SEQUENCE OF GS2310PPLUSACLACEStatusEntry
   MAX-ACCESS  not-accessible
   STATUS      current
   DESCRIPTION
       " ACL ACE Status entry. "
   ::= { gs2310pplusACLACE 6 }

gs2310pplusACLACEStatusEntry OBJECT-TYPE
   SYNTAX      GS2310PPLUSACLACEStatusEntry
   MAX-ACCESS  not-accessible
   STATUS      current
   DESCRIPTION
       ""
   INDEX    { gs2310pplusACLACEStatusIndex  }
   ::= { gs2310pplusACLACEStatusTable 1 }

GS2310PPLUSACLACEStatusEntry ::= SEQUENCE {
   gs2310pplusACLACEStatusIndex          Integer32,
   gs2310pplusACLACEStatusUser           DisplayString,
   gs2310pplusACLACEStatusID             Integer32,
   gs2310pplusACLACEStatusIngressPort    DisplayString,
   gs2310pplusACLACEStatusFrameType      DisplayString,
   gs2310pplusACLACEStatusAction         DisplayString,
   gs2310pplusACLACEStatusRateLimiter    DisplayString,
   gs2310pplusACLACEStatusPortCopy       DisplayString,
   gs2310pplusACLACEStatusMirror         DisplayString,
   gs2310pplusACLACEStatusCPU            DisplayString,
   gs2310pplusACLACEStatusCounter        Counter32,
   gs2310pplusACLACEStatusConflict       DisplayString
}

gs2310pplusACLACEStatusIndex OBJECT-TYPE
   SYNTAX      Integer32(1..256)
   MAX-ACCESS  not-accessible
   STATUS      current
   DESCRIPTION
       " "
   ::= { gs2310pplusACLACEStatusEntry 1 }

gs2310pplusACLACEStatusUser OBJECT-TYPE
   SYNTAX      DisplayString
   MAX-ACCESS  read-only
   STATUS      current
   DESCRIPTION
       " Indicates the ACL user. 
         S : Static.  
         IPMG : IP Management.  
         IPSG : IP Source Guard.  
         IPMC : IPMC.  
         ARPI : Arp Inspection.  
         UPnP : UPnP.  
         DHCP : DHCP. "
   ::= { gs2310pplusACLACEStatusEntry 2 }

gs2310pplusACLACEStatusID OBJECT-TYPE
   SYNTAX      Integer32(1..256)
   MAX-ACCESS  read-only
   STATUS      current
   DESCRIPTION
       " ACE ID.
         range : 1 - 256. "
   ::= { gs2310pplusACLACEStatusEntry 3 }

gs2310pplusACLACEStatusIngressPort OBJECT-TYPE
   SYNTAX      DisplayString
   MAX-ACCESS  read-only
   STATUS      current
   DESCRIPTION
       " Indicates the ingress port of the ACE. Possible values are: 
         All: The ACE will match all ingress port. 
         Port: The ACE will match a specific ingress port. "
   ::= { gs2310pplusACLACEStatusEntry 4 }

gs2310pplusACLACEStatusFrameType OBJECT-TYPE
   SYNTAX      DisplayString
   MAX-ACCESS  read-only
   STATUS      current
   DESCRIPTION
       " Indicates the frame type of the ACE. "
   ::= { gs2310pplusACLACEStatusEntry 5 }

gs2310pplusACLACEStatusAction OBJECT-TYPE
   SYNTAX      DisplayString
   MAX-ACCESS  read-only
   STATUS      current
   DESCRIPTION
       " Indicates the forwarding action of the ACE. "
   ::= { gs2310pplusACLACEStatusEntry 6 }

gs2310pplusACLACEStatusRateLimiter OBJECT-TYPE
   SYNTAX      DisplayString
   MAX-ACCESS  read-only
   STATUS      current
   DESCRIPTION
       " Indicates the rate limiter number of the ACE. "
   ::= { gs2310pplusACLACEStatusEntry 7 }

gs2310pplusACLACEStatusPortCopy OBJECT-TYPE
   SYNTAX      DisplayString
   MAX-ACCESS  read-only
   STATUS      current
   DESCRIPTION
       " Indicates the port redirect operation of the ACE. Frames matching the ACE are redirected to the port number. "
   ::= { gs2310pplusACLACEStatusEntry 8 }

gs2310pplusACLACEStatusMirror OBJECT-TYPE
   SYNTAX      DisplayString
   MAX-ACCESS  read-only
   STATUS      current
   DESCRIPTION
       " Specify the mirror operation of this port. "
   ::= { gs2310pplusACLACEStatusEntry 9 }

gs2310pplusACLACEStatusCPU OBJECT-TYPE
   SYNTAX      DisplayString
   MAX-ACCESS  read-only
   STATUS      current
   DESCRIPTION
       " Forward packet that matched the specific ACE to CPU. "
   ::= { gs2310pplusACLACEStatusEntry 10 }

gs2310pplusACLACEStatusCounter OBJECT-TYPE
   SYNTAX      Counter32
   MAX-ACCESS  read-only
   STATUS      current
   DESCRIPTION
       " The counter indicates the number of times the ACE was hit by a frame. "
   ::= { gs2310pplusACLACEStatusEntry 11 }
   
gs2310pplusACLACEStatusConflict OBJECT-TYPE
   SYNTAX      DisplayString
   MAX-ACCESS  read-only
   STATUS      current
   DESCRIPTION
       " Indicates the hardware status of the specific ACE. The specific ACE is not applied to the hardware due to hardware limitations. "
   ::= { gs2310pplusACLACEStatusEntry 12 }

gs2310pplusLoopProtection                                                  OBJECT IDENTIFIER ::= { gs2310pplusConfiguration 12 }

gs2310pplusLoopProtectionConfig                                            OBJECT IDENTIFIER ::= { gs2310pplusLoopProtection 1 }

gs2310pplusLoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2310pplusLoopProtectionConfig 1 }
   
gs2310pplusLoopProtectionTranmisstionTime OBJECT-TYPE
   SYNTAX      Integer32(1..10)
   MAX-ACCESS  read-write
   STATUS      current
   DESCRIPTION
       "Configure loop protection transmit interval.
        default: 5,
        range: 1-10. "
   ::= { gs2310pplusLoopProtectionConfig 2 }
   
gs2310pplusLoopProtectionShutdownTime OBJECT-TYPE
   SYNTAX      Integer32(0..604800)
   MAX-ACCESS  read-write
   STATUS      current
   DESCRIPTION
       "Configure loop protection shutdown time.
        default: 180,
        range: 0-604800. "
   ::= { gs2310pplusLoopProtectionConfig 3 }

gs2310pplusLoopProtectionConfigurationTable OBJECT-TYPE
   SYNTAX      SEQUENCE OF GS2310PPLUSLoopProtectionConfigurationEntry
   MAX-ACCESS  not-accessible
   STATUS      current
   DESCRIPTION
       " Show Loop Protection configurations. "
   ::= { gs2310pplusLoopProtectionConfig 4 }

gs2310pplusLoopProtectionConfigurationEntry OBJECT-TYPE
   SYNTAX      GS2310PPLUSLoopProtectionConfigurationEntry
   MAX-ACCESS  not-accessible
   STATUS      current
   DESCRIPTION
       ""
   INDEX    { gs2310pplusLoopProtectionConfPort  }
   ::= { gs2310pplusLoopProtectionConfigurationTable 1 }

GS2310PPLUSLoopProtectionConfigurationEntry ::= SEQUENCE {
   gs2310pplusLoopProtectionConfPort	    Integer32,
   gs2310pplusLoopProtectionConfEnable	INTEGER,
   gs2310pplusLoopProtectionConfAction	INTEGER,
   gs2310pplusLoopProtectionConfTxmode	INTEGER
}

gs2310pplusLoopProtectionConfPort OBJECT-TYPE
   SYNTAX      Integer32(1..4095)
   MAX-ACCESS  not-accessible
   STATUS      current
   DESCRIPTION
       " port, range : 1 - port number. "
   ::= { gs2310pplusLoopProtectionConfigurationEntry 1 }

gs2310pplusLoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2310pplusLoopProtectionConfigurationEntry 2 }

gs2310pplusLoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2310pplusLoopProtectionConfigurationEntry 3 }
   
gs2310pplusLoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2310pplusLoopProtectionConfigurationEntry 4 }
   
gs2310pplusLoopProtectionStatusTable OBJECT-TYPE
   SYNTAX      SEQUENCE OF GS2310PPLUSLoopProtectionStatusEntry
   MAX-ACCESS  not-accessible
   STATUS      current
   DESCRIPTION
       " Show Loop Protection Status. "
   ::= { gs2310pplusLoopProtection 2 }

gs2310pplusLoopProtectionStatusEntry OBJECT-TYPE
   SYNTAX      GS2310PPLUSLoopProtectionStatusEntry
   MAX-ACCESS  not-accessible
   STATUS      current
   DESCRIPTION
       ""
   INDEX    { gs2310pplusLoopProtectionStatusPort  }
   ::= { gs2310pplusLoopProtectionStatusTable 1 }

GS2310PPLUSLoopProtectionStatusEntry ::= SEQUENCE {
   gs2310pplusLoopProtectionStatusPort	       Integer32,
   gs2310pplusLoopProtectionStatusAction	       DisplayString,
   gs2310pplusLoopProtectionStatusTransmit	   DisplayString,
   gs2310pplusLoopProtectionStatusLoops	       Integer32,
   gs2310pplusLoopProtectionStatusStatus	       DisplayString,
   gs2310pplusLoopProtectionStatusLoop	       DisplayString,
   gs2310pplusLoopProtectionStatusTimeLastLoop  DisplayString
}

gs2310pplusLoopProtectionStatusPort OBJECT-TYPE
   SYNTAX      Integer32(1..4095)
   MAX-ACCESS  not-accessible
   STATUS      current
   DESCRIPTION
       " port, range : 1 - port number. "
   ::= { gs2310pplusLoopProtectionStatusEntry 1 }
   
gs2310pplusLoopProtectionStatusAction OBJECT-TYPE
   SYNTAX      DisplayString
   MAX-ACCESS  read-only
   STATUS      current
   DESCRIPTION
       " The currently configured port action. "
   ::= { gs2310pplusLoopProtectionStatusEntry 2 }
   
gs2310pplusLoopProtectionStatusTransmit OBJECT-TYPE
   SYNTAX      DisplayString
   MAX-ACCESS  read-only
   STATUS      current
   DESCRIPTION
       " The currently configured port transmit mode. "
   ::= { gs2310pplusLoopProtectionStatusEntry 3 }
   
gs2310pplusLoopProtectionStatusLoops OBJECT-TYPE
   SYNTAX      Integer32(0..1000000)
   MAX-ACCESS  read-only
   STATUS      current
   DESCRIPTION
       " The number of loops detected on this port. "
   ::= { gs2310pplusLoopProtectionStatusEntry 4 }
   
gs2310pplusLoopProtectionStatusStatus OBJECT-TYPE
   SYNTAX      DisplayString
   MAX-ACCESS  read-only
   STATUS      current
   DESCRIPTION
       " The current loop protection status of the port. "
   ::= { gs2310pplusLoopProtectionStatusEntry 5 }
   
gs2310pplusLoopProtectionStatusLoop OBJECT-TYPE
   SYNTAX      DisplayString
   MAX-ACCESS  read-only
   STATUS      current
   DESCRIPTION
       " Whether a loop is currently detected on the port. "
   ::= { gs2310pplusLoopProtectionStatusEntry 6 }

gs2310pplusLoopProtectionStatusTimeLastLoop OBJECT-TYPE
   SYNTAX      DisplayString
   MAX-ACCESS  read-only
   STATUS      current
   DESCRIPTION
       " The time of the last loop event detected. "
   ::= { gs2310pplusLoopProtectionStatusEntry 7 }

gs2310pplusPoe                                                           OBJECT IDENTIFIER ::= { gs2310pplusConfiguration 13 }

gs2310pplusPoeStatus                                            OBJECT IDENTIFIER ::= { gs2310pplusPoe 1 }

gs2310pplusPoeStatusTable OBJECT-TYPE
   SYNTAX      SEQUENCE OF GS2310PPLUSPoeStatusEntry
   MAX-ACCESS  not-accessible
   STATUS      current
   DESCRIPTION
       " Configure PoE Scheduling Table. "
   ::= { gs2310pplusPoeStatus 1 }

gs2310pplusPoeStatusEntry OBJECT-TYPE
   SYNTAX      GS2310PPLUSPoeStatusEntry
   MAX-ACCESS  not-accessible
   STATUS      current
   DESCRIPTION
       ""
   INDEX    { gs2310pplusPoeStatusLocalPort }
   ::= { gs2310pplusPoeStatusTable 1 }

GS2310PPLUSPoeStatusEntry ::= SEQUENCE {
   gs2310pplusPoeStatusLocalPort	        Integer32,
   gs2310pplusPoeStatusPDclass	        INTEGER,
   gs2310pplusPoeStatusPowerRequested	    DisplayString,
   gs2310pplusPoeStatusPowerAllocated     DisplayString,
   gs2310pplusPoeStatusPowerUsed          DisplayString,
   gs2310pplusPoeStatusCurrentUsed        DisplayString,
   gs2310pplusPoeStatusPriority           DisplayString,
   gs2310pplusPoeStatusPortStatus         DisplayString
}

gs2310pplusPoeStatusLocalPort OBJECT-TYPE
   SYNTAX      Integer32(1..4094)
   MAX-ACCESS  not-accessible
   STATUS      current
   DESCRIPTION
       " port, range : 1 - port number. "
   ::= { gs2310pplusPoeStatusEntry 1}

gs2310pplusPoeStatusPDclass OBJECT-TYPE
   SYNTAX      INTEGER (0..4)
   MAX-ACCESS  read-only
   STATUS      current
   DESCRIPTION
       " Indicates the QCL user.
         0: Max. power 15.4 W,
         1: Max. power 4.0 W,
         2: Max. power 7.0 W,
         3: Max. power 15.4 W,
         4: Max. power 30.0 W. "
   ::= { gs2310pplusPoeStatusEntry 2 }

gs2310pplusPoeStatusPowerRequested OBJECT-TYPE
   SYNTAX      DisplayString
   MAX-ACCESS  read-only
   STATUS      current
   DESCRIPTION
      " The Power Requested shows the requested amount of power the PD wants to be reserved. "
   ::= { gs2310pplusPoeStatusEntry 3}

gs2310pplusPoeStatusPowerAllocated OBJECT-TYPE
   SYNTAX      DisplayString
   MAX-ACCESS  read-only
   STATUS      current
   DESCRIPTION
      " The Power Allocated shows the amount of power the switch has allocated for the PD. "
   ::= { gs2310pplusPoeStatusEntry 4}

gs2310pplusPoeStatusPowerUsed OBJECT-TYPE
   SYNTAX      DisplayString
   MAX-ACCESS  read-only
   STATUS      current
   DESCRIPTION
      " The Power Used shows how much power the PD currently is using. "
   ::= { gs2310pplusPoeStatusEntry 5}

gs2310pplusPoeStatusCurrentUsed OBJECT-TYPE
   SYNTAX      DisplayString
   MAX-ACCESS  read-only
   STATUS      current
   DESCRIPTION
      " The Power Used shows how much current the PD currently is using. "
   ::= { gs2310pplusPoeStatusEntry 6}

gs2310pplusPoeStatusPriority OBJECT-TYPE
   SYNTAX      DisplayString
   MAX-ACCESS  read-only
   STATUS      current
   DESCRIPTION
      " The Priority shows the port's priority configured by the user.  "
   ::= { gs2310pplusPoeStatusEntry 7}

gs2310pplusPoeStatusPortStatus OBJECT-TYPE
   SYNTAX      DisplayString
   MAX-ACCESS  read-only
   STATUS      current
   DESCRIPTION
      " The Port Status shows the port's status.  "
   ::= { gs2310pplusPoeStatusEntry 8}


gs2310pplusPoeStatusTotalPowerRequested OBJECT-TYPE
   SYNTAX      DisplayString
   MAX-ACCESS  read-only
   STATUS      current
   DESCRIPTION
      " Total Power Requested."
   ::= { gs2310pplusPoeStatus 2}

gs2310pplusPoeStatusTotalPowerAllocated OBJECT-TYPE
   SYNTAX      DisplayString
   MAX-ACCESS  read-only
   STATUS      current
   DESCRIPTION
      " Total Power allocated."
   ::= { gs2310pplusPoeStatus 3}

gs2310pplusPoeStatusTotalPowerUsed OBJECT-TYPE
   SYNTAX      DisplayString
   MAX-ACCESS  read-only
   STATUS      current
   DESCRIPTION
      " Total Power Used."
   ::= { gs2310pplusPoeStatus 4}

gs2310pplusPoeStatusTotalCurrentUsed OBJECT-TYPE
   SYNTAX      DisplayString
   MAX-ACCESS  read-only
   STATUS      current
   DESCRIPTION
      " Total Current Used."
   ::= { gs2310pplusPoeStatus 5}

gs2310pplusPoeMcuVersion OBJECT-TYPE
   SYNTAX      DisplayString
   MAX-ACCESS  read-only
   STATUS      current
   DESCRIPTION
      " PoE MCU version."
   ::= { gs2310pplusPoeStatus 6 }

gs2310pplusPoePowerDelay                                                 OBJECT IDENTIFIER ::= { gs2310pplusPoe 2 }

gs2310pplusPoePowerDelayTable OBJECT-TYPE
   SYNTAX      SEQUENCE OF GS2310PPLUSPoePowerDelayEntry
   MAX-ACCESS  not-accessible
   STATUS      current
   DESCRIPTION
       " Configure PoE Power Delay mode. "
   ::= { gs2310pplusPoePowerDelay 1 }

gs2310pplusPoePowerDelayEntry OBJECT-TYPE
   SYNTAX      GS2310PPLUSPoePowerDelayEntry
   MAX-ACCESS  not-accessible
   STATUS      current
   DESCRIPTION
       ""
   INDEX    { gs2310pplusPoePowerDelayPort  }
   ::= { gs2310pplusPoePowerDelayTable 1 }

GS2310PPLUSPoePowerDelayEntry ::= SEQUENCE {
   gs2310pplusPoePowerDelayPort	        Integer32,
   gs2310pplusPoePowerDelayMode	        INTEGER,
   gs2310pplusPoePowerDelayTime         Integer32
}

gs2310pplusPoePowerDelayPort OBJECT-TYPE
   SYNTAX      Integer32(1..4094)
   MAX-ACCESS  not-accessible
   STATUS      current
   DESCRIPTION
       " port, range : 1 - port number. "
   ::= { gs2310pplusPoePowerDelayEntry 1 }

gs2310pplusPoePowerDelayMode OBJECT-TYPE
   SYNTAX      INTEGER { disable(0), enable(1) }
   MAX-ACCESS  read-write
   STATUS      current
   DESCRIPTION
       "Turn on / off the power delay function,
        0: disable,
        1: enable,
        default: disable. "
   ::= { gs2310pplusPoePowerDelayEntry 2 }
   
gs2310pplusPoePowerDelayTime OBJECT-TYPE
   SYNTAX      Integer32(0..300)
   MAX-ACCESS  read-write
   STATUS      current
   DESCRIPTION
       "set Delay Time,
        default: 0,
        range: 0-300 sec. "
   ::= { gs2310pplusPoePowerDelayEntry 3 }
   
gs2310pplusPoeAutoCheck                                                 OBJECT IDENTIFIER ::= { gs2310pplusPoe 3 }

gs2310pplusPoeAutoCheckPingCheck OBJECT-TYPE
   SYNTAX      INTEGER { disable(0), enable(1) }
   MAX-ACCESS  read-write
   STATUS      current
   DESCRIPTION
       "connection between PoE port and power device.
        0: disable,
        1: enable,
        default: disable. "
   ::= { gs2310pplusPoeAutoCheck 1 }

gs2310pplusPoeAutoCheckTable OBJECT-TYPE
   SYNTAX      SEQUENCE OF GS2310PPLUSPoeAutoCheckEntry
   MAX-ACCESS  not-accessible
   STATUS      current
   DESCRIPTION
       " Configure PoE Power Delay mode. "
   ::= { gs2310pplusPoeAutoCheck 2 }

gs2310pplusPoeAutoCheckEntry OBJECT-TYPE
   SYNTAX      GS2310PPLUSPoeAutoCheckEntry
   MAX-ACCESS  not-accessible
   STATUS      current
   DESCRIPTION
       ""
   INDEX    { gs2310pplusPoeAutoCheckPort  }
   ::= { gs2310pplusPoeAutoCheckTable 1 }

GS2310PPLUSPoeAutoCheckEntry ::= SEQUENCE {
   gs2310pplusPoeAutoCheckPort	       Integer32,
   gs2310pplusPoeAutoCheckPingIPAddress  DisplayString,
   gs2310pplusPoeAutoCheckIntervalTime   Integer32,
   gs2310pplusPoeAutoCheckRetryTime      Integer32,
   gs2310pplusPoeAutoCheckFailureLog     DisplayString,
   gs2310pplusPoeAutoCheckFailureAction  INTEGER,
   gs2310pplusPoeAutoCheckRebootTime     Integer32
}

gs2310pplusPoeAutoCheckPort OBJECT-TYPE
   SYNTAX      Integer32(1..4094)
   MAX-ACCESS  not-accessible
   STATUS      current
   DESCRIPTION
       " port, range : 1 - port number. "
   ::= { gs2310pplusPoeAutoCheckEntry 1 }

gs2310pplusPoeAutoCheckPingIPAddress OBJECT-TYPE
   SYNTAX      DisplayString
   MAX-ACCESS  read-write
   STATUS      current
   DESCRIPTION
       "IP Address the system should ping.
        default: 0.0.0.0 . "
   ::= { gs2310pplusPoeAutoCheckEntry 2 }

gs2310pplusPoeAutoCheckIntervalTime OBJECT-TYPE
   SYNTAX      Integer32(10..120)
   MAX-ACCESS  read-write
   STATUS      current
   DESCRIPTION
       "Device will send checking message to PD each interval time.
        default: 30,
        range: 10-120 sec.  "
   ::= { gs2310pplusPoeAutoCheckEntry 3 }

gs2310pplusPoeAutoCheckRetryTime OBJECT-TYPE
   SYNTAX      Integer32(1..5)
   MAX-ACCESS  read-write
   STATUS      current
   DESCRIPTION
       "It will retry to send detection again.
        default: 3,
        range: 1-5.  "
   ::= { gs2310pplusPoeAutoCheckEntry 4 }
   
gs2310pplusPoeAutoCheckFailureLog OBJECT-TYPE
   SYNTAX      DisplayString
   MAX-ACCESS  read-only
   STATUS      current
   DESCRIPTION
       "Failure loggings counter. "
   ::= { gs2310pplusPoeAutoCheckEntry 5 }
   
gs2310pplusPoeAutoCheckFailureAction OBJECT-TYPE
   SYNTAX      INTEGER { nothing(0), reboot(1) }
   MAX-ACCESS  read-write
   STATUS      current
   DESCRIPTION
       "It will retry to send detection again,
        0: Nothing,
        1: Reboot Remote PD,
        default: Nothing. "
   ::= { gs2310pplusPoeAutoCheckEntry 6 }
   
gs2310pplusPoeAutoCheckRebootTime OBJECT-TYPE
   SYNTAX      Integer32(3..120)
   MAX-ACCESS  read-write
   STATUS      current
   DESCRIPTION
       "When PD has been rebooted, the PoE port restored power after the specified time.
        default: 15,
        range: 3-120 sec. "
   ::= { gs2310pplusPoeAutoCheckEntry 7 }

gs2310pplusPoeScheduling                                                 OBJECT IDENTIFIER ::= { gs2310pplusPoe 4 }

gs2310pplusPoeSchedulingTable OBJECT-TYPE
   SYNTAX      SEQUENCE OF GS2310PPLUSPoeSchedulingEntry
   MAX-ACCESS  not-accessible
   STATUS      current
   DESCRIPTION
       " Configure PoE Scheduling Table. "
   ::= { gs2310pplusPoeScheduling 1 }

gs2310pplusPoeSchedulingEntry OBJECT-TYPE
   SYNTAX      GS2310PPLUSPoeSchedulingEntry
   MAX-ACCESS  not-accessible
   STATUS      current
   DESCRIPTION
       ""
   INDEX    { gs2310pplusPoeSchedulingPort }
   ::= { gs2310pplusPoeSchedulingTable 1 }

GS2310PPLUSPoeSchedulingEntry ::= SEQUENCE {
   gs2310pplusPoeSchedulingPort	        Integer32,
   gs2310pplusPoeSchedulingStatus	        INTEGER
}

gs2310pplusPoeSchedulingPort OBJECT-TYPE
   SYNTAX      Integer32(1..4094)
   MAX-ACCESS  not-accessible
   STATUS      current
   DESCRIPTION
       " port, range : 1 - port number. "
   ::= { gs2310pplusPoeSchedulingEntry 1 }

gs2310pplusPoeSchedulingStatus OBJECT-TYPE
   SYNTAX      INTEGER { disable(0), enable(1) }
   MAX-ACCESS  read-write
   STATUS      current
   DESCRIPTION
       "PoE Scheduling Status.
        0: Disable,
        1: Enable,
        default: Disable. "
   ::= { gs2310pplusPoeSchedulingEntry 2 }

gs2310pplusPoeSchedulingTimeTable OBJECT-TYPE
   SYNTAX      SEQUENCE OF GS2310PPLUSPoeSchedulingTimeEntry
   MAX-ACCESS  not-accessible
   STATUS      current
   DESCRIPTION
       " Show Poe Scheduling Time Config. "
   ::= { gs2310pplusPoeScheduling 2 }

gs2310pplusPoeSchedulingTimeEntry OBJECT-TYPE
   SYNTAX      GS2310PPLUSPoeSchedulingTimeEntry
   MAX-ACCESS  not-accessible
   STATUS      current
   DESCRIPTION
       ""
   INDEX    { gs2310pplusPoeSchedulingTimePort, gs2310pplusPoeSchedulingTimeWeek, gs2310pplusPoeSchedulingTimeHour  }
   ::= { gs2310pplusPoeSchedulingTimeTable 1 }

GS2310PPLUSPoeSchedulingTimeEntry ::= SEQUENCE {
   gs2310pplusPoeSchedulingTimePort		Integer32,
   gs2310pplusPoeSchedulingTimeWeek		INTEGER,
   gs2310pplusPoeSchedulingTimeHour		Integer32,
   gs2310pplusPoeSchedulingProvidePower	INTEGER
}

gs2310pplusPoeSchedulingTimePort OBJECT-TYPE
   SYNTAX      Integer32(1..4095)
   MAX-ACCESS  not-accessible
   STATUS      current
   DESCRIPTION
       " port, range : 1 - port number. "
   ::= { gs2310pplusPoeSchedulingTimeEntry 1 }

gs2310pplusPoeSchedulingTimeWeek OBJECT-TYPE
   SYNTAX      INTEGER {
                        monday(1),
                        tuseday(2),
                        wednesday(3),
                        thursday(4),
                        friday(5),
                        saturday(6),
                        sunday(7)
                        }
   MAX-ACCESS  not-accessible
   STATUS      current
   DESCRIPTION
       " range: 1-7, 
         Sunday:7, Monday:1, Tuseday:2, Wednesday:3, Thursday:4, Friday:5, Saturday:6.  "
   ::= { gs2310pplusPoeSchedulingTimeEntry 2 }

gs2310pplusPoeSchedulingTimeHour OBJECT-TYPE
   SYNTAX      Integer32(1..24)
   MAX-ACCESS  not-accessible
   STATUS      current
   DESCRIPTION
       " range: 1-24,
         24: hour 0, 1: hour 1, 2: hour2..."
   ::= { gs2310pplusPoeSchedulingTimeEntry 3 }

gs2310pplusPoeSchedulingProvidePower OBJECT-TYPE
   SYNTAX      INTEGER { disable(0), enable(1) }
   MAX-ACCESS  read-write
   STATUS      current
   DESCRIPTION
       " 0: disable,
         1: enable,
         default: disable.  "
   ::= { gs2310pplusPoeSchedulingTimeEntry 4 }

gs2310pplusPoeConfiguration                                                 OBJECT IDENTIFIER ::= { gs2310pplusPoe 5 }

gs2310pplusPoeConfigurationPrimaryPowerSupply  OBJECT-TYPE
   SYNTAX      Integer32(0..1000)
   MAX-ACCESS  read-only
   STATUS      current
   DESCRIPTION
       "It must be defined what amount of power the primary and backup power sources
        can deliver. "
   ::= { gs2310pplusPoeConfiguration 1 }

gs2310pplusPoeConfigurationRetryTime OBJECT-TYPE
   SYNTAX      Integer32(0|5|10|20|30|40|50|60)
   MAX-ACCESS  read-write
   STATUS      current
   DESCRIPTION
       "The period (in seconds) for trying to turn on an overloaded PoE port.
        0: disable,
        5 sec,10 sec,20 sec,30 sec,40 sec,50 sec,60 sec,
        default: 60 sec. "
   ::= { gs2310pplusPoeConfiguration 2 }

gs2310pplusPoeConfigurationTable OBJECT-TYPE
   SYNTAX      SEQUENCE OF GS2310PPLUSPoeConfigurationEntry
   MAX-ACCESS  not-accessible
   STATUS      current
   DESCRIPTION
       " Configure PoE Configuration mode. "
   ::= { gs2310pplusPoeConfiguration 3 }

gs2310pplusPoeConfigurationEntry OBJECT-TYPE
   SYNTAX      GS2310PPLUSPoeConfigurationEntry
   MAX-ACCESS  not-accessible
   STATUS      current
   DESCRIPTION
       ""
   INDEX    { gs2310pplusPoeConfigurationPort  }
   ::= { gs2310pplusPoeConfigurationTable 1 }

GS2310PPLUSPoeConfigurationEntry ::= SEQUENCE {
   gs2310pplusPoeConfigurationPort	       Integer32,
   gs2310pplusPoeConfigurationPoEMode       INTEGER,
   gs2310pplusPoeConfigurationPriority      INTEGER,
   gs2310pplusPoeConfigurationMaximumPower  DisplayString,
   gs2310pplusPoeConfigurationDetection     INTEGER,
   gs2310pplusPoeConfigurationReset         INTEGER
}

gs2310pplusPoeConfigurationPort OBJECT-TYPE
   SYNTAX      Integer32(1..4094)
   MAX-ACCESS  not-accessible
   STATUS      current
   DESCRIPTION
       " port, range : 1 - port number. "
   ::= { gs2310pplusPoeConfigurationEntry 1 }

gs2310pplusPoeConfigurationPoEMode OBJECT-TYPE
   SYNTAX      INTEGER { disable(0), enable(1) }
   MAX-ACCESS  read-write
   STATUS      current
   DESCRIPTION
       "The PoE Mode represents the PoE operating mode for the port.
        0: Disable,
        1: Enable,
        default: Enable. "
   ::= { gs2310pplusPoeConfigurationEntry 2 }

gs2310pplusPoeConfigurationPriority OBJECT-TYPE
   SYNTAX      INTEGER { low(0), high(1), critical(2) }
   MAX-ACCESS  read-write
   STATUS      current
   DESCRIPTION
       "The Priority represents the ports priority. There are three levels of power priority named Low, High and Critical.
        0: Low,
        1: High,
        2: Critical,
        default: Low.  "
   ::= { gs2310pplusPoeConfigurationEntry 3 }

gs2310pplusPoeConfigurationMaximumPower OBJECT-TYPE
   SYNTAX      DisplayString
   MAX-ACCESS  read-write
   STATUS      current
   DESCRIPTION
       "The Maximum Power value contains a numerical value that indicates the maximum
        power in watts that can be delivered to a remote device.
        default: 15.4[W],
        max: 30[W]. "
   ::= { gs2310pplusPoeConfigurationEntry 4 }

gs2310pplusPoeConfigurationDetection OBJECT-TYPE
   SYNTAX      INTEGER(0..5)
   MAX-ACCESS  read-write
   STATUS      current
   DESCRIPTION
       "Configure PoE port capacitor detection.
        0: No Detection(read only),
        1: legacy,
        2: 4-point,
        3: 4-point-legacy,
        4: 2-point,
        5: 2-point-legacy, 
        default: 4-point. "
   ::= { gs2310pplusPoeConfigurationEntry 5 }

gs2310pplusPoeConfigurationReset OBJECT-TYPE
   SYNTAX      INTEGER { disable(0), enable(1) }
   MAX-ACCESS  read-write
   STATUS      current
   DESCRIPTION
       "Reset the specific PoE port.
        0: Disable,
        1: Enable,
        default: Disable. "
   ::= { gs2310pplusPoeConfigurationEntry 6 }

gs2310pplusPoeConfigurationLegacyMode  OBJECT-TYPE
   SYNTAX      INTEGER { disable(0), enable(1) }
   MAX-ACCESS  read-write
   STATUS      current
   DESCRIPTION
       "Legacy Detection.
        0: Disable,
        1: Enable,
        default: Disable. "
   ::= { gs2310pplusPoeConfiguration 4 }  


gs2310pplusQos                                                             OBJECT IDENTIFIER ::= { gs2310pplusConfiguration 14 }

gs2310pplusQosPortClassification                                           OBJECT IDENTIFIER ::= { gs2310pplusQos 1 }

gs2310pplusQosPortClassificationTable OBJECT-TYPE
   SYNTAX      SEQUENCE OF GS2310PPLUSQosPortClassificationEntry
   MAX-ACCESS  not-accessible
   STATUS      current
   DESCRIPTION
       " QoS Ingress Port Classification . "
   ::= { gs2310pplusQosPortClassification  1 }

gs2310pplusQosPortClassificationEntry OBJECT-TYPE
   SYNTAX      GS2310PPLUSQosPortClassificationEntry
   MAX-ACCESS  not-accessible
   STATUS      current
   DESCRIPTION
       ""
   INDEX    { gs2310pplusQosPortClassificationPort  }
   ::= { gs2310pplusQosPortClassificationTable 1 }

GS2310PPLUSQosPortClassificationEntry ::= SEQUENCE {
   gs2310pplusQosPortClassificationPort	        Integer32,
   gs2310pplusQosPortClassificationQoSclass       Integer32,
   gs2310pplusQosPortClassificationDPlevel	    Integer32,
   gs2310pplusQosPortClassificationPCP	        Integer32,
   gs2310pplusQosPortClassificationDEI	        INTEGER,
   gs2310pplusQosPortClassificationTagClass	    INTEGER,
   gs2310pplusQosPortClassificationDSCPBased    INTEGER,
   gs2310pplusQosPortClassificationAddressMode  INTEGER
}

gs2310pplusQosPortClassificationPort OBJECT-TYPE
   SYNTAX      Integer32(1..4095)
   MAX-ACCESS  not-accessible
   STATUS      current
   DESCRIPTION
       " port, range : 1 - port number. "
   ::= { gs2310pplusQosPortClassificationEntry 1 }

gs2310pplusQosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2310pplusQosPortClassificationEntry 2 }

gs2310pplusQosPortClassificationDPlevel OBJECT-TYPE
   SYNTAX      Integer32(0|1)
   MAX-ACCESS  read-write
   STATUS      current
   DESCRIPTION
       " DP level for frames not classified in any other way.
         range: 0-1,
         default: 0. "
   ::= { gs2310pplusQosPortClassificationEntry 3 }

gs2310pplusQosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2310pplusQosPortClassificationEntry 4 }

gs2310pplusQosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2310pplusQosPortClassificationEntry 5 }

gs2310pplusQosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2310pplusQosPortClassificationEntry 6 }

gs2310pplusQosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2310pplusQosPortClassificationEntry 7 }

gs2310pplusQosPortClassificationAddressMode OBJECT-TYPE
   SYNTAX      INTEGER { source(0), destination(1) }
   MAX-ACCESS  read-write
   STATUS      current
   DESCRIPTION
      "The IP/MAC address mode specifying whether the QCL classification
       must be based on source (SMAC/SIP) or destination (DMAC/DIP)
       addresses on this port.
        0: source,
        1: destination,
        default: source. "
   ::= { gs2310pplusQosPortClassificationEntry 8 }

gs2310pplusQoSIngressPortTagClassificationTable OBJECT-TYPE
   SYNTAX      SEQUENCE OF GS2310PPLUSQoSIngressPortTagClassificationEntry
   MAX-ACCESS  not-accessible
   STATUS      current
   DESCRIPTION
       " Show QoS Ingress Port Tag Classification. "
   ::= { gs2310pplusQosPortClassification 2 }

gs2310pplusQoSIngressPortTagClassificationEntry OBJECT-TYPE
   SYNTAX      GS2310PPLUSQoSIngressPortTagClassificationEntry
   MAX-ACCESS  not-accessible
   STATUS      current
   DESCRIPTION
       ""
   INDEX    { gs2310pplusQoSIngressPortTagClassificationPort, gs2310pplusQoSIngressPortTagPCP, gs2310pplusQoSIngressPortTagDEI  }
   ::= { gs2310pplusQoSIngressPortTagClassificationTable 1 }

GS2310PPLUSQoSIngressPortTagClassificationEntry ::= SEQUENCE {
   gs2310pplusQoSIngressPortTagClassificationPort	Integer32,
   gs2310pplusQoSIngressPortTagPCP					INTEGER,
   gs2310pplusQoSIngressPortTagDEI					INTEGER,
   gs2310pplusQoSIngressPortTagQosClass				Integer32,
   gs2310pplusQoSIngressPortTagDPLevel				Integer32
}

gs2310pplusQoSIngressPortTagClassificationPort OBJECT-TYPE
   SYNTAX      Integer32(1..4095)
   MAX-ACCESS  not-accessible
   STATUS      current
   DESCRIPTION
       " port, range : 1 - port number. "
   ::= { gs2310pplusQoSIngressPortTagClassificationEntry 1 }

gs2310pplusQoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8, 
         PCP0:1, PCP1:2...  "
   ::= { gs2310pplusQoSIngressPortTagClassificationEntry 2 }

gs2310pplusQoSIngressPortTagDEI OBJECT-TYPE
   SYNTAX      INTEGER { dei0(1), dei1(2) }
   MAX-ACCESS  not-accessible
   STATUS      current
   DESCRIPTION
       " range: 1-2,
         DEI0:1, DEI1:2. "
   ::= { gs2310pplusQoSIngressPortTagClassificationEntry 3 }

gs2310pplusQoSIngressPortTagQosClass OBJECT-TYPE
   SYNTAX      Integer32 (0..7)
   MAX-ACCESS  read-write
   STATUS      current
   DESCRIPTION
       " range: 0-7.  "
   ::= { gs2310pplusQoSIngressPortTagClassificationEntry 4 }
   
gs2310pplusQoSIngressPortTagDPLevel OBJECT-TYPE
   SYNTAX      Integer32 (0|1)
   MAX-ACCESS  read-write
   STATUS      current
   DESCRIPTION
       " range: 0-1.  "
   ::= { gs2310pplusQoSIngressPortTagClassificationEntry 5 }


gs2310pplusQosPortPolicingTable OBJECT-TYPE
   SYNTAX      SEQUENCE OF GS2310PPLUSQosPortPolicingEntry
   MAX-ACCESS  not-accessible
   STATUS      current
   DESCRIPTION
       "  configure the Policer settings for all switch ports. "
   ::= { gs2310pplusQos  2 }

gs2310pplusQosPortPolicingEntry OBJECT-TYPE
   SYNTAX      GS2310PPLUSQosPortPolicingEntry
   MAX-ACCESS  not-accessible
   STATUS      current
   DESCRIPTION
       ""
   INDEX    { gs2310pplusQosPortPolicingPort  }
   ::= { gs2310pplusQosPortPolicingTable 1 }

GS2310PPLUSQosPortPolicingEntry ::= SEQUENCE {
   gs2310pplusQosPortPolicingPort	        Integer32,
   gs2310pplusQosPortPolicingMode           INTEGER,
   gs2310pplusQosPortPolicingRate	        Integer32,
   gs2310pplusQosPortPolicingUnit	        INTEGER,
   gs2310pplusQosPortPolicingFlowControl	INTEGER
}

gs2310pplusQosPortPolicingPort OBJECT-TYPE
   SYNTAX      Integer32 (1..4095)
   MAX-ACCESS  not-accessible
   STATUS      current
   DESCRIPTION
       " port, range : 1 - port number. "
   ::= { gs2310pplusQosPortPolicingEntry 1 }

gs2310pplusQosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2310pplusQosPortPolicingEntry 2 }

gs2310pplusQosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2310pplusQosPortPolicingEntry 3 }

gs2310pplusQosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2310pplusQosPortPolicingEntry 4 }

gs2310pplusQosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2310pplusQosPortPolicingEntry 5 }

gs2310pplusQosPortScheduler                                           OBJECT IDENTIFIER ::= { gs2310pplusQos 3 }

gs2310pplusQosPortSchedulerModeTable OBJECT-TYPE
   SYNTAX      SEQUENCE OF GS2310PPLUSQosPortSchedulerModeEntry
   MAX-ACCESS  not-accessible
   STATUS      current
   DESCRIPTION
       " configure the basic QoS Port Scheduler Mode settings for all switch ports. "
   ::= { gs2310pplusQosPortScheduler  1 }

gs2310pplusQosPortSchedulerModeEntry OBJECT-TYPE
   SYNTAX      GS2310PPLUSQosPortSchedulerModeEntry
   MAX-ACCESS  not-accessible
   STATUS      current
   DESCRIPTION
       ""
   INDEX    { gs2310pplusQosSchedulerModePort  }
   ::= { gs2310pplusQosPortSchedulerModeTable 1 }

GS2310PPLUSQosPortSchedulerModeEntry ::= SEQUENCE {
   gs2310pplusQosSchedulerModePort	                Integer32,
   gs2310pplusQosSchedulerMode                        INTEGER,
   gs2310pplusQosSchedulerShaper	                    INTEGER,
   gs2310pplusQosSchedulerShaperRate	                Integer32
}

gs2310pplusQosSchedulerModePort OBJECT-TYPE
   SYNTAX      Integer32 (1..4095)
   MAX-ACCESS  not-accessible
   STATUS      current
   DESCRIPTION
       " port, range : 1 - port number. "
   ::= { gs2310pplusQosPortSchedulerModeEntry 1 }

gs2310pplusQosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2310pplusQosPortSchedulerModeEntry 2 }

gs2310pplusQosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2310pplusQosPortSchedulerModeEntry 3 }

gs2310pplusQosSchedulerShaperRate OBJECT-TYPE
   SYNTAX      Integer32(100..1000000)
   MAX-ACCESS  read-write
   STATUS      current
   DESCRIPTION
       " Controls the rate for the port shaper.
         range: 100-1000000
         default: 500 kbps. "
   ::= { gs2310pplusQosPortSchedulerModeEntry 4 }

gs2310pplusQosPortSchedulerTable OBJECT-TYPE
   SYNTAX      SEQUENCE OF GS2310PPLUSQosPortSchedulerEntry
   MAX-ACCESS  not-accessible
   STATUS      current
   DESCRIPTION
       " Show Qos Port Scheduler. "
   ::= { gs2310pplusQosPortScheduler 2 }

gs2310pplusQosPortSchedulerEntry OBJECT-TYPE
   SYNTAX      GS2310PPLUSQosPortSchedulerEntry
   MAX-ACCESS  not-accessible
   STATUS      current
   DESCRIPTION
       ""
   INDEX    { gs2310pplusQosSchedulerPort, gs2310pplusQosSchedulerPortQueue}
   ::= { gs2310pplusQosPortSchedulerTable 1 }

GS2310PPLUSQosPortSchedulerEntry ::= SEQUENCE {
   gs2310pplusQosSchedulerPort						Integer32,
   gs2310pplusQosSchedulerPortQueue					INTEGER,
   gs2310pplusQosSchedulerPortQueueShaper				INTEGER,
   gs2310pplusQosSchedulerPortQueueShaperRate			Integer32,
   gs2310pplusQosSchedulerPortQueueShaperExcess		INTEGER,
   gs2310pplusQosSchedulerPortQueueSchedulerWeight	Integer32,
   gs2310pplusQosSchedulerPortQueueSchedulerPercent	DisplayString
}

gs2310pplusQosSchedulerPort OBJECT-TYPE
   SYNTAX      Integer32 (1..4095)
   MAX-ACCESS  not-accessible
   STATUS      current
   DESCRIPTION
       " port, range : 1 - port number. "
   ::= { gs2310pplusQosPortSchedulerEntry 1 }

gs2310pplusQosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2310pplusQosPortSchedulerEntry 2 }
   
gs2310pplusQosSchedulerPortQueueShaper OBJECT-TYPE
   SYNTAX      INTEGER { disable(0), enable(1) }
   MAX-ACCESS  read-write
   STATUS      current
   DESCRIPTION
       " 0: disable  1:enable,
         default: 0.  "
   ::= { gs2310pplusQosPortSchedulerEntry 3 }
   
gs2310pplusQosSchedulerPortQueueShaperRate OBJECT-TYPE
   SYNTAX      Integer32(100..1000000)
   MAX-ACCESS  read-write
   STATUS      current
   DESCRIPTION
       " range: 100..1000000 kbps.  "
   ::= { gs2310pplusQosPortSchedulerEntry 4 }
   
gs2310pplusQosSchedulerPortQueueShaperExcess OBJECT-TYPE
   SYNTAX      INTEGER { disable(0), enable(1) }
   MAX-ACCESS  read-write
   STATUS      current
   DESCRIPTION
       " 0: disable  1:enable,
         default: 0.  "
   ::= { gs2310pplusQosPortSchedulerEntry 5 }
   
gs2310pplusQosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2310pplusQosPortSchedulerEntry 6 }
   
gs2310pplusQosSchedulerPortQueueSchedulerPercent OBJECT-TYPE
   SYNTAX      DisplayString
   MAX-ACCESS  read-only
   STATUS      current
   DESCRIPTION
       " Only use in Q0 - Q5. Q6 & Q7 show empty "
   ::= { gs2310pplusQosPortSchedulerEntry 7 }

gs2310pplusQosPortEgressTagRemarking                                           OBJECT IDENTIFIER ::= { gs2310pplusQos 4 }

gs2310pplusQosPortEgressTagRemarkingTable OBJECT-TYPE
   SYNTAX      SEQUENCE OF GS2310PPLUSQosPortEgressTagRemarkingEntry
   MAX-ACCESS  not-accessible
   STATUS      current
   DESCRIPTION
       " configure the basic QoS Port Egress Tag Remark Configuration settings for all switch ports. "
   ::= { gs2310pplusQosPortEgressTagRemarking  1 }

gs2310pplusQosPortEgressTagRemarkingEntry OBJECT-TYPE
   SYNTAX      GS2310PPLUSQosPortEgressTagRemarkingEntry
   MAX-ACCESS  not-accessible
   STATUS      current
   DESCRIPTION
       ""
   INDEX    { gs2310pplusQosEgressTagRemarkingPort  }
   ::= { gs2310pplusQosPortEgressTagRemarkingTable 1 }

GS2310PPLUSQosPortEgressTagRemarkingEntry ::= SEQUENCE {
   gs2310pplusQosEgressTagRemarkingPort	                Integer32,
   gs2310pplusQosEgressTagRemarkingMode	                INTEGER
}

gs2310pplusQosEgressTagRemarkingPort OBJECT-TYPE
   SYNTAX      Integer32 (1..4095)
   MAX-ACCESS  not-accessible
   STATUS      current
   DESCRIPTION
       " port, range : 1 - port number. "
   ::= { gs2310pplusQosPortEgressTagRemarkingEntry 1 }

gs2310pplusQosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2310pplusQosPortEgressTagRemarkingEntry 2 }


gs2310pplusQosPortEgressTagRemarkingDefTable OBJECT-TYPE
   SYNTAX      SEQUENCE OF GS2310PPLUSQosPortEgressTagRemarkingDefEntry
   MAX-ACCESS  not-accessible
   STATUS      current
   DESCRIPTION
       " configure the basic QoS Port Egress Tag Remark Configuration settings for all switch ports. "
   ::= { gs2310pplusQosPortEgressTagRemarking  2 }

gs2310pplusQosPortEgressTagRemarkingDefEntry OBJECT-TYPE
   SYNTAX      GS2310PPLUSQosPortEgressTagRemarkingDefEntry
   MAX-ACCESS  not-accessible
   STATUS      current
   DESCRIPTION
       ""
   INDEX    { gs2310pplusQosEgressTagRemarkingDefPort  }
   ::= { gs2310pplusQosPortEgressTagRemarkingDefTable 1 }

GS2310PPLUSQosPortEgressTagRemarkingDefEntry ::= SEQUENCE {
   gs2310pplusQosEgressTagRemarkingDefPort	            Integer32,
   gs2310pplusQosEgressTagRemarkingDefPCP	                Integer32,
   gs2310pplusQosEgressTagRemarkingDefDEI	                INTEGER
}

gs2310pplusQosEgressTagRemarkingDefPort OBJECT-TYPE
   SYNTAX      Integer32(1..4095)
   MAX-ACCESS  not-accessible
   STATUS      current
   DESCRIPTION
       " port, range : 1 - port number. "
   ::= { gs2310pplusQosPortEgressTagRemarkingDefEntry 1 }

gs2310pplusQosEgressTagRemarkingDefPCP OBJECT-TYPE
   SYNTAX      Integer32(0..7)
   MAX-ACCESS  read-write
   STATUS      current
   DESCRIPTION
       " Controls the default PCP
       Range : 0-7"
   ::= { gs2310pplusQosPortEgressTagRemarkingDefEntry 2 }

gs2310pplusQosEgressTagRemarkingDefDEI OBJECT-TYPE
   SYNTAX      INTEGER { disable(0), enable(1) }
   MAX-ACCESS  read-write
   STATUS      current
   DESCRIPTION
       " controls the DEI
       Range 0-1"
   ::= { gs2310pplusQosPortEgressTagRemarkingDefEntry 3 }

gs2310pplusQosPortEgressTagRemarkingMapTable OBJECT-TYPE
   SYNTAX      SEQUENCE OF GS2310PPLUSQosPortEgressTagRemarkingMapEntry
   MAX-ACCESS  not-accessible
   STATUS      current
   DESCRIPTION
       " Show Qos Port Egress Tag Remarking Map. "
   ::= { gs2310pplusQosPortEgressTagRemarking 4 }

gs2310pplusQosPortEgressTagRemarkingMapEntry OBJECT-TYPE
   SYNTAX      GS2310PPLUSQosPortEgressTagRemarkingMapEntry
   MAX-ACCESS  not-accessible
   STATUS      current
   DESCRIPTION
       ""
   INDEX    { gs2310pplusQosPortEgressTagRemarkingMapPort, gs2310pplusQosTagRemarkingQoSClass, gs2310pplusQosTagRemarkingDPLevel  }
   ::= { gs2310pplusQosPortEgressTagRemarkingMapTable 1 }

GS2310PPLUSQosPortEgressTagRemarkingMapEntry ::= SEQUENCE {
   gs2310pplusQosPortEgressTagRemarkingMapPort	Integer32,
   gs2310pplusQosTagRemarkingQoSClass			INTEGER,
   gs2310pplusQosTagRemarkingDPLevel				INTEGER,
   gs2310pplusQosTagRemarkingPCP					Integer32,
   gs2310pplusQosTagRemarkingDEI					INTEGER
}

gs2310pplusQosPortEgressTagRemarkingMapPort OBJECT-TYPE
   SYNTAX      Integer32 (1..4095)
   MAX-ACCESS  not-accessible
   STATUS      current
   DESCRIPTION
       " port, range : 1 - port number. "
   ::= { gs2310pplusQosPortEgressTagRemarkingMapEntry 1 }

gs2310pplusQosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8, 
         QoS Class0: 1, QoS Class1: 2...  "
   ::= { gs2310pplusQosPortEgressTagRemarkingMapEntry 2 }

gs2310pplusQosTagRemarkingDPLevel OBJECT-TYPE
   SYNTAX      INTEGER { level0(1), level1(2) }
   MAX-ACCESS  not-accessible
   STATUS      current
   DESCRIPTION
       " range: 1-2,
         DP Level0: 1, DP Level1: 2. "
   ::= { gs2310pplusQosPortEgressTagRemarkingMapEntry 3 }

gs2310pplusQosTagRemarkingPCP OBJECT-TYPE
   SYNTAX      Integer32 (0..7)
   MAX-ACCESS  read-write
   STATUS      current
   DESCRIPTION
       " range: 0-7.  "
   ::= { gs2310pplusQosPortEgressTagRemarkingMapEntry 4 }
   
gs2310pplusQosTagRemarkingDEI OBJECT-TYPE
   SYNTAX      INTEGER (0|1)
   MAX-ACCESS  read-write
   STATUS      current
   DESCRIPTION
       " range: 0-1.  "
   ::= { gs2310pplusQosPortEgressTagRemarkingMapEntry 5 }


gs2310pplusQosPortDSCPTable OBJECT-TYPE
   SYNTAX      SEQUENCE OF GS2310PPLUSQosPortDSCPEntry
   MAX-ACCESS  not-accessible
   STATUS      current
   DESCRIPTION
       " configure the basic QoS Port DSCP Configuration settings for all switch ports. "
   ::= { gs2310pplusQos  5 }

gs2310pplusQosPortDSCPEntry OBJECT-TYPE
   SYNTAX      GS2310PPLUSQosPortDSCPEntry
   MAX-ACCESS  not-accessible
   STATUS      current
   DESCRIPTION
       ""
   INDEX    { gs2310pplusQosPortDSCPPort  }
   ::= { gs2310pplusQosPortDSCPTable 1 }

GS2310PPLUSQosPortDSCPEntry ::= SEQUENCE {
   gs2310pplusQosPortDSCPPort	                Integer32,
   gs2310pplusQosPortDSCPIngressTranslate       INTEGER,
   gs2310pplusQosPortDSCPIngressClassify	    INTEGER,
   gs2310pplusQosPortDSCPEgressRewrite	        INTEGER
}

gs2310pplusQosPortDSCPPort OBJECT-TYPE
   SYNTAX      Integer32 (1..4095)
   MAX-ACCESS  not-accessible
   STATUS      current
   DESCRIPTION
       " port, range : 1 - port number. "
   ::= { gs2310pplusQosPortDSCPEntry 1 }

gs2310pplusQosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2310pplusQosPortDSCPEntry 2 }

gs2310pplusQosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2310pplusQosPortDSCPEntry 3 }

gs2310pplusQosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { gs2310pplusQosPortDSCPEntry 4 }


gs2310pplusQosDSCPTable OBJECT-TYPE
   SYNTAX      SEQUENCE OF GS2310PPLUSQosDSCPEntry
   MAX-ACCESS  not-accessible
   STATUS      current
   DESCRIPTION
       " configure the basic QoS DSCP based QoS Ingress Classification settings for all switches. "
   ::= { gs2310pplusQos  6 }

gs2310pplusQosDSCPEntry OBJECT-TYPE
   SYNTAX      GS2310PPLUSQosDSCPEntry
   MAX-ACCESS  not-accessible
   STATUS      current
   DESCRIPTION
       ""
   INDEX    { gs2310pplusQosDSCPList  }
   ::= { gs2310pplusQosDSCPTable 1 }

GS2310PPLUSQosDSCPEntry ::= SEQUENCE {
   gs2310pplusQosDSCPList       Integer32,
   gs2310pplusQosDSCP           DisplayString,
   gs2310pplusQosDSCPTrust      INTEGER,
   gs2310pplusQosDSCPQosClass	  Integer32,
   gs2310pplusQosDSCPDPL	      INTEGER
}

gs2310pplusQosDSCPList OBJECT-TYPE
   SYNTAX      Integer32(1..64)
   MAX-ACCESS  not-accessible
   STATUS      current
   DESCRIPTION
      " DSCP mapping table index(1-64). "
   ::= { gs2310pplusQosDSCPEntry 1 }

gs2310pplusQosDSCP OBJECT-TYPE
   SYNTAX      DisplayString
   MAX-ACCESS  read-only
   STATUS      current
   DESCRIPTION
      "Maximum number of supported DSCP values are 64."
   ::= { gs2310pplusQosDSCPEntry 2 }

gs2310pplusQosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2310pplusQosDSCPEntry 3 }

gs2310pplusQosDSCPQosClass OBJECT-TYPE
   SYNTAX      Integer32(0..7)
   MAX-ACCESS  read-write
   STATUS      current
   DESCRIPTION
      " QoS class.
        range: 0-7,
        default: 0. "
   ::= { gs2310pplusQosDSCPEntry 4 }

gs2310pplusQosDSCPDPL OBJECT-TYPE
   SYNTAX      INTEGER(0|1)
   MAX-ACCESS  read-write
   STATUS      current
   DESCRIPTION
      " Drop Precedence Level.
        range: 0-1,
        default: disable. "
   ::= { gs2310pplusQosDSCPEntry 5 }

gs2310pplusQosDSCPTranslationTable OBJECT-TYPE
   SYNTAX      SEQUENCE OF GS2310PPLUSQosDSCPTranslationEntry
   MAX-ACCESS  not-accessible
   STATUS      current
   DESCRIPTION
       "  configure the basic QoS DSCP Translation settings for all switches. "
   ::= { gs2310pplusQos  7 }

gs2310pplusQosDSCPTranslationEntry OBJECT-TYPE
   SYNTAX      GS2310PPLUSQosDSCPTranslationEntry
   MAX-ACCESS  not-accessible
   STATUS      current
   DESCRIPTION
       ""
   INDEX    { gs2310pplusQosDSCPTranslationList  }
   ::= { gs2310pplusQosDSCPTranslationTable 1 }

GS2310PPLUSQosDSCPTranslationEntry ::= SEQUENCE {
   gs2310pplusQosDSCPTranslationList                 Integer32,
   gs2310pplusQosDSCPTranslationDSCPBasedId          DisplayString,
   gs2310pplusQosDSCPTranslationIngressTranslate     Integer32,
   gs2310pplusQosDSCPTranslationIngressClassify      INTEGER,
   gs2310pplusQosDSCPTranslationEgressRemapDP0       Integer32,
   gs2310pplusQosDSCPTranslationEgressRemapDP1       Integer32
}

gs2310pplusQosDSCPTranslationList OBJECT-TYPE
   SYNTAX      Integer32(1..64)
   MAX-ACCESS  not-accessible
   STATUS      current
   DESCRIPTION
      " DSCP translation table index(1-64). "
   ::= { gs2310pplusQosDSCPTranslationEntry 1 }

gs2310pplusQosDSCPTranslationDSCPBasedId OBJECT-TYPE
   SYNTAX      DisplayString
   MAX-ACCESS  read-write
   STATUS      current
   DESCRIPTION
      " Configure global ingress DSCP translation table. "
   ::= { gs2310pplusQosDSCPTranslationEntry 2 }

gs2310pplusQosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2310pplusQosDSCPTranslationEntry 3 }

gs2310pplusQosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2310pplusQosDSCPTranslationEntry 4 }

gs2310pplusQosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { gs2310pplusQosDSCPTranslationEntry 5 }

gs2310pplusQosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { gs2310pplusQosDSCPTranslationEntry 6 }


gs2310pplusQosDSCPClassificationTable OBJECT-TYPE
   SYNTAX      SEQUENCE OF GS2310PPLUSQosDSCPClassificationEntry
   MAX-ACCESS  not-accessible
   STATUS      current
   DESCRIPTION
       "   configure the mapping of QoS class  to DSCP value. "
   ::= { gs2310pplusQos  8 }

gs2310pplusQosDSCPClassificationEntry OBJECT-TYPE
   SYNTAX      GS2310PPLUSQosDSCPClassificationEntry
   MAX-ACCESS  not-accessible
   STATUS      current
   DESCRIPTION
       ""
   INDEX    { gs2310pplusQosDSCPClassificationQoSClass, gs2310pplusQosDSCPClassificationDPL }
   ::= { gs2310pplusQosDSCPClassificationTable 1 }

GS2310PPLUSQosDSCPClassificationEntry ::= SEQUENCE {
   gs2310pplusQosDSCPClassificationQoSClass		INTEGER,
   gs2310pplusQosDSCPClassificationDPL			INTEGER,
   gs2310pplusQosDSCPClassificationDSCP			Integer32
}

gs2310pplusQosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2310pplusQosDSCPClassificationEntry 1 }

gs2310pplusQosDSCPClassificationDPL OBJECT-TYPE
   SYNTAX      INTEGER(1|2)
   MAX-ACCESS  not-accessible
   STATUS      current
   DESCRIPTION
      " DPL. Index 1~2 mean DPL 0~1."
   ::= { gs2310pplusQosDSCPClassificationEntry 2 }

gs2310pplusQosDSCPClassificationDSCP OBJECT-TYPE
   SYNTAX      Integer32(0..63)
   MAX-ACCESS  read-write
   STATUS      current
   DESCRIPTION
      " Select the classified DSCP value.
        range: 0-63,
        default: 0. "
   ::= { gs2310pplusQosDSCPClassificationEntry 3 }

gs2310pplusQosControlList                                         OBJECT IDENTIFIER ::= { gs2310pplusQos 9 }

gs2310pplusQosQceCreate OBJECT-TYPE
   SYNTAX       INTEGER { none(0), create(1) }
   MAX-ACCESS   read-write
   STATUS       current
   DESCRIPTION
       "default: 0
        0 : None  (read only)
        1 : Create an Qos entry"
   ::= { gs2310pplusQosControlList 1 }

gs2310pplusQosQceTable OBJECT-TYPE
   SYNTAX      SEQUENCE OF GS2310PPLUSQosQceEntry
   MAX-ACCESS  not-accessible
   STATUS      current
   DESCRIPTION
       " Create Qos QCE entry. "
   ::= { gs2310pplusQosControlList 2 }

gs2310pplusQosQceEntry OBJECT-TYPE
   SYNTAX      GS2310PPLUSQosQceEntry
   MAX-ACCESS  not-accessible
   STATUS      current
   DESCRIPTION
       ""
   INDEX    { gs2310pplusQosQceIndex  }
   ::= { gs2310pplusQosQceTable 1 }

GS2310PPLUSQosQceEntry ::= SEQUENCE {
   gs2310pplusQosQceIndex                Integer32,
   gs2310pplusQosQceID                   Integer32,
   gs2310pplusQosQceNextID               Integer32,
   gs2310pplusQosQcePortMembers          DisplayString,
   
   gs2310pplusQosQceTag                  DisplayString,
   gs2310pplusQosQceVID                  DisplayString,
   gs2310pplusQosPCP                     DisplayString,
   gs2310pplusQosDEI                     DisplayString,
   gs2310pplusQosSMAC                    DisplayString,
   gs2310pplusQosDMACType                DisplayString,
   gs2310pplusQosFrameType               INTEGER,
   
   gs2310pplusQosMacEtherType            DisplayString,
   
   gs2310pplusQosLLCSSAPAddr             DisplayString,
   gs2310pplusQosLLCDSAPAddr             DisplayString,
   gs2310pplusQosLLCControl              DisplayString,
   
   gs2310pplusQosSNAPPID                 DisplayString,
   
   gs2310pplusQosIpv4Protocol            DisplayString,
   gs2310pplusQosIpv4ProtocolValue       Integer32,
   gs2310pplusQosIpv4ProtocolUDPSport    DisplayString,
   gs2310pplusQosIpv4ProtocolUDPDport    DisplayString,
   gs2310pplusQosIpv4ProtocolTCPSport    DisplayString,
   gs2310pplusQosIpv4ProtocolTCPDport    DisplayString,
   gs2310pplusQosIpv4Ip                  DisplayString,
   gs2310pplusQosIpv4Mask                DisplayString,
   gs2310pplusQosIpv4IPFragment          INTEGER,
   gs2310pplusQosIpv4DSCP                DisplayString,


   gs2310pplusQosIpv6Protocol            DisplayString,
   gs2310pplusQosIpv6ProtocolValue       Integer32,
   gs2310pplusQosIpv6ProtocolUDPSport    DisplayString,
   gs2310pplusQosIpv6ProtocolUDPDport    DisplayString,
   gs2310pplusQosIpv6ProtocolTCPSport    DisplayString,
   gs2310pplusQosIpv6ProtocolTCPDport    DisplayString,
   gs2310pplusQosIpv6Ip                  DisplayString,
   gs2310pplusQosIpv6Mask                DisplayString,
   gs2310pplusQosIpv6DSCP                DisplayString,
   
   gs2310pplusQosActionClass             Integer32,
   gs2310pplusQosActionDPL               INTEGER,
   gs2310pplusQosActionDSCP              Integer32,
   gs2310pplusQosQceRowStatus            INTEGER
}

gs2310pplusQosQceIndex OBJECT-TYPE
   SYNTAX      Integer32(1..256)
   MAX-ACCESS  not-accessible
   STATUS      current
   DESCRIPTION
       " "
   ::= { gs2310pplusQosQceEntry 1 }

gs2310pplusQosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2310pplusQosQceEntry 2 }

gs2310pplusQosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2310pplusQosQceEntry 3 }

gs2310pplusQosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2310pplusQosQceEntry 4 }

gs2310pplusQosQceTag OBJECT-TYPE
   SYNTAX      DisplayString
   MAX-ACCESS  read-write
   STATUS      current
   DESCRIPTION
       " Value of Tag field can be 'Any', 'Untag' or 'Tag'. "
   ::= { gs2310pplusQosQceEntry 5 }

gs2310pplusQosQceVID OBJECT-TYPE
   SYNTAX      DisplayString
   MAX-ACCESS  read-write
   STATUS      current
   DESCRIPTION
       " Valid value of VLAN ID can be any value in 'Specific 1~4094' or 'range 1-4094' or 'Any'. "
   ::= { gs2310pplusQosQceEntry 6 }

gs2310pplusQosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2310pplusQosQceEntry 7 }

gs2310pplusQosDEI OBJECT-TYPE
   SYNTAX      DisplayString
   MAX-ACCESS  read-write
   STATUS      current
   DESCRIPTION
       " Drop Eligible Indicator: Valid value of DEI can be any of values between 0, 1 or 'Any'. "
   ::= { gs2310pplusQosQceEntry 8 }

gs2310pplusQosSMAC  OBJECT-TYPE
   SYNTAX      DisplayString
   MAX-ACCESS  read-write
   STATUS      current
   DESCRIPTION
       "  Source MAC address: 24 MS bits OUI(00-00-00 ~ FF-FF-FF) or 'Any'. "
   ::= { gs2310pplusQosQceEntry 9 }

gs2310pplusQosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2310pplusQosQceEntry 10 }

gs2310pplusQosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2310pplusQosQceEntry 11 }

gs2310pplusQosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2310pplusQosQceEntry 12 }

gs2310pplusQosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2310pplusQosQceEntry 13 }

gs2310pplusQosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2310pplusQosQceEntry 14 }

gs2310pplusQosLLCControl OBJECT-TYPE
   SYNTAX      DisplayString
   MAX-ACCESS  read-write
   STATUS      current
   DESCRIPTION
       " Valid Control field can vary from 0x00 to 0xFF or 'Any',
         range: 00-FF,
         default: Any. "
   ::= { gs2310pplusQosQceEntry 15 }

gs2310pplusQosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2310pplusQosQceEntry 16 }

gs2310pplusQosIpv4Protocol OBJECT-TYPE
   SYNTAX      DisplayString
   MAX-ACCESS  read-write
   STATUS      current
   DESCRIPTION
       " IP protocol number: (Other, TCP or UDP) or 'Any'. "
   ::= { gs2310pplusQosQceEntry 17 }

gs2310pplusQosIpv4ProtocolValue  OBJECT-TYPE
   SYNTAX      Integer32(0..255)
   MAX-ACCESS  read-write
   STATUS      current
   DESCRIPTION
       " Ipv4 Protocol is Other.
         range: 0-255
         default: 0. "
   ::= { gs2310pplusQosQceEntry 18 }

gs2310pplusQosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2310pplusQosQceEntry 19 }

gs2310pplusQosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2310pplusQosQceEntry 20 }

gs2310pplusQosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2310pplusQosQceEntry 21 }

gs2310pplusQosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2310pplusQosQceEntry 22 }

gs2310pplusQosIpv4Ip OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223.
          If a port is configured to match on DMAC/DIP, this field is the
          Destination IP address."
   ::= { gs2310pplusQosQceEntry 23 }

gs2310pplusQosIpv4Mask OBJECT-TYPE
   SYNTAX      DisplayString
   MAX-ACCESS  read-write
   STATUS      current
   DESCRIPTION
       " Specific IP address in mask format or value 0.0.0.0 is 'Any'. "
   ::= { gs2310pplusQosQceEntry 24 }

gs2310pplusQosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2310pplusQosQceEntry 25 }

gs2310pplusQosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2310pplusQosQceEntry 26 }

gs2310pplusQosIpv6Protocol OBJECT-TYPE
   SYNTAX      DisplayString
   MAX-ACCESS  read-write
   STATUS      current
   DESCRIPTION
       " IP protocol number: (Other, TCP or UDP) or 'Any'. "
   ::= { gs2310pplusQosQceEntry 27 }

gs2310pplusQosIpv6ProtocolValue OBJECT-TYPE
   SYNTAX      Integer32(0..255)
   MAX-ACCESS  read-write
   STATUS      current
   DESCRIPTION
       " when IPv6 protocol is Other ,
         range: 0-255. "
   ::= { gs2310pplusQosQceEntry 28 }

gs2310pplusQosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2310pplusQosQceEntry 29 }

gs2310pplusQosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2310pplusQosQceEntry 30 }

gs2310pplusQosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2310pplusQosQceEntry 31 }


gs2310pplusQosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2310pplusQosQceEntry 32 }

gs2310pplusQosIpv6Ip OBJECT-TYPE
   SYNTAX      DisplayString
   MAX-ACCESS  read-write
   STATUS      current
   DESCRIPTION
       " IPv6 source address: (a.b.c.d) or value 0.0.0.0 is 'Any', 32 LS bits.
         If a port is configured to match on DMAC/DIP, this field is the
         Destination IP address."
   ::= { gs2310pplusQosQceEntry 33 }

gs2310pplusQosIpv6Mask OBJECT-TYPE
   SYNTAX      DisplayString
   MAX-ACCESS  read-write
   STATUS      current
   DESCRIPTION
       " IPv6 mask address: (a.b.c.d) or value 0.0.0.0 is 'Any', 32 LS bits. "
   ::= { gs2310pplusQosQceEntry 34 }

gs2310pplusQosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2310pplusQosQceEntry 35 }

gs2310pplusQosActionClass  OBJECT-TYPE
   SYNTAX      Integer32(0..8)
   MAX-ACCESS  read-write
   STATUS      current
   DESCRIPTION
       " QoS class: (0-7) or 8: Default."
   ::= { gs2310pplusQosQceEntry 36 }

gs2310pplusQosActionDPL OBJECT-TYPE
   SYNTAX      INTEGER (0..4)
   MAX-ACCESS  read-write
   STATUS      current
   DESCRIPTION
       " DP Valid Drop Precedence Level can be (0-3) or 4: Default. "
   ::= { gs2310pplusQosQceEntry 37 }

gs2310pplusQosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2310pplusQosQceEntry 38 }

gs2310pplusQosQceRowStatus OBJECT-TYPE
   SYNTAX      INTEGER { active(1), notInservice(2), destroy(4) }
   MAX-ACCESS  read-write
   STATUS      current
   DESCRIPTION
       "  1: active2: notInservice 4: destroy"
   ::= { gs2310pplusQosQceEntry 39 }

gs2310pplusQosQceMoveID OBJECT-TYPE
   SYNTAX       Integer32(0..256)
   MAX-ACCESS   read-write
   STATUS       current
   DESCRIPTION
       " Move Qos,
         default: 0
         Qos ID must be exist.
         range : 0 - 256."
   ::= { gs2310pplusQosControlList 3 }

gs2310pplusQosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2310pplusQosControlList 4 }


gs2310pplusQosQCLStatusTable OBJECT-TYPE
   SYNTAX      SEQUENCE OF GS2310PPLUSQosQCLStatusEntry
   MAX-ACCESS  not-accessible
   STATUS      current
   DESCRIPTION
       "  configure the basic QoS DSCP Translation settings for all switches. "
   ::= { gs2310pplusQos  10 }

gs2310pplusQosQCLStatusEntry OBJECT-TYPE
   SYNTAX      GS2310PPLUSQosQCLStatusEntry
   MAX-ACCESS  not-accessible
   STATUS      current
   DESCRIPTION
       ""
   INDEX    { gs2310pplusQosQCLStatusList  }
   ::= { gs2310pplusQosQCLStatusTable 1 }

GS2310PPLUSQosQCLStatusEntry ::= SEQUENCE {
   gs2310pplusQosQCLStatusList               Integer32,
   gs2310pplusQosQCLStatusUser               DisplayString,
   gs2310pplusQosQCLStatusQCEId              DisplayString,
   gs2310pplusQosQCLStatusFrameType          DisplayString,
   gs2310pplusQosQCLStatusPortlist           DisplayString,
   gs2310pplusQosQCLStatusActionClass	       DisplayString,
   gs2310pplusQosQCLStatusActionDPL	       DisplayString,
   gs2310pplusQosQCLStatusActionDSCP	       DisplayString,
   gs2310pplusQosQCLStatusActionConflict     DisplayString
}

gs2310pplusQosQCLStatusList OBJECT-TYPE
   SYNTAX      Integer32(1..4095)
   MAX-ACCESS  not-accessible
   STATUS      current
   DESCRIPTION
       " QCL table index. "
   ::= { gs2310pplusQosQCLStatusEntry 1}
   
gs2310pplusQosQCLStatusUser OBJECT-TYPE
   SYNTAX      DisplayString
   MAX-ACCESS  read-only
   STATUS      current
   DESCRIPTION
       " Indicates the QCL user. "
   ::= { gs2310pplusQosQCLStatusEntry 2 }

gs2310pplusQosQCLStatusQCEId OBJECT-TYPE
   SYNTAX      DisplayString
   MAX-ACCESS  read-only
   STATUS      current
   DESCRIPTION
      " Indicates the index of QCE. "
   ::= { gs2310pplusQosQCLStatusEntry 3}

gs2310pplusQosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2310pplusQosQCLStatusEntry 4}

gs2310pplusQosQCLStatusPortlist OBJECT-TYPE
   SYNTAX      DisplayString
   MAX-ACCESS  read-only
   STATUS      current
   DESCRIPTION
       " Indicates the list of ports configured with the QCE. "
   ::= { gs2310pplusQosQCLStatusEntry 5}

gs2310pplusQosQCLStatusActionClass OBJECT-TYPE
   SYNTAX      DisplayString
   MAX-ACCESS  read-only
   STATUS      current
   DESCRIPTION
       " Classified QoS class; if a frame matches the QCE it will be put in the
       queue. "
   ::= { gs2310pplusQosQCLStatusEntry 6}

gs2310pplusQosQCLStatusActionDPL OBJECT-TYPE
   SYNTAX      DisplayString
   MAX-ACCESS  read-only
   STATUS      current
   DESCRIPTION
       " Drop Precedence Level; if a frame matches the QCE then DP level will
       set to value displayed under DPL column."
   ::= { gs2310pplusQosQCLStatusEntry 7}

gs2310pplusQosQCLStatusActionDSCP OBJECT-TYPE
   SYNTAX      DisplayString
   MAX-ACCESS  read-only
   STATUS      current
   DESCRIPTION
       " If a frame matches the QCE then DSCP will be classified with the value
       displayed under DSCP column."
   ::= { gs2310pplusQosQCLStatusEntry 8}

gs2310pplusQosQCLStatusActionConflict OBJECT-TYPE
   SYNTAX      DisplayString
   MAX-ACCESS  read-only
   STATUS      current
   DESCRIPTION
       " If a frame matches the QCE then DSCP will be classified with the value
        displayed under DSCP column. "
   ::= { gs2310pplusQosQCLStatusEntry 9}


gs2310pplusQosStormControl                                           OBJECT IDENTIFIER ::= { gs2310pplusQos 11 }

gs2310pplusQoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { gs2310pplusQosStormControl 2 }

gs2310pplusQoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2310pplusQosStormControl 3 }

gs2310pplusQoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { gs2310pplusQosStormControl 4 }

gs2310pplusQoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2310pplusQosStormControl 5 }

gs2310pplusQoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { gs2310pplusQosStormControl 6 }

gs2310pplusQoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2310pplusQosStormControl 7 }


gs2310pplusVlan                                                           OBJECT IDENTIFIER ::= { gs2310pplusConfiguration 15 }

gs2310pplusVlanPorts                                                      OBJECT IDENTIFIER ::= { gs2310pplusVlan 1 }

gs2310pplusVlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2310pplusVlanPorts 1 }

gs2310pplusVlanPortsTable OBJECT-TYPE
   SYNTAX      SEQUENCE OF GS2310PPLUSVlanPortsEntry
   MAX-ACCESS  not-accessible
   STATUS      current
   DESCRIPTION
       " Configure Vlan ports Configuration mode. "
   ::= { gs2310pplusVlanPorts 2 }

gs2310pplusVlanPortsEntry OBJECT-TYPE
   SYNTAX      GS2310PPLUSVlanPortsEntry
   MAX-ACCESS  not-accessible
   STATUS      current
   DESCRIPTION
       ""
   INDEX    { gs2310pplusVlanPortsPort  }
   ::= { gs2310pplusVlanPortsTable 1 }

GS2310PPLUSVlanPortsEntry ::= SEQUENCE {
   gs2310pplusVlanPortsPort	         Integer32,
   gs2310pplusVlanPortsPVID     Integer32,
   gs2310pplusVlanPortsFrameType      INTEGER,
   gs2310pplusVlanPortsIngressFilter  INTEGER,
   gs2310pplusVlanPortsEgressRule     INTEGER,
   gs2310pplusVlanPortsPortType       INTEGER
}

gs2310pplusVlanPortsPort OBJECT-TYPE
   SYNTAX      Integer32(1..4094)
   MAX-ACCESS  not-accessible
   STATUS      current
   DESCRIPTION
       " port, range : 1 - port number. "
   ::= { gs2310pplusVlanPortsEntry 1 }

gs2310pplusVlanPortsPVID OBJECT-TYPE
   SYNTAX      Integer32(1..4094)
   MAX-ACCESS  read-write
   STATUS      current
   DESCRIPTION
       "Configure PVID.
        range: 1-4094,
        default: 1. "
   ::= { gs2310pplusVlanPortsEntry 2 }

gs2310pplusVlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2310pplusVlanPortsEntry 3 }

gs2310pplusVlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2310pplusVlanPortsEntry 4 }

gs2310pplusVlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2310pplusVlanPortsEntry 5 }

gs2310pplusVlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2310pplusVlanPortsEntry 6 }

gs2310pplusVlanPrivateVLAN                                                              OBJECT IDENTIFIER ::= { gs2310pplusVlan 2 }

gs2310pplusVlanPrivateVLANMembership                                                    OBJECT IDENTIFIER ::= { gs2310pplusVlanPrivateVLAN 1 }

gs2310pplusVlanPrivateVLANMembershipCreate OBJECT-TYPE
   SYNTAX       Integer32(1..4094)
   MAX-ACCESS   read-write
   STATUS       current
   DESCRIPTION
       "default: 0
        0 : None  (read only)
        1 : Create a pvlan"
   ::= { gs2310pplusVlanPrivateVLANMembership 1 }

gs2310pplusVlanPrivateVLANMembershipTable OBJECT-TYPE
   SYNTAX      SEQUENCE OF Gs2310pplusVlanPrivateVLANMembershipEntry
   MAX-ACCESS  not-accessible
   STATUS      current
   DESCRIPTION
       " Configure Private Vlan Configuration. "
   ::= { gs2310pplusVlanPrivateVLANMembership 2 }

gs2310pplusVlanPrivateVLANMembershipEntry OBJECT-TYPE
   SYNTAX      Gs2310pplusVlanPrivateVLANMembershipEntry
   MAX-ACCESS  not-accessible
   STATUS      current
   DESCRIPTION
       ""
   INDEX    { gs2310pplusVlanPrivateVLANIndex  }
   ::= { gs2310pplusVlanPrivateVLANMembershipTable 1 }

Gs2310pplusVlanPrivateVLANMembershipEntry ::= SEQUENCE {
   gs2310pplusVlanPrivateVLANIndex          Integer32,
   gs2310pplusVlanPrivateVLANID             Integer32,
   gs2310pplusVlanPrivateVLANMemberships    DisplayString,
   gs2310pplusVlanPrivateVLANRowStatus      INTEGER
}

gs2310pplusVlanPrivateVLANIndex OBJECT-TYPE
   SYNTAX      Integer32(1..52)
   MAX-ACCESS  not-accessible
   STATUS      current
   DESCRIPTION
       "private VLAN Index. "
   ::= { gs2310pplusVlanPrivateVLANMembershipEntry 1 }

gs2310pplusVlanPrivateVLANID OBJECT-TYPE
   SYNTAX      Integer32(1..52)
   MAX-ACCESS  read-write
   STATUS      current
   DESCRIPTION
       "Indicates the ID of this particular private VLAN.
       The CreateEntry can be modify, the other entry can't be modify."
   ::= { gs2310pplusVlanPrivateVLANMembershipEntry 2 }

gs2310pplusVlanPrivateVLANMemberships OBJECT-TYPE
   SYNTAX      DisplayString
   MAX-ACCESS  read-write
   STATUS      current
   DESCRIPTION
       "To include the ports in a Private VLAN"
   ::= { gs2310pplusVlanPrivateVLANMembershipEntry 3 }

gs2310pplusVlanPrivateVLANRowStatus OBJECT-TYPE
   SYNTAX      INTEGER { active(1), notInservice(2), destroy(4) }
   MAX-ACCESS  read-write
   STATUS      current
   DESCRIPTION
       "1: active
        2: notInservice
        4: destroy"
   ::= { gs2310pplusVlanPrivateVLANMembershipEntry 4 }

gs2310pplusVlanPortIsolationTable OBJECT-TYPE
   SYNTAX      SEQUENCE OF Gs2310pplusVlanPortIsolationEntry
   MAX-ACCESS  not-accessible
   STATUS      current
   DESCRIPTION
       " Configure Vlan Port Isolation Configuration. "
   ::= { gs2310pplusVlanPrivateVLAN 2 }

gs2310pplusVlanPortIsolationEntry OBJECT-TYPE
   SYNTAX      Gs2310pplusVlanPortIsolationEntry
   MAX-ACCESS  not-accessible
   STATUS      current
   DESCRIPTION
       ""
   INDEX    { gs2310pplusVlanPortIsolationPort  }
   ::= { gs2310pplusVlanPortIsolationTable 1 }

Gs2310pplusVlanPortIsolationEntry ::= SEQUENCE {
   gs2310pplusVlanPortIsolationPort Integer32,
   gs2310pplusVlanPortIsolation     INTEGER
}

gs2310pplusVlanPortIsolationPort OBJECT-TYPE
   SYNTAX      Integer32(1..4094)
   MAX-ACCESS  not-accessible
   STATUS      current
   DESCRIPTION
       " port, range : 1 - port number. "
   ::= { gs2310pplusVlanPortIsolationEntry 1 }

gs2310pplusVlanPortIsolation OBJECT-TYPE
   SYNTAX      INTEGER{ disable(0), enable(1) }
   MAX-ACCESS  read-write
   STATUS      current
   DESCRIPTION
       "default: 0
        0:disable
        1:enable"
   ::= { gs2310pplusVlanPortIsolationEntry 2 }


gs2310pplusMACbasedVLAN                                                      OBJECT IDENTIFIER ::= { gs2310pplusVlan 3 }

gs2310pplusMACbasedVLANConf                                                      OBJECT IDENTIFIER ::= { gs2310pplusMACbasedVLAN 1 }

gs2310pplusMACbasedVLANConfCreate OBJECT-TYPE
   SYNTAX       Integer32
   MAX-ACCESS   read-write
   STATUS       current
   DESCRIPTION
       "default: 0
       0 : None  (read only) 1 : Create MAC base vlan"
   ::= { gs2310pplusMACbasedVLANConf 1 }

gs2310pplusMACbasedVLANConfTable OBJECT-TYPE
   SYNTAX      SEQUENCE OF Gs2310pplusMACbasedVLANConfEntry
   MAX-ACCESS  not-accessible
   STATUS      current
   DESCRIPTION
       " Configure Vlan Port Isolation Configuration. "
   ::= { gs2310pplusMACbasedVLANConf 2 }

gs2310pplusMACbasedVLANConfEntry OBJECT-TYPE
   SYNTAX      Gs2310pplusMACbasedVLANConfEntry
   MAX-ACCESS  not-accessible
   STATUS      current
   DESCRIPTION
       ""
   INDEX    { gs2310pplusMACbasedVLANIndex  }
   ::= { gs2310pplusMACbasedVLANConfTable 1 }

Gs2310pplusMACbasedVLANConfEntry ::= SEQUENCE {
   gs2310pplusMACbasedVLANIndex         Integer32,
   gs2310pplusMACbasedVLANMACAddress    MacAddress,
   gs2310pplusMACbasedVLANID            Integer32,
   gs2310pplusMACbasedMemberships       DisplayString,
   gs2310pplusMACbaseRowStatus          INTEGER
}

gs2310pplusMACbasedVLANIndex OBJECT-TYPE
   SYNTAX      Integer32(1..256)
   MAX-ACCESS  read-write
   STATUS      current
   DESCRIPTION
       "Indicates the VLAN ID. "
   ::= { gs2310pplusMACbasedVLANConfEntry 1 }

gs2310pplusMACbasedVLANMACAddress OBJECT-TYPE
   SYNTAX      MacAddress
   MAX-ACCESS  read-write
   STATUS      current
   DESCRIPTION
       "Indicates the MAC address.
       The CreateEntry can be modify, the other entry can't be modify."
   ::= { gs2310pplusMACbasedVLANConfEntry 2 }

gs2310pplusMACbasedVLANID OBJECT-TYPE
   SYNTAX      Integer32(1..4094)
   MAX-ACCESS  read-write
   STATUS      current
   DESCRIPTION
       "Indicates the VLAN ID. "
   ::= { gs2310pplusMACbasedVLANConfEntry 3 }

gs2310pplusMACbasedMemberships OBJECT-TYPE
   SYNTAX      DisplayString
   MAX-ACCESS  read-write
   STATUS      current
   DESCRIPTION
       "The ports are displayed for each MAC-based VLAN entry.
        To include the port in a MAC-based VLAN"
   ::= { gs2310pplusMACbasedVLANConfEntry 4 }


gs2310pplusMACbaseRowStatus OBJECT-TYPE
   SYNTAX      INTEGER { active(1), notInservice(2), destroy(4)}
   MAX-ACCESS  read-write
   STATUS      current
   DESCRIPTION
       "1: active
        2: notInservice
        4: destroy"
   ::= { gs2310pplusMACbasedVLANConfEntry 5 }


gs2310pplusIGMPSnooping                                                           OBJECT IDENTIFIER ::= { gs2310pplusConfiguration 16 }

gs2310pplusIGMPSnoopingBasic                                                      OBJECT IDENTIFIER ::= { gs2310pplusIGMPSnooping 1 }

gs2310pplusIGMPSnoopingEnable  OBJECT-TYPE
   SYNTAX      INTEGER { disable(0), enable(1) }
   MAX-ACCESS  read-write
   STATUS      current
   DESCRIPTION
       "Enable/Disable the Global IGMP Snooping"
   ::= { gs2310pplusIGMPSnoopingBasic 1 }

gs2310pplusIGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2310pplusIGMPSnoopingBasic 2 }

gs2310pplusIGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2310pplusIGMPSnoopingBasic 3 }
   
gs2310pplusIGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2310pplusIGMPSnoopingBasic 4 }

gs2310pplusIGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2310pplusIGMPSnoopingBasic 5 }

gs2310pplusIGMPSnoopingPortRelatedTable OBJECT-TYPE
   SYNTAX      SEQUENCE OF Gs2310pplusIGMPSnoopingPortRelatedEntry
   MAX-ACCESS  not-accessible
   STATUS      current
   DESCRIPTION
       " Configure IGMP Snooping Port Related Configuration. "
   ::= { gs2310pplusIGMPSnoopingBasic 6 }

gs2310pplusIGMPSnoopingPortRelatedEntry OBJECT-TYPE
   SYNTAX      Gs2310pplusIGMPSnoopingPortRelatedEntry
   MAX-ACCESS  not-accessible
   STATUS      current
   DESCRIPTION
       ""
   INDEX    { ifIndex  }
   ::= { gs2310pplusIGMPSnoopingPortRelatedTable 1 }

Gs2310pplusIGMPSnoopingPortRelatedEntry ::= SEQUENCE {
   gs2310pplusIGMPSnoopingRouterPort	INTEGER,
   gs2310pplusIGMPSnoopingFastLeave  	INTEGER,
   gs2310pplusIGMPSnoopingThrottling    Integer32
}

gs2310pplusIGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2310pplusIGMPSnoopingPortRelatedEntry 1 }

gs2310pplusIGMPSnoopingFastLeave OBJECT-TYPE
   SYNTAX      INTEGER { disable(0), enable(1) }
   MAX-ACCESS  read-write
   STATUS      current
   DESCRIPTION
       "Enable/Disable the fast leave on the port. "
   ::= { gs2310pplusIGMPSnoopingPortRelatedEntry 2 }
   
gs2310pplusIGMPSnoopingThrottling OBJECT-TYPE
   SYNTAX      Integer32(0..10)
   MAX-ACCESS  read-write
   STATUS      current
   DESCRIPTION
       "Enable to limit the number of multicast groups to which a switch port can belong.
       0: unlimited"
   ::= { gs2310pplusIGMPSnoopingPortRelatedEntry 3 }
   
gs2310pplusIGMPSnoopingVLANTable OBJECT-TYPE
   SYNTAX      SEQUENCE OF Gs2310pplusIGMPSnoopingVLANEntry
   MAX-ACCESS  not-accessible
   STATUS      current
   DESCRIPTION
       " Configure IGMP Snooping Vlan Configuration. "
   ::= { gs2310pplusIGMPSnooping 2 }

gs2310pplusIGMPSnoopingVLANEntry OBJECT-TYPE
   SYNTAX      Gs2310pplusIGMPSnoopingVLANEntry
   MAX-ACCESS  not-accessible
   STATUS      current
   DESCRIPTION
       ""
   INDEX    { gs2310pplusIGMPSnoopingVLANID  }
   ::= { gs2310pplusIGMPSnoopingVLANTable 1 }

Gs2310pplusIGMPSnoopingVLANEntry ::= SEQUENCE {
   gs2310pplusIGMPSnoopingVLANID        	Integer32,
   gs2310pplusIGMPSnoopingVLANEnable    	INTEGER,
   gs2310pplusIGMPSnoopingVLANIGMPQuerier   INTEGER,
   gs2310pplusIGMPSnoopingVLANCompatibility INTEGER,
   gs2310pplusIGMPSnoopingVLANRV        	Integer32,
   gs2310pplusIGMPSnoopingVLANQI      	    Integer32,
   gs2310pplusIGMPSnoopingVLANQRI   	    Integer32,
   gs2310pplusIGMPSnoopingVLANLLQI   	    Integer32,
   gs2310pplusIGMPSnoopingVLANURI    	    Integer32
}

gs2310pplusIGMPSnoopingVLANID OBJECT-TYPE
   SYNTAX      Integer32(1..4095)
   MAX-ACCESS  read-write
   STATUS      current
   DESCRIPTION
       "The VLAN ID of the entry"
   ::= { gs2310pplusIGMPSnoopingVLANEntry 1 }

gs2310pplusIGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2310pplusIGMPSnoopingVLANEntry 2 }

gs2310pplusIGMPSnoopingVLANIGMPQuerier OBJECT-TYPE
   SYNTAX      INTEGER { disable(0), enable(1) }
   MAX-ACCESS  read-write
   STATUS      current
   DESCRIPTION
       "Enable/Disable the IGMP Querier in the VLAN. "
   ::= { gs2310pplusIGMPSnoopingVLANEntry 3 }

gs2310pplusIGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2310pplusIGMPSnoopingVLANEntry 4 }
   
gs2310pplusIGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2310pplusIGMPSnoopingVLANEntry 5 }
   
gs2310pplusIGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2310pplusIGMPSnoopingVLANEntry 6 }
   
gs2310pplusIGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2310pplusIGMPSnoopingVLANEntry 7 }
   
gs2310pplusIGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2310pplusIGMPSnoopingVLANEntry 8 }

gs2310pplusIGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2310pplusIGMPSnoopingVLANEntry 9 }

gs2310pplusIGMPSnoopingPortGroupFiltering                                                      OBJECT IDENTIFIER ::= { gs2310pplusIGMPSnooping 3 }

gs2310pplusIGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2310pplusIGMPSnoopingPortGroupFiltering 1 }

gs2310pplusIGMPSnoopingPortGroupFilteringTable OBJECT-TYPE
   SYNTAX      SEQUENCE OF Gs2310pplusIGMPSnoopingPortGroupFilteringEntry
   MAX-ACCESS  not-accessible
   STATUS      current
   DESCRIPTION
       " Configure IGMP Snooping port group filtering. "
   ::= { gs2310pplusIGMPSnoopingPortGroupFiltering 2 }

gs2310pplusIGMPSnoopingPortGroupFilteringEntry OBJECT-TYPE
   SYNTAX      Gs2310pplusIGMPSnoopingPortGroupFilteringEntry
   MAX-ACCESS  not-accessible
   STATUS      current
   DESCRIPTION
       ""
   INDEX    { gs2310pplusIGMPSnoopingPortGroupFilteringIndex  }
   ::= { gs2310pplusIGMPSnoopingPortGroupFilteringTable 1 }

Gs2310pplusIGMPSnoopingPortGroupFilteringEntry ::= SEQUENCE {
   gs2310pplusIGMPSnoopingPortGroupFilteringIndex         Integer32,
   gs2310pplusIGMPSnoopingPortGroupFilteringPort          Integer32,
   gs2310pplusIGMPSnoopingPortGroupFilteringGroups        DisplayString,
   gs2310pplusIGMPSnoopingPortGroupFilteringRowStatus     INTEGER
}

gs2310pplusIGMPSnoopingPortGroupFilteringIndex OBJECT-TYPE
   SYNTAX      Integer32(1..65535)
   MAX-ACCESS  not-accessible
   STATUS      current
   DESCRIPTION
       "IGMP Snooping Port Group Filtering Configuration Index. "
   ::= { gs2310pplusIGMPSnoopingPortGroupFilteringEntry 1 }

gs2310pplusIGMPSnoopingPortGroupFilteringPort OBJECT-TYPE
   SYNTAX      Integer32(1..65535)
   MAX-ACCESS  read-write
   STATUS      current
   DESCRIPTION
       "The logical port for the settings. "
   ::= { gs2310pplusIGMPSnoopingPortGroupFilteringEntry 2 }

gs2310pplusIGMPSnoopingPortGroupFilteringGroups OBJECT-TYPE
   SYNTAX      DisplayString
   MAX-ACCESS  read-write
   STATUS      current
   DESCRIPTION
       "The IP Multicast Group that will be filtered. "
   ::= { gs2310pplusIGMPSnoopingPortGroupFilteringEntry 3 }

gs2310pplusIGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2310pplusIGMPSnoopingPortGroupFilteringEntry 4 }

gs2310pplusIGMPSnoopingStatus                                                      OBJECT IDENTIFIER ::= { gs2310pplusIGMPSnooping 4 }

gs2310pplusIGMPSnoopingstatisticClear OBJECT-TYPE
   SYNTAX      INTEGER { none(0), clear(1)}
   MAX-ACCESS  read-write
   STATUS      current
   DESCRIPTION
       "Clears all Statistics counters."
   ::= { gs2310pplusIGMPSnoopingStatus 1 }


gs2310pplusIGMPSnoopingstatisticTable OBJECT-TYPE
   SYNTAX      SEQUENCE OF Gs2310pplusIGMPSnoopingstatisticEntry
   MAX-ACCESS  not-accessible
   STATUS      current
   DESCRIPTION
       " Configure Vlan Port Isolation Configuration. "
   ::= { gs2310pplusIGMPSnoopingStatus 2 }

gs2310pplusIGMPSnoopingstatisticEntry OBJECT-TYPE
   SYNTAX      Gs2310pplusIGMPSnoopingstatisticEntry
   MAX-ACCESS  not-accessible
   STATUS      current
   DESCRIPTION
       ""
   INDEX    { gs2310pplusIGMPSnoopingstatisticVLANID  }
   ::= { gs2310pplusIGMPSnoopingstatisticTable 1 }

Gs2310pplusIGMPSnoopingstatisticEntry ::= SEQUENCE {
   gs2310pplusIGMPSnoopingstatisticVLANID              Integer32,
   gs2310pplusIGMPSnoopingstatisticQuerierVersion      DisplayString,
   gs2310pplusIGMPSnoopingstatisticHostVersion         DisplayString,
   gs2310pplusIGMPSnoopingstatisticQuerierStatus       DisplayString,
   gs2310pplusIGMPSnoopingstatisticQueriesTransmitted  Counter32,
   gs2310pplusIGMPSnoopingstatisticQueriesReceived     Counter32,
   gs2310pplusIGMPSnoopingstatisticV1ReportsReceived   Counter32,
   gs2310pplusIGMPSnoopingstatisticV2ReportsReceived   Counter32,
   gs2310pplusIGMPSnoopingstatisticV3ReportsReceived   Counter32,
   gs2310pplusIGMPSnoopingstatisticV2LeavesReceived    Counter32
}


gs2310pplusIGMPSnoopingstatisticVLANID OBJECT-TYPE
   SYNTAX      Integer32(1..4095)
   MAX-ACCESS  read-only
   STATUS      current
   DESCRIPTION
       "The VLAN ID of the entry. "
   ::= { gs2310pplusIGMPSnoopingstatisticEntry 1 }

gs2310pplusIGMPSnoopingstatisticQuerierVersion OBJECT-TYPE
   SYNTAX      DisplayString
   MAX-ACCESS  read-only
   STATUS      current
   DESCRIPTION
       "Working Querier Version currently. "
   ::= { gs2310pplusIGMPSnoopingstatisticEntry 2 }
   
gs2310pplusIGMPSnoopingstatisticHostVersion OBJECT-TYPE
   SYNTAX      DisplayString
   MAX-ACCESS  read-only
   STATUS      current
   DESCRIPTION
       "Working Host Version currently. "
   ::= { gs2310pplusIGMPSnoopingstatisticEntry 3 }

gs2310pplusIGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2310pplusIGMPSnoopingstatisticEntry 4 }

gs2310pplusIGMPSnoopingstatisticQueriesTransmitted OBJECT-TYPE
   SYNTAX      Counter32
   MAX-ACCESS  read-only
   STATUS      current
   DESCRIPTION
       "The number of Transmitted Queries. "
   ::= { gs2310pplusIGMPSnoopingstatisticEntry 5 }

gs2310pplusIGMPSnoopingstatisticQueriesReceived OBJECT-TYPE
   SYNTAX      Counter32
   MAX-ACCESS  read-only
   STATUS      current
   DESCRIPTION
       "The number of Received Queries. "
   ::= { gs2310pplusIGMPSnoopingstatisticEntry 6 }

gs2310pplusIGMPSnoopingstatisticV1ReportsReceived OBJECT-TYPE
   SYNTAX      Counter32
   MAX-ACCESS  read-only
   STATUS      current
   DESCRIPTION
       "The number of Received V1 Reports. "
   ::= { gs2310pplusIGMPSnoopingstatisticEntry 7 }

gs2310pplusIGMPSnoopingstatisticV2ReportsReceived OBJECT-TYPE
   SYNTAX      Counter32
   MAX-ACCESS  read-only
   STATUS      current
   DESCRIPTION
       "The number of Received V2 Reports. "
   ::= { gs2310pplusIGMPSnoopingstatisticEntry 8 }

gs2310pplusIGMPSnoopingstatisticV3ReportsReceived OBJECT-TYPE
   SYNTAX      Counter32
   MAX-ACCESS  read-only
   STATUS      current
   DESCRIPTION
       "The number of Received V3 Reports. "
   ::= { gs2310pplusIGMPSnoopingstatisticEntry 9 }

gs2310pplusIGMPSnoopingstatisticV2LeavesReceived OBJECT-TYPE
   SYNTAX      Counter32
   MAX-ACCESS  read-only
   STATUS      current
   DESCRIPTION
       "The number of Received V2 Leaves. "
   ::= { gs2310pplusIGMPSnoopingstatisticEntry 10 }

gs2310pplusIGMPSnoopingRouterPortTable OBJECT-TYPE
   SYNTAX      SEQUENCE OF Gs2310pplusIGMPSnoopingRouterPortEntry
   MAX-ACCESS  not-accessible
   STATUS      current
   DESCRIPTION
       " Configure Vlan Port Isolation Configuration. "
   ::= { gs2310pplusIGMPSnoopingStatus 3 }

gs2310pplusIGMPSnoopingRouterPortEntry OBJECT-TYPE
   SYNTAX      Gs2310pplusIGMPSnoopingRouterPortEntry
   MAX-ACCESS  not-accessible
   STATUS      current
   DESCRIPTION
       ""
   INDEX    { ifIndex  }
   ::= { gs2310pplusIGMPSnoopingRouterPortTable 1 }

Gs2310pplusIGMPSnoopingRouterPortEntry ::= SEQUENCE {
   gs2310pplusIGMPSnoopingRouterPortStatus            DisplayString
}

gs2310pplusIGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2310pplusIGMPSnoopingRouterPortEntry 1 }

gs2310pplusIGMPSnoopingGroupsTable OBJECT-TYPE
   SYNTAX      SEQUENCE OF Gs2310pplusIGMPSnoopingGroupsEntry
   MAX-ACCESS  not-accessible
   STATUS      current
   DESCRIPTION
       "IGMP Snooping Groups Information . "
   ::= { gs2310pplusIGMPSnooping 5 }

gs2310pplusIGMPSnoopingGroupsEntry OBJECT-TYPE
   SYNTAX      Gs2310pplusIGMPSnoopingGroupsEntry
   MAX-ACCESS  not-accessible
   STATUS      current
   DESCRIPTION
       ""
   INDEX    { gs2310pplusIGMPSnoopingGroupsIndex  }
   ::= { gs2310pplusIGMPSnoopingGroupsTable 1 }

Gs2310pplusIGMPSnoopingGroupsEntry ::= SEQUENCE {
   gs2310pplusIGMPSnoopingGroupsIndex          Integer32,
   gs2310pplusIGMPSnoopingGroupsVLANID         Integer32,
   gs2310pplusIGMPSnoopingGroups               InetAddress,
   gs2310pplusIGMPSnoopingGroupsMemberships    DisplayString
}

gs2310pplusIGMPSnoopingGroupsIndex OBJECT-TYPE
   SYNTAX      Integer32(1..65535)
   MAX-ACCESS  not-accessible
   STATUS      current
   DESCRIPTION
       "IGMP Snooping Groups Index"
   ::= { gs2310pplusIGMPSnoopingGroupsEntry 1 }

gs2310pplusIGMPSnoopingGroupsVLANID OBJECT-TYPE
   SYNTAX      Integer32(1..4095)
   MAX-ACCESS  read-only
   STATUS      current
   DESCRIPTION
       "VLAN ID of the group. "
   ::= { gs2310pplusIGMPSnoopingGroupsEntry 2 }

gs2310pplusIGMPSnoopingGroups OBJECT-TYPE
   SYNTAX      DisplayString
   MAX-ACCESS  read-only
   STATUS      current
   DESCRIPTION
       "Group address of the group displayed."
   ::= { gs2310pplusIGMPSnoopingGroupsEntry 3 }

gs2310pplusIGMPSnoopingGroupsMemberships OBJECT-TYPE
   SYNTAX      DisplayString
   MAX-ACCESS  read-only
   STATUS      current
   DESCRIPTION
       "Ports under this group."
   ::= { gs2310pplusIGMPSnoopingGroupsEntry 4 }
   
gs2310pplusIGMPSnoopingSSMTable OBJECT-TYPE
   SYNTAX      SEQUENCE OF Gs2310pplusIGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2310pplusIGMPSnooping 6 }

gs2310pplusIGMPSnoopingSSMEntry OBJECT-TYPE
   SYNTAX      Gs2310pplusIGMPSnoopingSSMEntry
   MAX-ACCESS  not-accessible
   STATUS      current
   DESCRIPTION
       ""
   INDEX    { gs2310pplusIGMPSnoopingSSMIndex  }
   ::= { gs2310pplusIGMPSnoopingSSMTable 1 }

Gs2310pplusIGMPSnoopingSSMEntry ::= SEQUENCE {
   gs2310pplusIGMPSnoopingSSMIndex          Integer32,
   gs2310pplusIGMPSnoopingSSMVLANID         Integer32,
   gs2310pplusIGMPSnoopingSSMGroup          DisplayString,
   gs2310pplusIGMPSnoopingSSMPort           Integer32,
   gs2310pplusIGMPSnoopingSSMMode           DisplayString,
   gs2310pplusIGMPSnoopingSSMSourceAddress  DisplayString,
   gs2310pplusIGMPSnoopingSSMType           DisplayString
}

gs2310pplusIGMPSnoopingSSMIndex OBJECT-TYPE
   SYNTAX      Integer32(1..65535)
   MAX-ACCESS  not-accessible
   STATUS      current
   DESCRIPTION
       "IGMP Snooping SSM Index"
   ::= { gs2310pplusIGMPSnoopingSSMEntry 1 }

gs2310pplusIGMPSnoopingSSMVLANID OBJECT-TYPE
   SYNTAX      Integer32(1..4095)
   MAX-ACCESS  read-only
   STATUS      current
   DESCRIPTION
       "VLAN ID of the group. "
   ::= { gs2310pplusIGMPSnoopingSSMEntry 2 }

gs2310pplusIGMPSnoopingSSMGroup OBJECT-TYPE
   SYNTAX      DisplayString
   MAX-ACCESS  read-only
   STATUS      current
   DESCRIPTION
       "Group address of the group displayed."
   ::= { gs2310pplusIGMPSnoopingSSMEntry 3 }

gs2310pplusIGMPSnoopingSSMPort OBJECT-TYPE
   SYNTAX      Integer32(1..65535)
   MAX-ACCESS  read-only
   STATUS      current
   DESCRIPTION
       "Ports under this group."
   ::= { gs2310pplusIGMPSnoopingSSMEntry 4 }
   
gs2310pplusIGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2310pplusIGMPSnoopingSSMEntry 5 }
   
gs2310pplusIGMPSnoopingSSMSourceAddress OBJECT-TYPE
   SYNTAX      DisplayString
   MAX-ACCESS  read-only
   STATUS      current
   DESCRIPTION
       "IP Address of the source. Currently, system limits the total number of
       IP source addresses for filtering to be 128."
   ::= { gs2310pplusIGMPSnoopingSSMEntry 6 }

gs2310pplusIGMPSnoopingSSMType OBJECT-TYPE
   SYNTAX      DisplayString
   MAX-ACCESS  read-only
   STATUS      current
   DESCRIPTION
       "Indicates the Type. It can be either Allow or Deny."
   ::= { gs2310pplusIGMPSnoopingSSMEntry 7 }   

gs2310pplusMLDSnooping                                                           OBJECT IDENTIFIER ::= { gs2310pplusConfiguration 17 }

gs2310pplusMLDSnoopingBasic                                                      OBJECT IDENTIFIER ::= { gs2310pplusMLDSnooping 1 }

gs2310pplusMLDSnoopingEnable  OBJECT-TYPE
   SYNTAX      INTEGER { disable(0), enable(1) }
   MAX-ACCESS  read-write
   STATUS      current
   DESCRIPTION
       "Enable/Disable the Global MLD Snooping"
   ::= { gs2310pplusMLDSnoopingBasic 1 }

gs2310pplusMLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2310pplusMLDSnoopingBasic 2 }

gs2310pplusMLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2310pplusMLDSnoopingBasic 3 }
   
gs2310pplusMLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2310pplusMLDSnoopingBasic 4 }

gs2310pplusMLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2310pplusMLDSnoopingBasic 5 }

gs2310pplusMLDSnoopingPortRelatedTable OBJECT-TYPE
   SYNTAX      SEQUENCE OF Gs2310pplusMLDSnoopingPortRelatedEntry
   MAX-ACCESS  not-accessible
   STATUS      current
   DESCRIPTION
       " Configure MLD Snooping Port Related Configuration. "
   ::= { gs2310pplusMLDSnoopingBasic 6 }

gs2310pplusMLDSnoopingPortRelatedEntry OBJECT-TYPE
   SYNTAX      Gs2310pplusMLDSnoopingPortRelatedEntry
   MAX-ACCESS  not-accessible
   STATUS      current
   DESCRIPTION
       ""
   INDEX    { ifIndex  }
   ::= { gs2310pplusMLDSnoopingPortRelatedTable 1 }

Gs2310pplusMLDSnoopingPortRelatedEntry ::= SEQUENCE {
   gs2310pplusMLDSnoopingRouterPort	INTEGER,
   gs2310pplusMLDSnoopingFastLeave  	INTEGER,
   gs2310pplusMLDSnoopingThrottling    Integer32
}

gs2310pplusMLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2310pplusMLDSnoopingPortRelatedEntry 1 }

gs2310pplusMLDSnoopingFastLeave OBJECT-TYPE
   SYNTAX      INTEGER { disable(0), enable(1) }
   MAX-ACCESS  read-write
   STATUS      current
   DESCRIPTION
       "Enable/Disable the fast leave on the port. "
   ::= { gs2310pplusMLDSnoopingPortRelatedEntry 2 }
   
gs2310pplusMLDSnoopingThrottling OBJECT-TYPE
   SYNTAX      Integer32(0..10)
   MAX-ACCESS  read-write
   STATUS      current
   DESCRIPTION
       "Enable to limit the number of multicast groups to which a switch port can belong.
       0: unlimited"
   ::= { gs2310pplusMLDSnoopingPortRelatedEntry 3 }
   
gs2310pplusMLDSnoopingVLANTable OBJECT-TYPE
   SYNTAX      SEQUENCE OF Gs2310pplusMLDSnoopingVLANEntry
   MAX-ACCESS  not-accessible
   STATUS      current
   DESCRIPTION
       " Configure MLD Snooping Vlan Configuration. "
   ::= { gs2310pplusMLDSnooping 2 }

gs2310pplusMLDSnoopingVLANEntry OBJECT-TYPE
   SYNTAX      Gs2310pplusMLDSnoopingVLANEntry
   MAX-ACCESS  not-accessible
   STATUS      current
   DESCRIPTION
       ""
   INDEX    { gs2310pplusMLDSnoopingVLANID  }
   ::= { gs2310pplusMLDSnoopingVLANTable 1 }

Gs2310pplusMLDSnoopingVLANEntry ::= SEQUENCE {
   gs2310pplusMLDSnoopingVLANID        	Integer32,
   gs2310pplusMLDSnoopingVLANEnable    	INTEGER,
   gs2310pplusMLDSnoopingVLANIGMPQuerier   INTEGER,
   gs2310pplusMLDSnoopingVLANCompatibility INTEGER,
   gs2310pplusMLDSnoopingVLANRV        	Integer32,
   gs2310pplusMLDSnoopingVLANQI      	    Integer32,
   gs2310pplusMLDSnoopingVLANQRI   	    Integer32,
   gs2310pplusMLDSnoopingVLANLLQI   	    Integer32,
   gs2310pplusMLDSnoopingVLANURI    	    Integer32
}

gs2310pplusMLDSnoopingVLANID OBJECT-TYPE
   SYNTAX      Integer32(1..4095)
   MAX-ACCESS  read-write
   STATUS      current
   DESCRIPTION
       "The VLAN ID of the entry"
   ::= { gs2310pplusMLDSnoopingVLANEntry 1 }

gs2310pplusMLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2310pplusMLDSnoopingVLANEntry 2 }

gs2310pplusMLDSnoopingVLANIGMPQuerier OBJECT-TYPE
   SYNTAX      INTEGER { disable(0), enable(1) }
   MAX-ACCESS  read-write
   STATUS      current
   DESCRIPTION
       "Enable/Disable the MLD Querier in the VLAN. "
   ::= { gs2310pplusMLDSnoopingVLANEntry 3 }

gs2310pplusMLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2310pplusMLDSnoopingVLANEntry 4 }
   
gs2310pplusMLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2310pplusMLDSnoopingVLANEntry 5 }
   
gs2310pplusMLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2310pplusMLDSnoopingVLANEntry 6 }
   
gs2310pplusMLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2310pplusMLDSnoopingVLANEntry 7 }
   
gs2310pplusMLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2310pplusMLDSnoopingVLANEntry 8 }

gs2310pplusMLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2310pplusMLDSnoopingVLANEntry 9 }

gs2310pplusMLDSnoopingPortGroupFiltering                                                      OBJECT IDENTIFIER ::= { gs2310pplusMLDSnooping 3 }

gs2310pplusMLDSnoopingPortGroupFilteringCreate OBJECT-TYPE
   SYNTAX       Integer32
   MAX-ACCESS   read-write
   STATUS       current
   DESCRIPTION
       "default: 0
       0 : None  (read only) 1 : Create MLD Snooping Port Group Filtering "
   ::= { gs2310pplusMLDSnoopingPortGroupFiltering 1 }

gs2310pplusMLDSnoopingPortGroupFilteringTable OBJECT-TYPE
   SYNTAX      SEQUENCE OF Gs2310pplusMLDSnoopingPortGroupFilteringEntry
   MAX-ACCESS  not-accessible
   STATUS      current
   DESCRIPTION
       " Configure MLD Snooping port group filtering. "
   ::= { gs2310pplusMLDSnoopingPortGroupFiltering 2 }

gs2310pplusMLDSnoopingPortGroupFilteringEntry OBJECT-TYPE
   SYNTAX      Gs2310pplusMLDSnoopingPortGroupFilteringEntry
   MAX-ACCESS  not-accessible
   STATUS      current
   DESCRIPTION
       ""
   INDEX    { gs2310pplusMLDSnoopingPortGroupFilteringIndex  }
   ::= { gs2310pplusMLDSnoopingPortGroupFilteringTable 1 }

Gs2310pplusMLDSnoopingPortGroupFilteringEntry ::= SEQUENCE {
   gs2310pplusMLDSnoopingPortGroupFilteringIndex         Integer32,
   gs2310pplusMLDSnoopingPortGroupFilteringPort          Integer32,
   gs2310pplusMLDSnoopingPortGroupFilteringGroups        DisplayString,
   gs2310pplusMLDSnoopingPortGroupFilteringRowStatus     INTEGER
}

gs2310pplusMLDSnoopingPortGroupFilteringIndex OBJECT-TYPE
   SYNTAX      Integer32(1..65535)
   MAX-ACCESS  not-accessible
   STATUS      current
   DESCRIPTION
       "MLD Snooping Port Group Filtering Configuration Index. "
   ::= { gs2310pplusMLDSnoopingPortGroupFilteringEntry 1 }

gs2310pplusMLDSnoopingPortGroupFilteringPort OBJECT-TYPE
   SYNTAX      Integer32(1..65535)
   MAX-ACCESS  read-write
   STATUS      current
   DESCRIPTION
       "The logical port for the settings. "
   ::= { gs2310pplusMLDSnoopingPortGroupFilteringEntry 2 }

gs2310pplusMLDSnoopingPortGroupFilteringGroups OBJECT-TYPE
   SYNTAX      DisplayString
   MAX-ACCESS  read-write
   STATUS      current
   DESCRIPTION
       "The IP Multicast Group that will be filtered. "
   ::= { gs2310pplusMLDSnoopingPortGroupFilteringEntry 3 }

gs2310pplusMLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2310pplusMLDSnoopingPortGroupFilteringEntry 4 }

gs2310pplusMLDSnoopingStatus                                                      OBJECT IDENTIFIER ::= { gs2310pplusMLDSnooping 4 }

gs2310pplusMLDSnoopingstatisticClear OBJECT-TYPE
   SYNTAX      INTEGER { none(0), clear(1)}
   MAX-ACCESS  read-write
   STATUS      current
   DESCRIPTION
       "Clears all Statistics counters."
   ::= { gs2310pplusMLDSnoopingStatus 1 }


gs2310pplusMLDSnoopingstatisticTable OBJECT-TYPE
   SYNTAX      SEQUENCE OF Gs2310pplusMLDSnoopingstatisticEntry
   MAX-ACCESS  not-accessible
   STATUS      current
   DESCRIPTION
       " Configure Vlan Port Isolation Configuration. "
   ::= { gs2310pplusMLDSnoopingStatus 2 }

gs2310pplusMLDSnoopingstatisticEntry OBJECT-TYPE
   SYNTAX      Gs2310pplusMLDSnoopingstatisticEntry
   MAX-ACCESS  not-accessible
   STATUS      current
   DESCRIPTION
       ""
   INDEX    { gs2310pplusMLDSnoopingstatisticVLANID  }
   ::= { gs2310pplusMLDSnoopingstatisticTable 1 }

Gs2310pplusMLDSnoopingstatisticEntry ::= SEQUENCE {
   gs2310pplusMLDSnoopingstatisticVLANID              Integer32,
   gs2310pplusMLDSnoopingstatisticQuerierVersion      DisplayString,
   gs2310pplusMLDSnoopingstatisticHostVersion         DisplayString,
   gs2310pplusMLDSnoopingstatisticQuerierStatus       DisplayString,
   gs2310pplusMLDSnoopingstatisticQueriesTransmitted  Counter32,
   gs2310pplusMLDSnoopingstatisticQueriesReceived     Counter32,
   gs2310pplusMLDSnoopingstatisticV1ReportsReceived   Counter32,
   gs2310pplusMLDSnoopingstatisticV2ReportsReceived   Counter32,
   gs2310pplusMLDSnoopingstatisticV1LeavesReceived    Counter32
}


gs2310pplusMLDSnoopingstatisticVLANID OBJECT-TYPE
   SYNTAX      Integer32(1..4095)
   MAX-ACCESS  read-only
   STATUS      current
   DESCRIPTION
       "The VLAN ID of the entry. "
   ::= { gs2310pplusMLDSnoopingstatisticEntry 1 }

gs2310pplusMLDSnoopingstatisticQuerierVersion OBJECT-TYPE
   SYNTAX      DisplayString
   MAX-ACCESS  read-only
   STATUS      current
   DESCRIPTION
       "Working Querier Version currently. "
   ::= { gs2310pplusMLDSnoopingstatisticEntry 2 }
   
gs2310pplusMLDSnoopingstatisticHostVersion OBJECT-TYPE
   SYNTAX      DisplayString
   MAX-ACCESS  read-only
   STATUS      current
   DESCRIPTION
       "Working Host Version currently. "
   ::= { gs2310pplusMLDSnoopingstatisticEntry 3 }

gs2310pplusMLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2310pplusMLDSnoopingstatisticEntry 4 }

gs2310pplusMLDSnoopingstatisticQueriesTransmitted OBJECT-TYPE
   SYNTAX      Counter32
   MAX-ACCESS  read-only
   STATUS      current
   DESCRIPTION
       "The number of Transmitted Queries. "
   ::= { gs2310pplusMLDSnoopingstatisticEntry 5 }

gs2310pplusMLDSnoopingstatisticQueriesReceived OBJECT-TYPE
   SYNTAX      Counter32
   MAX-ACCESS  read-only
   STATUS      current
   DESCRIPTION
       "The number of Received Queries. "
   ::= { gs2310pplusMLDSnoopingstatisticEntry 6 }

gs2310pplusMLDSnoopingstatisticV1ReportsReceived OBJECT-TYPE
   SYNTAX      Counter32
   MAX-ACCESS  read-only
   STATUS      current
   DESCRIPTION
       "The number of Received V1 Reports. "
   ::= { gs2310pplusMLDSnoopingstatisticEntry 7 }

gs2310pplusMLDSnoopingstatisticV2ReportsReceived OBJECT-TYPE
   SYNTAX      Counter32
   MAX-ACCESS  read-only
   STATUS      current
   DESCRIPTION
       "The number of Received V2 Reports. "
   ::= { gs2310pplusMLDSnoopingstatisticEntry 8 }

gs2310pplusMLDSnoopingstatisticV1LeavesReceived OBJECT-TYPE
   SYNTAX      Counter32
   MAX-ACCESS  read-only
   STATUS      current
   DESCRIPTION
       "The number of Received V1 Leaves. "
   ::= { gs2310pplusMLDSnoopingstatisticEntry 9 }

gs2310pplusMLDSnoopingRouterPortTable OBJECT-TYPE
   SYNTAX      SEQUENCE OF Gs2310pplusMLDSnoopingRouterPortEntry
   MAX-ACCESS  not-accessible
   STATUS      current
   DESCRIPTION
       " Configure Vlan Port Isolation Configuration. "
   ::= { gs2310pplusMLDSnoopingStatus 3 }

gs2310pplusMLDSnoopingRouterPortEntry OBJECT-TYPE
   SYNTAX      Gs2310pplusMLDSnoopingRouterPortEntry
   MAX-ACCESS  not-accessible
   STATUS      current
   DESCRIPTION
       ""
   INDEX    { ifIndex  }
   ::= { gs2310pplusMLDSnoopingRouterPortTable 1 }

Gs2310pplusMLDSnoopingRouterPortEntry ::= SEQUENCE {
   gs2310pplusMLDSnoopingRouterPortStatus            DisplayString
}

gs2310pplusMLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2310pplusMLDSnoopingRouterPortEntry 1 }

gs2310pplusMLDSnoopingGroupsTable OBJECT-TYPE
   SYNTAX      SEQUENCE OF Gs2310pplusMLDSnoopingGroupsEntry
   MAX-ACCESS  not-accessible
   STATUS      current
   DESCRIPTION
       "MLD Snooping Groups Information . "
   ::= { gs2310pplusMLDSnooping 5 }

gs2310pplusMLDSnoopingGroupsEntry OBJECT-TYPE
   SYNTAX      Gs2310pplusMLDSnoopingGroupsEntry
   MAX-ACCESS  not-accessible
   STATUS      current
   DESCRIPTION
       ""
   INDEX    { gs2310pplusMLDSnoopingGroupsIndex  }
   ::= { gs2310pplusMLDSnoopingGroupsTable 1 }

Gs2310pplusMLDSnoopingGroupsEntry ::= SEQUENCE {
   gs2310pplusMLDSnoopingGroupsIndex          Integer32,
   gs2310pplusMLDSnoopingGroupsVLANID         Integer32,
   gs2310pplusMLDSnoopingGroups               InetAddress,
   gs2310pplusMLDSnoopingGroupsMemberships    DisplayString
}

gs2310pplusMLDSnoopingGroupsIndex OBJECT-TYPE
   SYNTAX      Integer32(1..65535)
   MAX-ACCESS  not-accessible
   STATUS      current
   DESCRIPTION
       "MLD Snooping Groups Index"
   ::= { gs2310pplusMLDSnoopingGroupsEntry 1 }

gs2310pplusMLDSnoopingGroupsVLANID OBJECT-TYPE
   SYNTAX      Integer32(1..4095)
   MAX-ACCESS  read-only
   STATUS      current
   DESCRIPTION
       "VLAN ID of the group. "
   ::= { gs2310pplusMLDSnoopingGroupsEntry 2 }

gs2310pplusMLDSnoopingGroups OBJECT-TYPE
   SYNTAX      DisplayString
   MAX-ACCESS  read-only
   STATUS      current
   DESCRIPTION
       "Group address of the group displayed."
   ::= { gs2310pplusMLDSnoopingGroupsEntry 3 }

gs2310pplusMLDSnoopingGroupsMemberships OBJECT-TYPE
   SYNTAX      DisplayString
   MAX-ACCESS  read-only
   STATUS      current
   DESCRIPTION
       "Ports under this group."
   ::= { gs2310pplusMLDSnoopingGroupsEntry 4 }
   
gs2310pplusMLDSnoopingSSMTable OBJECT-TYPE
   SYNTAX      SEQUENCE OF Gs2310pplusMLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2310pplusMLDSnooping 6 }

gs2310pplusMLDSnoopingSSMEntry OBJECT-TYPE
   SYNTAX      Gs2310pplusMLDSnoopingSSMEntry
   MAX-ACCESS  not-accessible
   STATUS      current
   DESCRIPTION
       ""
   INDEX    { gs2310pplusMLDSnoopingSSMIndex  }
   ::= { gs2310pplusMLDSnoopingSSMTable 1 }

Gs2310pplusMLDSnoopingSSMEntry ::= SEQUENCE {
   gs2310pplusMLDSnoopingSSMIndex          Integer32,
   gs2310pplusMLDSnoopingSSMVLANID         Integer32,
   gs2310pplusMLDSnoopingSSMGroup          DisplayString,
   gs2310pplusMLDSnoopingSSMPort           Integer32,
   gs2310pplusMLDSnoopingSSMMode           DisplayString,
   gs2310pplusMLDSnoopingSSMSourceAddress  DisplayString,
   gs2310pplusMLDSnoopingSSMType           DisplayString
}

gs2310pplusMLDSnoopingSSMIndex OBJECT-TYPE
   SYNTAX      Integer32(1..65535)
   MAX-ACCESS  not-accessible
   STATUS      current
   DESCRIPTION
       "MLD Snooping SSM Index"
   ::= { gs2310pplusMLDSnoopingSSMEntry 1 }

gs2310pplusMLDSnoopingSSMVLANID OBJECT-TYPE
   SYNTAX      Integer32(1..4095)
   MAX-ACCESS  read-only
   STATUS      current
   DESCRIPTION
       "VLAN ID of the group. "
   ::= { gs2310pplusMLDSnoopingSSMEntry 2 }

gs2310pplusMLDSnoopingSSMGroup OBJECT-TYPE
   SYNTAX      DisplayString
   MAX-ACCESS  read-only
   STATUS      current
   DESCRIPTION
       "Group address of the group displayed."
   ::= { gs2310pplusMLDSnoopingSSMEntry 3 }

gs2310pplusMLDSnoopingSSMPort OBJECT-TYPE
   SYNTAX      Integer32(1..65535)
   MAX-ACCESS  read-only
   STATUS      current
   DESCRIPTION
       "Ports under this group."
   ::= { gs2310pplusMLDSnoopingSSMEntry 4 }
   
gs2310pplusMLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2310pplusMLDSnoopingSSMEntry 5 }
   
gs2310pplusMLDSnoopingSSMSourceAddress OBJECT-TYPE
   SYNTAX      DisplayString
   MAX-ACCESS  read-only
   STATUS      current
   DESCRIPTION
       "IP Address of the source. Currently, system limits the total number of
       IP source addresses for filtering to be 128."
   ::= { gs2310pplusMLDSnoopingSSMEntry 6 }

gs2310pplusMLDSnoopingSSMType OBJECT-TYPE
   SYNTAX      DisplayString
   MAX-ACCESS  read-only
   STATUS      current
   DESCRIPTION
       "Indicates the Type. It can be either Allow or Deny."
   ::= { gs2310pplusMLDSnoopingSSMEntry 7 }      
   

gs2310pplusMVR                                                                   OBJECT IDENTIFIER ::= { gs2310pplusConfiguration 18 }

gs2310pplusMVRConfiguration                                                      OBJECT IDENTIFIER ::= { gs2310pplusMVR 1 }

gs2310pplusMVRMode  OBJECT-TYPE
   SYNTAX      INTEGER { disable(0), enable(1) }
   MAX-ACCESS  read-write
   STATUS      current
   DESCRIPTION
       "Enable/Disable the Global MVR. "
   ::= { gs2310pplusMVRConfiguration 1 }

gs2310pplusMVRVLANId  OBJECT-TYPE
   SYNTAX      Integer32(1..4094)
   MAX-ACCESS  read-write
   STATUS      current
   DESCRIPTION
       "Specify the Multicast VLAN ID. "
   ::= { gs2310pplusMVRConfiguration 2 }

gs2310pplusMVRPortConfigurationTable OBJECT-TYPE
   SYNTAX      SEQUENCE OF Gs2310pplusMVRPortConfigurationEntry
   MAX-ACCESS  not-accessible
   STATUS      current
   DESCRIPTION
       " Configure MVR Port Configuration. "
   ::= { gs2310pplusMVRConfiguration 3 }

gs2310pplusMVRPortConfigurationEntry OBJECT-TYPE
   SYNTAX      Gs2310pplusMVRPortConfigurationEntry
   MAX-ACCESS  not-accessible
   STATUS      current
   DESCRIPTION
       ""
   INDEX    { ifIndex  }
   ::= { gs2310pplusMVRPortConfigurationTable 1 }

Gs2310pplusMVRPortConfigurationEntry ::= SEQUENCE {
   gs2310pplusMVRPortConfigurationMode	INTEGER,
   gs2310pplusMVRPortConfigurationType  	INTEGER,
   gs2310pplusMVRPortConfigurationImmediateLeave    INTEGER
}

gs2310pplusMVRPortConfigurationMode OBJECT-TYPE
   SYNTAX      INTEGER { disable(0), enable(1) }
   MAX-ACCESS  read-write
   STATUS      current
   DESCRIPTION
       "Enable MVR on the port. "
   ::= { gs2310pplusMVRPortConfigurationEntry 1 }

gs2310pplusMVRPortConfigurationType OBJECT-TYPE
   SYNTAX      INTEGER { receiver(0), source(1) }
   MAX-ACCESS  read-write
   STATUS      current
   DESCRIPTION
       "Specify the MVR port type on the port. "
   ::= { gs2310pplusMVRPortConfigurationEntry 2 }
   
gs2310pplusMVRPortConfigurationImmediateLeave OBJECT-TYPE
   SYNTAX      INTEGER { disable(0), enable(1) }
   MAX-ACCESS  read-write
   STATUS      current
   DESCRIPTION
       "Enable the fast leave on the port. "
   ::= { gs2310pplusMVRPortConfigurationEntry 3 }
      

gs2310pplusMVRPortGroupFiltering                                                      OBJECT IDENTIFIER ::= { gs2310pplusMVR 2 }

gs2310pplusMVRPortGroupFilteringCreate OBJECT-TYPE
   SYNTAX       Integer32
   MAX-ACCESS   read-write
   STATUS       current
   DESCRIPTION
       "default: 0
       0 : None  (read only) 1 : Create MLD Snooping Port Group Filtering "
   ::= { gs2310pplusMVRPortGroupFiltering 1 }

gs2310pplusMVRPortGroupFilteringTable OBJECT-TYPE
   SYNTAX      SEQUENCE OF Gs2310pplusMVRPortGroupFilteringEntry
   MAX-ACCESS  not-accessible
   STATUS      current
   DESCRIPTION
       " Configure MVR port group filtering. "
   ::= { gs2310pplusMVRPortGroupFiltering 2 }

gs2310pplusMVRPortGroupFilteringEntry OBJECT-TYPE
   SYNTAX      Gs2310pplusMVRPortGroupFilteringEntry
   MAX-ACCESS  not-accessible
   STATUS      current
   DESCRIPTION
       ""
   INDEX    { gs2310pplusMVRPortGroupFilteringIndex  }
   ::= { gs2310pplusMVRPortGroupFilteringTable 1 }

Gs2310pplusMVRPortGroupFilteringEntry ::= SEQUENCE {
   gs2310pplusMVRPortGroupFilteringIndex         Integer32,
   gs2310pplusMVRPortGroupFilteringPort          Integer32,
   gs2310pplusMVRPortGroupFilteringStartGroups   DisplayString,
   gs2310pplusMVRPortGroupFilteringEndGroups     DisplayString,
   gs2310pplusMVRPortGroupFilteringRowStatus     INTEGER
}

gs2310pplusMVRPortGroupFilteringIndex OBJECT-TYPE
   SYNTAX      Integer32(1..65535)
   MAX-ACCESS  not-accessible
   STATUS      current
   DESCRIPTION
       "MVR Port Group Filtering Configuration Index. "
   ::= { gs2310pplusMVRPortGroupFilteringEntry 1 }

gs2310pplusMVRPortGroupFilteringPort OBJECT-TYPE
   SYNTAX      Integer32(1..65535)
   MAX-ACCESS  read-write
   STATUS      current
   DESCRIPTION
       "The logical port for the settings. "
   ::= { gs2310pplusMVRPortGroupFilteringEntry 2 }

gs2310pplusMVRPortGroupFilteringStartGroups OBJECT-TYPE
   SYNTAX      DisplayString
   MAX-ACCESS  read-write
   STATUS      current
   DESCRIPTION
       "The IP Multicast Group that will be allowed. "
   ::= { gs2310pplusMVRPortGroupFilteringEntry 3 }

gs2310pplusMVRPortGroupFilteringEndGroups OBJECT-TYPE
   SYNTAX      DisplayString
   MAX-ACCESS  read-write
   STATUS      current
   DESCRIPTION
       "The IP Multicast Group that will be allowed. "
   ::= { gs2310pplusMVRPortGroupFilteringEntry 4 }   

gs2310pplusMVRPortGroupFilteringRowStatus OBJECT-TYPE
   SYNTAX      INTEGER { active(1), notInservice(2), destroy(4)}
   MAX-ACCESS  read-write
   STATUS      current
   DESCRIPTION
       "1: active
        2: notInservice
        4: destroy"
   ::= { gs2310pplusMVRPortGroupFilteringEntry 5 }

gs2310pplusMVRGroupsTable OBJECT-TYPE
   SYNTAX      SEQUENCE OF Gs2310pplusMVRGroupsEntry
   MAX-ACCESS  not-accessible
   STATUS      current
   DESCRIPTION
       "MVR Groups Information . "
   ::= { gs2310pplusMVR 3 }

gs2310pplusMVRGroupsEntry OBJECT-TYPE
   SYNTAX      Gs2310pplusMVRGroupsEntry
   MAX-ACCESS  not-accessible
   STATUS      current
   DESCRIPTION
       ""
   INDEX    { gs2310pplusMVRGroupsIndex  }
   ::= { gs2310pplusMVRGroupsTable 1 }

Gs2310pplusMVRGroupsEntry ::= SEQUENCE {
   gs2310pplusMVRGroupsIndex          Integer32,
   gs2310pplusMVRGroupsVLANID         Integer32,
   gs2310pplusMVRGroups               InetAddress,
   gs2310pplusMVRGroupsMemberships    DisplayString
}

gs2310pplusMVRGroupsIndex OBJECT-TYPE
   SYNTAX      Integer32(1..65535)
   MAX-ACCESS  not-accessible
   STATUS      current
   DESCRIPTION
       "MVR Groups Index"
   ::= { gs2310pplusMVRGroupsEntry 1 }

gs2310pplusMVRGroupsVLANID OBJECT-TYPE
   SYNTAX      Integer32(1..4095)
   MAX-ACCESS  read-only
   STATUS      current
   DESCRIPTION
       "VLAN ID of the group. "
   ::= { gs2310pplusMVRGroupsEntry 2 }

gs2310pplusMVRGroups OBJECT-TYPE
   SYNTAX      DisplayString
   MAX-ACCESS  read-only
   STATUS      current
   DESCRIPTION
       "Group address of the group displayed."
   ::= { gs2310pplusMVRGroupsEntry 3 }

gs2310pplusMVRGroupsMemberships OBJECT-TYPE
   SYNTAX      DisplayString
   MAX-ACCESS  read-only
   STATUS      current
   DESCRIPTION
       "Ports under this group."
   ::= { gs2310pplusMVRGroupsEntry 4 }
            

gs2310pplusMVRStatus                                                      OBJECT IDENTIFIER ::= { gs2310pplusMVR 4 }

gs2310pplusMVRstatisticClear OBJECT-TYPE
   SYNTAX      INTEGER { none(0), clear(1)}
   MAX-ACCESS  read-write
   STATUS      current
   DESCRIPTION
       "Clears all Statistics counters."
   ::= { gs2310pplusMVRStatus 1 }

gs2310pplusMVRstatisticVLANID OBJECT-TYPE
   SYNTAX      Integer32(1..4095)
   MAX-ACCESS  read-only
   STATUS      current
   DESCRIPTION
       "The VLAN ID of the entry. "
   ::= { gs2310pplusMVRStatus 2 }

gs2310pplusMVRstatisticV1ReportsReceived OBJECT-TYPE
   SYNTAX      Counter32
   MAX-ACCESS  read-only
   STATUS      current
   DESCRIPTION
       "The number of Received V1 Reports. "
   ::= { gs2310pplusMVRStatus 3 }

gs2310pplusMVRstatisticV2ReportsReceived OBJECT-TYPE
   SYNTAX      Counter32
   MAX-ACCESS  read-only
   STATUS      current
   DESCRIPTION
       "The number of Received V2 Reports. "
   ::= { gs2310pplusMVRStatus 4 }
   
gs2310pplusMVRstatisticV3ReportsReceived OBJECT-TYPE
   SYNTAX      Counter32
   MAX-ACCESS  read-only
   STATUS      current
   DESCRIPTION
       "The number of Received V3 Reports. "
   ::= { gs2310pplusMVRStatus 5 }

gs2310pplusMVRstatisticV2LeavesReceived OBJECT-TYPE
   SYNTAX      Counter32
   MAX-ACCESS  read-only
   STATUS      current
   DESCRIPTION
       "The number of Received V2 Leaves. "
   ::= { gs2310pplusMVRStatus 6 }


gs2310pplusLACP                                                     OBJECT IDENTIFIER ::= { gs2310pplusConfiguration 19 }

gs2310pplusLACPConf                                                 OBJECT IDENTIFIER ::= { gs2310pplusLACP 1 }

gs2310pplusLACPPortConfigurationTable OBJECT-TYPE
   SYNTAX      SEQUENCE OF Gs2310pplusLACPPortConfigurationEntry
   MAX-ACCESS  not-accessible
   STATUS      current
   DESCRIPTION
       " "
   ::= { gs2310pplusLACPConf 1 }

gs2310pplusLACPPortConfigurationEntry OBJECT-TYPE
   SYNTAX      Gs2310pplusLACPPortConfigurationEntry
   MAX-ACCESS  not-accessible
   STATUS      current
   DESCRIPTION
       ""
   INDEX    { gs2310pplusLACPPortConfigurationPort  }
   ::= { gs2310pplusLACPPortConfigurationTable 1 }
   
Gs2310pplusLACPPortConfigurationEntry ::= SEQUENCE {
    gs2310pplusLACPPortConfigurationPort         Integer32,
    gs2310pplusLACPPortConfigurationMode         INTEGER,
    gs2310pplusLACPPortConfigurationKey          Integer32,
    gs2310pplusLACPPortConfigurationRole         INTEGER
}

gs2310pplusLACPPortConfigurationPort OBJECT-TYPE
   SYNTAX      Integer32(1..4095)
   MAX-ACCESS  not-accessible
   STATUS      current
   DESCRIPTION
       " "
   ::= { gs2310pplusLACPPortConfigurationEntry 1 }

gs2310pplusLACPPortConfigurationMode OBJECT-TYPE
   SYNTAX      INTEGER { disable(0), enable(1) }
   MAX-ACCESS  read-write
   STATUS      current
   DESCRIPTION
       "Enable/Disable LACP Mode."
   ::= { gs2310pplusLACPPortConfigurationEntry 2 }
   
gs2310pplusLACPPortConfigurationKey OBJECT-TYPE
   SYNTAX      Integer32(0..65535)
   MAX-ACCESS  read-write
   STATUS      current
   DESCRIPTION
       "LACP key : 1-65535. 0 : Auto"
   ::= { gs2310pplusLACPPortConfigurationEntry 3 }
   
gs2310pplusLACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2310pplusLACPPortConfigurationEntry 4 }

gs2310pplusLACPSystemStatusTable OBJECT-TYPE
   SYNTAX      SEQUENCE OF Gs2310pplusLACPSystemStatusEntry
   MAX-ACCESS  not-accessible
   STATUS      current
   DESCRIPTION
       " "
   ::= { gs2310pplusLACP 2 }

gs2310pplusLACPSystemStatusEntry OBJECT-TYPE
   SYNTAX      Gs2310pplusLACPSystemStatusEntry
   MAX-ACCESS  not-accessible
   STATUS      current
   DESCRIPTION
       ""
   INDEX    { gs2310pplusLACPSystemStatusIndex  }
   ::= { gs2310pplusLACPSystemStatusTable 1 }

Gs2310pplusLACPSystemStatusEntry ::= SEQUENCE {
   gs2310pplusLACPSystemStatusIndex             Integer32,
   gs2310pplusLACPSystemStatusAggrID            DisplayString,
   gs2310pplusLACPSystemStatusPartnerSystemID   MacAddress,
   gs2310pplusLACPSystemStatusPartnerKey        DisplayString,
   gs2310pplusLACPSystemStatusLastchanged       DisplayString,
   gs2310pplusLACPSystemStatusLocalPorts        DisplayString
}

gs2310pplusLACPSystemStatusIndex OBJECT-TYPE
   SYNTAX      Integer32(1..12)
   MAX-ACCESS  not-accessible
   STATUS      current
   DESCRIPTION
       " "
   ::= { gs2310pplusLACPSystemStatusEntry 1 }

gs2310pplusLACPSystemStatusAggrID OBJECT-TYPE
   SYNTAX      DisplayString
   MAX-ACCESS  read-only
   STATUS      current
   DESCRIPTION
       "The Aggregation ID associated with this aggregation instance."
   ::= { gs2310pplusLACPSystemStatusEntry 2 }
   
gs2310pplusLACPSystemStatusPartnerSystemID OBJECT-TYPE
   SYNTAX      MacAddress
   MAX-ACCESS  read-only
   STATUS      current
   DESCRIPTION
       "The system ID (MAC address) of the aggregation partner."
   ::= { gs2310pplusLACPSystemStatusEntry 3 }

gs2310pplusLACPSystemStatusPartnerKey OBJECT-TYPE
   SYNTAX      DisplayString
   MAX-ACCESS  read-only
   STATUS      current
   DESCRIPTION
       " The Key that the partner has assigned to this aggregation ID. "
   ::= { gs2310pplusLACPSystemStatusEntry 4 }

gs2310pplusLACPSystemStatusLastchanged OBJECT-TYPE
   SYNTAX      DisplayString
   MAX-ACCESS  read-only
   STATUS      current
   DESCRIPTION
       " The time since this aggregation changed. "
   ::= { gs2310pplusLACPSystemStatusEntry 5 }
   
gs2310pplusLACPSystemStatusLocalPorts OBJECT-TYPE
   SYNTAX      DisplayString
   MAX-ACCESS  read-only
   STATUS      current
   DESCRIPTION
       " Shows which ports are a part of this aggregation for this switch. "
   ::= { gs2310pplusLACPSystemStatusEntry 6 }

gs2310pplusLACPStatusTable OBJECT-TYPE
   SYNTAX      SEQUENCE OF Gs2310pplusLACPStatusEntry
   MAX-ACCESS  not-accessible
   STATUS      current
   DESCRIPTION
       " "
   ::= { gs2310pplusLACP 3 }

gs2310pplusLACPStatusEntry OBJECT-TYPE
   SYNTAX      Gs2310pplusLACPStatusEntry
   MAX-ACCESS  not-accessible
   STATUS      current
   DESCRIPTION
       ""
   INDEX    { gs2310pplusLACPStatusPort  }
   ::= { gs2310pplusLACPStatusTable 1 }

Gs2310pplusLACPStatusEntry ::= SEQUENCE {
   gs2310pplusLACPStatusPort                Integer32,
   gs2310pplusLACPStatusLACP                DisplayString,
   gs2310pplusLACPStatusKey                 DisplayString,
   gs2310pplusLACPStatusAggrID              DisplayString,
   gs2310pplusLACPStatusPartnerSystemID     DisplayString,
   gs2310pplusLACPStatusPartnerPort         DisplayString
}

gs2310pplusLACPStatusPort OBJECT-TYPE
   SYNTAX      Integer32(1..4095)
   MAX-ACCESS  not-accessible
   STATUS      current
   DESCRIPTION
       " "
   ::= { gs2310pplusLACPStatusEntry 1 }

gs2310pplusLACPStatusLACP OBJECT-TYPE
   SYNTAX      DisplayString
   MAX-ACCESS  read-only
   STATUS      current
   DESCRIPTION
       "Enabled means that LACP is enabled and the port link is up. 
        Disabled means that LACP is not enabled or that the port link is down. 
        Backup means that the port could not join the aggregation group but will join if other port leaves. 
        Meanwhile it's LACP status is disabled."
   ::= { gs2310pplusLACPStatusEntry 2 }
   
gs2310pplusLACPStatusKey OBJECT-TYPE
   SYNTAX      DisplayString
   MAX-ACCESS  read-only
   STATUS      current
   DESCRIPTION
       "The key assigned to this port. Only ports with the same key can aggregate together."
   ::= { gs2310pplusLACPStatusEntry 3 }

gs2310pplusLACPStatusAggrID	 OBJECT-TYPE
   SYNTAX      DisplayString
   MAX-ACCESS  read-only
   STATUS      current
   DESCRIPTION
       " The Aggregation ID assigned to this aggregation group. "
   ::= { gs2310pplusLACPStatusEntry 4 }

gs2310pplusLACPStatusPartnerSystemID OBJECT-TYPE
   SYNTAX      DisplayString
   MAX-ACCESS  read-only
   STATUS      current
   DESCRIPTION
       " The partner's System ID. "
   ::= { gs2310pplusLACPStatusEntry 5 }
   
gs2310pplusLACPStatusPartnerPort OBJECT-TYPE
   SYNTAX      DisplayString
   MAX-ACCESS  read-only
   STATUS      current
   DESCRIPTION
       " The partner's port number connected to this port. "
   ::= { gs2310pplusLACPStatusEntry 6 }


gs2310pplusLACPStatisticsTable OBJECT-TYPE
   SYNTAX      SEQUENCE OF Gs2310pplusLACPStatisticsEntry
   MAX-ACCESS  not-accessible
   STATUS      current
   DESCRIPTION
       " "
   ::= { gs2310pplusLACP 4 }

gs2310pplusLACPStatisticsEntry OBJECT-TYPE
   SYNTAX      Gs2310pplusLACPStatisticsEntry
   MAX-ACCESS  not-accessible
   STATUS      current
   DESCRIPTION
       ""
   INDEX    { gs2310pplusLACPStatisticsPort  }
   ::= { gs2310pplusLACPStatisticsTable 1 }

Gs2310pplusLACPStatisticsEntry ::= SEQUENCE {
   gs2310pplusLACPStatisticsPort        Integer32,
   gs2310pplusLACPReceived              Counter32,
   gs2310pplusLACPTransmitted           Counter32,
   gs2310pplusLACPDiscardedUnknown      Counter32,
   gs2310pplusLACPDiscardedIllegal      Counter32
}

gs2310pplusLACPStatisticsPort OBJECT-TYPE
   SYNTAX      Integer32(1..4095)
   MAX-ACCESS  not-accessible
   STATUS      current
   DESCRIPTION
       " "
   ::= { gs2310pplusLACPStatisticsEntry 1 }
   
gs2310pplusLACPReceived OBJECT-TYPE
   SYNTAX      Counter32
   MAX-ACCESS  read-only
   STATUS      current
   DESCRIPTION
       "Shows how many LACP frames have been received at each port. "
   ::= { gs2310pplusLACPStatisticsEntry 2 }

gs2310pplusLACPTransmitted OBJECT-TYPE
   SYNTAX      Counter32
   MAX-ACCESS  read-only
   STATUS      current
   DESCRIPTION
       " Shows how many LACP frames have been sent from each port. "
   ::= { gs2310pplusLACPStatisticsEntry 3 }

gs2310pplusLACPDiscardedUnknown OBJECT-TYPE
   SYNTAX      Counter32
   MAX-ACCESS  read-only
   STATUS      current
   DESCRIPTION
       " Shows how many unknown LACP frames have been discarded at each port. "
   ::= { gs2310pplusLACPStatisticsEntry 4 }
   
gs2310pplusLACPDiscardedIllegal OBJECT-TYPE
   SYNTAX      Counter32
   MAX-ACCESS  read-only
   STATUS      current
   DESCRIPTION
       " Shows how many illegal LACP frames have been discarded at each port. "
   ::= { gs2310pplusLACPStatisticsEntry 5 }
   
gs2310pplusLACPStatisticsClear OBJECT-TYPE
   SYNTAX      INTEGER { none(0), clear(1) }
   MAX-ACCESS  read-write
   STATUS      current
   DESCRIPTION
       "default: 0
       0: none
       1: clear"
   ::= { gs2310pplusLACP 5 }

gs2310pplusSTP                                                     OBJECT IDENTIFIER ::= { gs2310pplusConfiguration 20 }

gs2310pplusSTPBridgeBasicConf                                                 OBJECT IDENTIFIER ::= { gs2310pplusSTP 1 }

gs2310pplusSTPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2310pplusSTPBridgeBasicConf 1 }

gs2310pplusSTPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2310pplusSTPBridgeBasicConf 2 }
   
gs2310pplusSTPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2310pplusSTPBridgeBasicConf 3 }
   
gs2310pplusSTPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2310pplusSTPBridgeBasicConf 4 }
   
gs2310pplusSTPBridgeMaximumHopCount OBJECT-TYPE
   SYNTAX      Integer32(6..40)
   MAX-ACCESS  read-write
   STATUS      current
   DESCRIPTION
       " Maximum Hop Count default: 20, range: 6 - 40."
   ::= { gs2310pplusSTPBridgeBasicConf 5 }
   
gs2310pplusSTPBridgeTransmitHoldCount OBJECT-TYPE
   SYNTAX      Integer32(1..10)
   MAX-ACCESS  read-write
   STATUS      current
   DESCRIPTION
       " Transmit Hold Count default: 6, range: 1 - 10."
   ::= { gs2310pplusSTPBridgeBasicConf 6 }
   
gs2310pplusSTPBridgeAdvancedConf                                                 OBJECT IDENTIFIER ::= { gs2310pplusSTP 2 }

gs2310pplusSTPBridgeEdgePortBPDUFiltering OBJECT-TYPE
   SYNTAX      INTEGER { disable(0), enable(1) }
   MAX-ACCESS  read-write
   STATUS      current
   DESCRIPTION
       " default: 0,
        0: disable
        1: enable"
   ::= { gs2310pplusSTPBridgeAdvancedConf 1 }
   
gs2310pplusSTPBridgeEdgePortBPDUGuard OBJECT-TYPE
   SYNTAX      INTEGER { disable(0), enable(1) }
   MAX-ACCESS  read-write
   STATUS      current
   DESCRIPTION
       " default: 0,
        0: disable
        1: enable"
   ::= { gs2310pplusSTPBridgeAdvancedConf 2 }
   
gs2310pplusSTPBridgePortErrorRecoveryTimeout OBJECT-TYPE
   SYNTAX      Integer32(0..86400)
   MAX-ACCESS  read-write
   STATUS      current
   DESCRIPTION
       " Port Error Recovery Timeout disable: 0, range: 30 - 86400."
   ::= { gs2310pplusSTPBridgeAdvancedConf 3 }
   
gs2310pplusSTPMSTIConf                                                 OBJECT IDENTIFIER ::= { gs2310pplusSTP 3 }
   
gs2310pplusSTPMSTIConfigurationName OBJECT-TYPE
   SYNTAX      DisplayString (SIZE (1..32))
   MAX-ACCESS  read-write
   STATUS      current
   DESCRIPTION
       "A text string up to 32 characters long."
   ::= { gs2310pplusSTPMSTIConf 1 }
   
gs2310pplusSTPMSTIConfigurationRevision   OBJECT-TYPE
   SYNTAX      Integer32(0..65535)
   MAX-ACCESS  read-write
   STATUS      current
   DESCRIPTION
       " Configuration Revision default: 0, range: 0 - 65535."
   ::= { gs2310pplusSTPMSTIConf 2 }
   
gs2310pplusSTPMSTIMappingConf                                                 OBJECT IDENTIFIER ::= { gs2310pplusSTP 4 }
   
gs2310pplusSTPMSTI1VLANsMapped OBJECT-TYPE
   SYNTAX      DisplayString (SIZE (1..4096))
   MAX-ACCESS  read-write
   STATUS      current
   DESCRIPTION
       "The list of VLANs mapped to the MSTI1. 
       The VLANs must be separated with comma or space. 
       An unused MSTI should just be left empty. "
   ::= { gs2310pplusSTPMSTIMappingConf 1 }

gs2310pplusSTPMSTI2VLANsMapped OBJECT-TYPE
   SYNTAX      DisplayString (SIZE (1..4096))
   MAX-ACCESS  read-write
   STATUS      current
   DESCRIPTION
       "The list of VLANs mapped to the MSTI2. 
       The VLANs must be separated with comma or space. 
       An unused MSTI should just be left empty. "
   ::= { gs2310pplusSTPMSTIMappingConf 2 }
   
gs2310pplusSTPMSTI3VLANsMapped OBJECT-TYPE
   SYNTAX      DisplayString (SIZE (1..4096))
   MAX-ACCESS  read-write
   STATUS      current
   DESCRIPTION
       "The list of VLANs mapped to the MSTI3. 
       The VLANs must be separated with comma or space. 
       An unused MSTI should just be left empty. "
   ::= { gs2310pplusSTPMSTIMappingConf 3 }
   
gs2310pplusSTPMSTI4VLANsMapped OBJECT-TYPE
   SYNTAX      DisplayString (SIZE (1..4096))
   MAX-ACCESS  read-write
   STATUS      current
   DESCRIPTION
       "The list of VLANs mapped to the MSTI4. 
       The VLANs must be separated with comma or space. 
       An unused MSTI should just be left empty. "
   ::= { gs2310pplusSTPMSTIMappingConf 4 }
   
gs2310pplusSTPMSTI5VLANsMapped OBJECT-TYPE
   SYNTAX      DisplayString (SIZE (1..4096))
   MAX-ACCESS  read-write
   STATUS      current
   DESCRIPTION
       "The list of VLANs mapped to the MSTI5. 
       The VLANs must be separated with comma or space. 
       An unused MSTI should just be left empty. "
   ::= { gs2310pplusSTPMSTIMappingConf 5 }

gs2310pplusSTPMSTI6VLANsMapped OBJECT-TYPE
   SYNTAX      DisplayString (SIZE (1..4096))
   MAX-ACCESS  read-write
   STATUS      current
   DESCRIPTION
       "The list of VLANs mapped to the MSTI6. 
       The VLANs must be separated with comma or space. 
       An unused MSTI should just be left empty. "
   ::= { gs2310pplusSTPMSTIMappingConf 6 }
   
gs2310pplusSTPMSTI7VLANsMapped OBJECT-TYPE
   SYNTAX      DisplayString (SIZE (1..4096))
   MAX-ACCESS  read-write
   STATUS      current
   DESCRIPTION
       "The list of VLANs mapped to the MSTI7. 
       The VLANs must be separated with comma or space. 
       An unused MSTI should just be left empty. "
   ::= { gs2310pplusSTPMSTIMappingConf 7 }
   
gs2310pplusSTPMSTIPriority                                                 OBJECT IDENTIFIER ::= { gs2310pplusSTP 5 }
   
gs2310pplusSTPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pplusSTPMSTIPriority 1 }
   
gs2310pplusSTPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pplusSTPMSTIPriority 2 }
   
gs2310pplusSTPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pplusSTPMSTIPriority 3 }
   
gs2310pplusSTPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pplusSTPMSTIPriority 4 }
   
gs2310pplusSTPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pplusSTPMSTIPriority 5 }
   
gs2310pplusSTPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pplusSTPMSTIPriority 6 }

gs2310pplusSTPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pplusSTPMSTIPriority 7 }  

gs2310pplusSTPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2310pplusSTPMSTIPriority 8 }
   
gs2310pplusSTPCISTPort                                                          OBJECT IDENTIFIER ::= { gs2310pplusSTP 6 }

gs2310pplusSTPCISTAggregatedPort                                                OBJECT IDENTIFIER ::= { gs2310pplusSTPCISTPort 1 }
   
gs2310pplusSTPCISTAggregatedPortSTPEnabled OBJECT-TYPE
   SYNTAX      INTEGER { disable(0), enable(1) }
   MAX-ACCESS  read-write
   STATUS      current
   DESCRIPTION
       " default: 0,
        0: disable
        1: enable"
   ::= { gs2310pplusSTPCISTAggregatedPort 1 }
   
gs2310pplusSTPCISTAggregatedPortPathCost OBJECT-TYPE
   SYNTAX      Integer32(0..200000000)
   MAX-ACCESS  read-write
   STATUS      current
   DESCRIPTION
       " Auto: 0,
        Specific Path Cost range: 1 - 200000000."
   ::= { gs2310pplusSTPCISTAggregatedPort 2 }
   
gs2310pplusSTPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2310pplusSTPCISTAggregatedPort 3 }
   
gs2310pplusSTPCISTAggregatedPortAdminEdge OBJECT-TYPE
   SYNTAX      INTEGER { non-edge(0), edge(1) }
   MAX-ACCESS  read-write
   STATUS      current
   DESCRIPTION
       " default: 0,
        0: non-edge
        1: edge"
   ::= { gs2310pplusSTPCISTAggregatedPort 4 }

gs2310pplusSTPCISTAggregatedPortAutoEdge OBJECT-TYPE
   SYNTAX      INTEGER { disable(0), enable(1) }
   MAX-ACCESS  read-write
   STATUS      current
   DESCRIPTION
       " default: 1,
        0: disable
        1: enable"
   ::= { gs2310pplusSTPCISTAggregatedPort 5 }
   
gs2310pplusSTPCISTAggregatedPortRestrictedRole OBJECT-TYPE
   SYNTAX      INTEGER { disable(0), enable(1) }
   MAX-ACCESS  read-write
   STATUS      current
   DESCRIPTION
       " default: 0,
        0: disable
        1: enable"
   ::= { gs2310pplusSTPCISTAggregatedPort 6 }
   
gs2310pplusSTPCISTAggregatedPortRestrictedTCN OBJECT-TYPE
   SYNTAX      INTEGER { disable(0), enable(1) }
   MAX-ACCESS  read-write
   STATUS      current
   DESCRIPTION
       " default: 0,
        0: disable
        1: enable"
   ::= { gs2310pplusSTPCISTAggregatedPort 7 }
   
gs2310pplusSTPCISTAggregatedPortBPDUGuard OBJECT-TYPE
   SYNTAX      INTEGER { disable(0), enable(1) }
   MAX-ACCESS  read-write
   STATUS      current
   DESCRIPTION
       " default: 0,
        0: disable
        1: enable"
   ::= { gs2310pplusSTPCISTAggregatedPort 8 }
   
gs2310pplusSTPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2310pplusSTPCISTAggregatedPort 9 }
   
gs2310pplusSTPCISTNormalPortTable OBJECT-TYPE
   SYNTAX      SEQUENCE OF Gs2310pplusSTPCISTNormalPortEntry
   MAX-ACCESS  not-accessible
   STATUS      current
   DESCRIPTION
       " Show CIST Normal Port Configurations. "
   ::= { gs2310pplusSTPCISTPort 2 }

gs2310pplusSTPCISTNormalPortEntry OBJECT-TYPE
   SYNTAX      Gs2310pplusSTPCISTNormalPortEntry
   MAX-ACCESS  not-accessible
   STATUS      current
   DESCRIPTION
       ""
   INDEX    { gs2310pplusSTPCISTNormalPortConfPort  }
   ::= { gs2310pplusSTPCISTNormalPortTable 1 }

Gs2310pplusSTPCISTNormalPortEntry ::= SEQUENCE {
   gs2310pplusSTPCISTNormalPortConfPort         Integer32,
   gs2310pplusSTPCISTNormalPortSTPEnabled       INTEGER,
   gs2310pplusSTPCISTNormalPortPathCost         Integer32,
   gs2310pplusSTPCISTNormalPortPriority         Integer32,
   gs2310pplusSTPCISTNormalPortAdminEdge        INTEGER,
   gs2310pplusSTPCISTNormalPortAutoEdge         INTEGER,
   gs2310pplusSTPCISTNormalPortRestrictedRole   INTEGER,
   gs2310pplusSTPCISTNormalPortRestrictedTCN    INTEGER,
   gs2310pplusSTPCISTNormalPortBPDUGuard        INTEGER,
   gs2310pplusSTPCISTNormalPortPointtoPoint     INTEGER
}

gs2310pplusSTPCISTNormalPortConfPort OBJECT-TYPE
   SYNTAX      Integer32(1..4095)
   MAX-ACCESS  not-accessible
   STATUS      current
   DESCRIPTION
       " port, range : 1 - port number. "
   ::= { gs2310pplusSTPCISTNormalPortEntry 1 }
   
gs2310pplusSTPCISTNormalPortSTPEnabled OBJECT-TYPE
   SYNTAX      INTEGER { disable(0), enable(1) }
   MAX-ACCESS  read-write
   STATUS      current
   DESCRIPTION
       " default: 0,
        0: disable
        1: enable"
   ::= { gs2310pplusSTPCISTNormalPortEntry 2 }
   
gs2310pplusSTPCISTNormalPortPathCost OBJECT-TYPE
   SYNTAX      Integer32(0..200000000)
   MAX-ACCESS  read-write
   STATUS      current
   DESCRIPTION
       " Auto: 0,
        Specific Path Cost range: 1 - 200000000."
   ::= { gs2310pplusSTPCISTNormalPortEntry 3 }
   
gs2310pplusSTPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2310pplusSTPCISTNormalPortEntry 4 }
   
gs2310pplusSTPCISTNormalPortAdminEdge OBJECT-TYPE
   SYNTAX      INTEGER { non-edge(0), edge(1) }
   MAX-ACCESS  read-write
   STATUS      current
   DESCRIPTION
       " default: 0,
        0: non-Edge
        1: edge"
   ::= { gs2310pplusSTPCISTNormalPortEntry 5 }
   
gs2310pplusSTPCISTNormalPortAutoEdge OBJECT-TYPE
   SYNTAX      INTEGER { disable(0), enable(1) }
   MAX-ACCESS  read-write
   STATUS      current
   DESCRIPTION
       " default: 1,
        0: disable
        1: enable"
   ::= { gs2310pplusSTPCISTNormalPortEntry 6 }
   
gs2310pplusSTPCISTNormalPortRestrictedRole OBJECT-TYPE
   SYNTAX      INTEGER { disable(0), enable(1) }
   MAX-ACCESS  read-write
   STATUS      current
   DESCRIPTION
       " default: 0,
        0: disable
        1: enable"
   ::= { gs2310pplusSTPCISTNormalPortEntry 7 }
   
gs2310pplusSTPCISTNormalPortRestrictedTCN OBJECT-TYPE
   SYNTAX      INTEGER { disable(0), enable(1) }
   MAX-ACCESS  read-write
   STATUS      current
   DESCRIPTION
       " default: 0,
        0: disable
        1: enable"
   ::= { gs2310pplusSTPCISTNormalPortEntry 8 }
   
gs2310pplusSTPCISTNormalPortBPDUGuard OBJECT-TYPE
   SYNTAX      INTEGER { disable(0), enable(1) }
   MAX-ACCESS  read-write
   STATUS      current
   DESCRIPTION
       " default: 0,
        0: disable
        1: enable"
   ::= { gs2310pplusSTPCISTNormalPortEntry 9 }
   
gs2310pplusSTPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2310pplusSTPCISTNormalPortEntry 10 }
   

gs2310pplusSTPMSTIPort                                                          OBJECT IDENTIFIER ::= { gs2310pplusSTP 7 }

gs2310pplusSTPMSTI1Port                                                         OBJECT IDENTIFIER ::= { gs2310pplusSTPMSTIPort 1 }

gs2310pplusSTPMSTI1AggregatedPort                                                OBJECT IDENTIFIER ::= { gs2310pplusSTPMSTI1Port 1 }
      
gs2310pplusSTPMSTI1AggregatedPortPathCost OBJECT-TYPE
   SYNTAX      Integer32(0..200000000)
   MAX-ACCESS  read-write
   STATUS      current
   DESCRIPTION
       " Auto: 0,
        Specific Path Cost range: 1 - 200000000."
   ::= { gs2310pplusSTPMSTI1AggregatedPort 1 }
   
gs2310pplusSTPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI1AggregatedPort 2 }
   
gs2310pplusSTPMSTI1NormalPortTable OBJECT-TYPE
   SYNTAX      SEQUENCE OF Gs2310pplusSTPMSTI1NormalPortEntry
   MAX-ACCESS  not-accessible
   STATUS      current
   DESCRIPTION
       " Show MSTI1 Normal Port Configurations. "
   ::= { gs2310pplusSTPMSTI1Port 2 }

gs2310pplusSTPMSTI1NormalPortEntry OBJECT-TYPE
   SYNTAX      Gs2310pplusSTPMSTI1NormalPortEntry
   MAX-ACCESS  not-accessible
   STATUS      current
   DESCRIPTION
       ""
   INDEX    { gs2310pplusSTPMSTI1NormalPortConfPort  }
   ::= { gs2310pplusSTPMSTI1NormalPortTable 1 }

Gs2310pplusSTPMSTI1NormalPortEntry ::= SEQUENCE {
   gs2310pplusSTPMSTI1NormalPortConfPort         Integer32,
   gs2310pplusSTPMSTI1NormalPortPathCost         Integer32,
   gs2310pplusSTPMSTI1NormalPortPriority         Integer32
}

gs2310pplusSTPMSTI1NormalPortConfPort OBJECT-TYPE
   SYNTAX      Integer32(1..4095)
   MAX-ACCESS  not-accessible
   STATUS      current
   DESCRIPTION
       " port, range : 1 - port number. "
   ::= { gs2310pplusSTPMSTI1NormalPortEntry 1 }
   
gs2310pplusSTPMSTI1NormalPortPathCost OBJECT-TYPE
   SYNTAX      Integer32(0..200000000)
   MAX-ACCESS  read-write
   STATUS      current
   DESCRIPTION
       " Auto: 0,
        Specific Path Cost range: 1 - 200000000."
   ::= { gs2310pplusSTPMSTI1NormalPortEntry 2 }
   
gs2310pplusSTPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI1NormalPortEntry 3 }

gs2310pplusSTPMSTI2Port                                                          OBJECT IDENTIFIER ::= { gs2310pplusSTPMSTIPort 2 }

gs2310pplusSTPMSTI2AggregatedPort                                                OBJECT IDENTIFIER ::= { gs2310pplusSTPMSTI2Port 1 }
      
gs2310pplusSTPMSTI2AggregatedPortPathCost OBJECT-TYPE
   SYNTAX      Integer32(0..200000000)
   MAX-ACCESS  read-write
   STATUS      current
   DESCRIPTION
       " Auto: 0,
        Specific Path Cost range: 1 - 200000000."
   ::= { gs2310pplusSTPMSTI2AggregatedPort 1 }
   
gs2310pplusSTPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI2AggregatedPort 2 }
   
gs2310pplusSTPMSTI2NormalPortTable OBJECT-TYPE
   SYNTAX      SEQUENCE OF Gs2310pplusSTPMSTI2NormalPortEntry
   MAX-ACCESS  not-accessible
   STATUS      current
   DESCRIPTION
       " Show MSTI2 Normal Port Configurations. "
   ::= { gs2310pplusSTPMSTI2Port 2 }

gs2310pplusSTPMSTI2NormalPortEntry OBJECT-TYPE
   SYNTAX      Gs2310pplusSTPMSTI2NormalPortEntry
   MAX-ACCESS  not-accessible
   STATUS      current
   DESCRIPTION
       ""
   INDEX    { gs2310pplusSTPMSTI2NormalPortConfPort  }
   ::= { gs2310pplusSTPMSTI2NormalPortTable 1 }

Gs2310pplusSTPMSTI2NormalPortEntry ::= SEQUENCE {
   gs2310pplusSTPMSTI2NormalPortConfPort         Integer32,
   gs2310pplusSTPMSTI2NormalPortPathCost         Integer32,
   gs2310pplusSTPMSTI2NormalPortPriority         Integer32
}

gs2310pplusSTPMSTI2NormalPortConfPort OBJECT-TYPE
   SYNTAX      Integer32(1..4095)
   MAX-ACCESS  not-accessible
   STATUS      current
   DESCRIPTION
       " port, range : 1 - port number. "
   ::= { gs2310pplusSTPMSTI2NormalPortEntry 1 }
   
gs2310pplusSTPMSTI2NormalPortPathCost OBJECT-TYPE
   SYNTAX      Integer32(0..200000000)
   MAX-ACCESS  read-write
   STATUS      current
   DESCRIPTION
       " Auto: 0,
        Specific Path Cost range: 1 - 200000000."
   ::= { gs2310pplusSTPMSTI2NormalPortEntry 2 }
   
gs2310pplusSTPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI2NormalPortEntry 3 }
   
gs2310pplusSTPMSTI3Port                                                          OBJECT IDENTIFIER ::= { gs2310pplusSTPMSTIPort 3 }

gs2310pplusSTPMSTI3AggregatedPort                                                OBJECT IDENTIFIER ::= { gs2310pplusSTPMSTI3Port 1 }
      
gs2310pplusSTPMSTI3AggregatedPortPathCost OBJECT-TYPE
   SYNTAX      Integer32(0..200000000)
   MAX-ACCESS  read-write
   STATUS      current
   DESCRIPTION
       " Auto: 0,
        Specific Path Cost range: 1 - 200000000."
   ::= { gs2310pplusSTPMSTI3AggregatedPort 1 }
   
gs2310pplusSTPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI3AggregatedPort 2 }
   
gs2310pplusSTPMSTI3NormalPortTable OBJECT-TYPE
   SYNTAX      SEQUENCE OF Gs2310pplusSTPMSTI3NormalPortEntry
   MAX-ACCESS  not-accessible
   STATUS      current
   DESCRIPTION
       " Show MSTI3 Normal Port Configurations. "
   ::= { gs2310pplusSTPMSTI3Port 2 }

gs2310pplusSTPMSTI3NormalPortEntry OBJECT-TYPE
   SYNTAX      Gs2310pplusSTPMSTI3NormalPortEntry
   MAX-ACCESS  not-accessible
   STATUS      current
   DESCRIPTION
       ""
   INDEX    { gs2310pplusSTPMSTI3NormalPortConfPort  }
   ::= { gs2310pplusSTPMSTI3NormalPortTable 1 }

Gs2310pplusSTPMSTI3NormalPortEntry ::= SEQUENCE {
   gs2310pplusSTPMSTI3NormalPortConfPort         Integer32,
   gs2310pplusSTPMSTI3NormalPortPathCost         Integer32,
   gs2310pplusSTPMSTI3NormalPortPriority         Integer32
}

gs2310pplusSTPMSTI3NormalPortConfPort OBJECT-TYPE
   SYNTAX      Integer32(1..4095)
   MAX-ACCESS  not-accessible
   STATUS      current
   DESCRIPTION
       " port, range : 1 - port number. "
   ::= { gs2310pplusSTPMSTI3NormalPortEntry 1 }
   
gs2310pplusSTPMSTI3NormalPortPathCost OBJECT-TYPE
   SYNTAX      Integer32(0..200000000)
   MAX-ACCESS  read-write
   STATUS      current
   DESCRIPTION
       " Auto: 0,
        Specific Path Cost range: 1 - 200000000."
   ::= { gs2310pplusSTPMSTI3NormalPortEntry 2 }
   
gs2310pplusSTPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI3NormalPortEntry 3 }
   
gs2310pplusSTPMSTI4Port                                                          OBJECT IDENTIFIER ::= { gs2310pplusSTPMSTIPort 4 }

gs2310pplusSTPMSTI4AggregatedPort                                                OBJECT IDENTIFIER ::= { gs2310pplusSTPMSTI4Port 1 }
      
gs2310pplusSTPMSTI4AggregatedPortPathCost OBJECT-TYPE
   SYNTAX      Integer32(0..200000000)
   MAX-ACCESS  read-write
   STATUS      current
   DESCRIPTION
       " Auto: 0,
        Specific Path Cost range: 1 - 200000000."
   ::= { gs2310pplusSTPMSTI4AggregatedPort 1 }
   
gs2310pplusSTPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI4AggregatedPort 2 }
   
gs2310pplusSTPMSTI4NormalPortTable OBJECT-TYPE
   SYNTAX      SEQUENCE OF Gs2310pplusSTPMSTI4NormalPortEntry
   MAX-ACCESS  not-accessible
   STATUS      current
   DESCRIPTION
       " Show MSTI4 Normal Port Configurations. "
   ::= { gs2310pplusSTPMSTI4Port 2 }

gs2310pplusSTPMSTI4NormalPortEntry OBJECT-TYPE
   SYNTAX      Gs2310pplusSTPMSTI4NormalPortEntry
   MAX-ACCESS  not-accessible
   STATUS      current
   DESCRIPTION
       ""
   INDEX    { gs2310pplusSTPMSTI4NormalPortConfPort  }
   ::= { gs2310pplusSTPMSTI4NormalPortTable 1 }

Gs2310pplusSTPMSTI4NormalPortEntry ::= SEQUENCE {
   gs2310pplusSTPMSTI4NormalPortConfPort         Integer32,
   gs2310pplusSTPMSTI4NormalPortPathCost         Integer32,
   gs2310pplusSTPMSTI4NormalPortPriority         Integer32
}

gs2310pplusSTPMSTI4NormalPortConfPort OBJECT-TYPE
   SYNTAX      Integer32(1..4095)
   MAX-ACCESS  not-accessible
   STATUS      current
   DESCRIPTION
       " port, range : 1 - port number. "
   ::= { gs2310pplusSTPMSTI4NormalPortEntry 1 }
   
gs2310pplusSTPMSTI4NormalPortPathCost OBJECT-TYPE
   SYNTAX      Integer32(0..200000000)
   MAX-ACCESS  read-write
   STATUS      current
   DESCRIPTION
       " Auto: 0,
        Specific Path Cost range: 1 - 200000000."
   ::= { gs2310pplusSTPMSTI4NormalPortEntry 2 }
   
gs2310pplusSTPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI4NormalPortEntry 3 }
   
gs2310pplusSTPMSTI5Port                                                          OBJECT IDENTIFIER ::= { gs2310pplusSTPMSTIPort 5 }

gs2310pplusSTPMSTI5AggregatedPort                                                OBJECT IDENTIFIER ::= { gs2310pplusSTPMSTI5Port 1 }
      
gs2310pplusSTPMSTI5AggregatedPortPathCost OBJECT-TYPE
   SYNTAX      Integer32(0..200000000)
   MAX-ACCESS  read-write
   STATUS      current
   DESCRIPTION
       " Auto: 0,
        Specific Path Cost range: 1 - 200000000."
   ::= { gs2310pplusSTPMSTI5AggregatedPort 1 }
   
gs2310pplusSTPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI5AggregatedPort 2 }
   
gs2310pplusSTPMSTI5NormalPortTable OBJECT-TYPE
   SYNTAX      SEQUENCE OF Gs2310pplusSTPMSTI5NormalPortEntry
   MAX-ACCESS  not-accessible
   STATUS      current
   DESCRIPTION
       " Show MSTI5 Normal Port Configurations. "
   ::= { gs2310pplusSTPMSTI5Port 2 }

gs2310pplusSTPMSTI5NormalPortEntry OBJECT-TYPE
   SYNTAX      Gs2310pplusSTPMSTI5NormalPortEntry
   MAX-ACCESS  not-accessible
   STATUS      current
   DESCRIPTION
       ""
   INDEX    { gs2310pplusSTPMSTI5NormalPortConfPort  }
   ::= { gs2310pplusSTPMSTI5NormalPortTable 1 }

Gs2310pplusSTPMSTI5NormalPortEntry ::= SEQUENCE {
   gs2310pplusSTPMSTI5NormalPortConfPort         Integer32,
   gs2310pplusSTPMSTI5NormalPortPathCost         Integer32,
   gs2310pplusSTPMSTI5NormalPortPriority         Integer32
}

gs2310pplusSTPMSTI5NormalPortConfPort OBJECT-TYPE
   SYNTAX      Integer32(1..4095)
   MAX-ACCESS  not-accessible
   STATUS      current
   DESCRIPTION
       " port, range : 1 - port number. "
   ::= { gs2310pplusSTPMSTI5NormalPortEntry 1 }
   
gs2310pplusSTPMSTI5NormalPortPathCost OBJECT-TYPE
   SYNTAX      Integer32(0..200000000)
   MAX-ACCESS  read-write
   STATUS      current
   DESCRIPTION
       " Auto: 0,
        Specific Path Cost range: 1 - 200000000."
   ::= { gs2310pplusSTPMSTI5NormalPortEntry 2 }
   
gs2310pplusSTPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI5NormalPortEntry 3 }
   
gs2310pplusSTPMSTI6Port                                                          OBJECT IDENTIFIER ::= { gs2310pplusSTPMSTIPort 6 }

gs2310pplusSTPMSTI6AggregatedPort                                                OBJECT IDENTIFIER ::= { gs2310pplusSTPMSTI6Port 1 }
      
gs2310pplusSTPMSTI6AggregatedPortPathCost OBJECT-TYPE
   SYNTAX      Integer32(0..200000000)
   MAX-ACCESS  read-write
   STATUS      current
   DESCRIPTION
       " Auto: 0,
        Specific Path Cost range: 1 - 200000000."
   ::= { gs2310pplusSTPMSTI6AggregatedPort 1 }
   
gs2310pplusSTPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI6AggregatedPort 2 }
   
gs2310pplusSTPMSTI6NormalPortTable OBJECT-TYPE
   SYNTAX      SEQUENCE OF Gs2310pplusSTPMSTI6NormalPortEntry
   MAX-ACCESS  not-accessible
   STATUS      current
   DESCRIPTION
       " Show MSTI6 Normal Port Configurations. "
   ::= { gs2310pplusSTPMSTI6Port 2 }

gs2310pplusSTPMSTI6NormalPortEntry OBJECT-TYPE
   SYNTAX      Gs2310pplusSTPMSTI6NormalPortEntry
   MAX-ACCESS  not-accessible
   STATUS      current
   DESCRIPTION
       ""
   INDEX    { gs2310pplusSTPMSTI6NormalPortConfPort  }
   ::= { gs2310pplusSTPMSTI6NormalPortTable 1 }

Gs2310pplusSTPMSTI6NormalPortEntry ::= SEQUENCE {
   gs2310pplusSTPMSTI6NormalPortConfPort         Integer32,
   gs2310pplusSTPMSTI6NormalPortPathCost         Integer32,
   gs2310pplusSTPMSTI6NormalPortPriority         Integer32
}

gs2310pplusSTPMSTI6NormalPortConfPort OBJECT-TYPE
   SYNTAX      Integer32(1..4095)
   MAX-ACCESS  not-accessible
   STATUS      current
   DESCRIPTION
       " port, range : 1 - port number. "
   ::= { gs2310pplusSTPMSTI6NormalPortEntry 1 }
   
gs2310pplusSTPMSTI6NormalPortPathCost OBJECT-TYPE
   SYNTAX      Integer32(0..200000000)
   MAX-ACCESS  read-write
   STATUS      current
   DESCRIPTION
       " Auto: 0,
        Specific Path Cost range: 1 - 200000000."
   ::= { gs2310pplusSTPMSTI6NormalPortEntry 2 }
   
gs2310pplusSTPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI6NormalPortEntry 3 }
   
gs2310pplusSTPMSTI7Port                                                          OBJECT IDENTIFIER ::= { gs2310pplusSTPMSTIPort 7 }

gs2310pplusSTPMSTI7AggregatedPort                                                OBJECT IDENTIFIER ::= { gs2310pplusSTPMSTI7Port 1 }
      
gs2310pplusSTPMSTI7AggregatedPortPathCost OBJECT-TYPE
   SYNTAX      Integer32(0..200000000)
   MAX-ACCESS  read-write
   STATUS      current
   DESCRIPTION
       " Auto: 0,
        Specific Path Cost range: 1 - 200000000."
   ::= { gs2310pplusSTPMSTI7AggregatedPort 1 }
   
gs2310pplusSTPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI7AggregatedPort 2 }
   
gs2310pplusSTPMSTI7NormalPortTable OBJECT-TYPE
   SYNTAX      SEQUENCE OF Gs2310pplusSTPMSTI7NormalPortEntry
   MAX-ACCESS  not-accessible
   STATUS      current
   DESCRIPTION
       " Show MSTI7 Normal Port Configurations. "
   ::= { gs2310pplusSTPMSTI7Port 2 }

gs2310pplusSTPMSTI7NormalPortEntry OBJECT-TYPE
   SYNTAX      Gs2310pplusSTPMSTI7NormalPortEntry
   MAX-ACCESS  not-accessible
   STATUS      current
   DESCRIPTION
       ""
   INDEX    { gs2310pplusSTPMSTI7NormalPortConfPort  }
   ::= { gs2310pplusSTPMSTI7NormalPortTable 1 }

Gs2310pplusSTPMSTI7NormalPortEntry ::= SEQUENCE {
   gs2310pplusSTPMSTI7NormalPortConfPort         Integer32,
   gs2310pplusSTPMSTI7NormalPortPathCost         Integer32,
   gs2310pplusSTPMSTI7NormalPortPriority         Integer32
}

gs2310pplusSTPMSTI7NormalPortConfPort OBJECT-TYPE
   SYNTAX      Integer32(1..4095)
   MAX-ACCESS  not-accessible
   STATUS      current
   DESCRIPTION
       " port, range : 1 - port number. "
   ::= { gs2310pplusSTPMSTI7NormalPortEntry 1 }
   
gs2310pplusSTPMSTI7NormalPortPathCost OBJECT-TYPE
   SYNTAX      Integer32(0..200000000)
   MAX-ACCESS  read-write
   STATUS      current
   DESCRIPTION
       " Auto: 0,
        Specific Path Cost range: 1 - 200000000."
   ::= { gs2310pplusSTPMSTI7NormalPortEntry 2 }
   
gs2310pplusSTPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2310pplusSTPMSTI7NormalPortEntry 3 }
   

gs2310pplusSTPBridgeStatus                                                      OBJECT IDENTIFIER ::= { gs2310pplusSTP 8 }

gs2310pplusCISTBridgeSTP                                                        OBJECT IDENTIFIER ::= { gs2310pplusSTPBridgeStatus 1 }

gs2310pplusCISTBridgeSTPStatus                                                  OBJECT IDENTIFIER ::= { gs2310pplusCISTBridgeSTP 1 }
      
gs2310pplusCISTBridgeInstance OBJECT-TYPE
   SYNTAX       DisplayString
   MAX-ACCESS   read-only
   STATUS       current
   DESCRIPTION
       "The Bridge instance - CIST, MST1, ..."
   ::= { gs2310pplusCISTBridgeSTPStatus 1 }
   
gs2310pplusCISTBridgeID OBJECT-TYPE
   SYNTAX       DisplayString
   MAX-ACCESS   read-only
   STATUS       current
   DESCRIPTION
       "The Bridge ID of this Bridge instance."
   ::= { gs2310pplusCISTBridgeSTPStatus 2 }
   
gs2310pplusCISTRootID OBJECT-TYPE
   SYNTAX       DisplayString
   MAX-ACCESS   read-only
   STATUS       current
   DESCRIPTION
       "The Bridge ID of the currently elected root bridge."
   ::= { gs2310pplusCISTBridgeSTPStatus 3 }
   
gs2310pplusCISTRootPort OBJECT-TYPE
   SYNTAX       DisplayString
   MAX-ACCESS   read-only
   STATUS       current
   DESCRIPTION
       "The switch port currently assigned the root port role."
   ::= { gs2310pplusCISTBridgeSTPStatus 4 }

gs2310pplusCISTRootCost OBJECT-TYPE
   SYNTAX       Integer32(0..200000000)
   MAX-ACCESS   read-only
   STATUS       current
   DESCRIPTION
       "Root Path Cost."
   ::= { gs2310pplusCISTBridgeSTPStatus 5 }
   
gs2310pplusCISTRegionalRoot OBJECT-TYPE
   SYNTAX       DisplayString
   MAX-ACCESS   read-only
   STATUS       current
   DESCRIPTION
       "The Bridge ID of the currently elected regional root bridge, inside the MSTP region of this bridge."
   ::= { gs2310pplusCISTBridgeSTPStatus 6 }
   
gs2310pplusCISTInternalRootCost OBJECT-TYPE
   SYNTAX       Integer32(0..200000000)
   MAX-ACCESS   read-only
   STATUS       current
   DESCRIPTION
       "The Regional Root Path Cost."
   ::= { gs2310pplusCISTBridgeSTPStatus 7 }

gs2310pplusCISTTopologyFlag OBJECT-TYPE
   SYNTAX       DisplayString
   MAX-ACCESS   read-only
   STATUS       current
   DESCRIPTION
       "The current state of the Topology Change Flag of this Bridge instance."
   ::= { gs2310pplusCISTBridgeSTPStatus 8 }

gs2310pplusCISTTopologyChangeCount OBJECT-TYPE
   SYNTAX       Counter32
   MAX-ACCESS   read-only
   STATUS       current
   DESCRIPTION
       "The number of times where the topology change flag has been set."
   ::= { gs2310pplusCISTBridgeSTPStatus 9 }
   
gs2310pplusCISTTopologyChangeLast OBJECT-TYPE
   SYNTAX       DisplayString
   MAX-ACCESS   read-only
   STATUS       current
   DESCRIPTION
       "The time passed since the Topology Flag was last set."
   ::= { gs2310pplusCISTBridgeSTPStatus 10 }
   
gs2310pplusCISTPortStateTable OBJECT-TYPE
   SYNTAX      SEQUENCE OF Gs2310pplusCISTPortStateEntry
   MAX-ACCESS  not-accessible
   STATUS      current
   DESCRIPTION
       " Show CIST Ports and Aggregations State Configurations. "
   ::= { gs2310pplusCISTBridgeSTP 2 }

gs2310pplusCISTPortStateEntry OBJECT-TYPE
   SYNTAX      Gs2310pplusCISTPortStateEntry
   MAX-ACCESS  not-accessible
   STATUS      current
   DESCRIPTION
       ""
   INDEX    { gs2310pplusCISTPortStateIndex  }
   ::= { gs2310pplusCISTPortStateTable 1 }

Gs2310pplusCISTPortStateEntry ::= SEQUENCE {
   gs2310pplusCISTPortStateIndex        Integer32,
   gs2310pplusCISTPortStatePort         DisplayString,
   gs2310pplusCISTPortStatePortID       DisplayString,
   gs2310pplusCISTPortStateRole         DisplayString,
   gs2310pplusCISTPortStateState        DisplayString,
   gs2310pplusCISTPortStatePathCost     Integer32,
   gs2310pplusCISTPortStateEdge         DisplayString,
   gs2310pplusCISTPortStatePoint2Point  DisplayString,
   gs2310pplusCISTPortStateUptime       DisplayString
}

gs2310pplusCISTPortStateIndex OBJECT-TYPE
   SYNTAX      Integer32(1..4095)
   MAX-ACCESS  not-accessible
   STATUS      current
   DESCRIPTION
       "table index."
   ::= { gs2310pplusCISTPortStateEntry 1 }
   
gs2310pplusCISTPortStatePort OBJECT-TYPE
   SYNTAX      DisplayString
   MAX-ACCESS  read-only
   STATUS      current
   DESCRIPTION
       "The switch port number of the logical STP port."
   ::= { gs2310pplusCISTPortStateEntry 2 }
   
gs2310pplusCISTPortStatePortID OBJECT-TYPE
   SYNTAX      DisplayString
   MAX-ACCESS  read-only
   STATUS      current
   DESCRIPTION
       "The port id as used by the STP protocol. 
        This is the priority part and the logical port index of the bridge port."
   ::= { gs2310pplusCISTPortStateEntry 3 }
   
gs2310pplusCISTPortStateRole OBJECT-TYPE
   SYNTAX      DisplayString
   MAX-ACCESS  read-only
   STATUS      current
   DESCRIPTION
       "The current STP port role."
   ::= { gs2310pplusCISTPortStateEntry 4 }
   
gs2310pplusCISTPortStateState OBJECT-TYPE
   SYNTAX      DisplayString
   MAX-ACCESS  read-only
   STATUS      current
   DESCRIPTION
       "The current STP port state."
   ::= { gs2310pplusCISTPortStateEntry 5 }
   
gs2310pplusCISTPortStatePathCost OBJECT-TYPE
   SYNTAX      Integer32(0..200000000)
   MAX-ACCESS  read-only
   STATUS      current
   DESCRIPTION
       "The current STP port path cost."
   ::= { gs2310pplusCISTPortStateEntry 6 }
   
gs2310pplusCISTPortStateEdge OBJECT-TYPE
   SYNTAX      DisplayString
   MAX-ACCESS  read-only
   STATUS      current
   DESCRIPTION
       "The current STP port Edge Flag."
   ::= { gs2310pplusCISTPortStateEntry 7 }
   
gs2310pplusCISTPortStatePoint2Point OBJECT-TYPE
   SYNTAX      DisplayString
   MAX-ACCESS  read-only
   STATUS      current
   DESCRIPTION
       "The current STP port point-to-point flag."
   ::= { gs2310pplusCISTPortStateEntry 8 }
   
gs2310pplusCISTPortStateUptime OBJECT-TYPE
   SYNTAX      DisplayString
   MAX-ACCESS  read-only
   STATUS      current
   DESCRIPTION
       "The time since the bridge port was last initialized."
   ::= { gs2310pplusCISTPortStateEntry 9 }
   
gs2310pplusMSTI1BridgeSTP                                                        OBJECT IDENTIFIER ::= { gs2310pplusSTPBridgeStatus 2 }

gs2310pplusMSTI1BridgeSTPStatus                                                  OBJECT IDENTIFIER ::= { gs2310pplusMSTI1BridgeSTP 1 }
      
gs2310pplusMSTI1BridgeInstance OBJECT-TYPE
   SYNTAX       DisplayString
   MAX-ACCESS   read-only
   STATUS       current
   DESCRIPTION
       "The Bridge instance - CIST, MST1, ..."
   ::= { gs2310pplusMSTI1BridgeSTPStatus 1 }
   
gs2310pplusMSTI1BridgeID OBJECT-TYPE
   SYNTAX       DisplayString
   MAX-ACCESS   read-only
   STATUS       current
   DESCRIPTION
       "The Bridge ID of this Bridge instance."
   ::= { gs2310pplusMSTI1BridgeSTPStatus 2 }
   
gs2310pplusMSTI1RootID OBJECT-TYPE
   SYNTAX       DisplayString
   MAX-ACCESS   read-only
   STATUS       current
   DESCRIPTION
       "The Bridge ID of the currently elected root bridge."
   ::= { gs2310pplusMSTI1BridgeSTPStatus 3 }
   
gs2310pplusMSTI1RootPort OBJECT-TYPE
   SYNTAX       DisplayString
   MAX-ACCESS   read-only
   STATUS       current
   DESCRIPTION
       "The switch port currently assigned the root port role."
   ::= { gs2310pplusMSTI1BridgeSTPStatus 4 }

gs2310pplusMSTI1RootCost OBJECT-TYPE
   SYNTAX       Integer32(0..200000000)
   MAX-ACCESS   read-only
   STATUS       current
   DESCRIPTION
       "Root Path Cost."
   ::= { gs2310pplusMSTI1BridgeSTPStatus 5 }

gs2310pplusMSTI1TopologyFlag OBJECT-TYPE
   SYNTAX       DisplayString
   MAX-ACCESS   read-only
   STATUS       current
   DESCRIPTION
       "The current state of the Topology Change Flag of this Bridge instance."
   ::= { gs2310pplusMSTI1BridgeSTPStatus 8 }

gs2310pplusMSTI1TopologyChangeCount OBJECT-TYPE
   SYNTAX       Counter32
   MAX-ACCESS   read-only
   STATUS       current
   DESCRIPTION
       "The number of times where the topology change flag has been set."
   ::= { gs2310pplusMSTI1BridgeSTPStatus 9 }
   
gs2310pplusMSTI1TopologyChangeLast OBJECT-TYPE
   SYNTAX       DisplayString
   MAX-ACCESS   read-only
   STATUS       current
   DESCRIPTION
       "The time passed since the Topology Flag was last set."
   ::= { gs2310pplusMSTI1BridgeSTPStatus 10 }
   
gs2310pplusMSTI1PortStateTable OBJECT-TYPE
   SYNTAX      SEQUENCE OF Gs2310pplusMSTI1PortStateEntry
   MAX-ACCESS  not-accessible
   STATUS      current
   DESCRIPTION
       " Show MSTI1 Ports and Aggregations State Configurations. "
   ::= { gs2310pplusMSTI1BridgeSTP 2 }

gs2310pplusMSTI1PortStateEntry OBJECT-TYPE
   SYNTAX      Gs2310pplusMSTI1PortStateEntry
   MAX-ACCESS  not-accessible
   STATUS      current
   DESCRIPTION
       ""
   INDEX    { gs2310pplusMSTI1PortStateIndex  }
   ::= { gs2310pplusMSTI1PortStateTable 1 }

Gs2310pplusMSTI1PortStateEntry ::= SEQUENCE {
   gs2310pplusMSTI1PortStateIndex        Integer32,
   gs2310pplusMSTI1PortStatePort         DisplayString,
   gs2310pplusMSTI1PortStatePortID       DisplayString,
   gs2310pplusMSTI1PortStateRole         DisplayString,
   gs2310pplusMSTI1PortStateState        DisplayString,
   gs2310pplusMSTI1PortStatePathCost     Integer32,
   gs2310pplusMSTI1PortStateEdge         DisplayString,
   gs2310pplusMSTI1PortStatePoint2Point  DisplayString,
   gs2310pplusMSTI1PortStateUptime       DisplayString
}

gs2310pplusMSTI1PortStateIndex OBJECT-TYPE
   SYNTAX      Integer32(1..4095)
   MAX-ACCESS  not-accessible
   STATUS      current
   DESCRIPTION
       "table index."
   ::= { gs2310pplusMSTI1PortStateEntry 1 }
   
gs2310pplusMSTI1PortStatePort OBJECT-TYPE
   SYNTAX      DisplayString
   MAX-ACCESS  read-only
   STATUS      current
   DESCRIPTION
       "The switch port number of the logical STP port."
   ::= { gs2310pplusMSTI1PortStateEntry 2 }
   
gs2310pplusMSTI1PortStatePortID OBJECT-TYPE
   SYNTAX      DisplayString
   MAX-ACCESS  read-only
   STATUS      current
   DESCRIPTION
       "The port id as used by the STP protocol. 
        This is the priority part and the logical port index of the bridge port."
   ::= { gs2310pplusMSTI1PortStateEntry 3 }
   
gs2310pplusMSTI1PortStateRole OBJECT-TYPE
   SYNTAX      DisplayString
   MAX-ACCESS  read-only
   STATUS      current
   DESCRIPTION
       "The current STP port role."
   ::= { gs2310pplusMSTI1PortStateEntry 4 }
   
gs2310pplusMSTI1PortStateState OBJECT-TYPE
   SYNTAX      DisplayString
   MAX-ACCESS  read-only
   STATUS      current
   DESCRIPTION
       "The current STP port state."
   ::= { gs2310pplusMSTI1PortStateEntry 5 }
   
gs2310pplusMSTI1PortStatePathCost OBJECT-TYPE
   SYNTAX      Integer32(0..200000000)
   MAX-ACCESS  read-only
   STATUS      current
   DESCRIPTION
       "The current STP port path cost."
   ::= { gs2310pplusMSTI1PortStateEntry 6 }
   
gs2310pplusMSTI1PortStateEdge OBJECT-TYPE
   SYNTAX      DisplayString
   MAX-ACCESS  read-only
   STATUS      current
   DESCRIPTION
       "The current STP port Edge Flag."
   ::= { gs2310pplusMSTI1PortStateEntry 7 }
   
gs2310pplusMSTI1PortStatePoint2Point OBJECT-TYPE
   SYNTAX      DisplayString
   MAX-ACCESS  read-only
   STATUS      current
   DESCRIPTION
       "The current STP port point-to-point flag."
   ::= { gs2310pplusMSTI1PortStateEntry 8 }
   
gs2310pplusMSTI1PortStateUptime OBJECT-TYPE
   SYNTAX      DisplayString
   MAX-ACCESS  read-only
   STATUS      current
   DESCRIPTION
       "The time since the bridge port was last initialized."
   ::= { gs2310pplusMSTI1PortStateEntry 9 }
   
gs2310pplusMSTI2BridgeSTP                                                        OBJECT IDENTIFIER ::= { gs2310pplusSTPBridgeStatus 3 }

gs2310pplusMSTI2BridgeSTPStatus                                                  OBJECT IDENTIFIER ::= { gs2310pplusMSTI2BridgeSTP 1 }
      
gs2310pplusMSTI2BridgeInstance OBJECT-TYPE
   SYNTAX       DisplayString
   MAX-ACCESS   read-only
   STATUS       current
   DESCRIPTION
       "The Bridge instance - CIST, MST1, ..."
   ::= { gs2310pplusMSTI2BridgeSTPStatus 1 }
   
gs2310pplusMSTI2BridgeID OBJECT-TYPE
   SYNTAX       DisplayString
   MAX-ACCESS   read-only
   STATUS       current
   DESCRIPTION
       "The Bridge ID of this Bridge instance."
   ::= { gs2310pplusMSTI2BridgeSTPStatus 2 }
   
gs2310pplusMSTI2RootID OBJECT-TYPE
   SYNTAX       DisplayString
   MAX-ACCESS   read-only
   STATUS       current
   DESCRIPTION
       "The Bridge ID of the currently elected root bridge."
   ::= { gs2310pplusMSTI2BridgeSTPStatus 3 }
   
gs2310pplusMSTI2RootPort OBJECT-TYPE
   SYNTAX       DisplayString
   MAX-ACCESS   read-only
   STATUS       current
   DESCRIPTION
       "The switch port currently assigned the root port role."
   ::= { gs2310pplusMSTI2BridgeSTPStatus 4 }

gs2310pplusMSTI2RootCost OBJECT-TYPE
   SYNTAX       Integer32(0..200000000)
   MAX-ACCESS   read-only
   STATUS       current
   DESCRIPTION
       "Root Path Cost."
   ::= { gs2310pplusMSTI2BridgeSTPStatus 5 }

gs2310pplusMSTI2TopologyFlag OBJECT-TYPE
   SYNTAX       DisplayString
   MAX-ACCESS   read-only
   STATUS       current
   DESCRIPTION
       "The current state of the Topology Change Flag of this Bridge instance."
   ::= { gs2310pplusMSTI2BridgeSTPStatus 8 }

gs2310pplusMSTI2TopologyChangeCount OBJECT-TYPE
   SYNTAX       Counter32
   MAX-ACCESS   read-only
   STATUS       current
   DESCRIPTION
       "The number of times where the topology change flag has been set."
   ::= { gs2310pplusMSTI2BridgeSTPStatus 9 }
   
gs2310pplusMSTI2TopologyChangeLast OBJECT-TYPE
   SYNTAX       DisplayString
   MAX-ACCESS   read-only
   STATUS       current
   DESCRIPTION
       "The time passed since the Topology Flag was last set."
   ::= { gs2310pplusMSTI2BridgeSTPStatus 10 }
   
gs2310pplusMSTI2PortStateTable OBJECT-TYPE
   SYNTAX      SEQUENCE OF Gs2310pplusMSTI2PortStateEntry
   MAX-ACCESS  not-accessible
   STATUS      current
   DESCRIPTION
       " Show MSTI2 Ports and Aggregations State Configurations. "
   ::= { gs2310pplusMSTI2BridgeSTP 2 }

gs2310pplusMSTI2PortStateEntry OBJECT-TYPE
   SYNTAX      Gs2310pplusMSTI2PortStateEntry
   MAX-ACCESS  not-accessible
   STATUS      current
   DESCRIPTION
       ""
   INDEX    { gs2310pplusMSTI2PortStateIndex  }
   ::= { gs2310pplusMSTI2PortStateTable 1 }

Gs2310pplusMSTI2PortStateEntry ::= SEQUENCE {
   gs2310pplusMSTI2PortStateIndex        Integer32,
   gs2310pplusMSTI2PortStatePort         DisplayString,
   gs2310pplusMSTI2PortStatePortID       DisplayString,
   gs2310pplusMSTI2PortStateRole         DisplayString,
   gs2310pplusMSTI2PortStateState        DisplayString,
   gs2310pplusMSTI2PortStatePathCost     Integer32,
   gs2310pplusMSTI2PortStateEdge         DisplayString,
   gs2310pplusMSTI2PortStatePoint2Point  DisplayString,
   gs2310pplusMSTI2PortStateUptime       DisplayString
}

gs2310pplusMSTI2PortStateIndex OBJECT-TYPE
   SYNTAX      Integer32(1..4095)
   MAX-ACCESS  not-accessible
   STATUS      current
   DESCRIPTION
       "table index."
   ::= { gs2310pplusMSTI2PortStateEntry 1 }
   
gs2310pplusMSTI2PortStatePort OBJECT-TYPE
   SYNTAX      DisplayString
   MAX-ACCESS  read-only
   STATUS      current
   DESCRIPTION
       "The switch port number of the logical STP port."
   ::= { gs2310pplusMSTI2PortStateEntry 2 }
   
gs2310pplusMSTI2PortStatePortID OBJECT-TYPE
   SYNTAX      DisplayString
   MAX-ACCESS  read-only
   STATUS      current
   DESCRIPTION
       "The port id as used by the STP protocol. 
        This is the priority part and the logical port index of the bridge port."
   ::= { gs2310pplusMSTI2PortStateEntry 3 }
   
gs2310pplusMSTI2PortStateRole OBJECT-TYPE
   SYNTAX      DisplayString
   MAX-ACCESS  read-only
   STATUS      current
   DESCRIPTION
       "The current STP port role."
   ::= { gs2310pplusMSTI2PortStateEntry 4 }
   
gs2310pplusMSTI2PortStateState OBJECT-TYPE
   SYNTAX      DisplayString
   MAX-ACCESS  read-only
   STATUS      current
   DESCRIPTION
       "The current STP port state."
   ::= { gs2310pplusMSTI2PortStateEntry 5 }
   
gs2310pplusMSTI2PortStatePathCost OBJECT-TYPE
   SYNTAX      Integer32(0..200000000)
   MAX-ACCESS  read-only
   STATUS      current
   DESCRIPTION
       "The current STP port path cost."
   ::= { gs2310pplusMSTI2PortStateEntry 6 }
   
gs2310pplusMSTI2PortStateEdge OBJECT-TYPE
   SYNTAX      DisplayString
   MAX-ACCESS  read-only
   STATUS      current
   DESCRIPTION
       "The current STP port Edge Flag."
   ::= { gs2310pplusMSTI2PortStateEntry 7 }
   
gs2310pplusMSTI2PortStatePoint2Point OBJECT-TYPE
   SYNTAX      DisplayString
   MAX-ACCESS  read-only
   STATUS      current
   DESCRIPTION
       "The current STP port point-to-point flag."
   ::= { gs2310pplusMSTI2PortStateEntry 8 }
   
gs2310pplusMSTI2PortStateUptime OBJECT-TYPE
   SYNTAX      DisplayString
   MAX-ACCESS  read-only
   STATUS      current
   DESCRIPTION
       "The time since the bridge port was last initialized."
   ::= { gs2310pplusMSTI2PortStateEntry 9 }

gs2310pplusMSTI3BridgeSTP                                                        OBJECT IDENTIFIER ::= { gs2310pplusSTPBridgeStatus 4 }

gs2310pplusMSTI3BridgeSTPStatus                                                  OBJECT IDENTIFIER ::= { gs2310pplusMSTI3BridgeSTP 1 }
      
gs2310pplusMSTI3BridgeInstance OBJECT-TYPE
   SYNTAX       DisplayString
   MAX-ACCESS   read-only
   STATUS       current
   DESCRIPTION
       "The Bridge instance - CIST, MST1, ..."
   ::= { gs2310pplusMSTI3BridgeSTPStatus 1 }
   
gs2310pplusMSTI3BridgeID OBJECT-TYPE
   SYNTAX       DisplayString
   MAX-ACCESS   read-only
   STATUS       current
   DESCRIPTION
       "The Bridge ID of this Bridge instance."
   ::= { gs2310pplusMSTI3BridgeSTPStatus 2 }
   
gs2310pplusMSTI3RootID OBJECT-TYPE
   SYNTAX       DisplayString
   MAX-ACCESS   read-only
   STATUS       current
   DESCRIPTION
       "The Bridge ID of the currently elected root bridge."
   ::= { gs2310pplusMSTI3BridgeSTPStatus 3 }
   
gs2310pplusMSTI3RootPort OBJECT-TYPE
   SYNTAX       DisplayString
   MAX-ACCESS   read-only
   STATUS       current
   DESCRIPTION
       "The switch port currently assigned the root port role."
   ::= { gs2310pplusMSTI3BridgeSTPStatus 4 }

gs2310pplusMSTI3RootCost OBJECT-TYPE
   SYNTAX       Integer32(0..200000000)
   MAX-ACCESS   read-only
   STATUS       current
   DESCRIPTION
       "Root Path Cost."
   ::= { gs2310pplusMSTI3BridgeSTPStatus 5 }

gs2310pplusMSTI3TopologyFlag OBJECT-TYPE
   SYNTAX       DisplayString
   MAX-ACCESS   read-only
   STATUS       current
   DESCRIPTION
       "The current state of the Topology Change Flag of this Bridge instance."
   ::= { gs2310pplusMSTI3BridgeSTPStatus 8 }

gs2310pplusMSTI3TopologyChangeCount OBJECT-TYPE
   SYNTAX       Counter32
   MAX-ACCESS   read-only
   STATUS       current
   DESCRIPTION
       "The number of times where the topology change flag has been set."
   ::= { gs2310pplusMSTI3BridgeSTPStatus 9 }
   
gs2310pplusMSTI3TopologyChangeLast OBJECT-TYPE
   SYNTAX       DisplayString
   MAX-ACCESS   read-only
   STATUS       current
   DESCRIPTION
       "The time passed since the Topology Flag was last set."
   ::= { gs2310pplusMSTI3BridgeSTPStatus 10 }
   
gs2310pplusMSTI3PortStateTable OBJECT-TYPE
   SYNTAX      SEQUENCE OF Gs2310pplusMSTI3PortStateEntry
   MAX-ACCESS  not-accessible
   STATUS      current
   DESCRIPTION
       " Show MSTI3 Ports and Aggregations State Configurations. "
   ::= { gs2310pplusMSTI3BridgeSTP 2 }

gs2310pplusMSTI3PortStateEntry OBJECT-TYPE
   SYNTAX      Gs2310pplusMSTI3PortStateEntry
   MAX-ACCESS  not-accessible
   STATUS      current
   DESCRIPTION
       ""
   INDEX    { gs2310pplusMSTI3PortStateIndex  }
   ::= { gs2310pplusMSTI3PortStateTable 1 }

Gs2310pplusMSTI3PortStateEntry ::= SEQUENCE {
   gs2310pplusMSTI3PortStateIndex        Integer32,
   gs2310pplusMSTI3PortStatePort         DisplayString,
   gs2310pplusMSTI3PortStatePortID       DisplayString,
   gs2310pplusMSTI3PortStateRole         DisplayString,
   gs2310pplusMSTI3PortStateState        DisplayString,
   gs2310pplusMSTI3PortStatePathCost     Integer32,
   gs2310pplusMSTI3PortStateEdge         DisplayString,
   gs2310pplusMSTI3PortStatePoint2Point  DisplayString,
   gs2310pplusMSTI3PortStateUptime       DisplayString
}

gs2310pplusMSTI3PortStateIndex OBJECT-TYPE
   SYNTAX      Integer32(1..4095)
   MAX-ACCESS  not-accessible
   STATUS      current
   DESCRIPTION
       "table index."
   ::= { gs2310pplusMSTI3PortStateEntry 1 }
   
gs2310pplusMSTI3PortStatePort OBJECT-TYPE
   SYNTAX      DisplayString
   MAX-ACCESS  read-only
   STATUS      current
   DESCRIPTION
       "The switch port number of the logical STP port."
   ::= { gs2310pplusMSTI3PortStateEntry 2 }
   
gs2310pplusMSTI3PortStatePortID OBJECT-TYPE
   SYNTAX      DisplayString
   MAX-ACCESS  read-only
   STATUS      current
   DESCRIPTION
       "The port id as used by the STP protocol. 
        This is the priority part and the logical port index of the bridge port."
   ::= { gs2310pplusMSTI3PortStateEntry 3 }
   
gs2310pplusMSTI3PortStateRole OBJECT-TYPE
   SYNTAX      DisplayString
   MAX-ACCESS  read-only
   STATUS      current
   DESCRIPTION
       "The current STP port role."
   ::= { gs2310pplusMSTI3PortStateEntry 4 }
   
gs2310pplusMSTI3PortStateState OBJECT-TYPE
   SYNTAX      DisplayString
   MAX-ACCESS  read-only
   STATUS      current
   DESCRIPTION
       "The current STP port state."
   ::= { gs2310pplusMSTI3PortStateEntry 5 }
   
gs2310pplusMSTI3PortStatePathCost OBJECT-TYPE
   SYNTAX      Integer32(0..200000000)
   MAX-ACCESS  read-only
   STATUS      current
   DESCRIPTION
       "The current STP port path cost."
   ::= { gs2310pplusMSTI3PortStateEntry 6 }
   
gs2310pplusMSTI3PortStateEdge OBJECT-TYPE
   SYNTAX      DisplayString
   MAX-ACCESS  read-only
   STATUS      current
   DESCRIPTION
       "The current STP port Edge Flag."
   ::= { gs2310pplusMSTI3PortStateEntry 7 }
   
gs2310pplusMSTI3PortStatePoint2Point OBJECT-TYPE
   SYNTAX      DisplayString
   MAX-ACCESS  read-only
   STATUS      current
   DESCRIPTION
       "The current STP port point-to-point flag."
   ::= { gs2310pplusMSTI3PortStateEntry 8 }
   
gs2310pplusMSTI3PortStateUptime OBJECT-TYPE
   SYNTAX      DisplayString
   MAX-ACCESS  read-only
   STATUS      current
   DESCRIPTION
       "The time since the bridge port was last initialized."
   ::= { gs2310pplusMSTI3PortStateEntry 9 }
   
gs2310pplusMSTI4BridgeSTP                                                        OBJECT IDENTIFIER ::= { gs2310pplusSTPBridgeStatus 5 }

gs2310pplusMSTI4BridgeSTPStatus                                                  OBJECT IDENTIFIER ::= { gs2310pplusMSTI4BridgeSTP 1 }
      
gs2310pplusMSTI4BridgeInstance OBJECT-TYPE
   SYNTAX       DisplayString
   MAX-ACCESS   read-only
   STATUS       current
   DESCRIPTION
       "The Bridge instance - CIST, MST1, ..."
   ::= { gs2310pplusMSTI4BridgeSTPStatus 1 }
   
gs2310pplusMSTI4BridgeID OBJECT-TYPE
   SYNTAX       DisplayString
   MAX-ACCESS   read-only
   STATUS       current
   DESCRIPTION
       "The Bridge ID of this Bridge instance."
   ::= { gs2310pplusMSTI4BridgeSTPStatus 2 }
   
gs2310pplusMSTI4RootID OBJECT-TYPE
   SYNTAX       DisplayString
   MAX-ACCESS   read-only
   STATUS       current
   DESCRIPTION
       "The Bridge ID of the currently elected root bridge."
   ::= { gs2310pplusMSTI4BridgeSTPStatus 3 }
   
gs2310pplusMSTI4RootPort OBJECT-TYPE
   SYNTAX       DisplayString
   MAX-ACCESS   read-only
   STATUS       current
   DESCRIPTION
       "The switch port currently assigned the root port role."
   ::= { gs2310pplusMSTI4BridgeSTPStatus 4 }

gs2310pplusMSTI4RootCost OBJECT-TYPE
   SYNTAX       Integer32(0..200000000)
   MAX-ACCESS   read-only
   STATUS       current
   DESCRIPTION
       "Root Path Cost."
   ::= { gs2310pplusMSTI4BridgeSTPStatus 5 }

gs2310pplusMSTI4TopologyFlag OBJECT-TYPE
   SYNTAX       DisplayString
   MAX-ACCESS   read-only
   STATUS       current
   DESCRIPTION
       "The current state of the Topology Change Flag of this Bridge instance."
   ::= { gs2310pplusMSTI4BridgeSTPStatus 8 }

gs2310pplusMSTI4TopologyChangeCount OBJECT-TYPE
   SYNTAX       Counter32
   MAX-ACCESS   read-only
   STATUS       current
   DESCRIPTION
       "The number of times where the topology change flag has been set."
   ::= { gs2310pplusMSTI4BridgeSTPStatus 9 }
   
gs2310pplusMSTI4TopologyChangeLast OBJECT-TYPE
   SYNTAX       DisplayString
   MAX-ACCESS   read-only
   STATUS       current
   DESCRIPTION
       "The time passed since the Topology Flag was last set."
   ::= { gs2310pplusMSTI4BridgeSTPStatus 10 }
   
gs2310pplusMSTI4PortStateTable OBJECT-TYPE
   SYNTAX      SEQUENCE OF Gs2310pplusMSTI4PortStateEntry
   MAX-ACCESS  not-accessible
   STATUS      current
   DESCRIPTION
       " Show MSTI4 Ports and Aggregations State Configurations. "
   ::= { gs2310pplusMSTI4BridgeSTP 2 }

gs2310pplusMSTI4PortStateEntry OBJECT-TYPE
   SYNTAX      Gs2310pplusMSTI4PortStateEntry
   MAX-ACCESS  not-accessible
   STATUS      current
   DESCRIPTION
       ""
   INDEX    { gs2310pplusMSTI4PortStateIndex  }
   ::= { gs2310pplusMSTI4PortStateTable 1 }

Gs2310pplusMSTI4PortStateEntry ::= SEQUENCE {
   gs2310pplusMSTI4PortStateIndex        Integer32,
   gs2310pplusMSTI4PortStatePort         DisplayString,
   gs2310pplusMSTI4PortStatePortID       DisplayString,
   gs2310pplusMSTI4PortStateRole         DisplayString,
   gs2310pplusMSTI4PortStateState        DisplayString,
   gs2310pplusMSTI4PortStatePathCost     Integer32,
   gs2310pplusMSTI4PortStateEdge         DisplayString,
   gs2310pplusMSTI4PortStatePoint2Point  DisplayString,
   gs2310pplusMSTI4PortStateUptime       DisplayString
}

gs2310pplusMSTI4PortStateIndex OBJECT-TYPE
   SYNTAX      Integer32(1..4095)
   MAX-ACCESS  not-accessible
   STATUS      current
   DESCRIPTION
       "table index."
   ::= { gs2310pplusMSTI4PortStateEntry 1 }
   
gs2310pplusMSTI4PortStatePort OBJECT-TYPE
   SYNTAX      DisplayString
   MAX-ACCESS  read-only
   STATUS      current
   DESCRIPTION
       "The switch port number of the logical STP port."
   ::= { gs2310pplusMSTI4PortStateEntry 2 }
   
gs2310pplusMSTI4PortStatePortID OBJECT-TYPE
   SYNTAX      DisplayString
   MAX-ACCESS  read-only
   STATUS      current
   DESCRIPTION
       "The port id as used by the STP protocol. 
        This is the priority part and the logical port index of the bridge port."
   ::= { gs2310pplusMSTI4PortStateEntry 3 }
   
gs2310pplusMSTI4PortStateRole OBJECT-TYPE
   SYNTAX      DisplayString
   MAX-ACCESS  read-only
   STATUS      current
   DESCRIPTION
       "The current STP port role."
   ::= { gs2310pplusMSTI4PortStateEntry 4 }
   
gs2310pplusMSTI4PortStateState OBJECT-TYPE
   SYNTAX      DisplayString
   MAX-ACCESS  read-only
   STATUS      current
   DESCRIPTION
       "The current STP port state."
   ::= { gs2310pplusMSTI4PortStateEntry 5 }
   
gs2310pplusMSTI4PortStatePathCost OBJECT-TYPE
   SYNTAX      Integer32(0..200000000)
   MAX-ACCESS  read-only
   STATUS      current
   DESCRIPTION
       "The current STP port path cost."
   ::= { gs2310pplusMSTI4PortStateEntry 6 }
   
gs2310pplusMSTI4PortStateEdge OBJECT-TYPE
   SYNTAX      DisplayString
   MAX-ACCESS  read-only
   STATUS      current
   DESCRIPTION
       "The current STP port Edge Flag."
   ::= { gs2310pplusMSTI4PortStateEntry 7 }
   
gs2310pplusMSTI4PortStatePoint2Point OBJECT-TYPE
   SYNTAX      DisplayString
   MAX-ACCESS  read-only
   STATUS      current
   DESCRIPTION
       "The current STP port point-to-point flag."
   ::= { gs2310pplusMSTI4PortStateEntry 8 }
   
gs2310pplusMSTI4PortStateUptime OBJECT-TYPE
   SYNTAX      DisplayString
   MAX-ACCESS  read-only
   STATUS      current
   DESCRIPTION
       "The time since the bridge port was last initialized."
   ::= { gs2310pplusMSTI4PortStateEntry 9 }
   
gs2310pplusMSTI5BridgeSTP                                                        OBJECT IDENTIFIER ::= { gs2310pplusSTPBridgeStatus 6 }

gs2310pplusMSTI5BridgeSTPStatus                                                  OBJECT IDENTIFIER ::= { gs2310pplusMSTI5BridgeSTP 1 }
      
gs2310pplusMSTI5BridgeInstance OBJECT-TYPE
   SYNTAX       DisplayString
   MAX-ACCESS   read-only
   STATUS       current
   DESCRIPTION
       "The Bridge instance - CIST, MST1, ..."
   ::= { gs2310pplusMSTI5BridgeSTPStatus 1 }
   
gs2310pplusMSTI5BridgeID OBJECT-TYPE
   SYNTAX       DisplayString
   MAX-ACCESS   read-only
   STATUS       current
   DESCRIPTION
       "The Bridge ID of this Bridge instance."
   ::= { gs2310pplusMSTI5BridgeSTPStatus 2 }
   
gs2310pplusMSTI5RootID OBJECT-TYPE
   SYNTAX       DisplayString
   MAX-ACCESS   read-only
   STATUS       current
   DESCRIPTION
       "The Bridge ID of the currently elected root bridge."
   ::= { gs2310pplusMSTI5BridgeSTPStatus 3 }
   
gs2310pplusMSTI5RootPort OBJECT-TYPE
   SYNTAX       DisplayString
   MAX-ACCESS   read-only
   STATUS       current
   DESCRIPTION
       "The switch port currently assigned the root port role."
   ::= { gs2310pplusMSTI5BridgeSTPStatus 4 }

gs2310pplusMSTI5RootCost OBJECT-TYPE
   SYNTAX       Integer32(0..200000000)
   MAX-ACCESS   read-only
   STATUS       current
   DESCRIPTION
       "Root Path Cost."
   ::= { gs2310pplusMSTI5BridgeSTPStatus 5 }

gs2310pplusMSTI5TopologyFlag OBJECT-TYPE
   SYNTAX       DisplayString
   MAX-ACCESS   read-only
   STATUS       current
   DESCRIPTION
       "The current state of the Topology Change Flag of this Bridge instance."
   ::= { gs2310pplusMSTI5BridgeSTPStatus 8 }

gs2310pplusMSTI5TopologyChangeCount OBJECT-TYPE
   SYNTAX       Counter32
   MAX-ACCESS   read-only
   STATUS       current
   DESCRIPTION
       "The number of times where the topology change flag has been set."
   ::= { gs2310pplusMSTI5BridgeSTPStatus 9 }
   
gs2310pplusMSTI5TopologyChangeLast OBJECT-TYPE
   SYNTAX       DisplayString
   MAX-ACCESS   read-only
   STATUS       current
   DESCRIPTION
       "The time passed since the Topology Flag was last set."
   ::= { gs2310pplusMSTI5BridgeSTPStatus 10 }
   
gs2310pplusMSTI5PortStateTable OBJECT-TYPE
   SYNTAX      SEQUENCE OF Gs2310pplusMSTI5PortStateEntry
   MAX-ACCESS  not-accessible
   STATUS      current
   DESCRIPTION
       " Show MSTI5 Ports and Aggregations State Configurations. "
   ::= { gs2310pplusMSTI5BridgeSTP 2 }

gs2310pplusMSTI5PortStateEntry OBJECT-TYPE
   SYNTAX      Gs2310pplusMSTI5PortStateEntry
   MAX-ACCESS  not-accessible
   STATUS      current
   DESCRIPTION
       ""
   INDEX    { gs2310pplusMSTI5PortStateIndex  }
   ::= { gs2310pplusMSTI5PortStateTable 1 }

Gs2310pplusMSTI5PortStateEntry ::= SEQUENCE {
   gs2310pplusMSTI5PortStateIndex        Integer32,
   gs2310pplusMSTI5PortStatePort         DisplayString,
   gs2310pplusMSTI5PortStatePortID       DisplayString,
   gs2310pplusMSTI5PortStateRole         DisplayString,
   gs2310pplusMSTI5PortStateState        DisplayString,
   gs2310pplusMSTI5PortStatePathCost     Integer32,
   gs2310pplusMSTI5PortStateEdge         DisplayString,
   gs2310pplusMSTI5PortStatePoint2Point  DisplayString,
   gs2310pplusMSTI5PortStateUptime       DisplayString
}

gs2310pplusMSTI5PortStateIndex OBJECT-TYPE
   SYNTAX      Integer32(1..4095)
   MAX-ACCESS  not-accessible
   STATUS      current
   DESCRIPTION
       "table index."
   ::= { gs2310pplusMSTI5PortStateEntry 1 }
   
gs2310pplusMSTI5PortStatePort OBJECT-TYPE
   SYNTAX      DisplayString
   MAX-ACCESS  read-only
   STATUS      current
   DESCRIPTION
       "The switch port number of the logical STP port."
   ::= { gs2310pplusMSTI5PortStateEntry 2 }
   
gs2310pplusMSTI5PortStatePortID OBJECT-TYPE
   SYNTAX      DisplayString
   MAX-ACCESS  read-only
   STATUS      current
   DESCRIPTION
       "The port id as used by the STP protocol. 
        This is the priority part and the logical port index of the bridge port."
   ::= { gs2310pplusMSTI5PortStateEntry 3 }
   
gs2310pplusMSTI5PortStateRole OBJECT-TYPE
   SYNTAX      DisplayString
   MAX-ACCESS  read-only
   STATUS      current
   DESCRIPTION
       "The current STP port role."
   ::= { gs2310pplusMSTI5PortStateEntry 4 }
   
gs2310pplusMSTI5PortStateState OBJECT-TYPE
   SYNTAX      DisplayString
   MAX-ACCESS  read-only
   STATUS      current
   DESCRIPTION
       "The current STP port state."
   ::= { gs2310pplusMSTI5PortStateEntry 5 }
   
gs2310pplusMSTI5PortStatePathCost OBJECT-TYPE
   SYNTAX      Integer32(0..200000000)
   MAX-ACCESS  read-only
   STATUS      current
   DESCRIPTION
       "The current STP port path cost."
   ::= { gs2310pplusMSTI5PortStateEntry 6 }
   
gs2310pplusMSTI5PortStateEdge OBJECT-TYPE
   SYNTAX      DisplayString
   MAX-ACCESS  read-only
   STATUS      current
   DESCRIPTION
       "The current STP port Edge Flag."
   ::= { gs2310pplusMSTI5PortStateEntry 7 }
   
gs2310pplusMSTI5PortStatePoint2Point OBJECT-TYPE
   SYNTAX      DisplayString
   MAX-ACCESS  read-only
   STATUS      current
   DESCRIPTION
       "The current STP port point-to-point flag."
   ::= { gs2310pplusMSTI5PortStateEntry 8 }
   
gs2310pplusMSTI5PortStateUptime OBJECT-TYPE
   SYNTAX      DisplayString
   MAX-ACCESS  read-only
   STATUS      current
   DESCRIPTION
       "The time since the bridge port was last initialized."
   ::= { gs2310pplusMSTI5PortStateEntry 9 }
   
gs2310pplusMSTI6BridgeSTP                                                        OBJECT IDENTIFIER ::= { gs2310pplusSTPBridgeStatus 7 }

gs2310pplusMSTI6BridgeSTPStatus                                                  OBJECT IDENTIFIER ::= { gs2310pplusMSTI6BridgeSTP 1 }
      
gs2310pplusMSTI6BridgeInstance OBJECT-TYPE
   SYNTAX       DisplayString
   MAX-ACCESS   read-only
   STATUS       current
   DESCRIPTION
       "The Bridge instance - CIST, MST1, ..."
   ::= { gs2310pplusMSTI6BridgeSTPStatus 1 }
   
gs2310pplusMSTI6BridgeID OBJECT-TYPE
   SYNTAX       DisplayString
   MAX-ACCESS   read-only
   STATUS       current
   DESCRIPTION
       "The Bridge ID of this Bridge instance."
   ::= { gs2310pplusMSTI6BridgeSTPStatus 2 }
   
gs2310pplusMSTI6RootID OBJECT-TYPE
   SYNTAX       DisplayString
   MAX-ACCESS   read-only
   STATUS       current
   DESCRIPTION
       "The Bridge ID of the currently elected root bridge."
   ::= { gs2310pplusMSTI6BridgeSTPStatus 3 }
   
gs2310pplusMSTI6RootPort OBJECT-TYPE
   SYNTAX       DisplayString
   MAX-ACCESS   read-only
   STATUS       current
   DESCRIPTION
       "The switch port currently assigned the root port role."
   ::= { gs2310pplusMSTI6BridgeSTPStatus 4 }

gs2310pplusMSTI6RootCost OBJECT-TYPE
   SYNTAX       Integer32(0..200000000)
   MAX-ACCESS   read-only
   STATUS       current
   DESCRIPTION
       "Root Path Cost."
   ::= { gs2310pplusMSTI6BridgeSTPStatus 5 }

gs2310pplusMSTI6TopologyFlag OBJECT-TYPE
   SYNTAX       DisplayString
   MAX-ACCESS   read-only
   STATUS       current
   DESCRIPTION
       "The current state of the Topology Change Flag of this Bridge instance."
   ::= { gs2310pplusMSTI6BridgeSTPStatus 8 }

gs2310pplusMSTI6TopologyChangeCount OBJECT-TYPE
   SYNTAX       Counter32
   MAX-ACCESS   read-only
   STATUS       current
   DESCRIPTION
       "The number of times where the topology change flag has been set."
   ::= { gs2310pplusMSTI6BridgeSTPStatus 9 }
   
gs2310pplusMSTI6TopologyChangeLast OBJECT-TYPE
   SYNTAX       DisplayString
   MAX-ACCESS   read-only
   STATUS       current
   DESCRIPTION
       "The time passed since the Topology Flag was last set."
   ::= { gs2310pplusMSTI6BridgeSTPStatus 10 }
   
gs2310pplusMSTI6PortStateTable OBJECT-TYPE
   SYNTAX      SEQUENCE OF Gs2310pplusMSTI6PortStateEntry
   MAX-ACCESS  not-accessible
   STATUS      current
   DESCRIPTION
       " Show MSTI6 Ports and Aggregations State Configurations. "
   ::= { gs2310pplusMSTI6BridgeSTP 2 }

gs2310pplusMSTI6PortStateEntry OBJECT-TYPE
   SYNTAX      Gs2310pplusMSTI6PortStateEntry
   MAX-ACCESS  not-accessible
   STATUS      current
   DESCRIPTION
       ""
   INDEX    { gs2310pplusMSTI6PortStateIndex  }
   ::= { gs2310pplusMSTI6PortStateTable 1 }

Gs2310pplusMSTI6PortStateEntry ::= SEQUENCE {
   gs2310pplusMSTI6PortStateIndex        Integer32,
   gs2310pplusMSTI6PortStatePort         DisplayString,
   gs2310pplusMSTI6PortStatePortID       DisplayString,
   gs2310pplusMSTI6PortStateRole         DisplayString,
   gs2310pplusMSTI6PortStateState        DisplayString,
   gs2310pplusMSTI6PortStatePathCost     Integer32,
   gs2310pplusMSTI6PortStateEdge         DisplayString,
   gs2310pplusMSTI6PortStatePoint2Point  DisplayString,
   gs2310pplusMSTI6PortStateUptime       DisplayString
}

gs2310pplusMSTI6PortStateIndex OBJECT-TYPE
   SYNTAX      Integer32(1..4095)
   MAX-ACCESS  not-accessible
   STATUS      current
   DESCRIPTION
       "table index."
   ::= { gs2310pplusMSTI6PortStateEntry 1 }
   
gs2310pplusMSTI6PortStatePort OBJECT-TYPE
   SYNTAX      DisplayString
   MAX-ACCESS  read-only
   STATUS      current
   DESCRIPTION
       "The switch port number of the logical STP port."
   ::= { gs2310pplusMSTI6PortStateEntry 2 }
   
gs2310pplusMSTI6PortStatePortID OBJECT-TYPE
   SYNTAX      DisplayString
   MAX-ACCESS  read-only
   STATUS      current
   DESCRIPTION
       "The port id as used by the STP protocol. 
        This is the priority part and the logical port index of the bridge port."
   ::= { gs2310pplusMSTI6PortStateEntry 3 }
   
gs2310pplusMSTI6PortStateRole OBJECT-TYPE
   SYNTAX      DisplayString
   MAX-ACCESS  read-only
   STATUS      current
   DESCRIPTION
       "The current STP port role."
   ::= { gs2310pplusMSTI6PortStateEntry 4 }
   
gs2310pplusMSTI6PortStateState OBJECT-TYPE
   SYNTAX      DisplayString
   MAX-ACCESS  read-only
   STATUS      current
   DESCRIPTION
       "The current STP port state."
   ::= { gs2310pplusMSTI6PortStateEntry 5 }
   
gs2310pplusMSTI6PortStatePathCost OBJECT-TYPE
   SYNTAX      Integer32(0..200000000)
   MAX-ACCESS  read-only
   STATUS      current
   DESCRIPTION
       "The current STP port path cost."
   ::= { gs2310pplusMSTI6PortStateEntry 6 }
   
gs2310pplusMSTI6PortStateEdge OBJECT-TYPE
   SYNTAX      DisplayString
   MAX-ACCESS  read-only
   STATUS      current
   DESCRIPTION
       "The current STP port Edge Flag."
   ::= { gs2310pplusMSTI6PortStateEntry 7 }
   
gs2310pplusMSTI6PortStatePoint2Point OBJECT-TYPE
   SYNTAX      DisplayString
   MAX-ACCESS  read-only
   STATUS      current
   DESCRIPTION
       "The current STP port point-to-point flag."
   ::= { gs2310pplusMSTI6PortStateEntry 8 }
   
gs2310pplusMSTI6PortStateUptime OBJECT-TYPE
   SYNTAX      DisplayString
   MAX-ACCESS  read-only
   STATUS      current
   DESCRIPTION
       "The time since the bridge port was last initialized."
   ::= { gs2310pplusMSTI6PortStateEntry 9 }
   
gs2310pplusMSTI7BridgeSTP                                                        OBJECT IDENTIFIER ::= { gs2310pplusSTPBridgeStatus 8 }

gs2310pplusMSTI7BridgeSTPStatus                                                  OBJECT IDENTIFIER ::= { gs2310pplusMSTI7BridgeSTP 1 }
      
gs2310pplusMSTI7BridgeInstance OBJECT-TYPE
   SYNTAX       DisplayString
   MAX-ACCESS   read-only
   STATUS       current
   DESCRIPTION
       "The Bridge instance - CIST, MST1, ..."
   ::= { gs2310pplusMSTI7BridgeSTPStatus 1 }
   
gs2310pplusMSTI7BridgeID OBJECT-TYPE
   SYNTAX       DisplayString
   MAX-ACCESS   read-only
   STATUS       current
   DESCRIPTION
       "The Bridge ID of this Bridge instance."
   ::= { gs2310pplusMSTI7BridgeSTPStatus 2 }
   
gs2310pplusMSTI7RootID OBJECT-TYPE
   SYNTAX       DisplayString
   MAX-ACCESS   read-only
   STATUS       current
   DESCRIPTION
       "The Bridge ID of the currently elected root bridge."
   ::= { gs2310pplusMSTI7BridgeSTPStatus 3 }
   
gs2310pplusMSTI7RootPort OBJECT-TYPE
   SYNTAX       DisplayString
   MAX-ACCESS   read-only
   STATUS       current
   DESCRIPTION
       "The switch port currently assigned the root port role."
   ::= { gs2310pplusMSTI7BridgeSTPStatus 4 }

gs2310pplusMSTI7RootCost OBJECT-TYPE
   SYNTAX       Integer32(0..200000000)
   MAX-ACCESS   read-only
   STATUS       current
   DESCRIPTION
       "Root Path Cost."
   ::= { gs2310pplusMSTI7BridgeSTPStatus 5 }

gs2310pplusMSTI7TopologyFlag OBJECT-TYPE
   SYNTAX       DisplayString
   MAX-ACCESS   read-only
   STATUS       current
   DESCRIPTION
       "The current state of the Topology Change Flag of this Bridge instance."
   ::= { gs2310pplusMSTI7BridgeSTPStatus 8 }

gs2310pplusMSTI7TopologyChangeCount OBJECT-TYPE
   SYNTAX       Counter32
   MAX-ACCESS   read-only
   STATUS       current
   DESCRIPTION
       "The number of times where the topology change flag has been set."
   ::= { gs2310pplusMSTI7BridgeSTPStatus 9 }
   
gs2310pplusMSTI7TopologyChangeLast OBJECT-TYPE
   SYNTAX       DisplayString
   MAX-ACCESS   read-only
   STATUS       current
   DESCRIPTION
       "The time passed since the Topology Flag was last set."
   ::= { gs2310pplusMSTI7BridgeSTPStatus 10 }
   
gs2310pplusMSTI7PortStateTable OBJECT-TYPE
   SYNTAX      SEQUENCE OF Gs2310pplusMSTI7PortStateEntry
   MAX-ACCESS  not-accessible
   STATUS      current
   DESCRIPTION
       " Show MSTI7 Ports and Aggregations State Configurations. "
   ::= { gs2310pplusMSTI7BridgeSTP 2 }

gs2310pplusMSTI7PortStateEntry OBJECT-TYPE
   SYNTAX      Gs2310pplusMSTI7PortStateEntry
   MAX-ACCESS  not-accessible
   STATUS      current
   DESCRIPTION
       ""
   INDEX    { gs2310pplusMSTI7PortStateIndex  }
   ::= { gs2310pplusMSTI7PortStateTable 1 }

Gs2310pplusMSTI7PortStateEntry ::= SEQUENCE {
   gs2310pplusMSTI7PortStateIndex        Integer32,
   gs2310pplusMSTI7PortStatePort         DisplayString,
   gs2310pplusMSTI7PortStatePortID       DisplayString,
   gs2310pplusMSTI7PortStateRole         DisplayString,
   gs2310pplusMSTI7PortStateState        DisplayString,
   gs2310pplusMSTI7PortStatePathCost     Integer32,
   gs2310pplusMSTI7PortStateEdge         DisplayString,
   gs2310pplusMSTI7PortStatePoint2Point  DisplayString,
   gs2310pplusMSTI7PortStateUptime       DisplayString
}

gs2310pplusMSTI7PortStateIndex OBJECT-TYPE
   SYNTAX      Integer32(1..4095)
   MAX-ACCESS  not-accessible
   STATUS      current
   DESCRIPTION
       "table index."
   ::= { gs2310pplusMSTI7PortStateEntry 1 }
   
gs2310pplusMSTI7PortStatePort OBJECT-TYPE
   SYNTAX      DisplayString
   MAX-ACCESS  read-only
   STATUS      current
   DESCRIPTION
       "The switch port number of the logical STP port."
   ::= { gs2310pplusMSTI7PortStateEntry 2 }
   
gs2310pplusMSTI7PortStatePortID OBJECT-TYPE
   SYNTAX      DisplayString
   MAX-ACCESS  read-only
   STATUS      current
   DESCRIPTION
       "The port id as used by the STP protocol. 
        This is the priority part and the logical port index of the bridge port."
   ::= { gs2310pplusMSTI7PortStateEntry 3 }
   
gs2310pplusMSTI7PortStateRole OBJECT-TYPE
   SYNTAX      DisplayString
   MAX-ACCESS  read-only
   STATUS      current
   DESCRIPTION
       "The current STP port role."
   ::= { gs2310pplusMSTI7PortStateEntry 4 }
   
gs2310pplusMSTI7PortStateState OBJECT-TYPE
   SYNTAX      DisplayString
   MAX-ACCESS  read-only
   STATUS      current
   DESCRIPTION
       "The current STP port state."
   ::= { gs2310pplusMSTI7PortStateEntry 5 }
   
gs2310pplusMSTI7PortStatePathCost OBJECT-TYPE
   SYNTAX      Integer32(0..200000000)
   MAX-ACCESS  read-only
   STATUS      current
   DESCRIPTION
       "The current STP port path cost."
   ::= { gs2310pplusMSTI7PortStateEntry 6 }
   
gs2310pplusMSTI7PortStateEdge OBJECT-TYPE
   SYNTAX      DisplayString
   MAX-ACCESS  read-only
   STATUS      current
   DESCRIPTION
       "The current STP port Edge Flag."
   ::= { gs2310pplusMSTI7PortStateEntry 7 }
   
gs2310pplusMSTI7PortStatePoint2Point OBJECT-TYPE
   SYNTAX      DisplayString
   MAX-ACCESS  read-only
   STATUS      current
   DESCRIPTION
       "The current STP port point-to-point flag."
   ::= { gs2310pplusMSTI7PortStateEntry 8 }
   
gs2310pplusMSTI7PortStateUptime OBJECT-TYPE
   SYNTAX      DisplayString
   MAX-ACCESS  read-only
   STATUS      current
   DESCRIPTION
       "The time since the bridge port was last initialized."
   ::= { gs2310pplusMSTI7PortStateEntry 9 }
   
gs2310pplusSTPPortStatusTable OBJECT-TYPE
   SYNTAX      SEQUENCE OF Gs2310pplusSTPPortStatusEntry
   MAX-ACCESS  not-accessible
   STATUS      current
   DESCRIPTION
       " Show STP Port Status."
   ::= { gs2310pplusSTP 9 }

gs2310pplusSTPPortStatusEntry OBJECT-TYPE
   SYNTAX      Gs2310pplusSTPPortStatusEntry
   MAX-ACCESS  not-accessible
   STATUS      current
   DESCRIPTION
       ""
   INDEX    { gs2310pplusSTPPortStatusPort  }
   ::= { gs2310pplusSTPPortStatusTable 1 }

Gs2310pplusSTPPortStatusEntry ::= SEQUENCE {
   gs2310pplusSTPPortStatusPort         Integer32,
   gs2310pplusSTPPortStatusCISTRole     DisplayString,
   gs2310pplusSTPPortStatusCISTState    DisplayString,
   gs2310pplusSTPPortStatusUptime       DisplayString
}

gs2310pplusSTPPortStatusPort OBJECT-TYPE
   SYNTAX      Integer32(1..4095)
   MAX-ACCESS  not-accessible
   STATUS      current
   DESCRIPTION
       " port, range : 1 - port number. "
   ::= { gs2310pplusSTPPortStatusEntry 1 }

gs2310pplusSTPPortStatusCISTRole OBJECT-TYPE
   SYNTAX      DisplayString
   MAX-ACCESS  read-only
   STATUS      current
   DESCRIPTION
       " The current STP port role of the CIST port. "
   ::= { gs2310pplusSTPPortStatusEntry 2 }

gs2310pplusSTPPortStatusCISTState OBJECT-TYPE
   SYNTAX      DisplayString
   MAX-ACCESS  read-only
   STATUS      current
   DESCRIPTION
       " The current STP port state of the CIST port. "
   ::= { gs2310pplusSTPPortStatusEntry 3 }

gs2310pplusSTPPortStatusUptime OBJECT-TYPE
   SYNTAX      DisplayString
   MAX-ACCESS  read-only
   STATUS      current
   DESCRIPTION
       " The time since the bridge port was last initialized. "
   ::= { gs2310pplusSTPPortStatusEntry 4 }
   
gs2310pplusSTPPortStatisticsTable OBJECT-TYPE
   SYNTAX      SEQUENCE OF Gs2310pplusSTPPortStatisticsEntry
   MAX-ACCESS  not-accessible
   STATUS      current
   DESCRIPTION
       " Show STP Port Statistics."
   ::= { gs2310pplusSTP 10 }

gs2310pplusSTPPortStatisticsEntry OBJECT-TYPE
   SYNTAX      Gs2310pplusSTPPortStatisticsEntry
   MAX-ACCESS  not-accessible
   STATUS      current
   DESCRIPTION
       ""
   INDEX    { gs2310pplusSTPStatisticsIndex  }
   ::= { gs2310pplusSTPPortStatisticsTable 1 }

Gs2310pplusSTPPortStatisticsEntry ::= SEQUENCE {
   gs2310pplusSTPStatisticsIndex            Integer32,
   gs2310pplusSTPStatisticsPort             DisplayString,
   gs2310pplusSTPStatisticsTxMSTP           Counter32,
   gs2310pplusSTPStatisticsTxRSTP           Counter32,
   gs2310pplusSTPStatisticsTxSTP            Counter32,
   gs2310pplusSTPStatisticsTxTCN            Counter32,
   gs2310pplusSTPStatisticsRxMSTP           Counter32,
   gs2310pplusSTPStatisticsRxRSTP           Counter32,
   gs2310pplusSTPStatisticsRxSTP            Counter32,
   gs2310pplusSTPStatisticsRxTCN            Counter32,
   gs2310pplusSTPStatisticsDiscardedUnknown Counter32,
   gs2310pplusSTPStatisticsDiscardedIllegal Counter32
}

gs2310pplusSTPStatisticsIndex OBJECT-TYPE
   SYNTAX      Integer32(1..4095)
   MAX-ACCESS  not-accessible
   STATUS      current
   DESCRIPTION
       "table index."
   ::= { gs2310pplusSTPPortStatisticsEntry 1 }
   
gs2310pplusSTPStatisticsPort OBJECT-TYPE
   SYNTAX      DisplayString
   MAX-ACCESS  not-accessible
   STATUS      current
   DESCRIPTION
       " port, range : 1 - port number. "
   ::= { gs2310pplusSTPPortStatisticsEntry 2 }

gs2310pplusSTPStatisticsTxMSTP OBJECT-TYPE
   SYNTAX      Counter32
   MAX-ACCESS  read-only
   STATUS      current
   DESCRIPTION
       " The number of MSTP Configuration BPDU's received/transmitted on the port."
   ::= { gs2310pplusSTPPortStatisticsEntry 3 }

gs2310pplusSTPStatisticsTxRSTP OBJECT-TYPE
   SYNTAX      Counter32
   MAX-ACCESS  read-only
   STATUS      current
   DESCRIPTION
       " The number of RSTP Configuration BPDU's received/transmitted on the port. "
   ::= { gs2310pplusSTPPortStatisticsEntry 4 }

gs2310pplusSTPStatisticsTxSTP OBJECT-TYPE
   SYNTAX      Counter32
   MAX-ACCESS  read-only
   STATUS      current
   DESCRIPTION
       " The number of legacy STP Configuration BPDU's received/transmitted on the port. "
   ::= { gs2310pplusSTPPortStatisticsEntry 5 }

gs2310pplusSTPStatisticsTxTCN OBJECT-TYPE
   SYNTAX      Counter32
   MAX-ACCESS  read-only
   STATUS      current
   DESCRIPTION
       " The number of Topology Change Notification BPDU's received/transmitted on the port. "
   ::= { gs2310pplusSTPPortStatisticsEntry 6 }
   
gs2310pplusSTPStatisticsRxMSTP OBJECT-TYPE
   SYNTAX      Counter32
   MAX-ACCESS  read-only
   STATUS      current
   DESCRIPTION
       " The number of MSTP Configuration BPDU's received/transmitted on the port."
   ::= { gs2310pplusSTPPortStatisticsEntry 7 }

gs2310pplusSTPStatisticsRxRSTP OBJECT-TYPE
   SYNTAX      Counter32
   MAX-ACCESS  read-only
   STATUS      current
   DESCRIPTION
       " The number of RSTP Configuration BPDU's received/transmitted on the port. "
   ::= { gs2310pplusSTPPortStatisticsEntry 8 }

gs2310pplusSTPStatisticsRxSTP OBJECT-TYPE
   SYNTAX      Counter32
   MAX-ACCESS  read-only
   STATUS      current
   DESCRIPTION
       " The number of legacy STP Configuration BPDU's received/transmitted on the port. "
   ::= { gs2310pplusSTPPortStatisticsEntry 9 }

gs2310pplusSTPStatisticsRxTCN OBJECT-TYPE
   SYNTAX      Counter32
   MAX-ACCESS  read-only
   STATUS      current
   DESCRIPTION
       " The number of Topology Change Notification BPDU's received/transmitted on the port. "
   ::= { gs2310pplusSTPPortStatisticsEntry 10 }

gs2310pplusSTPStatisticsDiscardedUnknown OBJECT-TYPE
   SYNTAX      Counter32
   MAX-ACCESS  read-only
   STATUS      current
   DESCRIPTION
       " The number of unknown Spanning Tree BPDU's received and discarded on the port. "
   ::= { gs2310pplusSTPPortStatisticsEntry 11 }
   
gs2310pplusSTPStatisticsDiscardedIllegal OBJECT-TYPE
   SYNTAX      Counter32
   MAX-ACCESS  read-only
   STATUS      current
   DESCRIPTION
       " The number of illegal Spanning Tree BPDU's received and discarded on the port. "
   ::= { gs2310pplusSTPPortStatisticsEntry 12 }


gs2310pplusFilteringDataBase                                                  OBJECT IDENTIFIER ::= { gs2310pplusConfiguration 21 }

gs2310pplusFilteringDataBaseConfig                                            OBJECT IDENTIFIER ::= { gs2310pplusFilteringDataBase 1 }

gs2310pplusFilteringDataBaseAgingTime OBJECT-TYPE
   SYNTAX      Integer32(0..1000000)
   MAX-ACCESS  read-write
   STATUS      current
   DESCRIPTION
       "Configure aging time by entering a value here in seconds.
        default: 300,
        range: 10-1000000. 
        Disable automatic aging : 0."
   ::= { gs2310pplusFilteringDataBaseConfig 1 }

gs2310pplusFilteringDataBaseConfigTable OBJECT-TYPE
   SYNTAX      SEQUENCE OF GS2310PPLUSFilteringDataBaseConfigEntry
   MAX-ACCESS  not-accessible
   STATUS      current
   DESCRIPTION
       " "
   ::= { gs2310pplusFilteringDataBaseConfig 2 }

gs2310pplusFilteringDataBaseConfigEntry OBJECT-TYPE
   SYNTAX      GS2310PPLUSFilteringDataBaseConfigEntry
   MAX-ACCESS  not-accessible
   STATUS      current
   DESCRIPTION
       ""
   INDEX    { gs2310pplusFilteringDataBaseConfigPort  }
   ::= { gs2310pplusFilteringDataBaseConfigTable 1 }
   
GS2310PPLUSFilteringDataBaseConfigEntry ::= SEQUENCE {
   gs2310pplusFilteringDataBaseConfigPort        Integer32,
   gs2310pplusFilteringDataBaseConfigLearning    INTEGER
}

gs2310pplusFilteringDataBaseConfigPort OBJECT-TYPE
   SYNTAX      Integer32(1..4095)
   MAX-ACCESS  not-accessible
   STATUS      current
   DESCRIPTION
       " "
   ::= { gs2310pplusFilteringDataBaseConfigEntry 1 }

gs2310pplusFilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2310pplusFilteringDataBaseConfigEntry 2 }


gs2310pplusFilteringDataBaseStaticMAC                                OBJECT IDENTIFIER ::= { gs2310pplusFilteringDataBaseConfig 3 }

gs2310pplusFilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2310pplusFilteringDataBaseStaticMAC 1 }

gs2310pplusFilteringDataBaseStaticMACTable OBJECT-TYPE
   SYNTAX      SEQUENCE OF GS2310PPLUSFilteringDataBaseStaticMACEntry
   MAX-ACCESS  not-accessible
   STATUS      current
   DESCRIPTION
       " "
   ::= { gs2310pplusFilteringDataBaseStaticMAC 2 }

gs2310pplusFilteringDataBaseStaticMACEntry OBJECT-TYPE
   SYNTAX      GS2310PPLUSFilteringDataBaseStaticMACEntry
   MAX-ACCESS  not-accessible
   STATUS      current
   DESCRIPTION
       ""
   INDEX    { gs2310pplusFilteringDataBaseStaticMACIndex  }
   ::= { gs2310pplusFilteringDataBaseStaticMACTable 1 }

GS2310PPLUSFilteringDataBaseStaticMACEntry ::= SEQUENCE {
   gs2310pplusFilteringDataBaseStaticMACIndex	    Integer32,
   gs2310pplusFilteringDataBaseStaticMACVLANId	    Integer32,
   gs2310pplusFilteringDataBaseStaticMACAddress      MacAddress,
   gs2310pplusFilteringDataBaseStaticMACPortMembers  DisplayString,
   gs2310pplusFilteringDataBaseStaticMACRowStatus	INTEGER
}

gs2310pplusFilteringDataBaseStaticMACIndex OBJECT-TYPE
   SYNTAX      Integer32(1..4095)
   MAX-ACCESS  not-accessible
   STATUS      current
   DESCRIPTION
       " "
   ::= { gs2310pplusFilteringDataBaseStaticMACEntry 1 }

gs2310pplusFilteringDataBaseStaticMACVLANId OBJECT-TYPE
   SYNTAX      Integer32(1..4094)
   MAX-ACCESS  read-write
   STATUS      current
   DESCRIPTION
       " VLAN ID, range: 1 - 4094. "
   ::= { gs2310pplusFilteringDataBaseStaticMACEntry 2 }

gs2310pplusFilteringDataBaseStaticMACAddress OBJECT-TYPE
   SYNTAX      MacAddress
   MAX-ACCESS  read-write
   STATUS      current
   DESCRIPTION
       " MAC address, format 0a 1b 2c 3d 4e 5f "
   ::= { gs2310pplusFilteringDataBaseStaticMACEntry 3 }

gs2310pplusFilteringDataBaseStaticMACPortMembers OBJECT-TYPE
   SYNTAX      DisplayString
   MAX-ACCESS  read-write
   STATUS      current
   DESCRIPTION
       "To include the ports in a Static MAC Table"
   ::= { gs2310pplusFilteringDataBaseStaticMACEntry 4 }

gs2310pplusFilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pplusFilteringDataBaseStaticMACEntry 5 }
   

gs2310pplusFilteringDataBaseDynamicMACTable OBJECT-TYPE
   SYNTAX      SEQUENCE OF GS2310PPLUSFilteringDataBaseDynamicMACEntry
   MAX-ACCESS  not-accessible
   STATUS      current
   DESCRIPTION
       " "
   ::= { gs2310pplusFilteringDataBaseConfig 4 }

gs2310pplusFilteringDataBaseDynamicMACEntry OBJECT-TYPE
   SYNTAX      GS2310PPLUSFilteringDataBaseDynamicMACEntry
   MAX-ACCESS  not-accessible
   STATUS      current
   DESCRIPTION
       ""
   INDEX    { gs2310pplusFilteringDataBaseDynamicMACIndex  }
   ::= { gs2310pplusFilteringDataBaseDynamicMACTable 1 }
   
GS2310PPLUSFilteringDataBaseDynamicMACEntry ::= SEQUENCE {
   gs2310pplusFilteringDataBaseDynamicMACIndex	    Integer32,
   gs2310pplusFilteringDataBaseDynamicMACType	    INTEGER,
   gs2310pplusFilteringDataBaseDynamicMACVLAN	    Integer32,
   gs2310pplusFilteringDataBaseDynamicMACAddress     MacAddress,
   gs2310pplusFilteringDataBaseDynamicPortMembers    DisplayString
}

gs2310pplusFilteringDataBaseDynamicMACIndex OBJECT-TYPE
   SYNTAX      Integer32(1..4095)
   MAX-ACCESS  not-accessible
   STATUS      current
   DESCRIPTION
       " "
   ::= { gs2310pplusFilteringDataBaseDynamicMACEntry 1 }

gs2310pplusFilteringDataBaseDynamicMACType OBJECT-TYPE
   SYNTAX      INTEGER { dynamic(0), static(1) }
   MAX-ACCESS  read-only
   STATUS      current
   DESCRIPTION
       "Indicates whether the entry is a static or a dynamic entry."
   ::= { gs2310pplusFilteringDataBaseDynamicMACEntry 2 }

gs2310pplusFilteringDataBaseDynamicMACVLAN OBJECT-TYPE
   SYNTAX      Integer32(1..4094)
   MAX-ACCESS  read-only
   STATUS      current
   DESCRIPTION
       "The VLAN ID of the entry."
   ::= { gs2310pplusFilteringDataBaseDynamicMACEntry 3 }

gs2310pplusFilteringDataBaseDynamicMACAddress OBJECT-TYPE
   SYNTAX      MacAddress
   MAX-ACCESS  read-only
   STATUS      current
   DESCRIPTION
       "The MAC address of the entry."
   ::= { gs2310pplusFilteringDataBaseDynamicMACEntry 4 }
   
gs2310pplusFilteringDataBaseDynamicPortMembers OBJECT-TYPE
   SYNTAX      DisplayString
   MAX-ACCESS  read-only
   STATUS      current
   DESCRIPTION
       "The ports that are members of the entry."
   ::= { gs2310pplusFilteringDataBaseDynamicMACEntry 5 } 


gs2310pplusSFlowAgent                                                  OBJECT IDENTIFIER ::= { gs2310pplusConfiguration 22 }

gs2310pplusSFlowAgentCollector                                            OBJECT IDENTIFIER ::= { gs2310pplusSFlowAgent 1 }

gs2310pplusSFlowAgentReceiverMode OBJECT-TYPE
   SYNTAX      INTEGER { disable(0), enable(1) }
   MAX-ACCESS  read-write
   STATUS      current
   DESCRIPTION
       "default: 0
       0: disable
       1: enable "
   ::= { gs2310pplusSFlowAgentCollector 1 }


gs2310pplusLMC                                                   OBJECT IDENTIFIER ::= { gs2310pplusConfiguration 1500 }

gs2310pplusLMCOperating OBJECT-TYPE
   SYNTAX      INTEGER { disabled(0), enabled(1), try(2) }
   MAX-ACCESS  read-write
   STATUS      current
   DESCRIPTION
       "0: disabled
        1: enabled
        2: try"
   ::= { gs2310pplusLMC 1 }

gs2310pplusLMCConfigViaDhcp OBJECT-TYPE
   SYNTAX      INTEGER { disabled(0), enabled(1) }
   MAX-ACCESS  read-write
   STATUS      current
   DESCRIPTION
       "0: disabled
        1: enabled"
   ::= { gs2310pplusLMC 2 }

gs2310pplusLMCDomain OBJECT-TYPE
   SYNTAX      DisplayString(SIZE(0..255))
   MAX-ACCESS  read-write
   STATUS      current
   DESCRIPTION
       "0: disabled
        1: enabled"
   ::= { gs2310pplusLMC 3 }

gs2310pplusLMCDhcpClientAutoRenew OBJECT-TYPE
   SYNTAX      INTEGER { disabled(0), enabled(1) }
   MAX-ACCESS  read-write
   STATUS      current
   DESCRIPTION
       "0: disabled
        1: enabled"
   ::= { gs2310pplusLMC 4 }
   
gs2310pplusLMCZeroTouchSupport OBJECT-TYPE
   SYNTAX      INTEGER { No(0), Yes(1) }
   MAX-ACCESS  read-only
   STATUS      current
   DESCRIPTION
       "0: No
        1: Yes"
   ::= { gs2310pplusLMC 50 }   
   
gs2310pplusLMCPairingTokenPresent OBJECT-TYPE
   SYNTAX      INTEGER { No(0), Yes(1) }
   MAX-ACCESS  read-only
   STATUS      current
   DESCRIPTION
       "0: No
        1: Yes"
   ::= { gs2310pplusLMC 51 }
   
gs2310pplusLMCClientStatus OBJECT-TYPE
   SYNTAX      DisplayString
   MAX-ACCESS  read-only
   STATUS      current
   DESCRIPTION
           ""
   ::= { gs2310pplusLMC  52 }
   
   
gs2310pplusLMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2310pplusLMC  53 }
   
gs2310pplusLMCControlStatus OBJECT-TYPE
   SYNTAX      INTEGER {Disabled(2), Operating(4)}
   MAX-ACCESS  read-only
   STATUS      current
   DESCRIPTION
           "2: Disabled
            4: Operating"
   ::= { gs2310pplusLMC  54 }          
   
gs2310pplusLMCMonitoringStatus OBJECT-TYPE
   SYNTAX      INTEGER {Disabled(2), Operating(4)}
   MAX-ACCESS  read-only
   STATUS      current
   DESCRIPTION
           "2: Disabled
            4: Operating"
   ::= { gs2310pplusLMC  55 }
   
gs2310pplusLMCConfigurationSource OBJECT-TYPE
   SYNTAX      DisplayString
   MAX-ACCESS  read-only
   STATUS      current
   DESCRIPTION
           ""
   ::= { gs2310pplusLMC  56 }
   
gs2310pplusLMCConfigModified OBJECT-TYPE
   SYNTAX      INTEGER { No(0), Yes(1) }
   MAX-ACCESS  read-only
   STATUS      current
   DESCRIPTION
       "0: No
        1: Yes"
   ::= { gs2310pplusLMC 57 }
   
gs2310pplusLMCDeviceID OBJECT-TYPE
   SYNTAX      DisplayString
   MAX-ACCESS  read-only
   STATUS      current
   DESCRIPTION
           ""
   ::= { gs2310pplusLMC  58 }
   
gs2310pplusLMCRoundTripTime OBJECT-TYPE
   SYNTAX      INTEGER
   MAX-ACCESS  read-only
   STATUS      current
   DESCRIPTION
           ""
   ::= { gs2310pplusLMC  100 }
----------------------------------------------------------------------------------------------------------------------------
gs2310pplusSecurity                                              OBJECT IDENTIFIER ::= { lancomGS2310PPLUS 3 }

gs2310pplusIPSourceGuard                                         OBJECT IDENTIFIER ::= { gs2310pplusSecurity 1 }

gs2310pplusIPSourceGuardConf                                     OBJECT IDENTIFIER ::= { gs2310pplusIPSourceGuard 1 }

gs2310pplusIPSourceGuardMode OBJECT-TYPE
   SYNTAX      INTEGER { disable(0), enable(1) }
   MAX-ACCESS  read-write
   STATUS      current
   DESCRIPTION
       " default:  0
        0: disable
        1: enable"
   ::= { gs2310pplusIPSourceGuardConf 1 }

gs2310pplusIPSourceGuardPortConfigTable OBJECT-TYPE
   SYNTAX      SEQUENCE OF GS2310PPLUSIPSourceGuardPortConfigEntry
   MAX-ACCESS  not-accessible
   STATUS      current
   DESCRIPTION
       " "
   ::= { gs2310pplusIPSourceGuardConf 2 }

gs2310pplusIPSourceGuardPortConfigEntry OBJECT-TYPE
   SYNTAX      GS2310PPLUSIPSourceGuardPortConfigEntry
   MAX-ACCESS  not-accessible
   STATUS      current
   DESCRIPTION
       ""
   INDEX    { gs2310pplusIPSourceGuardPortConfigPort  }
   ::= { gs2310pplusIPSourceGuardPortConfigTable 1 }

GS2310PPLUSIPSourceGuardPortConfigEntry ::= SEQUENCE {
   gs2310pplusIPSourceGuardPortConfigPort               Integer32,
   gs2310pplusIPSourceGuardPortConfigMode               INTEGER,
   gs2310pplusIPSourceGuardPortMaxDynamicClients        Integer32
}

gs2310pplusIPSourceGuardPortConfigPort OBJECT-TYPE
   SYNTAX      Integer32(1..4095)
   MAX-ACCESS  not-accessible
   STATUS      current
   DESCRIPTION
       " "
   ::= { gs2310pplusIPSourceGuardPortConfigEntry 1 }

gs2310pplusIPSourceGuardPortConfigMode OBJECT-TYPE
   SYNTAX      INTEGER { disable(0), enable(1) }
   MAX-ACCESS  read-write
   STATUS      current
   DESCRIPTION
       "default: 0
       0:disable
       1:enable "
   ::= { gs2310pplusIPSourceGuardPortConfigEntry 2 }

gs2310pplusIPSourceGuardPortMaxDynamicClients OBJECT-TYPE
   SYNTAX      Integer32(0..2|99)
   MAX-ACCESS  read-write
   STATUS      current
   DESCRIPTION
       "default: 99
       0~2: Max Dynamic clients
       99:Unlimited "
   ::= { gs2310pplusIPSourceGuardPortConfigEntry 3 }


gs2310pplusIPSourceGuardStatic                                OBJECT IDENTIFIER ::= { gs2310pplusIPSourceGuard 2 }

gs2310pplusIPSourceGuardStaticCreate OBJECT-TYPE
   SYNTAX       INTEGER { none(0), create(1) }
   MAX-ACCESS   read-write
   STATUS       current
   DESCRIPTION
       "default: 0
        0 : None  (read only)
        1 : Create a IP Source Guard"
   ::= { gs2310pplusIPSourceGuardStatic 1 }

gs2310pplusIPSourceGuardStaticTable OBJECT-TYPE
   SYNTAX      SEQUENCE OF GS2310PPLUSIPSourceGuardStaticEntry
   MAX-ACCESS  not-accessible
   STATUS      current
   DESCRIPTION
       " "
   ::= { gs2310pplusIPSourceGuardStatic 2 }

gs2310pplusIPSourceGuardStaticEntry OBJECT-TYPE
   SYNTAX      GS2310PPLUSIPSourceGuardStaticEntry
   MAX-ACCESS  not-accessible
   STATUS      current
   DESCRIPTION
       ""
   INDEX    { gs2310pplusIPSourceGuardStaticIndex  }
   ::= { gs2310pplusIPSourceGuardStaticTable 1 }

GS2310PPLUSIPSourceGuardStaticEntry ::= SEQUENCE {
   gs2310pplusIPSourceGuardStaticIndex         Integer32,
   gs2310pplusIPSourceGuardStaticPort          Integer32,
   gs2310pplusIPSourceGuardStaticVLANId        Integer32,
   gs2310pplusIPSourceGuardStaticIPAddress     IpAddress,
   gs2310pplusIPSourceGuardStaticMACAddress    MacAddress,
   gs2310pplusIPSourceGuardStaticRowStatus     INTEGER
}

gs2310pplusIPSourceGuardStaticIndex OBJECT-TYPE
   SYNTAX      Integer32(1..28)
   MAX-ACCESS  not-accessible
   STATUS      current
   DESCRIPTION
       " "
   ::= { gs2310pplusIPSourceGuardStaticEntry 1 }

gs2310pplusIPSourceGuardStaticPort OBJECT-TYPE
   SYNTAX      Integer32(1..4095)
   MAX-ACCESS  read-write
   STATUS      current
   DESCRIPTION
       " Port, range: 1 - port number. "
   ::= { gs2310pplusIPSourceGuardStaticEntry 2 }

gs2310pplusIPSourceGuardStaticVLANId OBJECT-TYPE
   SYNTAX      Integer32(1..4094)
   MAX-ACCESS  read-write
   STATUS      current
   DESCRIPTION
       " VLAN ID, range: 1 - 4094. "
   ::= { gs2310pplusIPSourceGuardStaticEntry 3 }

gs2310pplusIPSourceGuardStaticIPAddress OBJECT-TYPE
   SYNTAX      IpAddress
   MAX-ACCESS  read-write
   STATUS      current
   DESCRIPTION
       " IP address allowed for doing IP source guard. "
   ::= { gs2310pplusIPSourceGuardStaticEntry 4 }

gs2310pplusIPSourceGuardStaticMACAddress OBJECT-TYPE
   SYNTAX      MacAddress
   MAX-ACCESS  read-write
   STATUS      current
   DESCRIPTION
       " Allowed Source MAC address, format 0a 1b 2c 3d 4e 5f "
   ::= { gs2310pplusIPSourceGuardStaticEntry 5 }

gs2310pplusIPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2310pplusIPSourceGuardStaticEntry 6 }

gs2310pplusIPSourceGuardDynamicTable OBJECT-TYPE
   SYNTAX      SEQUENCE OF GS2310PPLUSIPSourceGuardDynamicEntry
   MAX-ACCESS  not-accessible
   STATUS      current
   DESCRIPTION
       " "
   ::= { gs2310pplusIPSourceGuard 3 }

gs2310pplusIPSourceGuardDynamicEntry OBJECT-TYPE
   SYNTAX      GS2310PPLUSIPSourceGuardDynamicEntry
   MAX-ACCESS  not-accessible
   STATUS      current
   DESCRIPTION
       ""
   INDEX    { gs2310pplusIPSourceGuardDynamicIndex  }
   ::= { gs2310pplusIPSourceGuardDynamicTable 1 }

GS2310PPLUSIPSourceGuardDynamicEntry ::= SEQUENCE {
   gs2310pplusIPSourceGuardDynamicIndex          Integer32,
   gs2310pplusIPSourceGuardDynamicPort           Integer32,
   gs2310pplusIPSourceGuardDynamicVLANId         Integer32,
   gs2310pplusIPSourceGuardDynamicIPAddress      IpAddress,
   gs2310pplusIPSourceGuardDynamicMACAddress     MacAddress
}

gs2310pplusIPSourceGuardDynamicIndex OBJECT-TYPE
   SYNTAX      Integer32(1..4095)
   MAX-ACCESS  not-accessible
   STATUS      current
   DESCRIPTION
       " "
   ::= { gs2310pplusIPSourceGuardDynamicEntry 1 }

gs2310pplusIPSourceGuardDynamicPort OBJECT-TYPE
   SYNTAX      Integer32(1..10)
   MAX-ACCESS  read-only
   STATUS      current
   DESCRIPTION
       " "
   ::= { gs2310pplusIPSourceGuardDynamicEntry 2 }

gs2310pplusIPSourceGuardDynamicVLANId OBJECT-TYPE
   SYNTAX      Integer32(1..4094)
   MAX-ACCESS  read-only
   STATUS      current
   DESCRIPTION
       " "
   ::= { gs2310pplusIPSourceGuardDynamicEntry 3 }

gs2310pplusIPSourceGuardDynamicIPAddress OBJECT-TYPE
   SYNTAX      IpAddress
   MAX-ACCESS  read-only
   STATUS      current
   DESCRIPTION
       " "
   ::= { gs2310pplusIPSourceGuardDynamicEntry 4 }

gs2310pplusIPSourceGuardDynamicMACAddress OBJECT-TYPE
   SYNTAX      MacAddress
   MAX-ACCESS  read-only
   STATUS      current
   DESCRIPTION
       " "
   ::= { gs2310pplusIPSourceGuardDynamicEntry 5 }

gs2310pplusARPInspection                                         OBJECT IDENTIFIER ::= { gs2310pplusSecurity 2 }

gs2310pplusARPInspectionConf                                     OBJECT IDENTIFIER ::= { gs2310pplusARPInspection 1 }

gs2310pplusARPInspectionConfMode OBJECT-TYPE
   SYNTAX      INTEGER { disable(0), enable(1) }
   MAX-ACCESS  read-write
   STATUS      current
   DESCRIPTION
       "default: 0
        0: disable
        1: enable"
   ::= { gs2310pplusARPInspectionConf 1 }

gs2310pplusARPInspectionConfTable OBJECT-TYPE
   SYNTAX      SEQUENCE OF GS2310PPLUSARPInspectionConfEntry
   MAX-ACCESS  not-accessible
   STATUS      current
   DESCRIPTION
       " "
   ::= { gs2310pplusARPInspectionConf 2 }

gs2310pplusARPInspectionConfEntry OBJECT-TYPE
   SYNTAX      GS2310PPLUSARPInspectionConfEntry
   MAX-ACCESS  not-accessible
   STATUS      current
   DESCRIPTION
       ""
   INDEX    { gs2310pplusARPInspectionConfPortIndex  }
   ::= { gs2310pplusARPInspectionConfTable 1 }

GS2310PPLUSARPInspectionConfEntry ::= SEQUENCE {
   gs2310pplusARPInspectionConfPortIndex	Integer32,
   gs2310pplusARPInspectionConfPortMode	INTEGER
}

gs2310pplusARPInspectionConfPortIndex OBJECT-TYPE
   SYNTAX      Integer32(1..4095)
   MAX-ACCESS  not-accessible
   STATUS      current
   DESCRIPTION
       " "
   ::= { gs2310pplusARPInspectionConfEntry 1 }

gs2310pplusARPInspectionConfPortMode OBJECT-TYPE
   SYNTAX      INTEGER { disable(0), enable(1) }
   MAX-ACCESS  read-write
   STATUS      current
   DESCRIPTION
       "default: 0
        0: disable
        1: enable"
   ::= { gs2310pplusARPInspectionConfEntry 2 }


gs2310pplusARPInspectionStatic                                OBJECT IDENTIFIER ::= { gs2310pplusARPInspection 2 }

gs2310pplusARPInspectionStaticCreate OBJECT-TYPE
   SYNTAX      INTEGER { none(0), create(1) }
   MAX-ACCESS  read-write
   STATUS      current
   DESCRIPTION
       "default: 0
        0: none
        1: create"
   ::= { gs2310pplusARPInspectionStatic 1 }

gs2310pplusARPInspectionStaticTable OBJECT-TYPE
   SYNTAX      SEQUENCE OF GS2310PPLUSARPInspectionStaticEntry
   MAX-ACCESS  not-accessible
   STATUS      current
   DESCRIPTION
       " "
   ::= { gs2310pplusARPInspectionStatic 2 }

gs2310pplusARPInspectionStaticEntry OBJECT-TYPE
   SYNTAX      GS2310PPLUSARPInspectionStaticEntry
   MAX-ACCESS  not-accessible
   STATUS      current
   DESCRIPTION
       ""
   INDEX    { gs2310pplusARPInspectionStaticIndex  }
   ::= { gs2310pplusARPInspectionStaticTable 1 }

GS2310PPLUSARPInspectionStaticEntry ::= SEQUENCE {
   gs2310pplusARPInspectionStaticIndex       Integer32,
   gs2310pplusARPInspectionStaticPort        Integer32,
   gs2310pplusARPInspectionStaticVLANId      Integer32,
   gs2310pplusARPInspectionStaticIPAddress   IpAddress,
   gs2310pplusARPInspectionStaticMACAddress  MacAddress,
   gs2310pplusARPInspectionStaticRowStatus   INTEGER
}

gs2310pplusARPInspectionStaticIndex OBJECT-TYPE
   SYNTAX      Integer32(1..4095)
   MAX-ACCESS  not-accessible
   STATUS      current
   DESCRIPTION
       ""
   ::= { gs2310pplusARPInspectionStaticEntry 1 }

gs2310pplusARPInspectionStaticPort OBJECT-TYPE
   SYNTAX      Integer32(1..4095)
   MAX-ACCESS  read-write
   STATUS      current
   DESCRIPTION
       " Port, range: 1 - port number. "
   ::= { gs2310pplusARPInspectionStaticEntry 2 }

gs2310pplusARPInspectionStaticVLANId OBJECT-TYPE
   SYNTAX      Integer32(1..4094)
   MAX-ACCESS  read-write
   STATUS      current
   DESCRIPTION
       " VLAN ID, range: 1 - 4094. "
   ::= { gs2310pplusARPInspectionStaticEntry 3 }

gs2310pplusARPInspectionStaticIPAddress OBJECT-TYPE
   SYNTAX      IpAddress
   MAX-ACCESS  read-write
   STATUS      current
   DESCRIPTION
       " IP address allowed for doing ARP request. "
   ::= { gs2310pplusARPInspectionStaticEntry 4 }

gs2310pplusARPInspectionStaticMACAddress OBJECT-TYPE
   SYNTAX      MacAddress
   MAX-ACCESS  read-write
   STATUS      current
   DESCRIPTION
       " Allowed Source MAC address in ARP request packets, format 0a 1b 2c 3d 4e 5f "
   ::= { gs2310pplusARPInspectionStaticEntry 5 }

gs2310pplusARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2310pplusARPInspectionStaticEntry 6 }

gs2310pplusARPInspectionDynamicTable OBJECT-TYPE
   SYNTAX      SEQUENCE OF GS2310PPLUSARPInspectionDynamicEntry
   MAX-ACCESS  not-accessible
   STATUS      current
   DESCRIPTION
       " "
   ::= { gs2310pplusARPInspection 3 }

gs2310pplusARPInspectionDynamicEntry OBJECT-TYPE
   SYNTAX      GS2310PPLUSARPInspectionDynamicEntry
   MAX-ACCESS  not-accessible
   STATUS      current
   DESCRIPTION
       ""
   INDEX    { gs2310pplusARPInspectionDynamicIndex  }
   ::= { gs2310pplusARPInspectionDynamicTable 1 }

GS2310PPLUSARPInspectionDynamicEntry ::= SEQUENCE {
   gs2310pplusARPInspectionDynamicIndex          Integer32,
   gs2310pplusARPInspectionDynamicPort           Integer32,
   gs2310pplusARPInspectionDynamicVLANId         Integer32,
   gs2310pplusARPInspectionDynamicIPAddress      IpAddress,
   gs2310pplusARPInspectionDynamicMACAddress     MacAddress
}

gs2310pplusARPInspectionDynamicIndex OBJECT-TYPE
   SYNTAX      Integer32(1..4095)
   MAX-ACCESS  not-accessible
   STATUS      current
   DESCRIPTION
       " "
   ::= { gs2310pplusARPInspectionDynamicEntry 1 }

gs2310pplusARPInspectionDynamicPort OBJECT-TYPE
   SYNTAX      Integer32(1..4095)
   MAX-ACCESS  read-only
   STATUS      current
   DESCRIPTION
       ""
   ::= { gs2310pplusARPInspectionDynamicEntry 2 }

gs2310pplusARPInspectionDynamicVLANId OBJECT-TYPE
   SYNTAX      Integer32(1..4094)
   MAX-ACCESS  read-only
   STATUS      current
   DESCRIPTION
       ""
   ::= { gs2310pplusARPInspectionDynamicEntry 3 }

gs2310pplusARPInspectionDynamicIPAddress OBJECT-TYPE
   SYNTAX      IpAddress
   MAX-ACCESS  read-only
   STATUS      current
   DESCRIPTION
       ""
   ::= { gs2310pplusARPInspectionDynamicEntry 4 }

gs2310pplusARPInspectionDynamicMACAddress OBJECT-TYPE
   SYNTAX      MacAddress
   MAX-ACCESS  read-only
   STATUS      current
   DESCRIPTION
       ""
   ::= { gs2310pplusARPInspectionDynamicEntry 5 }

gs2310pplusARPStaticGatewayCtrl	                                OBJECT IDENTIFIER ::= { gs2310pplusARPInspection 6 }

gs2310pplusARPStaticGatewayCtrlSystemConf                                      OBJECT IDENTIFIER ::= { gs2310pplusARPStaticGatewayCtrl 1 }

gs2310pplusARPStaticGatewayCtrlMode OBJECT-TYPE
   SYNTAX      INTEGER { disable(0), enable(1) }
   MAX-ACCESS  read-write
   STATUS      current
   DESCRIPTION
       "default: 0
       0: disable
       1: enable "
   ::= { gs2310pplusARPStaticGatewayCtrlSystemConf 1 }

gs2310pplusARPStaticGatewayCtrlCreate OBJECT-TYPE
   SYNTAX      INTEGER { none(0), create(1) }
   MAX-ACCESS  read-write
   STATUS      current
   DESCRIPTION
       "default: 0
        0: none
        1: create"
   ::= { gs2310pplusARPStaticGatewayCtrl 2 }

gs2310pplusARPStaticGatewayCtrlTable OBJECT-TYPE
   SYNTAX      SEQUENCE OF GS2310PPLUSARPStaticGatewayCtrlEntry
   MAX-ACCESS  not-accessible
   STATUS      current
   DESCRIPTION
       " "
   ::= { gs2310pplusARPStaticGatewayCtrl 3 }

gs2310pplusARPStaticGatewayCtrlEntry OBJECT-TYPE
   SYNTAX      GS2310PPLUSARPStaticGatewayCtrlEntry
   MAX-ACCESS  not-accessible
   STATUS      current
   DESCRIPTION
       ""
   INDEX    { gs2310pplusARPStaticGatewayCtrlIndex  }
   ::= { gs2310pplusARPStaticGatewayCtrlTable 1 }

GS2310PPLUSARPStaticGatewayCtrlEntry ::= SEQUENCE {
   gs2310pplusARPStaticGatewayCtrlIndex       Integer32,
   gs2310pplusARPStaticGatewayCtrlIPAddress   IpAddress,
   gs2310pplusARPStaticGatewayCtrlMACAddress  MacAddress,
   gs2310pplusARPStaticGatewayCtrlPort        Integer32,
   gs2310pplusARPStaticGatewayCtrlAction      INTEGER,
   gs2310pplusARPStaticGatewayCtrlState       DisplayString,
   gs2310pplusARPStaticGatewayCtrlReOpen      INTEGER,
   gs2310pplusARPStaticGatewayCtrlRowStatus   INTEGER
}

gs2310pplusARPStaticGatewayCtrlIndex OBJECT-TYPE
   SYNTAX      Integer32(1..4)
   MAX-ACCESS  not-accessible
   STATUS      current
   DESCRIPTION
       ""
   ::= { gs2310pplusARPStaticGatewayCtrlEntry 1 }

gs2310pplusARPStaticGatewayCtrlIPAddress OBJECT-TYPE
   SYNTAX      IpAddress
   MAX-ACCESS  read-write
   STATUS      current
   DESCRIPTION
       " Source IP address. "
   ::= { gs2310pplusARPStaticGatewayCtrlEntry 2 }

gs2310pplusARPStaticGatewayCtrlMACAddress OBJECT-TYPE
   SYNTAX      MacAddress
   MAX-ACCESS  read-write
   STATUS      current
   DESCRIPTION
       " Source MAC address , format 0a 1b 2c 3d 4e 5f "
   ::= { gs2310pplusARPStaticGatewayCtrlEntry 3 }

gs2310pplusARPStaticGatewayCtrlPort OBJECT-TYPE
   SYNTAX      Integer32(1..4095)
   MAX-ACCESS  read-write
   STATUS      current
   DESCRIPTION
       " Port, range: 1 - port number. "
   ::= { gs2310pplusARPStaticGatewayCtrlEntry 4 }

gs2310pplusARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2310pplusARPStaticGatewayCtrlEntry 5 }

gs2310pplusARPStaticGatewayCtrlState OBJECT-TYPE
   SYNTAX      DisplayString
   MAX-ACCESS  read-only
   STATUS      current
   DESCRIPTION
       ""
   ::= { gs2310pplusARPStaticGatewayCtrlEntry 6 }

gs2310pplusARPStaticGatewayCtrlReOpen OBJECT-TYPE
   SYNTAX      INTEGER { none(0), reopen(1) }
   MAX-ACCESS  read-write
   STATUS      current
   DESCRIPTION
       "default: 0
       0: none
       1: reopen"
   ::= { gs2310pplusARPStaticGatewayCtrlEntry 7 }  
   
gs2310pplusARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2310pplusARPStaticGatewayCtrlEntry 8 }

gs2310pplusARPSpoofingPrevention	                                OBJECT IDENTIFIER ::= { gs2310pplusARPInspection 7 }

gs2310pplusARPSpoofingPreventionSystemConf                                      OBJECT IDENTIFIER ::= { gs2310pplusARPSpoofingPrevention 1 }

gs2310pplusARPSpoofingPreventionMode OBJECT-TYPE
   SYNTAX      INTEGER { disable(0), enable(1) }
   MAX-ACCESS  read-write
   STATUS      current
   DESCRIPTION
       "default: 0
       0: disable
       1: enable "
   ::= { gs2310pplusARPSpoofingPreventionSystemConf 1 }

gs2310pplusARPSpoofingPreventionTable OBJECT-TYPE
   SYNTAX      SEQUENCE OF GS2310PPLUSARPSpoofingPreventionEntry
   MAX-ACCESS  not-accessible
   STATUS      current
   DESCRIPTION
       " "
   ::= { gs2310pplusARPSpoofingPrevention 2 }

gs2310pplusARPSpoofingPreventionEntry OBJECT-TYPE
   SYNTAX      GS2310PPLUSARPSpoofingPreventionEntry
   MAX-ACCESS  not-accessible
   STATUS      current
   DESCRIPTION
       ""
   INDEX    { gs2310pplusARPSpoofingPreventionPort  }
   ::= { gs2310pplusARPSpoofingPreventionTable 1 }

GS2310PPLUSARPSpoofingPreventionEntry ::= SEQUENCE {
   gs2310pplusARPSpoofingPreventionPort           Integer32,
   gs2310pplusARPSpoofingPreventionPortMode       INTEGER,
   gs2310pplusARPSpoofingPreventionPortLimit      Integer32,
   gs2310pplusARPSpoofingPreventionPortAction     INTEGER,
   gs2310pplusARPSpoofingPreventionPortState      DisplayString,
   gs2310pplusARPSpoofingPreventionPortReOpen     INTEGER
}

gs2310pplusARPSpoofingPreventionPort OBJECT-TYPE
   SYNTAX      Integer32(1..4095)
   MAX-ACCESS  not-accessible
   STATUS      current
   DESCRIPTION
       " "
   ::= { gs2310pplusARPSpoofingPreventionEntry 1 }

gs2310pplusARPSpoofingPreventionPortMode OBJECT-TYPE
   SYNTAX      INTEGER { disable(0), enable(1) }
   MAX-ACCESS  read-write
   STATUS      current
   DESCRIPTION
       "default: 0
       0: disable
       1: enable"
   ::= { gs2310pplusARPSpoofingPreventionEntry 2 }

gs2310pplusARPSpoofingPreventionPortLimit OBJECT-TYPE
   SYNTAX      Integer32(1..100)
   MAX-ACCESS  read-write
   STATUS      current
   DESCRIPTION
       "default: 1, range: 1-100"
   ::= { gs2310pplusARPSpoofingPreventionEntry 3 }

gs2310pplusARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2310pplusARPSpoofingPreventionEntry 4 }

gs2310pplusARPSpoofingPreventionPortState OBJECT-TYPE
   SYNTAX      DisplayString
   MAX-ACCESS  read-only
   STATUS      current
   DESCRIPTION
       ""
   ::= { gs2310pplusARPSpoofingPreventionEntry 5 }

gs2310pplusARPSpoofingPreventionPortReOpen OBJECT-TYPE
   SYNTAX      INTEGER { none(0), reopen(1) }
   MAX-ACCESS  read-write
   STATUS      current
   DESCRIPTION
       "default: 0
       0: none
       1: reopen"
   ::= { gs2310pplusARPSpoofingPreventionEntry 6 }  

gs2310pplusARPIPDoSPrevention	                                OBJECT IDENTIFIER ::= { gs2310pplusARPInspection 8 }

gs2310pplusARPIPDoSPreventionTCPMode OBJECT-TYPE
   SYNTAX      INTEGER { disable(0), enable(1) }
   MAX-ACCESS  read-write
   STATUS      current
   DESCRIPTION
       "default: 0
       0: disable
       1: enable "
   ::= { gs2310pplusARPIPDoSPrevention 1 }

gs2310pplusARPIPDoSPreventionUDPMode OBJECT-TYPE
   SYNTAX      INTEGER { disable(0), enable(1) }
   MAX-ACCESS  read-write
   STATUS      current
   DESCRIPTION
       "default: 0
       0: disable
       1: enable "
   ::= { gs2310pplusARPIPDoSPrevention 2 }
   
gs2310pplusARPIPDoSPreventionICMPMode OBJECT-TYPE
   SYNTAX      INTEGER { disable(0), enable(1) }
   MAX-ACCESS  read-write
   STATUS      current
   DESCRIPTION
       "default: 0
       0: disable
       1: enable "
   ::= { gs2310pplusARPIPDoSPrevention 3 }   

gs2310pplusARPIPDoSPreventionServerPort1 OBJECT-TYPE
   SYNTAX      Integer32(0..4094)
   MAX-ACCESS  read-write
   STATUS      current
   DESCRIPTION
       " Port, range: 0 - port number. 0: none. "
   ::= { gs2310pplusARPIPDoSPrevention 4 }  

gs2310pplusARPIPDoSPreventionServerPort2 OBJECT-TYPE
   SYNTAX      Integer32(0..4094)
   MAX-ACCESS  read-write
   STATUS      current
   DESCRIPTION
       " Port, range: 0 - port number. 0: none. "
   ::= { gs2310pplusARPIPDoSPrevention 5 }  
   
gs2310pplusARPIPDoSPreventionServerPort3 OBJECT-TYPE
   SYNTAX      Integer32(0..4094)
   MAX-ACCESS  read-write
   STATUS      current
   DESCRIPTION
       " Port, range: 0 - port number. 0: none. "
   ::= { gs2310pplusARPIPDoSPrevention 6 }  
   
gs2310pplusARPIPDoSPreventionServerPort4 OBJECT-TYPE
   SYNTAX      Integer32(0..4094)
   MAX-ACCESS  read-write
   STATUS      current
   DESCRIPTION
       " Port, range: 0 - port number. 0: none. "
   ::= { gs2310pplusARPIPDoSPrevention 7 }        

gs2310pplusDHCPSnooping                                          OBJECT IDENTIFIER ::= { gs2310pplusSecurity 3 }

gs2310pplusDHCPSnoopingConf                                          OBJECT IDENTIFIER ::= { gs2310pplusDHCPSnooping 1 }

gs2310pplusDHCPSnoopingMode OBJECT-TYPE
   SYNTAX      INTEGER { disable(0), enable(1) }
   MAX-ACCESS  read-write
   STATUS      current
   DESCRIPTION
       "default: 0
       0: disable
       1: enable"
   ::= { gs2310pplusDHCPSnoopingConf 1 }

gs2310pplusDHCPSnoopingPortModeConfigurationTable OBJECT-TYPE
   SYNTAX      SEQUENCE OF GS2310PPLUSDHCPSnoopingPortModeConfigurationEntry
   MAX-ACCESS  not-accessible
   STATUS      current
   DESCRIPTION
       " "
   ::= { gs2310pplusDHCPSnoopingConf 2 }

gs2310pplusDHCPSnoopingPortModeConfigurationEntry OBJECT-TYPE
   SYNTAX      GS2310PPLUSDHCPSnoopingPortModeConfigurationEntry
   MAX-ACCESS  not-accessible
   STATUS      current
   DESCRIPTION
       ""
   INDEX    { gs2310pplusDHCPSnoopingPortModeConfigurationPort  }
   ::= { gs2310pplusDHCPSnoopingPortModeConfigurationTable 1 }
   
GS2310PPLUSDHCPSnoopingPortModeConfigurationEntry ::= SEQUENCE {
   gs2310pplusDHCPSnoopingPortModeConfigurationPort	Integer32,
   gs2310pplusDHCPSnoopingPortModeConfigurationMode	INTEGER
}

gs2310pplusDHCPSnoopingPortModeConfigurationPort OBJECT-TYPE
   SYNTAX      Integer32(1..4095)
   MAX-ACCESS  not-accessible
   STATUS      current
   DESCRIPTION
       " "
   ::= { gs2310pplusDHCPSnoopingPortModeConfigurationEntry 1 }

gs2310pplusDHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2310pplusDHCPSnoopingPortModeConfigurationEntry 2 }

gs2310pplusDHCPSnoopingStatisticsTable OBJECT-TYPE
   SYNTAX      SEQUENCE OF GS2310PPLUSDHCPSnoopingStatisticsEntry
   MAX-ACCESS  not-accessible
   STATUS      current
   DESCRIPTION
       " "
   ::= { gs2310pplusDHCPSnooping 2 }

gs2310pplusDHCPSnoopingStatisticsEntry OBJECT-TYPE
   SYNTAX      GS2310PPLUSDHCPSnoopingStatisticsEntry
   MAX-ACCESS  not-accessible
   STATUS      current
   DESCRIPTION
       ""
   INDEX    { gs2310pplusDHCPSnoopingStatisticsPort  }
   ::= { gs2310pplusDHCPSnoopingStatisticsTable 1 }

GS2310PPLUSDHCPSnoopingStatisticsEntry ::= SEQUENCE {
   gs2310pplusDHCPSnoopingStatisticsPort         Integer32,
   gs2310pplusDHCPSnoopingStatisticsClear        INTEGER,
   gs2310pplusDHCPSnoopingRxDiscover             Counter32,
   gs2310pplusDHCPSnoopingRxOffer                Counter32,
   gs2310pplusDHCPSnoopingRxRequest              Counter32,
   gs2310pplusDHCPSnoopingRxDecline              Counter32,
   gs2310pplusDHCPSnoopingRxACK                  Counter32,
   gs2310pplusDHCPSnoopingRxNAK                  Counter32,
   gs2310pplusDHCPSnoopingRxRelease              Counter32,
   gs2310pplusDHCPSnoopingRxInform               Counter32,
   gs2310pplusDHCPSnoopingRxLeaseQuery           Counter32,
   gs2310pplusDHCPSnoopingRxLeaseUnassigned      Counter32,
   gs2310pplusDHCPSnoopingRxLeaseUnknown         Counter32,
   gs2310pplusDHCPSnoopingRxLeaseActive          Counter32,
   gs2310pplusDHCPSnoopingTxDiscover             Counter32,
   gs2310pplusDHCPSnoopingTxOffer                Counter32,
   gs2310pplusDHCPSnoopingTxRequest              Counter32,
   gs2310pplusDHCPSnoopingTxDecline              Counter32,
   gs2310pplusDHCPSnoopingTxACK                  Counter32,
   gs2310pplusDHCPSnoopingTxNAK                  Counter32,
   gs2310pplusDHCPSnoopingTxRelease              Counter32,
   gs2310pplusDHCPSnoopingTxInform               Counter32,
   gs2310pplusDHCPSnoopingTxLeaseQuery           Counter32,
   gs2310pplusDHCPSnoopingTxLeaseUnassigned      Counter32,
   gs2310pplusDHCPSnoopingTxLeaseUnknown         Counter32,
   gs2310pplusDHCPSnoopingTxLeaseActive          Counter32
}

gs2310pplusDHCPSnoopingStatisticsPort OBJECT-TYPE
   SYNTAX      Integer32(1..4095)
   MAX-ACCESS  not-accessible
   STATUS      current
   DESCRIPTION
       " "
   ::= { gs2310pplusDHCPSnoopingStatisticsEntry 1 }

gs2310pplusDHCPSnoopingStatisticsClear OBJECT-TYPE
   SYNTAX      INTEGER { none(0), clear(1) }
   MAX-ACCESS  read-write
   STATUS      current
   DESCRIPTION
       "default: 0
       0: none
       1: clear"
   ::= { gs2310pplusDHCPSnoopingStatisticsEntry 2 }
   
gs2310pplusDHCPSnoopingRxDiscover OBJECT-TYPE
   SYNTAX      Counter32
   MAX-ACCESS  read-only
   STATUS      current
   DESCRIPTION
       " "
   ::= { gs2310pplusDHCPSnoopingStatisticsEntry 3 }

gs2310pplusDHCPSnoopingRxOffer OBJECT-TYPE
   SYNTAX      Counter32
   MAX-ACCESS  read-only
   STATUS      current
   DESCRIPTION
       " "
   ::= { gs2310pplusDHCPSnoopingStatisticsEntry 4 }

gs2310pplusDHCPSnoopingRxRequest OBJECT-TYPE
   SYNTAX      Counter32
   MAX-ACCESS  read-only
   STATUS      current
   DESCRIPTION
       " "
   ::= { gs2310pplusDHCPSnoopingStatisticsEntry 5 }

gs2310pplusDHCPSnoopingRxDecline OBJECT-TYPE
   SYNTAX      Counter32
   MAX-ACCESS  read-only
   STATUS      current
   DESCRIPTION
       " "
   ::= { gs2310pplusDHCPSnoopingStatisticsEntry 6 }

gs2310pplusDHCPSnoopingRxACK OBJECT-TYPE
   SYNTAX      Counter32
   MAX-ACCESS  read-only
   STATUS      current
   DESCRIPTION
       " "
   ::= { gs2310pplusDHCPSnoopingStatisticsEntry 7 }

gs2310pplusDHCPSnoopingRxNAK OBJECT-TYPE
   SYNTAX      Counter32
   MAX-ACCESS  read-only
   STATUS      current
   DESCRIPTION
       " "
   ::= { gs2310pplusDHCPSnoopingStatisticsEntry 8 }   

gs2310pplusDHCPSnoopingRxRelease OBJECT-TYPE
   SYNTAX      Counter32
   MAX-ACCESS  read-only
   STATUS      current
   DESCRIPTION
       " "
   ::= { gs2310pplusDHCPSnoopingStatisticsEntry 9 }

gs2310pplusDHCPSnoopingRxInform OBJECT-TYPE
   SYNTAX      Counter32
   MAX-ACCESS  read-only
   STATUS      current
   DESCRIPTION
       " "
   ::= { gs2310pplusDHCPSnoopingStatisticsEntry 10 }

gs2310pplusDHCPSnoopingRxLeaseQuery OBJECT-TYPE
   SYNTAX      Counter32
   MAX-ACCESS  read-only
   STATUS      current
   DESCRIPTION
       " "
   ::= { gs2310pplusDHCPSnoopingStatisticsEntry 11 }

gs2310pplusDHCPSnoopingRxLeaseUnassigned OBJECT-TYPE
   SYNTAX      Counter32
   MAX-ACCESS  read-only
   STATUS      current
   DESCRIPTION
       " "
   ::= { gs2310pplusDHCPSnoopingStatisticsEntry 12 }

gs2310pplusDHCPSnoopingRxLeaseUnknown OBJECT-TYPE
   SYNTAX      Counter32
   MAX-ACCESS  read-only
   STATUS      current
   DESCRIPTION
       " "
   ::= { gs2310pplusDHCPSnoopingStatisticsEntry 13 }

gs2310pplusDHCPSnoopingRxLeaseActive OBJECT-TYPE
   SYNTAX      Counter32
   MAX-ACCESS  read-only
   STATUS      current
   DESCRIPTION
       " "
   ::= { gs2310pplusDHCPSnoopingStatisticsEntry 14 }

gs2310pplusDHCPSnoopingTxDiscover OBJECT-TYPE
   SYNTAX      Counter32
   MAX-ACCESS  read-only
   STATUS      current
   DESCRIPTION
       " "
   ::= { gs2310pplusDHCPSnoopingStatisticsEntry 15 }

gs2310pplusDHCPSnoopingTxOffer OBJECT-TYPE
   SYNTAX      Counter32
   MAX-ACCESS  read-only
   STATUS      current
   DESCRIPTION
       " "
   ::= { gs2310pplusDHCPSnoopingStatisticsEntry 16 }

gs2310pplusDHCPSnoopingTxRequest OBJECT-TYPE
   SYNTAX      Counter32
   MAX-ACCESS  read-only
   STATUS      current
   DESCRIPTION
       " "
   ::= { gs2310pplusDHCPSnoopingStatisticsEntry 17 }

gs2310pplusDHCPSnoopingTxDecline OBJECT-TYPE
   SYNTAX      Counter32
   MAX-ACCESS  read-only
   STATUS      current
   DESCRIPTION
       " "
   ::= { gs2310pplusDHCPSnoopingStatisticsEntry 18 }

gs2310pplusDHCPSnoopingTxACK OBJECT-TYPE
   SYNTAX      Counter32
   MAX-ACCESS  read-only
   STATUS      current
   DESCRIPTION
       " "
   ::= { gs2310pplusDHCPSnoopingStatisticsEntry 19 }

gs2310pplusDHCPSnoopingTxNAK OBJECT-TYPE
   SYNTAX      Counter32
   MAX-ACCESS  read-only
   STATUS      current
   DESCRIPTION
       " "
   ::= { gs2310pplusDHCPSnoopingStatisticsEntry 20 }   

gs2310pplusDHCPSnoopingTxRelease OBJECT-TYPE
   SYNTAX      Counter32
   MAX-ACCESS  read-only
   STATUS      current
   DESCRIPTION
       " "
   ::= { gs2310pplusDHCPSnoopingStatisticsEntry 21 }

gs2310pplusDHCPSnoopingTxInform OBJECT-TYPE
   SYNTAX      Counter32
   MAX-ACCESS  read-only
   STATUS      current
   DESCRIPTION
       " "
   ::= { gs2310pplusDHCPSnoopingStatisticsEntry 22 }

gs2310pplusDHCPSnoopingTxLeaseQuery OBJECT-TYPE
   SYNTAX      Counter32
   MAX-ACCESS  read-only
   STATUS      current
   DESCRIPTION
       " "
   ::= { gs2310pplusDHCPSnoopingStatisticsEntry 23 }

gs2310pplusDHCPSnoopingTxLeaseUnassigned OBJECT-TYPE
   SYNTAX      Counter32
   MAX-ACCESS  read-only
   STATUS      current
   DESCRIPTION
       " "
   ::= { gs2310pplusDHCPSnoopingStatisticsEntry 24 }

gs2310pplusDHCPSnoopingTxLeaseUnknown OBJECT-TYPE
   SYNTAX      Counter32
   MAX-ACCESS  read-only
   STATUS      current
   DESCRIPTION
       " "
   ::= { gs2310pplusDHCPSnoopingStatisticsEntry 25 }

gs2310pplusDHCPSnoopingTxLeaseActive OBJECT-TYPE
   SYNTAX      Counter32
   MAX-ACCESS  read-only
   STATUS      current
   DESCRIPTION
       " "
   ::= { gs2310pplusDHCPSnoopingStatisticsEntry 26 }


gs2310pplusDHCPRelay                                             OBJECT IDENTIFIER ::= { gs2310pplusSecurity 4 }

gs2310pplusDHCPRelayConfiguration                                         OBJECT IDENTIFIER ::= { gs2310pplusDHCPRelay 1 }

gs2310pplusDHCPRelayMode OBJECT-TYPE
   SYNTAX      INTEGER { disable(0), enable(1) }
   MAX-ACCESS  read-write
   STATUS      current
   DESCRIPTION
       "default: 0
       0: disable
       1: enable 
       We need at least one server"
   ::= { gs2310pplusDHCPRelayConfiguration 1 }

gs2310pplusDHCPRelayServer OBJECT-TYPE
   SYNTAX      IpAddress
   MAX-ACCESS  read-write
   STATUS      current
   DESCRIPTION
       " "
   ::= { gs2310pplusDHCPRelayConfiguration 2 }

gs2310pplusDHCPRelayInformationMode OBJECT-TYPE
   SYNTAX      INTEGER { disable(0), enable(1) }
   MAX-ACCESS  read-write
   STATUS      current
   DESCRIPTION
       "default: 0
       0: disable
       1: enable "
   ::= { gs2310pplusDHCPRelayConfiguration 3 }

gs2310pplusDHCPRelayInformationPolicy OBJECT-TYPE
   SYNTAX      INTEGER { replace(0), keep(1), drop(2) }
   MAX-ACCESS  read-write
   STATUS      current
   DESCRIPTION
       "default: 0
       0: replace
       1: keep
       2: drop "
   ::= { gs2310pplusDHCPRelayConfiguration 4 }

gs2310pplusDHCPRelayInformationCustom OBJECT-TYPE
   SYNTAX      DisplayString(SIZE(0..32))
   MAX-ACCESS  read-write
   STATUS      current
   DESCRIPTION
       "DHCP Option 82 Circuit ID custom information"
   ::= { gs2310pplusDHCPRelayConfiguration 1500 }

gs2310pplusDHCPRelayConfigurationGateways                                          OBJECT IDENTIFIER ::= { gs2310pplusDHCPRelayConfiguration 5 }

gs2310pplusDHCPRelayConfigurationGatewaysCreate OBJECT-TYPE
   SYNTAX       INTEGER { none(0), create(1) }
   MAX-ACCESS   read-write
   STATUS       current
   DESCRIPTION
       "default: 0
        0 : None  (read only)
        1 : Create entry"
   ::= { gs2310pplusDHCPRelayConfigurationGateways 1 }

gs2310pplusDHCPRelayConfigurationGatewaysTable OBJECT-TYPE
   SYNTAX      SEQUENCE OF Gs2310pplusDHCPRelayConfigurationGatewaysEntry
   MAX-ACCESS  not-accessible
   STATUS      current
   DESCRIPTION
       " Create DHCP Relay Gateway IP address entry."
   ::= { gs2310pplusDHCPRelayConfigurationGateways 2 }

gs2310pplusDHCPRelayConfigurationGatewaysEntry OBJECT-TYPE
   SYNTAX      Gs2310pplusDHCPRelayConfigurationGatewaysEntry
   MAX-ACCESS  not-accessible
   STATUS      current
   DESCRIPTION
       ""
   INDEX    { gs2310pplusDHCPRelayConfigurationGatewaysIndex  }
   ::= { gs2310pplusDHCPRelayConfigurationGatewaysTable 1 }

Gs2310pplusDHCPRelayConfigurationGatewaysEntry ::= SEQUENCE {
   gs2310pplusDHCPRelayConfigurationGatewaysIndex           Integer32,
   gs2310pplusDHCPRelayConfigurationGatewaysVLANId          Integer32,
   gs2310pplusDHCPRelayConfigurationGatewaysIP              IpAddress,
   gs2310pplusDHCPRelayConfigurationGatewaysRowStatus       INTEGER
}

gs2310pplusDHCPRelayConfigurationGatewaysIndex OBJECT-TYPE
   SYNTAX      Integer32(1..6)
   MAX-ACCESS  not-accessible
   STATUS      current
   DESCRIPTION
       " "
   ::= { gs2310pplusDHCPRelayConfigurationGatewaysEntry 1 }

gs2310pplusDHCPRelayConfigurationGatewaysVLANId OBJECT-TYPE
   SYNTAX      Integer32(1..4094)
   MAX-ACCESS  read-write
   STATUS      current
   DESCRIPTION
       " VLAN ID "
   ::= { gs2310pplusDHCPRelayConfigurationGatewaysEntry 2 }

gs2310pplusDHCPRelayConfigurationGatewaysIP OBJECT-TYPE
   SYNTAX      IpAddress
   MAX-ACCESS  read-write
   STATUS      current
   DESCRIPTION
       "DHCP GIADDR address."
   ::= { gs2310pplusDHCPRelayConfigurationGatewaysEntry 3 }
   
gs2310pplusDHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2310pplusDHCPRelayConfigurationGatewaysEntry 4 }


gs2310pplusDHCPRelayStatistics                                   OBJECT IDENTIFIER ::= { gs2310pplusDHCPRelay 2 }

gs2310pplusDHCPRelayServerStatistics                                   OBJECT IDENTIFIER ::= { gs2310pplusDHCPRelayStatistics 1 }

gs2310pplusServerStatTransmitToServer OBJECT-TYPE
   SYNTAX      Counter32
   MAX-ACCESS  read-only
   STATUS      current
   DESCRIPTION
       " "
   ::= { gs2310pplusDHCPRelayServerStatistics 1 }

gs2310pplusServerStatTransmitError OBJECT-TYPE
   SYNTAX      Counter32
   MAX-ACCESS  read-only
   STATUS      current
   DESCRIPTION
       " "
   ::= { gs2310pplusDHCPRelayServerStatistics 2 }

gs2310pplusServerStatReceiveFromServer OBJECT-TYPE
   SYNTAX      Counter32
   MAX-ACCESS  read-only
   STATUS      current
   DESCRIPTION
       " "
   ::= { gs2310pplusDHCPRelayServerStatistics 3 }

gs2310pplusServerStatReceiveMissingAgentOption OBJECT-TYPE
   SYNTAX      Counter32
   MAX-ACCESS  read-only
   STATUS      current
   DESCRIPTION
       " "
   ::= { gs2310pplusDHCPRelayServerStatistics 4 }

gs2310pplusServerStatReceiveMissingCircuitID OBJECT-TYPE
   SYNTAX      Counter32
   MAX-ACCESS  read-only
   STATUS      current
   DESCRIPTION
       " "
   ::= { gs2310pplusDHCPRelayServerStatistics 5 }

gs2310pplusServerStatReceiveMissingRemoteID OBJECT-TYPE
   SYNTAX      Counter32
   MAX-ACCESS  read-only
   STATUS      current
   DESCRIPTION
       " "
   ::= { gs2310pplusDHCPRelayServerStatistics 6 }

gs2310pplusServerStatReceiveBadCircuitID OBJECT-TYPE
   SYNTAX      Counter32
   MAX-ACCESS  read-only
   STATUS      current
   DESCRIPTION
       " "
   ::= { gs2310pplusDHCPRelayServerStatistics 7 }

gs2310pplusServerStatReceiveBadRemoteID OBJECT-TYPE
   SYNTAX      Counter32
   MAX-ACCESS  read-only
   STATUS      current
   DESCRIPTION
       " "
   ::= { gs2310pplusDHCPRelayServerStatistics 8 }

gs2310pplusDHCPRelayClientStatistics                                   OBJECT IDENTIFIER ::= { gs2310pplusDHCPRelayStatistics 2 }

gs2310pplusClientStatTransmitToClient OBJECT-TYPE
   SYNTAX      Counter32
   MAX-ACCESS  read-only
   STATUS      current
   DESCRIPTION
       " "
   ::= { gs2310pplusDHCPRelayClientStatistics 1 }

gs2310pplusClientStatTransmitError OBJECT-TYPE
   SYNTAX      Counter32
   MAX-ACCESS  read-only
   STATUS      current
   DESCRIPTION
       " "
   ::= { gs2310pplusDHCPRelayClientStatistics 2 }

gs2310pplusClientStatReceivefromClient OBJECT-TYPE
   SYNTAX      Counter32
   MAX-ACCESS  read-only
   STATUS      current
   DESCRIPTION
       " "
   ::= { gs2310pplusDHCPRelayClientStatistics 3 }

gs2310pplusClientStatReceiveAgentOption OBJECT-TYPE
   SYNTAX      Counter32
   MAX-ACCESS  read-only
   STATUS      current
   DESCRIPTION
       " "
   ::= { gs2310pplusDHCPRelayClientStatistics 4 }

gs2310pplusClientStatReplaceAgentOption OBJECT-TYPE
   SYNTAX      Counter32
   MAX-ACCESS  read-only
   STATUS      current
   DESCRIPTION
       " "
   ::= { gs2310pplusDHCPRelayClientStatistics 5 }

gs2310pplusClientStatKeepAgentOption OBJECT-TYPE
   SYNTAX      Counter32
   MAX-ACCESS  read-only
   STATUS      current
   DESCRIPTION
       " "
   ::= { gs2310pplusDHCPRelayClientStatistics 6 }

gs2310pplusClientStatDropAgentOption OBJECT-TYPE
   SYNTAX      Counter32
   MAX-ACCESS  read-only
   STATUS      current
   DESCRIPTION
       " "
   ::= { gs2310pplusDHCPRelayClientStatistics 7 }

gs2310pplusPortSecurity                                          OBJECT IDENTIFIER ::= { gs2310pplusSecurity 5 }

gs2310pplusPortSecLimitCtrl                                      OBJECT IDENTIFIER ::= { gs2310pplusPortSecurity 1 }

gs2310pplusPortSecLimitCtrlSystemConf                                      OBJECT IDENTIFIER ::= { gs2310pplusPortSecLimitCtrl 1 }

gs2310pplusPortSecurityMode OBJECT-TYPE
   SYNTAX      INTEGER { disable(0), enable(1) }
   MAX-ACCESS  read-write
   STATUS      current
   DESCRIPTION
       "default: 0
       0: disable
       1: enable "
   ::= { gs2310pplusPortSecLimitCtrlSystemConf 1 }

gs2310pplusPortSecurityAging OBJECT-TYPE
   SYNTAX      INTEGER { disable(0), enable(1) }
   MAX-ACCESS  read-write
   STATUS      current
   DESCRIPTION
       "default: 0
       0: disable
       1: enable "
   ::= { gs2310pplusPortSecLimitCtrlSystemConf 2 }

gs2310pplusPortSecurityAgingPeriod OBJECT-TYPE
   SYNTAX      INTEGER(10..10000000)
   MAX-ACCESS  read-write
   STATUS      current
   DESCRIPTION
       "default: 3600, range: 10-10000000 "
   ::= { gs2310pplusPortSecLimitCtrlSystemConf 3 }

gs2310pplusPortSecLimitCtrlTable OBJECT-TYPE
   SYNTAX      SEQUENCE OF GS2310PPLUSPortSecLimitCtrlEntry
   MAX-ACCESS  not-accessible
   STATUS      current
   DESCRIPTION
       " "
   ::= { gs2310pplusPortSecLimitCtrl 2 }

gs2310pplusPortSecLimitCtrlEntry OBJECT-TYPE
   SYNTAX      GS2310PPLUSPortSecLimitCtrlEntry
   MAX-ACCESS  not-accessible
   STATUS      current
   DESCRIPTION
       ""
   INDEX    { gs2310pplusPortSecLimitCtrlPort  }
   ::= { gs2310pplusPortSecLimitCtrlTable 1 }

GS2310PPLUSPortSecLimitCtrlEntry ::= SEQUENCE {
   gs2310pplusPortSecLimitCtrlPort           Integer32,
   gs2310pplusPortSecLimitCtrlPortMode       INTEGER,
   gs2310pplusPortSecLimitCtrlPortLimit      Integer32,
   gs2310pplusPortSecLimitCtrlPortAction     INTEGER,
   gs2310pplusPortSecLimitCtrlPortState      DisplayString,
   gs2310pplusPortSecLimitCtrlPortReOpen     INTEGER
}

gs2310pplusPortSecLimitCtrlPort OBJECT-TYPE
   SYNTAX      Integer32(1..4095)
   MAX-ACCESS  not-accessible
   STATUS      current
   DESCRIPTION
       " "
   ::= { gs2310pplusPortSecLimitCtrlEntry 1 }

gs2310pplusPortSecLimitCtrlPortMode OBJECT-TYPE
   SYNTAX      INTEGER { disable(0), enable(1) }
   MAX-ACCESS  read-write
   STATUS      current
   DESCRIPTION
       "default: 0
       0: disable
       1: enable"
   ::= { gs2310pplusPortSecLimitCtrlEntry 2 }

gs2310pplusPortSecLimitCtrlPortLimit OBJECT-TYPE
   SYNTAX      Integer32(1..1024)
   MAX-ACCESS  read-write
   STATUS      current
   DESCRIPTION
       "default: 4, range: 1-1024"
   ::= { gs2310pplusPortSecLimitCtrlEntry 3 }

gs2310pplusPortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2310pplusPortSecLimitCtrlEntry 4 }

gs2310pplusPortSecLimitCtrlPortState OBJECT-TYPE
   SYNTAX      DisplayString
   MAX-ACCESS  read-only
   STATUS      current
   DESCRIPTION
       ""
   ::= { gs2310pplusPortSecLimitCtrlEntry 5 }

gs2310pplusPortSecLimitCtrlPortReOpen OBJECT-TYPE
   SYNTAX      INTEGER { none(0), reopen(1) }
   MAX-ACCESS  read-write
   STATUS      current
   DESCRIPTION
       "default: 0
       0: none
       1: reopen"
   ::= { gs2310pplusPortSecLimitCtrlEntry 6 }

gs2310pplusPortSecSwitchStatusTable OBJECT-TYPE
   SYNTAX      SEQUENCE OF GS2310PPLUSPortSecSwitchStatusEntry
   MAX-ACCESS  not-accessible
   STATUS      current
   DESCRIPTION
       " "
   ::= { gs2310pplusPortSecurity 2 }

gs2310pplusPortSecSwitchStatusEntry OBJECT-TYPE
   SYNTAX      GS2310PPLUSPortSecSwitchStatusEntry
   MAX-ACCESS  not-accessible
   STATUS      current
   DESCRIPTION
       ""
   INDEX    { gs2310pplusPortSecSwitchStatusPort  }
   ::= { gs2310pplusPortSecSwitchStatusTable 1 }

GS2310PPLUSPortSecSwitchStatusEntry ::= SEQUENCE {
   gs2310pplusPortSecSwitchStatusPort                Integer32,
   gs2310pplusPortSecSwitchStatusUsers               DisplayString,
   gs2310pplusPortSecSwitchStatusState               DisplayString,
   gs2310pplusPortSecSwitchStatusMACCountCurrent     Integer32,
   gs2310pplusPortSecSwitchStatusMACCountLimit       Integer32
}

gs2310pplusPortSecSwitchStatusPort OBJECT-TYPE
   SYNTAX      Integer32(1..4095)
   MAX-ACCESS  not-accessible
   STATUS      current
   DESCRIPTION
       " "
   ::= { gs2310pplusPortSecSwitchStatusEntry 1 }

gs2310pplusPortSecSwitchStatusUsers OBJECT-TYPE
   SYNTAX      DisplayString
   MAX-ACCESS  read-only
   STATUS      current
   DESCRIPTION
       " Users Abbr: L = Limit Control, 8 = 802.1X, D = DHCP Snooping, V = Voice VLAN, 
         '-' means that the corresponding user module is not enabled. "
   ::= { gs2310pplusPortSecSwitchStatusEntry 2 }

gs2310pplusPortSecSwitchStatusState OBJECT-TYPE
   SYNTAX      DisplayString
   MAX-ACCESS  read-only
   STATUS      current
   DESCRIPTION
       " Shows the current state of the port : Disabled, Ready, Limit Reached, Shutdown. "
   ::= { gs2310pplusPortSecSwitchStatusEntry 3 }

gs2310pplusPortSecSwitchStatusMACCountCurrent OBJECT-TYPE
   SYNTAX      Integer32(1..4095)
   MAX-ACCESS  read-only
   STATUS      current
   DESCRIPTION
       ""
   ::= { gs2310pplusPortSecSwitchStatusEntry 4 }

gs2310pplusPortSecSwitchStatusMACCountLimit OBJECT-TYPE
   SYNTAX      Integer32(1..4095)
   MAX-ACCESS  read-only
   STATUS      current
   DESCRIPTION
       ""
   ::= { gs2310pplusPortSecSwitchStatusEntry 5 }

gs2310pplusPortSecPortStatus                                      OBJECT IDENTIFIER ::= { gs2310pplusPortSecurity 3 }

gs2310pplusPortSecPortStatusPort OBJECT-TYPE
   SYNTAX       Integer32(1..4095)
   MAX-ACCESS   read-write
   STATUS       current
   DESCRIPTION
       "port number
        default: 1
        range: 1 - port number."
   ::= { gs2310pplusPortSecPortStatus 1 }

gs2310pplusPortSecPortStatusTable OBJECT-TYPE
   SYNTAX      SEQUENCE OF GS2310PPLUSPortSecPortStatusEntry
   MAX-ACCESS  not-accessible
   STATUS      current
   DESCRIPTION
      " "
   ::= { gs2310pplusPortSecPortStatus 2 }
       
gs2310pplusPortSecPortStatusEntry OBJECT-TYPE
   SYNTAX      GS2310PPLUSPortSecPortStatusEntry
   MAX-ACCESS  not-accessible
   STATUS      current
   DESCRIPTION
       ""
   INDEX    { gs2310pplusPortSecPortStatusIndex  }
   ::= { gs2310pplusPortSecPortStatusTable 1 }       

GS2310PPLUSPortSecPortStatusEntry ::= SEQUENCE {
   gs2310pplusPortSecPortStatusIndex              Integer32,
   gs2310pplusPortSecPortStatusMACAddress         MacAddress,
   gs2310pplusPortSecPortStatusVLANId             Integer32,
   gs2310pplusPortSecPortStatusState              DisplayString,
   gs2310pplusPortSecPortStatusTimeOfAddition     DisplayString,
   gs2310pplusPortSecPortStatusAgeAndHold         DisplayString
}

gs2310pplusPortSecPortStatusIndex OBJECT-TYPE
   SYNTAX      Integer32(1..4095)
   MAX-ACCESS  not-accessible
   STATUS      current
   DESCRIPTION
       " "
   ::= { gs2310pplusPortSecPortStatusEntry 1 }

gs2310pplusPortSecPortStatusMACAddress OBJECT-TYPE
   SYNTAX      MacAddress
   MAX-ACCESS  read-only
   STATUS      current
   DESCRIPTION
       " "
   ::= { gs2310pplusPortSecPortStatusEntry 2 }

gs2310pplusPortSecPortStatusVLANId OBJECT-TYPE
   SYNTAX      Integer32(1..4094)
   MAX-ACCESS  read-only
   STATUS      current
   DESCRIPTION
       " "
   ::= { gs2310pplusPortSecPortStatusEntry 3 }

gs2310pplusPortSecPortStatusState OBJECT-TYPE
   SYNTAX      DisplayString
   MAX-ACCESS  read-only
   STATUS      current
   DESCRIPTION
       "Blocked / Forwarding "
   ::= { gs2310pplusPortSecPortStatusEntry 4 }

gs2310pplusPortSecPortStatusTimeOfAddition OBJECT-TYPE
   SYNTAX      DisplayString
   MAX-ACCESS  read-only
   STATUS      current
   DESCRIPTION
       " "
   ::= { gs2310pplusPortSecPortStatusEntry 5 }

gs2310pplusPortSecPortStatusAgeAndHold OBJECT-TYPE
   SYNTAX      DisplayString
   MAX-ACCESS  read-only
   STATUS      current
   DESCRIPTION
       " "
   ::= { gs2310pplusPortSecPortStatusEntry 6 }       
       

gs2310pplusAccessManagement                                      OBJECT IDENTIFIER ::= { gs2310pplusSecurity 6 }

gs2310pplusAccessMgtConf                                         OBJECT IDENTIFIER ::= { gs2310pplusAccessManagement 1 }

gs2310pplusAccessMgtConfMode OBJECT-TYPE
   SYNTAX      INTEGER { disable(0), enable(1) }
   MAX-ACCESS  read-write
   STATUS      current
   DESCRIPTION
       "default: 0
       0: disable
       1: enable "
   ::= { gs2310pplusAccessMgtConf 1 }

gs2310pplusAccessMgtConfCreate OBJECT-TYPE
   SYNTAX      INTEGER { none(0), create(1) }
   MAX-ACCESS  read-write
   STATUS      current
   DESCRIPTION
       "default: 0
       0: none
       1: create "
   ::= { gs2310pplusAccessMgtConf 2 }

gs2310pplusAccessMgtConfTable OBJECT-TYPE
   SYNTAX      SEQUENCE OF GS2310PPLUSAccessMgtConfEntry
   MAX-ACCESS  not-accessible
   STATUS      current
   DESCRIPTION
       " "
   ::= { gs2310pplusAccessMgtConf 3 }

gs2310pplusAccessMgtConfEntry OBJECT-TYPE
   SYNTAX      GS2310PPLUSAccessMgtConfEntry
   MAX-ACCESS  not-accessible
   STATUS      current
   DESCRIPTION
       ""
   INDEX    { gs2310pplusAccessMgtIndex  }
   ::= { gs2310pplusAccessMgtConfTable 1 }
   
GS2310PPLUSAccessMgtConfEntry ::= SEQUENCE {
   gs2310pplusAccessMgtIndex             Integer32,
   gs2310pplusAccessMgtAddresstype       INTEGER,
   gs2310pplusAccessMgtStartIpAddress    DisplayString,
   gs2310pplusAccessMgtEndIpAddress      DisplayString,
   gs2310pplusAccessMgtHttpHttps         INTEGER,
   gs2310pplusAccessMgtSNMP              INTEGER,
   gs2310pplusAccessMgtTelnetSSH         INTEGER,
   gs2310pplusAccessMgtRowStatus         INTEGER
}

gs2310pplusAccessMgtIndex OBJECT-TYPE
   SYNTAX      Integer32(1..16)
   MAX-ACCESS  read-write
   STATUS      current
   DESCRIPTION
       "Set Access Management config index
        range : 1-16."
   ::= { gs2310pplusAccessMgtConfEntry 1 }

gs2310pplusAccessMgtAddresstype OBJECT-TYPE
   SYNTAX      INTEGER { ipv4(0), ipv6(1) }
   MAX-ACCESS  read-write
   STATUS      current
   DESCRIPTION
       "0: ipv4
        1: ipv6 "
   ::= { gs2310pplusAccessMgtConfEntry 2 }
   
gs2310pplusAccessMgtStartIpAddress OBJECT-TYPE
   SYNTAX      DisplayString
   MAX-ACCESS  read-write
   STATUS      current
   DESCRIPTION
       " Start IP address. 
         IP address doesn't allowed all zero or all 'ff'H."
   ::= { gs2310pplusAccessMgtConfEntry 3 }
   
gs2310pplusAccessMgtEndIpAddress OBJECT-TYPE
   SYNTAX      DisplayString
   MAX-ACCESS  read-write
   STATUS      current
   DESCRIPTION
       " End IP address. 
         IP address doesn't allowed all zero or all 'ff'H.
         End ip address is not less than start ip address."
   ::= { gs2310pplusAccessMgtConfEntry 4 }

gs2310pplusAccessMgtHttpHttps OBJECT-TYPE
   SYNTAX      INTEGER { disable(0), enable(1) }
   MAX-ACCESS  read-write
   STATUS      current
   DESCRIPTION
       "default: 0
       0: disable
       1: enable "
   ::= { gs2310pplusAccessMgtConfEntry 5 }

gs2310pplusAccessMgtSNMP OBJECT-TYPE
   SYNTAX      INTEGER { disable(0), enable(1) }
   MAX-ACCESS  read-write
   STATUS      current
   DESCRIPTION
       "default: 0
       0: disable
       1: enable "
   ::= { gs2310pplusAccessMgtConfEntry 6 }

gs2310pplusAccessMgtTelnetSSH OBJECT-TYPE
   SYNTAX      INTEGER { disable(0), enable(1) }
   MAX-ACCESS  read-write
   STATUS      current
   DESCRIPTION
       "default: 0
       0: disable
       1: enable "
   ::= { gs2310pplusAccessMgtConfEntry 7 }

gs2310pplusAccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2310pplusAccessMgtConfEntry 8 }

gs2310pplusAccessMgtStatistics                                   OBJECT IDENTIFIER ::= { gs2310pplusAccessManagement 2 }

gs2310pplusHttpReceivedPkts OBJECT-TYPE
   SYNTAX      Counter32
   MAX-ACCESS  read-only
   STATUS      current
   DESCRIPTION
       " "
   ::= { gs2310pplusAccessMgtStatistics 1 }

gs2310pplusHttpAllowedPkts OBJECT-TYPE
   SYNTAX      Counter32
   MAX-ACCESS  read-only
   STATUS      current
   DESCRIPTION
       " "
   ::= { gs2310pplusAccessMgtStatistics 2 }

gs2310pplusHttpDiscardedPkts OBJECT-TYPE
   SYNTAX      Counter32
   MAX-ACCESS  read-only
   STATUS      current
   DESCRIPTION
       " "
   ::= { gs2310pplusAccessMgtStatistics 3 }

gs2310pplusHttpsReceivedPkts OBJECT-TYPE
   SYNTAX      Counter32
   MAX-ACCESS  read-only
   STATUS      current
   DESCRIPTION
       " "
   ::= { gs2310pplusAccessMgtStatistics 4 }

gs2310pplusHttpsAllowedPkts OBJECT-TYPE
   SYNTAX      Counter32
   MAX-ACCESS  read-only
   STATUS      current
   DESCRIPTION
       " "
   ::= { gs2310pplusAccessMgtStatistics 5 }

gs2310pplusHttpsDiscardedPkts OBJECT-TYPE
   SYNTAX      Counter32
   MAX-ACCESS  read-only
   STATUS      current
   DESCRIPTION
       " "
   ::= { gs2310pplusAccessMgtStatistics 6 }

gs2310pplusSnmpReceivedPkts OBJECT-TYPE
   SYNTAX      Counter32
   MAX-ACCESS  read-only
   STATUS      current
   DESCRIPTION
       " "
   ::= { gs2310pplusAccessMgtStatistics 7 }

gs2310pplusSnmpAllowedPkts OBJECT-TYPE
   SYNTAX      Counter32
   MAX-ACCESS  read-only
   STATUS      current
   DESCRIPTION
       " "
   ::= { gs2310pplusAccessMgtStatistics 8 }

gs2310pplusSnmpDiscardedPkts OBJECT-TYPE
   SYNTAX      Counter32
   MAX-ACCESS  read-only
   STATUS      current
   DESCRIPTION
       " "
   ::= { gs2310pplusAccessMgtStatistics 9 }

gs2310pplusTelnetReceivedPkts OBJECT-TYPE
   SYNTAX      Counter32
   MAX-ACCESS  read-only
   STATUS      current
   DESCRIPTION
       " "
   ::= { gs2310pplusAccessMgtStatistics 10 }

gs2310pplusTelnetAllowedPkts OBJECT-TYPE
   SYNTAX      Counter32
   MAX-ACCESS  read-only
   STATUS      current
   DESCRIPTION
       " "
   ::= { gs2310pplusAccessMgtStatistics 11 }

gs2310pplusTelnetDiscardedPkts OBJECT-TYPE
   SYNTAX      Counter32
   MAX-ACCESS  read-only
   STATUS      current
   DESCRIPTION
       " "
   ::= { gs2310pplusAccessMgtStatistics 12 }

gs2310pplusSSHReceivedPkts OBJECT-TYPE
   SYNTAX      Counter32
   MAX-ACCESS  read-only
   STATUS      current
   DESCRIPTION
       " "
   ::= { gs2310pplusAccessMgtStatistics 13 }

gs2310pplusSSHAllowedPkts OBJECT-TYPE
   SYNTAX      Counter32
   MAX-ACCESS  read-only
   STATUS      current
   DESCRIPTION
       " "
   ::= { gs2310pplusAccessMgtStatistics 14 }

gs2310pplusSSHDiscardedPkts OBJECT-TYPE
   SYNTAX      Counter32
   MAX-ACCESS  read-only
   STATUS      current
   DESCRIPTION
       " "
   ::= { gs2310pplusAccessMgtStatistics 15 }

gs2310pplusAccessMgtStatisticsClearAll OBJECT-TYPE
   SYNTAX      INTEGER { none(0), clear(1) }
   MAX-ACCESS  read-write
   STATUS      current
   DESCRIPTION
       "0: none
        1: clear"
   ::= { gs2310pplusAccessMgtStatistics 16 }

gs2310pplusSSH                                                   OBJECT IDENTIFIER ::= { gs2310pplusSecurity 7 }

gs2310pplusSSHMode OBJECT-TYPE
   SYNTAX      INTEGER { disable(0), enable(1) }
   MAX-ACCESS  read-write
   STATUS      current
   DESCRIPTION
       "default: 1
        0: disable
        1: enable"
   ::= { gs2310pplusSSH 1 }

gs2310pplusHTTPS                                                 OBJECT IDENTIFIER ::= { gs2310pplusSecurity 8 }

gs2310pplusHTTPSMode OBJECT-TYPE
   SYNTAX      INTEGER { disable(0), enable(1) }
   MAX-ACCESS  read-write
   STATUS      current
   DESCRIPTION
       "default: 1
        0: disable
        1: enable"
   ::= { gs2310pplusHTTPS 1 }

gs2310pplusHTTPSAutoRedirect OBJECT-TYPE
   SYNTAX      INTEGER { disable(0), enable(1) }
   MAX-ACCESS  read-write
   STATUS      current
   DESCRIPTION
       "default: 0
        0: disable
        1: enable"
   ::= { gs2310pplusHTTPS 2 }

gs2310pplusHTTPSCertRenew OBJECT-TYPE
   SYNTAX      INTEGER { doNothing(0), renew(1) }
   MAX-ACCESS  read-write
   STATUS      current
   DESCRIPTION
       "default: 0 ,
        0: doNothing
        1: renew"
   ::= { gs2310pplusHTTPS 3 }

gs2310pplusHTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2310pplusHTTPS 4 }

gs2310pplusHTTPMode OBJECT-TYPE
   SYNTAX      INTEGER { disable(0), enable(1) }
   MAX-ACCESS  read-write
   STATUS      current
   DESCRIPTION
       "default: 1
        0: disable
        1: enable"
   ::= { gs2310pplusHTTPS 5 }

gs2310pplusAuthMethod                                            OBJECT IDENTIFIER ::= { gs2310pplusSecurity 9 }

gs2310pplusConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pplusAuthMethod 1 }

gs2310pplusConsoleFallback OBJECT-TYPE
   SYNTAX      INTEGER { disable(0), enable(1) }
   MAX-ACCESS  read-write
   STATUS      current
   DESCRIPTION
       "default: 0
        0:disable
        1:enable"
   ::= { gs2310pplusAuthMethod 2 }

gs2310pplusTelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pplusAuthMethod 3 }

gs2310pplusTelnetFallback OBJECT-TYPE
   SYNTAX      INTEGER { disable(0), enable(1) }
   MAX-ACCESS  read-write
   STATUS      current
   DESCRIPTION
       "default: 0
        0:disable
        1:enable"
   ::= { gs2310pplusAuthMethod 4 }

gs2310pplusSshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pplusAuthMethod 5 }

gs2310pplusSshFallback OBJECT-TYPE
   SYNTAX      INTEGER { disable(0), enable(1) }
   MAX-ACCESS  read-write
   STATUS      current
   DESCRIPTION
       "default: 0
        0:disable
        1:enable"
   ::= { gs2310pplusAuthMethod 6 }

gs2310pplusTftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pplusAuthMethod 9 }

gs2310pplusTftpFallback OBJECT-TYPE
   SYNTAX      INTEGER { disable(0), enable(1) }
   MAX-ACCESS  read-write
   STATUS      current
   DESCRIPTION
       "default: 0
        0:disable
        1:enable"
   ::= { gs2310pplusAuthMethod 10 }
   
gs2310pplusLoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2310pplusAuthMethod 11 }

gs2310pplusLockMinutes OBJECT-TYPE
   SYNTAX      Integer32(1..99)
   MAX-ACCESS  read-write
   STATUS      current
   DESCRIPTION
       "Lock time to login failures trigger.
        range: 1-99.
        default: 5."
   ::= { gs2310pplusAuthMethod 12 }

gs2310pplusHttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pplusAuthMethod 13 }

gs2310pplusHttpFallback OBJECT-TYPE
   SYNTAX      INTEGER { disable(0), enable(1) }
   MAX-ACCESS  read-write
   STATUS      current
   DESCRIPTION
       "default: 0
        0:disable
        1:enable"
   ::= { gs2310pplusAuthMethod 14 }

gs2310pplusHttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2310pplusAuthMethod 15 }

gs2310pplusHttpsFallback OBJECT-TYPE
   SYNTAX      INTEGER { disable(0), enable(1) }
   MAX-ACCESS  read-write
   STATUS      current
   DESCRIPTION
       "default: 0
        0:disable
        1:enable"
   ::= { gs2310pplusAuthMethod 16 }


gs2310pplusAAA                                              OBJECT IDENTIFIER ::= { gs2310pplusSecurity 10 }

gs2310pplusAAACommonServer                                  OBJECT IDENTIFIER ::= { gs2310pplusAAA 1 }

gs2310pplusAAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2310pplusAAACommonServer 1 }

gs2310pplusAAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2310pplusAAACommonServer 2 }

gs2310pplusAAATACACSPlusAuthAndAccounting                  OBJECT IDENTIFIER ::= { gs2310pplusAAA 2 }

gs2310pplusAAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2310pplusAAATACACSPlusAuthAndAccounting 1 }

gs2310pplusAAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2310pplusAAATACACSPlusAuthAndAccounting 2 }

gs2310pplusAAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2310pplusAAATACACSPlusAuthAndAccounting 3 }

gs2310pplusRADIUSAuthenticationServerTable OBJECT-TYPE
   SYNTAX      SEQUENCE OF Gs2310pplusRADIUSAuthenticationServerEntry
   MAX-ACCESS  not-accessible
   STATUS      current
   DESCRIPTION
       " "
   ::= { gs2310pplusAAA 3 }

gs2310pplusRADIUSAuthenticationServerEntry OBJECT-TYPE
   SYNTAX      Gs2310pplusRADIUSAuthenticationServerEntry
   MAX-ACCESS  not-accessible
   STATUS      current
   DESCRIPTION
       ""
   INDEX    { gs2310pplusRADIUSAuthenticationServerIndex  }
   ::= { gs2310pplusRADIUSAuthenticationServerTable 1 }

Gs2310pplusRADIUSAuthenticationServerEntry ::= SEQUENCE {
   gs2310pplusRADIUSAuthenticationServerIndex     Integer32,
   gs2310pplusRADIUSAuthenticationServerEnable    INTEGER,
   gs2310pplusRADIUSAuthenticationServerIP        DisplayString,
   gs2310pplusRADIUSAuthenticationServerPort      Integer32,
   gs2310pplusRADIUSAuthenticationServerSecret    DisplayString
}

gs2310pplusRADIUSAuthenticationServerIndex OBJECT-TYPE
   SYNTAX      Integer32(1..5)
   MAX-ACCESS  not-accessible
   STATUS      current
   DESCRIPTION
       "RADIUS Authentication Server index
        range : 1-5."
   ::= { gs2310pplusRADIUSAuthenticationServerEntry 1 }

gs2310pplusRADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2310pplusRADIUSAuthenticationServerEntry 2 }

gs2310pplusRADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2310pplusRADIUSAuthenticationServerEntry 3 }

gs2310pplusRADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2310pplusRADIUSAuthenticationServerEntry 4 }

gs2310pplusRADIUSAuthenticationServerSecret OBJECT-TYPE
   SYNTAX      DisplayString
   MAX-ACCESS  read-write
   STATUS      current
   DESCRIPTION
       "The secret - up to 64 characters long - shared between the RADIUS Authentication Server and the switch. "
   ::= { gs2310pplusRADIUSAuthenticationServerEntry 5 }
   

gs2310pplusRADIUSAccountingServerTable OBJECT-TYPE
   SYNTAX      SEQUENCE OF Gs2310pplusRADIUSAccountingServerEntry
   MAX-ACCESS  not-accessible
   STATUS      current
   DESCRIPTION
       " "
   ::= { gs2310pplusAAA 4 }

gs2310pplusRADIUSAccountingServerEntry OBJECT-TYPE
   SYNTAX      Gs2310pplusRADIUSAccountingServerEntry
   MAX-ACCESS  not-accessible
   STATUS      current
   DESCRIPTION
       ""
   INDEX    { gs2310pplusRADIUSAccountingServerIndex  }
   ::= { gs2310pplusRADIUSAccountingServerTable 1 }

Gs2310pplusRADIUSAccountingServerEntry ::= SEQUENCE {
   gs2310pplusRADIUSAccountingServerIndex     Integer32,
   gs2310pplusRADIUSAccountingServerEnable    INTEGER,
   gs2310pplusRADIUSAccountingServerIP        DisplayString,
   gs2310pplusRADIUSAccountingServerPort      Integer32,
   gs2310pplusRADIUSAccountingServerSecret    DisplayString
}

gs2310pplusRADIUSAccountingServerIndex OBJECT-TYPE
   SYNTAX      Integer32(1..5)
   MAX-ACCESS  not-accessible
   STATUS      current
   DESCRIPTION
       "RADIUS Accounting Server index
        range : 1-5."
   ::= { gs2310pplusRADIUSAccountingServerEntry 1 }

gs2310pplusRADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2310pplusRADIUSAccountingServerEntry 2 }

gs2310pplusRADIUSAccountingServerIP OBJECT-TYPE
   SYNTAX      DisplayString
   MAX-ACCESS  read-write
   STATUS      current
   DESCRIPTION
       "The IP address or hostname of the RADIUS Accounting Server.
       IP address is expressed in  dotted decimal notation. "
   ::= { gs2310pplusRADIUSAccountingServerEntry 3 }

gs2310pplusRADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2310pplusRADIUSAccountingServerEntry 4 }

gs2310pplusRADIUSAccountingServerSecret OBJECT-TYPE
   SYNTAX      DisplayString
   MAX-ACCESS  read-write
   STATUS      current
   DESCRIPTION
       "The secret - up to 64 characters long - shared between the RADIUS Accounting Server and the switch. "
   ::= { gs2310pplusRADIUSAccountingServerEntry 5 }

gs2310pplusTACACSPlusAuthenticationServerTable OBJECT-TYPE
   SYNTAX      SEQUENCE OF Gs2310pplusTACACSPlusAuthenticationServerEntry
   MAX-ACCESS  not-accessible
   STATUS      current
   DESCRIPTION
       " "
   ::= { gs2310pplusAAA 5 }

gs2310pplusTACACSPlusAuthenticationServerEntry OBJECT-TYPE
   SYNTAX      Gs2310pplusTACACSPlusAuthenticationServerEntry
   MAX-ACCESS  not-accessible
   STATUS      current
   DESCRIPTION
       ""
   INDEX    { gs2310pplusTACACSPlusAuthenticationServerIndex  }
   ::= { gs2310pplusTACACSPlusAuthenticationServerTable 1 }

Gs2310pplusTACACSPlusAuthenticationServerEntry ::= SEQUENCE {
   gs2310pplusTACACSPlusAuthenticationServerIndex     Integer32,
   gs2310pplusTACACSPlusAuthenticationServerEnable    INTEGER,
   gs2310pplusTACACSPlusAuthenticationServerIP        DisplayString,
   gs2310pplusTACACSPlusAuthenticationServerPort      Integer32,
   gs2310pplusTACACSPlusAuthenticationServerSecret    DisplayString
}

gs2310pplusTACACSPlusAuthenticationServerIndex OBJECT-TYPE
   SYNTAX      Integer32(1..5)
   MAX-ACCESS  not-accessible
   STATUS      current
   DESCRIPTION
       "TACACSPlus Authentication Server index
        range : 1-5."
   ::= { gs2310pplusTACACSPlusAuthenticationServerEntry 1 }

gs2310pplusTACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2310pplusTACACSPlusAuthenticationServerEntry 2 }

gs2310pplusTACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2310pplusTACACSPlusAuthenticationServerEntry 3 }

gs2310pplusTACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2310pplusTACACSPlusAuthenticationServerEntry 4 }

gs2310pplusTACACSPlusAuthenticationServerSecret OBJECT-TYPE
   SYNTAX      DisplayString
   MAX-ACCESS  read-write
   STATUS      current
   DESCRIPTION
       "The secret - up to 64 characters long - shared between the TACACSPlus Authentication Server and the switch. "
   ::= { gs2310pplusTACACSPlusAuthenticationServerEntry 5 }


gs2310pplusRADIUSStatisticsTable OBJECT-TYPE
   SYNTAX      SEQUENCE OF Gs2310pplusRADIUSStatisticsEntry
   MAX-ACCESS  not-accessible
   STATUS      current
   DESCRIPTION
       " "
   ::= { gs2310pplusAAA 6 }

gs2310pplusRADIUSStatisticsEntry OBJECT-TYPE
   SYNTAX      Gs2310pplusRADIUSStatisticsEntry
   MAX-ACCESS  not-accessible
   STATUS      current
   DESCRIPTION
       ""
   INDEX    { gs2310pplusRADIUSAuthStatisticsServerIndex  }
   ::= { gs2310pplusRADIUSStatisticsTable 1 }

Gs2310pplusRADIUSStatisticsEntry ::= SEQUENCE {
   gs2310pplusRADIUSAuthStatisticsServerIndex                           Integer32,
   gs2310pplusRADIUSAuthStatisticsRecPktAccessAccepts                   Counter32,
   gs2310pplusRADIUSAuthStatisticsRecPktAccessRejects                   Counter32,
   gs2310pplusRADIUSAuthStatisticsRecPktAccessChallenges                Counter32,
   gs2310pplusRADIUSAuthStatisticsRecPktMalformedAccResponses           Counter32,
   gs2310pplusRADIUSAuthStatisticsRecPktBadAuthenticators               Counter32,
   gs2310pplusRADIUSAuthStatisticsRecPktUnknownTypes                    Counter32,
   gs2310pplusRADIUSAuthStatisticsRecPktDropped                         Counter32,
   gs2310pplusRADIUSAuthStatisticsTransmitPktAccessRequests             Counter32,
   gs2310pplusRADIUSAuthStatisticsTransmitPktAccessRetransmissions      Counter32,
   gs2310pplusRADIUSAuthStatisticsTransmitPktPendingRequests            Counter32,
   gs2310pplusRADIUSAuthStatisticsTransmitPktTimeouts                   Counter32,
   gs2310pplusRADIUSAuthIP                                              DisplayString,
   gs2310pplusRADIUSAuthState                                           DisplayString,
   gs2310pplusRADIUSAuthRoundTripTime                                   DisplayString,

   gs2310pplusRADIUSAccountingStatisticsRecPktResponses                 Counter32,
   gs2310pplusRADIUSAccountingStatisticsRecPktMalformedResponses        Counter32,
   gs2310pplusRADIUSAccountingStatisticsRecPktBadAuthenticators         Counter32,
   gs2310pplusRADIUSAccountingStatisticsRecPktUnknownTypes              Counter32,
   gs2310pplusRADIUSAccountingStatisticsRecPktDropped                   Counter32,
   gs2310pplusRADIUSAccountingStatisticsTransmitPktRequests             Counter32,
   gs2310pplusRADIUSAccountingStatisticsTransmitPktRetransmissions      Counter32,
   gs2310pplusRADIUSAccountingStatisticsTransmitPktPendingRequests      Counter32,
   gs2310pplusRADIUSAccountingStatisticsTransmitPktTimeouts             Counter32,
   gs2310pplusRADIUSAccountingIP                                        DisplayString,
   gs2310pplusRADIUSAccountingState                                     DisplayString,
   gs2310pplusRADIUSAccountingRoundTripTime                             DisplayString,
   gs2310pplusRADIUSStatisticsClear                                     INTEGER
}

gs2310pplusRADIUSAuthStatisticsServerIndex OBJECT-TYPE
   SYNTAX      Integer32(1..5)
   MAX-ACCESS  not-accessible
   STATUS      current
   DESCRIPTION
       "RADIUS Authentication Server index
        range : 1-5."
   ::= { gs2310pplusRADIUSStatisticsEntry 1 }

gs2310pplusRADIUSAuthStatisticsRecPktAccessAccepts OBJECT-TYPE
   SYNTAX      Counter32
   MAX-ACCESS  read-only
   STATUS      current
   DESCRIPTION
       "The number of RADIUS Access-Accept packets (valid or invalid) received from the server."
   ::= { gs2310pplusRADIUSStatisticsEntry 2 }

gs2310pplusRADIUSAuthStatisticsRecPktAccessRejects OBJECT-TYPE
   SYNTAX      Counter32
   MAX-ACCESS  read-only
   STATUS      current
   DESCRIPTION
       "The number of RADIUS Access-Reject packets (valid or invalid) received from the server."
   ::= { gs2310pplusRADIUSStatisticsEntry 3 }

gs2310pplusRADIUSAuthStatisticsRecPktAccessChallenges OBJECT-TYPE
   SYNTAX      Counter32
   MAX-ACCESS  read-only
   STATUS      current
   DESCRIPTION
       "The number of RADIUS Access-Challenge packets (valid or invalid) received from the server. "
   ::= { gs2310pplusRADIUSStatisticsEntry 4 }

gs2310pplusRADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2310pplusRADIUSStatisticsEntry 5 }

gs2310pplusRADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2310pplusRADIUSStatisticsEntry 6 }

gs2310pplusRADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2310pplusRADIUSStatisticsEntry 7 }

gs2310pplusRADIUSAuthStatisticsRecPktDropped OBJECT-TYPE
   SYNTAX      Counter32
   MAX-ACCESS  read-only
   STATUS      current
   DESCRIPTION
       "The number of RADIUS packets that were received from the server on the
       authentication port and dropped for some other reason."
   ::= { gs2310pplusRADIUSStatisticsEntry 8 }

gs2310pplusRADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2310pplusRADIUSStatisticsEntry 9 }

gs2310pplusRADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2310pplusRADIUSStatisticsEntry 10 }

gs2310pplusRADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2310pplusRADIUSStatisticsEntry 11 }

gs2310pplusRADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2310pplusRADIUSStatisticsEntry 12 }

gs2310pplusRADIUSAuthIP OBJECT-TYPE
   SYNTAX      DisplayString
   MAX-ACCESS  read-only
   STATUS      current
   DESCRIPTION
       "IP address and UDP port for the authentication server in question."
   ::= { gs2310pplusRADIUSStatisticsEntry 13 }

gs2310pplusRADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2310pplusRADIUSStatisticsEntry 14 }

gs2310pplusRADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2310pplusRADIUSStatisticsEntry 15 }

gs2310pplusRADIUSAccountingStatisticsRecPktResponses OBJECT-TYPE
   SYNTAX      Counter32
   MAX-ACCESS  read-only
   STATUS      current
   DESCRIPTION
       "The number of RADIUS packets (valid or invalid) received from the server."
   ::= { gs2310pplusRADIUSStatisticsEntry 16 }

gs2310pplusRADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2310pplusRADIUSStatisticsEntry 17 }

gs2310pplusRADIUSAccountingStatisticsRecPktBadAuthenticators OBJECT-TYPE
   SYNTAX      Counter32
   MAX-ACCESS  read-only
   STATUS      current
   DESCRIPTION
       "The number of RADIUS packets containing invalid authenticators received
       from the server."
   ::= { gs2310pplusRADIUSStatisticsEntry 18 }

gs2310pplusRADIUSAccountingStatisticsRecPktUnknownTypes OBJECT-TYPE
   SYNTAX      Counter32
   MAX-ACCESS  read-only
   STATUS      current
   DESCRIPTION
       "The number of RADIUS packets of unknown types that were received from
       the server on the accounting port."
   ::= { gs2310pplusRADIUSStatisticsEntry 19 }

gs2310pplusRADIUSAccountingStatisticsRecPktDropped OBJECT-TYPE
   SYNTAX      Counter32
   MAX-ACCESS  read-only
   STATUS      current
   DESCRIPTION
       "The number of RADIUS packets that were received from the server on the
       accounting port and dropped for some other reason."
   ::= { gs2310pplusRADIUSStatisticsEntry 20 }

gs2310pplusRADIUSAccountingStatisticsTransmitPktRequests OBJECT-TYPE
   SYNTAX      Counter32
   MAX-ACCESS  read-only
   STATUS      current
   DESCRIPTION
       "The number of RADIUS packets sent to the server. This does not include
       retransmissions."
   ::= { gs2310pplusRADIUSStatisticsEntry 21 }

gs2310pplusRADIUSAccountingStatisticsTransmitPktRetransmissions OBJECT-TYPE
   SYNTAX      Counter32
   MAX-ACCESS  read-only
   STATUS      current
   DESCRIPTION
       "The number of RADIUS packets retransmitted to the RADIUS accounting server."
   ::= { gs2310pplusRADIUSStatisticsEntry 22 }

gs2310pplusRADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2310pplusRADIUSStatisticsEntry 23 }

gs2310pplusRADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2310pplusRADIUSStatisticsEntry 24 }

gs2310pplusRADIUSAccountingIP OBJECT-TYPE
   SYNTAX      DisplayString
   MAX-ACCESS  read-only
   STATUS      current
   DESCRIPTION
       "IP address and UDP port for the accounting server in question."
   ::= { gs2310pplusRADIUSStatisticsEntry 25 }

gs2310pplusRADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2310pplusRADIUSStatisticsEntry 26 }
   
gs2310pplusRADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2310pplusRADIUSStatisticsEntry 27 }

gs2310pplusRADIUSStatisticsClear OBJECT-TYPE
   SYNTAX      INTEGER(0|1)
   MAX-ACCESS  read-write
   STATUS      current
   DESCRIPTION
       "Clears the counters for the server.
       read: always 0
       clear: set 1"
   ::= { gs2310pplusRADIUSStatisticsEntry 28 }


gs2310pplusNAS                                              OBJECT IDENTIFIER ::= { gs2310pplusSecurity 11 }

gs2310pplusNASConfiguration                                 OBJECT IDENTIFIER ::= { gs2310pplusNAS 1 }

gs2310pplusNASConfigMode OBJECT-TYPE
   SYNTAX      INTEGER { disable(0), enable(1) }
   MAX-ACCESS  read-write
   STATUS      current
   DESCRIPTION
       "Indicates if NAS is globally enabled or disabled on the switch. 
	    If globally disabled, all ports are allowed forwarding of frames."
   ::= { gs2310pplusNASConfiguration 1 }

gs2310pplusNASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication 
		Period. Reauthentication for 802.1X-enabled ports can be used to 
		detect if a new device is plugged into a switch port or if a 
		supplicant is no longer attached. 
		For MAC-based ports, reauthentication is only useful if the RADIUS 
		server configuration has changed. It does not involve communication 
		between the switch and the client, and therefore doesn't imply that 
		a client is still present on a port."
   ::= { gs2310pplusNASConfiguration 2 }

gs2310pplusNASConfigReauthPeriod OBJECT-TYPE
   SYNTAX      Integer32(1..3600)
   MAX-ACCESS  read-write
   STATUS      current
   DESCRIPTION
       "Determines the period, in seconds, after which a connected client must 
	    be reauthenticated. This is only active if the Reauthentication Enabled 
		checkbox is checked. 
		range: 1 - 3600 seconds."
   ::= { gs2310pplusNASConfiguration 3 }

gs2310pplusNASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2310pplusNASConfiguration 4 }
   
gs2310pplusNASConfigAgingPeriod OBJECT-TYPE
   SYNTAX      Integer32(10..1000000)
   MAX-ACCESS  read-write
   STATUS      current
   DESCRIPTION
       "When the NAS module uses the Port Security module to secure MAC addresses, 
	    the Port Security module needs to check for activity on the MAC address 
		in question at regular intervals and free resources if no activity 
		is seen within a given period of time.
		Admin State supported : Single, Multi and MAC-Based Auth. 802.1X.
		range: 10 - 1000000 seconds."
   ::= { gs2310pplusNASConfiguration 5 }   
   
gs2310pplusNASConfigHoldTime OBJECT-TYPE
   SYNTAX      Integer32(10..1000000)
   MAX-ACCESS  read-write
   STATUS      current
   DESCRIPTION
       "If a client is denied access - either because the RADIUS server denies
	    the client access or because the RADIUS server request times out 
		- the client is put on hold in the Unauthorized state. The hold timer 
		does not count during an on-going authentication. In MAC-based Auth. 
		mode, the switch will ignore new frames coming from the client during 
		the hold time.
		Admin State supported : Single, Multi and MAC-Based Auth. 802.1X.
		range: 10 - 1000000 seconds."
   ::= { gs2310pplusNASConfiguration 6 }  

gs2310pplusNASConfigRADIUSAssignedQoSEnabled OBJECT-TYPE
   SYNTAX      INTEGER { disable(0), enable(1) }
   MAX-ACCESS  read-write
   STATUS      current
   DESCRIPTION
       "RADIUS-assigned QoS provides a means to centrally control the 
	    traffic class to which traffic coming from a successfully authenticated 
		supplicant is assigned on the switch. The RADIUS server must be configured 
		to transmit special RADIUS attributes to take advantage of this feature."
   ::= { gs2310pplusNASConfiguration 7 }  
 
gs2310pplusNASConfigRADIUSAssignedVLANEnabled OBJECT-TYPE
   SYNTAX      INTEGER { disable(0), enable(1) }
   MAX-ACCESS  read-write
   STATUS      current
   DESCRIPTION
       "RADIUS-assigned VLAN provides a means to centrally control the VLAN on 
	    which a successfully authenticated supplicant is placed on the switch. 
	    Incoming traffic will be classified to and switched on the RADIUS-assigned 
		VLAN. The RADIUS server must be configured to transmit special RADIUS 
		attributes to take advantage of this feature.When enable, the individual 
		ports' ditto setting determine whether RADIUS-assigned VLAN is enabled 
		on that port. When disable, RADIUS-server assigned VLAN is disabled on 
		all ports. "
   ::= { gs2310pplusNASConfiguration 8 }    
   
gs2310pplusNASConfigGuestVLANEnabled OBJECT-TYPE
   SYNTAX      INTEGER { disable(0), enable(1) }
   MAX-ACCESS  read-write
   STATUS      current
   DESCRIPTION
       "A Guest VLAN is a special VLAN - typically with limited network access - 
	   on which 802.1X-unaware clients are placed after a network administrator-defined 
	   timeout. The switch follows a set of rules for entering and leaving the Guest 
	   VLAN as listed below.When enable, the individual ports' ditto setting determines 
	   whether the port can be moved into Guest VLAN. When disable, the ability to 
	   move to the Guest VLAN is disabled on all ports. "
   ::= { gs2310pplusNASConfiguration 9 } 
   
gs2310pplusNASConfigGuestVLANID OBJECT-TYPE
   SYNTAX      Integer32(1..4094)
   MAX-ACCESS  read-write
   STATUS      current
   DESCRIPTION
       "This is the value that a port's Port VLAN ID is set to if a port is moved into 
	   the Guest VLAN. It is only changeable if the Guest VLAN option is globally enabled.
	   range: 1 - 4094."
   ::= { gs2310pplusNASConfiguration 10 }

gs2310pplusNASConfigMaxReauthCount OBJECT-TYPE
   SYNTAX      Integer32(1..255)
   MAX-ACCESS  read-write
   STATUS      current
   DESCRIPTION
       "The number of times the switch transmits an EAPOL Request Identity frame without 
	   response before considering entering the Guest VLAN is adjusted with this setting. 
	   The value can only be changed if the Guest VLAN option is globally enabled.
	   range: 1 - 255."
   ::= { gs2310pplusNASConfiguration 11 }

gs2310pplusNASConfigAllowGuestVLANEAPOLSeen OBJECT-TYPE
   SYNTAX      INTEGER { disable(0), enable(1) }
   MAX-ACCESS  read-write
   STATUS      current
   DESCRIPTION
       "The switch remembers if an EAPOL frame has been received on the port for the 
	   life-time of the port. Once the switch considers whether to enter the Guest VLAN, 
	   it will first check if this option is enabled or disabled. If disabled, the switch 
	   will only enter the Guest VLAN if an EAPOL frame has not been received on the port 
	   for the life-time of the port. If enabled (checked), the switch will consider 
	   entering the Guest VLAN even if an EAPOL frame has been received on the port for 
	   the life-time of the port.The value can only be changed if the Guest VLAN option 
	   is globally enabled."
   ::= { gs2310pplusNASConfiguration 12 }

gs2310pplusNASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2310pplusNASConfiguration 101 }

gs2310pplusNASPortConfigTable OBJECT-TYPE
   SYNTAX      SEQUENCE OF Gs2310pplusNASPortConfigEntry
   MAX-ACCESS  not-accessible
   STATUS      current
   DESCRIPTION
       ""
   ::= { gs2310pplusNASConfiguration 13 }

gs2310pplusNASPortConfigEntry OBJECT-TYPE
   SYNTAX      Gs2310pplusNASPortConfigEntry
   MAX-ACCESS  not-accessible
   STATUS      current
   DESCRIPTION
       ""
   INDEX    { gs2310pplusNASPortConfigPort }
   ::= { gs2310pplusNASPortConfigTable 1 }

Gs2310pplusNASPortConfigEntry ::= SEQUENCE {
   gs2310pplusNASPortConfigPort                       Integer32,
   gs2310pplusNASPortConfigAdminState                 INTEGER,
   gs2310pplusNASPortConfigRADIUSAssignedQoSEnabled	  INTEGER,
   gs2310pplusNASPortConfigRADIUSAssignedVLANEnabled  INTEGER,
   gs2310pplusNASPortConfigGuestVLANEnabled           INTEGER,   
   gs2310pplusNASPortConfigFallbackEnabled            INTEGER,   
   gs2310pplusNASPortConfigPortState                  DisplayString,
   gs2310pplusNASPortConfigReauthenticate             INTEGER,
   gs2310pplusNASPortConfigReinitialize               INTEGER
}
  
gs2310pplusNASPortConfigPort OBJECT-TYPE
   SYNTAX      Integer32(1..255)
   MAX-ACCESS  not-accessible
   STATUS      current
   DESCRIPTION
       " port, range : 1 - port number. "
   ::= { gs2310pplusNASPortConfigEntry 1 }   
   
gs2310pplusNASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2310pplusNASPortConfigEntry 2 }   
   
gs2310pplusNASPortConfigRADIUSAssignedQoSEnabled OBJECT-TYPE
   SYNTAX      INTEGER { disable(0), enable(1) }
   MAX-ACCESS  read-write
   STATUS      current
   DESCRIPTION
       "When RADIUS-Assigned QoS is both globally enabled and enabled (checked) 
	    on a given port, the switch reacts to QoS Class information carried in 
		the RADIUS Access-Accept packet transmitted by the RADIUS server when a 
		supplicant is successfully authenticated. If present and valid, traffic 
		received on the supplicant's port will be classified to the given QoS Class.
		Admin State supported : Port-based and Single 802.1X and MAC-based Single Auth."
   ::= { gs2310pplusNASPortConfigEntry 3 }    
   
gs2310pplusNASPortConfigRADIUSAssignedVLANEnabled OBJECT-TYPE
   SYNTAX      INTEGER { disable(0), enable(1) }
   MAX-ACCESS  read-write
   STATUS      current
   DESCRIPTION
       "When RADIUS-Assigned VLAN is both globally enabled and enabled (checked) 
	   for a given port, the switch reacts to VLAN ID information carried in the 
	   RADIUS Access-Accept packet transmitted by the RADIUS server when a supplicant 
	   is successfully authenticated. If present and valid, the port's Port VLAN ID 
	   will be changed to this VLAN ID, the port will be set to be a member of that 
	   VLAN ID, and the port will be forced into VLAN unaware mode. Once assigned, 
	   all traffic arriving on the port will be classified and switched on the 
	   RADIUS-assigned VLAN ID.
	   Admin State supported : Port-based and Single 802.1X and MAC-based Single Auth."
   ::= { gs2310pplusNASPortConfigEntry 4 }    
   
gs2310pplusNASPortConfigGuestVLANEnabled OBJECT-TYPE
   SYNTAX      INTEGER { disable(0), enable(1) }
   MAX-ACCESS  read-write
   STATUS      current
   DESCRIPTION
       "When Guest VLAN is both globally enabled and enabled (checked) for a given port, 
	   the switch considers moving the port into the Guest VLAN according to the rules
	   outlined below.
	   Admin State supported : Port-based , Single and Multi 802.1X."
   ::= { gs2310pplusNASPortConfigEntry 5 }    
   
gs2310pplusNASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode 
		and the supplicant is authorized.
		Unauthorized: The port is in Force Unauthorized or a single-supplicant 
		mode and the supplicant is not successfully authorized by the RADIUS server.
		X Auth/Y Unauth: The port is in a multi-supplicant mode. Currently X clients 
		are authorized and Y are unauthorized."
   ::= { gs2310pplusNASPortConfigEntry 6 }    
   
gs2310pplusNASPortConfigReauthenticate OBJECT-TYPE
   SYNTAX      INTEGER { doNothing(0), do(1) }
   MAX-ACCESS  read-write
   STATUS      current
   DESCRIPTION
       "Schedules a reauthentication whenever the quiet-period of the port runs out 
	   (EAPOL-based authentication). For MAC-based authentication, reauthentication 
	   will be attempted immediately.The button only has effect for successfully 
	   authenticated clients on the port and will not cause the clients to get 
	   temporarily unauthorized."
   ::= { gs2310pplusNASPortConfigEntry 7 }    

gs2310pplusNASPortConfigReinitialize OBJECT-TYPE
   SYNTAX      INTEGER { doNothing(0), do(1) }
   MAX-ACCESS  read-write
   STATUS      current
   DESCRIPTION
       "Forces a reinitialization of the clients on the port and thereby a reauthentication 
	   immediately. The clients will transfer to the unauthorized state while the 
	   reauthentication is in progress."
   ::= { gs2310pplusNASPortConfigEntry 8 }    

gs2310pplusNASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2310pplusNASPortConfigEntry 101 }

gs2310pplusNASSwitchStatusTable OBJECT-TYPE
   SYNTAX      SEQUENCE OF Gs2310pplusNASSwitchStatusEntry
   MAX-ACCESS  not-accessible
   STATUS      current
   DESCRIPTION
       ""
   ::= { gs2310pplusNAS 2 }

gs2310pplusNASSwitchStatusEntry OBJECT-TYPE
   SYNTAX      Gs2310pplusNASSwitchStatusEntry
   MAX-ACCESS  not-accessible
   STATUS      current
   DESCRIPTION
       ""
   INDEX    { gs2310pplusNASPortConfigPort }
   ::= { gs2310pplusNASSwitchStatusTable 1 }

Gs2310pplusNASSwitchStatusEntry ::= SEQUENCE {
   gs2310pplusNASSwitchStatusAdminState 	DisplayString,
   gs2310pplusNASSwitchStatusPortState		DisplayString,
   gs2310pplusNASSwitchStatusLastSource		DisplayString,
   gs2310pplusNASSwitchStatusLastID			DisplayString,
   gs2310pplusNASSwitchStatusQoSClass		DisplayString,
   gs2310pplusNASSwitchStatusPortVlanID		DisplayString
}
   
gs2310pplusNASSwitchStatusAdminState OBJECT-TYPE
   SYNTAX      DisplayString
   MAX-ACCESS  read-only
   STATUS      current
   DESCRIPTION
       "The port's current administrative state. Refer to NAS Admin State for a description of possible values."
   ::= { gs2310pplusNASSwitchStatusEntry 2 }   
   
gs2310pplusNASSwitchStatusPortState OBJECT-TYPE
   SYNTAX      DisplayString
   MAX-ACCESS  read-only
   STATUS      current
   DESCRIPTION
       "The current state of the port. Refer to NAS Port State for a description of the individual states."
   ::= { gs2310pplusNASSwitchStatusEntry 3 }      
   
gs2310pplusNASSwitchStatusLastSource OBJECT-TYPE
   SYNTAX      DisplayString
   MAX-ACCESS  read-only
   STATUS      current
   DESCRIPTION
       "The source MAC address carried in the most recently received EAPOL frame for EAPOL-based authentication, 
	   and the most recently received frame from a new client for MAC-based authentication."
   ::= { gs2310pplusNASSwitchStatusEntry 4 }      

gs2310pplusNASSwitchStatusLastID OBJECT-TYPE
   SYNTAX      DisplayString
   MAX-ACCESS  read-only
   STATUS      current
   DESCRIPTION
       "The user name (supplicant identity) carried in the most recently received Response Identity EAPOL frame 
	   for EAPOL-based authentication, and the source MAC address from the most recently received frame from a 
	   new client for MAC-based authentication."
   ::= { gs2310pplusNASSwitchStatusEntry 5 }      

gs2310pplusNASSwitchStatusQoSClass OBJECT-TYPE
   SYNTAX      DisplayString
   MAX-ACCESS  read-only
   STATUS      current
   DESCRIPTION
       "QoS Class assigned to the port by the RADIUS server if enabled."
   ::= { gs2310pplusNASSwitchStatusEntry 6 } 
   
gs2310pplusNASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2310pplusNASSwitchStatusEntry 7 } 

gs2310pplusNASPortStatus                                 OBJECT IDENTIFIER ::= { gs2310pplusNAS 3 }
   
gs2310pplusNASPortStatusCountersTable OBJECT-TYPE
   SYNTAX      SEQUENCE OF Gs2310pplusNASPortStatusCountersEntry
   MAX-ACCESS  not-accessible
   STATUS      current
   DESCRIPTION
       ""
   ::= { gs2310pplusNASPortStatus 1 }

gs2310pplusNASPortStatusCountersEntry OBJECT-TYPE
   SYNTAX      Gs2310pplusNASPortStatusCountersEntry
   MAX-ACCESS  not-accessible
   STATUS      current
   DESCRIPTION
       ""
   INDEX    { gs2310pplusNASPortConfigPort }
   ::= { gs2310pplusNASPortStatusCountersTable 1 }

Gs2310pplusNASPortStatusCountersEntry ::= SEQUENCE {
   gs2310pplusNASRxCountersEAPOLTotal  	                  Counter32,
   gs2310pplusNASRxCountersEAPOLResponseID	              Counter32,
   gs2310pplusNASRxCountersEAPOLResponses	              Counter32,
   gs2310pplusNASRxCountersEAPOLStart	                  Counter32,
   gs2310pplusNASRxCountersEAPOLLogoff                    Counter32,
   gs2310pplusNASRxCountersEAPOLInvalidType               Counter32,
   gs2310pplusNASRxCountersEAPOLInvalidLength             Counter32,
   gs2310pplusNASTxCountersEAPOLTotal                     Counter32,
   gs2310pplusNASTxCountersEAPOLRequestID                 Counter32,
   gs2310pplusNASTxCountersEAPOLRequests                  Counter32,
   gs2310pplusNASRxBackendServerCountersAccessChallenges  Counter32,
   gs2310pplusNASRxBackendServerCountersOtherRequests     Counter32,
   gs2310pplusNASRxBackendServerCountersAuthSuccesses     Counter32,
   gs2310pplusNASRxBackendServerCountersAuthFailures      Counter32,
   gs2310pplusNASTxBackendServerCountersResponses         Counter32,
   gs2310pplusNASLastSupplicantInfoMACAddress             DisplayString,
   gs2310pplusNASLastSupplicantInfoVlanID                 Integer32,
   gs2310pplusNASLastSupplicantInfoVersion                Integer32,
   gs2310pplusNASLastSupplicantInfoIdentity               DisplayString,
   gs2310pplusNASCountersDoClear                          INTEGER
}

gs2310pplusNASRxCountersEAPOLTotal OBJECT-TYPE
   SYNTAX      Counter32
   MAX-ACCESS  read-only
   STATUS      current
   DESCRIPTION
       "The number of valid EAPOL frames of any type that have been received by the switch."
   ::= { gs2310pplusNASPortStatusCountersEntry 2 }   

gs2310pplusNASRxCountersEAPOLResponseID OBJECT-TYPE
   SYNTAX      Counter32
   MAX-ACCESS  read-only
   STATUS      current
   DESCRIPTION
       "The number of valid EAPOL Response Identity frames that have been received by the switch."
   ::= { gs2310pplusNASPortStatusCountersEntry 3 }   

gs2310pplusNASRxCountersEAPOLResponses OBJECT-TYPE
   SYNTAX      Counter32
   MAX-ACCESS  read-only
   STATUS      current
   DESCRIPTION
       "The number of valid EAPOL response frames (other than Response Identity frames) 
	   that have been received by the switch."
   ::= { gs2310pplusNASPortStatusCountersEntry 4 }   

gs2310pplusNASRxCountersEAPOLStart OBJECT-TYPE
   SYNTAX      Counter32
   MAX-ACCESS  read-only
   STATUS      current
   DESCRIPTION
       "The number of EAPOL Start frames that have been received by the switch."
   ::= { gs2310pplusNASPortStatusCountersEntry 5 }   

gs2310pplusNASRxCountersEAPOLLogoff OBJECT-TYPE
   SYNTAX      Counter32
   MAX-ACCESS  read-only
   STATUS      current
   DESCRIPTION
       "The number of valid EAPOL Logoff frames that have been received by the switch."
   ::= { gs2310pplusNASPortStatusCountersEntry 6 }   

gs2310pplusNASRxCountersEAPOLInvalidType OBJECT-TYPE
   SYNTAX      Counter32
   MAX-ACCESS  read-only
   STATUS      current
   DESCRIPTION
       "The number of EAPOL frames that have been received by the switch in which 
	   the frame type is not recognized."
   ::= { gs2310pplusNASPortStatusCountersEntry 7 }   
   
gs2310pplusNASRxCountersEAPOLInvalidLength OBJECT-TYPE
   SYNTAX      Counter32
   MAX-ACCESS  read-only
   STATUS      current
   DESCRIPTION
       "The number of EAPOL frames that have been received by the switch in which the 
	   Packet Body Length field is invalid."
   ::= { gs2310pplusNASPortStatusCountersEntry 8 }   
   
gs2310pplusNASTxCountersEAPOLTotal OBJECT-TYPE
   SYNTAX      Counter32
   MAX-ACCESS  read-only
   STATUS      current
   DESCRIPTION
       "The number of EAPOL frames of any type that have been transmitted by the switch."
   ::= { gs2310pplusNASPortStatusCountersEntry 9 }   
   
gs2310pplusNASTxCountersEAPOLRequestID OBJECT-TYPE
   SYNTAX      Counter32
   MAX-ACCESS  read-only
   STATUS      current
   DESCRIPTION
       "The number of EAPOL Request Identity frames that have been transmitted by the switch."
   ::= { gs2310pplusNASPortStatusCountersEntry 10 }      

gs2310pplusNASTxCountersEAPOLRequests OBJECT-TYPE
   SYNTAX      Counter32
   MAX-ACCESS  read-only
   STATUS      current
   DESCRIPTION
       "The number of valid EAPOL Request frames (other than Request Identity frames) 
	   that have been transmitted by the switch."
   ::= { gs2310pplusNASPortStatusCountersEntry 11 }      
   
gs2310pplusNASRxBackendServerCountersAccessChallenges OBJECT-TYPE
   SYNTAX      Counter32
   MAX-ACCESS  read-only
   STATUS      current
   DESCRIPTION
       "802.1X-based: Counts the number of times that the switch receives the first request 
	   from the backend server following the first response from the supplicant.
	   MAC-based: Counts all Access Challenges received from the backend server for this 
	   port or client."
   ::= { gs2310pplusNASPortStatusCountersEntry 12 }      

gs2310pplusNASRxBackendServerCountersOtherRequests OBJECT-TYPE
   SYNTAX      Counter32
   MAX-ACCESS  read-only
   STATUS      current
   DESCRIPTION
       "802.1X-based: Counts the number of times that the switch sends an EAP Request 
	   packet following the first to the supplicant.
	   MAC-based: Not applicable."
   ::= { gs2310pplusNASPortStatusCountersEntry 13 }      
   
gs2310pplusNASRxBackendServerCountersAuthSuccesses OBJECT-TYPE
   SYNTAX      Counter32
   MAX-ACCESS  read-only
   STATUS      current
   DESCRIPTION
       "Counts the number of times that the switch receives a success indication. 
	   Indicates that the supplicant/client has successfully authenticated to the 
	   backend server."
   ::= { gs2310pplusNASPortStatusCountersEntry 14 }      
   
gs2310pplusNASRxBackendServerCountersAuthFailures OBJECT-TYPE
   SYNTAX      Counter32
   MAX-ACCESS  read-only
   STATUS      current
   DESCRIPTION
       "Counts the number of times that the switch receives a failure message. 
	   This indicates that the supplicant/client has not authenticated to the 
	   backend server. "
   ::= { gs2310pplusNASPortStatusCountersEntry 15 }      
   
gs2310pplusNASTxBackendServerCountersResponses OBJECT-TYPE
   SYNTAX      Counter32
   MAX-ACCESS  read-only
   STATUS      current
   DESCRIPTION
       "802.1X-based: Counts the number of times that the switch attempts to 
	   send a supplicant's first response packet to the backend server. Indicates 
	   the switch attempted communication with the backend server. Possible 
	   retransmissions are not counted. 
	   MAC-based: Counts all the backend server packets sent from the switch 
	   towards the backend server for a given port or client. Possible 
	   retransmissions are not counted."
   ::= { gs2310pplusNASPortStatusCountersEntry 16 }  

gs2310pplusNASLastSupplicantInfoMACAddress OBJECT-TYPE
   SYNTAX      DisplayString
   MAX-ACCESS  read-only
   STATUS      current
   DESCRIPTION
       "The MAC address of the last supplicant/client."
   ::= { gs2310pplusNASPortStatusCountersEntry 17 }  

gs2310pplusNASLastSupplicantInfoVlanID OBJECT-TYPE
   SYNTAX      Integer32
   MAX-ACCESS  read-only
   STATUS      current
   DESCRIPTION
       "The VLAN ID on which the last frame from the last supplicant/client was received."
   ::= { gs2310pplusNASPortStatusCountersEntry 18 }  
   
gs2310pplusNASLastSupplicantInfoVersion OBJECT-TYPE
   SYNTAX      Integer32
   MAX-ACCESS  read-only
   STATUS      current
   DESCRIPTION
       "802.1X-based: The protocol version number carried in the most recently 
	   received EAPOL frame. 
	   MAC-based: Not applicable."
   ::= { gs2310pplusNASPortStatusCountersEntry 19 }  

gs2310pplusNASLastSupplicantInfoIdentity OBJECT-TYPE
   SYNTAX      DisplayString
   MAX-ACCESS  read-only
   STATUS      current
   DESCRIPTION
       "802.1X-based: The user name (supplicant identity) carried in the most recently received 
	   Response Identity EAPOL frame. 
	   MAC-based: Not applicable."
   ::= { gs2310pplusNASPortStatusCountersEntry 20 }  

gs2310pplusNASCountersDoClear OBJECT-TYPE
   SYNTAX      INTEGER { doNothing(0), do(1) }
   MAX-ACCESS  read-write
   STATUS      current
   DESCRIPTION
       "Clear the counters for the selected port."
   ::= { gs2310pplusNASPortStatusCountersEntry 21 }    

gs2310pplusNASPortStatusClientsTable OBJECT-TYPE
   SYNTAX      SEQUENCE OF Gs2310pplusNASPortStatusClientsEntry
   MAX-ACCESS  not-accessible
   STATUS      current
   DESCRIPTION
       ""
   ::= { gs2310pplusNASPortStatus 2 }

gs2310pplusNASPortStatusClientsEntry OBJECT-TYPE
   SYNTAX      Gs2310pplusNASPortStatusClientsEntry
   MAX-ACCESS  not-accessible
   STATUS      current
   DESCRIPTION
       ""
   INDEX    { gs2310pplusNASPortConfigPort,
		gs2310pplusNASClientsIndex}
   ::= { gs2310pplusNASPortStatusClientsTable 1 }

Gs2310pplusNASPortStatusClientsEntry ::= SEQUENCE {
   gs2310pplusNASClientsIndex  	                  		    Integer32,
   gs2310pplusNASClientsIdentity							DisplayString,
   gs2310pplusNASClientsMACAddress  	                  	DisplayString,
   gs2310pplusNASClientsVlanID		              			Integer32,
   gs2310pplusNASClientsState	              				DisplayString,
   gs2310pplusNASClientsLastAuth	                  		DisplayString,
   gs2310pplusNASRxClientsEAPOLTotal  	                  	Counter32,
   gs2310pplusNASRxClientsEAPOLResponseID	              	Counter32,
   gs2310pplusNASRxClientsEAPOLResponses	              	Counter32,
   gs2310pplusNASRxClientsEAPOLStart	                  	Counter32,
   gs2310pplusNASRxClientsEAPOLLogoff                    	Counter32,
   gs2310pplusNASRxClientsEAPOLInvalidType               	Counter32,
   gs2310pplusNASRxClientsEAPOLInvalidLength             	Counter32,
   gs2310pplusNASTxClientsEAPOLTotal                     	Counter32,
   gs2310pplusNASTxClientsEAPOLRequestID                 	Counter32,
   gs2310pplusNASTxClientsEAPOLRequests                  	Counter32,
   gs2310pplusNASRxBackendServerClientsAccessChallenges  	Counter32,
   gs2310pplusNASRxBackendServerClientsOtherRequests     	Counter32,
   gs2310pplusNASRxBackendServerClientsAuthSuccesses     	Counter32,
   gs2310pplusNASRxBackendServerClientsAuthFailures      	Counter32,
   gs2310pplusNASTxBackendServerClientsResponses         	Counter32
}

gs2310pplusNASClientsIndex OBJECT-TYPE
   SYNTAX      Integer32(1..255)
   MAX-ACCESS  not-accessible
   STATUS      current
   DESCRIPTION
       "Entry of client table in the port."
   ::= { gs2310pplusNASPortStatusClientsEntry 1 } 
   
gs2310pplusNASClientsIdentity OBJECT-TYPE
   SYNTAX      DisplayString
   MAX-ACCESS  read-only
   STATUS      current
   DESCRIPTION
       "Shows the identity of the supplicant, as received in the Response Identity 
	   EAPOL frame.This isn't available for MAC-based Auth."
   ::= { gs2310pplusNASPortStatusClientsEntry 2 }
   
gs2310pplusNASClientsMACAddress OBJECT-TYPE
   SYNTAX      DisplayString
   MAX-ACCESS  read-only
   STATUS      current
   DESCRIPTION
       "Multi 802.1X, this column holds the MAC address of the attached supplicant. 
	   MAC-based Auth., this column holds the MAC address of the attached client."
   ::= { gs2310pplusNASPortStatusClientsEntry 3 }  

gs2310pplusNASClientsVlanID OBJECT-TYPE
   SYNTAX      Integer32(1..4095)
   MAX-ACCESS  read-only
   STATUS      current
   DESCRIPTION
       "This column holds the VLAN ID that the corresponding client is currently 
	   secured through the Port Security module."
   ::= { gs2310pplusNASPortStatusClientsEntry 4 }  
   
gs2310pplusNASClientsState OBJECT-TYPE
   SYNTAX      DisplayString
   MAX-ACCESS  read-only
   STATUS      current
   DESCRIPTION
       "The client can either be authenticated or unauthenticated. In the authenticated 
	   state, it is allowed to forward frames on the port, and in the unauthenticated 
	   state, it is blocked."
   ::= { gs2310pplusNASPortStatusClientsEntry 5 }  

gs2310pplusNASClientsLastAuth OBJECT-TYPE
   SYNTAX      DisplayString
   MAX-ACCESS  read-only
   STATUS      current
   DESCRIPTION
       "Shows the date and time of the last authentication of the client."
   ::= { gs2310pplusNASPortStatusClientsEntry 6 }  
   
gs2310pplusNASRxClientsEAPOLTotal OBJECT-TYPE
   SYNTAX      Counter32
   MAX-ACCESS  read-only
   STATUS      current
   DESCRIPTION
       "The number of valid EAPOL frames of any type that have been received by the switch."
   ::= { gs2310pplusNASPortStatusClientsEntry 7 }  

gs2310pplusNASRxClientsEAPOLResponseID OBJECT-TYPE
   SYNTAX      Counter32
   MAX-ACCESS  read-only
   STATUS      current
   DESCRIPTION
       "The number of valid EAPOL Response Identity frames that have been received by the switch."
   ::= { gs2310pplusNASPortStatusClientsEntry 8 }   

gs2310pplusNASRxClientsEAPOLResponses OBJECT-TYPE
   SYNTAX      Counter32
   MAX-ACCESS  read-only
   STATUS      current
   DESCRIPTION
       "The number of valid EAPOL response frames (other than Response Identity frames) 
	   that have been received by the switch."
   ::= { gs2310pplusNASPortStatusClientsEntry 9 }   

gs2310pplusNASRxClientsEAPOLStart OBJECT-TYPE
   SYNTAX      Counter32
   MAX-ACCESS  read-only
   STATUS      current
   DESCRIPTION
       "The number of EAPOL Start frames that have been received by the switch."
   ::= { gs2310pplusNASPortStatusClientsEntry 10 }   

gs2310pplusNASRxClientsEAPOLLogoff OBJECT-TYPE
   SYNTAX      Counter32
   MAX-ACCESS  read-only
   STATUS      current
   DESCRIPTION
       "The number of valid EAPOL Logoff frames that have been received by the switch."
   ::= { gs2310pplusNASPortStatusClientsEntry 11 }   

gs2310pplusNASRxClientsEAPOLInvalidType OBJECT-TYPE
   SYNTAX      Counter32
   MAX-ACCESS  read-only
   STATUS      current
   DESCRIPTION
       "The number of EAPOL frames that have been received by the switch in which 
	   the frame type is not recognized."
   ::= { gs2310pplusNASPortStatusClientsEntry 12 }   
   
gs2310pplusNASRxClientsEAPOLInvalidLength OBJECT-TYPE
   SYNTAX      Counter32
   MAX-ACCESS  read-only
   STATUS      current
   DESCRIPTION
       "The number of EAPOL frames that have been received by the switch in which the 
	   Packet Body Length field is invalid."
   ::= { gs2310pplusNASPortStatusClientsEntry 13 }

gs2310pplusNASTxClientsEAPOLTotal OBJECT-TYPE
   SYNTAX      Counter32
   MAX-ACCESS  read-only
   STATUS      current
   DESCRIPTION
       "The number of EAPOL frames of any type that have been transmitted by the switch."
   ::= { gs2310pplusNASPortStatusClientsEntry 14 }   
   
gs2310pplusNASTxClientsEAPOLRequestID OBJECT-TYPE
   SYNTAX      Counter32
   MAX-ACCESS  read-only
   STATUS      current
   DESCRIPTION
       "The number of EAPOL Request Identity frames that have been transmitted by the switch."
   ::= { gs2310pplusNASPortStatusClientsEntry 15 }      

gs2310pplusNASTxClientsEAPOLRequests OBJECT-TYPE
   SYNTAX      Counter32
   MAX-ACCESS  read-only
   STATUS      current
   DESCRIPTION
       "The number of valid EAPOL Request frames (other than Request Identity frames) 
	   that have been transmitted by the switch."
   ::= { gs2310pplusNASPortStatusClientsEntry 16 }        

gs2310pplusNASRxBackendServerClientsAccessChallenges OBJECT-TYPE
   SYNTAX      Counter32
   MAX-ACCESS  read-only
   STATUS      current
   DESCRIPTION
       "802.1X-based: Counts the number of times that the switch receives the first request 
	   from the backend server following the first response from the supplicant.
	   MAC-based: Counts all Access Challenges received from the backend server for this 
	   port or client."
   ::= { gs2310pplusNASPortStatusClientsEntry 17 }      

gs2310pplusNASRxBackendServerClientsOtherRequests OBJECT-TYPE
   SYNTAX      Counter32
   MAX-ACCESS  read-only
   STATUS      current
   DESCRIPTION
       "802.1X-based: Counts the number of times that the switch sends an EAP Request 
	   packet following the first to the supplicant.
	   MAC-based: Not applicable."
   ::= { gs2310pplusNASPortStatusClientsEntry 18 }      
   
gs2310pplusNASRxBackendServerClientsAuthSuccesses OBJECT-TYPE
   SYNTAX      Counter32
   MAX-ACCESS  read-only
   STATUS      current
   DESCRIPTION
       "Counts the number of times that the switch receives a success indication. 
	   Indicates that the supplicant/client has successfully authenticated to the 
	   backend server."
   ::= { gs2310pplusNASPortStatusClientsEntry 19 }      
   
gs2310pplusNASRxBackendServerClientsAuthFailures OBJECT-TYPE
   SYNTAX      Counter32
   MAX-ACCESS  read-only
   STATUS      current
   DESCRIPTION
       "Counts the number of times that the switch receives a failure message. 
	   This indicates that the supplicant/client has not authenticated to the 
	   backend server. "
   ::= { gs2310pplusNASPortStatusClientsEntry 20 }      
   
gs2310pplusNASTxBackendServerClientsResponses OBJECT-TYPE
   SYNTAX      Counter32
   MAX-ACCESS  read-only
   STATUS      current
   DESCRIPTION
       "802.1X-based: Counts the number of times that the switch attempts to 
	   send a supplicant's first response packet to the backend server. Indicates 
	   the switch attempted communication with the backend server. Possible 
	   retransmissions are not counted. 
	   MAC-based: Counts all the backend server packets sent from the switch 
	   towards the backend server for a given port or client. Possible 
	   retransmissions are not counted."
   ::= { gs2310pplusNASPortStatusClientsEntry 21 }  
   

gs2310pplusMaintenance                                           OBJECT IDENTIFIER ::= { lancomGS2310PPLUS 4 }

gs2310pplusRestartDevice OBJECT-TYPE
   SYNTAX      INTEGER { disable(0), enable(1) }
   MAX-ACCESS  read-write
   STATUS      current
   DESCRIPTION
       "default: 0
        0:none
        1:yes"
   ::= { gs2310pplusMaintenance 1 }

gs2310pplusColdRestartDevice OBJECT-TYPE
   SYNTAX      INTEGER { disable(0), enable(1) }
   MAX-ACCESS  read-write
   STATUS      current
   DESCRIPTION
       "default: 0
        0:none
        1:yes"
   ::= { gs2310pplusMaintenance 1500 }

gs2310pplusFirmware                                         OBJECT IDENTIFIER ::= { gs2310pplusMaintenance 2 }

gs2310pplusFirmwareIpAddress OBJECT-TYPE
   SYNTAX       IpAddress
   MAX-ACCESS   read-write
   STATUS       current
   DESCRIPTION
        "Get/Set the firmware tftp server."
   ::= { gs2310pplusFirmware 1 }

gs2310pplusFirmwareFileName OBJECT-TYPE
   SYNTAX       DisplayString
   MAX-ACCESS   read-write
   STATUS       current
   DESCRIPTION
        "Get/Set the path and filename for firmware upgrading."
   ::= { gs2310pplusFirmware 2 }

gs2310pplusDoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2310pplusFirmware 3 }

gs2310pplusSaveOrRestore                                         OBJECT IDENTIFIER ::= { gs2310pplusMaintenance 3 }

gs2310pplusFactoryDefaults OBJECT-TYPE
   SYNTAX      INTEGER { none(0), yes(1) }
   MAX-ACCESS  read-write
   STATUS      current
   DESCRIPTION
       "default: 0
        0:none
        1:yes"
   ::= { gs2310pplusSaveOrRestore 1 }

gs2310pplusSaveStart OBJECT-TYPE
   SYNTAX      INTEGER { none(0), yes(1) }
   MAX-ACCESS  read-write
   STATUS      current
   DESCRIPTION
       "default: 0
        0:none
        1:yes"
   ::= { gs2310pplusSaveOrRestore 2 }

gs2310pplusSaveUser OBJECT-TYPE
   SYNTAX      INTEGER { none(0), yes(1) }
   MAX-ACCESS  read-write
   STATUS      current
   DESCRIPTION
       "default: 0
        0:none
        1:yes"
   ::= { gs2310pplusSaveOrRestore 3 }

gs2310pplusRestoreUser OBJECT-TYPE
   SYNTAX      INTEGER { none(0), yes(1) }
   MAX-ACCESS  read-write
   STATUS      current
   DESCRIPTION
       "default: 0
        0:none
        1:yes"
   ::= { gs2310pplusSaveOrRestore 4 }


gs2310pplusExportOrImport                                        OBJECT IDENTIFIER ::= { gs2310pplusMaintenance 4 }

gs2310pplusExportIpAddress OBJECT-TYPE
   SYNTAX       IpAddress
   MAX-ACCESS   read-write
   STATUS       current
   DESCRIPTION
        "Get/Set the export tftp server."
   ::= { gs2310pplusExportOrImport 1 }

gs2310pplusExportConfigName OBJECT-TYPE
   SYNTAX       DisplayString
   MAX-ACCESS   read-write
   STATUS       current
   DESCRIPTION
       "Get/Set the export file path and name."
   ::= { gs2310pplusExportOrImport 2 }

gs2310pplusDoExportConfig OBJECT-TYPE
   SYNTAX       INTEGER{ doNothing(0), do(1) }
   MAX-ACCESS   read-write
   STATUS       current
   DESCRIPTION
        "Do export-config.
         Get this OID always return zero.
         1 - export."
   ::= { gs2310pplusExportOrImport 3 }

gs2310pplusImportIpAddress OBJECT-TYPE
   SYNTAX       IpAddress
   MAX-ACCESS   read-write
   STATUS       current
   DESCRIPTION
        "Get/Set the import tftp server."
   ::= { gs2310pplusExportOrImport 4 }

gs2310pplusImportConfigName OBJECT-TYPE
   SYNTAX      DisplayString
   MAX-ACCESS  read-write
   STATUS      current
   DESCRIPTION
       "Get/Set the import file path and name."
   ::= { gs2310pplusExportOrImport 5 }

gs2310pplusDoImportConfig OBJECT-TYPE
   SYNTAX       INTEGER{ doNothing(0), do(1) }
   MAX-ACCESS   read-write
   STATUS       current
   DESCRIPTION
        "Do export-config.
         Get this OID always return zero.
         1 - import."
   ::= { gs2310pplusExportOrImport 6 }

gs2310pplusDiagnostics                                           OBJECT IDENTIFIER ::= { gs2310pplusMaintenance 5 }

gs2310pplusPingIpAddress OBJECT-TYPE
   SYNTAX      IpAddress
   MAX-ACCESS  read-write
   STATUS      current
   DESCRIPTION
       " The destination IP Address. "
   ::= { gs2310pplusDiagnostics 1 }
   
gs2310pplusPingSize OBJECT-TYPE
   SYNTAX      Integer32(60..1400)
   MAX-ACCESS  read-write
   STATUS      current
   DESCRIPTION
       " Size of ICMP echo packet.
         range : 60-1400, default : 64. "
   ::= { gs2310pplusDiagnostics 2 }   

gs2310pplusDoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2310pplusDiagnostics 3 }

gs2310pplusPingResult OBJECT-TYPE
   SYNTAX      DisplayString
   MAX-ACCESS  read-only
   STATUS      current
   DESCRIPTION
       " Show ping result. "
   ::= { gs2310pplusDiagnostics 4 }

gs2310pplusPing6IpAddress OBJECT-TYPE
   SYNTAX      DisplayString
   MAX-ACCESS  read-write
   STATUS      current
   DESCRIPTION
       " The destination IPv6 Address. "
   ::= { gs2310pplusDiagnostics 5 }
   
gs2310pplusPing6Size OBJECT-TYPE
   SYNTAX      Integer32(60..1400)
   MAX-ACCESS  read-write
   STATUS      current
   DESCRIPTION
       " Size of ICMP echo packet.
         range : 60-1400. "
   ::= { gs2310pplusDiagnostics 6 }   

gs2310pplusDoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2310pplusDiagnostics 7 }

gs2310pplusPing6Result OBJECT-TYPE
   SYNTAX      DisplayString
   MAX-ACCESS  read-only
   STATUS      current
   DESCRIPTION
       " Show ping result. "
   ::= { gs2310pplusDiagnostics 8 }




------------------------------------------------------------------------------------------------------------------
gs2310pplusTrap                                                  OBJECT IDENTIFIER ::= { lancomGS2310PPLUS 5 }

gs2310pplusTrapEvent                                             OBJECT IDENTIFIER ::= { gs2310pplusTrap 1 }

gs2310pplusEmergency NOTIFICATION-TYPE
  OBJECTS   { gs2310pplusInformation }
  STATUS        current
    DESCRIPTION
        "The severity level is Emergency. The system is unusable."
    ::= { gs2310pplusTrapEvent 1 }

gs2310pplusAlert NOTIFICATION-TYPE
  OBJECTS   { gs2310pplusInformation }
  STATUS        current
    DESCRIPTION
        "The severity level is Alert. The action must be taken immediately."
    ::= { gs2310pplusTrapEvent 2 }

gs2310pplusCritical NOTIFICATION-TYPE
  OBJECTS   { gs2310pplusInformation }
  STATUS        current
    DESCRIPTION
        "The severity level is Critical. Critical conditions."
    ::= { gs2310pplusTrapEvent 3 }

gs2310pplusError NOTIFICATION-TYPE
  OBJECTS   { gs2310pplusInformation }
  STATUS        current
    DESCRIPTION
        "The severity level is Error. Error conditions."
    ::= { gs2310pplusTrapEvent 4 }

gs2310pplusWarning NOTIFICATION-TYPE
  OBJECTS   { gs2310pplusInformation }
  STATUS        current
    DESCRIPTION
        "The severity level is Warning. Warning conditions."
    ::= { gs2310pplusTrapEvent 5 }

gs2310pplusNotice NOTIFICATION-TYPE
  OBJECTS   { gs2310pplusInformation }
  STATUS        current
    DESCRIPTION
        "The severity level is Notice. Normal but significant condition."
    ::= { gs2310pplusTrapEvent 6 }

gs2310pplusInformational NOTIFICATION-TYPE
  OBJECTS   { gs2310pplusInformation }
  STATUS        current
    DESCRIPTION
        "The severity level is Informational. Informational messages."
    ::= { gs2310pplusTrapEvent 7 }

gs2310pplusDebug NOTIFICATION-TYPE
  OBJECTS   { gs2310pplusInformation }
  STATUS        current
    DESCRIPTION
        "The severity level is Debug. debug-level messages."
    ::= { gs2310pplusTrapEvent 8 }

gs2310pplusTrapVariable                                          OBJECT IDENTIFIER ::= { gs2310pplusTrap 2 }

gs2310pplusInformation OBJECT-TYPE
    SYNTAX      DisplayString
    MAX-ACCESS  read-only
    STATUS      current
    DESCRIPTION
        "Trap information."
    ::= { gs2310pplusTrapVariable 1 }


END

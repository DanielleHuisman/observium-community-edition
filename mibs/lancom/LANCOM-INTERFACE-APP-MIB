LANCOM-INTERFACE-APP-MIB DEFINITIONS ::= BEGIN

-- Broadcom FASTPATH INTERFACE APPLICATION MIB
-- Copyright 2016 Broadcom.
-- This SNMP Management Information Specification
-- embodies Broadcom's confidential and proprietary
-- intellectual property.  Broadcom retains all title
-- and ownership in the Specification including any revisions.

-- This Specification is supplied "AS IS", Broadcom 
-- makes no warranty, either expressed or implied,
-- as to the use, operation, condition, or performance of the
-- Specification.

IMPORTS
    MODULE-IDENTITY, OBJECT-TYPE,
    NOTIFICATION-TYPE, Unsigned32       FROM SNMPv2-SMI
    ifIndex                             FROM IF-MIB
    fastPath                            FROM LANCOM-REF-MIB;

    fastPathInterfaceApp MODULE-IDENTITY
        LAST-UPDATED "201608180000Z" -- 18 Aug 2016 12:00:00 GMT
        ORGANIZATION "Broadcom "
        CONTACT-INFO
            "                      Customer Support
            Postal:                Broadcom 
                                   1030 Swabia Court
                                   Suite 400
                                   Durham, NC 27703
            Tel:                   +1 919 865 2700"
        DESCRIPTION
            "The Broadcom Private MIB for FASTPATH INTERFACE APPLICATION"

        -- Revision history.
        REVISION
            "201608180000Z" -- 18 Aug 2016 12:00:00 GMT
        DESCRIPTION
            "Initial version."
           
    ::= { fastPath 70 }

agentLinkFlapMIBObjects  OBJECT IDENTIFIER ::= { fastPathInterfaceApp 1 }
agentLinkFlapGlobal      OBJECT IDENTIFIER ::= { agentLinkFlapMIBObjects 1 }

-- ***************************************************************************
--
-- The INTERFACE APPLICATION Global Group
--
-- ***************************************************************************

agentLinkFlapAdminMode  OBJECT-TYPE
        SYNTAX      INTEGER {
                      enable(1),
                      disable(2)
                    }
        MAX-ACCESS  read-write
        STATUS      current
        DESCRIPTION
                   "Indicates the Administrative mode of Link Flap
                    Feature.

                    enable -- Link Flap is enabled.
                    disable -- Link Flap is disabled."
        ::= { agentLinkFlapGlobal 1 }

agentLinkFlapDuration OBJECT-TYPE
        SYNTAX      Unsigned32  (3..200)
        UNITS       "seconds"
        MAX-ACCESS  read-write
        STATUS      current
        DESCRIPTION
                   "Indicates interval in seconds at which link flaps
                    are collected. When the time is out, the link flap 
                    counter is cleared."
        ::= { agentLinkFlapGlobal 2 }

agentLinkFlapMaxCount OBJECT-TYPE
        SYNTAX      Unsigned32 (2..100)
        MAX-ACCESS  read-write
        STATUS      current
        DESCRIPTION
                   "Indicates the number of link flaps per configured
                    duration which triggers a port to d-disable mode."
        ::= { agentLinkFlapGlobal 3 }

END

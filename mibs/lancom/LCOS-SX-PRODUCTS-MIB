LCOS-SX-PRODUCTS-MIB  DEFINITIONS ::= BEGIN

IMPORTS
    MODULE-IDENTITY, OBJECT-TYPE, enterprises  FROM SNMPv2-SMI
    lcosSX2                                    FROM LANCOM-REF-MIB;

lcosSxProducts MODULE-IDENTITY
    LAST-UPDATED "202111190000Z"
    ORGANIZATION "LANCOM Systems GmbH"
    CONTACT-INFO
        "
        Adenauerstrasse 20 / B2
        52146 Wuerselen
        Germany

        Phone:  +49 (0)2405 49 93 6 0
        Fax:    +49 (0)2405 49 93 6 99
        E-Mail: info@lancom.de"
    DESCRIPTION
        "LANCOM LCOS-SX Products MIB"
    REVISION      "202111190000Z"
    DESCRIPTION
        "Initial version of this MIB module."
    ::= { lcosSX2 8 }

lcosSxProductsGS4530X   OBJECT IDENTIFIER ::= { lcosSxProducts 4530 }

lcosSxProductsGS4530XP  OBJECT IDENTIFIER ::= { lcosSxProducts 4531 }

lcosSxProductsGS4554X   OBJECT IDENTIFIER ::= { lcosSxProducts 4554 }

lcosSxProductsGS4554XP  OBJECT IDENTIFIER ::= { lcosSxProducts 4555 }

lcosSxProductsXS5110F   OBJECT IDENTIFIER ::= { lcosSxProducts 5110 }

lcosSxProductsXS5116QF  OBJECT IDENTIFIER ::= { lcosSxProducts 5116 }

lcosSxProductsXS6128QF  OBJECT IDENTIFIER ::= { lcosSxProducts 6128 }


END

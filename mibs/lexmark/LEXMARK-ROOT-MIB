LEXMARK-ROOT-MIB DEFINITIONS ::= BEGIN

IMPORTS
    MODULE-IDENTITY, enterprises
        FROM SNMPv2-SMI;

lexmarkMIB       MODULE-IDENTITY
    LAST-UPDATED "201012012300Z"
    ORGANIZATION "Lexmark International, Inc."
    CONTACT-INFO "Contact your local support team or service provider."
    DESCRIPTION  "The root mib Module for Lexmark International

                  Copyright 2009 Lexmark International"
    REVISION    "201012012300Z"
    DESCRIPTION
        "Version 1.0.0 of the LEXMARK-ROOT-MIB"
    REVISION     "200911242040Z"
    DESCRIPTION  "Version 0.0.1 Initial release of LEXMARK-ROOT-MIB"
    ::= { lexmarkModules 1 }

lexmark                  OBJECT IDENTIFIER ::= { enterprises 641 }
lexmarkModules           OBJECT IDENTIFIER ::= { lexmark 4 }
lexmarkMibObjects        OBJECT IDENTIFIER ::= { lexmark 5 }

END

-- Lexmark International
        --
        --
        -- filename: LEXMARK-SETTINGS.mib
        -- $Revision: 1.0 $
        -- $Date: 2014/04/15

LEXMARK-SETTINGS-MIB DEFINITIONS ::= BEGIN

IMPORTS
    lexmark, lexmarkModules
        FROM LEXMARK-ROOT-MIB

    MODULE-IDENTITY
        FROM SNMPv2-SMI;

settings MODULE-IDENTITY
    LAST-UPDATED "201403161242Z"
    ORGANIZATION "Lexmark International, Inc."
    CONTACT-INFO "Contact your local support team or service provider."
    DESCRIPTION
        "The MIB defines the device settings permitting management, values and
         specification of the device settings.

         Copyright (C) 2014 Lexmark International, Inc."
    REVISION    "201403161242Z"
    DESCRIPTION
        "Definition of the settings OID under the lexmark OID"
    ::= { lexmark 7 }

settingsMIBAdminInfo    OBJECT IDENTIFIER ::= { settings 1 }
settingsMIBCompliances  OBJECT IDENTIFIER ::= { settingsMIBAdminInfo 1 }
settingsMIBGroups       OBJECT IDENTIFIER ::= { settingsMIBAdminInfo 2 }

settingsControl         OBJECT IDENTIFIER ::= { settings 2 }
settingsDefinition      OBJECT IDENTIFIER ::= { settings 3 }

END

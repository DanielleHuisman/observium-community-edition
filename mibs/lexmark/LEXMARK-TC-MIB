-- Updated on Thursday December 07, 2017; 16:30
-- Version 1.0.3
LEXMARK-TC-MIB DEFINITIONS ::=BEGIN

IMPORTS
    lexmarkModules
        FROM LEXMARK-ROOT-MIB
    MODULE-IDENTITY
        FROM SNMPv2-SMI
    TEXTUAL-CONVENTION
        FROM SNMPv2-TC;

lexmarkTCMIB       MODULE-IDENTITY
    LAST-UPDATED "201105021547Z"
    ORGANIZATION "Lexmark International, Inc."
    CONTACT-INFO "Contact your local support team or service provider."
    DESCRIPTION  "Textual conventions and enumerations used by Lexmark MIBs
                 Copyright 2009 Lexmark International"

    REVISION     "201712071630Z"
    DESCRIPTION
        "Version 1.0.3
         Added the following paperSizeTC entries:
            paper11x17(143)
            a3Plus(144)
            bannerLetter(145)
            bannerA4(146)"

    REVISION     "201709151530Z"
    DESCRIPTION
        "Version 1.0.2
         Added the this UnitsTC entry:
            tenthsOfOtherUnits(42)"

    REVISION     "201707201810Z"
    DESCRIPTION
        "Version 1.0.1
         Added the following paperTypeTC entries:
            coatedPaper (38)
            glossy (39)
            photPaper (40)
            greetingCard (41)
            heavyCard (42)
            roughEnvelop (43)
            heavyCottonPaper (44)
            veryHeavyPaper (45)
            heavyGloss (46)
            rfidLabels (47)
            businessCard (48)"

    REVISION     "201105021547Z"
    DESCRIPTION
        "Version 1.0.0
         Added the following paperSizeTC entries:
            card3onehalfx5 (21)
            card4x8 (22)
            card5x7 (23)
            card10x15 (24)
            card10x20 (25)
            card13x18 (26)

         Added the following paperTypeTC entries:
            premiumPlain (17)
            colorLokCertifiedPlain (18)
            lexmarkPerfectFinishPhoto (19)
            lexmarkPhoto (20)
            glossyPhoto (21)
            mattePhoto (22)
            inkjetMatteBrochure (23)
            inkjetGlossyBrochure (24)
            ironOnTransfer (25)

         Copyright 2009 Lexmark International"
	REVISION     "200904030000Z"
    DESCRIPTION  "Ver 0.0.1
                  03 Apr 2009 - Moved AdminStatusTC and StatusTC here from
                     LEXMARK-NONAME-MIB and created new KeyValueTC.
                  06 Mar 2009 - Initial creation
                  - under development"
   ::= { lexmarkModules 2 }

-- definition of textual conventions

UnitsTC ::= TEXTUAL-CONVENTION
    STATUS      current
    DESCRIPTION
        "Units of measure used by the corresponding counter"
    SYNTAX      INTEGER {
                    unknown(1),
                    other(2),
                    items(3),
                    sides(4),
                    sheets(5),
                    millimeters(16),
                    centimeters(17),
                    meters(18),
                    inches(19),
                    feet(20),
                    grams(21),
                    ounces(22),
                    nanoseconds(32),
                    microseconds(33),
                    milliseconds(34),
                    seconds(35),
                    minutes(36),
                    hours(37),
                    days(38),
                    weeks(39),
                    months(40),
                    years(41),
                    tenthsOfOtherUnits(42)
                }

PaperSizeTC ::= TEXTUAL-CONVENTION
    STATUS      current
    DESCRIPTION
        "Paper sizes.
         bit 5 - envelope
         bit 6 - ISO size
         bit 7 - JIS size

         1 -> 31  -  US Papers
         32 -> 63 -  US Envelopes
         64 -> 95 -  ISO papers
         96 -> 127 - ISO envelopes
         128 -> 160 - JIS papers
         161 -> 192 - JIS envelopes
         "
    SYNTAX      INTEGER {
                    unknown(1),
                    other(2),
                    universal(3),
                    custom(4),

                    letter(8),
                    legal(9),
                    executive(10),
                    folio(11),
                    statement(12),
                    oficio(13),
                    tabloid(14),
                    businessCard(15),
                    idCard(16),
                    card3x5(17),
                    card4x6(18),
                    bookOriginal(19),
                    hagaki(20),
                    card3onehalfx5(21),
                    card4x8(22),
                    card5x7(23),
                    card10x15(24),
                    card10x20(25),
                    card13x18(26),
                    paper12x18(27),
                    sra3(28),
                    envelope7threequarters(32),
                    envelope9(33),
                    envelope10(34),
                    envelopeDL(35),
                    envelopeOther(36),
                    isoA0(64),
                    isoA1(65),
                    isoA2(66),
                    isoA3(67),
                    isoA4(68),
                    isoA5(69),
                    isoA6(70),

                    isoB0(72),
                    isoB1(73),
                    isoB2(74),
                    isoB3(75),
                    isoB4(76),
                    isoB5(77),
                    isoB6(78),

                    isoC0(80),
                    isoC1(81),
                    isoC2(82),
                    isoC3(83),
                    isoC4(84),
                    isoC5(85),
                    isoC6(86),

                    isoEnvelopeA0(96),
                    isoEnvelopeA1(97),
                    isoEnvelopeA2(98),
                    isoEnvelopeA3(99),
                    isoEnvelopeA4(100),
                    isoEnvelopeA5(101),
                    isoEnvelopeA6(102),

                    isoEnvelopeB0(104),
                    isoEnvelopeB1(105),
                    isoEnvelopeB2(106),
                    isoEnvelopeB3(107),
                    isoEnvelopeB4(108),
                    isoEnvelopeB5(109),
                    isoEnvelopeB6(110),

                    isoEnvelopeC0(112),
                    isoEnvelopeC1(113),
                    isoEnvelopeC2(114),
                    isoEnvelopeC3(115),
                    isoEnvelopeC4(116),
                    isoEnvelopeC5(117),
                    isoEnvelopeC6(118),

                    jisB0(136),
                    jisB1(137),
                    jisB2(138),
                    jisB3(139),
                    jisB4(140),
                    jisB5(141),
                    jisB6(142),

                    paper11x17(143),
                    a3Plus(144),
                    bannerLetter(145),
                    bannerA4(146)

                    }


PaperTypeTC ::= TEXTUAL-CONVENTION
    STATUS      current
    DESCRIPTION
        "Paper types."
    SYNTAX      INTEGER {
                    unknown(1),
                    other(2),
                    plain(3),
                    cardstock(4),
                    transparancy(5),
                    recycled(6),
                    labels(7),
                    vinylLabels(8),
                    bond(9),
                    letterhead(10),
                    preprinted(11),
                    colored(12),
                    light(13),
                    heavy(14),
                    roughOrCotton(15),
                    envelope(16),
                    premimuPlain(17),
                    colorLokCertifiedPlain(18),
                    lexmarkPerfectFinishPhoto(19),
                    lexmarkPhoto(20),
                    glossyPhoto(21),
                    mattePhoto(22),
                    inkjetMatteBrochure(23),
                    inkjetGlossyBrochure(24),
                    ironOnTransfer(25),
                    customtype1(32),
                    customtype2(33),
                    customtype3(34),
                    customtype4(35),
                    customtype5(36),
                    customtype6(37),
                    coatedPaper(38),
                    glossy(39),
                    photPaper(40),
                    greetingCard(41),
                    heavyCard(42),
                    roughEnvelop(43),
                    heavyCottonPaper(44),
                    veryHeavyPaper(45),
                    heavyGloss(46),
                    rfidLabels(47),
                    businessCard(48)
                }

AdminStatusTC ::= TEXTUAL-CONVENTION
    STATUS     current
    DESCRIPTION
        "The administrative status for the item.  This is the desired state for
        the object as set by the administrator.  The types of unknown and other
        are for reporting only and should not be supported for setting.

        Definitions:
        up        - The desired state of this item is active and running.
        disabled  - The desired state of this item is disabled."

    SYNTAX      INTEGER {
                    unknown(1),
                    other(3),
                    up(4),
                    disabled(5)
                }

StatusTC ::= TEXTUAL-CONVENTION
    STATUS     current
    DESCRIPTION
        "The status of an item.  The bottom 4 bits will describe operational
         status and higher bits will be anded with this to determine the
         current status.
         Bitmap:
         - bit 0-3  - General status
         - bit 4    - Disabled.  Set only if the item has been disabled by the
                      admin.  Cleared otherwise.
         - bit 5    - Optional license required.  Set only if this item
                      requires an optional license for operation.
         - bit 6    - License state.  0 = unlicensed, 1 = licensed.  This bit
                      may only be set if bit 5 is also set (licensed required)"

    SYNTAX      INTEGER {
                    unknown(1),
                    other(2),
                    ok(3),
                    offline(4),
                    warning(5),
                    broken(6),

                    disabledUnknown(17),    -- 16 + 1
                    disabledOther(18),      -- 16 + 2
                    disabledOk(19),         -- 16 + 3
                    disabledOffline(20),    -- 16 + 4
                    disabledWarning(21),    -- 16 + 5
                    disabledBroken(22),     -- 16 + 6

                    unlicensedUnknown(33),  -- 32 + 1
                    unlicensedOther(34),    -- 32 + 2
                    unlicensedOk(35),       -- 32 + 3
                    unlicensedOffline(36),  -- 32 + 4
                    unlicensedWarning(37),  -- 32 + 5
                    unlicensedBroken(38),   -- 32 + 6

                    licensedUnknown(97),    -- 64 + 32 + 1
                    licensedOther(98),      -- 64 + 32 + 2
                    licensedOk(99),         -- 64 + 32 + 3
                    licensedOffline(100),   -- 64 + 32 + 4
                    licensedWarning(101),   -- 64 + 32 + 5
                    licensedBroken(102)     -- 64 + 32 + 6

                }

KeyValueTC ::= TEXTUAL-CONVENTION
    DISPLAY-HINT "255a"
    STATUS       current
    DESCRIPTION
        "A key=value; delimited string to hold various pieces of data.  Each
        data item should consist of a key (as defined in the table below),
        followed by an equal sign ('='), followed by a semi-colon.  The last
        item in the list should have a semi-colon.  If it is necessary to use
        and equal or a semi-colon as part of the data, it should be delimited
        via the \ character (ie \= or \;)

        Keynames should be planned to be case insenstive.

        The following list shows defined keys.  Keys not in this list should
        NOT be used.  If a key is needed that is not in the list, it should
        be added to the list.  This will avoid key overlap.  Keys may be
        anywhere from 2 chars to 8 chars.  Shorter keys will allow for more
        possible data.

        Defined key list
           SrvCode      The yyy.xx Service code associated with an error.
           PJLCode      The PJL Code associated with an error.
           FixedID      The fixed ID of the alert
           Triplet      NPA triplet of the alert
           SerNum       The serial number of the item
           PartNum      The part number of the item
           Color        The color of the item.  Primarily for use with toner.
           Level        Percent of supply that is left.
           PapSize      The size of the paper referred to.  This should use the
                        pwg standard size names.
           PapType      The type of the paper referred to.  This should use the
                        pwg standard type names.
           TrayName     The name of the input tray referred to.
           BinNum       The number of the output bin referred to.
           PctComp      The percentage complete of the operation.
           Actions      Actions that can be performed for this IR,
                        Known Values: Reset, Continue, Cancel, Change Paper
                        If multiple items are there, comma delimit.
           BaseDesc     The description of the status associated with an error.
           EstPgRem     The Estimated pages remaining associated with an error.
                        Primarily for use with toner.
           CustMsg      Any optional message.
        Examples:
           If this string was being used to describe a 'Load Paper' event, the
           resulting string might look like
           'TrayName=Tray 1;PapSize=na_letter_8.5x11in;PapType=stationary;'

           A string for a toner low event might look like
           'Color=black;SerNum=12345678;Level=10%'"
    SYNTAX       OCTET STRING (SIZE (0..255))

END

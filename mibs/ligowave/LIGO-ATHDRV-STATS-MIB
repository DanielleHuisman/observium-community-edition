--
--  LigoWave Atheros Driver Statistics MIB
--

LIGO-ATHDRV-STATS-MIB DEFINITIONS ::= BEGIN
IMPORTS
    MODULE-IDENTITY, OBJECT-TYPE,
    Counter32, Integer32, Counter64, Gauge32
        FROM SNMPv2-SMI
    MacAddress
        FROM SNMPv2-TC
    ifIndex
        FROM IF-MIB
    ligoMgmt
        FROM LIGOWAVE-MIB;

ligoAthDrvStatsMIB MODULE-IDENTITY
    LAST-UPDATED    "200812120000Z"
    ORGANIZATION    "LigoWave"
    CONTACT-INFO    "
        LigoWave Customer Support
        E-mail: support@ligowave.com"
    DESCRIPTION
        "The Atheros Driver Statistics MIB by LigoWave."
    REVISION    "200812120000Z"
    DESCRIPTION
        "First revision."
    ::= { ligoMgmt 7 }

ligoAthDrvStatsMIBObjects  OBJECT IDENTIFIER ::= { ligoAthDrvStatsMIB 1 }

ligoAthStatsTable OBJECT-TYPE
    SYNTAX  SEQUENCE OF LigoAthStatsEntry
    MAX-ACCESS  not-accessible
    STATUS  current
    DESCRIPTION
        "Atheros driver's network traffic statistics table."
    ::= { ligoAthDrvStatsMIBObjects 1 }

ligoAthStatsEntry OBJECT-TYPE
    SYNTAX  LigoAthStatsEntry
    MAX-ACCESS  not-accessible
    STATUS  current
    DESCRIPTION
        "Atheros driver's network traffic statistics table entry."
    INDEX { ifIndex }
    ::= { ligoAthStatsTable 1 }

LigoAthStatsEntry ::=
    SEQUENCE {
        ligoAthWatchdogTimeouts             Counter32,
        ligoAthHardwareErrorInterrupts      Counter32,
        ligoAthBeaconMissInterrupts         Counter32,
        ligoAthRecvOverrunInterrupts        Counter32,
        ligoAthRecvEolInterrupts            Counter32,
        ligoAthTxmitUnderrunInterrupts      Counter32,
        ligoAthTxManagementFrames           Counter32,
        ligoAthTxFramesDiscQueueDepth       Counter32,
        ligoAthTxFramesDiscDeviceGone       Counter32,
        ligoAthTxQueueFull                  Counter32,
        ligoAthTxEncapsulationFailed        Counter32,
        ligoAthTxFailedNoNode               Counter32,
        ligoAthTxFailedNoDataTxBuffer       Counter32,
        ligoAthTxFailedNoMgtTxBuffer        Counter32,
        ligoAthTxFailedTooManyRetries       Counter32,
        ligoAthTxFailedFifoUnderrun         Counter32,
        ligoAthTxFailedXmitFiltered         Counter32,
        ligoAthShortOnchipTxRetries         Counter32,
        ligoAthLongOnchipTxRetries          Counter32,
        ligoAthTxFailedBogusXmitRate        Counter32,
        ligoAthTxFramesNoAckMarked          Counter32,
        ligoAthTxFramesRtsEnabled           Counter32,
        ligoAthTxFramesCtsEnabled           Counter32,
        ligoAthTxFramesShortPreamble        Counter32,
        ligoAthTxFramesAlternateRate        Counter32,
        ligoAthTxFrames11gProtection        Counter32,
        ligoAthRxFailedDescOverrun          Counter32,
        ligoAthRxFailedBadCrc               Counter32,
        ligoAthRxFailedFifoOverrun          Counter32,
        ligoAthRxFailedDecryptErrors        Counter32,
        ligoAthRxFailedMicFailure           Counter32,
        ligoAthRxFailedFrameTooShort        Counter32,
        ligoAthRxSetupFailedNoSkbuff        Counter32,
        ligoAthRxManagementFrames           Counter32,
        ligoAthRxControlFrames              Counter32,
        ligoAthNoSkbuffForBeacon            Counter32,
        ligoAthBeaconsTransmitted           Counter32,
        ligoAthPeriodicCalibrations         Counter32,
        ligoAthPeriodicCalibrFailures       Counter32,
        ligoAthRfgainValueChange            Counter32,
        ligoAthRateControlChecks            Counter32,
        ligoAthRateCtrlRaisedXmitRate       Counter32,
        ligoAthRateCtrlDroppedXmitRate      Counter32,
        ligoAthRssiOfLastAck                Gauge32,
        ligoAthRssiOfLastRcv                Gauge32
}

ligoAthWatchdogTimeouts OBJECT-TYPE
    SYNTAX      Counter32
    MAX-ACCESS  read-only
    STATUS      current
    DESCRIPTION
        "Watchdog timeouts."
    ::= { ligoAthStatsEntry 1 }

ligoAthHardwareErrorInterrupts OBJECT-TYPE
    SYNTAX      Counter32
    MAX-ACCESS  read-only
    STATUS      current
    DESCRIPTION
        "Hardware error interrupts."
    ::= { ligoAthStatsEntry 2 }

ligoAthBeaconMissInterrupts OBJECT-TYPE
    SYNTAX      Counter32
    MAX-ACCESS  read-only
    STATUS      current
    DESCRIPTION
        "Beacon miss interrupts."
    ::= { ligoAthStatsEntry 3 }
 
ligoAthRecvOverrunInterrupts OBJECT-TYPE
    SYNTAX      Counter32
    MAX-ACCESS  read-only
    STATUS      current
    DESCRIPTION
        "Received overrun interrupts."
    ::= { ligoAthStatsEntry 4 }

ligoAthRecvEolInterrupts OBJECT-TYPE
    SYNTAX      Counter32
    MAX-ACCESS  read-only
    STATUS      current
    DESCRIPTION
        "Received EOL interrupts."
    ::= { ligoAthStatsEntry 5 }

ligoAthTxmitUnderrunInterrupts OBJECT-TYPE
    SYNTAX      Counter32
    MAX-ACCESS  read-only
    STATUS      current
    DESCRIPTION
        "Transmission underrun interrupts."
    ::= { ligoAthStatsEntry 6 }

ligoAthTxManagementFrames OBJECT-TYPE
    SYNTAX      Counter32
    MAX-ACCESS  read-only
    STATUS      current
    DESCRIPTION
        "Transmitted management frames."
    ::= { ligoAthStatsEntry 7 }
 
ligoAthTxFramesDiscQueueDepth OBJECT-TYPE
    SYNTAX      Counter32
    MAX-ACCESS  read-only
    STATUS      current
    DESCRIPTION
        "Transmit frames discarded due to queue depth."
    ::= { ligoAthStatsEntry 8 }

ligoAthTxFramesDiscDeviceGone OBJECT-TYPE
    SYNTAX      Counter32
    MAX-ACCESS  read-only
    STATUS      current
    DESCRIPTION
        "Transmit frames discarded due to device gone."
    ::= { ligoAthStatsEntry 9 }

ligoAthTxQueueFull OBJECT-TYPE
    SYNTAX      Counter32
    MAX-ACCESS  read-only
    STATUS      current
    DESCRIPTION
        "Transmit queue stopped because it is full."
    ::= { ligoAthStatsEntry 10 }

ligoAthTxEncapsulationFailed OBJECT-TYPE
    SYNTAX      Counter32
    MAX-ACCESS  read-only
    STATUS      current
    DESCRIPTION
        "Transmit encapsulation failed."
    ::= { ligoAthStatsEntry 11 }
 
ligoAthTxFailedNoNode OBJECT-TYPE
    SYNTAX      Counter32
    MAX-ACCESS  read-only
    STATUS      current
    DESCRIPTION
        "Transmissions failed due to no node."
    ::= { ligoAthStatsEntry 12 }

ligoAthTxFailedNoDataTxBuffer OBJECT-TYPE
    SYNTAX      Counter32
    MAX-ACCESS  read-only
    STATUS      current
    DESCRIPTION
        "Transmissions failed due to no place in transmit buffer for data frames."
    ::= { ligoAthStatsEntry 13 }

ligoAthTxFailedNoMgtTxBuffer OBJECT-TYPE
    SYNTAX      Counter32
    MAX-ACCESS  read-only
    STATUS      current
    DESCRIPTION
        "Transmissions failed due to no place in transmit buffer for management frames."
    ::= { ligoAthStatsEntry 14 }

ligoAthTxFailedTooManyRetries OBJECT-TYPE
    SYNTAX      Counter32
    MAX-ACCESS  read-only
    STATUS      current
    DESCRIPTION
        "Transmissions failed due to too many retries."
    ::= { ligoAthStatsEntry 15 }

ligoAthTxFailedFifoUnderrun OBJECT-TYPE
    SYNTAX      Counter32
    MAX-ACCESS  read-only
    STATUS      current
    DESCRIPTION
        "Transmissions failed due to FIFO underruns."
    ::= { ligoAthStatsEntry 16 }

ligoAthTxFailedXmitFiltered OBJECT-TYPE
    SYNTAX      Counter32
    MAX-ACCESS  read-only
    STATUS      current
    DESCRIPTION
        "Transmissions failed due to filtered packets."
    ::= { ligoAthStatsEntry 17 }
 
ligoAthShortOnchipTxRetries OBJECT-TYPE
    SYNTAX      Counter32
    MAX-ACCESS  read-only
    STATUS      current
    DESCRIPTION
        "Short on-chip transmission retries."
    ::= { ligoAthStatsEntry 18 }

ligoAthLongOnchipTxRetries OBJECT-TYPE
    SYNTAX      Counter32
    MAX-ACCESS  read-only
    STATUS      current
    DESCRIPTION
        "Long on-chip transmission retries."
    ::= { ligoAthStatsEntry 19 }
 
ligoAthTxFailedBogusXmitRate OBJECT-TYPE
    SYNTAX      Counter32
    MAX-ACCESS  read-only
    STATUS      current
    DESCRIPTION
        "Transmissions failed due to bogus transmission rate."
    ::= { ligoAthStatsEntry 20 }
 
ligoAthTxFramesNoAckMarked OBJECT-TYPE
    SYNTAX      Counter32
    MAX-ACCESS  read-only
    STATUS      current
    DESCRIPTION
        "Transmitted frames with no ACK marked."
    ::= { ligoAthStatsEntry 21 }

ligoAthTxFramesRtsEnabled OBJECT-TYPE
    SYNTAX      Counter32
    MAX-ACCESS  read-only
    STATUS      current
    DESCRIPTION
        "Transmitted frames with RTS enabled."
    ::= { ligoAthStatsEntry 22 }
 
ligoAthTxFramesCtsEnabled OBJECT-TYPE
    SYNTAX      Counter32
    MAX-ACCESS  read-only
    STATUS      current
    DESCRIPTION
        "Transmitted frames with CTS enabled."
    ::= { ligoAthStatsEntry 23 }

ligoAthTxFramesShortPreamble OBJECT-TYPE
    SYNTAX      Counter32
    MAX-ACCESS  read-only
    STATUS      current
    DESCRIPTION
        "Transmitted frames with short preamble."
    ::= { ligoAthStatsEntry 24 }

ligoAthTxFramesAlternateRate OBJECT-TYPE
    SYNTAX      Counter32
    MAX-ACCESS  read-only
    STATUS      current
    DESCRIPTION
        "Transmitted frames with an alternate rate."
    ::= { ligoAthStatsEntry 25 }

ligoAthTxFrames11gProtection OBJECT-TYPE
    SYNTAX      Counter32
    MAX-ACCESS  read-only
    STATUS      current
    DESCRIPTION
        "Transmitted frames with 11g protection."
    ::= { ligoAthStatsEntry 26 }

ligoAthRxFailedDescOverrun OBJECT-TYPE
    SYNTAX      Counter32
    MAX-ACCESS  read-only
    STATUS      current
    DESCRIPTION
        "Receptions failed due to desc overrun."
    ::= { ligoAthStatsEntry 27 }
 
ligoAthRxFailedBadCrc OBJECT-TYPE
    SYNTAX      Counter32
    MAX-ACCESS  read-only
    STATUS      current
    DESCRIPTION
        "Receptions failed due to bad CRC."
    ::= { ligoAthStatsEntry 28 }

ligoAthRxFailedFifoOverrun OBJECT-TYPE
    SYNTAX      Counter32
    MAX-ACCESS  read-only
    STATUS      current
    DESCRIPTION
        "Receptions failed due to FIFO overrun."
    ::= { ligoAthStatsEntry 29 }

ligoAthRxFailedDecryptErrors OBJECT-TYPE
    SYNTAX      Counter32
    MAX-ACCESS  read-only
    STATUS      current
    DESCRIPTION
        "Receptions failed due to decryption errors."
    ::= { ligoAthStatsEntry 30 }

ligoAthRxFailedMicFailure OBJECT-TYPE
    SYNTAX      Counter32
    MAX-ACCESS  read-only
    STATUS      current
    DESCRIPTION
        "Receptions failed due to MIC failure."
    ::= { ligoAthStatsEntry 31 }

ligoAthRxFailedFrameTooShort OBJECT-TYPE
    SYNTAX      Counter32
    MAX-ACCESS  read-only
    STATUS      current
    DESCRIPTION
        "Receptions failed due to frame being too short."
    ::= { ligoAthStatsEntry 32 }

ligoAthRxSetupFailedNoSkbuff OBJECT-TYPE
    SYNTAX      Counter32
    MAX-ACCESS  read-only
    STATUS      current
    DESCRIPTION
        "Reception setup failed due to no space in skbuff buffer."
    ::= { ligoAthStatsEntry 33 }
 
ligoAthRxManagementFrames OBJECT-TYPE
    SYNTAX      Counter32
    MAX-ACCESS  read-only
    STATUS      current
    DESCRIPTION
        "Received management frames."
    ::= { ligoAthStatsEntry 34 }
 
ligoAthRxControlFrames OBJECT-TYPE
    SYNTAX      Counter32
    MAX-ACCESS  read-only
    STATUS      current
    DESCRIPTION
        "Received control frames."
    ::= { ligoAthStatsEntry 35 }
 
ligoAthNoSkbuffForBeacon OBJECT-TYPE
    SYNTAX      Counter32
    MAX-ACCESS  read-only
    STATUS      current
    DESCRIPTION
        "No skbuff buffer space available for beacon."
    ::= { ligoAthStatsEntry 36 }

ligoAthBeaconsTransmitted OBJECT-TYPE
    SYNTAX      Counter32
    MAX-ACCESS  read-only
    STATUS      current
    DESCRIPTION
        "Beacons transmitted."
    ::= { ligoAthStatsEntry 37 }

ligoAthPeriodicCalibrations OBJECT-TYPE
    SYNTAX      Counter32
    MAX-ACCESS  read-only
    STATUS      current
    DESCRIPTION
        "Periodic calibrations."
    ::= { ligoAthStatsEntry 38 }

ligoAthPeriodicCalibrFailures OBJECT-TYPE
    SYNTAX      Counter32
    MAX-ACCESS  read-only
    STATUS      current
    DESCRIPTION
        "Periodic calibration failures."
    ::= { ligoAthStatsEntry 39 }

ligoAthRfgainValueChange OBJECT-TYPE
    SYNTAX      Counter32
    MAX-ACCESS  read-only
    STATUS      current
    DESCRIPTION
        "RFgain value changes."
    ::= { ligoAthStatsEntry 40 }

ligoAthRateControlChecks OBJECT-TYPE
    SYNTAX      Counter32
    MAX-ACCESS  read-only
    STATUS      current
    DESCRIPTION
        "Rate control checks."
    ::= { ligoAthStatsEntry 41 }
 
ligoAthRateCtrlRaisedXmitRate OBJECT-TYPE
    SYNTAX      Counter32
    MAX-ACCESS  read-only
    STATUS      current
    DESCRIPTION
        "Rate control raised transmission rate."
    ::= { ligoAthStatsEntry 42 }

ligoAthRateCtrlDroppedXmitRate OBJECT-TYPE
    SYNTAX      Counter32
    MAX-ACCESS  read-only
    STATUS      current
    DESCRIPTION
        "Rate control dropped transmission rate."
    ::= { ligoAthStatsEntry 43 }
 
ligoAthRssiOfLastAck OBJECT-TYPE
    SYNTAX      Gauge32
    MAX-ACCESS  read-only
    STATUS      current
    DESCRIPTION
        "RSSI of last ACK."
    ::= { ligoAthStatsEntry 44 }

ligoAthRssiOfLastRcv OBJECT-TYPE
    SYNTAX      Gauge32
    MAX-ACCESS  read-only
    STATUS      current
    DESCRIPTION
        "RSSI of last reception."
    ::= { ligoAthStatsEntry 45 }

ligoAthPhyErrorsTable OBJECT-TYPE
    SYNTAX  SEQUENCE OF LigoAthPhyErrorsEntry
    MAX-ACCESS  not-accessible
    STATUS  current
    DESCRIPTION
        "PHY errrors table."
    ::= { ligoAthDrvStatsMIBObjects 2 }

ligoAthPhyErrorsEntry OBJECT-TYPE
    SYNTAX  LigoAthPhyErrorsEntry
    MAX-ACCESS  not-accessible
    STATUS  current
    DESCRIPTION
        "PHY errors table entry."
    INDEX { ifIndex }
    ::= { ligoAthPhyErrorsTable 1 }

LigoAthPhyErrorsEntry ::=
    SEQUENCE {
        ligoAthPhyTransmitUnderrun          Counter32,
        ligoAthPhyTimingError               Counter32,
        ligoAthPhyIllegalParity             Counter32,
        ligoAthPhyIllegalRate               Counter32,
        ligoAthPhyIllegalLength             Counter32,
        ligoAthPhyRadarDetect               Counter32,
        ligoAthPhyIllegalService            Counter32,
        ligoAthPhyTxmitOverrideRecv         Counter32,
        ligoAthPhyOfdmTiming                Counter32,
        ligoAthPhyOfdmIllegalParity         Counter32,
        ligoAthPhyOfdmIllegalRate           Counter32,
        ligoAthPhyOfdmIllegalLength         Counter32,
        ligoAthPhyOfdmPowerDrop             Counter32,
        ligoAthPhyOfdmIllegalService        Counter32,
        ligoAthPhyOfdmRestart               Counter32,
        ligoAthPhyCckTiming                 Counter32,
        ligoAthPhyCckHeaderCrc              Counter32,
        ligoAthPhyCckIllegalRate            Counter32,
        ligoAthPhyCckIllegalService         Counter32,
        ligoAthPhyCckRestart                Counter32
}

ligoAthPhyTransmitUnderrun OBJECT-TYPE
    SYNTAX      Counter32
    MAX-ACCESS  read-only
    STATUS      current
    DESCRIPTION
        "Transmit underrun errors."
    ::= { ligoAthPhyErrorsEntry 1 }

ligoAthPhyTimingError OBJECT-TYPE
    SYNTAX      Counter32
    MAX-ACCESS  read-only
    STATUS      current
    DESCRIPTION
        "Timing errors."
    ::= { ligoAthPhyErrorsEntry 2 }

ligoAthPhyIllegalParity OBJECT-TYPE
    SYNTAX      Counter32
    MAX-ACCESS  read-only
    STATUS      current
    DESCRIPTION
        "Illegal parity errors."
    ::= { ligoAthPhyErrorsEntry 3 }

ligoAthPhyIllegalRate OBJECT-TYPE
    SYNTAX      Counter32
    MAX-ACCESS  read-only
    STATUS      current
    DESCRIPTION
        "Illegal rate errors."
    ::= { ligoAthPhyErrorsEntry 4 }

ligoAthPhyIllegalLength OBJECT-TYPE
    SYNTAX      Counter32
    MAX-ACCESS  read-only
    STATUS      current
    DESCRIPTION
        "Illegal length errors."
    ::= { ligoAthPhyErrorsEntry 5 }

ligoAthPhyRadarDetect OBJECT-TYPE
    SYNTAX      Counter32
    MAX-ACCESS  read-only
    STATUS      current
    DESCRIPTION
        "Radar detected."
    ::= { ligoAthPhyErrorsEntry 6 }

ligoAthPhyIllegalService OBJECT-TYPE
    SYNTAX      Counter32
    MAX-ACCESS  read-only
    STATUS      current
    DESCRIPTION
        "Illegal service errors."
    ::= { ligoAthPhyErrorsEntry 7 }

ligoAthPhyTxmitOverrideRecv OBJECT-TYPE
    SYNTAX      Counter32
    MAX-ACCESS  read-only
    STATUS      current
    DESCRIPTION
        "Transmission overrode reception errors."
    ::= { ligoAthPhyErrorsEntry 8 }

ligoAthPhyOfdmTiming OBJECT-TYPE
    SYNTAX      Counter32
    MAX-ACCESS  read-only
    STATUS      current
    DESCRIPTION
        "OFDM timing errors."
    ::= { ligoAthPhyErrorsEntry 9 }

ligoAthPhyOfdmIllegalParity OBJECT-TYPE
    SYNTAX      Counter32
    MAX-ACCESS  read-only
    STATUS      current
    DESCRIPTION
        "OFDM illegal parity errors."
    ::= { ligoAthPhyErrorsEntry 10 }

ligoAthPhyOfdmIllegalRate OBJECT-TYPE
    SYNTAX      Counter32
    MAX-ACCESS  read-only
    STATUS      current
    DESCRIPTION
        "OFDM illegal rate errors."
    ::= { ligoAthPhyErrorsEntry 11 }

ligoAthPhyOfdmIllegalLength OBJECT-TYPE
    SYNTAX      Counter32
    MAX-ACCESS  read-only
    STATUS      current
    DESCRIPTION
        "OFDM illegal length errors."
    ::= { ligoAthPhyErrorsEntry 12 }

ligoAthPhyOfdmPowerDrop OBJECT-TYPE
    SYNTAX      Counter32
    MAX-ACCESS  read-only
    STATUS      current
    DESCRIPTION
        "OFDM power dropped."
    ::= { ligoAthPhyErrorsEntry 13 }

ligoAthPhyOfdmIllegalService OBJECT-TYPE
    SYNTAX      Counter32
    MAX-ACCESS  read-only
    STATUS      current
    DESCRIPTION
        "OFDM illegal service errors."
    ::= { ligoAthPhyErrorsEntry 14 }

ligoAthPhyOfdmRestart OBJECT-TYPE
    SYNTAX      Counter32
    MAX-ACCESS  read-only
    STATUS      current
    DESCRIPTION
        "Number of times OFDM restarted."
    ::= { ligoAthPhyErrorsEntry 15 }

ligoAthPhyCckTiming OBJECT-TYPE
    SYNTAX      Counter32
    MAX-ACCESS  read-only
    STATUS      current
    DESCRIPTION
        "CCK timing errors."
    ::= { ligoAthPhyErrorsEntry 16 }

ligoAthPhyCckHeaderCrc OBJECT-TYPE
    SYNTAX      Counter32
    MAX-ACCESS  read-only
    STATUS      current
    DESCRIPTION
        "CCK header CRC errors."
    ::= { ligoAthPhyErrorsEntry 17 }

ligoAthPhyCckIllegalRate OBJECT-TYPE
    SYNTAX      Counter32
    MAX-ACCESS  read-only
    STATUS      current
    DESCRIPTION
        "CCK illegal rate errors."
    ::= { ligoAthPhyErrorsEntry 18 }

ligoAthPhyCckIllegalService OBJECT-TYPE
    SYNTAX      Counter32
    MAX-ACCESS  read-only
    STATUS      current
    DESCRIPTION
        "CCK illegal service errors."
    ::= { ligoAthPhyErrorsEntry 19 }

ligoAthPhyCckRestart OBJECT-TYPE
    SYNTAX      Counter32
    MAX-ACCESS  read-only
    STATUS      current
    DESCRIPTION
        "Number of times CCK restarted."
    ::= { ligoAthPhyErrorsEntry 20 }

ligoAthAntennaStatsTable OBJECT-TYPE
    SYNTAX  SEQUENCE OF LigoAthAntennaStatsEntry
    MAX-ACCESS  not-accessible
    STATUS  current
    DESCRIPTION
        "Antenna statistics table."
    ::= { ligoAthDrvStatsMIBObjects 3 }

ligoAthAntennaStatsEntry OBJECT-TYPE
    SYNTAX  LigoAthAntennaStatsEntry
    MAX-ACCESS  not-accessible
    STATUS  current
    DESCRIPTION
        "Antenna statistics table entry."
    INDEX { ifIndex }
    ::= { ligoAthAntennaStatsTable 1 }

LigoAthAntennaStatsEntry ::=
    SEQUENCE {
        ligoAthSwitchedDefaultRxAntenna     Counter32,
        ligoAthTxUsedAlternateAntenna       Counter32,
        ligoAthTxFramesAntenna1             Counter32,
        ligoAthRxFramesAntenna1             Counter32,
        ligoAthTxFramesAntenna2             Counter32,
        ligoAthRxFramesAntenna2             Counter32,
        ligoAthTxFramesAntenna3             Counter32,
        ligoAthRxFramesAntenna3             Counter32
}

ligoAthSwitchedDefaultRxAntenna OBJECT-TYPE
    SYNTAX      Counter32
    MAX-ACCESS  read-only
    STATUS      current
    DESCRIPTION
        "Number of times default/RX antenna was switched."
    ::= { ligoAthAntennaStatsEntry 1 }
 
ligoAthTxUsedAlternateAntenna OBJECT-TYPE
    SYNTAX      Counter32
    MAX-ACCESS  read-only
    STATUS      current
    DESCRIPTION
        "Number of times alternate antenna was used for transmission."
    ::= { ligoAthAntennaStatsEntry 2 }

ligoAthTxFramesAntenna1 OBJECT-TYPE
    SYNTAX      Counter32
    MAX-ACCESS  read-only
    STATUS      current
    DESCRIPTION
        "Transmitted over first antenna."
    ::= { ligoAthAntennaStatsEntry 3 }

ligoAthRxFramesAntenna1 OBJECT-TYPE
    SYNTAX      Counter32
    MAX-ACCESS  read-only
    STATUS      current
    DESCRIPTION
        "Received over first antenna."
    ::= { ligoAthAntennaStatsEntry 4 }

ligoAthTxFramesAntenna2 OBJECT-TYPE
    SYNTAX      Counter32
    MAX-ACCESS  read-only
    STATUS      current
    DESCRIPTION
        "Transmitted over second antenna."
    ::= { ligoAthAntennaStatsEntry 5 }

ligoAthRxFramesAntenna2 OBJECT-TYPE
    SYNTAX      Counter32
    MAX-ACCESS  read-only
    STATUS      current
    DESCRIPTION
        "Received over second antenna."
    ::= { ligoAthAntennaStatsEntry 6 }

ligoAthTxFramesAntenna3 OBJECT-TYPE
    SYNTAX      Counter32
    MAX-ACCESS  read-only
    STATUS      current
    DESCRIPTION
        "Transmitted over third antenna."
    ::= { ligoAthAntennaStatsEntry 7 }

ligoAthRxFramesAntenna3 OBJECT-TYPE
    SYNTAX      Counter32
    MAX-ACCESS  read-only
    STATUS      current
    DESCRIPTION
        "Received over third antenna."
    ::= { ligoAthAntennaStatsEntry 8 }

ligoAthDot11StatsTable OBJECT-TYPE
    SYNTAX  SEQUENCE OF LigoAthDot11StatsEntry
    MAX-ACCESS  not-accessible
    STATUS  current
    DESCRIPTION
        "802.11 stack statistics table."
    ::= { ligoAthDrvStatsMIBObjects 4 }

ligoAthDot11StatsEntry OBJECT-TYPE
    SYNTAX  LigoAthDot11StatsEntry
    MAX-ACCESS  not-accessible
    STATUS  current
    DESCRIPTION
        "802.11 stack statistics table entry."
    INDEX { ifIndex }
    ::= { ligoAthDot11StatsTable 1 }

LigoAthDot11StatsEntry ::=
    SEQUENCE {
        ligoAthDot11RxBadVersion          Counter32,
        ligoAthDot11RxTooShort            Counter32,
        ligoAthDot11RxWrongBssid          Counter32,
        ligoAthDot11RxDup                 Counter32,
        ligoAthDot11RxWrongDirection      Counter32,
        ligoAthDot11RxMcastEcho           Counter32,
        ligoAthDot11RxNotAssoc            Counter32,
        ligoAthDot11RxNoPrivacy           Counter32,
        ligoAthDot11RxUnencrypted         Counter32,
        ligoAthDot11RxWepFail             Counter32,
        ligoAthDot11RxDecapFail           Counter32,
        ligoAthDot11RxDiscardMgt          Counter32,
        ligoAthDot11RxDiscardCtrl         Counter32,
        ligoAthDot11RxBeaconFrames        Counter32,
        ligoAthDot11RxRateSetTrunc        Counter32,
        ligoAthDot11RxReqElemMissing      Counter32,
        ligoAthDot11RxElementTooBig       Counter32,
        ligoAthDot11RxElementTooSmall     Counter32,
        ligoAthDot11RxElementUnknown      Counter32,
        ligoAthDot11RxInvalidChannel      Counter32,
        ligoAthDot11RxChannelMismatch     Counter32,
        ligoAthDot11RxNodesAllocated      Counter32,
        ligoAthDot11RxSsidMismatch        Counter32,
        ligoAthDot11RxUnsupportedAuthAlg  Counter32,
        ligoAthDot11RxAuthFail            Counter32,
        ligoAthDot11RxTkipCtrm            Counter32,
        ligoAthDot11RxAssocWrongBssid     Counter32,
        ligoAthDot11RxAssocNotAuth        Counter32,
        ligoAthDot11RxAssocCapMismatch    Counter32,
        ligoAthDot11RxAssocNoRateMatch    Counter32,
        ligoAthDot11RxAssocBadWpaIe       Counter32,
        ligoAthDot11RxDeauth              Counter32,
        ligoAthDot11RxDisassoc            Counter32,
        ligoAthDot11RxUnknownSubtype      Counter32,
        ligoAthDot11RxNoBuffer            Counter32,
        ligoAthDot11RxDecryptCrcError     Counter32,
        ligoAthDot11RxMgmtInAhdocDemo     Counter32,
        ligoAthDot11RxBadAuthRequest      Counter32,
        ligoAthDot11RxPortUnauth          Counter32,
        ligoAthDot11RxBadKeyId            Counter32,
        ligoAthDot11RxCcmpBadSeqNum       Counter32,
        ligoAthDot11RxCcmpBadFormat       Counter32,
        ligoAthDot11RxCcmpMicCheck        Counter32,
        ligoAthDot11RxTkipBadSeqNum       Counter32,
        ligoAthDot11RxTkipBadFormat       Counter32,
        ligoAthDot11RxTkipMicCheck        Counter32,
        ligoAthDot11RxTkipIcvCheck        Counter32,
        ligoAthDot11RxBadCipherKeyType    Counter32,
        ligoAthDot11RxCipherKeyNotSet     Counter32,
        ligoAthDot11RxAclPolicy           Counter32,
        ligoAthDot11RxFastFrames          Counter32,
        ligoAthDot11RxFfBadTunnelHdr      Counter32,
        ligoAthDot11TxNoBuffer            Counter32,
        ligoAthDot11TxNoNode              Counter32,
        ligoAthDot11TxBadMgtFrames        Counter32,
        ligoAthDot11TxBadCipherKeyType    Counter32,
        ligoAthDot11TxNoDefKey            Counter32,
        ligoAthDot11TxNoCryptoHeadroom    Counter32,
        ligoAthDot11TxGoodFastFrames      Counter32,
        ligoAthDot11TxBadFastFrames       Counter32,
        ligoAthDot11ActiveScans           Counter32,
        ligoAthDot11PassiveScans          Counter32,
        ligoAthDot11NodesTimeout          Counter32,
        ligoAthDot11CryptoCipherMalloc    Counter32,
        ligoAthDot11CryptoSwTkip          Counter32,
        ligoAthDot11CryptoTkipSwMicEnc    Counter32,
        ligoAthDot11CryptoTkipSwMicDec    Counter32,
        ligoAthDot11CryptoTkipCtrm        Counter32,
        ligoAthDot11CryptoSwCcmp          Counter32,
        ligoAthDot11CryptoSwWep           Counter32,
        ligoAthDot11CryptoCipherRej       Counter32,
        ligoAthDot11CryptoNoKey           Counter32,
        ligoAthDot11CryptoDelKey          Counter32,
        ligoAthDot11CryptoBadCipher       Counter32,
        ligoAthDot11CryptoNoCipher        Counter32,
        ligoAthDot11CryptoAttachFail      Counter32,
        ligoAthDot11CryptoSwFallback      Counter32,
        ligoAthDot11CryptoKeyFail         Counter32,
        ligoAthDot11SnoopMcastPass        Counter32,
        ligoAthDot11SnoopMcastDrop        Counter32
    }
    
ligoAthDot11RxBadVersion OBJECT-TYPE
    SYNTAX      Counter32
    MAX-ACCESS  read-only
    STATUS      current
    DESCRIPTION
        "Received frames with bad version."
    ::= { ligoAthDot11StatsEntry 1 }

ligoAthDot11RxTooShort OBJECT-TYPE
    SYNTAX      Counter32
    MAX-ACCESS  read-only
    STATUS      current
    DESCRIPTION
        "Received too short frames."
    ::= { ligoAthDot11StatsEntry 2 }

ligoAthDot11RxWrongBssid OBJECT-TYPE
    SYNTAX      Counter32
    MAX-ACCESS  read-only
    STATUS      current
    DESCRIPTION
        "Received from wrong BSSID."
    ::= { ligoAthDot11StatsEntry 3 }

ligoAthDot11RxDup OBJECT-TYPE
    SYNTAX      Counter32
    MAX-ACCESS  read-only
    STATUS      current
    DESCRIPTION
        "Received and discarded duplicate frames."
    ::= { ligoAthDot11StatsEntry 4 }

ligoAthDot11RxWrongDirection OBJECT-TYPE
    SYNTAX      Counter32
    MAX-ACCESS  read-only
    STATUS      current
    DESCRIPTION
        "Received with wrong direction."
    ::= { ligoAthDot11StatsEntry 5 }

ligoAthDot11RxMcastEcho OBJECT-TYPE
    SYNTAX      Counter32
    MAX-ACCESS  read-only
    STATUS      current
    DESCRIPTION
        "Received frames discarded due to multicast echo."
    ::= { ligoAthDot11StatsEntry 6 }

ligoAthDot11RxNotAssoc OBJECT-TYPE
    SYNTAX      Counter32
    MAX-ACCESS  read-only
    STATUS      current
    DESCRIPTION
        "Received frames discarded because station is not associated."
    ::= { ligoAthDot11StatsEntry 7 }

ligoAthDot11RxNoPrivacy OBJECT-TYPE
    SYNTAX      Counter32
    MAX-ACCESS  read-only
    STATUS      current
    DESCRIPTION
        "Received frames with WEP while privacy was off."
    ::= { ligoAthDot11StatsEntry 8 }

ligoAthDot11RxUnencrypted OBJECT-TYPE
    SYNTAX      Counter32
    MAX-ACCESS  read-only
    STATUS      current
    DESCRIPTION
        "Received unencrypted frames while privacy was on."
    ::= { ligoAthDot11StatsEntry 9 }

ligoAthDot11RxWepFail OBJECT-TYPE
    SYNTAX      Counter32
    MAX-ACCESS  read-only
    STATUS      current
    DESCRIPTION
        "Received frames that failed WEP processing."
    ::= { ligoAthDot11StatsEntry 10 }

ligoAthDot11RxDecapFail OBJECT-TYPE
    SYNTAX      Counter32
    MAX-ACCESS  read-only
    STATUS      current
    DESCRIPTION
        "Received frames that failed decapsulation."
    ::= { ligoAthDot11StatsEntry 11 }

ligoAthDot11RxDiscardMgt OBJECT-TYPE
    SYNTAX      Counter32
    MAX-ACCESS  read-only
    STATUS      current
    DESCRIPTION
        "Received and discarded management frames."
    ::= { ligoAthDot11StatsEntry 12 }

ligoAthDot11RxDiscardCtrl OBJECT-TYPE
    SYNTAX      Counter32
    MAX-ACCESS  read-only
    STATUS      current
    DESCRIPTION
        "Received and discarded control frames."
    ::= { ligoAthDot11StatsEntry 13 }

ligoAthDot11RxBeaconFrames OBJECT-TYPE
    SYNTAX      Counter32
    MAX-ACCESS  read-only
    STATUS      current
    DESCRIPTION
        "Received beacon frames."
    ::= { ligoAthDot11StatsEntry 14 }

ligoAthDot11RxRateSetTrunc OBJECT-TYPE
    SYNTAX      Counter32
    MAX-ACCESS  read-only
    STATUS      current
    DESCRIPTION
        "Received frames with rate set truncated."
    ::= { ligoAthDot11StatsEntry 15 }

ligoAthDot11RxReqElemMissing OBJECT-TYPE
    SYNTAX      Counter32
    MAX-ACCESS  read-only
    STATUS      current
    DESCRIPTION
        "Received frames with required element missing."
    ::= { ligoAthDot11StatsEntry 16 }

ligoAthDot11RxElementTooBig OBJECT-TYPE
    SYNTAX      Counter32
    MAX-ACCESS  read-only
    STATUS      current
    DESCRIPTION
        "Received frames with too big elements."
    ::= { ligoAthDot11StatsEntry 17 }

ligoAthDot11RxElementTooSmall OBJECT-TYPE
    SYNTAX      Counter32
    MAX-ACCESS  read-only
    STATUS      current
    DESCRIPTION
        "Received frames with too small elements."
    ::= { ligoAthDot11StatsEntry 18 }

ligoAthDot11RxElementUnknown OBJECT-TYPE
    SYNTAX      Counter32
    MAX-ACCESS  read-only
    STATUS      current
    DESCRIPTION
        "Received frames with unknown elements."
    ::= { ligoAthDot11StatsEntry 19 }

ligoAthDot11RxInvalidChannel OBJECT-TYPE
    SYNTAX      Counter32
    MAX-ACCESS  read-only
    STATUS      current
    DESCRIPTION
        "Recevied frames with invalid channel."
    ::= { ligoAthDot11StatsEntry 20 }

ligoAthDot11RxChannelMismatch OBJECT-TYPE
    SYNTAX      Counter32
    MAX-ACCESS  read-only
    STATUS      current
    DESCRIPTION
        "Received frames with channel mismatch."
    ::= { ligoAthDot11StatsEntry 21 }

ligoAthDot11RxNodesAllocated OBJECT-TYPE
    SYNTAX      Counter32
    MAX-ACCESS  read-only
    STATUS      current
    DESCRIPTION
        "Nodes allocated for received frames."
    ::= { ligoAthDot11StatsEntry 22 }

ligoAthDot11RxSsidMismatch OBJECT-TYPE
    SYNTAX      Counter32
    MAX-ACCESS  read-only
    STATUS      current
    DESCRIPTION
        "Received frame SSID mismatches."
    ::= { ligoAthDot11StatsEntry 23 }

ligoAthDot11RxUnsupportedAuthAlg OBJECT-TYPE
    SYNTAX      Counter32
    MAX-ACCESS  read-only
    STATUS      current
    DESCRIPTION
        "Received frames with unsupported authentication algorithm."
    ::= { ligoAthDot11StatsEntry 24 }

ligoAthDot11RxAuthFail OBJECT-TYPE
    SYNTAX      Counter32
    MAX-ACCESS  read-only
    STATUS      current
    DESCRIPTION
        "Station authentication failures."
    ::= { ligoAthDot11StatsEntry 25 }

ligoAthDot11RxTkipCtrm OBJECT-TYPE
    SYNTAX      Counter32
    MAX-ACCESS  read-only
    STATUS      current
    DESCRIPTION
        "Station authentication failures due to TKIP countermeasures."
    ::= { ligoAthDot11StatsEntry 26 }

ligoAthDot11RxAssocWrongBssid OBJECT-TYPE
    SYNTAX      Counter32
    MAX-ACCESS  read-only
    STATUS      current
    DESCRIPTION
        "Associations from wrong BSSID."
    ::= { ligoAthDot11StatsEntry 27 }

ligoAthDot11RxAssocNotAuth OBJECT-TYPE
    SYNTAX      Counter32
    MAX-ACCESS  read-only
    STATUS      current
    DESCRIPTION
        "Associations without authentication."
    ::= { ligoAthDot11StatsEntry 28 }

ligoAthDot11RxAssocCapMismatch OBJECT-TYPE
    SYNTAX      Counter32
    MAX-ACCESS  read-only
    STATUS      current
    DESCRIPTION
        "Associations with capabilities mismatch."
    ::= { ligoAthDot11StatsEntry 29 }

ligoAthDot11RxAssocNoRateMatch OBJECT-TYPE
    SYNTAX      Counter32
    MAX-ACCESS  read-only
    STATUS      current
    DESCRIPTION
        "Associations with no matching rate."
    ::= { ligoAthDot11StatsEntry 30 }

ligoAthDot11RxAssocBadWpaIe OBJECT-TYPE
    SYNTAX      Counter32
    MAX-ACCESS  read-only
    STATUS      current
    DESCRIPTION
        "Associations with bad WPA IE."
    ::= { ligoAthDot11StatsEntry 31 }

ligoAthDot11RxDeauth OBJECT-TYPE
    SYNTAX      Counter32
    MAX-ACCESS  read-only
    STATUS      current
    DESCRIPTION
        "Deauthentications."
    ::= { ligoAthDot11StatsEntry 32 }

ligoAthDot11RxDisassoc OBJECT-TYPE
    SYNTAX      Counter32
    MAX-ACCESS  read-only
    STATUS      current
    DESCRIPTION
        "Disassociations."
    ::= { ligoAthDot11StatsEntry 33 }

ligoAthDot11RxUnknownSubtype OBJECT-TYPE
    SYNTAX      Counter32
    MAX-ACCESS  read-only
    STATUS      current
    DESCRIPTION
        "Received frames with unknown subtype."
    ::= { ligoAthDot11StatsEntry 34 }

ligoAthDot11RxNoBuffer OBJECT-TYPE
    SYNTAX      Counter32
    MAX-ACCESS  read-only
    STATUS      current
    DESCRIPTION
        "Buffer allocations failed for received frames."
    ::= { ligoAthDot11StatsEntry 35 }

ligoAthDot11RxDecryptCrcError OBJECT-TYPE
    SYNTAX      Counter32
    MAX-ACCESS  read-only
    STATUS      current
    DESCRIPTION
        "Decryptions failed with CRC error."
    ::= { ligoAthDot11StatsEntry 36 }

ligoAthDot11RxMgmtInAhdocDemo OBJECT-TYPE
    SYNTAX      Counter32
    MAX-ACCESS  read-only
    STATUS      current
    DESCRIPTION
        "Discarded management frames received in ahdoc demo mode."
    ::= { ligoAthDot11StatsEntry 37 }

ligoAthDot11RxBadAuthRequest OBJECT-TYPE
    SYNTAX      Counter32
    MAX-ACCESS  read-only
    STATUS      current
    DESCRIPTION
        "Bad authentication requests."
    ::= { ligoAthDot11StatsEntry 38 }

ligoAthDot11RxPortUnauth OBJECT-TYPE
    SYNTAX      Counter32
    MAX-ACCESS  read-only
    STATUS      current
    DESCRIPTION
        "Received frames discarded due to unauthorized port."
    ::= { ligoAthDot11StatsEntry 39 }

ligoAthDot11RxBadKeyId OBJECT-TYPE
    SYNTAX      Counter32
    MAX-ACCESS  read-only
    STATUS      current
    DESCRIPTION
        "Received frames with incorrect keyid."
    ::= { ligoAthDot11StatsEntry 40 }

ligoAthDot11RxCcmpBadSeqNum OBJECT-TYPE
    SYNTAX      Counter32
    MAX-ACCESS  read-only
    STATUS      current
    DESCRIPTION
        "CCMP sequence number violations."
    ::= { ligoAthDot11StatsEntry 41 }

ligoAthDot11RxCcmpBadFormat OBJECT-TYPE
    SYNTAX      Counter32
    MAX-ACCESS  read-only
    STATUS      current
    DESCRIPTION
        "Bad format CCMP frames."
    ::= { ligoAthDot11StatsEntry 42 }

ligoAthDot11RxCcmpMicCheck OBJECT-TYPE
    SYNTAX      Counter32
    MAX-ACCESS  read-only
    STATUS      current
    DESCRIPTION
        "CCMP MIC check failures."
    ::= { ligoAthDot11StatsEntry 43 }

ligoAthDot11RxTkipBadSeqNum OBJECT-TYPE
    SYNTAX      Counter32
    MAX-ACCESS  read-only
    STATUS      current
    DESCRIPTION
        "TKIP sequence number violations."
    ::= { ligoAthDot11StatsEntry 44 }

ligoAthDot11RxTkipBadFormat OBJECT-TYPE
    SYNTAX      Counter32
    MAX-ACCESS  read-only
    STATUS      current
    DESCRIPTION
        "Bad format TKIP frames."
    ::= { ligoAthDot11StatsEntry 45 }

ligoAthDot11RxTkipMicCheck OBJECT-TYPE
    SYNTAX      Counter32
    MAX-ACCESS  read-only
    STATUS      current
    DESCRIPTION
        "TKIP MIC check failures."
    ::= { ligoAthDot11StatsEntry 46 }

ligoAthDot11RxTkipIcvCheck OBJECT-TYPE
    SYNTAX      Counter32
    MAX-ACCESS  read-only
    STATUS      current
    DESCRIPTION
        "TKIP ICV check failures."
    ::= { ligoAthDot11StatsEntry 47 }

ligoAthDot11RxBadCipherKeyType OBJECT-TYPE
    SYNTAX      Counter32
    MAX-ACCESS  read-only
    STATUS      current
    DESCRIPTION
        "Receptions failed due to bad cipher/key type."
    ::= { ligoAthDot11StatsEntry 48 }

ligoAthDot11RxCipherKeyNotSet OBJECT-TYPE
    SYNTAX      Counter32
    MAX-ACCESS  read-only
    STATUS      current
    DESCRIPTION
        "Receptions failed due to cipher/key not setup."
    ::= { ligoAthDot11StatsEntry 49 }

ligoAthDot11RxAclPolicy OBJECT-TYPE
    SYNTAX      Counter32
    MAX-ACCESS  read-only
    STATUS      current
    DESCRIPTION
        "Received frames discarded due to ACL policy."
    ::= { ligoAthDot11StatsEntry 50 }

ligoAthDot11RxFastFrames OBJECT-TYPE
    SYNTAX      Counter32
    MAX-ACCESS  read-only
    STATUS      current
    DESCRIPTION
        "Received fast frames."
    ::= { ligoAthDot11StatsEntry 51 }

ligoAthDot11RxFfBadTunnelHdr OBJECT-TYPE
    SYNTAX      Counter32
    MAX-ACCESS  read-only
    STATUS      current
    DESCRIPTION
        "Fast frames failed due to bad tunnel header."
    ::= { ligoAthDot11StatsEntry 52 }

ligoAthDot11TxNoBuffer OBJECT-TYPE
    SYNTAX      Counter32
    MAX-ACCESS  read-only
    STATUS      current
    DESCRIPTION
        "Buffer allocations failed for transmitted frames."
    ::= { ligoAthDot11StatsEntry 53 }

ligoAthDot11TxNoNode OBJECT-TYPE
    SYNTAX      Counter32
    MAX-ACCESS  read-only
    STATUS      current
    DESCRIPTION
        "Transmissions failed for no node."
    ::= { ligoAthDot11StatsEntry 54 }

ligoAthDot11TxBadMgtFrames OBJECT-TYPE
    SYNTAX      Counter32
    MAX-ACCESS  read-only
    STATUS      current
    DESCRIPTION
        "Attempted transmissions of unknown management frame."
    ::= { ligoAthDot11StatsEntry 55 }

ligoAthDot11TxBadCipherKeyType OBJECT-TYPE
    SYNTAX      Counter32
    MAX-ACCESS  read-only
    STATUS      current
    DESCRIPTION
        "Transmissions failed due to bad cipher/key type."
    ::= { ligoAthDot11StatsEntry 56 }

ligoAthDot11TxNoDefKey OBJECT-TYPE
    SYNTAX      Counter32
    MAX-ACCESS  read-only
    STATUS      current
    DESCRIPTION
        "Transmissions failed due to no default key."
    ::= { ligoAthDot11StatsEntry 57 }

ligoAthDot11TxNoCryptoHeadroom OBJECT-TYPE
    SYNTAX      Counter32
    MAX-ACCESS  read-only
    STATUS      current
    DESCRIPTION
        "Transmissions failed due to no space for crypto headers."
    ::= { ligoAthDot11StatsEntry 58 }

ligoAthDot11TxGoodFastFrames OBJECT-TYPE
    SYNTAX      Counter32
    MAX-ACCESS  read-only
    STATUS      current
    DESCRIPTION
        "Successful fast frames transmissions."
    ::= { ligoAthDot11StatsEntry 59 }

ligoAthDot11TxBadFastFrames OBJECT-TYPE
    SYNTAX      Counter32
    MAX-ACCESS  read-only
    STATUS      current
    DESCRIPTION
        "Failed fast frames transmissions."
    ::= { ligoAthDot11StatsEntry 60 }

ligoAthDot11ActiveScans OBJECT-TYPE
    SYNTAX      Counter32
    MAX-ACCESS  read-only
    STATUS      current
    DESCRIPTION
        "Active scans started."
    ::= { ligoAthDot11StatsEntry 61 }

ligoAthDot11PassiveScans OBJECT-TYPE
    SYNTAX      Counter32
    MAX-ACCESS  read-only
    STATUS      current
    DESCRIPTION
        "Passive scans started."
    ::= { ligoAthDot11StatsEntry 62 }

ligoAthDot11NodesTimeout OBJECT-TYPE
    SYNTAX      Counter32
    MAX-ACCESS  read-only
    STATUS      current
    DESCRIPTION
        "Nodes timed out due to inactivity."
    ::= { ligoAthDot11StatsEntry 63 }

ligoAthDot11CryptoCipherMalloc OBJECT-TYPE
    SYNTAX      Counter32
    MAX-ACCESS  read-only
    STATUS      current
    DESCRIPTION
        "Failed memory allocations for cipher context."
    ::= { ligoAthDot11StatsEntry 64 }

ligoAthDot11CryptoSwTkip OBJECT-TYPE
    SYNTAX      Counter32
    MAX-ACCESS  read-only
    STATUS      current
    DESCRIPTION
        "TKIP encryptions done in software."
    ::= { ligoAthDot11StatsEntry 65 }

ligoAthDot11CryptoTkipSwMicEnc OBJECT-TYPE
    SYNTAX      Counter32
    MAX-ACCESS  read-only
    STATUS      current
    DESCRIPTION
        "TKIP MIC encryptions done in software."
    ::= { ligoAthDot11StatsEntry 66 }

ligoAthDot11CryptoTkipSwMicDec OBJECT-TYPE
    SYNTAX      Counter32
    MAX-ACCESS  read-only
    STATUS      current
    DESCRIPTION
        "TKIP MIC decryptions done in software."
    ::= { ligoAthDot11StatsEntry 67 }

ligoAthDot11CryptoTkipCtrm OBJECT-TYPE
    SYNTAX      Counter32
    MAX-ACCESS  read-only
    STATUS      current
    DESCRIPTION
        "TKIP frames dropped due to countermeasures."
    ::= { ligoAthDot11StatsEntry 68 }

ligoAthDot11CryptoSwCcmp OBJECT-TYPE
    SYNTAX      Counter32
    MAX-ACCESS  read-only
    STATUS      current
    DESCRIPTION
        "CCMP encryptions done in software."
    ::= { ligoAthDot11StatsEntry 69 }

ligoAthDot11CryptoSwWep OBJECT-TYPE
    SYNTAX      Counter32
    MAX-ACCESS  read-only
    STATUS      current
    DESCRIPTION
        "WEP encryptions done in software."
    ::= { ligoAthDot11StatsEntry 70 }

ligoAthDot11CryptoCipherRej OBJECT-TYPE
    SYNTAX      Counter32
    MAX-ACCESS  read-only
    STATUS      current
    DESCRIPTION
        "Crypto failures due to cipher rejected data."
    ::= { ligoAthDot11StatsEntry 71 }

ligoAthDot11CryptoNoKey OBJECT-TYPE
    SYNTAX      Counter32
    MAX-ACCESS  read-only
    STATUS      current
    DESCRIPTION
        "Crypto failures due to no key index."
    ::= { ligoAthDot11StatsEntry 72 }

ligoAthDot11CryptoDelKey OBJECT-TYPE
    SYNTAX      Counter32
    MAX-ACCESS  read-only
    STATUS      current
    DESCRIPTION
        "Failed driver key deletions."
    ::= { ligoAthDot11StatsEntry 73 }

ligoAthDot11CryptoBadCipher OBJECT-TYPE
    SYNTAX      Counter32
    MAX-ACCESS  read-only
    STATUS      current
    DESCRIPTION
        "Crypto failures due to unknown cipher."
    ::= { ligoAthDot11StatsEntry 74 }

ligoAthDot11CryptoNoCipher OBJECT-TYPE
    SYNTAX      Counter32
    MAX-ACCESS  read-only
    STATUS      current
    DESCRIPTION
        "Crypto failures due to unavailable cipher module."
    ::= { ligoAthDot11StatsEntry 75 }

ligoAthDot11CryptoAttachFail OBJECT-TYPE
    SYNTAX      Counter32
    MAX-ACCESS  read-only
    STATUS      current
    DESCRIPTION
        "Crypto failures due to cipher attach failure."
    ::= { ligoAthDot11StatsEntry 76 }

ligoAthDot11CryptoSwFallback OBJECT-TYPE
    SYNTAX      Counter32
    MAX-ACCESS  read-only
    STATUS      current
    DESCRIPTION
        "Crypto fallbacks to software implementation."
    ::= { ligoAthDot11StatsEntry 77 }

ligoAthDot11CryptoKeyFail OBJECT-TYPE
    SYNTAX      Counter32
    MAX-ACCESS  read-only
    STATUS      current
    DESCRIPTION
        "Crypto failures due to driver key allocation failure."
    ::= { ligoAthDot11StatsEntry 78 }

ligoAthDot11SnoopMcastPass OBJECT-TYPE
    SYNTAX      Counter32
    MAX-ACCESS  read-only
    STATUS      current
    DESCRIPTION
        "Multicast packets passed by snooping filter."
    ::= { ligoAthDot11StatsEntry 79 }

ligoAthDot11SnoopMcastDrop OBJECT-TYPE
    SYNTAX      Counter32
    MAX-ACCESS  read-only
    STATUS      current
    DESCRIPTION
        "Multicast packets dropped by snooping filter."
    ::= { ligoAthDot11StatsEntry 80 }

ligoAthPeerStatsTable OBJECT-TYPE
    SYNTAX  SEQUENCE OF LigoAthPeerStatsEntry
    MAX-ACCESS  not-accessible
    STATUS  current
    DESCRIPTION
        "Peer statistics table."
    ::= { ligoAthDrvStatsMIBObjects 5 }

ligoAthPeerStatsEntry OBJECT-TYPE
    SYNTAX  LigoAthPeerStatsEntry
    MAX-ACCESS  not-accessible
    STATUS  current
    DESCRIPTION
        "Peer statistics table entry."
    INDEX { ifIndex, ligoAthPeerIndex }
    ::= { ligoAthPeerStatsTable 1 }

LigoAthPeerStatsEntry ::=
    SEQUENCE {
        ligoAthPeerIndex             Integer32,
        ligoAthPeerMacAddr           MacAddress,
        ligoAthPeerRxData            Counter32,
        ligoAthPeerRxMgmt            Counter32,
        ligoAthPeerRxCtrl            Counter32,
        ligoAthPeerRxBeacons         Counter64,
        ligoAthPeerRxProbeResponse   Counter32,
        ligoAthPeerRxUcast           Counter32,
        ligoAthPeerRxMcast           Counter32,
        ligoAthPeerRxBytes           Counter64,
        ligoAthPeerRxDup             Counter32,
        ligoAthPeerRxNoPrivacy       Counter32,
        ligoAthPeerRxWepFail         Counter32,
        ligoAthPeerRxDemicFail       Counter32,
        ligoAthPeerRxDecapFail       Counter32,
        ligoAthPeerRxDefragFail      Counter32,
        ligoAthPeerRxDissasoc        Counter32,
        ligoAthPeerRxDeauth          Counter32,
        ligoAthPeerRxDecryptCrc      Counter32,
        ligoAthPeerRxUnauth          Counter32,
        ligoAthPeerRxUnencrypted     Counter32,
        ligoAthPeerTxData            Counter32,
        ligoAthPeerTxMgmt            Counter32,
        ligoAthPeerTxProbeReq        Counter32,
        ligoAthPeerTxUcast           Counter32,
        ligoAthPeerTxMcast           Counter32,
        ligoAthPeerTxBytes           Counter64,
        ligoAthPeerTxNoVlanTag       Counter32,
        ligoAthPeerTxVlanMismatch    Counter32,
        ligoAthPeerTxUapsd           Counter32,
        ligoAthPeerUapsdTriggers     Counter32,
        ligoAthPeerTxEospLost        Counter32,
        ligoAthPeerTxAssoc           Counter32,
        ligoAthPeerTxAssocFail       Counter32,
        ligoAthPeerTxAuth            Counter32,
        ligoAthPeerTxAuthFail        Counter32,
        ligoAthPeerTxDeauth          Counter32,
        ligoAthPeerTxDeauthCode      Counter32,
        ligoAthPeerTxDisassoc        Counter32,
        ligoAthPeerTxDisassocCode    Counter32,
        ligoAthPeerPsqDrops          Counter32,
        ligoAthPeerMcastSnoop        Counter32
    }

ligoAthPeerIndex OBJECT-TYPE
    SYNTAX      Integer32
    MAX-ACCESS  not-accessible
    STATUS      current
    DESCRIPTION
        "Peer index, indexed from 1."
    ::= { ligoAthPeerStatsEntry 1 }

ligoAthPeerMacAddr OBJECT-TYPE
    SYNTAX      MacAddress
    MAX-ACCESS  read-only
    STATUS      current
    DESCRIPTION
        "Peer MAC address."
    ::= { ligoAthPeerStatsEntry 2 }

ligoAthPeerRxData OBJECT-TYPE
    SYNTAX      Counter32
    MAX-ACCESS  read-only
    STATUS      current
    DESCRIPTION
        "Received data frames."
    ::= { ligoAthPeerStatsEntry 3 }

ligoAthPeerRxMgmt OBJECT-TYPE
    SYNTAX      Counter32
    MAX-ACCESS  read-only
    STATUS      current
    DESCRIPTION
        "Received management frames."
    ::= { ligoAthPeerStatsEntry 4 }

ligoAthPeerRxCtrl OBJECT-TYPE
    SYNTAX      Counter32
    MAX-ACCESS  read-only
    STATUS      current
    DESCRIPTION
        "Received control frames."
    ::= { ligoAthPeerStatsEntry 5 }

ligoAthPeerRxBeacons OBJECT-TYPE
    SYNTAX      Counter64
    MAX-ACCESS  read-only
    STATUS      current
    DESCRIPTION
        "Received beacon frames."
    ::= { ligoAthPeerStatsEntry 6 }

ligoAthPeerRxProbeResponse OBJECT-TYPE
    SYNTAX      Counter32
    MAX-ACCESS  read-only
    STATUS      current
    DESCRIPTION
        "Received probe response frames."
    ::= { ligoAthPeerStatsEntry 7 }

ligoAthPeerRxUcast OBJECT-TYPE
    SYNTAX      Counter32
    MAX-ACCESS  read-only
    STATUS      current
    DESCRIPTION
        "Received unicast frames."
    ::= { ligoAthPeerStatsEntry 8 }

ligoAthPeerRxMcast OBJECT-TYPE
    SYNTAX      Counter32
    MAX-ACCESS  read-only
    STATUS      current
    DESCRIPTION
        "Received multicast/broadcast frames."
    ::= { ligoAthPeerStatsEntry 9 }

ligoAthPeerRxBytes OBJECT-TYPE
    SYNTAX      Counter64
    MAX-ACCESS  read-only
    STATUS      current
    DESCRIPTION
        "Received bytes."
    ::= { ligoAthPeerStatsEntry 10 }

ligoAthPeerRxDup OBJECT-TYPE
    SYNTAX      Counter32
    MAX-ACCESS  read-only
    STATUS      current
    DESCRIPTION
        "Received and discarded duplicate frames."
    ::= { ligoAthPeerStatsEntry 11 }

ligoAthPeerRxNoPrivacy OBJECT-TYPE
    SYNTAX      Counter32
    MAX-ACCESS  read-only
    STATUS      current
    DESCRIPTION
        "Received frames with WEP while privacy was off."
    ::= { ligoAthPeerStatsEntry 12 }

ligoAthPeerRxWepFail OBJECT-TYPE
    SYNTAX      Counter32
    MAX-ACCESS  read-only
    STATUS      current
    DESCRIPTION
        "Received frames that failed WEP processing."
    ::= { ligoAthPeerStatsEntry 13 }

ligoAthPeerRxDemicFail OBJECT-TYPE
    SYNTAX      Counter32
    MAX-ACCESS  read-only
    STATUS      current
    DESCRIPTION
        "MIC decoding failures."
    ::= { ligoAthPeerStatsEntry 14 }

ligoAthPeerRxDecapFail OBJECT-TYPE
    SYNTAX      Counter32
    MAX-ACCESS  read-only
    STATUS      current
    DESCRIPTION
        "Decapsulation failures."
    ::= { ligoAthPeerStatsEntry 15 }

ligoAthPeerRxDefragFail OBJECT-TYPE
    SYNTAX      Counter32
    MAX-ACCESS  read-only
    STATUS      current
    DESCRIPTION
        "Defragmentation failures."
    ::= { ligoAthPeerStatsEntry 16 }

ligoAthPeerRxDissasoc OBJECT-TYPE
    SYNTAX      Counter32
    MAX-ACCESS  read-only
    STATUS      current
    DESCRIPTION
        "Disassociations."
    ::= { ligoAthPeerStatsEntry 17 }

ligoAthPeerRxDeauth OBJECT-TYPE
    SYNTAX      Counter32
    MAX-ACCESS  read-only
    STATUS      current
    DESCRIPTION
        "Deauthentications."
    ::= { ligoAthPeerStatsEntry 18 }

ligoAthPeerRxDecryptCrc OBJECT-TYPE
    SYNTAX      Counter32
    MAX-ACCESS  read-only
    STATUS      current
    DESCRIPTION
        "Decryptions failed with CRC error."
    ::= { ligoAthPeerStatsEntry 19 }

ligoAthPeerRxUnauth OBJECT-TYPE
    SYNTAX      Counter32
    MAX-ACCESS  read-only
    STATUS      current
    DESCRIPTION
        "Received frames discarded due to unauthorized port."
    ::= { ligoAthPeerStatsEntry 20 }

ligoAthPeerRxUnencrypted OBJECT-TYPE
    SYNTAX      Counter32
    MAX-ACCESS  read-only
    STATUS      current
    DESCRIPTION
        "Received unencrypted frames while privacy was on."
    ::= { ligoAthPeerStatsEntry 21 }

ligoAthPeerTxData OBJECT-TYPE
    SYNTAX      Counter32
    MAX-ACCESS  read-only
    STATUS      current
    DESCRIPTION
        "Transmitted data frames."
    ::= { ligoAthPeerStatsEntry 22 }

ligoAthPeerTxMgmt OBJECT-TYPE
    SYNTAX      Counter32
    MAX-ACCESS  read-only
    STATUS      current
    DESCRIPTION
        "Tranmitted management frames."
    ::= { ligoAthPeerStatsEntry 23 }

ligoAthPeerTxProbeReq OBJECT-TYPE
    SYNTAX      Counter32
    MAX-ACCESS  read-only
    STATUS      current
    DESCRIPTION
        "Transmitted probe requests."
    ::= { ligoAthPeerStatsEntry 24 }

ligoAthPeerTxUcast OBJECT-TYPE
    SYNTAX      Counter32
    MAX-ACCESS  read-only
    STATUS      current
    DESCRIPTION
        "Transmitted unicast frames."
    ::= { ligoAthPeerStatsEntry 25 }

ligoAthPeerTxMcast OBJECT-TYPE
    SYNTAX      Counter32
    MAX-ACCESS  read-only
    STATUS      current
    DESCRIPTION
        "Transmitted multicast/broadcast frames."
    ::= { ligoAthPeerStatsEntry 26 }

ligoAthPeerTxBytes OBJECT-TYPE
    SYNTAX      Counter64
    MAX-ACCESS  read-only
    STATUS      current
    DESCRIPTION
        "Transmitted bytes."
    ::= { ligoAthPeerStatsEntry 27 }

ligoAthPeerTxNoVlanTag OBJECT-TYPE
    SYNTAX      Counter32
    MAX-ACCESS  read-only
    STATUS      current
    DESCRIPTION
        "Frames discarded due to no tag."
    ::= { ligoAthPeerStatsEntry 28 }

ligoAthPeerTxVlanMismatch OBJECT-TYPE
    SYNTAX      Counter32
    MAX-ACCESS  read-only
    STATUS      current
    DESCRIPTION
        "Frames discarded due to bad tag."
    ::= { ligoAthPeerStatsEntry 29 }

ligoAthPeerTxUapsd OBJECT-TYPE
    SYNTAX      Counter32
    MAX-ACCESS  read-only
    STATUS      current
    DESCRIPTION
        "Frames in UAPSD queue."
    ::= { ligoAthPeerStatsEntry 30 }

ligoAthPeerUapsdTriggers OBJECT-TYPE
    SYNTAX      Counter32
    MAX-ACCESS  read-only
    STATUS      current
    DESCRIPTION
        "Number of UAPSD triggers."
    ::= { ligoAthPeerStatsEntry 31 }

ligoAthPeerTxEospLost OBJECT-TYPE
    SYNTAX      Counter32
    MAX-ACCESS  read-only
    STATUS      current
    DESCRIPTION
        "Retried frames with UAPSD EOSP set."
    ::= { ligoAthPeerStatsEntry 32 }

ligoAthPeerTxAssoc OBJECT-TYPE
    SYNTAX      Counter32
    MAX-ACCESS  read-only
    STATUS      current
    DESCRIPTION
        "Associations/reassociations."
    ::= { ligoAthPeerStatsEntry 33 }

ligoAthPeerTxAssocFail OBJECT-TYPE
    SYNTAX      Counter32
    MAX-ACCESS  read-only
    STATUS      current
    DESCRIPTION
        "Association/reassociation failures."
    ::= { ligoAthPeerStatsEntry 34 }

ligoAthPeerTxAuth OBJECT-TYPE
    SYNTAX      Counter32
    MAX-ACCESS  read-only
    STATUS      current
    DESCRIPTION
        "Authentications/reauthentications."
    ::= { ligoAthPeerStatsEntry 35 }

ligoAthPeerTxAuthFail OBJECT-TYPE
    SYNTAX      Counter32
    MAX-ACCESS  read-only
    STATUS      current
    DESCRIPTION
        "Authentication/reauthentication failures."
    ::= { ligoAthPeerStatsEntry 36 }

ligoAthPeerTxDeauth OBJECT-TYPE
    SYNTAX      Counter32
    MAX-ACCESS  read-only
    STATUS      current
    DESCRIPTION
        "Deauthentications."
    ::= { ligoAthPeerStatsEntry 37 }

ligoAthPeerTxDeauthCode OBJECT-TYPE
    SYNTAX      Counter32
    MAX-ACCESS  read-only
    STATUS      current
    DESCRIPTION
        "Last deauthentication reason."
    ::= { ligoAthPeerStatsEntry 38 }

ligoAthPeerTxDisassoc OBJECT-TYPE
    SYNTAX      Counter32
    MAX-ACCESS  read-only
    STATUS      current
    DESCRIPTION
        "Disassociations."
    ::= { ligoAthPeerStatsEntry 39 }

ligoAthPeerTxDisassocCode OBJECT-TYPE
    SYNTAX      Counter32
    MAX-ACCESS  read-only
    STATUS      current
    DESCRIPTION
        "Last disassociation reason."
    ::= { ligoAthPeerStatsEntry 40 }

ligoAthPeerPsqDrops OBJECT-TYPE
    SYNTAX      Counter32
    MAX-ACCESS  read-only
    STATUS      current
    DESCRIPTION
        "Power save queue drops."
    ::= { ligoAthPeerStatsEntry 41 }

ligoAthPeerMcastSnoop OBJECT-TYPE
    SYNTAX      Counter32
    MAX-ACCESS  read-only
    STATUS      current
    DESCRIPTION
        "Frames passed by multicast snooping."
    ::= { ligoAthPeerStatsEntry 42 }

END

--
--  LigoWave 3 series radio driver MIB
--

LIGO-RADIO3-DRV-MIB DEFINITIONS ::= BEGIN
IMPORTS
    MODULE-IDENTITY, OBJECT-TYPE, NOTIFICATION-TYPE,
    Integer32, Counter32, Gauge32, IpAddress, TimeTicks
        FROM SNMPv2-SMI
    MacAddress
        FROM SNMPv2-TC
    sysLocation
        FROM SNMPv2-MIB
    ifIndex
        FROM IF-MIB
    ligoMgmt
        FROM LIGOWAVE-MIB;

ligoRadio3DrvMIB MODULE-IDENTITY
    LAST-UPDATED    "201001060000Z"
    ORGANIZATION    "LigoWave"
    CONTACT-INFO    "
        LigoWave Customer Support
        E-mail: support@ligowave.com"
    DESCRIPTION
        "LigoWave 3 series radio driver MIB."
    REVISION    "201001060000Z"
    DESCRIPTION
        "First revision."
    ::= { ligoMgmt 8 }

ligoRadio3DrvMIBObjects
        OBJECT IDENTIFIER ::= { ligoRadio3DrvMIB 1 }

ligoRdo3DrvNotifs
        OBJECT IDENTIFIER ::= { ligoRadio3DrvMIBObjects 0 }
ligoRdo3DrvInfo
        OBJECT IDENTIFIER ::= { ligoRadio3DrvMIBObjects 1 }
ligoRdo3DrvConf
        OBJECT IDENTIFIER ::= { ligoRadio3DrvMIBObjects 2 }
ligoRdo3DrvStats
        OBJECT IDENTIFIER ::= { ligoRadio3DrvMIBObjects 3 }

ligoRdo3StatsTable OBJECT-TYPE
    SYNTAX  SEQUENCE OF LigoRdo3StatsEntry
    MAX-ACCESS  not-accessible
    STATUS  current
    DESCRIPTION
        "Radio driver's information and network traffic statistics table."
    ::= { ligoRdo3DrvStats 1 }

ligoRdo3StatsEntry OBJECT-TYPE
    SYNTAX  LigoRdo3StatsEntry
    MAX-ACCESS  not-accessible
    STATUS  current
    DESCRIPTION
        "Radio driver's information and network traffic statistics table entry."
    INDEX { ifIndex, ligoRdo3Endpoint }
    ::= { ligoRdo3StatsTable 1 }

LigoRdo3StatsEntry ::=
    SEQUENCE {
        ligoRdo3Endpoint                     Integer32,
        ligoRdo3LastUpdate                   TimeTicks,
        ligoRdo3MacAddress                   MacAddress,
        ligoRdo3IpAddress                    IpAddress,
        ligoRdo3CountryCode                  OCTET STRING,
        ligoRdo3Encryption                   OCTET STRING,
        ligoRdo3Parameters                   OCTET STRING,
        ligoRdo3Capabilities                 OCTET STRING,
        ligoRdo3TxPower                      Gauge32,
        ligoRdo3TxPackets                    Counter32,
        ligoRdo3TxBytes                      Counter32,
        ligoRdo3TxXmitFailed                 Counter32,
        ligoRdo3TxXmitDropped                Counter32,
        ligoRdo3TxOverruns                   Counter32,
        ligoRdo3TxSuccess                    Counter32,
        ligoRdo3TxFailed                     Counter32,
        ligoRdo3TxRetried                    Counter32,
        ligoRdo3TxNotRetried                 Counter32,
        ligoRdo3TxPacketsPerMcs              OCTET STRING,
        ligoRdo3TxMsdus                      Counter32,
        ligoRdo3TxNotAggregated              Counter32,
        ligoRdo3TxAckRequired                Counter32,
        ligoRdo3TxNoAckRequired              Counter32,
        ligoRdo3TxAltRate                    Counter32,
        ligoRdo3TxManagement                 Counter32,
        ligoRdo3TxLegacy                     Counter32,
        ligoRdo3TxLegacyBytes                Counter32,
        ligoRdo3TxAmsdus                     Counter32,
        ligoRdo3TxPktsInAmsdus               Counter32,
        ligoRdo3TxAmsduBytes                 Counter32,
        ligoRdo3TxMpdus                      Counter32,
        ligoRdo3TxMpduBytes                  Counter32,
        ligoRdo3TxFragmented                 Counter32,
        ligoRdo3TxFragBytes                  Counter32,
        ligoRdo3RxPackets                    Counter32,
        ligoRdo3RxBytes                      Counter32,
        ligoRdo3RxDropped                    Counter32,
        ligoRdo3RxCrcErrors                  Counter32,
        ligoRdo3RxIcvErrors                  Counter32,
        ligoRdo3RxMicErrors                  Counter32,
        ligoRdo3RxKeyNotValid                Counter32,
        ligoRdo3RxAclDiscarded               Counter32,
        ligoRdo3RxManagement                 Counter32,
        ligoRdo3RxControl                    Counter32,
        ligoRdo3RxData                       Counter32,
        ligoRdo3RxUnknown                    Counter32,
        ligoRdo3RxNullData                   Counter32,
        ligoRdo3RxBroadcast                  Counter32,
        ligoRdo3RxMulticast                  Counter32,
        ligoRdo3RxUnicast                    Counter32,
        ligoRdo3RxCck                        Counter32,
        ligoRdo3RxOfdm                       Counter32,
        ligoRdo3RxHtMixedMode                Counter32,
        ligoRdo3RxHtGreenfield               Counter32,
        ligoRdo3RxAmsdus                     Counter32,
        ligoRdo3RxPacketsInAmsdus            Counter32,
        ligoRdo3RxAmpdus                     Counter32,
        ligoRdo3RxMpduBytes                  Counter32,
        ligoRdo3RxRoBufTotal                 Counter32,
        ligoRdo3RxRoBufInSeq                 Counter32,
        ligoRdo3RxRoBufDup                   Counter32,
        ligoRdo3RxRoBufExpired               Counter32,
        ligoRdo3RxRoBufBuffered              Counter32,
        ligoRdo3RxRoBufReordered             Counter32,
        ligoRdo3RxRoBufFlushed               Counter32,
        ligoRdo3RxRoBufTooBig                Counter32,
        ligoRdo3RxL2Pad                      Counter32,
        ligoRdo3RxBlockAcks                  Counter32,
        ligoRdo3RxFragments                  Counter32,
        ligoRdo3RxStbc                       Counter32,
        ligoRdo3RxShortGuardInt              Counter32,
        ligoRdo3Rx40MhzBandwidth             Counter32,
        ligoRdo3RxHtControl                  Counter32,
        ligoRdo3RxPacketsPerMcs              OCTET STRING,
        ligoRdo3RxLastSigLevel0              Integer32,
        ligoRdo3RxLastSigLevel1              Integer32,
        ligoRdo3RxLastSigLevel2              Integer32,
        ligoRdo3RxNoise                      Integer32,
        ligoRdo3RxLastSnr0                   Integer32,
        ligoRdo3RxLastSnr1                   Integer32
}        

ligoRdo3Endpoint OBJECT-TYPE
    SYNTAX      Integer32
    MAX-ACCESS  not-accessible
    STATUS      current
    DESCRIPTION
        "Peer index. Local device has index 0."
    ::= { ligoRdo3StatsEntry 1 }

ligoRdo3LastUpdate OBJECT-TYPE
    SYNTAX      TimeTicks
    MAX-ACCESS  read-only
    STATUS      current
    DESCRIPTION
        "sysUptime value of time point when statistics was gathered."
    ::= { ligoRdo3StatsEntry 2 }

ligoRdo3MacAddress OBJECT-TYPE
    SYNTAX      MacAddress
    MAX-ACCESS  read-only
    STATUS      current
    DESCRIPTION
        "Device's MAC address."
    ::= { ligoRdo3StatsEntry 3 }

ligoRdo3IpAddress OBJECT-TYPE
    SYNTAX      IpAddress
    MAX-ACCESS  read-only
    STATUS      current
    DESCRIPTION
        "Device's IP address."
    ::= { ligoRdo3StatsEntry 4 }

ligoRdo3CountryCode OBJECT-TYPE
    SYNTAX      OCTET STRING
    MAX-ACCESS  read-only
    STATUS      current
    DESCRIPTION
        "Country code."
    ::= { ligoRdo3StatsEntry 5 }

ligoRdo3Encryption OBJECT-TYPE
    SYNTAX      OCTET STRING
    MAX-ACCESS  read-only
    STATUS      current
    DESCRIPTION
        "Encryption type."
    ::= { ligoRdo3StatsEntry 6 }

ligoRdo3Parameters OBJECT-TYPE
    SYNTAX      OCTET STRING
    MAX-ACCESS  read-only
    STATUS      current
    DESCRIPTION
        "Radio parameters."
    ::= { ligoRdo3StatsEntry 7 }

ligoRdo3Capabilities OBJECT-TYPE
    SYNTAX      OCTET STRING
    MAX-ACCESS  read-only
    STATUS      current
    DESCRIPTION
        "Radio capabilities."
    ::= { ligoRdo3StatsEntry 8 }

ligoRdo3TxPower OBJECT-TYPE
    SYNTAX      Gauge32
    MAX-ACCESS  read-only
    STATUS      current
    DESCRIPTION
        "Transmission power."
    ::= { ligoRdo3StatsEntry 9 }

ligoRdo3TxPackets OBJECT-TYPE
    SYNTAX      Counter32
    MAX-ACCESS  read-only
    STATUS      current
    DESCRIPTION
        "Number of transmitted packets."
    ::= { ligoRdo3StatsEntry 10 }

ligoRdo3TxBytes OBJECT-TYPE
    SYNTAX      Counter32
    MAX-ACCESS  read-only
    STATUS      current
    DESCRIPTION
        "Number of transmitted bytes."
    ::= { ligoRdo3StatsEntry 11 }

ligoRdo3TxXmitFailed OBJECT-TYPE
    SYNTAX      Counter32
    MAX-ACCESS  read-only
    STATUS      current
    DESCRIPTION
        "Number of packets failing initial checks before sending them to radio hardware."
    ::= { ligoRdo3StatsEntry 12 }

ligoRdo3TxXmitDropped OBJECT-TYPE
    SYNTAX      Counter32
    MAX-ACCESS  read-only
    STATUS      current
    DESCRIPTION
        "Number of packets dropped because radio was offline or in reset state."
    ::= { ligoRdo3StatsEntry 13 }

ligoRdo3TxOverruns OBJECT-TYPE
    SYNTAX      Counter32
    MAX-ACCESS  read-only
    STATUS      current
    DESCRIPTION
        "Number of transmission overruns."
    ::= { ligoRdo3StatsEntry 14 }

ligoRdo3TxSuccess OBJECT-TYPE
    SYNTAX      Counter32
    MAX-ACCESS  read-only
    STATUS      current
    DESCRIPTION
        "Number of successfully transmitted packets."
    ::= { ligoRdo3StatsEntry 15 }

ligoRdo3TxFailed OBJECT-TYPE
    SYNTAX      Counter32
    MAX-ACCESS  read-only
    STATUS      current
    DESCRIPTION
        "Number of transmission failures."
    ::= { ligoRdo3StatsEntry 16 }

ligoRdo3TxRetried OBJECT-TYPE
    SYNTAX      Counter32
    MAX-ACCESS  read-only
    STATUS      current
    DESCRIPTION
        "Number of transmission retries."
    ::= { ligoRdo3StatsEntry 17 }

ligoRdo3TxNotRetried OBJECT-TYPE
    SYNTAX      Counter32
    MAX-ACCESS  read-only
    STATUS      current
    DESCRIPTION
        "Number of packets sent without retries."
    ::= { ligoRdo3StatsEntry 18 }

ligoRdo3TxPacketsPerMcs OBJECT-TYPE
    SYNTAX      OCTET STRING
    MAX-ACCESS  read-only
    STATUS      current
    DESCRIPTION
        "Number of packets sent using each of Modulation and Coding Schemes."
    ::= { ligoRdo3StatsEntry 19 }

ligoRdo3TxMsdus OBJECT-TYPE
    SYNTAX      Counter32
    MAX-ACCESS  read-only
    STATUS      current
    DESCRIPTION
        "Number of transmitted MAC Service Data Units."
    ::= { ligoRdo3StatsEntry 20 }

ligoRdo3TxNotAggregated OBJECT-TYPE
    SYNTAX      Counter32
    MAX-ACCESS  read-only
    STATUS      current
    DESCRIPTION
        "Number of packets transmitted without aggregation."
    ::= { ligoRdo3StatsEntry 21 }

ligoRdo3TxAckRequired OBJECT-TYPE
    SYNTAX      Counter32
    MAX-ACCESS  read-only
    STATUS      current
    DESCRIPTION
        "Number of packets transmitted which required acknowledgment."
    ::= { ligoRdo3StatsEntry 22 }

ligoRdo3TxNoAckRequired OBJECT-TYPE
    SYNTAX      Counter32
    MAX-ACCESS  read-only
    STATUS      current
    DESCRIPTION
        "Number of packets transmitted which did not require acknowledgment."
    ::= { ligoRdo3StatsEntry 23 }

ligoRdo3TxAltRate OBJECT-TYPE
    SYNTAX      Counter32
    MAX-ACCESS  read-only
    STATUS      current
    DESCRIPTION
        "Number of data rate alterations."
    ::= { ligoRdo3StatsEntry 24 }

ligoRdo3TxManagement OBJECT-TYPE
    SYNTAX      Counter32
    MAX-ACCESS  read-only
    STATUS      current
    DESCRIPTION
        "Number of transmitted management frames."
    ::= { ligoRdo3StatsEntry 25 }

ligoRdo3TxLegacy OBJECT-TYPE
    SYNTAX      Counter32
    MAX-ACCESS  read-only
    STATUS      current
    DESCRIPTION
        "Number of transmitted legacy packets."
    ::= { ligoRdo3StatsEntry 26 }

ligoRdo3TxLegacyBytes OBJECT-TYPE
    SYNTAX      Counter32
    MAX-ACCESS  read-only
    STATUS      current
    DESCRIPTION
        "Number of bytes transmitted in legacy mode."
    ::= { ligoRdo3StatsEntry 27 }

ligoRdo3TxAmsdus OBJECT-TYPE
    SYNTAX      Counter32
    MAX-ACCESS  read-only
    STATUS      current
    DESCRIPTION
        "Number of transmitted aggregated MAC Service Data Units."
    ::= { ligoRdo3StatsEntry 28 }

ligoRdo3TxPktsInAmsdus OBJECT-TYPE
    SYNTAX      Counter32
    MAX-ACCESS  read-only
    STATUS      current
    DESCRIPTION
        "Number of packets contained in transmitted aggregated MAC Service Data Units."
    ::= { ligoRdo3StatsEntry 29 }

ligoRdo3TxAmsduBytes OBJECT-TYPE
    SYNTAX      Counter32
    MAX-ACCESS  read-only
    STATUS      current
    DESCRIPTION
        "Number of bytes transmitted in aggregated MAC Service Data Units."
    ::= { ligoRdo3StatsEntry 30 }

ligoRdo3TxMpdus OBJECT-TYPE
    SYNTAX      Counter32
    MAX-ACCESS  read-only
    STATUS      current
    DESCRIPTION
        "Number of transmitted MAC Protocol Data Units."
    ::= { ligoRdo3StatsEntry 31 }

ligoRdo3TxMpduBytes OBJECT-TYPE
    SYNTAX      Counter32
    MAX-ACCESS  read-only
    STATUS      current
    DESCRIPTION
        "Number of bytes transmitted in MAC Protocol Data Units."
    ::= { ligoRdo3StatsEntry 32 }

ligoRdo3TxFragmented OBJECT-TYPE
    SYNTAX      Counter32
    MAX-ACCESS  read-only
    STATUS      current
    DESCRIPTION
        "Number of transmitted fragmented packets."
    ::= { ligoRdo3StatsEntry 33 }

ligoRdo3TxFragBytes OBJECT-TYPE
    SYNTAX      Counter32
    MAX-ACCESS  read-only
    STATUS      current
    DESCRIPTION
        "Number of bytes transmitted in fragmented packets."
    ::= { ligoRdo3StatsEntry 34 }

ligoRdo3RxPackets OBJECT-TYPE
    SYNTAX      Counter32
    MAX-ACCESS  read-only
    STATUS      current
    DESCRIPTION
        "Number of received packets."
    ::= { ligoRdo3StatsEntry 35 }

ligoRdo3RxBytes OBJECT-TYPE
    SYNTAX      Counter32
    MAX-ACCESS  read-only
    STATUS      current
    DESCRIPTION
        "Number of received bytes."
    ::= { ligoRdo3StatsEntry 36 }

ligoRdo3RxDropped OBJECT-TYPE
    SYNTAX      Counter32
    MAX-ACCESS  read-only
    STATUS      current
    DESCRIPTION
        "Number of dropped packets."
    ::= { ligoRdo3StatsEntry 37 }

ligoRdo3RxCrcErrors OBJECT-TYPE
    SYNTAX      Counter32
    MAX-ACCESS  read-only
    STATUS      current
    DESCRIPTION
        "Number of received packets that failed CRC check."
    ::= { ligoRdo3StatsEntry 38 }

ligoRdo3RxIcvErrors OBJECT-TYPE
    SYNTAX      Counter32
    MAX-ACCESS  read-only
    STATUS      current
    DESCRIPTION
        "Number of received packets with invalid Integrity Check Value."
    ::= { ligoRdo3StatsEntry 39 }

ligoRdo3RxMicErrors OBJECT-TYPE
    SYNTAX      Counter32
    MAX-ACCESS  read-only
    STATUS      current
    DESCRIPTION
        "Number of received packets failing Message Integrity Code check."
    ::= { ligoRdo3StatsEntry 40 }

ligoRdo3RxKeyNotValid OBJECT-TYPE
    SYNTAX      Counter32
    MAX-ACCESS  read-only
    STATUS      current
    DESCRIPTION
        "Number of received packets with encryption key errors."
    ::= { ligoRdo3StatsEntry 41 }

ligoRdo3RxAclDiscarded OBJECT-TYPE
    SYNTAX      Counter32
    MAX-ACCESS  read-only
    STATUS      current
    DESCRIPTION
        "Number of received packets discarded by Access Control List check."
    ::= { ligoRdo3StatsEntry 42 }

ligoRdo3RxManagement OBJECT-TYPE
    SYNTAX      Counter32
    MAX-ACCESS  read-only
    STATUS      current
    DESCRIPTION
        "Number of received management packets."
    ::= { ligoRdo3StatsEntry 43 }

ligoRdo3RxControl OBJECT-TYPE
    SYNTAX      Counter32
    MAX-ACCESS  read-only
    STATUS      current
    DESCRIPTION
        "Number of received control packets."
    ::= { ligoRdo3StatsEntry 44 }

ligoRdo3RxData OBJECT-TYPE
    SYNTAX      Counter32
    MAX-ACCESS  read-only
    STATUS      current
    DESCRIPTION
        "Number of received data packets."
    ::= { ligoRdo3StatsEntry 45 }

ligoRdo3RxUnknown OBJECT-TYPE
    SYNTAX      Counter32
    MAX-ACCESS  read-only
    STATUS      current
    DESCRIPTION
        "Number of received packets of unknown type."
    ::= { ligoRdo3StatsEntry 46 }

ligoRdo3RxNullData OBJECT-TYPE
    SYNTAX      Counter32
    MAX-ACCESS  read-only
    STATUS      current
    DESCRIPTION
        "Number of received NULL DATA frames."
    ::= { ligoRdo3StatsEntry 47 }

ligoRdo3RxBroadcast OBJECT-TYPE
    SYNTAX      Counter32
    MAX-ACCESS  read-only
    STATUS      current
    DESCRIPTION
        "Number of received broadcast packets."
    ::= { ligoRdo3StatsEntry 48 }

ligoRdo3RxMulticast OBJECT-TYPE
    SYNTAX      Counter32
    MAX-ACCESS  read-only
    STATUS      current
    DESCRIPTION
        "Number of received multicast packets."
    ::= { ligoRdo3StatsEntry 49 }

ligoRdo3RxUnicast OBJECT-TYPE
    SYNTAX      Counter32
    MAX-ACCESS  read-only
    STATUS      current
    DESCRIPTION
        "Number of received unicast packets."
    ::= { ligoRdo3StatsEntry 50 }

ligoRdo3RxCck OBJECT-TYPE
    SYNTAX      Counter32
    MAX-ACCESS  read-only
    STATUS      current
    DESCRIPTION
        "Number of packets received using Complementary Code Keying modulation."
    ::= { ligoRdo3StatsEntry 51 }

ligoRdo3RxOfdm OBJECT-TYPE
    SYNTAX      Counter32
    MAX-ACCESS  read-only
    STATUS      current
    DESCRIPTION
        "Number of packets received using Orthogonal Frequency-Division Multiplexing modulation."
    ::= { ligoRdo3StatsEntry 52 }

ligoRdo3RxHtMixedMode OBJECT-TYPE
    SYNTAX      Counter32
    MAX-ACCESS  read-only
    STATUS      current
    DESCRIPTION
        "Number of packets received using High Throughput mixed mode."
    ::= { ligoRdo3StatsEntry 53 }

ligoRdo3RxHtGreenfield OBJECT-TYPE
    SYNTAX      Counter32
    MAX-ACCESS  read-only
    STATUS      current
    DESCRIPTION
        "Number of packets received using High Throughput Greenfield mode."
    ::= { ligoRdo3StatsEntry 54 }

ligoRdo3RxAmsdus OBJECT-TYPE
    SYNTAX      Counter32
    MAX-ACCESS  read-only
    STATUS      current
    DESCRIPTION
        "Number of received aggregated MAC Service Data Units."
    ::= { ligoRdo3StatsEntry 55 }

ligoRdo3RxPacketsInAmsdus OBJECT-TYPE
    SYNTAX      Counter32
    MAX-ACCESS  read-only
    STATUS      current
    DESCRIPTION
        "Number of packets received in aggregated MAC Service Data Units."
    ::= { ligoRdo3StatsEntry 56 }

ligoRdo3RxAmpdus OBJECT-TYPE
    SYNTAX      Counter32
    MAX-ACCESS  read-only
    STATUS      current
    DESCRIPTION
        "Number of received aggregated MAC Protocol Data Units."
    ::= { ligoRdo3StatsEntry 57 }

ligoRdo3RxMpduBytes OBJECT-TYPE
    SYNTAX      Counter32
    MAX-ACCESS  read-only
    STATUS      current
    DESCRIPTION
        "Number of bytes received in MAC Protocol Data Units."
    ::= { ligoRdo3StatsEntry 58 }

ligoRdo3RxRoBufTotal OBJECT-TYPE
    SYNTAX      Counter32
    MAX-ACCESS  read-only
    STATUS      current
    DESCRIPTION
        "Total number of received packets moved into reordering buffer."
    ::= { ligoRdo3StatsEntry 59 }

ligoRdo3RxRoBufInSeq OBJECT-TYPE
    SYNTAX      Counter32
    MAX-ACCESS  read-only
    STATUS      current
    DESCRIPTION
        "Number of packets in reordering buffer which are in sequence."
    ::= { ligoRdo3StatsEntry 60 }

ligoRdo3RxRoBufDup OBJECT-TYPE
    SYNTAX      Counter32
    MAX-ACCESS  read-only
    STATUS      current
    DESCRIPTION
        "Number of duplicate packets in reordering buffer."
    ::= { ligoRdo3StatsEntry 61 }

ligoRdo3RxRoBufExpired OBJECT-TYPE
    SYNTAX      Counter32
    MAX-ACCESS  read-only
    STATUS      current
    DESCRIPTION
        "Number of expired packets in reordering buffer."
    ::= { ligoRdo3StatsEntry 62 }

ligoRdo3RxRoBufBuffered OBJECT-TYPE
    SYNTAX      Counter32
    MAX-ACCESS  read-only
    STATUS      current
    DESCRIPTION
        "Number of packets held in reordering buffer."
    ::= { ligoRdo3StatsEntry 63 }

ligoRdo3RxRoBufReordered OBJECT-TYPE
    SYNTAX      Counter32
    MAX-ACCESS  read-only
    STATUS      current
    DESCRIPTION
        "Number of packets reordered in reordering buffer."
    ::= { ligoRdo3StatsEntry 64 }

ligoRdo3RxRoBufFlushed OBJECT-TYPE
    SYNTAX      Counter32
    MAX-ACCESS  read-only
    STATUS      current
    DESCRIPTION
        "Number of packets flushed from reordering buffer."
    ::= { ligoRdo3StatsEntry 65 }

ligoRdo3RxRoBufTooBig OBJECT-TYPE
    SYNTAX      Counter32
    MAX-ACCESS  read-only
    STATUS      current
    DESCRIPTION
        "Number of oversized packets dropped from reordering buffer."
    ::= { ligoRdo3StatsEntry 66 }

ligoRdo3RxL2Pad OBJECT-TYPE
    SYNTAX      Counter32
    MAX-ACCESS  read-only
    STATUS      current
    DESCRIPTION
        "Number of packets received with padding between header and payload."
    ::= { ligoRdo3StatsEntry 67 }

ligoRdo3RxBlockAcks OBJECT-TYPE
    SYNTAX      Counter32
    MAX-ACCESS  read-only
    STATUS      current
    DESCRIPTION
        "Number of received block acknowledgments."
    ::= { ligoRdo3StatsEntry 68 }

ligoRdo3RxFragments OBJECT-TYPE
    SYNTAX      Counter32
    MAX-ACCESS  read-only
    STATUS      current
    DESCRIPTION
        "Number of received fragmented packets."
    ::= { ligoRdo3StatsEntry 69 }

ligoRdo3RxStbc OBJECT-TYPE
    SYNTAX      Counter32
    MAX-ACCESS  read-only
    STATUS      current
    DESCRIPTION
        "Number of packets received using Space-Time Block Coding technique."
    ::= { ligoRdo3StatsEntry 70 }

ligoRdo3RxShortGuardInt OBJECT-TYPE
    SYNTAX      Counter32
    MAX-ACCESS  read-only
    STATUS      current
    DESCRIPTION
        "Number of packets received with Short Guard Interval."
    ::= { ligoRdo3StatsEntry 71 }

ligoRdo3Rx40MhzBandwidth OBJECT-TYPE
    SYNTAX      Counter32
    MAX-ACCESS  read-only
    STATUS      current
    DESCRIPTION
        "Number of packets received using 40MHz bandwidth."
    ::= { ligoRdo3StatsEntry 72 }

ligoRdo3RxHtControl OBJECT-TYPE
    SYNTAX      Counter32
    MAX-ACCESS  read-only
    STATUS      current
    DESCRIPTION
        "Number of packets received using High Throughput encoding."
    ::= { ligoRdo3StatsEntry 73 }

ligoRdo3RxPacketsPerMcs OBJECT-TYPE
    SYNTAX      OCTET STRING
    MAX-ACCESS  read-only
    STATUS      current
    DESCRIPTION
        "Number of packets received using each of Modulation and Coding Schemes."
    ::= { ligoRdo3StatsEntry 74 }

ligoRdo3RxLastSigLevel0 OBJECT-TYPE
    SYNTAX      Integer32
    MAX-ACCESS  read-only
    STATUS      current
    DESCRIPTION
        "Reception signal level on antenna 0."
    ::= { ligoRdo3StatsEntry 75 }

ligoRdo3RxLastSigLevel1 OBJECT-TYPE
    SYNTAX      Integer32
    MAX-ACCESS  read-only
    STATUS      current
    DESCRIPTION
        "Reception signal level on antenna 1."
    ::= { ligoRdo3StatsEntry 76 }

ligoRdo3RxLastSigLevel2 OBJECT-TYPE
    SYNTAX      Integer32
    MAX-ACCESS  read-only
    STATUS      current
    DESCRIPTION
        "Reception signal level on antenna 2."
    ::= { ligoRdo3StatsEntry 77 }

ligoRdo3RxNoise OBJECT-TYPE
    SYNTAX      Integer32
    MAX-ACCESS  read-only
    STATUS      current
    DESCRIPTION
        "Reception noise."
    ::= { ligoRdo3StatsEntry 78 }

ligoRdo3RxLastSnr0 OBJECT-TYPE
    SYNTAX      Integer32
    MAX-ACCESS  read-only
    STATUS      current
    DESCRIPTION
        "Last registered signal-to-noise level on antenna 0."
    ::= { ligoRdo3StatsEntry 79 }

ligoRdo3RxLastSnr1 OBJECT-TYPE
    SYNTAX      Integer32
    MAX-ACCESS  read-only
    STATUS      current
    DESCRIPTION
        "Last registered signal-to-noise level on antenna 1."
    ::= { ligoRdo3StatsEntry 80 }

ligoRdo3RxDropsThreshold NOTIFICATION-TYPE
    OBJECTS {
        sysLocation,
        ifIndex,
        ligoRdo3MacAddress,
        ligoRdo3RxDropped
    }
    STATUS      current
    DESCRIPTION
        "This notification is sent when percentage of frames dropped in relation
         to number of frames received over the same time period reaches the threshold."
    ::= { ligoRdo3DrvNotifs 1 }

ligoRdo3TxRetriesThreshold NOTIFICATION-TYPE
    OBJECTS {
        sysLocation,
        ifIndex,
        ligoRdo3MacAddress,
        ligoRdo3TxRetried
    }
    STATUS      current
    DESCRIPTION
        "This notification is sent when percentage of transmission retries in relation
         to number of frames transmitted over the same time period reaches the threshold."
    ::= { ligoRdo3DrvNotifs 2 }

END

--
--  LigoWave W-Jet MIMO MIB
--

LIGO-W-JET-MIMO-MIB DEFINITIONS ::= BEGIN
IMPORTS
    MODULE-IDENTITY, OBJECT-TYPE,
    Integer32, Counter32
        FROM SNMPv2-SMI
    MacAddress
        FROM SNMPv2-TC
    ifIndex
        FROM IF-MIB
    ligoMgmt
        FROM LIGOWAVE-MIB;

ligoWJetMimoMIB MODULE-IDENTITY
    LAST-UPDATED    "201003220000Z"
    ORGANIZATION    "LigoWave"
    CONTACT-INFO    "
        LigoWave Customer Support
        E-mail: support@ligowave.com"
    DESCRIPTION
        "The LigoWave W-Jet MIMO Protocol MIB."
    REVISION    "201003220000Z"
    DESCRIPTION
        "First revision."
    ::= { ligoMgmt 9 }

ligoWJetMimoMIBObjects
        OBJECT IDENTIFIER ::= { ligoWJetMimoMIB 1 }

ligoWJetMimoNotifs
        OBJECT IDENTIFIER ::= { ligoWJetMimoMIBObjects 0 }
ligoWJetMimoInfo
        OBJECT IDENTIFIER ::= { ligoWJetMimoMIBObjects 1 }
ligoWJetMimoConf
        OBJECT IDENTIFIER ::= { ligoWJetMimoMIBObjects 2 }
ligoWJetMimoStats
        OBJECT IDENTIFIER ::= { ligoWJetMimoMIBObjects 3 }

wJetMimoStatsTable OBJECT-TYPE
    SYNTAX  SEQUENCE OF WJetMimoStatsEntry
    MAX-ACCESS  not-accessible
    STATUS  current
    DESCRIPTION
        "W-Jet MIMO protocol statistics table."
    ::= { ligoWJetMimoStats 1 }

wJetMimoStatsEntry OBJECT-TYPE
    SYNTAX  WJetMimoStatsEntry
    MAX-ACCESS  not-accessible
    STATUS  current
    DESCRIPTION
        "W-Jet MIMO protocol statistics table entry."
    INDEX { ifIndex, wJetMimoPeerIndex }
    ::= { wJetMimoStatsTable 1 }

WJetMimoStatsEntry ::=
    SEQUENCE {
        wJetMimoPeerIndex          Integer32,
        wJetMimoMacAddress         MacAddress,
        wJetMimoTxTokens           Counter32,
        wJetMimoRxTokens           Counter32,
        wJetMimoDupTokens          Counter32,
        wJetMimoLostTokens         Counter32,
        wJetMimoDroppedTokens      Counter32,
        wJetMimoTxFailures         Counter32,
        wJetMimoReinjectedTokens   Counter32
    }

wJetMimoPeerIndex OBJECT-TYPE
    SYNTAX      Integer32
    MAX-ACCESS  not-accessible
    STATUS      current
    DESCRIPTION
        "Peer index. Local device has index 0."
    ::= { wJetMimoStatsEntry 1 }

wJetMimoMacAddress OBJECT-TYPE
    SYNTAX      MacAddress
    MAX-ACCESS  read-only
    STATUS      current
    DESCRIPTION
        "Peer MAC address."
    ::= { wJetMimoStatsEntry 2 }

wJetMimoTxTokens OBJECT-TYPE
    SYNTAX      Counter32
    MAX-ACCESS  read-only
    STATUS      current
    DESCRIPTION
        "Number of transmitted tokens."
    ::= { wJetMimoStatsEntry 3 }

wJetMimoRxTokens OBJECT-TYPE
    SYNTAX      Counter32
    MAX-ACCESS  read-only
    STATUS      current
    DESCRIPTION
        "Number of received tokens."
    ::= { wJetMimoStatsEntry 4 }

wJetMimoDupTokens OBJECT-TYPE
    SYNTAX      Counter32
    MAX-ACCESS  read-only
    STATUS      current
    DESCRIPTION
        "Number of duplicate tokens."
    ::= { wJetMimoStatsEntry 5 }

wJetMimoLostTokens OBJECT-TYPE
    SYNTAX      Counter32
    MAX-ACCESS  read-only
    STATUS      current
    DESCRIPTION
        "Number of lost tokens."
    ::= { wJetMimoStatsEntry 6 }

wJetMimoDroppedTokens OBJECT-TYPE
    SYNTAX      Counter32
    MAX-ACCESS  read-only
    STATUS      current
    DESCRIPTION
        "Number of dropped tokens."
    ::= { wJetMimoStatsEntry 7 }

wJetMimoTxFailures OBJECT-TYPE
    SYNTAX      Counter32
    MAX-ACCESS  read-only
    STATUS      current
    DESCRIPTION
        "Number of token transmissions failures."
    ::= { wJetMimoStatsEntry 8 }

wJetMimoReinjectedTokens OBJECT-TYPE
    SYNTAX      Counter32
    MAX-ACCESS  read-only
    STATUS      current
    DESCRIPTION
        "Number of reinjected tokens."
    ::= { wJetMimoStatsEntry 9 }

END

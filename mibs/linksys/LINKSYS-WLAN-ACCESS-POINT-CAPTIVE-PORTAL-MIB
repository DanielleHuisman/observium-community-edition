LINKSYS-WLAN-ACCESS-POINT-CAPTIVE-PORTAL-MIB DEFINITIONS ::= BEGIN

-- LAPAC1750PRO Captive Portal MIB
-- (C) 2014 Belkin International, Inc. and/or its subsidiaries and affiliates, including Linksys, LLC. All rights reserved.

-- This SNMP Management Information Specification
-- embodies Linksys, LLC. Corporation's confidential and proprietary
-- intellectual property. Linksys, LLC. Corporation retains all title
-- and ownership in the Specification including any revisions.

-- This Specification is supplied "AS IS", Linksys, LLC. Corporation
-- makes no warranty, either expressed or implied,
-- as to the use, operation, condition, or performance of the
-- Specification.

    IMPORTS
        MODULE-IDENTITY, OBJECT-TYPE, NOTIFICATION-TYPE, IpAddress,
        IpAddress,Integer32, Counter32, Counter64, TimeTicks, Unsigned32
                                            FROM SNMPv2-SMI
        RowStatus,MacAddress,TEXTUAL-CONVENTION
                                            FROM SNMPv2-TC
        DisplayString                       FROM RFC1213-MIB
        ifIndex                             FROM IF-MIB
        InterfaceIndex                      FROM IF-MIB
        InetAddressType, InetAddress        FROM INET-ADDRESS-MIB
        wap03			                    FROM LINKSYS-WLAN-ACCESS-POINT-MIB;

    apCaptivePortal MODULE-IDENTITY
        LAST-UPDATED "201404090000Z" -- 09 April 2014 12:00:00 GMT
        ORGANIZATION "Linksys Small Business"
        CONTACT-INFO
        "  Postal:            Linksys, LLC. 
				131 Theory Drive
				Irvine, CA 92617
          Support Website:    http://www.linksys.com/business/support"
        DESCRIPTION
          "Private MIB for Captive Portal"

        -- Revision history.
        REVISION
          "201404090000Z" -- 09 April 2014 12:00:00 GMT
        DESCRIPTION
          "Initial version."

    ::= { wap03 120 }


   -- 
   -- ***********************************************************
   -- 
   -- Textual Conventions
   -- 
   -- ***********************************************************


   --**************************************************************************************
   --    apcpConfigGroup
   --**************************************************************************************
   
   apcpConfigGroup                      OBJECT IDENTIFIER ::= { apCaptivePortal 1 }

    --**************************************************************************************
    --    apcpGlobalConfigGroup
    --**************************************************************************************
    
    apcpGlobalConfigGroup            OBJECT IDENTIFIER ::= { apcpConfigGroup 1 }

    apcpAdminMode OBJECT-TYPE
         SYNTAX      INTEGER {
                     enable(1),
                     disable(2)
                  }
         MAX-ACCESS  read-write
         STATUS      current
         DESCRIPTION
                     "Enable or disable captive portal feature on the system."
         DEFVAL { disable }
         ::= { apcpGlobalConfigGroup 1 }

    apcpAuthTimeout OBJECT-TYPE
         SYNTAX      Integer32 (60..600)
         MAX-ACCESS  read-write
         STATUS      current
         DESCRIPTION
                     "The length of time to maintain an authentication session 
                     from a client. This time is measured from when a client
                     initiates an authentication request. The value is 
                     represented in seconds.This applies to both http and 
                     https sessions."
         DEFVAL { 300 }
         ::= { apcpGlobalConfigGroup 2 }
         
    apcpAdditionalHttpPort OBJECT-TYPE
         SYNTAX      Integer32 (1025..65535)
         MAX-ACCESS  read-write
         STATUS      current
         DESCRIPTION
                     "The additional captive portal authentication server port for 
                     HTTP web connection. Valid range is from 1025-65535 or 80.
                     apcpAdditionalHttpPort and apcpAdditionalHttpSecurePort should 
                     not have same value. 0 denotes no additional http port is used."
         DEFVAL { 0 }
         ::= { apcpGlobalConfigGroup 3 }

    apcpAdditionalHttpSecurePort OBJECT-TYPE
         SYNTAX      Integer32 (1025..65535)
         MAX-ACCESS  read-write
         STATUS      current
         DESCRIPTION
                     "The additional captive portal authentication server port for 
                     HTTPS web connection. Valid range is from 1025-65535 or 443.
                     apcpAdditionalHttpSecurePort and apcpAdditionalHttpPort should
                     not have same value. 0 denotes no additional https port is used."
         DEFVAL { 0 }
         ::= { apcpGlobalConfigGroup 4 }

     apcpDebugFlag OBJECT-TYPE
          SYNTAX      Integer32(0..4)
          MAX-ACCESS  read-write
          STATUS      current
          DESCRIPTION
                      "Debug Flag to enable trace messages for Captive Portal 
                      Package."
          DEFVAL          { 0 }
          ::= { apcpGlobalConfigGroup 5 }

    --**************************************************************************************
    -- apCaptivePortalConfigGroup
    --
    --**************************************************************************************
    apCaptivePortalConfigGroup      OBJECT IDENTIFIER ::= {apcpConfigGroup 2 }

    apCaptivePortalTable OBJECT-TYPE
         SYNTAX      SEQUENCE OF ApCaptivePortalEntry
         MAX-ACCESS  not-accessible
         STATUS      current
         DESCRIPTION
                     "A table of config parms for instances of captive portal."
         ::= { apCaptivePortalConfigGroup 1 }

    apCaptivePortalEntry OBJECT-TYPE
         SYNTAX      ApCaptivePortalEntry
         MAX-ACCESS  not-accessible
         STATUS      current
         DESCRIPTION
                     "Captive Portal instance entry."
         INDEX       { apCaptivePortalInstanceId, apCaptivePortalConfigName}
         ::= { apCaptivePortalTable 1 }

    ApCaptivePortalEntry ::= SEQUENCE {
             apCaptivePortalInstanceId          Unsigned32,
             apCaptivePortalConfigName          DisplayString,
             apCaptivePortalAdminMode           INTEGER,
             apCaptivePortalProtocolMode        INTEGER,
             apCaptivePortalVerifyMode          INTEGER,
             apCaptivePortalURLRedirectMode     INTEGER,
             apCaptivePortalRedirectURL         DisplayString,
             apCaptivePortalAwayTime            Unsigned32,
             apCaptivePortalSessionTimeout      Unsigned32,
             apCaptivePortalUserUpRate          Unsigned32,
             apCaptivePortalUserDownRate        Unsigned32,
             apCaptivePortalUserGroup           DisplayString,
             apCaptivePortalUseRadiusSetting    INTEGER,   
             apCaptivePortalRadiusServerIPType  INTEGER,
             apCaptivePortalRadiusServer1       InetAddress,
             apCaptivePortalRadiusServer2       InetAddress,
             apCaptivePortalRadiusServer3       InetAddress,
             apCaptivePortalRadiusServer4       InetAddress,
--#IFDEF IPV6_MGMT
             apCaptivePortalIPv6RadiusServer1   InetAddress,
             apCaptivePortalIPv6RadiusServer2   InetAddress,
             apCaptivePortalIPv6RadiusServer3   InetAddress,
             apCaptivePortalIPv6RadiusServer4   InetAddress,
--#ENDIF
             apCaptivePortalRadiusServerKey1    DisplayString,
             apCaptivePortalRadiusServerKey2    DisplayString,
             apCaptivePortalRadiusServerKey3    DisplayString,
             apCaptivePortalRadiusServerKey4    DisplayString,
             apCaptivePortalRadiusAccounting    INTEGER,
             apCaptivePortalRowStatus           RowStatus
           }

    apCaptivePortalInstanceId      OBJECT-TYPE
         SYNTAX      Unsigned32(1..2)
         MAX-ACCESS  not-accessible
         STATUS      current
         DESCRIPTION
                     "The identifier associated with this instance of captive 
                     portal."
         ::= { apCaptivePortalEntry 1 }

    apCaptivePortalConfigName OBJECT-TYPE
         SYNTAX      DisplayString (SIZE(0..32))
         MAX-ACCESS  not-accessible
         STATUS      current
         DESCRIPTION
                     "The name, in alpha-numeric characters, assigned to this 
                     captive portal configuration."
         ::= { apCaptivePortalEntry 2 }

    apCaptivePortalAdminMode OBJECT-TYPE
         SYNTAX      INTEGER {
                     enable(1),
                     disable(2)
                  }
         MAX-ACCESS  read-write
         STATUS      current
         DESCRIPTION
                     "Enable or disable this instance of captive portal on 
                     the system."
         DEFVAL { disable }
         ::= { apCaptivePortalEntry 3 }

    apCaptivePortalProtocolMode OBJECT-TYPE
         SYNTAX      INTEGER {
                     http(1),
                     https(2)
                  }
         MAX-ACCESS  read-write
         STATUS      current
         DESCRIPTION
                     "The protocol mode to be used."
         DEFVAL { http }
         ::= { apCaptivePortalEntry 4 }

    apCaptivePortalVerifyMode OBJECT-TYPE
         SYNTAX      INTEGER {
                     guest(0),
                     local(1),
                     radius(2)
                  }
         MAX-ACCESS  read-write
         STATUS      current
         DESCRIPTION
                     "The type of user verification to perform."
         DEFVAL { guest }
         ::= { apCaptivePortalEntry 5 }

    apCaptivePortalURLRedirectMode OBJECT-TYPE
         SYNTAX      INTEGER {
                     enable(1),
                     disable(2)
                  }
         MAX-ACCESS  read-write
         STATUS      current
         DESCRIPTION
                     "Whether the captive portal should redirect newly 
                     authenticated clients to the configured URL. If this mode 
                     is disabled, the default locale specific welcome page is 
                     used. If enabled, the client is redirected to a configured 
                     URL."
         DEFVAL { disable }
         ::= { apCaptivePortalEntry 6 }

    apCaptivePortalRedirectURL OBJECT-TYPE
         SYNTAX      DisplayString (SIZE(0..256))
         MAX-ACCESS  read-write
         STATUS      current
         DESCRIPTION
                     "The URL to which the newly authenticated client is 
                     redirected if apCaptivePortalURLRedirectMode is enabled."
         ::= { apCaptivePortalEntry 7 }

    apCaptivePortalAwayTime OBJECT-TYPE
         SYNTAX      Unsigned32(0..1440)
         MAX-ACCESS  read-write
         STATUS      current
         DESCRIPTION
                      "This field indicates the expiry time in minutes for 
                      authenticated  clients that have been disassociated. The 
                      client is removed from captive portal client user list if
                      away time exceeds this configured value."
         DEFVAL { 60 }
         ::= { apCaptivePortalEntry 8 }

    apCaptivePortalSessionTimeout OBJECT-TYPE
         SYNTAX      Unsigned32(0..1440)
         MAX-ACCESS  read-write
         STATUS      current
         DESCRIPTION
                     "The session timeout in minutes. After this limit has been reached 
                     the user will be disconnected. If this value is set to 0, 
                     no timeout is enforced.This value is represented in 
                     minutes." 
         DEFVAL { 0 }
         ::= { apCaptivePortalEntry 9 }

    apCaptivePortalUserUpRate      OBJECT-TYPE
         SYNTAX      Unsigned32(0..300)
         MAX-ACCESS  read-write
         STATUS      current
         DESCRIPTION
                     "The maximum bandwidth, in megabytes per second, that a
                     client can transmit traffic when using Captive Portal. This 
                     setting limits the bandwidth at which the client can send 
                     data into the network. If this value is set to 0, no rate 
                     limiting is enforced."
         DEFVAL { 0 }
         ::= { apCaptivePortalEntry 10 }

    apCaptivePortalUserDownRate      OBJECT-TYPE
         SYNTAX      Unsigned32(0..300)
         MAX-ACCESS  read-write
         STATUS      current
         DESCRIPTION
                     "The maximum bandwidth, in megabytes per second, that a
                     client can receive traffic when using Captive Portal. This 
                     setting limits the bandwidth at which the client can 
                     receive data from the network. If this value is set to 0, 
                     no rate limiting is enforced."
         DEFVAL { 0 }
         ::= { apCaptivePortalEntry 11 }

    apCaptivePortalUserGroup          OBJECT-TYPE
         SYNTAX      DisplayString (SIZE(1..32))
         MAX-ACCESS  read-write
         STATUS      current
         DESCRIPTION
                     "This field indicates the group name assigned to the 
                     configuration to be used by local users."
          DEFVAL      { "Default" }
         ::= { apCaptivePortalEntry 12 }

    apCaptivePortalUseRadiusSetting OBJECT-TYPE
          SYNTAX    INTEGER {
                        enable(1),
                        disable(2)
                       }
          MAX-ACCESS  read-write
          STATUS      current
          DESCRIPTION
                      "Indicates to use global radius settings or CP instance 
                      radius settings."
          DEFVAL      { enable }
          ::= { apCaptivePortalEntry 13 }
                                     
    apCaptivePortalRadiusServerIPType OBJECT-TYPE
          SYNTAX      INTEGER {
                        ipv4(1),
                        ipv6(2)
                       }
          MAX-ACCESS  read-write
          STATUS      current
          DESCRIPTION
                      "Indicates the RADIUS server IP address type for AP 
                      Captive Portal."
          DEFVAL     { ipv4 }
          ::= { apCaptivePortalEntry 14 }

    apCaptivePortalRadiusServer1  OBJECT-TYPE
          SYNTAX              InetAddress
          MAX-ACCESS          read-write
          STATUS              current
          DESCRIPTION
                      "Indicates IPv4 address of the primary RADIUS server."
          ::= { apCaptivePortalEntry 15 }

    apCaptivePortalRadiusServer2  OBJECT-TYPE
          SYNTAX              InetAddress
          MAX-ACCESS          read-write
          STATUS              current
          DESCRIPTION
                      "Indicates IPv4 address of the first backup RADIUS server."
          ::= { apCaptivePortalEntry 16 }

    apCaptivePortalRadiusServer3  OBJECT-TYPE
          SYNTAX              InetAddress
          MAX-ACCESS          read-write
          STATUS              current
          DESCRIPTION
                      "Indicates IPv4 address of the second backup RADIUS server."
          ::= { apCaptivePortalEntry 17 }
          
    apCaptivePortalRadiusServer4  OBJECT-TYPE
          SYNTAX              InetAddress
          MAX-ACCESS          read-write
          STATUS              current
          DESCRIPTION
                      "Indicates IPv4 address of the third backup RADIUS server."
          ::= { apCaptivePortalEntry 18 }

--#IFDEF IPV6_MGMT
    apCaptivePortalIPv6RadiusServer1  OBJECT-TYPE
          SYNTAX              InetAddress
          MAX-ACCESS          read-write
          STATUS              current
          DESCRIPTION
                      "Indicates IPv6 address of the primary RADIUS server."
          ::= { apCaptivePortalEntry 19 }

    apCaptivePortalIPv6RadiusServer2  OBJECT-TYPE
          SYNTAX              InetAddress
          MAX-ACCESS          read-write
          STATUS              current
          DESCRIPTION
                      "Indicates IPv6 address of the first backup RADIUS server."
          ::= { apCaptivePortalEntry 20 }

    apCaptivePortalIPv6RadiusServer3  OBJECT-TYPE
          SYNTAX              InetAddress
          MAX-ACCESS          read-write
          STATUS              current
          DESCRIPTION
                      "Indicates IPv6 address of the second backup RADIUS server."
          ::= { apCaptivePortalEntry 21 }
          
    apCaptivePortalIPv6RadiusServer4  OBJECT-TYPE
          SYNTAX              InetAddress
          MAX-ACCESS          read-write
          STATUS              current
          DESCRIPTION
                      "Indicates IPv6 address of the third backup RADIUS server."
          ::= { apCaptivePortalEntry 22 }
--#ENDIF
          
    apCaptivePortalRadiusServerKey1     OBJECT-TYPE
         SYNTAX           DisplayString(SIZE(1..64))
         MAX-ACCESS       read-write
         STATUS           current
         DESCRIPTION
                     "Indicates the shared secret key for the AP Captive Portal
                      RADIUS server. The text you enter will be displayed as '*'
                      characters to prevent others from seeing the RADIUS key as
                      you type. Default value of RADIUS key is NULL."
        ::= { apCaptivePortalEntry 23 }

    apCaptivePortalRadiusServerKey2     OBJECT-TYPE
         SYNTAX           DisplayString(SIZE(1..64))
         MAX-ACCESS       read-write
         STATUS           current
         DESCRIPTION
                     "Indicates the shared secret key for the AP Captive Portal
                      RADIUS server. The text you enter will be displayed as '*'
                      characters to prevent others from seeing the RADIUS key as
                      you type. Default value of RADIUS key is NULL."
        ::= { apCaptivePortalEntry 24 }
        
    apCaptivePortalRadiusServerKey3     OBJECT-TYPE
         SYNTAX           DisplayString(SIZE(1..64))
         MAX-ACCESS       read-write
         STATUS           current
         DESCRIPTION
                     "Indicates the shared secret key for the AP Captive Portal
                      RADIUS server. The text you enter will be displayed as '*'
                      characters to prevent others from seeing the RADIUS key as
                      you type. Default value of RADIUS key is NULL."
        ::= { apCaptivePortalEntry 25 }

    apCaptivePortalRadiusServerKey4     OBJECT-TYPE
         SYNTAX           DisplayString(SIZE(1..64))
         MAX-ACCESS       read-write
         STATUS           current
         DESCRIPTION
                     "Indicates the shared secret key for the AP Captive Portal
                      RADIUS server. The text you enter will be displayed as '*'
                      characters to prevent others from seeing the RADIUS key as
                      you type. Default value of RADIUS key is NULL."
        ::= { apCaptivePortalEntry 26 }

    apCaptivePortalRadiusAccounting  OBJECT-TYPE
          SYNTAX    INTEGER {
                        enable(1),
                        disable(2)
                       }
          MAX-ACCESS  read-write
          STATUS      current
          DESCRIPTION
                      "Indicates RADIUS Accounting is enabled or not."
          DEFVAL      { disable }
          ::= { apCaptivePortalEntry 27 }

    apCaptivePortalRowStatus OBJECT-TYPE
         SYNTAX      RowStatus 
         MAX-ACCESS  read-create
         STATUS      current
         DESCRIPTION
                     "The captive portal instance status. 

                     Supported values:
                     active(1)      - This status is displayed after a valid 
                                      Captive Portal instance is created.
                     createAndGo(4) - Set to this value to create a new 
                                      Captive Portal instance.
                     destroy(6)     - Set to this value to remove an 
                                      existing Captive Portal instance."
         ::= { apCaptivePortalEntry 28 }                  

    --**************************************************************************************
    --    apcpConfigWebLocaleGroup
    --**************************************************************************************

    apcpConfigWebLocaleGroup          OBJECT IDENTIFIER ::= {  apcpConfigGroup 3 }

    apcpConfigWebLocaleTable OBJECT-TYPE
         SYNTAX      SEQUENCE OF ApcpConfigWebLocaleEntry
         MAX-ACCESS  not-accessible
         STATUS      current
         DESCRIPTION
                     "This database is used to web config."
         ::= { apcpConfigWebLocaleGroup 1 }

    apcpConfigWebLocaleEntry OBJECT-TYPE
         SYNTAX      ApcpConfigWebLocaleEntry
         MAX-ACCESS  not-accessible
         STATUS      current
         DESCRIPTION
                     "Captive Portal instance client status entry."
         INDEX       {apcpConfigWebLocaleId,apcpConfigWebLocaleConfigName,apcpConfigWebLocaleInstanceName}
         ::= { apcpConfigWebLocaleTable 1 }

    ApcpConfigWebLocaleEntry ::= SEQUENCE {
                         apcpConfigWebLocaleId
                           Unsigned32,
                         apcpConfigWebLocaleConfigName
                           DisplayString,
                        apcpConfigWebLocaleInstanceName
                           DisplayString,
                        apcpConfigWebLocaleInstanceId
                           Unsigned32,
                        apcpConfigWebLocaleBackgroundImageName
                           DisplayString,
                        apcpConfigWebLocaleLogoImageName
                           DisplayString,
                        apcpConfigWebLocaleFontList
                           DisplayString,
                        apcpConfigWebLocaleBrowserTitle 
                           DisplayString,
                        apcpConfigWebLocaleTitleText      
                           DisplayString,
                        apcpConfigWebLocaleForegroundColour
                           DisplayString,
                        apcpConfigWebLocaleBackgroundColour
                           DisplayString,
                        apcpConfigWebLocaleSeperatorColour
                           DisplayString,
                        apcpConfigWebLocaleLabel
                           DisplayString,
                        apcpConfigWebLocaleLocale
                           DisplayString,
                        apcpConfigWebLocaleAccountImageName
                           DisplayString,
                        apcpConfigWebLocaleAccountLabel       
                           DisplayString,
                        apcpConfigWebLocaleUserLabel       
                           DisplayString,
                        apcpConfigWebLocalePasswordLabel       
                           DisplayString,
                        apcpConfigWebLocaleButtonLabel       
                           DisplayString,
                        apcpConfigWebLocaleInstructionalText       
                           DisplayString,
                        apcpConfigWebLocaleAUPText       
                           DisplayString,
                        apcpConfigWebLocaleAcceptText       
                           DisplayString,
                        apcpConfigWebLocaleNoAcceptText       
                           DisplayString,
                        apcpConfigWebLocaleWIPMsgText       
                           DisplayString,
                        apcpConfigWebLocaleDeniedMsgText       
                           DisplayString,
                        apcpConfigWebLocaleResourceMsgText       
                           DisplayString,
                        apcpConfigWebLocaleTimeoutMsgText       
                           DisplayString,
                        apcpConfigWebLocaleWelcomeTitleText      
                           DisplayString,
                        apcpConfigWebLocaleWelcomeText      
                           DisplayString,
                        apcpConfigWebLocaleRowStatus
                           RowStatus
           }
   
    apcpConfigWebLocaleId OBJECT-TYPE
         SYNTAX      Unsigned32(1..3)
         MAX-ACCESS  not-accessible
         STATUS      current
         DESCRIPTION
                     "Unique identifier used to index this locale within its 
                     assigned captive portal configuration."
         ::= { apcpConfigWebLocaleEntry 1 }
               
   apcpConfigWebLocaleConfigName OBJECT-TYPE
         SYNTAX      DisplayString(SIZE(0..32))
         MAX-ACCESS  not-accessible
         STATUS      current
         DESCRIPTION
                     "Unique name used to index this locale within its 
                     assigned captive portal configuration."
         ::= { apcpConfigWebLocaleEntry 2 }      
   
   apcpConfigWebLocaleInstanceName OBJECT-TYPE
         SYNTAX      DisplayString(SIZE(0..32))
         MAX-ACCESS  not-accessible
         STATUS      current
         DESCRIPTION
                     "Unique name associated with captive portal instance." 
         ::= { apcpConfigWebLocaleEntry 3 }      

   apcpConfigWebLocaleInstanceId OBJECT-TYPE
         SYNTAX      Unsigned32
         MAX-ACCESS  read-only
         STATUS      current
         DESCRIPTION
                     "The identifier associated with Captive Portal instance."
         ::= { apcpConfigWebLocaleEntry 4 }

   apcpConfigWebLocaleBackgroundImageName OBJECT-TYPE
         SYNTAX      DisplayString(SIZE(5..32))
         MAX-ACCESS  read-write
         STATUS      current
         DESCRIPTION
                     "Optional background image. Recommended image should be 
                     5KB max,GIF or JPG format."
         DEFVAL      { "brcm_bkg.jpg" }
         ::= { apcpConfigWebLocaleEntry 5 }

   apcpConfigWebLocaleLogoImageName OBJECT-TYPE
         SYNTAX      DisplayString(SIZE(5..32))
         MAX-ACCESS  read-write
         STATUS      current
         DESCRIPTION
                     "File name of an image used for branding purposes, such as 
                     the company logo. Image should be 5KB max, 200x200 pixels,
                     GIF or JPG format."
         DEFVAL      { "brcm_logo.gif" }
         ::= { apcpConfigWebLocaleEntry 6 }

   apcpConfigWebLocaleFontList OBJECT-TYPE
         SYNTAX      DisplayString(SIZE(1..512))
         MAX-ACCESS  read-write
         STATUS      current
         DESCRIPTION
                     "Prioritized, comma separated, list of fonts to be used by 
                     the client brower. Font specifications are necessary for 
                     proper locale display."
         DEFVAL      { "\'MS UI Gothic\', arial, sans-serif" }
         ::= { apcpConfigWebLocaleEntry 7 }

   apcpConfigWebLocaleBrowserTitle  OBJECT-TYPE
         SYNTAX      DisplayString(SIZE(1..128))
         MAX-ACCESS  read-write
         STATUS      current
         DESCRIPTION
                     "Enter the text to display on the client Web browser 
                     title bar or tab."
         DEFVAL      { "Captive Portal" }
         ::= { apcpConfigWebLocaleEntry 8 }

   apcpConfigWebLocaleTitleText  OBJECT-TYPE
         SYNTAX      DisplayString(SIZE(1..128))
         MAX-ACCESS  read-write
         STATUS      current
         DESCRIPTION
                     "Enter the text for use to greet the users." 
         DEFVAL      { "Welcome to the Wireless Network" }
         ::= { apcpConfigWebLocaleEntry 9 }

   apcpConfigWebLocaleForegroundColour  OBJECT-TYPE
         SYNTAX      DisplayString(SIZE(1..32))
         MAX-ACCESS  read-write
         STATUS      current
         DESCRIPTION
                     "Foreground color of login page using a well known color 
                     name or RGB value."
         DEFVAL      { "#999999" }
         ::= { apcpConfigWebLocaleEntry 10 }

   apcpConfigWebLocaleBackgroundColour  OBJECT-TYPE
         SYNTAX      DisplayString(SIZE(1..32))
         MAX-ACCESS  read-write
         STATUS      current
         DESCRIPTION
                     "Background color of login page using a well known color 
                     name or RGB value."
         DEFVAL      { "#BFBFBF" }
         ::= { apcpConfigWebLocaleEntry 11 }

   apcpConfigWebLocaleSeperatorColour  OBJECT-TYPE
         SYNTAX      DisplayString(SIZE(1..32))
         MAX-ACCESS  read-write
         STATUS      current
         DESCRIPTION
                     "Separator bar color of the login page using a well known 
                     color name or RGB value."
         DEFVAL      { "#BFBFBF" }
         ::= { apcpConfigWebLocaleEntry 12 }

   apcpConfigWebLocaleLabel  OBJECT-TYPE
         SYNTAX      DisplayString(SIZE(1..32))
         MAX-ACCESS  read-write
         STATUS      current
         DESCRIPTION
                     "Label text for tab and links identifying the language."
         DEFVAL      { "English" }
         ::= { apcpConfigWebLocaleEntry 13 }

   apcpConfigWebLocaleLocale  OBJECT-TYPE
         SYNTAX      DisplayString(SIZE(1..32))
         MAX-ACCESS  read-write
         STATUS      current
         DESCRIPTION
                     "Used to identify the users language of choice for 
                     customized content."
         DEFVAL      { "en" }
         ::= { apcpConfigWebLocaleEntry 14 }

   apcpConfigWebLocaleAccountImageName OBJECT-TYPE
         SYNTAX      DisplayString(SIZE(5..32))
         MAX-ACCESS  read-write
         STATUS      current
         DESCRIPTION
                     "Account image that is stretched across the account column.
                     Recommended image should be 5KB max ,GIF or JPG format."
         DEFVAL      { "login_key.jpg" }
         ::= { apcpConfigWebLocaleEntry 15 }

   apcpConfigWebLocaleAccountLabel     OBJECT-TYPE
         SYNTAX      DisplayString(SIZE(1..32))
         MAX-ACCESS  read-write
         STATUS      current
         DESCRIPTION
                     "General label text used to identify the account type."
         DEFVAL      { "Enter your Username" }
         ::= { apcpConfigWebLocaleEntry 16 }

   apcpConfigWebLocaleUserLabel        OBJECT-TYPE
         SYNTAX      DisplayString(SIZE(1..32))
         MAX-ACCESS  read-write
         STATUS      current
         DESCRIPTION
                     "Enter the text to display next to the field where the 
                     user enters the username."
         DEFVAL      { "Username:" }
         ::= { apcpConfigWebLocaleEntry 17 }

   apcpConfigWebLocalePasswordLabel          OBJECT-TYPE
         SYNTAX      DisplayString(SIZE(1..64))
         MAX-ACCESS  read-write
         STATUS      current
         DESCRIPTION
                     "Enter the text to display next to the field where the 
                     user enters the password."
         DEFVAL      { "Password:" }
         ::= { apcpConfigWebLocaleEntry 18 }

   apcpConfigWebLocaleButtonLabel           OBJECT-TYPE
         SYNTAX      DisplayString(SIZE(2..32))
         MAX-ACCESS  read-write
         STATUS      current
         DESCRIPTION
                     "Enter the text to display on the button the user clicks 
                     to connect to the network."
         DEFVAL      { "Connect" }
         ::= { apcpConfigWebLocaleEntry 19 }

   apcpConfigWebLocaleInstructionalText      OBJECT-TYPE
         SYNTAX      DisplayString(SIZE(1..256))
         MAX-ACCESS  read-write
         STATUS      current
         DESCRIPTION
                     "Text used to provide instructional content."
         DEFVAL      { "To start using this service, enter your credentials and click the Connect button." }
         ::= { apcpConfigWebLocaleEntry 20 }


   apcpConfigWebLocaleAUPText          OBJECT-TYPE
         SYNTAX      DisplayString(SIZE(1..4096))
         MAX-ACCESS  read-write
         STATUS      current
         DESCRIPTION
                     "Enter the text to display in the Acceptance Use Policy field. 
                     The acceptance use policy instructs users about the 
                     conditions under which they are allowed to access the 
                     network."
         DEFVAL      { "Acceptance Use Policy" }
         ::= { apcpConfigWebLocaleEntry 21 }

   apcpConfigWebLocaleAcceptText          OBJECT-TYPE
         SYNTAX      DisplayString(SIZE(1..128))
         MAX-ACCESS  read-write
         STATUS      current
         DESCRIPTION
                     "Enter the text to display next to the box that the user 
                     must select to indicate that he or she accepts the terms 
                     of use.Acceptance."
         DEFVAL      { "Check here to indicate that you have read and accepted the Acceptance Use Policy." } 
         ::= { apcpConfigWebLocaleEntry 22 }

   apcpConfigWebLocaleNoAcceptText       OBJECT-TYPE
         SYNTAX      DisplayString(SIZE(1..128))
         MAX-ACCESS  read-write
         STATUS      current
         DESCRIPTION
                     "Text used to indicate that authentication failed because 
                     the client did not acknowledge the AUP."
         DEFVAL      { "Error: You must acknowledge the Acceptance Use Policy before connecting!" }
         ::= { apcpConfigWebLocaleEntry 23 }

   apcpConfigWebLocaleWIPMsgText       OBJECT-TYPE
         SYNTAX      DisplayString(SIZE(1..128))
         MAX-ACCESS  read-write
         STATUS      current
         DESCRIPTION
                     "Text used while waiting for user verification."
         DEFVAL      { "Connecting, please be patient" }
         ::= { apcpConfigWebLocaleEntry 24 }

   apcpConfigWebLocaleDeniedMsgText    OBJECT-TYPE
         SYNTAX      DisplayString(SIZE(1..128))
         MAX-ACCESS  read-write
         STATUS      current
         DESCRIPTION
                     "Enter the text to display when the user does not provide 
                     valid authentication information. This message displays 
                     after the user clicks the button to connect to the 
                     network."
         DEFVAL      { "Error: Invalid Credentials, please try again!" }   
         ::= { apcpConfigWebLocaleEntry 25 }

   apcpConfigWebLocaleResourceMsgText   OBJECT-TYPE
         SYNTAX      DisplayString(SIZE(1..128))
         MAX-ACCESS  read-write
         STATUS      obsolete
         DESCRIPTION
                     "Enter the text to display when the system has rejected 
                     authentication due to system  resource limitations. This 
                     message displays after the user clicks the button  to 
                     connect to the network."
         DEFVAL      { "Error: Limited Resources, please reconnect and try again later!" } 
         ::= { apcpConfigWebLocaleEntry 26 }

   apcpConfigWebLocaleTimeoutMsgText  OBJECT-TYPE
         SYNTAX      DisplayString(SIZE(1..128))
         MAX-ACCESS  read-write
         STATUS      obsolete
         DESCRIPTION
                     "Enter the text to display when the system has rejected 
                     authentication because the authentication transaction took
                     too long. This could be due to user input time, or a 
                     timeout due to the overall transaction."
         DEFVAL      { "Error: Timed Out, please reconnect and try again!" }
         ::= { apcpConfigWebLocaleEntry 27 }

   apcpConfigWebLocaleWelcomeTitleText    OBJECT-TYPE
         SYNTAX      DisplayString(SIZE(1..128))
         MAX-ACCESS  read-write
         STATUS      current
         DESCRIPTION
                     "Enter the title to display to greet the user after he or 
                     she successfully connects to the network."
         DEFVAL      { "Congratulations!" }
         ::= { apcpConfigWebLocaleEntry 28 }

   apcpConfigWebLocaleWelcomeText     OBJECT-TYPE
         SYNTAX      DisplayString(SIZE(1..256))
         MAX-ACCESS  read-write
         STATUS      current
         DESCRIPTION
                     "Enter the additional text to display when the user is 
                     successfully connected to the network"
         DEFVAL      { "You are now authorized and connected to the network." }
         ::= { apcpConfigWebLocaleEntry 29 }

   apcpConfigWebLocaleRowStatus OBJECT-TYPE
         SYNTAX      RowStatus 
         MAX-ACCESS  read-create
         STATUS      current
         DESCRIPTION
                     "The captive portal web locale instance status. 
                     Supported values:
                     active(1)      - This status is displayed after a valid 
                                      Captive Portal instance is created.
                     createAndGo(4) - Set to this value to create a new 
                                      Captive Portal instance.
                     destroy(6)     - Set to this value to remove an 
                                      existing Captive Portal instance."
         ::= { apcpConfigWebLocaleEntry 30 }

    --**************************************************************************************
    --    apcpLocalUserDatabaseGroup
    --**************************************************************************************
    
    apcpLocalUserDatabaseGroup     OBJECT IDENTIFIER ::= { apcpConfigGroup 4 }

    -- ---------------------------------
    -- apcpLocalUserGroupTable
    -- ---------------------------------

    apcpLocalUserGroupTable OBJECT-TYPE
         SYNTAX      SEQUENCE OF ApcpLocalUserGroupEntry  
         MAX-ACCESS  not-accessible
         STATUS      current
         DESCRIPTION
                     "A table of group definitions for the local users. This 
                     database is used by captive portal instances and local 
                     users if the verification mode is set to LOCAL."
         ::= { apcpLocalUserDatabaseGroup 1 }

    apcpLocalUserGroupEntry OBJECT-TYPE
         SYNTAX      ApcpLocalUserGroupEntry
         MAX-ACCESS  not-accessible
         STATUS      current
         DESCRIPTION
                     "The user group entry."
         INDEX       { apcpLocalUserGroupName }
         ::= { apcpLocalUserGroupTable 1 }

    ApcpLocalUserGroupEntry ::= SEQUENCE {
             apcpLocalUserGroupName           DisplayString,
             apcpLocalUserGroupRowStatus      RowStatus
           }

    apcpLocalUserGroupName OBJECT-TYPE
         SYNTAX      DisplayString (SIZE(1..32))
         MAX-ACCESS  not-accessible
         STATUS      current
         DESCRIPTION
                     "The user group name, limited to alpha-numeric strings 
                     (including the '-' and '_' characters)."
         ::= { apcpLocalUserGroupEntry 1 }

    apcpLocalUserGroupRowStatus OBJECT-TYPE
         SYNTAX      RowStatus 
         MAX-ACCESS  read-create
         STATUS      current
         DESCRIPTION
                     "The user group entry status. 

                     Supported values:
                     active(1)      - This status is displayed after a valid 
                                      user group is created.
                     createAndGo(4) - Set to this value to create a new user
                                      group.
                     destroy(6)     - Set to this value to remove an existing 
                                      user group."
         ::= { apcpLocalUserGroupEntry 2 }

    -- ---------------------------------
    -- apcpLocalUserTable
    -- ---------------------------------

    apcpLocalUserTable OBJECT-TYPE
         SYNTAX      SEQUENCE OF ApcpLocalUserEntry  
         MAX-ACCESS  not-accessible
         STATUS      current
         DESCRIPTION
                     "A table of user definitions for the local database. This 
                     database is used by a captive portal instance if its 
                     verification mode is set to LOCAL."
         ::= { apcpLocalUserDatabaseGroup 2 }

    apcpLocalUserEntry OBJECT-TYPE
         SYNTAX      ApcpLocalUserEntry
         MAX-ACCESS  not-accessible
         STATUS      current
         DESCRIPTION
                     "The local user entry."
         INDEX       { apcpLocalUserName }
         ::= { apcpLocalUserTable 1 }

    ApcpLocalUserEntry ::= SEQUENCE {
                        apcpLocalUserName              DisplayString,
                        apcpLocalUserPassword          DisplayString,
                        apcpLocalUserGroup             DisplayString,
                        apcpLocalUserAwayTimeout       Integer32,
                        apcpLocalUserMaxBandwidthUp    Unsigned32,
                        apcpLocalUserMaxBandwidthDown  Unsigned32,
                        apcpLocalUserRowStatus         RowStatus
           }

    apcpLocalUserName OBJECT-TYPE
         SYNTAX      DisplayString (SIZE(1..32))
         MAX-ACCESS  not-accessible
         STATUS      current
         DESCRIPTION
                     "The user name, limited to alpha-numeric strings 
                     (including the '-' and '_' characters)."

         ::= { apcpLocalUserEntry 1 }

    apcpLocalUserPassword OBJECT-TYPE
         SYNTAX      DisplayString (SIZE(8..64))
         MAX-ACCESS  read-write
         STATUS      current
         DESCRIPTION
                     "The user password is set of alphanumeric characters and 
                     allowed special characters  ` ~ ! @ # $ % ^ & * ( ) - _+ 
                     = { } [ ] | ; : , < > . ?. This object will return an 
                     empty string even if a password is set."    
                     
         ::= { apcpLocalUserEntry 2 }

    apcpLocalUserAwayTimeout OBJECT-TYPE
         SYNTAX      Integer32 (0..1440) 
         MAX-ACCESS  read-write
         STATUS      current
         DESCRIPTION
                     "The away timeout in minutes. After this limit is 
                     reached, the user is disconnected.If this value is set to 
                     0, the default value for the captive portal is used."
         DEFVAL { 0 }
         ::= { apcpLocalUserEntry 3 }

    apcpLocalUserMaxBandwidthUp OBJECT-TYPE
         SYNTAX      Unsigned32(0..300)
         MAX-ACCESS  read-write
         STATUS      current
         DESCRIPTION
                     "The maximum bandwidth, in megabytes per second, that the
                     user can transmit traffic when using Captive Portal. This 
                     setting limits the bandwidth at which the user can send 
                     data into the network. If this value is set to 0, no rate 
                     limiting is enforced."
         DEFVAL { 0 }
         ::= { apcpLocalUserEntry 4 }

    apcpLocalUserMaxBandwidthDown OBJECT-TYPE
         SYNTAX      Unsigned32(0..300)
         MAX-ACCESS  read-write
         STATUS      current
         DESCRIPTION
                     "The maximum bandwidth, in megabytes per second, that the
                     user can receive traffic when using Captive Portal. This 
                     setting limits the bandwidth at which the user can send 
                     data into the network. If this value is set to 0, no rate 
                     limiting is enforced."
         DEFVAL { 0 }
         ::= { apcpLocalUserEntry 5 }

    apcpLocalUserRowStatus OBJECT-TYPE
         SYNTAX      RowStatus 
         MAX-ACCESS  read-create
         STATUS      current
         DESCRIPTION
                     "The user entry status. 

                     Supported values:
                     active(1)      - This status is displayed after a valid 
                                      user is created.
                     createAndGo(4) - Set to this value to create a new user.
                     destroy(6)     - Set to this value to remove an existing 
                                      user."
         ::= { apcpLocalUserEntry 6 }

    -- ---------------------------------
    -- apcpLocalUserGroupAssociationTable
    -- ---------------------------------

    apcpLocalUserGroupAssociationTable OBJECT-TYPE
         SYNTAX      SEQUENCE OF ApcpLocalUserGroupAssociationEntry  
         MAX-ACCESS  not-accessible
         STATUS      current
         DESCRIPTION
                     "The mapping of local user assignments to a user group."
         ::= { apcpLocalUserDatabaseGroup 3 }

    apcpLocalUserGroupAssociationEntry OBJECT-TYPE
         SYNTAX      ApcpLocalUserGroupAssociationEntry
         MAX-ACCESS  not-accessible
         STATUS      current
         DESCRIPTION
                     "The local user group association entry."
         INDEX       { apcpLocalUserGroupAssociationGroupName, apcpLocalUserGroupAssociationUserName }
         ::= { apcpLocalUserGroupAssociationTable 1 }

    ApcpLocalUserGroupAssociationEntry ::= SEQUENCE {
                        apcpLocalUserGroupAssociationGroupName
                           DisplayString,
                        apcpLocalUserGroupAssociationUserName
                           DisplayString,                           
                        apcpLocalUserGroupAssociationRowStatus
                           RowStatus
           }

    apcpLocalUserGroupAssociationGroupName OBJECT-TYPE
         SYNTAX      DisplayString (SIZE(1..32))
         MAX-ACCESS  not-accessible
         STATUS      current
         DESCRIPTION
                     "The user group association entry group name."
         ::= { apcpLocalUserGroupAssociationEntry 1 }

    apcpLocalUserGroupAssociationUserName OBJECT-TYPE
         SYNTAX      DisplayString (SIZE(1..32))
         MAX-ACCESS  not-accessible
         STATUS      current
         DESCRIPTION
                     "The user name associated with user group association entry."
         ::= { apcpLocalUserGroupAssociationEntry 2 }

    
    apcpLocalUserGroupAssociationRowStatus OBJECT-TYPE
         SYNTAX      RowStatus 
         MAX-ACCESS  read-create
         STATUS      current
         DESCRIPTION
                     "The local user to user group association entry status. 

                     Supported values:
                     active(1)      - This status is displayed after a valid 
                                      association between a local user and a 
                                      user group is created.
                     createAndGo(4) - Set to this value to create a new 
                                      association between a local user and a 
                                      user group.
                     destroy(6)     - Set to this value to remove an existing 
                                      association between a local user and a 
                                      user group."
         ::= { apcpLocalUserGroupAssociationEntry 3 }

    --**************************************************************************************
    --    apcpVAPConfigGroup
    --**************************************************************************************
    
    apcpVAPConfigGroup     OBJECT IDENTIFIER ::= { apcpConfigGroup 5 }

    -- ---------------------------------
    -- apcpVAPConfigGroupTable
    -- ---------------------------------

    apcpVAPConfigGroupTable OBJECT-TYPE
         SYNTAX      SEQUENCE OF ApcpVAPConfigGroupEntry  
         MAX-ACCESS  not-accessible
         STATUS      current
         DESCRIPTION
                     "A table of group definitions for the local users. This 
                     database is used by captive portal instances and local 
                     users if the verification mode is set to LOCAL."
         ::= { apcpVAPConfigGroup 1 }

    apcpVAPConfigGroupEntry OBJECT-TYPE
         SYNTAX      ApcpVAPConfigGroupEntry
         MAX-ACCESS  not-accessible
         STATUS      current
         DESCRIPTION
                     "The user group entry."
         INDEX       { apcpVAPConfigGroupIndex,apcpVAPConfigGroupRadioIndex }
         ::= { apcpVAPConfigGroupTable 1 }

    ApcpVAPConfigGroupEntry ::= SEQUENCE {
             apcpVAPConfigGroupIndex               DisplayString,
             apcpVAPConfigGroupRadioIndex          DisplayString,
             apcpVAPConfigGroupCPIntance           DisplayString
           }

    apcpVAPConfigGroupIndex OBJECT-TYPE
         SYNTAX      DisplayString
         MAX-ACCESS  not-accessible
         STATUS      current
         DESCRIPTION
                     "The VAP interface entry index, it can take values from 
                     vap0 to vap15."
         ::= { apcpVAPConfigGroupEntry 1 }  
         
    apcpVAPConfigGroupRadioIndex OBJECT-TYPE
         SYNTAX      DisplayString 
         MAX-ACCESS  not-accessible
         STATUS      current
         DESCRIPTION
                     "The radio interface entry index, it can take values 
                     from wlan0 to wlan1."
         ::= { apcpVAPConfigGroupEntry 2 }


    apcpVAPConfigGroupCPIntance OBJECT-TYPE
         SYNTAX      DisplayString
         MAX-ACCESS  read-write
         STATUS      current
         DESCRIPTION
                     "The name of captive portal instance, assigned to this 
                     VAP/radio configuration."
         ::= { apcpVAPConfigGroupEntry 3 }
  
   --**************************************************************************************
   --    apcpStatusGroup
   --**************************************************************************************
   
   apcpStatusGroup                      OBJECT IDENTIFIER ::= { apCaptivePortal 2 }

    --**************************************************************************************
    --    apcpAuthenticatedClientStatusGroup
    --**************************************************************************************
    
    apcpAuthenticatedClientStatusGroup            OBJECT IDENTIFIER ::= { apcpStatusGroup 1 }

    apcpAuthenticatedClientStatusTable OBJECT-TYPE
         SYNTAX      SEQUENCE OF ApcpAuthenticatedClientStatusEntry  
         MAX-ACCESS  not-accessible
         STATUS      current
         DESCRIPTION
                     "This database is used to report status of authenticated 
                     clients."
         ::= { apcpAuthenticatedClientStatusGroup 1 }

    apcpAuthenticatedClientStatusEntry OBJECT-TYPE
         SYNTAX      ApcpAuthenticatedClientStatusEntry
         MAX-ACCESS  not-accessible
         STATUS      current
         DESCRIPTION
                     "Captive portal authenticated client status entry."
         INDEX       { apcpAuthenticatedClientMacAddress }
         ::= { apcpAuthenticatedClientStatusTable 1 }

    ApcpAuthenticatedClientStatusEntry ::= SEQUENCE {
                         apcpAuthenticatedClientMacAddress
                           MacAddress,
                         apcpAuthenticatedClientIpAddress
                           DisplayString,
                         apcpAuthenticatedClientUserName
                           DisplayString,                                      
                         apcpAuthenticatedClientProtocolMode
                           INTEGER,                                      
                         apcpAuthenticatedClientVerifyMode
                           INTEGER,                                      
                         apcpAuthenticatedClientVapIndex
                           InterfaceIndex,                                      
                         apcpAuthenticatedClientRadioIndex
                           InterfaceIndex,                            
                         apcpAuthenticatedClientCPInstanceId
                           Integer32,                                      
                         apcpAuthenticatedClientSessionTimeout
                           DisplayString,
                         apcpAuthenticatedClientAwayTimeout
                           DisplayString,
                         apcpAuthenticatedClientInitalURL
                           DisplayString,
                         apcpAuthenticatedClientRxPackets
                           Unsigned32,
                         apcpAuthenticatedClientTxPackets
                           Unsigned32,
                         apcpAuthenticatedClientRxBytes
                           Unsigned32,
                         apcpAuthenticatedClientTxBytes
                           Unsigned32
           }

    apcpAuthenticatedClientMacAddress OBJECT-TYPE
         SYNTAX      MacAddress
         MAX-ACCESS  not-accessible
         STATUS      current
         DESCRIPTION
                     "The MAC address of authenticated client." 
                     ::= { apcpAuthenticatedClientStatusEntry 1 }

    apcpAuthenticatedClientIpAddress OBJECT-TYPE
         SYNTAX      DisplayString
         MAX-ACCESS  read-only
         STATUS      current
         DESCRIPTION
                     "The IP address of the authenticated client."
         ::= { apcpAuthenticatedClientStatusEntry 2 }

    apcpAuthenticatedClientUserName OBJECT-TYPE
         SYNTAX      DisplayString (SIZE(1..32))
         MAX-ACCESS  read-only
         STATUS      current
         DESCRIPTION
                     "User name (or Guest ID) of the connected client."
         ::= { apcpAuthenticatedClientStatusEntry 3 }

    apcpAuthenticatedClientProtocolMode OBJECT-TYPE
         SYNTAX      INTEGER {
                     http(1),
                     https(2)
                  }
         MAX-ACCESS  read-only
         STATUS      current
         DESCRIPTION
                     "Protocol mode used for the client authentication."
         ::= { apcpAuthenticatedClientStatusEntry 4 }

    apcpAuthenticatedClientVerifyMode OBJECT-TYPE
         SYNTAX      INTEGER {
                     guest(0),
                     local(1),
                     radius(2)
                  }
         MAX-ACCESS  read-only
         STATUS      current
         DESCRIPTION
                     "Type of user verification performed for the client 
                     authentication."
         ::= { apcpAuthenticatedClientStatusEntry 5 }

    apcpAuthenticatedClientVapIndex OBJECT-TYPE
         SYNTAX      InterfaceIndex
         MAX-ACCESS  read-only
         STATUS      current
         DESCRIPTION
                     "The VAP interface on which the client was authenticated."
         ::= { apcpAuthenticatedClientStatusEntry 6 }

    apcpAuthenticatedClientRadioIndex OBJECT-TYPE
         SYNTAX      InterfaceIndex
         MAX-ACCESS  read-only
         STATUS      current
         DESCRIPTION
                     "The radio index on which the client was authenticated." 
         ::= { apcpAuthenticatedClientStatusEntry 7 }

    apcpAuthenticatedClientCPInstanceId     OBJECT-TYPE
         SYNTAX      Integer32
         MAX-ACCESS  read-only
         STATUS      current
         DESCRIPTION
                     "The captive portal instance on which the client is 
                     authenticated." 
         ::= { apcpAuthenticatedClientStatusEntry 8 }

    apcpAuthenticatedClientSessionTimeout OBJECT-TYPE
         SYNTAX      DisplayString
         MAX-ACCESS  read-only
         STATUS      current
         DESCRIPTION
                     "The time remaining (in seconds) for the client to get unauthorized by the AP."
         ::= { apcpAuthenticatedClientStatusEntry 9 }

    apcpAuthenticatedClientAwayTimeout OBJECT-TYPE
         SYNTAX      DisplayString
         MAX-ACCESS  read-only
         STATUS      current
         DESCRIPTION
                     "The time remaining (in seconds) for the client to get disassociated  
                     by AP."
         ::= { apcpAuthenticatedClientStatusEntry 10 }

    apcpAuthenticatedClientInitalURL OBJECT-TYPE
          SYNTAX      DisplayString (SIZE(0..256))
         MAX-ACCESS  read-only
         STATUS      deprecated
         DESCRIPTION
                     "The URL received in the initial request."
         ::= { apcpAuthenticatedClientStatusEntry 11 }

    apcpAuthenticatedClientRxPackets OBJECT-TYPE
         SYNTAX      Unsigned32
         MAX-ACCESS  read-only
         STATUS      current
         DESCRIPTION
                     "The number of packets received by the client"
         ::= { apcpAuthenticatedClientStatusEntry 12 }

    apcpAuthenticatedClientTxPackets OBJECT-TYPE
         SYNTAX      Unsigned32
         MAX-ACCESS  read-only
         STATUS      current
         DESCRIPTION
                     "The number of packets transmitted by the client"
         ::= { apcpAuthenticatedClientStatusEntry 13 }

    apcpAuthenticatedClientRxBytes OBJECT-TYPE
         SYNTAX      Unsigned32
         MAX-ACCESS  read-only
         STATUS      current
         DESCRIPTION
                     "The number of bytes received by the client"
         ::= { apcpAuthenticatedClientStatusEntry 14 }

    apcpAuthenticatedClientTxBytes OBJECT-TYPE
         SYNTAX      Unsigned32
         MAX-ACCESS  read-only
         STATUS      current
         DESCRIPTION
                     "The number of bytes transmitted by the client"
         ::= { apcpAuthenticatedClientStatusEntry 15 }

    --**************************************************************************************
    --    apcpAuthFailedClientStatusGroup
    --**************************************************************************************
    
    apcpAuthFailedClientStatusGroup            OBJECT IDENTIFIER ::= { apcpStatusGroup 2 }

    apcpAuthFailedClientStatusTable OBJECT-TYPE
         SYNTAX      SEQUENCE OF ApcpAuthFailedClientStatusEntry  
         MAX-ACCESS  not-accessible
         STATUS      current
         DESCRIPTION
                     "This database is used to report status of authenticated 
                     clients."
         ::= { apcpAuthFailedClientStatusGroup 1 }

    apcpAuthFailedClientStatusEntry OBJECT-TYPE
         SYNTAX      ApcpAuthFailedClientStatusEntry
         MAX-ACCESS  not-accessible
         STATUS      current
         DESCRIPTION
                     "Captive portal authenticated client status entry."
         INDEX       { apcpAuthFailedClientMacAddress }
         ::= { apcpAuthFailedClientStatusTable 1 }

    ApcpAuthFailedClientStatusEntry ::= SEQUENCE {
                         apcpAuthFailedClientMacAddress
                           MacAddress,
                         apcpAuthFailedClientIpAddress
                           DisplayString,
                         apcpAuthFailedClientTimeStamp
                           DisplayString,
                         apcpAuthFailedClientUserName
                           DisplayString,                                      
                         apcpAuthFailedClientVerifyMode
                           INTEGER,                                      
                         apcpAuthFailedClientVapIndex
                           InterfaceIndex,                                      
                         apcpAuthFailedClientRadioIndex
                           InterfaceIndex,                                      
                         apcpAuthFailedClientCPInstanceId
                           Integer32                                      
           }

    apcpAuthFailedClientMacAddress OBJECT-TYPE
         SYNTAX      MacAddress
         MAX-ACCESS  not-accessible
         STATUS      current
         DESCRIPTION
                     "The MAC address of authentication failed client." 
                     ::= { apcpAuthFailedClientStatusEntry 1 }

    apcpAuthFailedClientIpAddress OBJECT-TYPE
         SYNTAX      DisplayString
         MAX-ACCESS  read-only
         STATUS      current
         DESCRIPTION
                     "The IP address of the authentication failed client."
         ::= { apcpAuthFailedClientStatusEntry 2 }

    apcpAuthFailedClientTimeStamp OBJECT-TYPE
         SYNTAX      DisplayString
         MAX-ACCESS  read-only
         STATUS      current
         DESCRIPTION
                     "The time (in seconds) since the client failed 
                     authorization." 
         ::= { apcpAuthFailedClientStatusEntry 3 }

    apcpAuthFailedClientUserName OBJECT-TYPE
         SYNTAX      DisplayString (SIZE(0..32))
         MAX-ACCESS  read-only
         STATUS      current
         DESCRIPTION
                     "User name (or Guest ID) of the authentication failed 
                     client."
         ::= { apcpAuthFailedClientStatusEntry 4 }

    apcpAuthFailedClientVerifyMode OBJECT-TYPE
         SYNTAX      INTEGER {
                     guest(0),
                     local(1),
                     radius(2)
                  }
         MAX-ACCESS  read-only
         STATUS      current
         DESCRIPTION
                     "Type of user verification performed for the 
                     authentication failed client."
         ::= { apcpAuthFailedClientStatusEntry 5 }

    apcpAuthFailedClientVapIndex OBJECT-TYPE
         SYNTAX      InterfaceIndex
         MAX-ACCESS  read-only
         STATUS      current
         DESCRIPTION
                     "The VAP interface on which the client failed 
                     authentication." 
         ::= { apcpAuthFailedClientStatusEntry 6 }

    apcpAuthFailedClientRadioIndex OBJECT-TYPE
         SYNTAX      InterfaceIndex
         MAX-ACCESS  read-only
         STATUS      current
         DESCRIPTION
                     "The radio index on which the client failed 
                     authentication." 
         ::= { apcpAuthFailedClientStatusEntry 7 }

    apcpAuthFailedClientCPInstanceId     OBJECT-TYPE
         SYNTAX      Integer32
         MAX-ACCESS  read-only
         STATUS      current
         DESCRIPTION
                     "The captive portal instance on which the client failed 
                     authentication." 
         ::= { apcpAuthFailedClientStatusEntry 8 }

END

------------------------------------------------------------------------------
--
--  File         : maipuCarMIB.mib
--  Description  : Maipu Commited Access Rate MIB file.
--  Version      : 1.00
--  Date         : December 26, 2009
-- 	Copyright    : 2009 by Maipu Communication Technology Co., LTD.
--					All rights reserved.
--
-- $Id:
-- 
------------------------------------------------------------------------------

------------------------------------------------------------------------------
MAIPU-CAR-MIB DEFINITIONS ::= BEGIN


IMPORTS
        MODULE-IDENTITY, OBJECT-TYPE, NOTIFICATION-TYPE, enterprises, Counter32, Gauge32,
          Integer32, Unsigned32, TimeTicks,IpAddress,Counter64
            FROM SNMPv2-SMI
        TEXTUAL-CONVENTION, TruthValue, MacAddress,
          RowStatus, DisplayString, DateAndTime
            FROM SNMPv2-TC
        MODULE-COMPLIANCE, OBJECT-GROUP
            FROM SNMPv2-CONF
        mpMgmt
            FROM MAIPU-SMI;


maipu               	OBJECT IDENTIFIER ::= { enterprises 5651 }
mpMgmt2             	OBJECT IDENTIFIER ::= { maipu 6 }
mpRouterTech        	OBJECT IDENTIFIER ::= { mpMgmt2 2 }
mpRtQoSv2           	OBJECT IDENTIFIER ::= { mpRouterTech 3 }


maipuCarMIB         	MODULE-IDENTITY
                    		LAST-UPDATED 	"0912261452Z"
                    		ORGANIZATION 	"Maipu Communication Technology Co., LTD."
                    		CONTACT-INFO
                    			""
                    		DESCRIPTION
                      			"Maipu Commited Access Rate MIB"
                    		::= { mpRtQoSv2  1 }

-- Textual Conventions
Unsigned64 ::= TEXTUAL-CONVENTION
    STATUS          current
    DESCRIPTION
        "An unsigned 64 bit integer. We use SYNTAX Counter64 for the encoding rules, such as rate 
        in bps."
    SYNTAX          Counter64

------------------------------------------------------------------------------
maipuCarMIBObjects  	OBJECT IDENTIFIER ::= { maipuCarMIB 1 }


------------------------------------------------------------------------------
mpCarConfigs        	OBJECT IDENTIFIER ::= { maipuCarMIBObjects 1 }

mpCarInterfaceCfgTable	OBJECT-TYPE
                    		SYNTAX  SEQUENCE OF  MpCarInterfaceCfgEntry
                    		MAX-ACCESS  not-accessible
                    		STATUS  current
                    		DESCRIPTION
                    			"A table of rate limit configuration entries. Rate Limit is a 
                    			method of traffic control.  It allows a set of rate limits to be 
                    			configured and applied to packets flowing into/out of an 
                    			interface to regulate network traffic."
                    		::= { mpCarConfigs 1 }

mpCarInterfaceCfgEntry	OBJECT-TYPE
                    		SYNTAX  MpCarInterfaceCfgEntry
                    		MAX-ACCESS  not-accessible
                    		STATUS  current
                    		DESCRIPTION
                    			"A collection of rate-limit configuration objects on this 
                    			interface. Entries in the mpCarInterfaceCfgTable is created 
                    			and deleted via the rate-limit command line interface."
                    		INDEX  { ifIndex,   mpCarIFCfgDirection,   mpCarIFCfgRowIndex }
                    		::= { mpCarInterfaceCfgTable 1 }

MpCarInterfaceCfgEntry	::= SEQUENCE {
                    			mpCarIFCfgDirection   INTEGER,
                    			mpCarIFCfgRowIndex   Integer32,
                    			mpCarIFCfgType   INTEGER,
                    			mpCarIFCfgAclName   DisplayString,
                    			mpCarIFCfgRate64   Unsigned64,
                    			mpCarIFCfgBurstSize   Integer32,
                    			mpCarIFCfgExtBurstSize   Integer32,
                    			mpCarIFCfgConformAction   INTEGER,
                    			mpCarIFCfgConformSetValue   Integer32,
                    			mpCarIFCfgExceedAction   INTEGER,
                    			mpCarIFCfgExceedSetValue   Integer32,
                    			mpCarIFCfgColorMode   INTEGER
                    	             }


mpCarIFCfgDirection	OBJECT-TYPE
                    		SYNTAX  INTEGER {
                    			          input(1),
                    			          output(2)
                    			        }
                    		MAX-ACCESS  not-accessible
                    		STATUS  current
                    		DESCRIPTION
                    			"The data source for the Rate Limit object."
                    		::= { mpCarInterfaceCfgEntry 1 }

mpCarIFCfgRowIndex	OBJECT-TYPE
                    		SYNTAX  Integer32(1..2147483647)
                    		MAX-ACCESS  not-accessible
                    		STATUS  current
                    		DESCRIPTION
                    			"An arbitrary index for rate limit objects. It will increase as 
                    			the list is traversed, but may skip."
                    		::= { mpCarInterfaceCfgEntry 2 }

mpCarIFCfgType	OBJECT-TYPE
                    		SYNTAX  INTEGER {
                    			          all(1),
                    			          accessList(2)
                    			        }
                    		MAX-ACCESS  read-only
                    		STATUS  current
                    		DESCRIPTION
                    			"The type of traffic rate-limited against."
                    		::= { mpCarInterfaceCfgEntry 3 }

mpCarIFCfgAclName	OBJECT-TYPE
                    		SYNTAX  DisplayString(SIZE(0..255))
                    		MAX-ACCESS  read-only
                    		STATUS  current
                    		DESCRIPTION
                    			"Access list name.This field only makes sense when mpCarIFCfgType 
                    			is accessList(2)."
                    		::= { mpCarInterfaceCfgEntry 4 }

mpCarIFCfgRate64	OBJECT-TYPE
                    		SYNTAX  Unsigned64
                    		UNITS  "bits/second"
                    		MAX-ACCESS  read-only
                    		STATUS  current
                    		DESCRIPTION
                    			"The comitted access rate, in bits/second.  This is the sustained 
                    			rate permitted by the rate limit."
                    		::= { mpCarInterfaceCfgEntry 5 }

mpCarIFCfgBurstSize	OBJECT-TYPE
                    		SYNTAX  Integer32
                    		UNITS  "bytes"
                    		MAX-ACCESS  read-only
                    		STATUS  current
                    		DESCRIPTION
                    			"The normal burst size.  The amout of traffic, in bytes, in 
                    			excess of the committed access rate which will be instantaneously 
                    			permitted by the rate limit."
                    		::= { mpCarInterfaceCfgEntry 6 }

mpCarIFCfgExtBurstSize	OBJECT-TYPE
                    		SYNTAX  Integer32
                    		UNITS  "bytes"
                    		MAX-ACCESS  read-only
                    		STATUS  current
                    		DESCRIPTION
                    			"The extended burst size. The amount of traffic, in bytes, in 
                    			excess of the burst limit which may be conditionnally permitted 
                    			by the rate limit."
                    		::= { mpCarInterfaceCfgEntry 7 }

mpCarIFCfgConformAction	OBJECT-TYPE
                    		SYNTAX  INTEGER {
                    			          drop(1),
                    			          xmit(2),
                    			          continue(3),
                    			          precXmit(4),
                    			          precCont(5),
                    			          dscpXmit(6),
                    			          dscpCont(7),
                    			          mplsExpXmit(8),
                    			          mplsExpCont(9),
                    			          qosGroupXmit(10),
                    			          qosGroupCont(11)
                    			        }
                    		MAX-ACCESS  read-only
                    		STATUS  current
                    		DESCRIPTION
                    			"Action to be taken when the traffic is within the Rate Limit."
                    		::= { mpCarInterfaceCfgEntry 8 }

mpCarIFCfgConformSetValue	OBJECT-TYPE
                    		SYNTAX  Integer32
                    		MAX-ACCESS  read-only
                    		STATUS  current
                    		DESCRIPTION
                    			"New packet attribute values for each packets that conforms to 
                    			the configured Police rate."
                    		::= { mpCarInterfaceCfgEntry 9 }

mpCarIFCfgExceedAction	OBJECT-TYPE
                    		SYNTAX  INTEGER {
                    			          drop(1),
                    			          xmit(2),
                    			          continue(3),
                    			          precXmit(4),
                    			          precCont(5),
                    			          dscpXmit(6),
                    			          dscpCont(7),
                    			          mplsExpXmit(8),
                    			          mplsExpCont(9),
                    			          qosGroupXmit(10),
                    			          qosGroupCont(11)
                    			        }
                    		MAX-ACCESS  read-only
                    		STATUS  current
                    		DESCRIPTION
                    			"Action to be taken when the traffic exceeds the Rate Limit."
                    		::= { mpCarInterfaceCfgEntry 10 }

mpCarIFCfgExceedSetValue	OBJECT-TYPE
                    		SYNTAX  Integer32
                    		MAX-ACCESS  read-only
                    		STATUS  current
                    		DESCRIPTION
                    			"New packet attribute values for each packets that exceeds to the 
                    			configured Police rate."
                    		::= { mpCarInterfaceCfgEntry 11 }

mpCarIFCfgColorMode	OBJECT-TYPE
                    		SYNTAX  INTEGER {
                    			          none(1),
                    			          colorKeep(2)
                    			        }
                    		MAX-ACCESS  read-only
                    		STATUS  current
                    		DESCRIPTION
                    			"Color mode for the Rate Limit."
                    		::= { mpCarInterfaceCfgEntry 12 }


------------------------------------------------------------------------------
mpCarFrameRelayVCCfgTable	OBJECT-TYPE
                    		SYNTAX  SEQUENCE OF  MpCarFrameRelayVCCfgEntry
                    		MAX-ACCESS  not-accessible
                    		STATUS  current
                    		DESCRIPTION
                    			"A table of rate limit configuration entries for Frame Relay VC. 
                    			Rate Limit is a method of traffic control.  It allows a set of 
                    			rate limits to be configured and applied to packets flowing 
                    			into/out of an interface to regulate network traffic."
                    		::= { mpCarConfigs 2 }

mpCarFrameRelayVCCfgEntry	OBJECT-TYPE
                    		SYNTAX  MpCarFrameRelayVCCfgEntry
                    		MAX-ACCESS  not-accessible
                    		STATUS  current
                    		DESCRIPTION
                    			"A collection of rate-limit configuration objects on this Frame 
                    			Relay VC. Entries in the mpCarFrameRelayVCCfgTable is created 
                    			and deleted via the rate-limit command line interface."
                    		INDEX  { ifIndex,   mpCarFRCfgDLCI,   mpCarFRCfgDirection,   mpCarFRCfgRowIndex }
                    		::= { mpCarFrameRelayVCCfgTable 1 }

MpCarFrameRelayVCCfgEntry	::= SEQUENCE {
                    			mpCarFRCfgDLCI         Unsigned32,
                    			mpCarFRCfgDirection    INTEGER,
                    			mpCarFRCfgRowIndex     Integer32,
                    			mpCarFRCfgType         INTEGER,
                    			mpCarFRCfgAclName      DisplayString,
                    			mpCarFRCfgRate64       Unsigned64,
                    			mpCarFRCfgBurstSize    Integer32,
                    			mpCarFRCfgExtBurstSize   Integer32,
                    			mpCarFRCfgConformAction   INTEGER,
                    			mpCarFRCfgConformSetValue   Integer32,
                    			mpCarFRCfgExceedAction   INTEGER,
                    			mpCarFRCfgExceedSetValue   Integer32,
                    			mpCarFRCfgColorMode    INTEGER
                    	             }


mpCarFRCfgDLCI      	OBJECT-TYPE
                    		SYNTAX  Unsigned32(0..1007)
                    		MAX-ACCESS  not-accessible
                    		STATUS  current
                    		DESCRIPTION
                    			"DLCI for the FRVC to which the Rate Limit objectis attached."
                    		::= { mpCarFrameRelayVCCfgEntry 1 }

mpCarFRCfgDirection 	OBJECT-TYPE
                    		SYNTAX  INTEGER {
                    			          input(1),
                    			          output(2)
                    			        }
                    		MAX-ACCESS  not-accessible
                    		STATUS  current
                    		DESCRIPTION
                    			"The data source for the Rate Limit object."
                    		::= { mpCarFrameRelayVCCfgEntry 2 }

mpCarFRCfgRowIndex  	OBJECT-TYPE
                    		SYNTAX  Integer32(1..2147483647)
                    		MAX-ACCESS  not-accessible
                    		STATUS  current
                    		DESCRIPTION
                    			"An arbitrary index for rate limit objects. It will increase as 
                    			the list is traversed, but may skip."
                    		::= { mpCarFrameRelayVCCfgEntry 3 }

mpCarFRCfgType      	OBJECT-TYPE
                    		SYNTAX  INTEGER {
                    			          all(1),
                    			          accessList(2)
                    			        }
                    		MAX-ACCESS  read-only
                    		STATUS  current
                    		DESCRIPTION
                    			"The type of traffic rate-limited against."
                    		::= { mpCarFrameRelayVCCfgEntry 4 }

mpCarFRCfgAclName   	OBJECT-TYPE
                    		SYNTAX  DisplayString(SIZE(0..255))
                    		MAX-ACCESS  read-only
                    		STATUS  current
                    		DESCRIPTION
                    			"Access list name.This field only makes sense when mpCarFRCfgType 
                    			is accessList(2)."
                    		::= { mpCarFrameRelayVCCfgEntry 5 }

mpCarFRCfgRate64      	OBJECT-TYPE
                    		SYNTAX  Unsigned64
                    		UNITS  "bits/second"
                    		MAX-ACCESS  read-only
                    		STATUS  current
                    		DESCRIPTION
                    			"The comitted access rate, in bits/second.  This is the sustained 
                    			rate permitted by the rate limit."
                    		::= { mpCarFrameRelayVCCfgEntry 6 }

mpCarFRCfgBurstSize 	OBJECT-TYPE
                    		SYNTAX  Integer32
                    		UNITS  "bytes"
                    		MAX-ACCESS  read-only
                    		STATUS  current
                    		DESCRIPTION
                    			"The normal burst size.  The amout of traffic, in bytes, in 
                    			excess of the committed access rate which will be instantaneously 
                    			permitted by the rate limit."
                    		::= { mpCarFrameRelayVCCfgEntry 7 }

mpCarFRCfgExtBurstSize	OBJECT-TYPE
                    		SYNTAX  Integer32
                    		UNITS  "bytes"
                    		MAX-ACCESS  read-only
                    		STATUS  current
                    		DESCRIPTION
                    			"The extended burst size. The amount of traffic, in bytes, in 
                    			excess of the burst limit which may be conditionnally permitted 
                    			by the rate limit."
                    		::= { mpCarFrameRelayVCCfgEntry 8 }

mpCarFRCfgConformAction	OBJECT-TYPE
                    		SYNTAX  INTEGER {
                    			          drop(1),
                    			          xmit(2),
                    			          continue(3),
                    			          precXmit(4),
                    			          precCont(5),
                    			          dscpXmit(6),
                    			          dscpCont(7),
                    			          mplsExpXmit(8),
                    			          mplsExpCont(9),
                    			          qosGroupXmit(10),
                    			          qosGroupCont(11)
                    			        }
                    		MAX-ACCESS  read-only
                    		STATUS  current
                    		DESCRIPTION
                    			"Action to be taken when the traffic is within the Rate Limit."
                    		::= { mpCarFrameRelayVCCfgEntry 9 }

mpCarFRCfgConformSetValue	OBJECT-TYPE
                    		SYNTAX  Integer32
                    		MAX-ACCESS  read-only
                    		STATUS  current
                    		DESCRIPTION
                    			"New packet attribute values for each packets that conforms to 
                    			the configured Police rate."
                    		::= { mpCarFrameRelayVCCfgEntry 10 }

mpCarFRCfgExceedAction	OBJECT-TYPE
                    		SYNTAX  INTEGER {
                    			          drop(1),
                    			          xmit(2),
                    			          continue(3),
                    			          precXmit(4),
                    			          precCont(5),
                    			          dscpXmit(6),
                    			          dscpCont(7),
                    			          mplsExpXmit(8),
                    			          mplsExpCont(9),
                    			          qosGroupXmit(10),
                    			          qosGroupCont(11)
                    			        }
                    		MAX-ACCESS  read-only
                    		STATUS  current
                    		DESCRIPTION
                    			"Action to be taken when the traffic exceeds the Rate Limit."
                    		::= { mpCarFrameRelayVCCfgEntry 11 }

mpCarFRCfgExceedSetValue	OBJECT-TYPE
                    		SYNTAX  Integer32
                    		MAX-ACCESS  read-only
                    		STATUS  current
                    		DESCRIPTION
                    			"New packet attribute values for each packets that exceeds to the 
                    			configured Police rate."
                    		::= { mpCarFrameRelayVCCfgEntry 12 }

mpCarFRCfgColorMode 	OBJECT-TYPE
                    		SYNTAX  INTEGER {
                    			          none(1),
                    			          colorKeep(2)
                    			        }
                    		MAX-ACCESS  read-only
                    		STATUS  current
                    		DESCRIPTION
                    			"Color mode for the Rate Limit."
                    		::= { mpCarFrameRelayVCCfgEntry 13 }


------------------------------------------------------------------------------
mpCarATMPVCCfgTable 	OBJECT-TYPE
                    		SYNTAX  SEQUENCE OF  MpCarATMPVCCfgEntry
                    		MAX-ACCESS  not-accessible
                    		STATUS  current
                    		DESCRIPTION
                    			"A table of rate limit configuration entries for ATM PVC. Rate 
                    			Limit is a method of traffic control.  It allows a set of rate 
                    			limits to be configured and applied to packets flowing into/out 
                    			of an interface to regulate network traffic."
                    		::= { mpCarConfigs 3 }

mpCarATMPVCCfgEntry 	OBJECT-TYPE
                    		SYNTAX  MpCarATMPVCCfgEntry
                    		MAX-ACCESS  not-accessible
                    		STATUS  current
                    		DESCRIPTION
                    			"A collection of rate-limit configuration objects on this ATM 
                    			PVC. Entries in the mpCarATMPVCCfgTable is created and deleted 
                    			via the rate-limit command line interface."
                    		INDEX  { ifIndex,   mpCarATMCfgVPI,   mpCarATMCfgVCI,   mpCarATMCfgDirection,   mpCarATMCfgRowIndex }
                    		::= { mpCarATMPVCCfgTable 1 }

MpCarATMPVCCfgEntry 	::= SEQUENCE {
                    			mpCarATMCfgVPI         Unsigned32,
                    			mpCarATMCfgVCI         Unsigned32,
                    			mpCarATMCfgDirection   INTEGER,
                    			mpCarATMCfgRowIndex    Integer32,
                    			mpCarATMCfgType        INTEGER,
                    			mpCarATMCfgAclName     DisplayString,
                    			mpCarATMCfgRate64      Unsigned64,
                    			mpCarATMCfgBurstSize   Integer32,
                    			mpCarATMCfgExtBurstSize   Integer32,
                    			mpCarATMCfgConformAction   INTEGER,
                    			mpCarATMCfgConformSetValue   Integer32,
                    			mpCarATMCfgExceedAction   INTEGER,
                    			mpCarATMCfgExceedSetValue   Integer32,
                    			mpCarATMCfgColorMode   INTEGER
                    	             }


mpCarATMCfgVPI      	OBJECT-TYPE
                    		SYNTAX  Unsigned32(0..4095)
                    		MAX-ACCESS  not-accessible
                    		STATUS  current
                    		DESCRIPTION
                    			"VPI for the ATMVC to which the Rate Limit objectis attached."
                    		::= { mpCarATMPVCCfgEntry 1 }

mpCarATMCfgVCI      	OBJECT-TYPE
                    		SYNTAX  Unsigned32(0..65535)
                    		MAX-ACCESS  not-accessible
                    		STATUS  current
                    		DESCRIPTION
                    			"VCI for the ATMVC to which the Rate Limit objectis attached."
                    		::= { mpCarATMPVCCfgEntry 2 }

mpCarATMCfgDirection	OBJECT-TYPE
                    		SYNTAX  INTEGER {
                    			          input(1),
                    			          output(2)
                    			        }
                    		MAX-ACCESS  not-accessible
                    		STATUS  current
                    		DESCRIPTION
                    			"The data source for the Rate Limit object."
                    		::= { mpCarATMPVCCfgEntry 3 }

mpCarATMCfgRowIndex 	OBJECT-TYPE
                    		SYNTAX  Integer32(1..2147483647)
                    		MAX-ACCESS  not-accessible
                    		STATUS  current
                    		DESCRIPTION
                    			"An arbitrary index for rate limit objects. It will increase as 
                    			the list is traversed, but may skip."
                    		::= { mpCarATMPVCCfgEntry 4 }

mpCarATMCfgType     	OBJECT-TYPE
                    		SYNTAX  INTEGER {
                    			          all(1),
                    			          accessList(2)
                    			        }
                    		MAX-ACCESS  read-only
                    		STATUS  current
                    		DESCRIPTION
                    			"The type of traffic rate-limited against."
                    		::= { mpCarATMPVCCfgEntry 5 }

mpCarATMCfgAclName  	OBJECT-TYPE
                    		SYNTAX  DisplayString(SIZE(0..255))
                    		MAX-ACCESS  read-only
                    		STATUS  current
                    		DESCRIPTION
                    			"Access list name.This field only makes sense when 
                    			mpCarATMCfgType is accessList(2)."
                    		::= { mpCarATMPVCCfgEntry 6 }

mpCarATMCfgRate64     	OBJECT-TYPE
                    		SYNTAX  Unsigned64
                    		UNITS	"bits/second"
                    		MAX-ACCESS  read-only
                    		STATUS  current
                    		DESCRIPTION
                    			"The comitted access rate, in bits/second.  This is the sustained 
                    			rate permitted by the rate limit."
                    		::= { mpCarATMPVCCfgEntry 7 }

mpCarATMCfgBurstSize	OBJECT-TYPE
                    		SYNTAX  Integer32
                    		UNITS  "bytes"
                    		MAX-ACCESS  read-only
                    		STATUS  current
                    		DESCRIPTION
                    			"The normal burst size.  The amout of traffic, in bytes, in 
                    			excess of the committed access rate which will be instantaneously 
                    			permitted by the rate limit."
                    		::= { mpCarATMPVCCfgEntry 8 }

mpCarATMCfgExtBurstSize	OBJECT-TYPE
                    		SYNTAX  Integer32
                    		UNITS  "bytes"
                    		MAX-ACCESS  read-only
                    		STATUS  current
                    		DESCRIPTION
                    			"The extended burst size. The amount of traffic, in bytes, in 
                    			excess of the burst limit which may be conditionnally permitted 
                    			by the rate limit."
                    		::= { mpCarATMPVCCfgEntry 9 }

mpCarATMCfgConformAction	OBJECT-TYPE
                    		SYNTAX  INTEGER {
                    			          drop(1),
                    			          xmit(2),
                    			          continue(3),
                    			          precXmit(4),
                    			          precCont(5),
                    			          dscpXmit(6),
                    			          dscpCont(7),
                    			          mplsExpXmit(8),
                    			          mplsExpCont(9),
                    			          qosGroupXmit(10),
                    			          qosGroupCont(11)
                    			        }
                    		MAX-ACCESS  read-only
                    		STATUS  current
                    		DESCRIPTION
                    			"Action to be taken when the traffic is within the Rate Limit."
                    		::= { mpCarATMPVCCfgEntry 10 }

mpCarATMCfgConformSetValue	OBJECT-TYPE
                    		SYNTAX  Integer32
                    		MAX-ACCESS  read-only
                    		STATUS  current
                    		DESCRIPTION
                    			"New packet attribute values for each packets that conforms to 
                    			the configured Police rate."
                    		::= { mpCarATMPVCCfgEntry 11 }

mpCarATMCfgExceedAction	OBJECT-TYPE
                    		SYNTAX  INTEGER {
                    			          drop(1),
                    			          xmit(2),
                    			          continue(3),
                    			          precXmit(4),
                    			          precCont(5),
                    			          dscpXmit(6),
                    			          dscpCont(7),
                    			          mplsExpXmit(8),
                    			          mplsExpCont(9),
                    			          qosGroupXmit(10),
                    			          qosGroupCont(11)
                    			        }
                    		MAX-ACCESS  read-only
                    		STATUS  current
                    		DESCRIPTION
                    			"Action to be taken when the traffic exceeds the Rate Limit."
                    		::= { mpCarATMPVCCfgEntry 12 }

mpCarATMCfgExceedSetValue	OBJECT-TYPE
                    		SYNTAX  Integer32
                    		MAX-ACCESS  read-only
                    		STATUS  current
                    		DESCRIPTION
                    			"New packet attribute values for each packets that exceeds to the 
                    			configured Police rate."
                    		::= { mpCarATMPVCCfgEntry 13 }

mpCarATMCfgColorMode	OBJECT-TYPE
                    		SYNTAX  INTEGER {
                    			          none(1),
                    			          colorKeep(2)
                    			        }
                    		MAX-ACCESS  read-only
                    		STATUS  current
                    		DESCRIPTION
                    			"Color mode for the Rate Limit."
                    		::= { mpCarATMPVCCfgEntry 14 }


------------------------------------------------------------------------------
mpCarStats          	OBJECT IDENTIFIER ::= { maipuCarMIBObjects 2 }

mpCarInterfaceStatTable	OBJECT-TYPE
                    		SYNTAX  SEQUENCE OF  MpCarInterfaceStatEntry
                    		MAX-ACCESS  not-accessible
                    		STATUS  current
                    		DESCRIPTION
                    			"A table of rate limit statistics entries."
                    		::= { mpCarStats 1 }

mpCarInterfaceStatEntry	OBJECT-TYPE
                    		SYNTAX  MpCarInterfaceStatEntry
                    		MAX-ACCESS  not-accessible
                    		STATUS  current
                    		DESCRIPTION
                    			"A collection of rate-limit statistical objects on this interface. 
                    			Entries are created and deleted via the rate-limit command line 
                    			interface."
                    		INDEX  { ifIndex,   mpCarIFCfgDirection,   mpCarIFCfgRowIndex }
                    		::= { mpCarInterfaceStatTable 1 }

MpCarInterfaceStatEntry	::= SEQUENCE {
                    			mpCarIFStatSwitchedPkts64   Counter64,
                    			mpCarIFStatSwitchedBytes64   Counter64,
                    			mpCarIFStatFilteredPkts64   Counter64,
                    			mpCarIFStatFilteredBytes64   Counter64,
                    			mpCarIFStatCurBurst   Gauge32
                    	             }


mpCarIFStatSwitchedPkts64	OBJECT-TYPE
                    		SYNTAX  Counter64
                    		UNITS  "packets"
                    		MAX-ACCESS  read-only
                    		STATUS  current
                    		DESCRIPTION
                    			"The counter of packets permitted by this rate limit."
                    		::= { mpCarInterfaceStatEntry 1 }

mpCarIFStatSwitchedBytes64	OBJECT-TYPE
                    		SYNTAX  Counter64
                    		UNITS  "bytes"
                    		MAX-ACCESS  read-only
                    		STATUS  current
                    		DESCRIPTION
                    			"The counter of bytes permitted by this interface."
                    		::= { mpCarInterfaceStatEntry 2 }

mpCarIFStatFilteredPkts64	OBJECT-TYPE
                    		SYNTAX  Counter64
                    		UNITS  "packets"
                    		MAX-ACCESS  read-only
                    		STATUS  current
                    		DESCRIPTION
                    			"The counter of packets which exceeded this rate limit."
                    		::= { mpCarInterfaceStatEntry 3 }

mpCarIFStatFilteredBytes64	OBJECT-TYPE
                    		SYNTAX  Counter64
                    		UNITS  "bytes"
                    		MAX-ACCESS  read-only
                    		STATUS  current
                    		DESCRIPTION
                    			"The counter of bytes which exceeded this rate limit."
                    		::= { mpCarInterfaceStatEntry 4 }

mpCarIFStatCurBurst	OBJECT-TYPE
                    		SYNTAX  Gauge32
                    		UNITS  "bytes"
                    		MAX-ACCESS  read-only
                    		STATUS  current
                    		DESCRIPTION
                    			"The current received burst size."
                    		::= { mpCarInterfaceStatEntry 5 }


------------------------------------------------------------------------------
mpCarFrameRelayVCStatTable	OBJECT-TYPE
                    		SYNTAX  SEQUENCE OF  MpCarFrameRelayVCStatEntry
                    		MAX-ACCESS  not-accessible
                    		STATUS  current
                    		DESCRIPTION
                    			"A table of rate limit statistics entries for Frame Relay VC."
                    		::= { mpCarStats 2 }

mpCarFrameRelayVCStatEntry	OBJECT-TYPE
                    		SYNTAX  MpCarFrameRelayVCStatEntry
                    		MAX-ACCESS  not-accessible
                    		STATUS  current
                    		DESCRIPTION
                    			"A collection of rate-limit statistical objects on this Frame Relay 
                    			VC. Entries are created and deleted via the rate-limit command 
                    			line interface."
                    		INDEX  { ifIndex,   mpCarFRCfgDLCI,   mpCarFRCfgDirection,   mpCarFRCfgRowIndex }
                    		::= { mpCarFrameRelayVCStatTable 1 }

MpCarFrameRelayVCStatEntry	::= SEQUENCE {
                    			mpCarFRStatSwitchedPkts64   Counter64,
                    			mpCarFRStatSwitchedBytes64   Counter64,
                    			mpCarFRStatFilteredPkts64   Counter64,
                    			mpCarFRStatFilteredBytes64   Counter64,
                    			mpCarFRStatCurBurst    Gauge32
                    	             }


mpCarFRStatSwitchedPkts64	OBJECT-TYPE
                    		SYNTAX  Counter64
                    		UNITS  "packets"
                    		MAX-ACCESS  read-only
                    		STATUS  current
                    		DESCRIPTION
                    			"The counter of packets permitted by this rate limit."
                    		::= { mpCarFrameRelayVCStatEntry 1 }

mpCarFRStatSwitchedBytes64	OBJECT-TYPE
                    		SYNTAX  Counter64
                    		UNITS  "bytes"
                    		MAX-ACCESS  read-only
                    		STATUS  current
                    		DESCRIPTION
                    			"The counter of bytes permitted by this interface."
                    		::= { mpCarFrameRelayVCStatEntry 2 }

mpCarFRStatFilteredPkts64	OBJECT-TYPE
                    		SYNTAX  Counter64
                    		UNITS  "packets"
                    		MAX-ACCESS  read-only
                    		STATUS  current
                    		DESCRIPTION
                    			"The counter of packets which exceeded this rate limit."
                    		::= { mpCarFrameRelayVCStatEntry 3 }

mpCarFRStatFilteredBytes64	OBJECT-TYPE
                    		SYNTAX  Counter64
                    		UNITS  "bytes"
                    		MAX-ACCESS  read-only
                    		STATUS  current
                    		DESCRIPTION
                    			"The counter of bytes which exceeded this rate limit."
                    		::= { mpCarFrameRelayVCStatEntry 4 }

mpCarFRStatCurBurst 	OBJECT-TYPE
                    		SYNTAX  Gauge32
                    		UNITS  "bytes"
                    		MAX-ACCESS  read-only
                    		STATUS  current
                    		DESCRIPTION
                    			"The current received burst size."
                    		::= { mpCarFrameRelayVCStatEntry 5 }


------------------------------------------------------------------------------
mpCarATMPVCStatTable	OBJECT-TYPE
                    		SYNTAX  SEQUENCE OF  MpCarATMPVCStatEntry
                    		MAX-ACCESS  not-accessible
                    		STATUS  current
                    		DESCRIPTION
                    			"A table of rate limit statistics entries for ATM PVC."
                    		::= { mpCarStats 3 }

mpCarATMPVCStatEntry	OBJECT-TYPE
                    		SYNTAX  MpCarATMPVCStatEntry
                    		MAX-ACCESS  not-accessible
                    		STATUS  current
                    		DESCRIPTION
                    			"A collection of rate-limit statistical objects on this ATM PVC. 
                    			Entries are created and deleted via the rate-limit command line 
                    			interface."
                    		INDEX  { ifIndex,   mpCarATMCfgVPI,   mpCarATMCfgVCI,   mpCarATMCfgDirection,   mpCarATMCfgRowIndex }
                    		::= { mpCarATMPVCStatTable 1 }

MpCarATMPVCStatEntry	::= SEQUENCE {
                    			mpCarATMStatSwitchedPkts64   Counter64,
                    			mpCarATMStatSwitchedBytes64   Counter64,
                    			mpCarATMStatFilteredPkts64   Counter64,
                    			mpCarATMStatFilteredBytes64   Counter64,
                    			mpCarATMStatCurBurst   Gauge32
                    	             }


mpCarATMStatSwitchedPkts64	OBJECT-TYPE
                    		SYNTAX  Counter64
                    		UNITS  "packets"
                    		MAX-ACCESS  read-only
                    		STATUS  current
                    		DESCRIPTION
                    			"The counter of packets permitted by this rate limit."
                    		::= { mpCarATMPVCStatEntry 1 }

mpCarATMStatSwitchedBytes64	OBJECT-TYPE
                    		SYNTAX  Counter64
                    		UNITS  "bytes"
                    		MAX-ACCESS  read-only
                    		STATUS  current
                    		DESCRIPTION
                    			"The counter of bytes permitted by this interface."
                    		::= { mpCarATMPVCStatEntry 2 }

mpCarATMStatFilteredPkts64	OBJECT-TYPE
                    		SYNTAX  Counter64
                    		UNITS  "packets"
                    		MAX-ACCESS  read-only
                    		STATUS  current
                    		DESCRIPTION
                    			"The counter of packets which exceeded this rate limit."
                    		::= { mpCarATMPVCStatEntry 3 }

mpCarATMStatFilteredBytes64	OBJECT-TYPE
                    		SYNTAX  Counter64
                    		UNITS  "bytes"
                    		MAX-ACCESS  read-only
                    		STATUS  current
                    		DESCRIPTION
                    			"The counter of bytes which exceeded this rate limit."
                    		::= { mpCarATMPVCStatEntry 4 }

mpCarATMStatCurBurst	OBJECT-TYPE
                    		SYNTAX  Gauge32
                    		UNITS  "bytes"
                    		MAX-ACCESS  read-only
                    		STATUS  current
                    		DESCRIPTION
                    			"The current received burst size."
                    		::= { mpCarATMPVCStatEntry 5 }



END
------------------------------------------------------------------------------
-- ============================================================================
-- $Log: maipuCarMIB.mib,v $
--
--
-- ============================================================================

------------------------------------------------------------------------------
--
--  File         : maipuCBQosMIB.mib
--  Description  : Maipu Class-Based QoS MIB
--  Version      : 1.00
--  Date         : December 26, 2009
-- 	Copyright    : 2009 by Maipu Communication Technology Co., LTD.
--					All rights reserved.
--
-- $Id:
-- 
------------------------------------------------------------------------------

------------------------------------------------------------------------------
MAIPU-CBQOS-MIB DEFINITIONS ::= BEGIN


IMPORTS
        MODULE-IDENTITY, OBJECT-TYPE, NOTIFICATION-TYPE, enterprises, Counter32, Gauge32,
          Integer32, Unsigned32, TimeTicks,IpAddress,Counter64
        	FROM SNMPv2-SMI
        TEXTUAL-CONVENTION, TruthValue, MacAddress, 
	      RowStatus, DisplayString, DateAndTime 
            FROM SNMPv2-TC
        MODULE-COMPLIANCE, OBJECT-GROUP         
        	FROM SNMPv2-CONF
        mpMgmt
            FROM MAIPU-SMI;


maipu               	OBJECT IDENTIFIER ::= { enterprises 5651 }
mpMgmt2             	OBJECT IDENTIFIER ::= { maipu 6 }
mpRouterTech        	OBJECT IDENTIFIER ::= { mpMgmt2 2 }
mpRtQoSv2           	OBJECT IDENTIFIER ::= { mpRouterTech 3 }


maipuCBQosMIB       	MODULE-IDENTITY
                    		LAST-UPDATED 	"0912261519Z"
                    		ORGANIZATION 	"Maipu Communication Technology Co., LTD."
                    		CONTACT-INFO
                    			""
                    		DESCRIPTION
                      			"Maipu Class-Based QoS MIB"
                    		::= { mpRtQoSv2  4 }


-- Textual Conventions
Unsigned64 ::= TEXTUAL-CONVENTION
    STATUS          current
    DESCRIPTION
        "An unsigned 64 bit integer. We use SYNTAX Counter64 for the encoding rules, such as rate 
        in bps."
    SYNTAX          Counter64


------------------------------------------------------------------------------
maipuCBQosMIBObjects	OBJECT IDENTIFIER ::= { maipuCBQosMIB 1 }


------------------------------------------------------------------------------
mpCbQosServicePolicy	OBJECT IDENTIFIER ::= { maipuCBQosMIBObjects 1 }

mpCbQosServicePolicyTable	OBJECT-TYPE
                    		SYNTAX  SEQUENCE OF  MpCbQosServicePolicyEntry
                    		MAX-ACCESS  not-accessible
                    		STATUS  current
                    		DESCRIPTION
                    			"This table describes the logical interfaces/media types and the 
                    			policymap that are attached to it."
                    		::= { mpCbQosServicePolicy 1 }

mpCbQosServicePolicyEntry	OBJECT-TYPE
                    		SYNTAX  MpCbQosServicePolicyEntry
                    		MAX-ACCESS  not-accessible
                    		STATUS  current
                    		DESCRIPTION
                    			"Each entry in this table describes to which a logical interface 
                    			a given policymap is attached. Depending on the logical 
                    			interface/media type, some fields may have meaningful values, and 
                    			some may not. Please see each individual descriptions."
                    		INDEX  { mpCbQosPolicyIndex }
                    		::= { mpCbQosServicePolicyTable 1 }

MpCbQosServicePolicyEntry	::= SEQUENCE {
                    			mpCbQosPolicyIndex     Unsigned32,
                    			mpCbQosIfType          INTEGER,
                    			mpCbQosPolicyDirection   INTEGER,
                    			mpCbQosIfIndex         Integer32,
                    			mpCbQosFrDLCI          Unsigned32,
                    			mpCbQosAtmVPI          Unsigned32,
                    			mpCbQosAtmVCI          Unsigned32,
                    			mpCbQosEntityIndex     Integer32,
                    			mpCbQosVlanIndex       Unsigned32
                    	             }


mpCbQosPolicyIndex  	OBJECT-TYPE
                    		SYNTAX  Unsigned32
                    		MAX-ACCESS  not-accessible
                    		STATUS  current
                    		DESCRIPTION
                    			"An arbitrary (system-assigned) index for all service policies 
                    			(PolicyMap that has been attached to a given logical interface)."
                    		::= { mpCbQosServicePolicyEntry 1 }

mpCbQosIfType       	OBJECT-TYPE
                    		SYNTAX  INTEGER {
                    			          mainInterface(1),
                    			          subInterface(2),
                    			          frDLCI(3),
                    			          atmPVC(4),
                    			          controlPlane(5),
                    			          vlanPort(6)
                    			        }
                    		MAX-ACCESS  read-only
                    		STATUS  current
                    		DESCRIPTION
                    			"This describes the logical interface/media type to which this 
                    			service policy is attached."
                    		::= { mpCbQosServicePolicyEntry 2 }

mpCbQosPolicyDirection	OBJECT-TYPE
                    		SYNTAX  INTEGER {
                    			         input(1),
                    			         output(2)
                    			        }
                    		MAX-ACCESS  read-only
                    		STATUS  current
                    		DESCRIPTION
                    			"This indicates the direction of traffic for which this service 
                    			policy is applied."
                    		::= { mpCbQosServicePolicyEntry 3 }

mpCbQosIfIndex      	OBJECT-TYPE
                    		SYNTAX  Integer32
                    		MAX-ACCESS  read-only
                    		STATUS  current
                    		DESCRIPTION
                    			"ifIndex for the interface to which this service is attached."
                    		::= { mpCbQosServicePolicyEntry 4 }

mpCbQosFrDLCI	        OBJECT-TYPE
                    		SYNTAX  Unsigned32(0..1007)
                    		MAX-ACCESS  read-only
                    		STATUS  current
                    		DESCRIPTION
                    			"DLCI for the FRVC to which this service is attached. This field 
                    			only make sense if the service policy is attached to a Frame 
                    			Relay DLCI."
                    		::= { mpCbQosServicePolicyEntry 5 }

mpCbQosAtmVPI       	OBJECT-TYPE
                    		SYNTAX  Unsigned32(0..4095)
                    		MAX-ACCESS  read-only
                    		STATUS  current
                    		DESCRIPTION
                    			"VPI for the ATMVC to which this service is attached. This field 
                    			only make sense if the service policy is attached to a ATM VC."
                    		::= { mpCbQosServicePolicyEntry 6 }

mpCbQosAtmVCI       	OBJECT-TYPE
                    		SYNTAX  Unsigned32(0..65535)
                    		MAX-ACCESS  read-only
                    		STATUS  current
                    		DESCRIPTION
                    			"VCI for the ATMVC to which this service is attached. This field 
                    			only make sense if the service policy is attached to a ATM VC."
                    		::= { mpCbQosServicePolicyEntry 7 }

mpCbQosEntityIndex  	OBJECT-TYPE
                    		SYNTAX  Integer32
                    		MAX-ACCESS  read-only
                    		STATUS  current
                    		DESCRIPTION
                    			"In cases where the policy is attached to an entity e.g. 
                    			control-plane, this object represents the entity physical index 
                    			of the entity to which the policy has been attached. A value zero 
                    			may be returned if the policy is not attached to a physical 
                    			entity or the entPhysicalTable is not supported on the SNMP agent."
                    		::= { mpCbQosServicePolicyEntry 8 }

mpCbQosVlanIndex    	OBJECT-TYPE
                    		SYNTAX  Unsigned32(0..4094)
                    		MAX-ACCESS  read-only
                    		STATUS  current
                    		DESCRIPTION
                    			"If the service policy is attached to a particular vlan on a 
                    			trunk or multi-vlan access port, then this object specifies the 
                    			corresponding VLAN. In all other cases the value of this object 
                    			is '0'."
                    		::= { mpCbQosServicePolicyEntry 9 }


------------------------------------------------------------------------------
mpCbQosInterfacePolicy	OBJECT IDENTIFIER ::= { maipuCBQosMIBObjects 2 }

mpCbQosInterfacePolicyTable	OBJECT-TYPE
                    		SYNTAX  SEQUENCE OF  MpCbQosInterfacePolicyEntry
                    		MAX-ACCESS  not-accessible
                    		STATUS  current
                    		DESCRIPTION
                    			"This table describes the service polices that are attached to 
                    			main and sub interfaces."
                    		::= { mpCbQosInterfacePolicy 1 }

mpCbQosInterfacePolicyEntry	OBJECT-TYPE
                    		SYNTAX  MpCbQosInterfacePolicyEntry
                    		MAX-ACCESS  not-accessible
                    		STATUS  current
                    		DESCRIPTION
                    			"Using ifIndex and Direction, each unique index pair translates 
                    			to a service policy that is attached to a main/sub interface, for 
                    			particular traffic direction."
                    		INDEX  { ifIndex,  mpCbQosPolicyDirection }
                    		::= { mpCbQosInterfacePolicyTable 1 }

MpCbQosInterfacePolicyEntry	::= SEQUENCE {
                    			mpCbQosIFPolicyIndex   Unsigned32
                    	             }


mpCbQosIFPolicyIndex	OBJECT-TYPE
                    		SYNTAX  Unsigned32
                    		MAX-ACCESS  read-only
                    		STATUS  current
                    		DESCRIPTION
                    			"An arbitrary (system-assigned) index for all Service Policies. 
                    			This is identical to mpCbQosPolicyIndex."
                    		::= { mpCbQosInterfacePolicyEntry 1 }


------------------------------------------------------------------------------
mpCbQosFrameRelayVCPolicy	OBJECT IDENTIFIER ::= { maipuCBQosMIBObjects 3 }

mpCbQosFrameRelayPolicyTable	OBJECT-TYPE
                    		SYNTAX  SEQUENCE OF  MpCbQosFrameRelayPolicyEntry
                    		MAX-ACCESS  not-accessible
                    		STATUS  current
                    		DESCRIPTION
                    			"This table describes the service polices that are attached to 
                    			Frame Relay DLCIs."
                    		::= { mpCbQosFrameRelayVCPolicy 1 }

mpCbQosFrameRelayPolicyEntry	OBJECT-TYPE
                    		SYNTAX  MpCbQosFrameRelayPolicyEntry
                    		MAX-ACCESS  not-accessible
                    		STATUS  current
                    		DESCRIPTION
                    			"Using ifIndex, FR DLCI, and Direction, each unique index 
                    			combination translates to a service policy that is attached to a 
                    			FR DLCI, for particular traffic direction."
                    		INDEX  { ifIndex,  mpCbQosFrDLCI,  mpCbQosPolicyDirection }
                    		::= { mpCbQosFrameRelayPolicyTable 1 }

MpCbQosFrameRelayPolicyEntry	::= SEQUENCE {
                    			mpCbQosFRPolicyIndex   Unsigned32
                    	             }


mpCbQosFRPolicyIndex	OBJECT-TYPE
                    		SYNTAX  Unsigned32
                    		MAX-ACCESS  read-only
                    		STATUS  current
                    		DESCRIPTION
                    			"An arbitrary (system-assigned) index for all Service Policies. 
                    			This is identical to mpCbQosPolicyIndex."
                    		::= { mpCbQosFrameRelayPolicyEntry 1 }


------------------------------------------------------------------------------
mpCbQosATMPVCPolicy 	OBJECT IDENTIFIER ::= { maipuCBQosMIBObjects 4 }

mpCbQosATMPVCPolicyTable	OBJECT-TYPE
                    		SYNTAX  SEQUENCE OF  MpCbQosATMPVCPolicyEntry
                    		MAX-ACCESS  not-accessible
                    		STATUS  current
                    		DESCRIPTION
                    			"This table describes the policies that are attached to a ATM PVC."
                    		::= { mpCbQosATMPVCPolicy 1 }

mpCbQosATMPVCPolicyEntry	OBJECT-TYPE
                    		SYNTAX  MpCbQosATMPVCPolicyEntry
                    		MAX-ACCESS  not-accessible
                    		STATUS  current
                    		DESCRIPTION
                    			"Using ifIndex, VPI, VCI, and Direction, each unique index 
                    			combination translates to a service policy that is attached to a 
                    			ATM VC, for particular traffic direction."
                    		INDEX  { ifIndex,  mpCbQosAtmVPI,  mpCbQosAtmVCI,  mpCbQosPolicyDirection }
                    		::= { mpCbQosATMPVCPolicyTable 1 }

MpCbQosATMPVCPolicyEntry	::= SEQUENCE {
                    			mpCbQosATMPVCPolicyIndex   Unsigned32
                    	             }


mpCbQosATMPVCPolicyIndex	OBJECT-TYPE
                    		SYNTAX  Unsigned32
                    		MAX-ACCESS  read-only
                    		STATUS  current
                    		DESCRIPTION
                    			"An arbitrary (system-assigned) index for all Service Policies. 
                    			This is identical to mpCbQosPolicyIndex."
                    		::= { mpCbQosATMPVCPolicyEntry 1 }


------------------------------------------------------------------------------
mpCbQosObjects      	OBJECT IDENTIFIER ::= { maipuCBQosMIBObjects 5 }

mpCbQosObjectsTable 	OBJECT-TYPE
                    		SYNTAX  SEQUENCE OF  MpCbQosObjectsEntry
                    		MAX-ACCESS  not-accessible
                    		STATUS  current
                    		DESCRIPTION
                    			"This table specifies QoS objects (classmap, policymap, match 
                    			statements, and actions) hierarchy. This table also provide 
                    			relationship between each PolicyIndex/ObjectsIndex pair and the 
                    			ConfigIndex. ConfigIndex is essential for querying any 
                    			configuration tables."
                    		::= { mpCbQosObjects 1 }

mpCbQosObjectsEntry 	OBJECT-TYPE
                    		SYNTAX  MpCbQosObjectsEntry
                    		MAX-ACCESS  not-accessible
                    		STATUS  current
                    		DESCRIPTION
                    			"A QoS object entry. Objects covered in this table are PolicyMap, 
                    			ClassMap, Match Statements, and Actions. Each entry is indexed by 
                    			system-generated mpCbQosPolicyIndex, and mpCbQosObjectsIndex, 
                    			which represents a runtime instance of a QoS object. In 
                    			conjunction with the mpCbQosParentObjectsIndex, a management 
                    			station can determine the hierarchical relationship of those QoS 
                    			objects. Given that classmaps and service policies can be nested 
                    			entites, each entry in this table represents a unique instance of 
                    			such object. Each runtime object instance has a corresponding 
                    			config object, which contains the configuration information of 
                    			such QoS object. The config object is indexed by 
                    			mpCbQosConfigIndex."
                    		INDEX  { mpCbQosPolicyIndex,  mpCbQosObjectsIndex }
                    		::= { mpCbQosObjectsTable 1 }

MpCbQosObjectsEntry 	::= SEQUENCE {
                    			mpCbQosObjectsIndex    Unsigned32,
                    			mpCbQosConfigIndex     Unsigned32,
                    			mpCbQosObjectsType     INTEGER,
                    			mpCbQosParentObjectsIndex   Unsigned32
                    	             }


mpCbQosObjectsIndex 	OBJECT-TYPE
                    		SYNTAX  Unsigned32
                    		MAX-ACCESS  not-accessible
                    		STATUS  current
                    		DESCRIPTION
                    			"An arbitrary (system-assigned) instance specific index for 
                    			mpCbQosObjectsEntry."
                    		::= { mpCbQosObjectsEntry 1 }

mpCbQosConfigIndex  	OBJECT-TYPE
                    		SYNTAX  Unsigned32
                    		MAX-ACCESS  read-only
                    		STATUS  current
                    		DESCRIPTION
                    			"An arbitrary (system-assigned) config (instance independent) 
                    			index for each Object. Each objects having the same configuration 
                    			share the same config index."
                    		::= { mpCbQosObjectsEntry 2 }

mpCbQosObjectsType  	OBJECT-TYPE
                    		SYNTAX  INTEGER {
                    			          policymap(1),
                    			          classmap(2),
                    			          matchStatement(3),
                    			          queueing(4),
                    			          randomDetect(5),
                    			          trafficShaping(6),
                    			          police(7),
                    			          set(8)
                    			        }
                    		MAX-ACCESS  read-only
                    		STATUS  current
                    		DESCRIPTION
                    			"The type of the QoS object."
                    		::= { mpCbQosObjectsEntry 3 }

mpCbQosParentObjectsIndex	OBJECT-TYPE
                    		SYNTAX  Unsigned32
                    		MAX-ACCESS  read-only
                    		STATUS  current
                    		DESCRIPTION
                    			"The parent instance index of a QoS object. For a ClassMap, the 
                    			parent index would be the index of the attached PolicyMap. For a 
                    			Match Statement, the parent index would be the index of the 
                    			ClassMap that uses this Match Statement. For an action, the 
                    			parent index would be the index of the ClassMap that applies such 
                    			Action. For a non-hierarchical PolicyMap, the parent would be the 
                    			logical interface to which the policy is attached, thus the 
                    			parent index would be 0. For a hierarchical PolicyMap, the parent 
                    			index would be the index of the ClassMap to which the nested 
                    			policy is attached."
                    		::= { mpCbQosObjectsEntry 4 }


------------------------------------------------------------------------------
mpCbQosPolicyMapCfg 	OBJECT IDENTIFIER ::= { maipuCBQosMIBObjects 6 }

mpCbQosPolicyMapCfgTable	OBJECT-TYPE
                    		SYNTAX  SEQUENCE OF  MpCbQosPolicyMapCfgEntry
                    		MAX-ACCESS  not-accessible
                    		STATUS  current
                    		DESCRIPTION
                    			"This table specifies Policymap configuration information."
                    		::= { mpCbQosPolicyMapCfg 1 }

mpCbQosPolicyMapCfgEntry	OBJECT-TYPE
                    		SYNTAX  MpCbQosPolicyMapCfgEntry
                    		MAX-ACCESS  not-accessible
                    		STATUS  current
                    		DESCRIPTION
                    			"Each entry in this table describes configuration information 
                    			about a policymap. The information includes: Name, and it's 
                    			description."
                    		INDEX  { mpCbQosConfigIndex }
                    		::= { mpCbQosPolicyMapCfgTable 1 }

MpCbQosPolicyMapCfgEntry	::= SEQUENCE {
                    			mpCbQosPolicyMapName   DisplayString,
                    			mpCbQosPolicyMapDesc   DisplayString
                    	             }


mpCbQosPolicyMapName	OBJECT-TYPE
                    		SYNTAX  DisplayString(SIZE(0..255))
                    		MAX-ACCESS  read-only
                    		STATUS  current
                    		DESCRIPTION
                    			"Name of the Policymap."
                    		::= { mpCbQosPolicyMapCfgEntry 1 }

mpCbQosPolicyMapDesc	OBJECT-TYPE
                    		SYNTAX  DisplayString(SIZE(0..255))
                    		MAX-ACCESS  read-only
                    		STATUS  current
                    		DESCRIPTION
                    			"Description of the PolicyMap."
                    		::= { mpCbQosPolicyMapCfgEntry 2 }


------------------------------------------------------------------------------
mpCbQosClassMapCfg  	OBJECT IDENTIFIER ::= { maipuCBQosMIBObjects 7 }

mpCbQosCMCfgTable   	OBJECT-TYPE
                    		SYNTAX  SEQUENCE OF  MpCbQosCMCfgEntry
                    		MAX-ACCESS  not-accessible
                    		STATUS  current
                    		DESCRIPTION
                    			"This table specifies ClassMap configuration information."
                    		::= { mpCbQosClassMapCfg 1 }

mpCbQosCMCfgEntry   	OBJECT-TYPE
                    		SYNTAX  MpCbQosCMCfgEntry
                    		MAX-ACCESS  not-accessible
                    		STATUS  current
                    		DESCRIPTION
                    			"Each entry in this table describes configuration information 
                    			about a classmap. The information includes: Name, and it's 
                    			description and whether it is a Match-All or Match-Any class."
                    		INDEX  { mpCbQosConfigIndex }
                    		::= { mpCbQosCMCfgTable 1 }

MpCbQosCMCfgEntry   	::= SEQUENCE {
                    			mpCbQosCMName          DisplayString,
                    			mpCbQosCMDesc          DisplayString,
                    			mpCbQosCMInfo          INTEGER
                    	             }


mpCbQosCMName       	OBJECT-TYPE
                    		SYNTAX  DisplayString(SIZE(0..255))
                    		MAX-ACCESS  read-only
                    		STATUS  current
                    		DESCRIPTION
                    			"Name of the Classmap."
                    		::= { mpCbQosCMCfgEntry 1 }

mpCbQosCMDesc       	OBJECT-TYPE
                    		SYNTAX  DisplayString(SIZE(0..255))
                    		MAX-ACCESS  read-only
                    		STATUS  current
                    		DESCRIPTION
                    			"Description of the Classmap."
                    		::= { mpCbQosCMCfgEntry 2 }

mpCbQosCMInfo       	OBJECT-TYPE
                    		SYNTAX  INTEGER {
                    			          none(1),
                    			          matchAll(2),
                    			          matchAny(3)
                    			        }
                    		MAX-ACCESS  read-only
                    		STATUS  current
                    		DESCRIPTION
                    			"Match all vs Match any in a given class."
                    		::= { mpCbQosCMCfgEntry 3 }


------------------------------------------------------------------------------
mpCbQosMatchStmtCfg 	OBJECT IDENTIFIER ::= { maipuCBQosMIBObjects 8 }

mpCbQosMatchStmtCfgTable	OBJECT-TYPE
                    		SYNTAX  SEQUENCE OF  MpCbQosMatchStmtCfgEntry
                    		MAX-ACCESS  not-accessible
                    		STATUS  current
                    		DESCRIPTION
                    			"This table specifies ClassMap configuration information."
                    		::= { mpCbQosMatchStmtCfg 1 }

mpCbQosMatchStmtCfgEntry	OBJECT-TYPE
                    		SYNTAX  MpCbQosMatchStmtCfgEntry
                    		MAX-ACCESS  not-accessible
                    		STATUS  current
                    		DESCRIPTION
                    			"Each entry in this table describes configuration information 
                    			about a MatchStatement. The information includes: Name, and 
                    			whether it is a Match or Match-Not tatement. This table contains 
                    			configuration information only, no statistics associated with it. 
                    			Therefore, it is indexed by the mpCbQosConfigIndex of each 
                    			MatchStatement."
                    		INDEX  { mpCbQosConfigIndex }
                    		::= { mpCbQosMatchStmtCfgTable 1 }

MpCbQosMatchStmtCfgEntry	::= SEQUENCE {
                    			mpCbQosMatchStmtName   DisplayString,
                    			mpCbQosMatchStmtInfo   INTEGER
                    	             }


mpCbQosMatchStmtName	OBJECT-TYPE
                    		SYNTAX  DisplayString(SIZE(0..255))
                    		MAX-ACCESS  read-only
                    		STATUS  current
                    		DESCRIPTION
                    			"Name of the Match Statement."
                    		::= { mpCbQosMatchStmtCfgEntry 1 }

mpCbQosMatchStmtInfo	OBJECT-TYPE
                    		SYNTAX  INTEGER {
                    			          none(1),
                    			          matchNot(2)
                    			        }
                    		MAX-ACCESS  read-only
                    		STATUS  current
                    		DESCRIPTION
                    			"Match vs Match Not in a given class."
                    		::= { mpCbQosMatchStmtCfgEntry 2 }


------------------------------------------------------------------------------
mpCbQosQueueingCfg  	OBJECT IDENTIFIER ::= { maipuCBQosMIBObjects 9 }

mpCbQosQueueingCfgTable	OBJECT-TYPE
                    		SYNTAX  SEQUENCE OF  MpCbQosQueueingCfgEntry
                    		MAX-ACCESS  not-accessible
                    		STATUS  current
                    		DESCRIPTION
                    			"This table specifies Queueing Action configuration information."
                    		::= { mpCbQosQueueingCfg 1 }

mpCbQosQueueingCfgEntry	OBJECT-TYPE
                    		SYNTAX  MpCbQosQueueingCfgEntry
                    		MAX-ACCESS  not-accessible
                    		STATUS  current
                    		DESCRIPTION
                    			"Each entry in this table describes configuration information 
                    			about a queueing action. The information includes: Bandwidth, 
                    			Units, Flow Enabled, Priority Enabled, and Q size."
                    		INDEX  { mpCbQosConfigIndex }
                    		::= { mpCbQosQueueingCfgTable 1 }

MpCbQosQueueingCfgEntry	::= SEQUENCE {
                    			mpCbQosQueueingCfgBandwidth   Unsigned32,
                    			mpCbQosQueueingCfgBandwidthUnits   INTEGER,
                    			mpCbQosQueueingCfgFlowEnabled   TruthValue,
                    			mpCbQosQueueingCfgPriorityEnabled   TruthValue,
                    			mpCbQosQueueingCfgDynamicQNumber   Integer32,
                    			mpCbQosQueueingCfgPrioBurstSize   Unsigned32,
                    			mpCbQosQueueingCfgQLimitUnits   INTEGER,
                    			mpCbQosQueueingCfgAggregateQLimit   Unsigned32,
                    			mpCbQosQueueingCfgAggrQLimitTime   Unsigned32,
                    			mpCbQosQueueingCfgIndividualQLimit   Unsigned32
                    	             }


mpCbQosQueueingCfgBandwidth	OBJECT-TYPE
                    		SYNTAX  Unsigned32
                    		MAX-ACCESS  read-only
                    		STATUS  current
                    		DESCRIPTION
                    			"The type of bandwidth configuration value represented by this 
                    			object is indicated by the value of 
                    			mpCbQosQueueingCfgBandwidthUnits for this entry. If the 
                    			mpCbQosQueueingCfgBandwidthUnits value is 'kbps(1)' or 
                    			'percentage(2)', this object represents the configured bandwidth 
                    			allocated to this traffic class.In the case of a bandwidth 
                    			policy, this value represents a minimum bandwidth guarantee for 
                    			the traffic class. In the case of a priority policy, this value 
                    			represents the maximum rate at which priority service is 
                    			guaranteed. If the mpCbQosQueueingCfgBandwidthUnits value is 
                    			'percentageRemaining(3)', this object represents the percentage 
                    			of the unallocated bandwidth to allocate to this class.  If the 
                    			mpCbQosQueueingCfgBandwidthUnits value is 'ratioRemaining(4)', 
                    			this object represents the ratio value, relative to other class' 
                    			configured ratio values, used to determine the portion of the 
                    			unallocated bandwidth to apply to this class."
                    		::= { mpCbQosQueueingCfgEntry 1 }

mpCbQosQueueingCfgBandwidthUnits	OBJECT-TYPE
                    		SYNTAX  INTEGER {
                    			          kbps(1),
                    			          percentage(2),
                    			          percentageRemaining(3),
                    			          ratioRemaining(4)
                    			        }
                    		MAX-ACCESS  read-only
                    		STATUS  current
                    		DESCRIPTION
                    			"Units of the accompanying mpCbQosQueueingCfgbandwidth parameter."
                    		::= { mpCbQosQueueingCfgEntry 2 }

mpCbQosQueueingCfgFlowEnabled	OBJECT-TYPE
                    		SYNTAX  TruthValue
                    		MAX-ACCESS  read-only
                    		STATUS  current
                    		DESCRIPTION
                    			"Boolean to indicate if flow-based fair-queue is enabled for this 
                    			class."
                    		::= { mpCbQosQueueingCfgEntry 3 }

mpCbQosQueueingCfgPriorityEnabled	OBJECT-TYPE
                    		SYNTAX  TruthValue
                    		MAX-ACCESS  read-only
                    		STATUS  current
                    		DESCRIPTION
                    			"Boolean to indicate if low latency queueing (priority) is 
                    			enabled for this class."
                    		::= { mpCbQosQueueingCfgEntry 4 }

mpCbQosQueueingCfgDynamicQNumber	OBJECT-TYPE
                    		SYNTAX  Integer32(0..32768)
                    		MAX-ACCESS  read-only
                    		STATUS  current
                    		DESCRIPTION
                    			"Number of dynamic queues supported when flow-based fair-queue is 
                    			in use."
                    		::= { mpCbQosQueueingCfgEntry 5 }

mpCbQosQueueingCfgPrioBurstSize	OBJECT-TYPE
                    		SYNTAX  Unsigned32
                    		UNITS  "Bytes"
                    		MAX-ACCESS  read-only
                    		STATUS  current
                    		DESCRIPTION
                    			"In the priority queue, this is the number of bytes allowed in a 
                    			single burst. This parameter only makes sense if Priority is 
                    			enabled."
                    		::= { mpCbQosQueueingCfgEntry 6 }

mpCbQosQueueingCfgQLimitUnits	OBJECT-TYPE
                    		SYNTAX  INTEGER {
                    			          packets(1),
                    			          bytes(2),
                    			          cells(3),
                    			          ms(4),
                    			          us(5)
                    			        }
                    		MAX-ACCESS  read-only
                    		STATUS  current
                    		DESCRIPTION
                    			"Represents the unit type of mpCbQosQueueingCfgAggregateQLimit 
                    			and mpCbQosQueueingCfgIndividualQLimit objects."
                    		::= { mpCbQosQueueingCfgEntry 7 }

mpCbQosQueueingCfgAggregateQLimit	OBJECT-TYPE
                    		SYNTAX  Unsigned32
                    		MAX-ACCESS  read-only
                    		STATUS  current
                    		DESCRIPTION
                    			"Maximum allowed queue size for all the individual queues 
                    			associated with this class. When the queue size exceed this 
                    			value, the packets will be dropped."
                    		::= { mpCbQosQueueingCfgEntry 8 }

mpCbQosQueueingCfgAggrQLimitTime	OBJECT-TYPE
						    SYNTAX  Unsigned32
						    UNITS  "milli-seconds"
						    MAX-ACCESS  read-only
						    STATUS  current
						    DESCRIPTION
						        "Maximum allowed queue size in milli-seconds for all individual 
						        queues associated with this class.  It is internally converted to 
						        bytes by using the bandwidth that is available for the class." 
						    ::= { mpCbQosQueueingCfgEntry 9 }

mpCbQosQueueingCfgIndividualQLimit	OBJECT-TYPE
                            SYNTAX          Unsigned32
                            MAX-ACCESS      read-only
                            STATUS          current
                            DESCRIPTION
                            	"Maximum number of units that can be held in an individual 
                            	Flow-based fair-queue associated with this class before it drops 
                            	packets. This field only makes sense in the context of Flow-based 
                            	fair-queueing."
                            ::= { mpCbQosQueueingCfgEntry 10 }

------------------------------------------------------------------------------
mpCbQosREDCfg       	OBJECT IDENTIFIER ::= { maipuCBQosMIBObjects 10 }

mpCbQosREDCfgTable  	OBJECT-TYPE
                    		SYNTAX  SEQUENCE OF  MpCbQosREDCfgEntry
                    		MAX-ACCESS  not-accessible
                    		STATUS  current
                    		DESCRIPTION
                    			"This table specifies WRED Action configuration information."
                    		::= { mpCbQosREDCfg 1 }

mpCbQosREDCfgEntry  	OBJECT-TYPE
                    		SYNTAX  MpCbQosREDCfgEntry
                    		MAX-ACCESS  not-accessible
                    		STATUS  current
                    		DESCRIPTION
                    			"Each entry in this table describes configuration information 
                    			about a WRED Action.  The table holds global (per traffic class) 
                    			configuration like: Expon Weight and Mean Q size."
                    		INDEX  { mpCbQosConfigIndex }
                    		::= { mpCbQosREDCfgTable 1 }

MpCbQosREDCfgEntry  	::= SEQUENCE {
                    			mpCbQosREDCfgExponWeight   Integer32,
                    			mpCbQosREDCfgDscpPrec   INTEGER,
                    			mpCbQosREDCfgECNEnabled   TruthValue
                    	             }


mpCbQosREDCfgExponWeight	OBJECT-TYPE
                    		SYNTAX  Integer32(1..16)
                    		MAX-ACCESS  read-only
                    		STATUS  current
                    		DESCRIPTION
                    			"The decay factor for the queue average calculation. The decay 
                    			factor is equal to raising 2 to the power of N, where N could be 
                    			up to 16. The smaller the number, the faster it decays."
                    		::= { mpCbQosREDCfgEntry 1 }

mpCbQosREDCfgDscpPrec	OBJECT-TYPE
                    		SYNTAX  INTEGER {
                    			          precedence(1),
                    			          dscp(2),
                    			          discardClass(3),
                    			          l2Cos(4),
                    			          atmClp(5),
                    			          mplsExp(6),
                    			          redDefault(7),
                    			          redUserDefault(8)
                    			        }
                    		MAX-ACCESS  read-only
                    		STATUS  current
                    		DESCRIPTION
                    			"The Classification mechanism used by RED."
                    		::= { mpCbQosREDCfgEntry 2 }

mpCbQosREDCfgECNEnabled		OBJECT-TYPE
						    SYNTAX  TruthValue
						    MAX-ACCESS  read-only
						    STATUS  current
						    DESCRIPTION
						        "Boolean to indicate if explicit congestion notification enabled 
						        for this class." 
						    ::= { mpCbQosREDCfgEntry 3 }


------------------------------------------------------------------------------
mpCbQosREDClassCfg  	OBJECT IDENTIFIER ::= { maipuCBQosMIBObjects 11 }

mpCbQosREDClassCfgTable	OBJECT-TYPE
                    		SYNTAX  SEQUENCE OF  MpCbQosREDClassCfgEntry
                    		MAX-ACCESS  not-accessible
                    		STATUS  current
                    		DESCRIPTION
                    			"This table specifies WRED Action configuration information on a 
                    			per IP precedence basis."
                    		::= { mpCbQosREDClassCfg 1 }

mpCbQosREDClassCfgEntry	OBJECT-TYPE
                    		SYNTAX  MpCbQosREDClassCfgEntry
                    		MAX-ACCESS  not-accessible
                    		STATUS  current
                    		DESCRIPTION
                    			"Each entry in this table describes configuration information 
                    			about a WRED Action. The table holds the per IP precedence based 
                    			WRED configuration parameters."
                    		INDEX  { mpCbQosConfigIndex,  mpCbQosREDValue }
                    		::= { mpCbQosREDClassCfgTable 1 }

MpCbQosREDClassCfgEntry	::= SEQUENCE {
                    			mpCbQosREDValue        Integer32,
                    			mpCbQosREDCfgPktDropProb   Integer32,
                    			mpCbQosREDClassCfgMinThresholdUnit   INTEGER,
                    			mpCbQosREDClassCfgMaxThresholdUnit   INTEGER,
                    			mpCbQosREDClassCfgMinThreshold   Unsigned32,
                    			mpCbQosREDClassCfgMaxThreshold   Unsigned32,
                    			mpCbQosREDClassCfgMinThresholdTime   Unsigned32,
                    			mpCbQosREDClassCfgMaxThresholdTime   Unsigned32
                    	             }


mpCbQosREDValue     	OBJECT-TYPE
                    		SYNTAX  Integer32(0..63)
                    		MAX-ACCESS  not-accessible
                    		STATUS  current
                    		DESCRIPTION
                    			"The IP precedence or IP DSCP of this entry."
                    		::= { mpCbQosREDClassCfgEntry 1 }

mpCbQosREDCfgPktDropProb	OBJECT-TYPE
                    		SYNTAX  Integer32(1..65536)
                    		MAX-ACCESS  read-only
                    		STATUS  current
                    		DESCRIPTION
                    			"Denominator for the fraction of packets dropped when the average 
                    			queue depth is MaxDepthThreshold. For example, if the denominator 
                    			is 10, one out of every 10 packets is dropped when the average 
                    			queue is at the MaxDepthThreshold."
                    		::= { mpCbQosREDClassCfgEntry 2 }

mpCbQosREDClassCfgMinThresholdUnit	OBJECT-TYPE
                    		SYNTAX  INTEGER {
                    			          packets(1),
                    			          bytes(2),
                    			          cells(3),
                    			          ms(4),
                    			          us(5)
                    			        }
                    		MAX-ACCESS  read-only
                    		STATUS  current
                    		DESCRIPTION
                    			"Represents the unit type to measure the RED thresholds. The 
                    			objects covered is mpCbQosREDClassCfgMinThreshold."
                    		::= { mpCbQosREDClassCfgEntry 3 }

mpCbQosREDClassCfgMaxThresholdUnit	OBJECT-TYPE
                    		SYNTAX  INTEGER {
                    			          packets(1),
                    			          bytes(2),
                    			          cells(3),
                    			          ms(4),
                    			          us(5)
                    			        }
                    		MAX-ACCESS  read-only
                    		STATUS  current
                    		DESCRIPTION
                    			"Represents the unit type to measure the RED thresholds. The 
                    			objects covered is mpCbQosREDClassCfgMaxThreshold."
                    		::= { mpCbQosREDClassCfgEntry 4 }

mpCbQosREDClassCfgMinThreshold	OBJECT-TYPE
                    		SYNTAX  Unsigned32
                    		MAX-ACCESS  read-only
                    		STATUS  current
                    		DESCRIPTION
                    			"The minimum WRED threshold value. When the average queue length 
                    			reaches this number, WRED begins to drop packets according to RED 
                    			Mechanism specificed in mpCbQosREDCfgDscpPrec."
                    		::= { mpCbQosREDClassCfgEntry 5 }

mpCbQosREDClassCfgMaxThreshold	OBJECT-TYPE
                    		SYNTAX  Unsigned32
                    		MAX-ACCESS  read-only
                    		STATUS  current
                    		DESCRIPTION
                    			"The maximum WRED threshold value. When the average queue length 
                    			exceeds this number, WRED drops all packets according to RED 
                    			Mechanism specificed in mpCbQosREDCfgDscpPrec."
                    		::= { mpCbQosREDClassCfgEntry 6 }

mpCbQosREDClassCfgMinThresholdTime	OBJECT-TYPE
						    SYNTAX  Unsigned32
						    UNITS  "milli-seconds"
						    MAX-ACCESS  read-only
						    STATUS  current
						    DESCRIPTION
						        "The minimum WRED threshold value specified in milli-seconds.  
						        The milli-second value is internally converted to bytes by using 
						        the bandwidth that is available for the class." 
						    ::= { mpCbQosREDClassCfgEntry 7 }

mpCbQosREDClassCfgMaxThresholdTime	OBJECT-TYPE
						    SYNTAX  Unsigned32
						    UNITS  "milli-seconds"
						    MAX-ACCESS  read-only
						    STATUS  current
						    DESCRIPTION
						        "The maximum WRED threshold value specified in milli-seconds.  
						        The milli-second value is internally converted to bytes by using 
						        the bandwidth that is available for the class." 
						    ::= { mpCbQosREDClassCfgEntry 8 }


------------------------------------------------------------------------------
mpCbQosPoliceCfg    	OBJECT IDENTIFIER ::= { maipuCBQosMIBObjects 12 }

mpCbQosPoliceCfgTable	OBJECT-TYPE
                    		SYNTAX  SEQUENCE OF  MpCbQosPoliceCfgEntry
                    		MAX-ACCESS  not-accessible
                    		STATUS  current
                    		DESCRIPTION
                    			"This table specifies Police Action configuration information."
                    		::= { mpCbQosPoliceCfg 1 }

mpCbQosPoliceCfgEntry	OBJECT-TYPE
                    		SYNTAX  MpCbQosPoliceCfgEntry
                    		MAX-ACCESS  not-accessible
                    		STATUS  current
                    		DESCRIPTION
                    			"Each entry in this table describes configuration information 
                    			about a Police Action.  The table holds Policy configuration 
                    			parameters, such as rate, burst size, and actions based on 
                    			traffic rates."
                    		INDEX  { mpCbQosConfigIndex }
                    		::= { mpCbQosPoliceCfgTable 1 }

MpCbQosPoliceCfgEntry	::= SEQUENCE {
                    			mpCbQosPoliceCfgRate64   Unsigned64,
                    			mpCbQosPoliceCfgBurstSize   Unsigned32,
                    			mpCbQosPoliceCfgExtBurstSize   Unsigned32,
                    			mpCbQosPoliceCfgPir64   Unsigned64,
                    			mpCbQosPoliceCfgRateType   INTEGER,
                    			mpCbQosPoliceCfgPercentRateValue   Unsigned32,
                    			mpCbQosPoliceCfgPercentPirValue   Unsigned32,
                    			mpCbQosPoliceCfgCellRate   Unsigned32,
                    			mpCbQosPoliceCfgCellPir   Unsigned32,
                    			mpCbQosPoliceCfgBurstCell   Unsigned32,
                    			mpCbQosPoliceCfgExtBurstCell   Unsigned32,
                    			mpCbQosPoliceCfgBurstTime   Unsigned32,
                    			mpCbQosPoliceCfgExtBurstTime   Unsigned32
                    	             }


mpCbQosPoliceCfgRate64	OBJECT-TYPE
                    		SYNTAX  Unsigned64
                    		UNITS  "bits/second"
                    		MAX-ACCESS  read-only
                    		STATUS  current
                    		DESCRIPTION
                    			"The committed policing rate in bits/second. This is the 
                    			sustained rate permitted by policing."
                    		::= { mpCbQosPoliceCfgEntry 1 }

mpCbQosPoliceCfgBurstSize	OBJECT-TYPE
                    		SYNTAX  Unsigned32
                    		UNITS  "Octets"
                    		MAX-ACCESS  read-only
                    		STATUS  current
                    		DESCRIPTION
                    			"The amount of traffic, in bytes, in excess of the committed 
                    			policing rate that will be permitted by the policing feature."
                    		::= { mpCbQosPoliceCfgEntry 2 }

mpCbQosPoliceCfgExtBurstSize	OBJECT-TYPE
                    		SYNTAX  Unsigned32
                    		UNITS  "Octets"
                    		MAX-ACCESS  read-only
                    		STATUS  current
                    		DESCRIPTION
                    			"The amount of traffic, in bytes, in excess of the burst limit, 
                    			which may be conditionally permitted by the policing feature. 
                    			The probability that the traffic is not permitted increases as 
                    			the received burst size increases."
                    		::= { mpCbQosPoliceCfgEntry 3 }

mpCbQosPoliceCfgPir64	OBJECT-TYPE
						    SYNTAX  Unsigned64
						    UNITS  "bits/second"
						    MAX-ACCESS  read-only
						    STATUS  current
						    DESCRIPTION
						        "The committed policing rate in bits/second. This is the peak 
						        rate permitted by two rate policing."
						    ::= { mpCbQosPoliceCfgEntry 4 }

mpCbQosPoliceCfgRateType	OBJECT-TYPE
						    SYNTAX  INTEGER {
                			          bps(1),
                			          percentage(2),
                			          cps(3)
						            }
						    MAX-ACCESS      read-only
						    STATUS          current
						    DESCRIPTION
						        "The rate type that configured for CIR & PIR. 1 means rates are 
						        configured in bps. 2 means rates are configured in percentage. 3 
						        means rates are configured in cps." 
						    ::= { mpCbQosPoliceCfgEntry 5 }

mpCbQosPoliceCfgPercentRateValue	OBJECT-TYPE
						    SYNTAX  Unsigned32 (0..100)
						    UNITS  "% of Interface Bandwidth"
						    MAX-ACCESS  read-only
						    STATUS  current
						    DESCRIPTION
						        "The committed policing rate in percentage.  Its value is valid 
						        only when mpCbQosPoliceCfgRateType equals to 2."
						    ::= { mpCbQosPoliceCfgEntry 6 }

mpCbQosPoliceCfgPercentPirValue		OBJECT-TYPE
						    SYNTAX  Unsigned32 (0..100)
						    UNITS  "% of Interface Bandwidth"
						    MAX-ACCESS  read-only
						    STATUS  current
						    DESCRIPTION
						        "The peak policing rate in percentage. Its value is valid only 
						        when mpCbQosPoliceCfgRateType equals to 2."
						    ::= { mpCbQosPoliceCfgEntry 7 }

mpCbQosPoliceCfgCellRate	OBJECT-TYPE
						    SYNTAX  Unsigned32
						    UNITS  "cells/second"
						    MAX-ACCESS  read-only
						    STATUS  current
						    DESCRIPTION
						        "The committed policing rate in cells/second. Its value is valid 
						        only when mpCbQosPoliceCfgRateType equals to 3."
						    ::= { mpCbQosPoliceCfgEntry 8 }

mpCbQosPoliceCfgCellPir		OBJECT-TYPE
						    SYNTAX  Unsigned32
						    UNITS  "cells/second"
						    MAX-ACCESS  read-only
						    STATUS  current
						    DESCRIPTION
						        "The peak policing rate in cells/second. Its value is valid only when 
						        mpCbQosPoliceCfgRateType equals to 3."
						    ::= { mpCbQosPoliceCfgEntry 9 }

mpCbQosPoliceCfgBurstCell	OBJECT-TYPE
						    SYNTAX  Unsigned32
						    UNITS  "Cells"
						    MAX-ACCESS  read-only
						    STATUS  current
						    DESCRIPTION
						        "The amount of traffic, in cells, in excess of the committed policing 
						        rate that will be permitted by the policing feature."
						    ::= { mpCbQosPoliceCfgEntry 10 }

mpCbQosPoliceCfgExtBurstCell	OBJECT-TYPE
						    SYNTAX  Unsigned32
						    UNITS  "Cells"
						    MAX-ACCESS  read-only
						    STATUS  current
						    DESCRIPTION
						        "The amount of traffic, in cells, in excess of the burst limit, which 
						        may be conditionally permitted by the policing feature. The 
						        probability that the traffic is not permitted increases as the 
						        received burst size increases."
						    ::= { mpCbQosPoliceCfgEntry 11 }

mpCbQosPoliceCfgBurstTime	OBJECT-TYPE
						    SYNTAX   Unsigned32
						    UNITS  "milli-seconds"
						    MAX-ACCESS  read-only
						    STATUS  current
						    DESCRIPTION
						        "The amount of traffic time, in ms (milli-seconds), in excess of the 
						        committed policing rate that will be permitted by the policing 
						        feature. The milli-second value is internally converted to bytes by 
						        using the bandwidth that is available for the class." 
						    ::= { mpCbQosPoliceCfgEntry 12 }

mpCbQosPoliceCfgExtBurstTime	OBJECT-TYPE
						    SYNTAX  Unsigned32
						    UNITS  "milli-seconds"
						    MAX-ACCESS  read-only
						    STATUS  current
						    DESCRIPTION
						        "The amount of traffic time, in ms (milli-seconds), in excess of the 
						        burst limit, which may be conditionally permitted by the policing 
						        feature. The probability that the traffic is not permitted increases 
						        as the received burst size increases.  The milli-second value is 
						        internally converted to bytes by using the bandwidth that is 
						        available for the class." 
						    ::= { mpCbQosPoliceCfgEntry 13 }


------------------------------------------------------------------------------
mpCbQosPoliceActionCfg     OBJECT IDENTIFIER ::= { maipuCBQosMIBObjects 13 }

mpCbQosPoliceActionCfgTable	OBJECT-TYPE
						    SYNTAX  SEQUENCE OF MpCbQosPoliceActionCfgEntry 
						    MAX-ACCESS  not-accessible
						    STATUS  current
						    DESCRIPTION
						        "This table specifies Police Action configuration information."
						    ::= { mpCbQosPoliceActionCfg 1 }

mpCbQosPoliceActionCfgEntry	OBJECT-TYPE
						    SYNTAX  MpCbQosPoliceActionCfgEntry
						    MAX-ACCESS  not-accessible
						    STATUS  current
						    DESCRIPTION
						        "Each entry in this table describes configuration information
						        about Actions for one Police.  The table holds Police action 
						        specific configuration parameters.  This table is a sub-table 
						        for mpCbQosPoliceCfgTable. There is a 1-to-1 association between 
						        one entry here and one entry in mpCbQosPoliceCfgTable. 
						        This table has two indices. The first is mpCbQosConfigIndex which 
						        is drived directly from mpCbQosPoliceCfgTable to keep the 1-to-1 
						        mapping nature between two tables. The second is 
						        mpCbQosPoliceActionCfgIndex used to reference the actual actions 
						        configured."
						    INDEX  { mpCbQosConfigIndex,  mpCbQosPoliceActionCfgIndex }
						    ::= { mpCbQosPoliceActionCfgTable 1 }

MpCbQosPoliceActionCfgEntry ::= SEQUENCE {
						        mpCbQosPoliceActionCfgIndex   Unsigned32,
						        mpCbQosPoliceActionCfgConform   INTEGER,
						        mpCbQosPoliceActionCfgConformSetValue   Unsigned32,
						        mpCbQosPoliceActionCfgExceed   INTEGER,
						        mpCbQosPoliceActionCfgExceedSetValue   Unsigned32,
						        mpCbQosPoliceActionCfgViolate   INTEGER,
						        mpCbQosPoliceActionCfgViolateSetValue   Unsigned32
										}

mpCbQosPoliceActionCfgIndex	OBJECT-TYPE
						    SYNTAX  Unsigned32
						    MAX-ACCESS  not-accessible
						    STATUS  current
						    DESCRIPTION
						        "An arbitrary (system-assigned) index for police actions that are 
						        defined by a police configuration." 
						    ::= { mpCbQosPoliceActionCfgEntry 1 }

mpCbQosPoliceActionCfgConform	OBJECT-TYPE
						    SYNTAX  INTEGER {
                    			          transmit(1),
                    			          setIpDSCP(2),
                    			          setIpPrecedence(3),
                    			          setQosGroup(4),
                    			          drop(5),
                    			          setMplsExp(6),
                    			          setAtmClp(7),
                    			          setFrDe(8),
                    			          setL2Cos(9),
                    			          setDiscardClass(10),
                    			          setMplsExpTopMost(11),
                    			          setIpDscpTunnel(12),
                    			          setIpPrecedenceTunnel(13),
                    			          setL2CosInner(14)
                    			        }
						    MAX-ACCESS  read-only
						    STATUS  current
						    DESCRIPTION
						        "Action to be taken when the traffic is within the configured 
                    			rate, that is, the traffic rate is conforming." 
						    ::= { mpCbQosPoliceActionCfgEntry 2 }

mpCbQosPoliceActionCfgConformSetValue	OBJECT-TYPE
						    SYNTAX   Unsigned32
						    MAX-ACCESS  read-only
						    STATUS  current
						    DESCRIPTION
						        "New packet attribute values for each packet set by police action 
						        defined in mpCbQosPoliceActionCfgConform. This object will be set 
						        to zero if the corresponding police action does not require a set 
						        value, such as no action, drop action or transmit action." 
						    ::= { mpCbQosPoliceActionCfgEntry 3 }

mpCbQosPoliceActionCfgExceed	OBJECT-TYPE
						    SYNTAX  INTEGER {
                    			          transmit(1),
                    			          setIpDSCP(2),
                    			          setIpPrecedence(3),
                    			          setQosGroup(4),
                    			          drop(5),
                    			          setMplsExp(6),
                    			          setAtmClp(7),
                    			          setFrDe(8),
                    			          setL2Cos(9),
                    			          setDiscardClass(10),
                    			          setMplsExpTopMost(11),
                    			          setIpDscpTunnel(12),
                    			          setIpPrecedenceTunnel(13),
                    			          setL2CosInner(14)
                    			        }
						    MAX-ACCESS  read-only
						    STATUS  current
						    DESCRIPTION
						        "Action to be taken when the traffic exceeds the configured rate, 
                    			that is, the traffic is non-conforming." 
						    ::= { mpCbQosPoliceActionCfgEntry 4 }

mpCbQosPoliceActionCfgExceedSetValue	OBJECT-TYPE
						    SYNTAX  Unsigned32
						    MAX-ACCESS  read-only
						    STATUS  current
						    DESCRIPTION
						        "New packet attribute values for each packet set by police action 
						        defined in mpCbQosPoliceActionCfgExceed. This object will be set 
						        to zero if the corresponding police action does not require a set 
						        value, such as no action, drop action or transmit action." 
						    ::= { mpCbQosPoliceActionCfgEntry 5 }

mpCbQosPoliceActionCfgViolate	OBJECT-TYPE
						    SYNTAX  INTEGER {
                    			          transmit(1),
                    			          setIpDSCP(2),
                    			          setIpPrecedence(3),
                    			          setQosGroup(4),
                    			          drop(5),
                    			          setMplsExp(6),
                    			          setAtmClp(7),
                    			          setFrDe(8),
                    			          setL2Cos(9),
                    			          setDiscardClass(10),
                    			          setMplsExpTopMost(11),
                    			          setIpDscpTunnel(12),
                    			          setIpPrecedenceTunnel(13),
                    			          setL2CosInner(14)
                    			        }
						    MAX-ACCESS  read-only
						    STATUS  current
						    DESCRIPTION
						        "Action to be taken when the traffic exceeds the conform and 
                    			exceed token buckets." 
						    ::= { mpCbQosPoliceActionCfgEntry 6 }

mpCbQosPoliceActionCfgViolateSetValue	OBJECT-TYPE
						    SYNTAX  Unsigned32
						    MAX-ACCESS  read-only
						    STATUS  current
						    DESCRIPTION
						        "New packet attribute values for each packet set by police action 
						        defined in mpCbQosPoliceActionCfgViolate. This object will be set 
						        to zero if the corresponding police action does not require a set 
						        value, such as no action, drop action or transmit action." 
						    ::= { mpCbQosPoliceActionCfgEntry 7 }


------------------------------------------------------------------------------
mpCbQosTSCfg        	OBJECT IDENTIFIER ::= { maipuCBQosMIBObjects 14 }

mpCbQosTSCfgTable   	OBJECT-TYPE
                    		SYNTAX  SEQUENCE OF  MpCbQosTSCfgEntry
                    		MAX-ACCESS  not-accessible
                    		STATUS  current
                    		DESCRIPTION
                    			"This table specifies traffic-shaping Action configuration 
                    			information."
                    		::= { mpCbQosTSCfg 1 }

mpCbQosTSCfgEntry   	OBJECT-TYPE
                    		SYNTAX  MpCbQosTSCfgEntry
                    		MAX-ACCESS  not-accessible
                    		STATUS  current
                    		DESCRIPTION
                    			"Each entry in this table describes configuration information 
                    			about a traffic-shaping Action.  The table holds Traffic Shaping 
                    			configuration parameters, such as rate, burst size, and Shaping 
                    			types."
                    		INDEX  { mpCbQosConfigIndex }
                    		::= { mpCbQosTSCfgTable 1 }

MpCbQosTSCfgEntry   	::= SEQUENCE {
                    			mpCbQosTSCfgRate64       Unsigned64,
                    			mpCbQosTSCfgBurstSize   Integer32,
                    			mpCbQosTSCfgExtBurstSize   Integer32,
                    			mpCbQosTSCfgAdaptiveEnabled  TruthValue,
                    			mpCbQosTSCfgAdaptiveRate64   Unsigned64,
                    			mpCbQosTSCfgLimitType        INTEGER,
                    			mpCbQosTSCfgRateType         INTEGER,
                    			mpCbQosTSCfgPercentRateValue Unsigned32,
                    			mpCbQosTSCfgBurstTime        Unsigned32,
                    			mpCbQosTSCfgExtBurstTime     Unsigned32,
                    	             }


mpCbQosTSCfgRate64    	OBJECT-TYPE
                    		SYNTAX  Unsigned64
                    		UNITS  "bits/second"
                    		MAX-ACCESS  read-only
                    		STATUS  current
                    		DESCRIPTION
                    			"The committed traffic-shaping rate in bits/second.  This is the 
                    			sustained rate permitted by the traffic-shaping."
                    		::= { mpCbQosTSCfgEntry 1 }

mpCbQosTSCfgBurstSize	OBJECT-TYPE
                    		SYNTAX  Integer32
                    		UNITS  "bits"
                    		MAX-ACCESS  read-only
                    		STATUS  current
                    		DESCRIPTION
                    			"The amount of traffic, in bits, in excess of the committed 
                    			traffic-shaping rate that will be instantaneously permitted by 
                    			this feature."
                    		::= { mpCbQosTSCfgEntry 2 }

mpCbQosTSCfgExtBurstSize	OBJECT-TYPE
                    		SYNTAX  Integer32
                    		UNITS  "bits"
                    		MAX-ACCESS  read-only
                    		STATUS  current
                    		DESCRIPTION
                    			"The amount of traffic, in bits, in excess of the burst limit, 
                    			which may be conditionally permitted by traffic-shaping feature."
                    		::= { mpCbQosTSCfgEntry 3 }

mpCbQosTSCfgAdaptiveEnabled	OBJECT-TYPE
						    SYNTAX  TruthValue
						    MAX-ACCESS  read-only
						    STATUS  current
						    DESCRIPTION
						        "This object indicates is adaptive traffic-shaping has been 
						        enabled." 
						    ::= { mpCbQosTSCfgEntry 4 }

mpCbQosTSCfgAdaptiveRate64 OBJECT-TYPE
						    SYNTAX  Unsigned64
						    UNITS  "bits/second"
						    MAX-ACCESS  read-only
						    STATUS  current
						    DESCRIPTION
						        "This object represents the current adaptive traffic shaping rate."
						    ::= { mpCbQosTSCfgEntry 5 }


mpCbQosTSCfgLimitType	OBJECT-TYPE
                    		SYNTAX  INTEGER {
                    			          average(1),
                    			          peak(2)
                    			        }
                    		MAX-ACCESS  read-only
                    		STATUS  current
                    		DESCRIPTION
                    			"This object indicates if traffic-shaping is limiting traffic 
                    			based on the peak rate or the average rate."
                    		::= { mpCbQosTSCfgEntry 6 }

mpCbQosTSCfgRateType	OBJECT-TYPE
                    		SYNTAX  INTEGER {
                    			          bps(1),
                    			          percentage(2),
                    			          cps(3)
                    			        }
                    		MAX-ACCESS  read-only
                    		STATUS  current
                    		DESCRIPTION
                    			"The rate type that configured for traffic-shaping. 1 means rate 
                    			is configured in bps (Bits Per Second). 2 means rate is 
                    			configured in percentage. 3 means rates are configured in cps 
                    			(Cells Per Second)."
                    		::= { mpCbQosTSCfgEntry 7 }

mpCbQosTSCfgPercentRateValue	OBJECT-TYPE
                    		SYNTAX  Unsigned32(0..100)
                    		UNITS  "% of Interface Bandwidth"
                    		MAX-ACCESS  read-only
                    		STATUS  current
                    		DESCRIPTION
                    			"The committed traffic-shaping rate in percentage. Its value is 
                    			valid only when mpCbQosTSCfgRateType equals to 2."
                    		::= { mpCbQosTSCfgEntry 8 }

mpCbQosTSCfgBurstTime		OBJECT-TYPE
						    SYNTAX  Unsigned32
						    UNITS  "milli-seconds"
						    MAX-ACCESS  read-only
						    STATUS  current
						    DESCRIPTION
						        "The amount of traffic, in ms, in excess of the committed 
						        traffic-shaping rate that will be instantaneously permitted by 
						        this feature. The milli-second value is internally converted to 
						        bits by using the bandwidth that is available for the class." 
						    ::= { mpCbQosTSCfgEntry 9 }

mpCbQosTSCfgExtBurstTime	OBJECT-TYPE
						    SYNTAX  Unsigned32
						    UNITS  "milli-seconds"
						    MAX-ACCESS  read-only
						    STATUS  current
						    DESCRIPTION
						        "The amount of traffic, in ms, in excess of the burst limit, 
						        which may be conditionnally permitted by traffic-shaping feature. 
						        The milli-second value is internally converted to bits by using 
						        the bandwidth that is available for the class." 
						    ::= { mpCbQosTSCfgEntry 10 }

------------------------------------------------------------------------------
mpCbQosSetCfg       	OBJECT IDENTIFIER ::= { maipuCBQosMIBObjects 15 }

mpCbQosSetCfgTable  	OBJECT-TYPE
                    		SYNTAX  SEQUENCE OF  MpCbQosSetCfgEntry
                    		MAX-ACCESS  not-accessible
                    		STATUS  current
                    		DESCRIPTION
                    			"This table specifies Packet Marking Action configuration 
                    			information."
                    		::= { mpCbQosSetCfg 1 }

mpCbQosSetCfgEntry  	OBJECT-TYPE
                    		SYNTAX  MpCbQosSetCfgEntry
                    		MAX-ACCESS  not-accessible
                    		STATUS  current
                    		DESCRIPTION
                    			"Each entry in this table describes configuration information 
                    			about a Packet Marking Action.  The table holds Packet Marking 
                    			configuration parameters, such as type of packet marking and 
                    			values being set to."
                    		INDEX  { mpCbQosConfigIndex }
                    		::= { mpCbQosSetCfgTable 1 }

MpCbQosSetCfgEntry  	::= SEQUENCE {
                    			mpCbQosSetCfgFeature   BITS,
                    			mpCbQosSetCfgIpDSCPValue   Integer32,
                    			mpCbQosSetCfgIpPrecedenceValue   Integer32,
                    			mpCbQosSetCfgQosGroupValue   Integer32,
                    			mpCbQosSetCfgL2CosValue   Integer32,
                    			mpCbQosSetCfgMplsExpValue   Unsigned32,
                    			mpCbQosSetCfgDiscardClassValue   Unsigned32,
                    			mpCbQosSetCfgMplsExpTopMostValue   Unsigned32,
                    			mpCbQosSetCfgFrFecnBecn   Unsigned32,
                    			mpCbQosSetCfgIpDSCPTunnelValue   Integer32,
                    			mpCbQosSetCfgIpPrecedenceTunnelValue   Integer32,
                    			mpCbQosSetCfgL2CosInnerValue   Integer32,
                    			mpCbQosSetCfgIpTosValue   Integer32
                    	             }


mpCbQosSetCfgFeature	OBJECT-TYPE
                    		SYNTAX  BITS {                        
                    					ipDscp(0),
                    					ipPrecedence(1),
                    					qosGroupNumber(2),
                    					frDeBit(3),
                    					atmClpBit(4),
                    					l2Cos(5),
                    					mplsExp(6),
                    					discardClass(7),
                    					mplsExpTopMost(8),
                    					frFecnBecn(9),
                    					ipDscpTunnel(10),
                    					ipPrecedenceTunnel(11),
                    					l2CosInner(12),
                    					ipTos(13)
                    					}
                    		MAX-ACCESS  read-only
                    		STATUS  current
                    		DESCRIPTION
                    			"The bit-wise position of each packet marking feature."
                    		::= { mpCbQosSetCfgEntry 1 }

mpCbQosSetCfgIpDSCPValue	OBJECT-TYPE
                    		SYNTAX  Integer32(0..63)
                    		MAX-ACCESS  read-only
                    		STATUS  current
                    		DESCRIPTION
                    			"The IP DSCP value at which the packet is being set by the 
                    			packet marking feature."
                    		::= { mpCbQosSetCfgEntry 2 }

mpCbQosSetCfgIpPrecedenceValue	OBJECT-TYPE
                    		SYNTAX  Integer32(0..7)
                    		MAX-ACCESS  read-only
                    		STATUS  current
                    		DESCRIPTION
                    			"The IP precedence value at which the packet is being set by the 
                    			packet marking feature."
                    		::= { mpCbQosSetCfgEntry 3 }

mpCbQosSetCfgQosGroupValue	OBJECT-TYPE
                    		SYNTAX  Integer32
                    		MAX-ACCESS  read-only
                    		STATUS  current
                    		DESCRIPTION
                    			"The QoS Group number at which the packet is being set by the 
                    			packet marking feature."
                    		::= { mpCbQosSetCfgEntry 4 }

mpCbQosSetCfgL2CosValue	OBJECT-TYPE
                    		SYNTAX  Integer32(0..7)
                    		MAX-ACCESS  read-only
                    		STATUS  current
                    		DESCRIPTION
                    			"The Layer 2 Cos value at which the packet is being set by the 
                    			packet marking feature."
                    		::= { mpCbQosSetCfgEntry 5 }

mpCbQosSetCfgMplsExpValue	OBJECT-TYPE
                    		SYNTAX  Unsigned32(0..7)
                    		MAX-ACCESS  read-only
                    		STATUS  current
                    		DESCRIPTION
                    			"The MPLS experimental value at which the packet is being set by 
                    			the packet marking feature."
                    		::= { mpCbQosSetCfgEntry 6 }

mpCbQosSetCfgDiscardClassValue	OBJECT-TYPE
                    		SYNTAX  Unsigned32(0..7)
                    		MAX-ACCESS  read-only
                    		STATUS  current
                    		DESCRIPTION
                    			"The Discard Class value at which the packet is being set by the 
                    			packet marking feature."
                    		::= { mpCbQosSetCfgEntry 7 }

mpCbQosSetCfgMplsExpTopMostValue	OBJECT-TYPE
                    		SYNTAX  Unsigned32(0..7)
                    		MAX-ACCESS  read-only
                    		STATUS  current
                    		DESCRIPTION
                    			"The MPLS experimental value on the topmost label at which the 
                    			packet is being set by the packet marking feature."
                    		::= { mpCbQosSetCfgEntry 8 }

mpCbQosSetCfgFrFecnBecn		OBJECT-TYPE
							SYNTAX  Unsigned32
							MAX-ACCESS  read-only
							STATUS  current
							DESCRIPTION
								"This is a configurable parameter in percentage of the queue 
								size. When the current queue size out of the queue limit is 
								greater than this parameter, both Frame Relay FECN and BECN bits 
								will be set for Frame Relay congestion notification mechanism."     
							::= { mpCbQosSetCfgEntry 9 }

mpCbQosSetCfgIpDSCPTunnelValue	OBJECT-TYPE
                    		SYNTAX  Integer32(0..63)
                    		MAX-ACCESS  read-only
                    		STATUS  current
                    		DESCRIPTION
                    			"The IP DSCP Tunnel field value at which the packet is being set 
                    			by the packet marking feature."
                    		::= { mpCbQosSetCfgEntry 10 }

mpCbQosSetCfgIpPrecedenceTunnelValue	OBJECT-TYPE
                    		SYNTAX  Integer32(0..7)
                    		MAX-ACCESS  read-only
                    		STATUS  current
                    		DESCRIPTION
                    			"The IP precedence Tunnel field value at which the packet is 
                    			being set by the packet marking feature."
                    		::= { mpCbQosSetCfgEntry 11 }

mpCbQosSetCfgL2CosInnerValue	OBJECT-TYPE
							SYNTAX  Integer32(0..7)
							MAX-ACCESS  read-only
							STATUS  current
							DESCRIPTION
								"The value to be set in the 802.1p priority field in the inner 
								802.1q VLAN tag (QinQ). This object is applicable when 
								mpCbQosSetCfgFeature has the 'l2CosInner' bit set."     
							::= { mpCbQosSetCfgEntry 12 }

mpCbQosSetCfgIpTosValue	OBJECT-TYPE
                    		SYNTAX  Integer32(0..255)
                    		MAX-ACCESS  read-only
                    		STATUS  current
                    		DESCRIPTION
                    			"The IP TOS value at which the packet is being set by the 
                    			packet marking feature."
                    		::= { mpCbQosSetCfgEntry 13 }


------------------------------------------------------------------------------
mpCbQosClassMapStats	OBJECT IDENTIFIER ::= { maipuCBQosMIBObjects 16 }

mpCbQosCMStatsTable 	OBJECT-TYPE
                    		SYNTAX  SEQUENCE OF  MpCbQosCMStatsEntry
                    		MAX-ACCESS  not-accessible
                    		STATUS  current
                    		DESCRIPTION
                    			"This table specifies ClassMap related Statistical information."
                    		::= { mpCbQosClassMapStats 1 }

mpCbQosCMStatsEntry 	OBJECT-TYPE
                    		SYNTAX  MpCbQosCMStatsEntry
                    		MAX-ACCESS  not-accessible
                    		STATUS  current
                    		DESCRIPTION
                    			"Each entry in this table describes the statistical information 
                    			about ClassMap. ClassMap specific information you can find in 
                    			this table are: pre/post policy pkt/byte counts, bit rates, drop 
                    			pkt/bytes and no buffer drops."
                    		INDEX  { mpCbQosPolicyIndex,  mpCbQosObjectsIndex }
                    		::= { mpCbQosCMStatsTable 1 }

MpCbQosCMStatsEntry 	::= SEQUENCE {
                    			mpCbQosCMPrePolicyPkt64   Counter64,
                    			mpCbQosCMPrePolicyByte64   Counter64,
                    			mpCbQosCMPrePolicyBitRate64   Unsigned64,
                    			mpCbQosCMPostPolicyPkt64   Counter64,
                    			mpCbQosCMPostPolicyByte64   Counter64,
                    			mpCbQosCMPostPolicyBitRate64   Unsigned64,
                    			mpCbQosCMDropPkt64     Counter64,
                    			mpCbQosCMDropByte64    Counter64,
                    			mpCbQosCMDropBitRate64   Unsigned64,
                    			mpCbQosCMNoBufDropPkt64   Counter64
                    	             }


mpCbQosCMPrePolicyPkt64	OBJECT-TYPE
                    		SYNTAX  Counter64
                    		UNITS  "Packets"
                    		MAX-ACCESS  read-only
                    		STATUS  current
                    		DESCRIPTION
                    			"The 64 bits count of inbound packets prior to executing any QoS 
                    			policies."
                    		::= { mpCbQosCMStatsEntry 1 }

mpCbQosCMPrePolicyByte64	OBJECT-TYPE
                    		SYNTAX  Counter64
                    		UNITS  "Octets"
                    		MAX-ACCESS  read-only
                    		STATUS  current
                    		DESCRIPTION
                    			"The 64 bits count of inbound octets prior to executing any QoS 
                    			policies."
                    		::= { mpCbQosCMStatsEntry 2 }

mpCbQosCMPrePolicyBitRate64	OBJECT-TYPE
                    		SYNTAX  Unsigned64
                    		UNITS  "bits per second"
                    		MAX-ACCESS  read-only
                    		STATUS  current
                    		DESCRIPTION
                    			"The bit rate of the traffic prior to executing any QoS policies."
                    		::= { mpCbQosCMStatsEntry 3 }

mpCbQosCMPostPolicyPkt64	OBJECT-TYPE
                    		SYNTAX  Counter64
                    		UNITS  "Packets"
                    		MAX-ACCESS  read-only
                    		STATUS  current
                    		DESCRIPTION
                    			"The lower 64 bits count of outbound packets after executing QoS 
                    			policies."
                    		::= { mpCbQosCMStatsEntry 4 }

mpCbQosCMPostPolicyByte64	OBJECT-TYPE
                    		SYNTAX  Counter64
                    		UNITS  "Octets"
                    		MAX-ACCESS  read-only
                    		STATUS  current
                    		DESCRIPTION
                    			"The 64 bits count of outbound octets after executing QoS 
                    			policies."
                    		::= { mpCbQosCMStatsEntry 5 }

mpCbQosCMPostPolicyBitRate64	OBJECT-TYPE
                    		SYNTAX  Unsigned64
                    		UNITS  "bits per second"
                    		MAX-ACCESS  read-only
                    		STATUS  current
                    		DESCRIPTION
                    			"The bit rate of the traffic after executing QoS policies."
                    		::= { mpCbQosCMStatsEntry 6 }

mpCbQosCMDropPkt64  	OBJECT-TYPE
                    		SYNTAX  Counter64
                    		UNITS  "Packets"
                    		MAX-ACCESS  read-only
                    		STATUS  current
                    		DESCRIPTION
                    			"The 64 bits counter of dropped pkts per class as the result of 
                    			all features that can produce drops (e.g., police, random detect, 
                    			etc.)."
                    		::= { mpCbQosCMStatsEntry 7 }

mpCbQosCMDropByte64 	OBJECT-TYPE
                    		SYNTAX  Counter64
                    		UNITS  "Octets"
                    		MAX-ACCESS  read-only
                    		STATUS  current
                    		DESCRIPTION
                    			"The 64 bits counter of dropped bytes per class as the result of 
                    			all features that can produce drops (e.g., police, random detect, 
                    			etc.)."
                    		::= { mpCbQosCMStatsEntry 8 }

mpCbQosCMDropBitRate64	OBJECT-TYPE
                    		SYNTAX  Unsigned64
                    		UNITS  "bits per second"
                    		MAX-ACCESS  read-only
                    		STATUS  current
                    		DESCRIPTION
                    			"The bit rate of the drops per class as the result of all 
                    			features that can produce drops (e.g., police, random detect, 
                    			etc.)."
                    		::= { mpCbQosCMStatsEntry 9 }

mpCbQosCMNoBufDropPkt64 OBJECT-TYPE
						    SYNTAX  Counter64
						    UNITS  "Packets"
						    MAX-ACCESS  read-only
						    STATUS  current
						    DESCRIPTION
						        "The 64 bits drop packet count which occured due to lack of buffers during output processing on an interface." 
						    ::= { mpCbQosCMStatsEntry 10 }


------------------------------------------------------------------------------
mpCbQosMatchStmtStats	OBJECT IDENTIFIER ::= { maipuCBQosMIBObjects 17 }

mpCbQosMatchStmtStatsTable	OBJECT-TYPE
                    		SYNTAX  SEQUENCE OF  MpCbQosMatchStmtStatsEntry
                    		MAX-ACCESS  not-accessible
                    		STATUS  current
                    		DESCRIPTION
                    			"This table specifies Match Statement related statistical 
                    			information."
                    		::= { mpCbQosMatchStmtStats 1 }

mpCbQosMatchStmtStatsEntry	OBJECT-TYPE
                    		SYNTAX  MpCbQosMatchStmtStatsEntry
                    		MAX-ACCESS  not-accessible
                    		STATUS  current
                    		DESCRIPTION
                    			"Each entry in this table describes the statistical information 
                    			about Match Statement. Match Statement specific information you 
                    			can find in this table are: Pre policy pkt/byte counters, and 
                    			bit rates."
                    		INDEX  { mpCbQosPolicyIndex,  mpCbQosObjectsIndex }
                    		::= { mpCbQosMatchStmtStatsTable 1 }

MpCbQosMatchStmtStatsEntry	::= SEQUENCE {
                    			mpCbQosMatchPrePolicyPkt64   Counter64,
                    			mpCbQosMatchPrePolicyByte64   Counter64,
                    			mpCbQosMatchPrePolicyBitRate64   Unsigned64
                    	             }


mpCbQosMatchPrePolicyPkt64	OBJECT-TYPE
                    		SYNTAX  Counter64
                    		MAX-ACCESS  read-only
                    		STATUS  current
                    		DESCRIPTION
                    			"The 64 bits count of inbound packets prior to executing any QoS 
                    			policies."
                    		::= { mpCbQosMatchStmtStatsEntry 1 }

mpCbQosMatchPrePolicyByte64	OBJECT-TYPE
                    		SYNTAX  Counter64
                    		MAX-ACCESS  read-only
                    		STATUS  current
                    		DESCRIPTION
                    			"The 64 bits count of inbound octets prior to executing any QoS 
                    			policies."
                    		::= { mpCbQosMatchStmtStatsEntry 2 }

mpCbQosMatchPrePolicyBitRate64	OBJECT-TYPE
                    		SYNTAX  Unsigned64
                    		UNITS  "bits per second"
                    		MAX-ACCESS  read-only
                    		STATUS  current
                    		DESCRIPTION
                    			"The bit rate of the traffic prior to executing any QoS policies."
                    		::= { mpCbQosMatchStmtStatsEntry 3 }


------------------------------------------------------------------------------
mpCbQosPoliceStats  	OBJECT IDENTIFIER ::= { maipuCBQosMIBObjects 18 }

mpCbQosPoliceStatsTable	OBJECT-TYPE
                    		SYNTAX  SEQUENCE OF  MpCbQosPoliceStatsEntry
                    		MAX-ACCESS  not-accessible
                    		STATUS  current
                    		DESCRIPTION
                    			"This table specifies Police Action related Statistical 
                    			information."
                    		::= { mpCbQosPoliceStats 1 }

mpCbQosPoliceStatsEntry	OBJECT-TYPE
                    		SYNTAX  MpCbQosPoliceStatsEntry
                    		MAX-ACCESS  not-accessible
                    		STATUS  current
                    		DESCRIPTION
                    			"Each entry in this table describes the statistical information 
                    			about Police Action. Police Action specific information you can 
                    			find in this table are: Conformed/Exceeded pkt/byte counters, bit 
                    			rates."
                    		INDEX  { mpCbQosPolicyIndex,  mpCbQosObjectsIndex }
                    		::= { mpCbQosPoliceStatsTable 1 }

MpCbQosPoliceStatsEntry	::= SEQUENCE {
                    			mpCbQosPoliceConformedPkt64   Counter64,
                    			mpCbQosPoliceConformedByte64   Counter64,
                    			mpCbQosPoliceConformedBitRate64   Unsigned64,
                    			mpCbQosPoliceExceededPkt64   Counter64,
                    			mpCbQosPoliceExceededByte64   Counter64,
                    			mpCbQosPoliceExceededBitRate64   Unsigned64,
                    			mpCbQosPoliceViolatedPkt64   Counter64,
                    			mpCbQosPoliceViolatedByte64   Counter64,
                    			mpCbQosPoliceViolatedBitRate64   Unsigned64
                    	             }


mpCbQosPoliceConformedPkt64	OBJECT-TYPE
                    		SYNTAX  Counter64
                    		UNITS  "Packets"
                    		MAX-ACCESS  read-only
                    		STATUS  current
                    		DESCRIPTION
                    			"The 64 bits count of packets treated as conforming by the 
                    			policing feature."
                    		::= { mpCbQosPoliceStatsEntry 1 }

mpCbQosPoliceConformedByte64	OBJECT-TYPE
                    		SYNTAX  Counter64
                    		UNITS  "Octets"
                    		MAX-ACCESS  read-only
                    		STATUS  current
                    		DESCRIPTION
                    			"The 64 bits count of octets treated as conforming by the 
                    			policing feature."
                    		::= { mpCbQosPoliceStatsEntry 2 }

mpCbQosPoliceConformedBitRate64	OBJECT-TYPE
                    		SYNTAX  Unsigned64
                    		UNITS  "bits per second"
                    		MAX-ACCESS  read-only
                    		STATUS  current
                    		DESCRIPTION
                    			"The bit rate of conforming traffic."
                    		::= { mpCbQosPoliceStatsEntry 3 }

mpCbQosPoliceExceededPkt64	OBJECT-TYPE
                    		SYNTAX  Counter64
                    		UNITS  "Packets"
                    		MAX-ACCESS  read-only
                    		STATUS  current
                    		DESCRIPTION
                    			"The 64 bits count of packets treated as non-conforming by the 
                    			policing feature."
                    		::= { mpCbQosPoliceStatsEntry 4 }

mpCbQosPoliceExceededByte64	OBJECT-TYPE
                    		SYNTAX  Counter64
                    		UNITS  "Octets"
                    		MAX-ACCESS  read-only
                    		STATUS  current
                    		DESCRIPTION
                    			"The 64 bits count of octets treated as non-conforming by the 
                    			policing feature."
                    		::= { mpCbQosPoliceStatsEntry 5 }

mpCbQosPoliceExceededBitRate64	OBJECT-TYPE
                    		SYNTAX  Unsigned64
                    		UNITS  "bits per second"
                    		MAX-ACCESS  read-only
                    		STATUS  current
                    		DESCRIPTION
                    			"The bit rate of the non-conforming traffic."
                    		::= { mpCbQosPoliceStatsEntry 6 }

mpCbQosPoliceViolatedPkt64	OBJECT-TYPE
                    		SYNTAX  Counter64
                    		UNITS  "Packets"
                    		MAX-ACCESS  read-only
                    		STATUS  current
                    		DESCRIPTION
                    			"The 64 bits count of packets treated as violated by the policing 
                    			feature."
                    		::= { mpCbQosPoliceStatsEntry 7 }

mpCbQosPoliceViolatedByte64	OBJECT-TYPE
                    		SYNTAX  Counter64
                    		UNITS  "Octets"
                    		MAX-ACCESS  read-only
                    		STATUS  current
                    		DESCRIPTION
                    			"The 64 bits count of octets treated as violated by the policing 
                    			feature."
                    		::= { mpCbQosPoliceStatsEntry 8 }

mpCbQosPoliceViolatedBitRate64	OBJECT-TYPE
                    		SYNTAX  Unsigned64
                    		UNITS  "bits per second"
                    		MAX-ACCESS  read-only
                    		STATUS  current
                    		DESCRIPTION
                    			"The bit rate of the violating traffic."
                    		::= { mpCbQosPoliceStatsEntry 9 }


------------------------------------------------------------------------------
mpCbQosQueueingStats	OBJECT IDENTIFIER ::= { maipuCBQosMIBObjects 19 }

mpCbQosQueueingStatsTable	OBJECT-TYPE
                    		SYNTAX  SEQUENCE OF  MpCbQosQueueingStatsEntry
                    		MAX-ACCESS  not-accessible
                    		STATUS  current
                    		DESCRIPTION
                    			"This table specifies Queueing Action related Statistical 
                    			information."
                    		::= { mpCbQosQueueingStats 1 }

mpCbQosQueueingStatsEntry	OBJECT-TYPE
                    		SYNTAX  MpCbQosQueueingStatsEntry
                    		MAX-ACCESS  not-accessible
                    		STATUS  current
                    		DESCRIPTION
                    			"Each entry in this table describes the statistical information 
                    			about queueing action. Queueing action specific information you 
                    			can find in this table are: various Q depth, and discard pkt/byte 
                    			counters."
                    		INDEX  { mpCbQosPolicyIndex,  mpCbQosObjectsIndex }
                    		::= { mpCbQosQueueingStatsTable 1 }

MpCbQosQueueingStatsEntry	::= SEQUENCE {
                    			mpCbQosQueueingQDepthUnit   INTEGER,
                    			mpCbQosQueueingCurrentQDepth   Gauge32,
                    			mpCbQosQueueingMaxQDepth   Gauge32,
                    			mpCbQosQueueingDiscardByte64   Counter64,
                    			mpCbQosQueueingDiscardPkt64   Counter64
                    	             }


mpCbQosQueueingQDepthUnit	OBJECT-TYPE
                    		SYNTAX  INTEGER {
                    			          packets(1),
                    			          bytes(2),
                    			          cells(3),
                    			          ms(4),
                    			          us(5)
                    			        }
                    		MAX-ACCESS  read-only
                    		STATUS  current
                    		DESCRIPTION
                    			"Represents the unit type to measure the depth of the queue."
                    		::= { mpCbQosQueueingStatsEntry 1 }

mpCbQosQueueingCurrentQDepth	OBJECT-TYPE
                    		SYNTAX  Gauge32
                    		MAX-ACCESS  read-only
                    		STATUS  current
                    		DESCRIPTION
                    			"The current depth of the queue."
                    		::= { mpCbQosQueueingStatsEntry 2 }

mpCbQosQueueingMaxQDepth	OBJECT-TYPE
                    		SYNTAX  Gauge32
                    		MAX-ACCESS  read-only
                    		STATUS  current
                    		DESCRIPTION
                    			"The maximum depth of the queue."
                    		::= { mpCbQosQueueingStatsEntry 3 }

mpCbQosQueueingDiscardByte64	OBJECT-TYPE
                    		SYNTAX  Counter64
                    		UNITS  "Octets"
                    		MAX-ACCESS  read-only
                    		STATUS  current
                    		DESCRIPTION
                    			"The count of octets, associated with this class, that were 
                    			dropped by queueing."
                    		::= { mpCbQosQueueingStatsEntry 4 }

mpCbQosQueueingDiscardPkt64	OBJECT-TYPE
                    		SYNTAX  Counter64
                    		UNITS  "Packets"
                    		MAX-ACCESS  read-only
                    		STATUS  current
                    		DESCRIPTION
                    			"The number of packets, associated with this class, that were 
                    			dropped by queueing."
                    		::= { mpCbQosQueueingStatsEntry 5 }


------------------------------------------------------------------------------
mpCbQosTSStats      	OBJECT IDENTIFIER ::= { maipuCBQosMIBObjects 20 }

mpCbQosTSStatsTable 	OBJECT-TYPE
                    		SYNTAX  SEQUENCE OF  MpCbQosTSStatsEntry
                    		MAX-ACCESS  not-accessible
                    		STATUS  current
                    		DESCRIPTION
                    			"This table specifies traffic-shaping Action related Statistical 
                    			information."
                    		::= { mpCbQosTSStats 1 }

mpCbQosTSStatsEntry 	OBJECT-TYPE
                    		SYNTAX  MpCbQosTSStatsEntry
                    		MAX-ACCESS  not-accessible
                    		STATUS  current
                    		DESCRIPTION
                    			"Each entry in this table describes the statistical information 
                    			about traffic-shaping Action. Traffic-shaping Action specific 
                    			information you can find in this table are: various delay/drop 
                    			pkt/byte counters, state of feature, and Q size."
                    		INDEX  { mpCbQosPolicyIndex,  mpCbQosObjectsIndex }
                    		::= { mpCbQosTSStatsTable 1 }

MpCbQosTSStatsEntry 	::= SEQUENCE {
                    			mpCbQosTSStatsDelayedByte64   Counter64,
                    			mpCbQosTSStatsDelayedPkt64   Counter64,
                    			mpCbQosTSStatsDropByte64   Counter64,
                    			mpCbQosTSStatsDropPkt64   Counter64,
                    			mpCbQosTSStatsActive   TruthValue,
                    			mpCbQosTSStatsCurrentQSize   Gauge32
                    	             }


mpCbQosTSStatsDelayedByte64	OBJECT-TYPE
                    		SYNTAX  Counter64
                    		UNITS  "Octets"
                    		MAX-ACCESS  read-only
                    		STATUS  current
                    		DESCRIPTION
                    			"This object represents the 64 bits counter of octets that have 
                    			been delayed."
                    		::= { mpCbQosTSStatsEntry 1 }

mpCbQosTSStatsDelayedPkt64	OBJECT-TYPE
                    		SYNTAX  Counter64
                    		UNITS  "Packets"
                    		MAX-ACCESS  read-only
                    		STATUS  current
                    		DESCRIPTION
                    			"This object represents the 64 bits counter of packets that have 
                    			been delayed."
                    		::= { mpCbQosTSStatsEntry 2 }

mpCbQosTSStatsDropByte64	OBJECT-TYPE
                    		SYNTAX  Counter64
                    		UNITS  "Octets"
                    		MAX-ACCESS  read-only
                    		STATUS  current
                    		DESCRIPTION
                    			"This object represents the 64 bits counter of octets that have 
                    			been dropped during shaping."
                    		::= { mpCbQosTSStatsEntry 3 }

mpCbQosTSStatsDropPkt64	OBJECT-TYPE
                    		SYNTAX  Counter64
                    		UNITS  "Packets"
                    		MAX-ACCESS  read-only
                    		STATUS  current
                    		DESCRIPTION
                    			"This object represents the 64 bits counter of packets that have 
                    			been dropped during shaping."
                    		::= { mpCbQosTSStatsEntry 4 }

mpCbQosTSStatsActive	OBJECT-TYPE
                    		SYNTAX  TruthValue
                    		MAX-ACCESS  read-only
                    		STATUS  current
                    		DESCRIPTION
                    			"This object indicates the current traffic-shaping state. When 
                    			traffic-shaping is enabled and the traffic rate exceeds the shape 
                    			rate, traffic-shaping is considered to be active.  Otherwise, it 
                    			is considered inactive."
                    		::= { mpCbQosTSStatsEntry 5 }

mpCbQosTSStatsCurrentQSize	OBJECT-TYPE
                    		SYNTAX  Gauge32
                    		UNITS  "Packets"
                    		MAX-ACCESS  read-only
                    		STATUS  current
                    		DESCRIPTION
                    			"This object indicates the current traffic-shaping queue depth in 
                    			packets."
                    		::= { mpCbQosTSStatsEntry 6 }


------------------------------------------------------------------------------
mpCbQosREDClassStats	OBJECT IDENTIFIER ::= { maipuCBQosMIBObjects 21 }

mpCbQosREDClassStatsTable	OBJECT-TYPE
                    		SYNTAX  SEQUENCE OF  MpCbQosREDClassStatsEntry
                    		MAX-ACCESS  not-accessible
                    		STATUS  current
                    		DESCRIPTION
                    			"This table specifies per Precedence WRED Action related 
                    			Statistical information."
                    		::= { mpCbQosREDClassStats 1 }

mpCbQosREDClassStatsEntry	OBJECT-TYPE
                    		SYNTAX  MpCbQosREDClassStatsEntry
                    		MAX-ACCESS  not-accessible
                    		STATUS  current
                    		DESCRIPTION
                    			"Each entry in this table describes the statistical information 
                    			about per Precedence WRED Action. per Precedence WRED Action 
                    			specific information you can find in this table are: Random 
                    			pkt/byte counters, and Tail drop pkt/byte counters."
                    		INDEX  { mpCbQosPolicyIndex,  mpCbQosObjectsIndex,  mpCbQosREDValue }
                    		::= { mpCbQosREDClassStatsTable 1 }

MpCbQosREDClassStatsEntry	::= SEQUENCE {
                    			mpCbQosREDRandomDropPkt64   Counter64,
                    			mpCbQosREDRandomDropByte64   Counter64,
                    			mpCbQosREDTailDropPkt64   Counter64,
                    			mpCbQosREDTailDropByte64   Counter64,
                    			mpCbQosREDTransmitPkt64   Counter64,
                    			mpCbQosREDTransmitByte64   Counter64,
                    			mpCbQosREDECNMarkPkt64   Counter64,
                    			mpCbQosREDECNMarkByte64   Counter64,
                    			mpCbQosREDMeanQSizeUnits   INTEGER,
                    			mpCbQosREDMeanQSize    Unsigned32
                    	             }


mpCbQosREDRandomDropPkt64	OBJECT-TYPE
                    		SYNTAX  Counter64
                    		UNITS  "Packets"
                    		MAX-ACCESS  read-only
                    		STATUS  current
                    		DESCRIPTION
                    			"The 64 bits count of packets dropped when the number of packets 
                    			in the associated queue was greater than the minimum threshold 
                    			and less than the maximum threshold."
                    		::= { mpCbQosREDClassStatsEntry 1 }

mpCbQosREDRandomDropByte64	OBJECT-TYPE
                    		SYNTAX  Counter64
                    		UNITS  "Octets"
                    		MAX-ACCESS  read-only
                    		STATUS  current
                    		DESCRIPTION
                    			"The 64 bits count of bytes dropped when the number of packets in 
                    			the associated queue was greater than the minimum threshold and 
                    			less than the maximum threshold."
                    		::= { mpCbQosREDClassStatsEntry 2 }

mpCbQosREDTailDropPkt64	OBJECT-TYPE
                    		SYNTAX  Counter64
                    		UNITS  "Packets"
                    		MAX-ACCESS  read-only
                    		STATUS  current
                    		DESCRIPTION
                    			"The 64 bits count of packets dropped when the number of packets 
                    			in the associated queue was greater than the maximum threshold."
                    		::= { mpCbQosREDClassStatsEntry 3 }

mpCbQosREDTailDropByte64	OBJECT-TYPE
                    		SYNTAX  Counter64
                    		UNITS  "Octets"
                    		MAX-ACCESS  read-only
                    		STATUS  current
                    		DESCRIPTION
                    			"The 64 bits count of bytes dropped when the number of packets in 
                    			the associated queue was greater than the maximum threshold."
                    		::= { mpCbQosREDClassStatsEntry 4 }

mpCbQosREDTransmitPkt64	OBJECT-TYPE
                    		SYNTAX  Counter64
                    		UNITS  "Packets"
                    		MAX-ACCESS  read-only
                    		STATUS  current
                    		DESCRIPTION
                    			"The 64 bits count of packets transmitted."
                    		::= { mpCbQosREDClassStatsEntry 5 }

mpCbQosREDTransmitByte64	OBJECT-TYPE
                    		SYNTAX  Counter64
                    		UNITS  "Octets"
                    		MAX-ACCESS  read-only
                    		STATUS  current
                    		DESCRIPTION
                    			"The 64 bits count of octets transmitted."
                    		::= { mpCbQosREDClassStatsEntry 6 }

mpCbQosREDECNMarkPkt64	OBJECT-TYPE
						    SYNTAX  Counter64
						    UNITS  "Packets"
						    MAX-ACCESS  read-only
						    STATUS  current
						    DESCRIPTION
						        "The 64 bits count of packets ecn marked when the number of 
						        packets in the associated queue was greater than the minimum 
						        threshold and less than the maximum threshold." 
						    ::= { mpCbQosREDClassStatsEntry 7 }

mpCbQosREDECNMarkByte64		OBJECT-TYPE
						    SYNTAX  Counter64
						    UNITS  "Octets"
						    MAX-ACCESS  read-only
						    STATUS  current
						    DESCRIPTION
						        "The 64 bits count of bytes ecn marked when the number of packets 
						        in the associated queue was greater than the minimum threshold 
						        and less than the maximum threshold." 
						    ::= { mpCbQosREDClassStatsEntry 8 }
    
mpCbQosREDMeanQSizeUnits	OBJECT-TYPE
                    		SYNTAX  INTEGER {
                    			          packets(1),
                    			          bytes(2),
                    			          cells(3),
                    			          ms(4),
                    			          us(5)
                    			        }
                    		MAX-ACCESS  read-only
                    		STATUS  current
                    		DESCRIPTION
                    			"Represents the unit type of mpCbQosREDMeanQSize object."
                    		::= { mpCbQosREDClassStatsEntry 9 }

mpCbQosREDMeanQSize 	OBJECT-TYPE
                    		SYNTAX  Unsigned32
                    		MAX-ACCESS  read-only
                    		STATUS  current
                    		DESCRIPTION
                    			"The average queue size computed and used by the WRED algorithm."
                    		::= { mpCbQosREDClassStatsEntry 10 }


------------------------------------------------------------------------------
mpCbQosSetStats     	OBJECT IDENTIFIER ::= { maipuCBQosMIBObjects 22 }

mpCbQosSetStatsTable	OBJECT-TYPE
                    		SYNTAX  SEQUENCE OF  MpCbQosSetStatsEntry
                    		MAX-ACCESS  not-accessible
                    		STATUS  current
                    		DESCRIPTION
                    			"This table specifies packet marking statistical information."
                    		::= { mpCbQosSetStats 1 }

mpCbQosSetStatsEntry	OBJECT-TYPE
                    		SYNTAX  MpCbQosSetStatsEntry
                    		MAX-ACCESS  not-accessible
                    		STATUS  current
                    		DESCRIPTION
                    			"Each entry in this table describes the packets that marked by 
                    			each marking type."
                    		INDEX  { mpCbQosPolicyIndex,  mpCbQosObjectsIndex }
                    		::= { mpCbQosSetStatsTable 1 }

MpCbQosSetStatsEntry	::= SEQUENCE {
                    			mpCbQosSetDscpPkt64    Counter64,
                    			mpCbQosSetPrecedencePkt64   Counter64,
                    			mpCbQosSetQosGroupPkt64   Counter64,
                    			mpCbQosSetFrDePkt64    Counter64,        
                    			mpCbQosSetAtmClpPkt64    Counter64,
                    			mpCbQosSetL2CosPkt64   Counter64,
                    			mpCbQosSetMplsExpImpositionPkt64   Counter64,
                    			mpCbQosSetDiscardClassPkt64   Counter64,
                    			mpCbQosSetMplsExpTopMostPkt64   Counter64,
                    			mpCbQosSetFrFecnBecnPkt64   Counter64,
                    			mpCbQosSetDscpTunnelPkt64   Counter64,
								          mpCbQosSetPrecedenceTunnelPkt64   Counter64,
                    			mpCbQosSetTosPkt64   Counter64
                    	             }


mpCbQosSetDscpPkt64 	OBJECT-TYPE
                    		SYNTAX  Counter64
                    		UNITS  "Packets"
                    		MAX-ACCESS  read-only
                    		STATUS  current
                    		DESCRIPTION
                    			"The 64 bits count of packets whose DSCP field is marked by Set 
                    			feature."
                    		::= { mpCbQosSetStatsEntry 1 }

mpCbQosSetPrecedencePkt64	OBJECT-TYPE
                    		SYNTAX  Counter64
                    		UNITS  "Packets"
                    		MAX-ACCESS  read-only
                    		STATUS  current
                    		DESCRIPTION
                    			"The 64 bits count of packets whose Precedence field is marked by 
                    			Set feature."
                    		::= { mpCbQosSetStatsEntry 2 }

mpCbQosSetQosGroupPkt64	OBJECT-TYPE
                    		SYNTAX  Counter64
                    		UNITS  "Packets"
                    		MAX-ACCESS  read-only
                    		STATUS  current
                    		DESCRIPTION
                    			"The 64 bits count of packets whose Qos Group field is marked by 
                    			Set feature."
                    		::= { mpCbQosSetStatsEntry 3 }

mpCbQosSetFrDePkt64 OBJECT-TYPE
							SYNTAX  Counter64
							UNITS  "Packets"
							MAX-ACCESS  read-only
							STATUS  current
							DESCRIPTION
								"The 64 bits count of packets whose Frame Relay DE Bit is marked 
								by Set feature."
							::= { mpCbQosSetStatsEntry 4 }

mpCbQosSetAtmClpPkt64 OBJECT-TYPE
							SYNTAX  Counter64
							UNITS  "Packets"
							MAX-ACCESS  read-only
							STATUS  current
							DESCRIPTION
								"The 64 bits count of packets whose ATM CLP Bit is marked by Set 
								feature."
							::= { mpCbQosSetStatsEntry 5 }

mpCbQosSetL2CosPkt64	OBJECT-TYPE
                    		SYNTAX  Counter64
                    		UNITS  "Packets"
                    		MAX-ACCESS  read-only
                    		STATUS  current
                    		DESCRIPTION
                    			"The 64 bits count of packets whose Layer 2 Cos field is marked 
                    			by Set feature."
                    		::= { mpCbQosSetStatsEntry 6 }

mpCbQosSetMplsExpImpositionPkt64	OBJECT-TYPE
                    		SYNTAX  Counter64
                    		UNITS  "Packets"
                    		MAX-ACCESS  read-only
                    		STATUS  current
                    		DESCRIPTION
                    			"The 64 bits count of packets whose MPLS Experimental Imposition 
                    			field is marked by Set feature."
                    		::= { mpCbQosSetStatsEntry 7 }

mpCbQosSetDiscardClassPkt64	OBJECT-TYPE
                    		SYNTAX  Counter64
                    		UNITS  "Packets"
                    		MAX-ACCESS  read-only
                    		STATUS  current
                    		DESCRIPTION
                    			"The 64 bits count of packets whose Discard Class field is marked 
                    			by Set feature."
                    		::= { mpCbQosSetStatsEntry 8 }

mpCbQosSetMplsExpTopMostPkt64	OBJECT-TYPE
                    		SYNTAX  Counter64
                    		UNITS  "Packets"
                    		MAX-ACCESS  read-only
                    		STATUS  current
                    		DESCRIPTION
                    			"The 64 bits count of packets whose MPLS Experimental TopMost 
                    			field is marked by Set feature."
                    		::= { mpCbQosSetStatsEntry 9 }

mpCbQosSetFrFecnBecnPkt64	OBJECT-TYPE
						    SYNTAX  Counter64
						    UNITS  "Packets"
						    MAX-ACCESS  read-only
						    STATUS  current
						    DESCRIPTION
						        "The 64 bits count of packets whose Frame Relay FECN BECN field 
						        is marked by Set feature." 
						    ::= { mpCbQosSetStatsEntry 10 }

mpCbQosSetDscpTunnelPkt64	OBJECT-TYPE
						    SYNTAX  Counter64
						    UNITS  "Packets"
						    MAX-ACCESS  read-only
						    STATUS  current
						    DESCRIPTION
						        "The 64 bits count of packets whose DSCP Tunnel field is marked 
						        by Set feature." 
						    ::= { mpCbQosSetStatsEntry 11 }

mpCbQosSetPrecedenceTunnelPkt64	OBJECT-TYPE
						    SYNTAX  Counter64
						    UNITS  "Packets"
						    MAX-ACCESS  read-only
						    STATUS  current
						    DESCRIPTION
						        "The 64 bits count of packets whose Precedence Tunnel field is 
						        marked by Set feature." 
						    ::= { mpCbQosSetStatsEntry 12 }

mpCbQosSetTosPkt64		OBJECT-TYPE
						    SYNTAX  Counter64
						    UNITS  "Packets"
						    MAX-ACCESS  read-only
						    STATUS  current
						    DESCRIPTION
						        "The 64 bits count of packets whose TOS field is marked by Set 
						        feature." 
						    ::= { mpCbQosSetStatsEntry 13 }

END
------------------------------------------------------------------------------
-- ============================================================================
-- $Log: maipuCBQosMIB.mib,v $
--
--
-- ============================================================================

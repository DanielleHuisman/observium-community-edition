------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MAIPU-DNS-MIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt
        	FROM MAIPU-SMI
        ObjectName, ObjectSyntax, NetworkAddress
                FROM RFC1155-SMI;



dnsMib              	MODULE-IDENTITY
                    		LAST-UPDATED 	"0803260920Z"
                    		ORGANIZATION 	"四川迈普数据通信股份有限公司,
                    		             	 Maipu (Sichuan) Communication Technology Co. LTD."
                    		CONTACT-INFO
                    			"编 写 人:  孙 健
                    			 联系地址： 四川省 成都市 高新区 九兴大道16号
                    			 邮    编： 610041
                    			 电    话：
                    			 传    真：
                    			 电子邮件： ????"
                    		DESCRIPTION
                      			"用户管理设备上域名配置"
                    		::= { mpMgmt  109 }




------------------------------------------------------------------------------
dnsGlobal           	OBJECT IDENTIFIER ::= { dnsMib 1 }

dnsDomainName       	OBJECT-TYPE
                    		SYNTAX  DisplayString(SIZE(1..255))
                    		MAX-ACCESS  read-write
                    		STATUS  current
                    		DESCRIPTION
                    			"Set the `domainName' member to the domain to which this resolver belongs."
                    		::= { dnsGlobal 1 }

dnsDomainOrder      	OBJECT-TYPE
                    		SYNTAX  INTEGER {
                    			         localfirst(1),
                    			          dnsfirst(2),
                    			          dnsonly(3)
                    			        }
                    		MAX-ACCESS  read-write
                    		STATUS  current
                    		DESCRIPTION
                    			"配置域名解析顺序:
                    			 QUERY_LOCAL_FIRST 1
                    			 QUERY_DNS_FIRST   2
                    			 QUERY_DNS_ONLY    3"
                    		::= { dnsGlobal 2 }

dnsNameServerTable  	OBJECT-TYPE
                    		SYNTAX  SEQUENCE OF   DnsNameServerEntry
                    		MAX-ACCESS  not-accessible
                    		STATUS  current
                    		DESCRIPTION
                    			"域名服务器列表"
                    		::= { dnsMib 2 }

dnsNameServerEntry  	OBJECT-TYPE
                    		SYNTAX  DnsNameServerEntry
                    		MAX-ACCESS  not-accessible
                    		STATUS  current
                    		DESCRIPTION
                    			"域名服务器列表"
                    		INDEX  { dnsNameServerIPAddress }
                    		::= { dnsNameServerTable 1 }

DnsNameServerEntry  	::= SEQUENCE {
                    			dnsNameServerIPAddress   IpAddress,
                    			dnsNameServerRowStatus   RowStatus
                    	             }


dnsNameServerIPAddress	OBJECT-TYPE
                    		SYNTAX  IpAddress
                    		MAX-ACCESS  read-only
                    		STATUS  current
                    		DESCRIPTION
                    			"域名服务器地址"
                    		::= { dnsNameServerEntry 1 }

dnsNameServerRowStatus	OBJECT-TYPE
                    		SYNTAX  RowStatus
                    		MAX-ACCESS  read-create
                    		STATUS  current
                    		DESCRIPTION
                    			"域名服务器列表行状态"
                    		::= { dnsNameServerEntry 2 }

dnsHostNameTable    	OBJECT-TYPE
                    		SYNTAX  SEQUENCE OF   DnsHostNameEntry
                    		MAX-ACCESS  not-accessible
                    		STATUS  current
                    		DESCRIPTION
                    			"主机名IP地址对应表"
                    		::= { dnsMib 3 }

dnsHostNameEntry    	OBJECT-TYPE
                    		SYNTAX  DnsHostNameEntry
                    		MAX-ACCESS  not-accessible
                    		STATUS  current
                    		DESCRIPTION
                    			"主机名IP地址对应表"
                    		INDEX  { dnsHostIPAddress, dnsHostName }
                    		::= { dnsHostNameTable 1 }

DnsHostNameEntry    	::= SEQUENCE {
                    			dnsHostIPAddress       IpAddress,
                    			dnsHostName            DisplayString,
                    			dnsHostAlias           TruthValue,
                    			dnsHostRawStatus       RowStatus
                    	             }


dnsHostIPAddress    	OBJECT-TYPE
                    		SYNTAX  IpAddress
                    		MAX-ACCESS  read-only
                    		STATUS  current
                    		DESCRIPTION
                    			"主机IP地址"
                    		::= { dnsHostNameEntry 1 }

dnsHostName         	OBJECT-TYPE
                    		SYNTAX  DisplayString(SIZE(0..32))
                    		MAX-ACCESS  read-only
                    		STATUS  current
                    		DESCRIPTION
                    			"配置主机名"
                    		::= { dnsHostNameEntry 2 }

dnsHostAlias        	OBJECT-TYPE
                    		SYNTAX  TruthValue
                    		MAX-ACCESS  read-only
                    		STATUS  current
                    		DESCRIPTION
                    			"是否是别名"
                    		::= { dnsHostNameEntry 3 }

dnsHostRawStatus    	OBJECT-TYPE
                    		SYNTAX  RowStatus
                    		MAX-ACCESS  read-create
                    		STATUS  current
                    		DESCRIPTION
                    			"行状态"
                    		::= { dnsHostNameEntry 4 }

dnsDomainNameTable  	OBJECT-TYPE
                    		SYNTAX  SEQUENCE OF   DnsDomainNameEntry
                    		MAX-ACCESS  not-accessible
                    		STATUS  current
                    		DESCRIPTION
                    			""
                    		::= { dnsMib 4 }

dnsDomainNameEntry  	OBJECT-TYPE
                    		SYNTAX  DnsDomainNameEntry
                    		MAX-ACCESS  not-accessible
                    		STATUS  current
                    		DESCRIPTION
                    			""
                    		INDEX  { dnsDomainTblNameVrf }
                    		::= { dnsDomainNameTable 1 }

DnsDomainNameEntry  	::= SEQUENCE {
                    			dnsDomainTblName       DisplayString,
                    			dnsDomainTblNameVrf    DisplayString
                    	             }


dnsDomainTblName    	OBJECT-TYPE
                    		SYNTAX  DisplayString(SIZE(1..255))
                    		MAX-ACCESS  read-write
                    		STATUS  current
                    		DESCRIPTION
                    			"域名VRF表"
                    		::= { dnsDomainNameEntry 1 }

dnsDomainTblNameVrf 	OBJECT-TYPE
                    		SYNTAX  DisplayString(SIZE(1..32))
                    		MAX-ACCESS  read-only
                    		STATUS  current
                    		DESCRIPTION
                    			"域名所属VRF"
                    		::= { dnsDomainNameEntry 2 }


dnsNameServerXTable  	OBJECT-TYPE
                    		SYNTAX  SEQUENCE OF   DnsNameServerXEntry
                    		MAX-ACCESS  not-accessible
                    		STATUS  current
                    		DESCRIPTION
                    			"域名服务器列表"
                    		::= { dnsMib 5 }

dnsNameServerXEntry  	OBJECT-TYPE
                    		SYNTAX  DnsNameServerXEntry
                    		MAX-ACCESS  not-accessible
                    		STATUS  current
                    		DESCRIPTION
                    			"域名服务器列表"
                    		INDEX  { dnsNameServerXIPAddress, dnsNameServerXVrf }
                    		::= { dnsNameServerXTable 1 }

DnsNameServerXEntry  	::= SEQUENCE {
                    			dnsNameServerXIPAddress   IpAddress,
                    			dnsNameServerXVrf       DisplayString,
                    			dnsNameServerXRowStatus   RowStatus
                    	             }

dnsNameServerXIPAddress	OBJECT-TYPE
                    		SYNTAX  IpAddress
                    		MAX-ACCESS  read-only
                    		STATUS  current
                    		DESCRIPTION
                    			"域名服务器地址"
                    		::= { dnsNameServerXEntry 1 }

dnsNameServerXVrf    	OBJECT-TYPE
                    		SYNTAX  DisplayString(SIZE(1..32))
                    		MAX-ACCESS  read-only
                    		STATUS  current
                    		DESCRIPTION
                    			"服务器所属VRF"
                    		::= { dnsNameServerXEntry 2 }

dnsNameServerXRowStatus	OBJECT-TYPE
                    		SYNTAX  RowStatus
                    		MAX-ACCESS  read-create
                    		STATUS  current
                    		DESCRIPTION
                    			"域名服务器列表行状态"
                    		::= { dnsNameServerXEntry 3 }

dnsHostNameXTable    	OBJECT-TYPE
                    		SYNTAX  SEQUENCE OF   DnsHostNameXEntry
                    		MAX-ACCESS  not-accessible
                    		STATUS  current
                    		DESCRIPTION
                    			"主机名IP地址对应表"
                    		::= { dnsMib 6 }

dnsHostNameXEntry    	OBJECT-TYPE
                    		SYNTAX  DnsHostNameXEntry
                    		MAX-ACCESS  not-accessible
                    		STATUS  current
                    		DESCRIPTION
                    			"主机名IP地址对应表"
                    		INDEX  { dnsHostXIPAddress, dnsHostXName, dnsHostXVrf }
                    		::= { dnsHostNameXTable 1 }

DnsHostNameXEntry    	::= SEQUENCE {
                    			dnsHostXIPAddress       IpAddress,
                    			dnsHostXName            DisplayString,
                    			dnsHostXVrf             DisplayString,
                    			dnsHostXAlias           TruthValue,
                    			dnsHostXRawStatus       RowStatus
                    	             }


dnsHostXIPAddress    	OBJECT-TYPE
                    		SYNTAX  IpAddress
                    		MAX-ACCESS  read-only
                    		STATUS  current
                    		DESCRIPTION
                    			"主机IP地址"
                    		::= { dnsHostNameXEntry 1 }

dnsHostXName         	OBJECT-TYPE
                    		SYNTAX  DisplayString(SIZE(1..32))
                    		MAX-ACCESS  read-only
                    		STATUS  current
                    		DESCRIPTION
                    			"配置主机名"
                    		::= { dnsHostNameXEntry 2 }

dnsHostXVrf          	OBJECT-TYPE
                    		SYNTAX  DisplayString(SIZE(1..32))
                    		MAX-ACCESS  read-only
                    		STATUS  current
                    		DESCRIPTION
                    			"主机所属VRF"
                    		::= { dnsHostNameXEntry 3 }

dnsHostXAlias        	OBJECT-TYPE
                    		SYNTAX  TruthValue
                    		MAX-ACCESS  read-only
                    		STATUS  current
                    		DESCRIPTION
                    			"是否是别名"
                    		::= { dnsHostNameXEntry 4 }

dnsHostXRawStatus    	OBJECT-TYPE
                    		SYNTAX  RowStatus
                    		MAX-ACCESS  read-create
                    		STATUS  current
                    		DESCRIPTION
                    			"行状态"
                    		::= { dnsHostNameXEntry 5 }

END
------------------------------------------------------------------------------
-- ============================================================================
-- $Log: dnsMib.mib,v $
-- Revision 1.1  2010/06/21 11:18:46  liyh
-- first commit
--
-- Revision 1.4  2008/04/17 06:32:53  linmao
-- MYPOWER-5211: DNS reserve Old MIB
--
-- Revision 1.3  2008/03/29 03:17:18  linmao
-- MYPOWER-5009: DNS MIB Support VRF
--
--
--
-- ============================================================================

-- *****************************************************************
-- MP2600-IRMP.my:  Maipu enterprise IRMP MIB file
--
-- Sep 19, 2002 Huang lulu
--
-- Copyright (c)  by Maipu DataComm Inc.
-- All rights reserved.
-- 
-- *****************************************************************
--
   
   MAIPU-IRMP-MIB DEFINITIONS ::= BEGIN

   IMPORTS
       MODULE-IDENTITY, OBJECT-TYPE, Counter32,
       IpAddress, Unsigned32		FROM SNMPv2-SMI
       RowStatus					FROM SNMPv2-TC
       mpMgmt						FROM MAIPU-SMI;


   mpIrmpMib  MODULE-IDENTITY
           LAST-UPDATED "0209192030Z"      -- Fri Dec 12 20:30:04 PDT 2000
           ORGANIZATION "Maipu DataComm"
           CONTACT-INFO
          "       Huang lulu
          Postal: Maipu Inc
                  Tel: (028)5161006
          E-Mail: office@maipu.com "

        DESCRIPTION
	 "The MIB module to describe the IRMP Protocol for Maipu Router"
     ::= { mpMgmt 26 }

-- *************

    mpIrmpConf	OBJECT IDENTIFIER ::= { mpIrmpMib 1 }
  
    mpIrmpIf	OBJECT IDENTIFIER ::= { mpIrmpMib 2 }
  
    mpIrmpStat	OBJECT IDENTIFIER ::= { mpIrmpMib 3 }



-- **************************
-- conf
-- **************************

-- *************
-- irmp configure

    mpIrmpConfTable OBJECT-TYPE
    	SYNTAX	SEQUENCE OF MpIrmpConfEntry
    	MAX-ACCESS   not-accessible
    	STATUS	current
    	DESCRIPTION
    	    "The valid Irmp Configure."
    	::= { mpIrmpConf 1 }

    mpIrmpConfEntry OBJECT-TYPE
    	SYNTAX	MpIrmpConfEntry
    	MAX-ACCESS  not-accessible
    	STATUS	current
    	DESCRIPTION
    	    "Single Irmp Configuration."
    	INDEX { irmpAutoNum }
    	::= { mpIrmpConfTable 1 }
    	
    MpIrmpConfEntry ::=
    	SEQUENCE {
			irmpAutoNum		INTEGER,
			irmpAutoSumm		INTEGER,
			irmpBandWidth		Unsigned32,
			irmpDelayMetric	Unsigned32,
			irmpReliabMetric	INTEGER,
			irmpEffBWMetric	INTEGER,
			irmpMaxTransMetric	INTEGER,
			irmpInterRouteDist	INTEGER,
			irmpExtRouteDist	INTEGER,
			irmpMaxPaths		INTEGER,
			irmpMetricWeiTOS	INTEGER,
			irmpMetricWeiK1	Unsigned,
			irmpMetricWeiK2	Unsigned,
			irmpMetricWeiK3	Unsigned,
			irmpMetricWeiK4	Unsigned,
			irmpMetricWeiK5	Unsigned,
			irmpRedisBgp		INTEGER,
			irmpRedisConnect	INTEGER,
			irmpRedisSnsp		INTEGER,
			irmpRedisOspf		INTEGER,
			irmpRedisRip		INTEGER,
			irmpRedisStatic	INTEGER,
			irmpRedisBgpRM		INTEGER,
			irmpRedisConnectRM	INTEGER,
			irmpRedisSnspRM		INTEGER,
			irmpRedisOspfRM	INTEGER,
			irmpRedisRipRM		INTEGER,
			irmpRedisStaticRM	INTEGER,
			irmpActivetime		Unsigned,
			irmpVariance		INTEGER,
			irmpRowStatus		RowStatus
			}
    		
    irmpAutoNum	OBJECT-TYPE
    	SYNTAX	INTEGER (1..65535)
    	MAX-ACCESS  read-create
    	STATUS	current
    	DESCRIPTION
    	    "Irmp 自治系统号."
    	::= { mpIrmpConfEntry 1 }

	irmpAutoSumm	OBJECT-TYPE
    	SYNTAX	INTEGER {
    				disable(1),
    				enable(2)
    					}
    	MAX-ACCESS  read-create
    	STATUS	current
    	DESCRIPTION
    	    "."
    	::= { mpIrmpConfEntry 2 }

	irmpBandWidth	OBJECT-TYPE
    	SYNTAX	Unsigned32 (1..4294967295)
    	MAX-ACCESS  read-create
    	STATUS	current
    	DESCRIPTION
    	    "."
    	::= { mpIrmpConfEntry 3 }

	irmpDelayMetric	OBJECT-TYPE
    	SYNTAX	Unsigned32
    	MAX-ACCESS  read-create
    	STATUS	current
    	DESCRIPTION
    	    "(1/10秒)."
    	::= { mpIrmpConfEntry 4 }

	irmpReliabMetric	OBJECT-TYPE
    	SYNTAX	INTEGER (0..255)
    	MAX-ACCESS  read-create
    	STATUS	current
    	DESCRIPTION
    	    "."
    	::= { mpIrmpConfEntry 5 }

	irmpEffBWMetric	OBJECT-TYPE
    	SYNTAX	INTEGER (1..255)
    	MAX-ACCESS  read-create
    	STATUS	current
    	DESCRIPTION
    	    "."
    	::= { mpIrmpConfEntry 6 }

	irmpMaxTransMetric	OBJECT-TYPE
    	SYNTAX	INTEGER (1..65535)
    	MAX-ACCESS  read-create
    	STATUS	current
    	DESCRIPTION
    	    "."
    	::= { mpIrmpConfEntry 7 }

	irmpInterRouteDist	OBJECT-TYPE
    	SYNTAX	INTEGER (1..255)
    	MAX-ACCESS  read-create
    	STATUS	current
    	DESCRIPTION
    	    "."
    	::= { mpIrmpConfEntry 8 }

	irmpExtRouteDist	OBJECT-TYPE
    	SYNTAX	INTEGER (1..255)
    	MAX-ACCESS  read-create
    	STATUS	current
    	DESCRIPTION
    	    "."
    	::= { mpIrmpConfEntry 9 }

	irmpMaxPaths	OBJECT-TYPE
    	SYNTAX	INTEGER (1..6)
    	MAX-ACCESS  read-create
    	STATUS	current
    	DESCRIPTION
    	    "."
    	::= { mpIrmpConfEntry 10 }

	irmpMetricWeiTOS	OBJECT-TYPE
    	SYNTAX	INTEGER (0..8)
    	MAX-ACCESS  read-create
    	STATUS	current
    	DESCRIPTION
    	    "."
    	::= { mpIrmpConfEntry 11 }

	irmpMetricWeiK1	OBJECT-TYPE
    	SYNTAX	Unsigned32
    	MAX-ACCESS  read-create
    	STATUS	current
    	DESCRIPTION
    	    "."
    	::= { mpIrmpConfEntry 12 }

	irmpMetricWeiK2	OBJECT-TYPE
    	SYNTAX	Unsigned32
    	MAX-ACCESS  read-create
    	STATUS	current
    	DESCRIPTION
    	    "."
    	::= { mpIrmpConfEntry 13 }

	irmpMetricWeiK3	OBJECT-TYPE
    	SYNTAX	Unsigned32
    	MAX-ACCESS  read-create
    	STATUS	current
    	DESCRIPTION
    	    "."
    	::= { mpIrmpConfEntry 14 }

	irmpMetricWeiK4	OBJECT-TYPE
    	SYNTAX	Unsigned32
    	MAX-ACCESS  read-create
    	STATUS	current
    	DESCRIPTION
    	    "."
    	::= { mpIrmpConfEntry 15 }

	irmpMetricWeiK5	OBJECT-TYPE
    	SYNTAX	Unsigned32
    	MAX-ACCESS  read-create
    	STATUS	current
    	DESCRIPTION
    	    "."
    	::= { mpIrmpConfEntry 16 }

	irmpRedisBgp	OBJECT-TYPE
    	SYNTAX	INTEGER {
    				disable(1),
    				enable(2),
    				routeMap(3)
    					}
    	MAX-ACCESS  read-create
    	STATUS	current
    	DESCRIPTION
    	    "."
    	::= { mpIrmpConfEntry 17 }

	irmpRedisConnect	OBJECT-TYPE
    	SYNTAX	INTEGER {
    				disable(1),
    				enable(2),
    				routeMap(3)
    					}
    	MAX-ACCESS  read-create
    	STATUS	current
    	DESCRIPTION
    	    "."
    	::= { mpIrmpConfEntry 18 }

	irmpRedisSnsp	OBJECT-TYPE
    	SYNTAX	INTEGER {
    				disable(1),
    				enable(2),
    				routeMap(3)
    					}
    	MAX-ACCESS  read-create
    	STATUS	current
    	DESCRIPTION
    	    "."
    	::= { mpIrmpConfEntry 19 }

	irmpRedisOspf	OBJECT-TYPE
    	SYNTAX	INTEGER {
    				disable(1),
    				enable(2),
    				routeMap(3)
    					}
    	MAX-ACCESS  read-create
    	STATUS	current
    	DESCRIPTION
    	    "."
    	::= { mpIrmpConfEntry 20 }

	irmpRedisRip	OBJECT-TYPE
    	SYNTAX	INTEGER {
    				disable(1),
    				enable(2),
    				routeMap(3)
    					}
    	MAX-ACCESS  read-create
    	STATUS	current
    	DESCRIPTION
    	    "."
    	::= { mpIrmpConfEntry 21 }

	irmpRedisStatic	OBJECT-TYPE
    	SYNTAX	INTEGER {
    				disable(1),
    				enable(2),
    				routeMap(3)
    					}
    	MAX-ACCESS  read-create
    	STATUS	current
    	DESCRIPTION
    	    "."
    	::= { mpIrmpConfEntry 22 }

	irmpRedisBgpRM	OBJECT-TYPE
    	SYNTAX	OCTET STRING (SIZE(0..32))
    	MAX-ACCESS  read-create
    	STATUS	current
    	DESCRIPTION
    	    "."
    	::= { mpIrmpConfEntry 23 }

	irmpRedisConnectRM	OBJECT-TYPE
    	SYNTAX	OCTET STRING (SIZE(0..32))
    	MAX-ACCESS  read-create
    	STATUS	current
    	DESCRIPTION
    	    "."
    	::= { mpIrmpConfEntry 24 }

	irmpRedisSnspRM	OBJECT-TYPE
    	SYNTAX	OCTET STRING (SIZE(0..32))
    	MAX-ACCESS  read-create
    	STATUS	current
    	DESCRIPTION
    	    "."
    	::= { mpIrmpConfEntry 25 }

	irmpRedisOspfRM	OBJECT-TYPE
    	SYNTAX	OCTET STRING (SIZE(0..32))
    	MAX-ACCESS  read-create
    	STATUS	current
    	DESCRIPTION
    	    "."
    	::= { mpIrmpConfEntry 26 }

	irmpRedisRipRM	OBJECT-TYPE
    	SYNTAX	OCTET STRING (SIZE(0..32))
    	MAX-ACCESS  read-create
    	STATUS	current
    	DESCRIPTION
    	    "."
    	::= { mpIrmpConfEntry 27 }

	irmpRedisStaticRM	OBJECT-TYPE
    	SYNTAX	OCTET STRING (SIZE(0..32))
    	MAX-ACCESS  read-create
    	STATUS	current
    	DESCRIPTION
    	    "."
    	::= { mpIrmpConfEntry 28 }

	irmpActivetime	OBJECT-TYPE
    	SYNTAX	Unsigned32 (1..4294967295)
    	MAX-ACCESS  read-create
    	STATUS	current
    	DESCRIPTION
    	    "."
    	::= { mpIrmpConfEntry 29 }

	irmpVariance	OBJECT-TYPE
    	SYNTAX	INTEGER (1..128)
    	MAX-ACCESS  read-create
    	STATUS	current
    	DESCRIPTION
    	    "."
    	::= { mpIrmpConfEntry 30 }

	irmpRowStatus	OBJECT-TYPE
    	SYNTAX	RowStatus
    	MAX-ACCESS  read-create
    	STATUS	current
    	DESCRIPTION
    	    "."
    	::= { mpIrmpConfEntry 31 }

-- *************************
-- irmp Redistribute irmp

    mpIrmpRedisIrmpTable OBJECT-TYPE
    	SYNTAX	SEQUENCE OF MpIrmpRedisIrmpEntry
    	MAX-ACCESS   not-accessible
    	STATUS	current
    	DESCRIPTION
    	    "The redistribute Irmp Table."
    	::= { mpIrmpConf 2 }

    mpIrmpRedisIrmpEntry OBJECT-TYPE
    	SYNTAX	MpIrmpRedisIrmpEntry
    	MAX-ACCESS  not-accessible
    	STATUS	current
    	DESCRIPTION
    	    "Single redistribute Irmp Table."
    	INDEX { redisIrmpAutoNum, redisIrmpNo }
    	::= { mpIrmpRedisIrmpTable 1 }
    	
    MpIrmpRedisIrmpEntry ::=
    	SEQUENCE {
    		redisIrmpAutoNum
    			INTEGER,
    		redisIrmpNo
    			INTEGER,
    		redisIrmpRouteMap
    			OCTET STRING,
    		redisIrmpRowStatus
    			RowStatus
    			}

    redisIrmpAutoNum OBJECT-TYPE
    	SYNTAX	INTEGER (1..65535)
    	MAX-ACCESS  read-only
    	STATUS	current
    	DESCRIPTION
    	    "irmp自治系统号."
    	::= { mpIrmpRedisIrmpEntry 1 }

    redisIrmpNo OBJECT-TYPE
    	SYNTAX	INTEGER (1..65535)
    	MAX-ACCESS  read-only
    	STATUS	current
    	DESCRIPTION
    	    "重分发irmp路由的irmp自治系统号."
    	::= { mpIrmpRedisIrmpEntry 2 }

    redisIrmpRouteMap OBJECT-TYPE
    	SYNTAX	OCTET STRING (SIZE(0..32))
    	MAX-ACCESS  read-create
    	STATUS	current
    	DESCRIPTION
    	    "重分发irmp路由所用的route map."
    	::= { mpIrmpRedisIrmpEntry 3 }

    redisIrmpRowStatus OBJECT-TYPE
    	SYNTAX	RowStatus
    	MAX-ACCESS  read-create
    	STATUS	current
    	DESCRIPTION
    	    "重分发irmp路由表的行状态,用于删除或添加行."
    	::= { mpIrmpRedisIrmpEntry 4 }

-- *************
-- irmp distribute

    mpIrmpDistTable OBJECT-TYPE
    	SYNTAX	SEQUENCE OF MpIrmpDistEntry
    	MAX-ACCESS   not-accessible
    	STATUS	current
    	DESCRIPTION
    	    "The valid Irmp Distribute Configure."
    	::= { mpIrmpConf 3 }

    mpIrmpDistEntry OBJECT-TYPE
    	SYNTAX	MpIrmpDistEntry
    	MAX-ACCESS  not-accessible
    	STATUS	current
    	DESCRIPTION
    	    "Single Irmp Distribute Configuration."
    	INDEX { irmpDistAutoNo, irmpDistFilterDirect, irmpDistIfIndex }
    	::= { mpIrmpDistTable 1 }
    	
    MpIrmpDistEntry ::=
    	SEQUENCE {
			irmpDistAutoNo			INTEGER,
			irmpDistFilterDirect	INTEGER,
			irmpDistIfIndex		Unsigned32,
			irmpDistAclNo			INTEGER,
			irmpDistRowStatus		RowStatus
				}

	irmpDistAutoNo	OBJECT-TYPE
    	SYNTAX	INTEGER (1..65535)
    	MAX-ACCESS  read-create
    	STATUS	current
    	DESCRIPTION
    	    "."
    	::= { mpIrmpDistEntry 1 }

	irmpDistFilterDirect	OBJECT-TYPE
    	SYNTAX	INTEGER {
    				in(1),
    				out(2)
    					}
    	MAX-ACCESS  read-create
    	STATUS	current
    	DESCRIPTION
    	    "."
    	::= { mpIrmpDistEntry 2 }

	irmpDistIfIndex	OBJECT-TYPE
    	SYNTAX	Unsigned32
    	MAX-ACCESS  read-create
    	STATUS	current
    	DESCRIPTION
    	    "如果没有接口配置,则此索引值为4294967295."
    	::= { mpIrmpDistEntry 3 }

	irmpDistAclNo	OBJECT-TYPE
    	SYNTAX	INTEGER (1..1000)
    	MAX-ACCESS  read-create
    	STATUS	current
    	DESCRIPTION
    	    "."
    	::= { mpIrmpDistEntry 4 }

	irmpDistRowStatus	OBJECT-TYPE
    	SYNTAX	RowStatus
    	MAX-ACCESS  read-create
    	STATUS	current
    	DESCRIPTION
    	    "."
    	::= { mpIrmpDistEntry 5 }

-- *************
-- irmp neighbor

    mpIrmpNbrTable OBJECT-TYPE
    	SYNTAX	SEQUENCE OF MpIrmpNbrEntry
    	MAX-ACCESS   not-accessible
    	STATUS	current
    	DESCRIPTION
    	    "The valid Irmp Neighbor Configure."
    	::= { mpIrmpConf 4 }

    mpIrmpNbrEntry OBJECT-TYPE
    	SYNTAX	MpIrmpNbrEntry
    	MAX-ACCESS  not-accessible
    	STATUS	current
    	DESCRIPTION
    	    "Single Irmp Neighbor Configuration."
    	INDEX { irmpNbrAutoNo, irmpNbrAddr }
    	::= { mpIrmpNbrTable 1 }
    	
    MpIrmpNbrEntry ::=
    	SEQUENCE {
			irmpNbrAutoNo		INTEGER,
			irmpNbrAddr		IpAddress,
			irmpNbrIfIndex		Unsigned32,
			irmpNbrRowStatus	RowStatus
				}

	irmpNbrAutoNo	OBJECT-TYPE
    	SYNTAX	INTEGER (1..65535)
    	MAX-ACCESS  read-create
    	STATUS	current
    	DESCRIPTION
    	    "."
    	::= { mpIrmpNbrEntry 1 }

	irmpNbrAddr	OBJECT-TYPE
    	SYNTAX	IpAddress
    	MAX-ACCESS  read-create
    	STATUS	current
    	DESCRIPTION
    	    "."
    	::= { mpIrmpNbrEntry 2 }

	irmpNbrIfIndex	OBJECT-TYPE
    	SYNTAX	Unsigned32
    	MAX-ACCESS  read-create
    	STATUS	current
    	DESCRIPTION
    	    "."
    	::= { mpIrmpNbrEntry 3 }

	irmpNbrRowStatus	OBJECT-TYPE
    	SYNTAX	RowStatus
    	MAX-ACCESS  read-create
    	STATUS	current
    	DESCRIPTION
    	    "."
    	::= { mpIrmpNbrEntry 4 }

-- *************
-- irmp network

    mpIrmpNetworkTable OBJECT-TYPE
    	SYNTAX	SEQUENCE OF MpIrmpNetworkEntry
    	MAX-ACCESS   not-accessible
    	STATUS	current
    	DESCRIPTION
    	    "The valid Irmp Network Configure."
    	::= { mpIrmpConf 5 }

    mpIrmpNetworkEntry OBJECT-TYPE
    	SYNTAX	MpIrmpNetworkEntry
    	MAX-ACCESS  not-accessible
    	STATUS	current
    	DESCRIPTION
    	    "Single Irmp Network Configuration."
    	INDEX { irmpNetAutoNo, irmpNetNumber }
    	::= { mpIrmpNetworkTable 1 }
    	
    MpIrmpNetworkEntry ::=
    	SEQUENCE {
			irmpNetAutoNo		INTEGER,
			irmpNetNumber		IpAddress,
			irmpNetWildcard	IpAddress,
			irmpNetRowStatus	RowStatus
				}

	irmpNetAutoNo	OBJECT-TYPE
    	SYNTAX	INTEGER (1..65535)
    	MAX-ACCESS  read-create
    	STATUS	current
    	DESCRIPTION
    	    "."
    	::= { mpIrmpNetworkEntry 1 }

	irmpNetNumber	OBJECT-TYPE
    	SYNTAX	IpAddress
    	MAX-ACCESS  read-create
    	STATUS	current
    	DESCRIPTION
    	    "."
    	::= { mpIrmpNetworkEntry 2 }

	irmpNetWildcard	OBJECT-TYPE
    	SYNTAX	IpAddress
    	MAX-ACCESS  read-create
    	STATUS	current
    	DESCRIPTION
    	    "."
    	::= { mpIrmpNetworkEntry 3 }

	irmpNetRowStatus	OBJECT-TYPE
    	SYNTAX	RowStatus
    	MAX-ACCESS  read-create
    	STATUS	current
    	DESCRIPTION
    	    "."
    	::= { mpIrmpNetworkEntry 4 }

-- *************
-- irmp offset

    mpIrmpOffsetTable OBJECT-TYPE
    	SYNTAX	SEQUENCE OF MpIrmpOffsetEntry
    	MAX-ACCESS   not-accessible
    	STATUS	current
    	DESCRIPTION
    	    "The valid Irmp Offset Configure."
    	::= { mpIrmpConf 6 }

    mpIrmpOffsetEntry OBJECT-TYPE
    	SYNTAX	MpIrmpOffsetEntry
    	MAX-ACCESS  not-accessible
    	STATUS	current
    	DESCRIPTION
    	    "Single Irmp Offset Configuration."
    	INDEX { irmpOffsetAutoNo, irmpOffsetDirection, irmpOffsetIfIndex }
    	::= { mpIrmpOffsetTable 1 }
    	
    MpIrmpOffsetEntry ::=
    	SEQUENCE {
			irmpOffsetAutoNo		INTEGER,
			irmpOffsetDirection	INTEGER,
			irmpOffsetIfIndex		Unsigned32,
			irmpOffsetValue		Unsigned32,
			irmpOffsetAclNo		INTEGER,
			irmpOffsetRowStatus	RowStatus
				}
				
	irmpOffsetAutoNo	OBJECT-TYPE
    	SYNTAX	INTEGER (1..65535)
    	MAX-ACCESS  read-create
    	STATUS	current
    	DESCRIPTION
    	    "."
    	::= { mpIrmpOffsetEntry 1 }

	irmpOffsetDirection	OBJECT-TYPE
    	SYNTAX	INTEGER {
    				in(1),
    				out(2)
    					}
    	MAX-ACCESS  read-create
    	STATUS	current
    	DESCRIPTION
    	    "."
    	::= { mpIrmpOffsetEntry 2 }

	irmpOffsetIfIndex	OBJECT-TYPE
    	SYNTAX	Unsigned32
    	MAX-ACCESS  read-create
    	STATUS	current
    	DESCRIPTION
    	    "如果没有接口配置,则此索引值为4294967295."
    	::= { mpIrmpOffsetEntry 3 }

	irmpOffsetValue	OBJECT-TYPE
    	SYNTAX	Unsigned32 (1..2147483647)
    	MAX-ACCESS  read-create
    	STATUS	current
    	DESCRIPTION
    	    "."
    	::= { mpIrmpOffsetEntry 4 }

	irmpOffsetAclNo	OBJECT-TYPE
    	SYNTAX	INTEGER (1..2000)
    	MAX-ACCESS  read-create
    	STATUS	current
    	DESCRIPTION
    	    "."
    	::= { mpIrmpOffsetEntry 5 }

	irmpOffsetRowStatus	OBJECT-TYPE
    	SYNTAX	RowStatus
    	MAX-ACCESS  read-create
    	STATUS	current
    	DESCRIPTION
    	    "."
    	::= { mpIrmpOffsetEntry 6 }

-- ************************
-- irmp passive interface

    mpIrmpPassvIfTable OBJECT-TYPE
    	SYNTAX	SEQUENCE OF MpIrmpPassvIfEntry
    	MAX-ACCESS   not-accessible
    	STATUS	current
    	DESCRIPTION
    	    "The valid Irmp Passive Interface Configure."
    	::= { mpIrmpConf 7 }

    mpIrmpPassvIfEntry OBJECT-TYPE
    	SYNTAX	MpIrmpPassvIfEntry
    	MAX-ACCESS  not-accessible
    	STATUS	current
    	DESCRIPTION
    	    "Single Irmp Passive Interface Configuration."
    	INDEX { irmpPassvIfAutoNo, irmpPassvIfIndex }
    	::= { mpIrmpPassvIfTable 1 }
    	
    MpIrmpPassvIfEntry ::=
    	SEQUENCE {
			irmpPassvIfAutoNo		INTEGER,
			irmpPassvIfIndex		INTEGER,
			irmpPassvIfRowStatus	RowStatus
				}

	irmpPassvIfAutoNo	OBJECT-TYPE
    	SYNTAX	INTEGER (1..65535)
    	MAX-ACCESS  read-create
    	STATUS	current
    	DESCRIPTION
    	    "."
    	::= { mpIrmpPassvIfEntry 1 }

	irmpPassvIfIndex	OBJECT-TYPE
    	SYNTAX	INTEGER
    	MAX-ACCESS  read-create
    	STATUS	current
    	DESCRIPTION
    	    "."
    	::= { mpIrmpPassvIfEntry 2 }

	irmpPassvIfRowStatus	OBJECT-TYPE
    	SYNTAX	RowStatus
    	MAX-ACCESS  read-create
    	STATUS	current
    	DESCRIPTION
    	    "."
    	::= { mpIrmpPassvIfEntry 3 }


-- **************************
-- interface
-- **************************

-- *************
-- interface configure

    mpIrmpIfTable OBJECT-TYPE
    	SYNTAX	SEQUENCE OF MpIrmpIfEntry
    	MAX-ACCESS   not-accessible
    	STATUS	current
    	DESCRIPTION
    	    "The valid Irmp Interface Configure."
    	::= { mpIrmpIf 1 }

    mpIrmpIfEntry OBJECT-TYPE
    	SYNTAX	MpIrmpIfEntry
    	MAX-ACCESS  not-accessible
    	STATUS	current
    	DESCRIPTION
    	    "Single Irmp interface Configuration."
    	INDEX { ifIrmpIfIndex, ifIrmpAutoNo }
    	::= { mpIrmpIfTable 1 }
    	
    MpIrmpIfEntry ::=
    	SEQUENCE {
			ifIrmpIfIndex			INTEGER,
			ifIrmpAutoNo			INTEGER,
			ifIrmpBWPercent		INTEGER,
			ifIrmpHelloInter		INTEGER,
			ifIrmpHoldtime			INTEGER,
			ifIrmpSplitHorizon		INTEGER,
			ifIrmpAuthKeyID		INTEGER,
			ifIrmpAuthType			INTEGER,
			ifIrmpAuthEncrypt		INTEGER,
			ifIrmpAuthPwd			OCTET STRING,
			ifIrmpAuthRowStatus	RowStatus
			ifIrmpRowStatus		RowStatus
				}

	ifIrmpIfIndex	OBJECT-TYPE
    	SYNTAX	INTEGER
    	MAX-ACCESS  read-create
    	STATUS	current
    	DESCRIPTION
    	    "接口索引."
    	::= { mpIrmpIfEntry 1 }

	ifIrmpAutoNo	OBJECT-TYPE
    	SYNTAX	INTEGER (1..65535)
    	MAX-ACCESS  read-create
    	STATUS	current
    	DESCRIPTION
    	    "irmp系统号."
    	::= { mpIrmpIfEntry 2 }

	ifIrmpBWPercent	OBJECT-TYPE
    	SYNTAX	INTEGER (1..999999)
    	MAX-ACCESS  read-create
    	STATUS	current
    	DESCRIPTION
    	    "."
    	::= { mpIrmpIfEntry 3 }

	ifIrmpHelloInter	OBJECT-TYPE
    	SYNTAX	INTEGER (1..65535)
    	MAX-ACCESS  read-create
    	STATUS	current
    	DESCRIPTION
    	    "."
    	::= { mpIrmpIfEntry 4 }

	ifIrmpHoldtime	OBJECT-TYPE
    	SYNTAX	INTEGER (1..6535)
    	MAX-ACCESS  read-create
    	STATUS	current
    	DESCRIPTION
    	    "."
    	::= { mpIrmpIfEntry 5 }

	ifIrmpSplitHorizon	OBJECT-TYPE
    	SYNTAX	INTEGER {
    				disable(1),
    				enable(2)
    					}
    	MAX-ACCESS  read-create
    	STATUS	current
    	DESCRIPTION
    	    "."
    	::= { mpIrmpIfEntry 6 }

	ifIrmpAuthKeyID	OBJECT-TYPE
    	SYNTAX	INTEGER (1..65535)
    	MAX-ACCESS  read-create
    	STATUS	current
    	DESCRIPTION
    	    "."
    	::= { mpIrmpIfEntry 7 }

	ifIrmpAuthType	OBJECT-TYPE
    	SYNTAX	INTEGER {
    				noAuth(1),
    				simpleTxt(2),
    				md5(3)
    					}
    	MAX-ACCESS  read-create
    	STATUS	current
    	DESCRIPTION
    	    "."
    	::= { mpIrmpIfEntry 8 }

	ifIrmpAuthEncrypt	OBJECT-TYPE
    	SYNTAX	INTEGER
    	MAX-ACCESS  read-create
    	STATUS	current
    	DESCRIPTION
    	    "irmp在接口上的认证密钥是否加密.其值为1时不加密, 为8时表示加密,其它值无意义."
    	::= { mpIrmpIfEntry 9 }

	ifIrmpAuthPwd	OBJECT-TYPE
    	SYNTAX	OCTET STRING (SIZE(1..16))
    	MAX-ACCESS  read-create
    	STATUS	current
    	DESCRIPTION
    	    "."
    	::= { mpIrmpIfEntry 10 }

	ifIrmpRowStatus	OBJECT-TYPE
    	SYNTAX	RowStatus
    	MAX-ACCESS  read-create
    	STATUS	current
    	DESCRIPTION
    	    "."
    	::= { mpIrmpIfEntry 11 }

-- *************
-- interface summary configure

    mpIrmpIfSummTable OBJECT-TYPE
    	SYNTAX	SEQUENCE OF MpIrmpIfSummEntry
    	MAX-ACCESS   not-accessible
    	STATUS	current
    	DESCRIPTION
    	    "The valid Irmp Interface summary Configure."
    	::= { mpIrmpIf 2 }

    mpIrmpIfSummEntry OBJECT-TYPE
    	SYNTAX	MpIrmpIfSummEntry
    	MAX-ACCESS  not-accessible
    	STATUS	current
    	DESCRIPTION
    	    "Single Irmp interface summary Configuration."
    	INDEX { ifIrmpSummIfIndex, ifIrmpSummAutoNo, ifIrmpSummAddr, ifIrmpSummMask }
    	::= { mpIrmpIfSummTable 1 }
    	
    MpIrmpIfSummEntry ::=
    	SEQUENCE {
			ifIrmpSummIfIndex		INTEGER,
			ifIrmpSummAutoNo		INTEGER,
			ifIrmpSummAddr			IpAddress,
			ifIrmpSummMask			IpAddress,
			ifIrmpSummRowStatus	RowStatus
				}

	ifIrmpSummIfIndex	OBJECT-TYPE
    	SYNTAX	INTEGER
    	MAX-ACCESS  read-create
    	STATUS	current
    	DESCRIPTION
    	    "接口索引."
    	::= { mpIrmpIfSummEntry 1 }

	ifIrmpSummAutoNo	OBJECT-TYPE
    	SYNTAX	INTEGER
    	MAX-ACCESS  read-create
    	STATUS	current
    	DESCRIPTION
    	    "irmp自治系统号."
    	::= { mpIrmpIfSummEntry 2 }

	ifIrmpSummAddr	OBJECT-TYPE
    	SYNTAX	IpAddress
    	MAX-ACCESS  read-create
    	STATUS	current
    	DESCRIPTION
    	    "."
    	::= { mpIrmpIfSummEntry 3 }

	ifIrmpSummMask	OBJECT-TYPE
    	SYNTAX	IpAddress
    	MAX-ACCESS  read-create
    	STATUS	current
    	DESCRIPTION
    	    "."
    	::= { mpIrmpIfSummEntry 4 }

	ifIrmpSummRowStatus	OBJECT-TYPE
    	SYNTAX	RowStatus
    	MAX-ACCESS  read-create
    	STATUS	current
    	DESCRIPTION
    	    "."
    	::= { mpIrmpIfSummEntry 5 }

-- *************
-- interface authentication configure

--    mpIrmpIfAuthTable OBJECT-TYPE
--    	SYNTAX	SEQUENCE OF MpIrmpIfAuthEntry
--    	MAX-ACCESS   not-accessible
--    	STATUS	current
--    	DESCRIPTION
--    	    "The valid Irmp Interface authentication Configure."
--    	::= { mpIrmpIf 3 }

--    mpIrmpIfAuthEntry OBJECT-TYPE
--    	SYNTAX	MpIrmpIfAuthEntry
--    	MAX-ACCESS  not-accessible
--    	STATUS	current
--    	DESCRIPTION
--    	    "Single Irmp interface authentication Configuration."
--    	INDEX { ifIrmpAuthIfIndex, ifIrmpAuthAutoNo }
--    	::= { mpIrmpIfAuthTable 1 }
    	
--    MpIrmpIfAuthEntry ::=
--    	SEQUENCE {
--			ifIrmpAuthIfIndex		INTEGER,
--			ifIrmpAuthAutoNo		INTEGER,
--			ifIrmpAuthKeyID		INTEGER,
--			ifIrmpAuthType			INTEGER,
--			ifIrmpAuthEncrypt		INTEGER,
--			ifIrmpAuthPwd			OCTET STRING,
--			ifIrmpAuthRowStatus	RowStatus
--				}

--	ifIrmpAuthIfIndex	OBJECT-TYPE
--    	SYNTAX	INTEGER
--    	MAX-ACCESS  read-create
--    	STATUS	current
--    	DESCRIPTION
--    	    "接口索引."
--    	::= { mpIrmpIfAuthEntry 1 }

--	ifIrmpAuthAutoNo	OBJECT-TYPE
--    	SYNTAX	INTEGER
--    	MAX-ACCESS  read-create
--    	STATUS	current
--    	DESCRIPTION
--    	    "irmp自治系统号."
--    	::= { mpIrmpIfAuthEntry 2 }

--	ifIrmpAuthKeyID	OBJECT-TYPE
--    	SYNTAX	INTEGER (1..65535)
--    	MAX-ACCESS  read-create
--    	STATUS	current
--    	DESCRIPTION
--    	    "."
--    	::= { mpIrmpIfAuthEntry 3 }

--	ifIrmpAuthType	OBJECT-TYPE
--    	SYNTAX	INTEGER {
--    				noAuth(1),
--    				simpleTxt(2),
--    				md5(3)
--    					}
--    	MAX-ACCESS  read-create
--    	STATUS	current
--    	DESCRIPTION
--    	    "."
--    	::= { mpIrmpIfAuthEntry 4 }

--	ifIrmpAuthEncrypt	OBJECT-TYPE
--    	SYNTAX	INTEGER
--    	MAX-ACCESS  read-create
--    	STATUS	current
--    	DESCRIPTION
--    	    "irmp在接口上的认证密钥是否加密.其值为1时不加密, 为8时表示加密,其它值无意义."
--    	::= { mpIrmpIfAuthEntry 5 }

--	ifIrmpAuthPwd	OBJECT-TYPE
--    	SYNTAX	OCTET STRING (SIZE(1..16))
--    	MAX-ACCESS  read-create
--    	STATUS	current
--    	DESCRIPTION
--    	    "."
--    	::= { mpIrmpIfAuthEntry 6 }

--	ifIrmpAuthRowStatus	OBJECT-TYPE
--    	SYNTAX	RowStatus
--    	MAX-ACCESS  read-create
--    	STATUS	current
--    	DESCRIPTION
--    	    "."
--    	::= { mpIrmpIfAuthEntry 7 }


-- **************************
-- statistic
-- **************************

-- *************
-- traffic

    mpIrmpTrafficTable OBJECT-TYPE
    	SYNTAX	SEQUENCE OF MpIrmpTrafficEntry
    	MAX-ACCESS   not-accessible
    	STATUS	current
    	DESCRIPTION
    	    "The valid Irmp traffic statistic."
    	::= { mpIrmpStat 1 }

    mpIrmpTrafficEntry OBJECT-TYPE
    	SYNTAX	MpIrmpTrafficEntry
    	MAX-ACCESS  not-accessible
    	STATUS	current
    	DESCRIPTION
    	    "Single Irmp raffic statistic."
    	INDEX { irmpTrafficAutoNo }
    	::= { mpIrmpTrafficTable 1 }
    	
    MpIrmpTrafficEntry ::=
    	SEQUENCE {
			irmpTrafficAutoNo		INTEGER,
			irmpTrafficHelloSents	Counter32,
			irmpTrafficUpdateSents	Counter32,
			irmpTrafficQuerySents	Counter32,
			irmpTrafficReplySents	Counter32,
			irmpTrafficAckSents	Counter32,
			irmpTrafficHelloRecvs	Counter32,
			irmpTrafficUpdateRecvs	Counter32,
			irmpTrafficQueryRecvs	Counter32,
			irmpTrafficReplyRecvs	Counter32,
			irmpTrafficAckRecvs	Counter32
				}

    irmpTrafficAutoNo OBJECT-TYPE
    	SYNTAX	INTEGER (1..65535)
    	MAX-ACCESS  read-only
    	STATUS	current
    	DESCRIPTION
    	    "自治系统号."
    	::= { mpIrmpTrafficEntry 1 }
    	
    irmpTrafficHelloSents	OBJECT-TYPE
    	SYNTAX	Counter32
    	MAX-ACCESS  read-only
    	STATUS	current
    	DESCRIPTION
    	    "."
    	::= { mpIrmpTrafficEntry 2 }

	irmpTrafficUpdateSents	OBJECT-TYPE
    	SYNTAX	Counter32
    	MAX-ACCESS  read-only
    	STATUS	current
    	DESCRIPTION
    	    "."
    	::= { mpIrmpTrafficEntry 3 }

	irmpTrafficQueriSents	OBJECT-TYPE
    	SYNTAX	Counter32
    	MAX-ACCESS  read-only
    	STATUS	current
    	DESCRIPTION
    	    "."
    	::= { mpIrmpTrafficEntry 4 }

	irmpTrafficReplySents	OBJECT-TYPE
    	SYNTAX	Counter32
    	MAX-ACCESS  read-only
    	STATUS	current
    	DESCRIPTION
    	    "."
    	::= { mpIrmpTrafficEntry 5 }

	irmpTrafficAckSents	OBJECT-TYPE
    	SYNTAX	Counter32
    	MAX-ACCESS  read-only
    	STATUS	current
    	DESCRIPTION
    	    "."
    	::= { mpIrmpTrafficEntry 6 }

    irmpTrafficHelloRecvs	OBJECT-TYPE
    	SYNTAX	Counter32
    	MAX-ACCESS  read-only
    	STATUS	current
    	DESCRIPTION
    	    "."
    	::= { mpIrmpTrafficEntry 7 }

	irmpTrafficUpdateRecvs	OBJECT-TYPE
    	SYNTAX	Counter32
    	MAX-ACCESS  read-only
    	STATUS	current
    	DESCRIPTION
    	    "."
    	::= { mpIrmpTrafficEntry 8 }

	irmpTrafficQueriRecvs	OBJECT-TYPE
    	SYNTAX	Counter32
    	MAX-ACCESS  read-only
    	STATUS	current
    	DESCRIPTION
    	    "."
    	::= { mpIrmpTrafficEntry 9 }

	irmpTrafficReplyRecvs	OBJECT-TYPE
    	SYNTAX	Counter32
    	MAX-ACCESS  read-only
    	STATUS	current
    	DESCRIPTION
    	    "."
    	::= { mpIrmpTrafficEntry 10 }

	irmpTrafficAckRecvs	OBJECT-TYPE
    	SYNTAX	Counter32
    	MAX-ACCESS  read-only
    	STATUS	current
    	DESCRIPTION
    	    "."
    	::= { mpIrmpTrafficEntry 11 }

-- *************
-- neighbor statistic

    mpIrmpNbrStatTable OBJECT-TYPE
    	SYNTAX	SEQUENCE OF MpIrmpNbrStatEntry
    	MAX-ACCESS   not-accessible
    	STATUS	current
    	DESCRIPTION
    	    "The valid Irmp neighbor statistic."
    	::= { mpIrmpStat 2 }

    mpIrmpNbrStatEntry OBJECT-TYPE
    	SYNTAX	MpIrmpNbrStatEntry
    	MAX-ACCESS  not-accessible
    	STATUS	current
    	DESCRIPTION
    	    "Single Irmp neighbor statistic."
    	INDEX { irmpNbrStatAutoNo, irmpNbrStatAddr }
    	::= { mpIrmpNbrStatTable 1 }
    	
    MpIrmpNbrStatEntry ::=
    	SEQUENCE {
			irmpNbrStatAutoNo		INTEGER,
			irmpNbrStatAddr		IpAddress,
			irmpNbrStatH			Counter32,
			irmpNbrStatIfIndex		INTEGER,
			irmpNbrStatHoldtime	Counter32,
			irmpNbrStatUptime		Counter32,
			irmpNbrStatSeqNum		Counter32
				}

    irmpNbrStatAutoNo OBJECT-TYPE
    	SYNTAX	INTEGER (1..65535)
    	MAX-ACCESS  read-only
    	STATUS	current
    	DESCRIPTION
    	    "自治系统号."
    	::= { mpIrmpNbrStatEntry 1 }

    irmpNbrStatAddr OBJECT-TYPE
    	SYNTAX	IpAddress
    	MAX-ACCESS  read-only
    	STATUS	current
    	DESCRIPTION
    	    "."
    	::= { mpIrmpNbrStatEntry 2 }
 	
    irmpNbrStatH OBJECT-TYPE
    	SYNTAX	Counter32
    	MAX-ACCESS  read-only
    	STATUS	current
    	DESCRIPTION
    	    "."
    	::= { mpIrmpNbrStatEntry 3 }
 	
    irmpNbrStatIfIndex OBJECT-TYPE
    	SYNTAX	INTEGER
    	MAX-ACCESS  read-only
    	STATUS	current
    	DESCRIPTION
    	    "."
    	::= { mpIrmpNbrStatEntry 4 }
 	
    irmpNbrStatHoldtime OBJECT-TYPE
    	SYNTAX	Counter32
    	MAX-ACCESS  read-only
    	STATUS	current
    	DESCRIPTION
    	    "."
    	::= { mpIrmpNbrStatEntry 5 }
 	
    irmpNbrStatUptime OBJECT-TYPE
    	SYNTAX	Counter32
    	MAX-ACCESS  read-only
    	STATUS	current
    	DESCRIPTION
    	    "."
    	::= { mpIrmpNbrStatEntry 6 }
 	
    irmpNbrStatSeqNum OBJECT-TYPE
    	SYNTAX	Counter32
    	MAX-ACCESS  read-only
    	STATUS	current
    	DESCRIPTION
    	    "."
    	::= { mpIrmpNbrStatEntry 7 }
 	
-- *************
-- interface statistic

    mpIrmpIfStatTable OBJECT-TYPE
    	SYNTAX	SEQUENCE OF MpIrmpIfStatEntry
    	MAX-ACCESS   not-accessible
    	STATUS	current
    	DESCRIPTION
    	    "The valid Irmp neighbor statistic."
    	::= { mpIrmpStat 3 }

    mpIrmpIfStatEntry OBJECT-TYPE
    	SYNTAX	MpIrmpIfStatEntry
    	MAX-ACCESS  not-accessible
    	STATUS	current
    	DESCRIPTION
    	    "Single Irmp interface statistic."
    	INDEX { irmpIfStatAutoNo, irmpIfStatIfIndex }
    	::= { mpIrmpIfStatTable 1 }
    	
    MpIrmpIfStatEntry ::=
    	SEQUENCE {
			irmpIfStatAutoNo		INTEGER,
			irmpIfStatIfIndex		INTEGER,
			irmpIfStatLocalAddr	IpAddress,
			irmpIfStatPeers		INTEGER,
			irmpIfStatHelloInter	INTEGER,
			irmpIfStatHoldTime		INTEGER,
			irmpIfStatPassive		INTEGER
				}

    irmpIfStatAutoNo OBJECT-TYPE
    	SYNTAX	INTEGER (1..65535)
    	MAX-ACCESS  read-only
    	STATUS	current
    	DESCRIPTION
    	    "自治系统号."
    	::= { mpIrmpIfStatEntry 1 }

    irmpIfStatIfIndex OBJECT-TYPE
    	SYNTAX	INTEGER
    	MAX-ACCESS  read-only
    	STATUS	current
    	DESCRIPTION
    	    "."
    	::= { mpIrmpIfStatEntry 2 }

    irmpIfStatLocalAddr OBJECT-TYPE
    	SYNTAX	IpAddress 
    	MAX-ACCESS  read-only
    	STATUS	current
    	DESCRIPTION
    	    "."
    	::= { mpIrmpIfStatEntry 3 }

    irmpIfStatPeers OBJECT-TYPE
    	SYNTAX	INTEGER
    	MAX-ACCESS  read-only
    	STATUS	current
    	DESCRIPTION
    	    "."
    	::= { mpIrmpIfStatEntry 4 }

    irmpIfStatHelloInter OBJECT-TYPE
    	SYNTAX	INTEGER
    	MAX-ACCESS  read-only
    	STATUS	current
    	DESCRIPTION
    	    "."
    	::= { mpIrmpIfStatEntry 5 }

    irmpIfStatHoldTime OBJECT-TYPE
    	SYNTAX	INTEGER
    	MAX-ACCESS  read-only
    	STATUS	current
    	DESCRIPTION
    	    "."
    	::= { mpIrmpIfStatEntry 6 }

    irmpIfStatPassive OBJECT-TYPE
    	SYNTAX	INTEGER {
    				disable(1),
    				enable(2)
    					}
    	MAX-ACCESS  read-only
    	STATUS	current
    	DESCRIPTION
    	    "该接口是否是passive接口."
    	::= { mpIrmpIfStatEntry 7 }

-- *************
-- interface statistic

    mpIrmpTopoTable OBJECT-TYPE
    	SYNTAX	SEQUENCE OF MpIrmpTopoEntry
    	MAX-ACCESS   not-accessible
    	STATUS	current
    	DESCRIPTION
    	    "The valid Irmp topo statistic."
    	::= { mpIrmpStat 4 }

    mpIrmpTopoEntry OBJECT-TYPE
    	SYNTAX	MpIrmpTopoEntry
    	MAX-ACCESS  not-accessible
    	STATUS	current
    	DESCRIPTION
    	    "Single Irmp topo statistic."
    	INDEX { irmpTopoAutoNo, irmpTopoAddr, irmpTopoMask }
    	::= { mpIrmpTopoTable 1 }
    	
    MpIrmpTopoEntry ::=
    	SEQUENCE {
			irmpTopoAutoNo		INTEGER,
			irmpTopoAddr		IpAddress,
			irmpTopoMask		IpAddress,
			irmpTopoType		INTEGER,
			irmpTopoSuccessors	INTEGER,
			irmpTopoFD			INTEGER,
				}

    irmpTopoAutoNo OBJECT-TYPE
    	SYNTAX	INTEGER (1..65535)
    	MAX-ACCESS  read-only
    	STATUS	current
    	DESCRIPTION
    	    "自治系统号."
    	::= { mpIrmpTopoEntry 1 }

    irmpTopoAddr OBJECT-TYPE
    	SYNTAX	IpAddress
    	MAX-ACCESS  read-only
    	STATUS	current
    	DESCRIPTION
    	    "."
    	::= { mpIrmpTopoEntry 2 }

    irmpTopoMask OBJECT-TYPE
    	SYNTAX	IpAddress
    	MAX-ACCESS  read-only
    	STATUS	current
    	DESCRIPTION
    	    "."
    	::= { mpIrmpTopoEntry 3 }

    irmpTopoType OBJECT-TYPE
    	SYNTAX	INTEGER {
    				passive(1),
    				active(2),
    				update(3),
    				query(4),
    				reply(5),
    				replyStatus(6),
    				holddown(7)
    					}
    	MAX-ACCESS  read-only
    	STATUS	current
    	DESCRIPTION
    	    "."
    	::= { mpIrmpTopoEntry 4 }

    irmpTopoSuccessors OBJECT-TYPE
    	SYNTAX	INTEGER
    	MAX-ACCESS  read-only
    	STATUS	current
    	DESCRIPTION
    	    "."
    	::= { mpIrmpTopoEntry 5 }

    irmpTopoFD OBJECT-TYPE
    	SYNTAX	INTEGER
    	MAX-ACCESS  read-only
    	STATUS	current
    	DESCRIPTION
    	    "."
    	::= { mpIrmpTopoEntry 6 }

 -- *************************
-- irmp topology via table

    mpIrmpTopoViaTable OBJECT-TYPE
    	SYNTAX	SEQUENCE OF MpIrmpTopoViaEntry
    	MAX-ACCESS   not-accessible
    	STATUS	current
    	DESCRIPTION
    	    "The irmp topology next hop table."
    	::= { mpIrmpStat 5 }

    mpIrmpTopoViaEntry OBJECT-TYPE
    	SYNTAX	MpIrmpTopoViaEntry
    	MAX-ACCESS  not-accessible
    	STATUS	current
    	DESCRIPTION
    	    "Single irmp topology next hop entry."
    	INDEX { irmpTopoViaAutoNum, irmpTopoViaTopoAddr, irmpTopoViaTopoMask, irmpTopoViaIndex }
    	::= { mpIrmpTopoViaTable 1 }
    	
    MpIrmpTopoViaEntry ::=
    	SEQUENCE {
    		irmpTopoViaAutoNum	INTEGER,
			irmpTopoViaTopoAddr	IpAddress,
			irmpTopoViaTopoMask	IpAddress,
			irmpTopoViaIndex	INTEGER,
    		irmpTopoViaAddr	IpAddress,
			irmpTopoViaType	INTEGER,
			irmpTopoViaIrmpNo	INTEGER,
			irmpTopoViaIpAddr	IpAddress,
			irmpTopoViaMyCost	INTEGER,
			irmpTopoViaHisCost	INTEGER,
			irmpTopoViaIfIndex	INTEGER
				}

   irmpTopoViaAutoNum OBJECT-TYPE
    	SYNTAX	INTEGER (1..65535)
    	MAX-ACCESS  read-only
    	STATUS	current
    	DESCRIPTION
    	    "irmp自治系统号."
    	::= { mpIrmpTopoViaEntry 1 }

	irmpTopoViaTopoAddr OBJECT-TYPE
    	SYNTAX	IpAddress
    	MAX-ACCESS  read-only
    	STATUS	current
    	DESCRIPTION
    	    "irmp拓扑地址."
    	::= { mpIrmpTopoViaEntry 2 }

	irmpTopoViaTopoMask OBJECT-TYPE
    	SYNTAX	IpAddress
    	MAX-ACCESS  read-only
    	STATUS	current
    	DESCRIPTION
    	    "irmp拓扑地址掩码."
    	::= { mpIrmpTopoViaEntry 3 }

	irmpTopoViaIndex OBJECT-TYPE
    	SYNTAX	INTEGER
    	MAX-ACCESS  read-only
    	STATUS	current
    	DESCRIPTION
    	    "irmp拓扑下一跳结点指针."
    	::= { mpIrmpTopoViaEntry 4 }

   irmpTopoViaAddr OBJECT-TYPE
    	SYNTAX	IpAddress
    	MAX-ACCESS  read-only
    	STATUS	current
    	DESCRIPTION
    	    "irmp路由的网段地址."
    	::= { mpIrmpTopoViaEntry 5 }

   irmpTopoViaType OBJECT-TYPE
    	SYNTAX	INTEGER {
    				connected(1),
    				gateway(2),
    				redisStatic(3),
    				redisBgp(4),
    				redisRip(5),
    				redisSnsp(6),
    				redisOspf(7),
    				redisConnected(8),
    				redisIrmp(9),
    				autoSummary(10),
    				summaryAddr(11)
    					}
    	MAX-ACCESS  read-only
    	STATUS	current
    	DESCRIPTION
    	    "irmp topology下一跳的类型."
    	::= { mpIrmpTopoViaEntry 6 }

   irmpTopoViaIrmpNo OBJECT-TYPE
    	SYNTAX	INTEGER (1..7000)
    	MAX-ACCESS  read-only
    	STATUS	current
    	DESCRIPTION
    	    "重分发IRMP的自治系统号.如果重分发类型不是irmp,则该值为大于65535的值。"
    	::= { mpIrmpTopoViaEntry 7 }

	irmpTopoViaIpAddr OBJECT-TYPE
    	SYNTAX	IpAddress
    	MAX-ACCESS  read-only
    	STATUS	current
    	DESCRIPTION
    	    "irmp topology下一跳是网关地址时的Ip地址."
    	::= { mpIrmpTopoViaEntry 8 }
    	
	irmpTopoViaMyCost OBJECT-TYPE
    	SYNTAX	INTEGER
    	MAX-ACCESS  read-only
    	STATUS	current
    	DESCRIPTION
    	    "irmp自己的费用."
    	::= { mpIrmpTopoViaEntry 9 }
    	
	irmpTopoViaHisCost OBJECT-TYPE
    	SYNTAX	INTEGER
    	MAX-ACCESS  read-only
    	STATUS	current
    	DESCRIPTION
    	    "irmp通告的费用."
    	::= { mpIrmpTopoViaEntry 10 }
    	
    irmpTopoViaIfIndex OBJECT-TYPE
    	SYNTAX	INTEGER
    	MAX-ACCESS  read-only
    	STATUS	current
    	DESCRIPTION
    	    "irmp topology下一跳出去的接口."
    	::= { mpIrmpTopoViaEntry 11 }

-- *************************
-- irmp total routes

    mpIrmpTRTable OBJECT-TYPE
    	SYNTAX	SEQUENCE OF MpIrmpTREntry
    	MAX-ACCESS   not-accessible
    	STATUS	current
    	DESCRIPTION
    	    "irmp total routes table."
    	::= { mpIrmpStat 6 }

    mpIrmpTREntry OBJECT-TYPE
    	SYNTAX	MpIrmpTREntry
    	MAX-ACCESS  not-accessible
    	STATUS	current
    	DESCRIPTION
    	    "Single irmp total routes entry."
    	INDEX { totalRouteIrmpAutoNo }
    	::= { mpIrmpTRTable 1 }
    	
    MpIrmpTREntry ::=
    	SEQUENCE {
    		totalRouteIrmpAutoNo
    			INTEGER,
    		irmpTotalRoutes
    			INTEGER
    			}

    totalRouteIrmpAutoNo OBJECT-TYPE
    	SYNTAX	INTEGER (1..65535)
    	MAX-ACCESS  read-only
    	STATUS	current
    	DESCRIPTION
    	    "irmp自治系统号."
    	::= { mpIrmpTREntry 1 }

    irmpTotalRoutes OBJECT-TYPE
    	SYNTAX	INTEGER
    	MAX-ACCESS  read-only
    	STATUS	current
    	DESCRIPTION
    	    "irmp的总路由数."
    	::= { mpIrmpTREntry 2 }


END

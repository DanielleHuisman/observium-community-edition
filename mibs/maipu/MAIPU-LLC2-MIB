-- *****************************************************************
-- MAIPU-LLC2.mib:  Maipu enterprise device SDLC MIB file
--
--version 1.0.0.0, April 27, 2002  Huanglulu, Rogerhu
--
-- Copyright (c)  by Maipu DataComm Inc.
-- All rights reserved.
-- 
-- *****************************************************************
--

MAIPU-LLC2-MIB DEFINITIONS ::= BEGIN

IMPORTS
    RowStatus				FROM SNMPv2-TC
    MODULE-IDENTITY, OBJECT-TYPE 	FROM SNMPv2-SMI
    mpMgmt	                        FROM MAIPU-SMI;

mpLlc2Mib MODULE-IDENTITY
    LAST-UPDATED "0204270000Z"
    ORGANIZATION "Maipu DataComm"
    CONTACT-INFO
	"   Maipu DataComm
		Customer Service

		Postal: Consulate Drive
			Chengdu, Sichuan  610041
			China

		Tel: 86-028-5161006

		E-mail: office@maipu.com"
    DESCRIPTION
		"The assignments for Maipu router's MIB of LLC2 infomation!"
    ::= {mpMgmt 23 }

-- ***********************************
llc2ConfTable OBJECT-TYPE
    SYNTAX SEQUENCE OF Llc2ConfEntry
    MAX-ACCESS not-accessible
    STATUS current
    DESCRIPTION
		"LLC2的配置表."
    ::= { mpLlc2Mib 1 }

llc2ConfEntry OBJECT-TYPE
    SYNTAX Llc2ConfEntry
    MAX-ACCESS not-accessible
    STATUS current
    DESCRIPTION
		"LLC2配置表条目."
    INDEX { llc2IfIndex }    
    ::= { llc2ConfTable 1 }

Llc2ConfEntry ::=
	SEQUENCE {
		llc2IfIndex
			INTEGER,
		llc2Group
			INTEGER,
		llc2Status
			RowStatus
			}
				
llc2IfIndex	OBJECT-TYPE
	SYNTAX	INTEGER
	MAX-ACCESS	read-only
	STATUS	current
	DESCRIPTION
		"llc2IfIndex"
	::= { llc2ConfEntry 1 }
	
llc2Group	OBJECT-TYPE
	SYNTAX	INTEGER	(0..10)
	MAX-ACCESS	read-create
	STATUS	current
	DESCRIPTION
		"llc2Group"
	::= { llc2ConfEntry 2 }

llc2Status	OBJECT-TYPE
	SYNTAX	RowStatus
	MAX-ACCESS	read-create
	STATUS	current
	DESCRIPTION
		""
	::= { llc2ConfEntry 3 }

END

-- *****************************************************************
-- MAIPU-ROUTEMAP.mib:  Maipu enterprise device RouteMap MIB file
--
--version 1.0.0.0, Oct 22, 2002 Huanglulu
--
-- Copyright (c)  by Maipu DataComm Inc.
-- All rights reserved.
-- 
-- *****************************************************************
--

MAIPU-ROUTEMAP-MIB DEFINITIONS ::= BEGIN

IMPORTS
    RowStatus								FROM SNMPv2-TC
    MODULE-IDENTITY, OBJECT-TYPE,
    IpAddress, OBJECT-IDENTITY, Counter32 	FROM SNMPv2-SMI
    mpMgmt                             		FROM MAIPU-SMI;

mpRouteMapMib MODULE-IDENTITY
    LAST-UPDATED "0102160000Z"
    ORGANIZATION "Maipu DataComm"
    CONTACT-INFO
	"   Maipu DataComm
		Customer Service

		Postal: Consulate Drive
			Chengdu, Sichuan  610041
			China

		Tel: 86-028-5161006

		E-mail: office@maipu.com"
    DESCRIPTION
		"The assignments for Maipu router's MIB of RouteMap infomation!"
    ::= { mpMgmt 33 }


-- *******************
-- SMI
-- *******************

rtMapConf	OBJECT IDENTIFIER ::= { mpRouteMapMib 1 }


-- *******************
-- Configure
-- *******************

-- *******************
-- match Configure

rtMapMatchTable OBJECT-TYPE
    SYNTAX SEQUENCE OF RtMapMatchEntry
    MAX-ACCESS not-accessible
    STATUS current
    DESCRIPTION
		"路由映射匹配配置表"
    ::= { rtMapConf 1 }

rtMapMatchEntry OBJECT-TYPE
    SYNTAX RtMapMatchEntry
    MAX-ACCESS not-accessible
    STATUS current
    DESCRIPTION
		"路由映射匹配配置表表项"
    INDEX { rtMapMatchRMName, rtMapMatchRMSeq }    
    ::= { rtMapMatchTable 1 }

RtMapMatchEntry ::=
    SEQUENCE {
		rtMapMatchRMName	OCTET STRING,
		rtMapMatchRMSeq		INTEGER,
		rtMapMatchAccess	INTEGER,
		rtMapMatchAsPath	OCTET STRING,
		rtMapMatchCom		OCTET STRING,
		rtMapMatchExtCom	OCTET STRING,
		rtMapMatchInt		OCTET STRING,
		rtMapMatchIpAddr	OCTET STRING,
		rtMapMatchIpNexthop	OCTET STRING,
		rtMapMatchIpRtSrc	OCTET STRING,
		rtMapMatchLenMin	INTEGER,
		rtMapMatchLenMax	INTEGER,
		rtMapMatchMetric	OCTET STRING,
		rtMapMatchRtType	INTEGER,
		rtMapMatchTag		OCTET STRING,
		rtMapMatchStatus	RowStatus,
		rtMapMatchComExact	INTEGER
			}

rtMapMatchRMName	OBJECT-TYPE
	SYNTAX	OCTET STRING
	MAX-ACCESS	read-only
	STATUS	current
	DESCRIPTION
		""
	::= { rtMapMatchEntry 1 }

rtMapMatchRMSeq	OBJECT-TYPE
	SYNTAX	INTEGER (1..65535)
	MAX-ACCESS	read-only
	STATUS	current
	DESCRIPTION
		""
	::= { rtMapMatchEntry 2 }

rtMapMatchAccess	OBJECT-TYPE
	SYNTAX	INTEGER {
				deny(1),
				permit(2)
					}
	MAX-ACCESS	read-create
	STATUS	current
	DESCRIPTION
		"route map的访问属性，默认为permit"
	::= { rtMapMatchEntry 3 }

rtMapMatchAsPath	OBJECT-TYPE
	SYNTAX	OCTET STRING
	MAX-ACCESS	read-create
	STATUS	current
	DESCRIPTION
		"1～199的数字字符串"
	::= { rtMapMatchEntry 4 }

rtMapMatchCom	OBJECT-TYPE
	SYNTAX	OCTET STRING
	MAX-ACCESS	read-create
	STATUS	current
	DESCRIPTION
		"1～199的数字字符串"
	::= { rtMapMatchEntry 5 }

rtMapMatchExtCom	OBJECT-TYPE
	SYNTAX	OCTET STRING
	MAX-ACCESS	read-create
	STATUS	current
	DESCRIPTION
		"1～99的数字字符串"
	::= { rtMapMatchEntry 6 }

rtMapMatchInt	OBJECT-TYPE
	SYNTAX	OCTET STRING
	MAX-ACCESS	read-create
	STATUS	current
	DESCRIPTION
		"接口名字符串s0、f0等等"
	::= { rtMapMatchEntry 7 }

rtMapMatchIpAddr	OBJECT-TYPE
	SYNTAX	OCTET STRING
	MAX-ACCESS	read-create
	STATUS	current
	DESCRIPTION
		"IP访问控制列表号或名字的字符串"
	::= { rtMapMatchEntry 8 }

rtMapMatchIpNexthop	OBJECT-TYPE
	SYNTAX	OCTET STRING
	MAX-ACCESS	read-create
	STATUS	current
	DESCRIPTION
		"IP标准访问控制列表号或名字的字符串"
	::= { rtMapMatchEntry 9 }

rtMapMatchIpRtSrc	OBJECT-TYPE
	SYNTAX	OCTET STRING
	MAX-ACCESS	read-create
	STATUS	current
	DESCRIPTION
		"IP标准访问控制列表号或名字的字符串"
	::= { rtMapMatchEntry 10 }

rtMapMatchLenMin	OBJECT-TYPE
	SYNTAX	INTEGER
	MAX-ACCESS	read-create
	STATUS	current
	DESCRIPTION
		"最小报文长度"
	::= { rtMapMatchEntry 11 }

rtMapMatchLenMax	OBJECT-TYPE
	SYNTAX	INTEGER
	MAX-ACCESS	read-create
	STATUS	current
	DESCRIPTION
		"最大报文长度"
	::= { rtMapMatchEntry 12 }

rtMapMatchMetric	OBJECT-TYPE
	SYNTAX	OCTET STRING
	MAX-ACCESS	read-create
	STATUS	current
	DESCRIPTION
		""
	::= { rtMapMatchEntry 13 }

rtMapMatchRtType	OBJECT-TYPE
	SYNTAX	INTEGER {
				extType1(1),
				extType2(2),
				internal(3),
				level1(4),
				level2(5),
				local(6),
				nssaExtType1(7),
				nssaExtType2(8)
					}
	MAX-ACCESS	read-create
	STATUS	current
	DESCRIPTION
		""
	::= { rtMapMatchEntry 14 }

rtMapMatchTag	OBJECT-TYPE
	SYNTAX	OCTET STRING
	MAX-ACCESS	read-create
	STATUS	current
	DESCRIPTION
		""
	::= { rtMapMatchEntry 15 }

rtMapMatchStatus	OBJECT-TYPE
	SYNTAX	RowStatus
	MAX-ACCESS	read-create
	STATUS	current
	DESCRIPTION
		"行状态"
	::= { rtMapMatchEntry 16 }

rtMapMatchComExact	OBJECT-TYPE
	SYNTAX	INTEGER {
				disable(1),
				enable(2)
					}
	MAX-ACCESS	read-create
	STATUS	current
	DESCRIPTION
		""
	::= { rtMapMatchEntry 17 }

-- *******************
-- set Configure

rtMapSetTable OBJECT-TYPE
    SYNTAX SEQUENCE OF RtMapSetEntry
    MAX-ACCESS not-accessible
    STATUS current
    DESCRIPTION
		"路由映射设置配置表"
    ::= { rtMapConf 2 }

rtMapSetEntry OBJECT-TYPE
    SYNTAX RtMapSetEntry
    MAX-ACCESS not-accessible
    STATUS current
    DESCRIPTION
		"路由映射设置配置表表项"
    INDEX { rtMapSetRMName, rtMapSetRMSeq }    
    ::= { rtMapSetTable 1 }

RtMapetEntry ::=
    SEQUENCE {
		rtMapSetRMName 				OCTET STRING,
		rtMapSetRMSeq 				INTEGER,
		rtMapSetAsPathPrepend		OCTET STRING,
		rtMapSetAsPathTag			INTEGER,
		rtMapSetAutoTag				INTEGER,
		rtMapSetCom		    		INTEGER,
		rtMapSetDampHalfLife		INTEGER,
		rtMapSetDampReuse			INTEGER,
		rtMapSetDampSuppress		INTEGER,
		rtMapSetDampMaxDura			INTEGER,
		rtMapSetDefaultInt			OCTET STRING,
		rtMapSetExtComRt			OCTET STRING,
		rtMapSetExtComSoo			OCTET STRING,
		rtMapSetInt					OCTET STRING,
		rtMapSetIpDefNextHop		OCTET STRING,
		rtMapSetIpDF				INTEGER,
		rtMapSetIpNextHop			OCTET STRING,
		rtMapSetIpNextHopAttr		INTEGER,
		rtMapSetIpPre				INTEGER,
		rtMapSetIpQosGrp			INTEGER,
		rtMapSetIpTos				INTEGER,
		rtMapSetLevel				INTEGER,
		rtMapSetLocalPre			INTEGER,
		rtMapSetMetricVal			INTEGER,
		rtMapSetMetricIgrpDelay		INTEGER,
		rtMapSetMetricIgrpRelia		INTEGER,
		rtMapSetMetricIgrpEffect	INTEGER,
		rtMapSetMetricIgrpMtu		INTEGER,
		rtMapSetMetricType			INTEGER,
		rtMapSetOrigin				INTEGER,
		rtMapSetOriEgpReAs			INTEGER,
		rtMapSetTag					INTEGER,
		rtMapSetWeight				INTEGER,
		rtMapSetStatus				RowStatus,
		rtMapSetComList				OCTET STRING,
		rtMapSetCommunity			OCTET STRING,
		rtMapSetAccess				INTEGER
			}

rtMapSetRMName	OBJECT-TYPE
	SYNTAX	OCTET STRING
	MAX-ACCESS	read-only
	STATUS	current
	DESCRIPTION
		""
	::= { rtMapSetEntry 1 }

rtMapSetRMSeq	OBJECT-TYPE
	SYNTAX	INTEGER (1..65535)
	MAX-ACCESS	read-only
	STATUS	current
	DESCRIPTION
		""
	::= { rtMapSetEntry 2 }

rtMapSetAsPathPrepend	OBJECT-TYPE
	SYNTAX	OCTET STRING
	MAX-ACCESS	read-create
	STATUS	current
	DESCRIPTION
		""
	::= { rtMapSetEntry 3 }

rtMapSetAsPathTag	OBJECT-TYPE
	SYNTAX	INTEGER {
				disable(1),
				enable(2)
					}
	MAX-ACCESS	read-create
	STATUS	current
	DESCRIPTION
		""
	::= { rtMapSetEntry 4 }

rtMapSetAutoTag	OBJECT-TYPE
	SYNTAX	INTEGER {
				disable(1),
				enable(2)
					}
	MAX-ACCESS	read-create
	STATUS	current
	DESCRIPTION
		""
	::= { rtMapSetEntry 5 }

rtMapSetCom	OBJECT-TYPE
	SYNTAX	INTEGER
	MAX-ACCESS	read-create
	STATUS	current
	DESCRIPTION
		"0x01:additive, 0x02:local-AS, 0x04: no-advertise, 0x08: no-export, 0x10:none"
	::= { rtMapSetEntry 6 }

rtMapSetDampHalfLife	OBJECT-TYPE
	SYNTAX	INTEGER (1..45)
	MAX-ACCESS	read-create
	STATUS	current
	DESCRIPTION
		""
	::= { rtMapSetEntry 7 }

rtMapSetDampReuse	OBJECT-TYPE
	SYNTAX	INTEGER (1..20000)
	MAX-ACCESS	read-create
	STATUS	current
	DESCRIPTION
		""
	::= { rtMapSetEntry 8 }

rtMapSetDampSuppress	OBJECT-TYPE
	SYNTAX	INTEGER (1..20000)
	MAX-ACCESS	read-create
	STATUS	current
	DESCRIPTION
		""
	::= { rtMapSetEntry 9 }

rtMapSetDampMaxDura	OBJECT-TYPE
	SYNTAX	INTEGER (1..255)
	MAX-ACCESS	read-create
	STATUS	current
	DESCRIPTION
		""
	::= { rtMapSetEntry 10 }

rtMapSetDefaultInt	OBJECT-TYPE
	SYNTAX	OCTET STRING
	MAX-ACCESS	read-create
	STATUS	current
	DESCRIPTION
		""
	::= { rtMapSetEntry 11 }

rtMapSetExtComRt	OBJECT-TYPE
	SYNTAX	OCTET STRING
	MAX-ACCESS	read-create
	STATUS	current
	DESCRIPTION
		""
	::= { rtMapSetEntry 12 }

rtMapSetExtComSoo	OBJECT-TYPE
	SYNTAX	OCTET STRING
	MAX-ACCESS	read-create
	STATUS	current
	DESCRIPTION
		""
	::= { rtMapSetEntry 13 }

rtMapSetInt	OBJECT-TYPE
	SYNTAX	OCTET STRING
	MAX-ACCESS	read-create
	STATUS	current
	DESCRIPTION
		""
	::= { rtMapSetEntry 14 }

rtMapSetIpDefNextHop	OBJECT-TYPE
	SYNTAX	OCTET STRING
	MAX-ACCESS	read-create
	STATUS	current
	DESCRIPTION
		""
	::= { rtMapSetEntry 15 }

rtMapSetIpDF	OBJECT-TYPE
	SYNTAX	INTEGER (1..2)
	MAX-ACCESS	read-create
	STATUS	current
	DESCRIPTION
		""
	::= { rtMapSetEntry 16 }

rtMapSetIpNextHop	OBJECT-TYPE
	SYNTAX	OCTET STRING
	MAX-ACCESS	read-create
	STATUS	current
	DESCRIPTION
		""
	::= { rtMapSetEntry 17 }

rtMapSetIpNextHopAttr	OBJECT-TYPE
	SYNTAX	INTEGER
	MAX-ACCESS	read-create
	STATUS	current
	DESCRIPTION
		"0x01：peer-address，0x02：verify-availability"
	::= { rtMapSetEntry 18 }

rtMapSetIpPre	OBJECT-TYPE
	SYNTAX	INTEGER {
				routine(1),
				priority(2),
				immediate(3),
				flash(4),
				flash-override(5),
				critical(6),
				internet(7),
				network(8)
					}
	MAX-ACCESS	read-create
	STATUS	current
	DESCRIPTION
		""
	::= { rtMapSetEntry 19 }

rtMapSetIpQosGrp	OBJECT-TYPE
	SYNTAX	INTEGER (1..100)
	MAX-ACCESS	read-create
	STATUS	current
	DESCRIPTION
		""
	::= { rtMapSetEntry 20 }

rtMapSetIpTos	OBJECT-TYPE
	SYNTAX	INTEGER {
				normal(1),
				min-monetary-cost(2),
				max-reliability(3),
				max-throughput(4),
				min-delay(5)
					}
	MAX-ACCESS	read-create
	STATUS	current
	DESCRIPTION
		""
	::= { rtMapSetEntry 21 }

rtMapSetLevel	OBJECT-TYPE
	SYNTAX	INTEGER {
				backbone(1),
				level-1(2),
				level-1-2(3),
				level-2(4),
				stub-area(5)
					}
	MAX-ACCESS	read-create
	STATUS	current
	DESCRIPTION
		""
	::= { rtMapSetEntry 22 }

rtMapSetLocalPre	OBJECT-TYPE
	SYNTAX	INTEGER
	MAX-ACCESS	read-create
	STATUS	current
	DESCRIPTION
		""
	::= { rtMapSetEntry 23 }

rtMapSetMetricVal	OBJECT-TYPE
	SYNTAX	INTEGER
	MAX-ACCESS	read-create
	STATUS	current
	DESCRIPTION
		""
	::= { rtMapSetEntry 24 }

rtMapSetMetricIgrpDelay	OBJECT-TYPE
	SYNTAX	INTEGER
	MAX-ACCESS	read-create
	STATUS	current
	DESCRIPTION
		""
	::= { rtMapSetEntry 25 }

rtMapSetMetricIgrpRelia	OBJECT-TYPE
	SYNTAX	INTEGER
	MAX-ACCESS	read-create
	STATUS	current
	DESCRIPTION
		""
	::= { rtMapSetEntry 26 }

rtMapSetMetricIgrpEffect	OBJECT-TYPE
	SYNTAX	INTEGER
	MAX-ACCESS	read-create
	STATUS	current
	DESCRIPTION
		""
	::= { rtMapSetEntry 27 }

rtMapSetMetricIgrpMtu	OBJECT-TYPE
	SYNTAX	INTEGER
	MAX-ACCESS	read-create
	STATUS	current
	DESCRIPTION
		""
	::= { rtMapSetEntry 28 }

rtMapSetMetricType	OBJECT-TYPE
	SYNTAX	INTEGER {
				external(1),
				internal(2),
				type-1(3),
				type-2(4)
					}
	MAX-ACCESS	read-create
	STATUS	current
	DESCRIPTION
		""
	::= { rtMapSetEntry 29 }

rtMapSetOrigin	OBJECT-TYPE
	SYNTAX	INTEGER {
				egp(1),
				igp(2),
				incomplete(3)
					}
	MAX-ACCESS	read-create
	STATUS	current
	DESCRIPTION
		""
	::= { rtMapSetEntry 30 }

rtMapSetOriEgpReAs	OBJECT-TYPE
	SYNTAX	INTEGER (1..65535)
	MAX-ACCESS	read-create
	STATUS	current
	DESCRIPTION
		""
	::= { rtMapSetEntry 31 }

rtMapSetTag	OBJECT-TYPE
	SYNTAX	INTEGER
	MAX-ACCESS	read-create
	STATUS	current
	DESCRIPTION
		""
	::= { rtMapSetEntry 32 }

rtMapSetWeight	OBJECT-TYPE
	SYNTAX	INTEGER
	MAX-ACCESS	read-create
	STATUS	current
	DESCRIPTION
		""
	::= { rtMapSetEntry 33 }

rtMapSetStatus	OBJECT-TYPE
	SYNTAX	RowStatus
	MAX-ACCESS	read-create
	STATUS	current
	DESCRIPTION
		"行状态"
	::= { rtMapSetEntry 34 }

rtMapSetComList	OBJECT-TYPE
	SYNTAX	OCTET STRING
	MAX-ACCESS	read-create
	STATUS	current
	DESCRIPTION
		""
	::= { rtMapSetEntry 35 }

rtMapSetCommunity	OBJECT-TYPE
	SYNTAX	OCTET STRING
	MAX-ACCESS	read-create
	STATUS	current
	DESCRIPTION
		""
	::= { rtMapSetEntry 36 }

rtMapSetAccess	OBJECT-TYPE
	SYNTAX	INTEGER {
				deny(1),
				permit(2)
					}
	MAX-ACCESS	read-create
	STATUS	current
	DESCRIPTION
		""
	::= { rtMapSetEntry 37 }


-- ****************************
-- set community-list Configure

--rtMapSetComListTable OBJECT-TYPE
--    SYNTAX SEQUENCE OF RtMapSetComListEntry
--    MAX-ACCESS not-accessible
--    STATUS current
--    DESCRIPTION
--		"路由映射设置共同体链表配置表"
--    ::= { rtMapConf 3 }

--rtMapSetComListEntry OBJECT-TYPE
--    SYNTAX RtMapSetComListEntry
--    MAX-ACCESS not-accessible
--    STATUS current
--    DESCRIPTION
--		"路由映射设置共同体链表配置表表项"
--    INDEX { rtMapSetComListRMName, rtMapSetComListRMSeq, rtMapSetComListNum }    
--    ::= { rtMapSetComListTable 1 }

--RtMapSetComListEntry ::=
--    SEQUENCE {
--		rtMapSetComListRMName 	OCTET STRING,
--		rtMapSetComListRMSeq 	INTEGER,
--		rtMapSetComListNum		INTEGER,
--		rtMapSetComListDel		INTEGER,
--		rtMapSetComListStatus	RowStatus
--			}

--rtMapSetComListRMName	OBJECT-TYPE
--	SYNTAX	OCTET STRING
--	MAX-ACCESS	read-only
--	STATUS	current
--	DESCRIPTION
--		""
--	::= { rtMapSetComListEntry 1 }

--rtMapSetComListRMSeq	OBJECT-TYPE
--	SYNTAX	INTEGER (1..65535)
--	MAX-ACCESS	read-only
--	STATUS	current
--	DESCRIPTION
--		""
--	::= { rtMapSetComListEntry 2 }

--rtMapSetComListNum	OBJECT-TYPE
--	SYNTAX	INTEGER (1..199)
--	MAX-ACCESS	read-only
--	STATUS	current
--	DESCRIPTION
--		""
--	::= { rtMapSetComListEntry 3 }

--rtMapSetComListDel	OBJECT-TYPE
--	SYNTAX	INTEGER {
--				disable(1),
--				enable(2)
--					}
--	MAX-ACCESS	read-create
--	STATUS	current
--	DESCRIPTION
--		""
--	::= { rtMapSetComListEntry 4 }

--rtMapSetComListStatus	OBJECT-TYPE
--	SYNTAX	RowStatus
--	MAX-ACCESS	read-create
--	STATUS	current
--	DESCRIPTION
--		"行状态"
--	::= { rtMapSetComListEntry 5 }

-- ****************************
-- set community Configure

--rtMapSetComTable OBJECT-TYPE
--    SYNTAX SEQUENCE OF RtMapSetComEntry
--    MAX-ACCESS not-accessible
--    STATUS current
--    DESCRIPTION
--		"路由映射设置共同体配置表"
--    ::= { rtMapConf 4 }

--rtMapSetComEntry OBJECT-TYPE
--    SYNTAX RtMapSetComEntry
--    MAX-ACCESS not-accessible
--    STATUS current
--    DESCRIPTION
--		"路由映射设置共同体配置表"
--    INDEX { rtMapSetComRMName, rtMapSetComRMSeq, rtMapSetComNum }    
--    ::= { rtMapSetComTable 1 }

--RtMapSetComEntry ::=
--    SEQUENCE {
--		rtMapSetComRMName 	OCTET STRING,
--		rtMapSetComRMSeq 	INTEGER,
--		rtMapSetComNum		INTEGER,
--		rtMapSetComStatus	RowStatus
--			}

--rtMapSetComRMName	OBJECT-TYPE
--	SYNTAX	OCTET STRING
--	MAX-ACCESS	read-only
--	STATUS	current
--	DESCRIPTION
--		""
--	::= { rtMapSetComEntry 1 }

--rtMapSetComRMSeq	OBJECT-TYPE
--	SYNTAX	INTEGER
--	MAX-ACCESS	read-only
--	STATUS	current
--	DESCRIPTION
--		""
--	::= { rtMapSetComEntry 2 }

--rtMapSetComNum	OBJECT-TYPE
--	SYNTAX	INTEGER
--	MAX-ACCESS	read-only
--	STATUS	current
--	DESCRIPTION
--		""
--	::= { rtMapSetComEntry 3 }

--rtMapSetComStatus	OBJECT-TYPE
--	SYNTAX	RowStatus
--	MAX-ACCESS	read-create
--	STATUS	current
--	DESCRIPTION
--		"行状态"
--	::= { rtMapSetComEntry 4 }

END

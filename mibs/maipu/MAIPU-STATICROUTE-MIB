MAIPU-STATICROUTE-MIB DEFINITIONS ::= BEGIN

IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt
        	FROM MAIPU-SMI
        ObjectName, ObjectSyntax, NetworkAddress
                FROM RFC1155-SMI;


routeMib            	OBJECT IDENTIFIER ::= { mpMgmt 81 }
	
staticRoute  OBJECT IDENTIFIER ::= {routeMib 7}

staticIfRouteTable  OBJECT-TYPE
    SYNTAX  SEQUENCE OF   StaticIfRouteEntry
    ACCESS  not-accessible
    STATUS  current
    DESCRIPTION
            "接口静态路由"
    ::= {staticRoute 1}

staticIfRouteEntry  OBJECT-TYPE
    SYNTAX  StaticIfRouteEntry
    ACCESS  not-accessible
    STATUS  current
    DESCRIPTION
            "接口静态路由"
    INDEX   {staticIfRouteVrfName, staticIfRouteDest, staticIfRouteMask, staticIfRouteIfName}
    ::= {staticIfRouteTable 1}

staticIfRouteVrfName  OBJECT-TYPE
    SYNTAX  DisplayString(SIZE(0..32))
    ACCESS  read-only
    STATUS  current
    DESCRIPTION
            "路由VRF名称"
    ::= {staticIfRouteEntry 1}

staticIfRouteDest  OBJECT-TYPE
    SYNTAX  IpAddress
    ACCESS  read-only
    STATUS  current
    DESCRIPTION
            "路由目的网络"
    ::= {staticIfRouteEntry 2}

staticIfRouteMask  OBJECT-TYPE
    SYNTAX  IpAddress
    ACCESS  read-only
    STATUS  current
    DESCRIPTION
            "路由目的网络掩码"
    ::= {staticIfRouteEntry 3}

staticIfRouteIfName  OBJECT-TYPE
    SYNTAX  DisplayString(SIZE(0..40))
    ACCESS  read-only
    STATUS  current
    DESCRIPTION
            "路由出接口名"
    ::= {staticIfRouteEntry 4}

staticIfRouteDistance  OBJECT-TYPE
    SYNTAX  INTEGER(0..255)
    ACCESS  read-only
    STATUS  current
    DESCRIPTION
            "路由管理距离"
    ::= {staticIfRouteEntry 5}

staticIfRouteRowStatus  OBJECT-TYPE
    SYNTAX  RowStatus
    ACCESS  read-only
    STATUS  current
    DESCRIPTION
            ""
    ::= {staticIfRouteEntry 6}

staticGwRouteTable  OBJECT-TYPE
    SYNTAX  SEQUENCE OF   StaticGwRouteEntry
    ACCESS  not-accessible
    STATUS  current
    DESCRIPTION
            "网关静态路由"
    ::= {staticRoute 2}

staticGwRouteEntry  OBJECT-TYPE
    SYNTAX  StaticGwRouteEntry
    ACCESS  not-accessible
    STATUS  current
    DESCRIPTION
            "网关静态路由"
    INDEX   {staticGwRouteVrfName, staticGwRouteDest, staticGwRouteMask, staticGwRouteGw, staticGwRouteGwVrfName}
    ::= {staticGwRouteTable 1}

staticGwRouteVrfName  OBJECT-TYPE
    SYNTAX  DisplayString(SIZE(0..32))
    ACCESS  read-only
    STATUS  current
    DESCRIPTION
            "路由VRF名称"
    ::= {staticGwRouteEntry 1}

staticGwRouteDest  OBJECT-TYPE
    SYNTAX  IpAddress
    ACCESS  read-only
    STATUS  current
    DESCRIPTION
            "路由目的网络"
    ::= {staticGwRouteEntry 2}

staticGwRouteMask  OBJECT-TYPE
    SYNTAX  IpAddress
    ACCESS  read-only
    STATUS  current
    DESCRIPTION
            "路由目的网络掩码"
    ::= {staticGwRouteEntry 3}

staticGwRouteGw  OBJECT-TYPE
    SYNTAX  IpAddress
    ACCESS  read-only
    STATUS  current
    DESCRIPTION
            "路由网关地址"
    ::= {staticGwRouteEntry 4}

staticGwRouteGwVrfName  OBJECT-TYPE
    SYNTAX  DisplayString(SIZE(0..32))
    ACCESS  read-only
    STATUS  current
    DESCRIPTION
            "网关VRF名称"
    ::= {staticGwRouteEntry 5}

staticGwRouteDistance  OBJECT-TYPE
    SYNTAX  INTEGER(0..255)
    ACCESS  read-only
    STATUS  current
    DESCRIPTION
            "路由管理距离"
    ::= {staticGwRouteEntry 6}

staticGwRouteRowStatus  OBJECT-TYPE
    SYNTAX  RowStatus
    ACCESS  read-only
    STATUS  current
    DESCRIPTION
            ""
    ::= {staticGwRouteEntry 7}
END

-- *****************************************************************
-- MP2600-TUNNEL.my:  Maipu enterprise TUNNEL MIB file
--
-- Dec 12, 2000 Huang lulu
-- Sep 05, 2002 Huang lulu
--
-- Copyright (c)  by Maipu DataComm Inc.
-- All rights reserved.
-- 
-- *****************************************************************
--
   
   MAIPU-TUNNEL-MIB DEFINITIONS ::= BEGIN

   IMPORTS
       MODULE-IDENTITY, OBJECT-TYPE, Counter32,
       IpAddress, Unsigned32		FROM SNMPv2-SMI
       RowStatus					FROM SNMPv2-TC
       mpMgmt						FROM MAIPU-SMI;


   mpTunnelMib  MODULE-IDENTITY
           LAST-UPDATED "0012122030Z"      -- Fri Dec 12 20:30:04 PDT 2000
           ORGANIZATION "Maipu DataComm"
           CONTACT-INFO
          "       Huang lulu
          Postal: Maipu Inc
                  Tel: (028)5161006
          E-Mail: office@maipu.com "

        DESCRIPTION
	 "The MIB module to describe the TUNNEL Protocol for Maipu Router"
     ::= { mpMgmt 37 }

   -- TUNNEL Managemeng Information Base
   
    tunnelConf OBJECT IDENTIFIER ::= { mpTunnelMib 1 }
    tunnelStatistic OBJECT IDENTIFIER ::= { mpTunnelMib 2 }

   -- ***********************************
   -- mpTunnelMib interface configuration
   -- ***********************************
      	
    tunnelIfConfTable OBJECT-TYPE
    	SYNTAX	SEQUENCE OF TunnelIfConfEntry
    	MAX-ACCESS   not-accessible
    	STATUS	current
    	DESCRIPTION
    	    "The valid RIP Networks."
    	::= { tunnelConf 1 }

    tunnelIfConfEntry OBJECT-TYPE
    	SYNTAX	TunnelIfConfEntry
    	MAX-ACCESS  not-accessible
    	STATUS	current
    	DESCRIPTION
    	    "Single Network in the Rip Global Configuration."
    	INDEX { tunnelIfIndex }
    	::= { tunnelIfConfTable 1 }
    	
    TunnelIfConfEntry ::=
    	SEQUENCE { 
    		tunnelIfIndex	INTEGER,
    		tunnelIfIpAddr	IpAddress,
    		tunnelSrcAddr	IpAddress,
    		tunnelDestAddr	IpAddress,
    		tunnelSeqData	INTEGER,
    		tunnelKey		Unsigned32,
    		tunnelChecksum	INTEGER,
    		tunnelState		INTEGER
	    		}
    		
    tunnelIfIndex OBJECT-TYPE
    	SYNTAX	INTEGER
    	MAX-ACCESS  read-only
    	STATUS	current
    	DESCRIPTION
    	    "接口索引，与接口表的ifIndex一致." 
    	::= { tunnelIfConfEntry 1 }
    	
    tunnelIfIpAddr OBJECT-TYPE
    	SYNTAX	IpAddress
    	MAX-ACCESS  read-write
    	STATUS	current
    	DESCRIPTION
    	    "接口地址." 
    	::= { tunnelIfConfEntry 2 }
    	
    tunnelSrcAddr OBJECT-TYPE
    	SYNTAX	IpAddress
    	MAX-ACCESS  read-write
    	STATUS	current
    	DESCRIPTION
    	    "源引用地址." 
    	::= { tunnelIfConfEntry 3 }
    	
    tunnelDestAddr OBJECT-TYPE
    	SYNTAX	IpAddress
    	MAX-ACCESS  read-write
    	STATUS	current
    	DESCRIPTION
    	    "目的应用地址." 
    	::= { tunnelIfConfEntry 4 }
    	
    tunnelSeqData OBJECT-TYPE
    	SYNTAX	INTEGER {
    				disable(1),
    				enable(2)
    					}
    	MAX-ACCESS  read-write
    	STATUS	current
    	DESCRIPTION
    	    "是否记录顺序号." 
    	::= { tunnelIfConfEntry 5 }
    	
    tunnelKey OBJECT-TYPE
    	SYNTAX	INTEGER (0..2147483647)
    	MAX-ACCESS  read-write
    	STATUS	current
    	DESCRIPTION
    	    "键值." 
    	::= { tunnelIfConfEntry 6 }
    	
    tunnelChecksum OBJECT-TYPE
    	SYNTAX	INTEGER {
    				disable(1),
    				enable(2)
    					}
    	MAX-ACCESS  read-write
    	STATUS	current
    	DESCRIPTION
    	    "是否检验校验和." 
    	::= { tunnelIfConfEntry 7 }
    	
    tunnelState OBJECT-TYPE
    	SYNTAX	INTEGER {
    				up(1),
    				down(2)
    					}
    	MAX-ACCESS  read-write
    	STATUS	current
    	DESCRIPTION
    	    "UP/DOWN." 
    	::= { tunnelIfConfEntry 8 }
    	
   -- ************************
   -- mpTunnelMib Statistics
   -- ************************
      	
    tunnelTooshort OBJECT-TYPE
    	SYNTAX	Counter32
    	MAX-ACCESS  read-only
    	STATUS	current
    	DESCRIPTION
    	    "长度错误包统计." 
    	::= { tunnelStatistic 1 }
    	
    tunnelBadhead OBJECT-TYPE
    	SYNTAX	Counter32
    	MAX-ACCESS  read-only
    	STATUS	current
    	DESCRIPTION
    	    "头部错误包统计." 
    	::= { tunnelStatistic 2 }
    	
    tunnelBadsum OBJECT-TYPE
    	SYNTAX	Counter32
    	MAX-ACCESS  read-only
    	STATUS	current
    	DESCRIPTION
    	    "校验和错误包统计." 
    	::= { tunnelStatistic 3 }
    	
    tunnelHashmiss OBJECT-TYPE
    	SYNTAX	Counter32
    	MAX-ACCESS  read-only
    	STATUS	current
    	DESCRIPTION
    	    "哈希值错误包统计." 
    	::= { tunnelStatistic 4 }
    	
    tunnelBadbcast OBJECT-TYPE
    	SYNTAX	Counter32
    	MAX-ACCESS  read-only
    	STATUS	current
    	DESCRIPTION
    	    "错误广播包统计." 
    	::= { tunnelStatistic 5 }
    	
    tunnelBadkey OBJECT-TYPE
    	SYNTAX	Counter32
    	MAX-ACCESS  read-only
    	STATUS	current
    	DESCRIPTION
    	    "key值错误包统计." 
    	::= { tunnelStatistic 6 }
    	
    tunnelBadproto OBJECT-TYPE
    	SYNTAX	Counter32
    	MAX-ACCESS  read-only
    	STATUS	current
    	DESCRIPTION
    	    "协议错误包统计." 
    	::= { tunnelStatistic 7 }

END

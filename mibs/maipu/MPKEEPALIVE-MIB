------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPKEEPALIVE-MIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt
        	FROM MAIPU-SMI
        ObjectName, ObjectSyntax, NetworkAddress
                FROM RFC1155-SMI;



mpKeepaliveMib      	MODULE-IDENTITY
                    		LAST-UPDATED 	"0704060952Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			""
                    		::= { mpMgmt  800 }



mpKeepaliveTable    	OBJECT-TYPE
                    		SYNTAX  SEQUENCE OF   MpKeepaliveEntry
                    		MAX-ACCESS  not-accessible
                    		STATUS  current
                    		DESCRIPTION
                    			""
                    		::= { mpKeepaliveMib 1 }

mpKeepaliveEntry    	OBJECT-TYPE
                    		SYNTAX  MpKeepaliveEntry
                    		MAX-ACCESS  not-accessible
                    		STATUS  current
                    		DESCRIPTION
                    			""
                    		INDEX  { mpIfNmae }
                    		::= { mpKeepaliveTable 1 }

MpKeepaliveEntry    	::= SEQUENCE {
                    			mpKaIfNmae             DisplayString,
                    			mpKaTimeout            INTEGER,
                    			mpKaRetry              INTEGER,
                    			mpKaGateway            IpAddress,
                    			mpKaRowstatus          RowStatus
                    	             }


mpKaIfNmae          	OBJECT-TYPE
                    		SYNTAX  DisplayString
                    		MAX-ACCESS  accessible-for-notify
                    		STATUS  current
                    		DESCRIPTION
                    			"索引
                    			 keepalive配置的接口名字"
                    		::= { mpKeepaliveEntry 1 }

mpKaTimeout         	OBJECT-TYPE
                    		SYNTAX  INTEGER(0..32767)
                    		MAX-ACCESS  read-write
                    		STATUS  current
                    		DESCRIPTION
                    			"keepalive保活帧间隔时间，默认值10秒"
                    		::= { mpKeepaliveEntry 2 }

mpKaRetry           	OBJECT-TYPE
                    		SYNTAX  INTEGER(1..255)
                    		MAX-ACCESS  read-write
                    		STATUS  current
                    		DESCRIPTION
                    			"keepalive保活重试次数,默认3次
                    			 广播网络无效"
                    		::= { mpKeepaliveEntry 3 }

mpKaGateway         	OBJECT-TYPE
                    		SYNTAX  IpAddress
                    		MAX-ACCESS  read-write
                    		STATUS  current
                    		DESCRIPTION
                    			"keepalive对端网关地址
                    			 点对点网络无效"
                    		::= { mpKeepaliveEntry 4 }

mpKaRowstatus       	OBJECT-TYPE
                    		SYNTAX  RowStatus
                    		MAX-ACCESS  read-create
                    		STATUS  current
                    		DESCRIPTION
                    			""
                    		::= { mpKeepaliveEntry 5 }



END
------------------------------------------------------------------------------
-- ============================================================================
-- $Log: mpKeepaliveMib.mib,v $
-- Revision 1.1  2010/06/21 11:18:46  liyh
-- first commit
--
--
--
-- ============================================================================

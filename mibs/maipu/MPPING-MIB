------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPPING-MIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt
        	FROM MAIPU-SMI
        ObjectName, ObjectSyntax, NetworkAddress
                FROM RFC1155-SMI;



mpPingMib           	MODULE-IDENTITY
                    		LAST-UPDATED 	"0412270856Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			""
                    		::= { mpMgmt  113 }




------------------------------------------------------------------------------
mpPingMIBObjects    	OBJECT IDENTIFIER ::= { mpPingMib 1 }

mpPingTable         	OBJECT-TYPE
                    		SYNTAX  SEQUENCE OF  MpPingEntry
                    		MAX-ACCESS  not-accessible
                    		STATUS  current
                    		DESCRIPTION
                    			"A table of ping request entries. When management station want to ping e host, it will get a unique serial number by get mpPinggGenSerialNum object, and create a new entry of this table. Ping will be started after mpPingRowStatus object is set to active. Management station can delete a entry by set mpPingRowStatus object to destroy. In order to prevent old entries from clogging the table, entries will be aged out. But an entry will never be deleted within fcTraceRouteAgeInterval milliseconds of completing."
                    		::= { mpPingMIBObjects 2 }

mpPingEntry         	OBJECT-TYPE
                    		SYNTAX  MpPingEntry
                    		MAX-ACCESS  not-accessible
                    		STATUS  current
                    		DESCRIPTION
                    			"A table of ping request entries. When management station want to ping e host, it will get a unique serial number by get mpPinggGenSerialNum object, and create a new entry of this table. Ping will be started after mpPingRowStatus object is set to active. Management station can delete a entry by set mpPingRowStatus object to destroy. In order to prevent old entries from clogging the table, entries will be aged out. But an entry will never be deleted within fcTraceRouteAgeInterval milliseconds of completing."
                    		INDEX  { mpPingSerialNum }
                    		::= { mpPingTable 1 }

MpPingEntry         	::= SEQUENCE {
                    			mpPingSerialNum        Integer32,
                    			mpPingIpAddress        IpAddress,
                    			mpPingVrfName          MVrfName,
                    			mpPingPacketCount      Integer32,
                    			mpPingPacketSize       Integer32,
                    			mpPingPacketTimeout    Integer32,
                    			mpPingDelay            Integer32,
                    			mpPingSentPackets      Counter32,
                    			mpPingReceivedPackets   Counter32,
                    			mpPingMinRtt           Integer32,
                    			mpPingAvgRtt           Integer32,
                    			mpPingMaxRtt           Integer32,
                    			mpPingCompleted        TruthValue,
                    			mpPingEntryOwner       DisplayString,
                    			mpPingRowStatus        RowStatus
                    	             }


mpPingSerialNum     	OBJECT-TYPE
                    		SYNTAX  Integer32(1..2147483647)
                    		MAX-ACCESS  not-accessible
                    		STATUS  current
                    		DESCRIPTION
                    			"全局唯一值，工作站在新建行时首先产生一个伪随机数，然后用此数为索引建立行，若此索引的行已存在则返回错误。"
                    		::= { mpPingEntry 1 }

mpPingIpAddress     	OBJECT-TYPE
                    		SYNTAX  IpAddress
                    		MAX-ACCESS  read-create
                    		STATUS  current
                    		DESCRIPTION
                    			"The address of the device to be pinged. An instance of this object cannot be created until the associated instance of ciscoPingProtocol is created."
                    		::= { mpPingEntry 2 }

mpPingVrfName       	OBJECT-TYPE
                    		SYNTAX  DisplayString(SIZE(0..40))
                    		MAX-ACCESS  read-create
                    		STATUS  current
                    		DESCRIPTION
                    			"This field is used to specify the VPN name in which the ping will be used. For regular ping this field should not be configured. The agent will use this field to identify the VPN routing Table for this ping. This is the same ascii string used in the CLI to refer to this VPN."
                    		::= { mpPingEntry 3 }

mpPingPacketCount   	OBJECT-TYPE
                    		SYNTAX  Integer32(1..2147483647)
                    		MAX-ACCESS  read-create
                    		STATUS  current
                    		DESCRIPTION
                    			"Specifies the number of ping packets to send to the target in this sequence."
                    		::= { mpPingEntry 4 }

mpPingPacketSize    	OBJECT-TYPE
                    		SYNTAX  Integer32
                    		MAX-ACCESS  read-create
                    		STATUS  current
                    		DESCRIPTION
                    			"Specifies the size of ping packets to send to the target in this sequence.  The lower and upper boundaries of this object are protocol-dependent. An instance of this object cannot be modified unless the associated instance of ciscoPingProtocol has been created (so as to allow protocol-specific range checking on the new value)."
                    		::= { mpPingEntry 5 }

mpPingPacketTimeout 	OBJECT-TYPE
                    		SYNTAX  Integer32(0..3600000)
                    		MAX-ACCESS  read-create
                    		STATUS  current
                    		DESCRIPTION
                    			"Specifies the amount of time to wait for a response to a transmitted packet before declaring the packet 'dropped.'"
                    		::= { mpPingEntry 6 }

mpPingDelay         	OBJECT-TYPE
                    		SYNTAX  Integer32(0..3600000)
                    		MAX-ACCESS  read-create
                    		STATUS  current
                    		DESCRIPTION
                    			"Specifies the minimum amount of time to wait before sending the next packet in a sequence after receiving a response or declaring a timeout for a previous packet.  The actual delay may be greater due to internal task scheduling."
                    		::= { mpPingEntry 7 }

mpPingSentPackets   	OBJECT-TYPE
                    		SYNTAX  Counter32
                    		MAX-ACCESS  read-only
                    		STATUS  current
                    		DESCRIPTION
                    			"The number of ping packets that have been sent to the target in this sequence."
                    		::= { mpPingEntry 8 }

mpPingReceivedPackets	OBJECT-TYPE
                    		SYNTAX  Counter32
                    		MAX-ACCESS  read-only
                    		STATUS  current
                    		DESCRIPTION
                    			"The number of ping packets that have been received from the target in this sequence."
                    		::= { mpPingEntry 9 }

mpPingMinRtt        	OBJECT-TYPE
                    		SYNTAX  Integer32
                    		MAX-ACCESS  read-only
                    		STATUS  current
                    		DESCRIPTION
                    			"The minimum round trip time of all the packets that have been sent in this sequence. This object will not be created until the first ping response in a sequence is received."
                    		::= { mpPingEntry 10 }

mpPingAvgRtt        	OBJECT-TYPE
                    		SYNTAX  Integer32
                    		MAX-ACCESS  read-only
                    		STATUS  current
                    		DESCRIPTION
                    			"The average round trip time of all the packets that have been sent in this sequence. This object will not be created until the first ping response in a sequence is received."
                    		::= { mpPingEntry 11 }

mpPingMaxRtt        	OBJECT-TYPE
                    		SYNTAX  Integer32
                    		MAX-ACCESS  read-only
                    		STATUS  current
                    		DESCRIPTION
                    			"The maximum round trip time of all the packets that have been sent in this sequence. This object will not be created until the first ping response in a sequence is received."
                    		::= { mpPingEntry 12 }

mpPingCompleted     	OBJECT-TYPE
                    		SYNTAX  integer32
                    		MAX-ACCESS  read-only
                    		STATUS  current
                    		DESCRIPTION
                    			"Set to true when all the packets in this sequence have been either responded to or timed out."
                    		::= { mpPingEntry 13 }

mpPingEntryOwner    	OBJECT-TYPE
                    		SYNTAX  DisplayString(SIZE(0..64))
                    		MAX-ACCESS  read-create
                    		STATUS  current
                    		DESCRIPTION
                    			"The entity that configured this entry."
                    		::= { mpPingEntry 19 }

mpPingRowStatus     	OBJECT-TYPE
                    		SYNTAX  RowStatus
                    		MAX-ACCESS  read-create
                    		STATUS  current
                    		DESCRIPTION
                    			"The status of this table entry.  Once the entry status is set to active, the associate entry cannot be modified until the sequence completes (ciscoPingCompleted is true)."
                    		::= { mpPingEntry 20 }



END
------------------------------------------------------------------------------
-- ============================================================================
-- $Log: mpPingMib.mib,v $
-- Revision 1.1  2010/06/21 11:18:46  liyh
-- first commit
--
-- Revision 1.1.2.1  2005/03/21 07:49:44  yeke
-- VRSP-6237:add mib ping add mib traceroute
--
--
--
-- ============================================================================

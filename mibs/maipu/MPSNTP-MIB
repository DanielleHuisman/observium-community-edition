-- *****************************************************************
-- MP2600-SNTP.my:  Maipu enterprise SNTP MIB file
--
-- Sep 23, 2002 Huang lulu
--
-- Copyright (c)  by Maipu DataComm Inc.
-- All rights reserved.
-- 
-- *****************************************************************
--
   
   MPSNTP-MIB DEFINITIONS ::= BEGIN

   IMPORTS
       MODULE-IDENTITY, OBJECT-TYPE, Counter32,
       IpAddress, Unsigned32		FROM SNMPv2-SMI
       RowStatus					FROM SNMPv2-TC
       mpMgmt						FROM MAIPU-SMI;


   mpSntpMib  MODULE-IDENTITY
           LAST-UPDATED "0012122030Z"      -- Fri Dec 12 20:30:04 PDT 2000
           ORGANIZATION "Maipu DataComm"
           CONTACT-INFO
          "       Huang lulu
          Postal: Maipu Inc
                  Tel: (028)5161006
          E-Mail: office@maipu.com "

        DESCRIPTION
	 "The MIB module to describe the Sntp Protocol for Maipu Router"
     ::= { mpMgmt 28 }

   -- Sntp Managemeng Information Base
   
   -- **********************
   -- SMI
   -- **********************
   
    sntpGlobal OBJECT IDENTIFIER ::= { mpSntpMib 1 }

   -- ***********
   
	sntpBroadcast	OBJECT-TYPE
    	SYNTAX	INTEGER {
    				disable(1),
    				enable(2)
    					}
    	MAX-ACCESS   read-write
    	STATUS	current
    	DESCRIPTION
    	    "."
    	::= { sntpGlobal 1 }

	sntpInterval	OBJECT-TYPE
    	SYNTAX	INTEGER (60..3600)
    	MAX-ACCESS   read-write
    	STATUS	current
    	DESCRIPTION
    	    "."
    	::= { sntpGlobal 2 }

	sntpSvrName	OBJECT-TYPE
    	SYNTAX	OCTET STRING
    	MAX-ACCESS   read-write
    	STATUS	current
    	DESCRIPTION
    	    "."
    	::= { sntpGlobal 3 }

	sntpTimeout	OBJECT-TYPE
    	SYNTAX	INTEGER (300..600)
    	MAX-ACCESS   read-write
    	STATUS	current
    	DESCRIPTION
    	    "."
    	::= { sntpGlobal 4 }

	sntpLeapVerMode	OBJECT-TYPE
    	SYNTAX	INTEGER
    	MAX-ACCESS   read-only
    	STATUS	current
    	DESCRIPTION
    	    "."
    	::= { sntpGlobal 5 }

	sntpStratum	OBJECT-TYPE
    	SYNTAX	INTEGER
    	MAX-ACCESS   read-only
    	STATUS	current
    	DESCRIPTION
    	    "."
    	::= { sntpGlobal 6 }

	sntpPoll	OBJECT-TYPE
    	SYNTAX	INTEGER
    	MAX-ACCESS   read-only
    	STATUS	current
    	DESCRIPTION
    	    "."
    	::= { sntpGlobal 7 }

	sntpPrecision	OBJECT-TYPE
    	SYNTAX	INTEGER
    	MAX-ACCESS   read-only
    	STATUS	current
    	DESCRIPTION
    	    "."
    	::= { sntpGlobal 8 }

	sntpRootDelay	OBJECT-TYPE
    	SYNTAX	INTEGER
    	MAX-ACCESS   read-only
    	STATUS	current
    	DESCRIPTION
    	    "."
    	::= { sntpGlobal 9 }

	sntpRootDispersion	OBJECT-TYPE
    	SYNTAX	INTEGER
    	MAX-ACCESS   read-only
    	STATUS	current
    	DESCRIPTION
    	    "."
    	::= { sntpGlobal 10 }

	sntpReferenceIdentifier	OBJECT-TYPE
    	SYNTAX	INTEGER
    	MAX-ACCESS   read-only
    	STATUS	current
    	DESCRIPTION
    	    "."
    	::= { sntpGlobal 11 }

	sntpReferencetimestampsec	OBJECT-TYPE
    	SYNTAX	INTEGER
    	MAX-ACCESS   read-only
    	STATUS	current
    	DESCRIPTION
    	    "."
    	::= { sntpGlobal 12 }

	sntpOriginateTimestampSec	OBJECT-TYPE
    	SYNTAX	INTEGER
    	MAX-ACCESS   read-only
    	STATUS	current
    	DESCRIPTION
    	    "."
    	::= { sntpGlobal 13 }

	sntpReveiveTimestampSec	OBJECT-TYPE
    	SYNTAX	INTEGER
    	MAX-ACCESS   read-only
    	STATUS	current
    	DESCRIPTION
    	    "."
    	::= { sntpGlobal 14 }

	sntpTransmitTimestampSec	OBJECT-TYPE
    	SYNTAX	INTEGER
    	MAX-ACCESS   read-only
    	STATUS	current
    	DESCRIPTION
    	    "."
    	::= { sntpGlobal 15 }

	sntpSysTimeStatus	OBJECT-TYPE
    	SYNTAX	OCTET STRING (SIZE(1..8))
    	MAX-ACCESS   read-only
    	STATUS	current
    	DESCRIPTION
    	    "."
    	::= { sntpGlobal 16 }

	sntpUpdataSysTime	OBJECT-TYPE
    	SYNTAX	OCTET STRING
    	MAX-ACCESS   read-only
    	STATUS	current
    	DESCRIPTION
    	    "."
    	::= { sntpGlobal 17 }

	sntpToNowSec	OBJECT-TYPE
    	SYNTAX	INTEGER
    	MAX-ACCESS   read-only
    	STATUS	current
    	DESCRIPTION
    	    "."
    	::= { sntpGlobal 18 }

	sntpRoundtripTime	OBJECT-TYPE
    	SYNTAX	INTEGER
    	MAX-ACCESS   read-only
    	STATUS	current
    	DESCRIPTION
    	    "."
    	::= { sntpGlobal 19 }

END

QLGC-GLOBAL-CAPABILITY DEFINITIONS ::= BEGIN

IMPORTS
        MODULE-IDENTITY
                FROM SNMPv2-SMI
        AGENT-CAPABILITIES
                FROM SNMPv2-CONF
       DisplayString
                FROM SNMPv2-TC
        qlogicAgentCapability
                FROM QLOGIC-SMI
;

qlgcSANBox2Capability MODULE-IDENTITY
        LAST-UPDATED "200909290000Z" -- September 29, 2009
        ORGANIZATION "QLOGIC Corporation"
        CONTACT-INFO "QLOGIC Technical Support
              Postal: QLogic Corporation
                      4601 Dean Lakes Blvd
                      Shakopee, MN 55379
                      US
                 Tel: +1 952 932 4040
                 Fax: +1 952 932 4018
              E-mail: support@QLogic.com"
         DESCRIPTION
            "The capabilities statement for the QLogic
            enterprise switch modules."

         REVISION "200909290000Z" -- September 29, 2009
         DESCRIPTION
            "The syntax and semantics errors reported by the
             smilint program were resolved."

         REVISION "200805070000Z" -- May 7, 2008
         DESCRIPTION
            "Make some objects included with release 7.4
             read-only, and general cleanup."

	 REVISION "200702270000Z" -- February 27, 2007
         DESCRIPTION 
            "Clean up FE-MIB objects to reflect the capabilities 
	        that are currently being supported."

	 REVISION "200702150000Z" -- February 15, 2007
         DESCRIPTION 
            "Modify name to reflect specific agent capabilities, even
	        if they are in a sense generic."

	 REVISION "0307252359Z" -- July 25, 2003
         DESCRIPTION 
            "Initial version of this MIB module."

::= { qlogicAgentCapability 1 }

sanbox2Agent AGENT-CAPABILITIES

  PRODUCT-RELEASE       "SANBox-2 agent release 2.1"
   STATUS               current
   DESCRIPTION          "QLogic release for SANBox-2"

--
-- MIB-2
--
  SUPPORTS              IF-MIB
      INCLUDES { interfaces }
      VARIATION         ifAdminStatus
         ACCESS         read-only
         DESCRIPTION    "Supported readonly"

      VARIATION         ifPromiscuousMode
         ACCESS         read-only
         DESCRIPTION    "Supported readonly"

   SUPPORTS             RFC1213-MIB
      INCLUDES { at }
      VARIATION         atPhysAddress
         ACCESS         read-only
         DESCRIPTION    "Not allowed through SNMP"

   SUPPORTS             RFC1213-MIB
      INCLUDES { ip }
      VARIATION         ipRouteIfIndex
         ACCESS         read-only
         DESCRIPTION    "Not allowed through SNMP"

      VARIATION         ipRouteMetric1
         ACCESS         read-only
         DESCRIPTION    "Not allowed through SNMP"

      VARIATION         ipRouteMetric2
         ACCESS         read-only
         DESCRIPTION    "Not allowed through SNMP"

      VARIATION         ipRouteMetric3
         ACCESS         read-only
         DESCRIPTION    "Not allowed through SNMP"

      VARIATION         ipRouteMetric4
         ACCESS         read-only
         DESCRIPTION    "Not allowed through SNMP"

      VARIATION         ipRouteNextHop
         ACCESS         read-only
         DESCRIPTION    "Not allowed through SNMP"

      VARIATION         ipRouteType
         ACCESS         read-only
         DESCRIPTION    "Not allowed through SNMP"

      VARIATION         ipRouteAge
         ACCESS         read-only
         DESCRIPTION    "Not allowed through SNMP"

      VARIATION         ipRouteMask
         ACCESS         read-only
         DESCRIPTION    "Not allowed through SNMP"

      VARIATION         ipRouteMetric5
         ACCESS         read-only
         DESCRIPTION    "Not allowed through SNMP"

   SUPPORTS             IP-MIB
      INCLUDES { ip }
      VARIATION         ipForwarding
         ACCESS         read-only
         DESCRIPTION    "Not allowed through SNMP"

      VARIATION         ipDefaultTTL
         ACCESS         read-only
         DESCRIPTION    "Not allowed through SNMP"

      VARIATION         ipNetToMediaPhysAddress
         ACCESS         read-only
         DESCRIPTION    "Not allowed through SNMP"

      VARIATION         ipNetToMediaType
         ACCESS         read-only
         DESCRIPTION    "Not allowed through SNMP"

      VARIATION         ipAddressIfIndex
         ACCESS         read-only
         DESCRIPTION    "Not allowed through SNMP"

      VARIATION         ipAddressType
         ACCESS         read-only
         DESCRIPTION    "Not allowed through SNMP"

      VARIATION         ipAddressStatus
         ACCESS         read-only
         DESCRIPTION    "Not allowed through SNMP"

      VARIATION         ipAddressRowStatus
         ACCESS         read-only
         DESCRIPTION    "Not allowed through SNMP"

      VARIATION         ipAddressStorageType
         ACCESS         read-only
         DESCRIPTION    "Not allowed through SNMP"

      VARIATION         ipNetToPhysicalPhysAddress
         ACCESS         read-only
         DESCRIPTION    "Not allowed through SNMP"

      VARIATION         ipNetToPhysicalType
         ACCESS         read-only
         DESCRIPTION    "Not allowed through SNMP"

      VARIATION         ipNetToPhysicalRowStatus
         ACCESS         read-only
         DESCRIPTION    "Not allowed through SNMP"

      VARIATION         ipv6IpForwarding
         ACCESS         read-only
         DESCRIPTION    "Not allowed through SNMP"

      VARIATION         ipv6IpDefaultHopLimit
         ACCESS         read-only
         DESCRIPTION    "Not allowed through SNMP"

   SUPPORTS             IPV6-MIB
      INCLUDES { ip }
      VARIATION         ipv6IfAdminStatus
         ACCESS         read-only
         DESCRIPTION    "Not allowed through SNMP"

      VARIATION         ipv6Forwarding
         ACCESS         read-only
         DESCRIPTION    "Not allowed through SNMP"

      VARIATION         ipv6DefaultHopLimit
         ACCESS         read-only
         DESCRIPTION    "Not allowed through SNMP"

      VARIATION         ipv6IfDescr
         ACCESS         read-only
         DESCRIPTION    "Not allowed through SNMP"

      VARIATION         ipv6IfAdminStatus
         ACCESS         read-only
         DESCRIPTION    "Not allowed through SNMP"

---
--- IP-FORWARD-MIB
---
   SUPPORTS             IP-FORWARD-MIB
      INCLUDES { ip }
      VARIATION         ipCidrRouteIfIndex
         ACCESS         read-only
         DESCRIPTION    "Not allowed through SNMP"

      VARIATION         ipCidrRouteType
         ACCESS         read-only
         DESCRIPTION    "Not allowed through SNMP"

      VARIATION         ipCidrRouteInfo
         ACCESS         read-only
         DESCRIPTION    "Not allowed through SNMP"

      VARIATION         ipCidrRouteNextHopAS
         ACCESS         read-only
         DESCRIPTION    "Not allowed through SNMP"

      VARIATION         ipCidrRouteStatus
         ACCESS         read-only
         DESCRIPTION    "Not allowed through SNMP"

      VARIATION         ipCidrRouteMetric1
         ACCESS         read-only
         DESCRIPTION    "Not allowed through SNMP"

      VARIATION         ipCidrRouteMetric2
         ACCESS         read-only
         DESCRIPTION    "Not allowed through SNMP"

      VARIATION         ipCidrRouteMetric3
         ACCESS         read-only
         DESCRIPTION    "Not allowed through SNMP"

      VARIATION         ipCidrRouteMetric4
         ACCESS         read-only
         DESCRIPTION    "Not allowed through SNMP"

      VARIATION         ipCidrRouteMetric5
         ACCESS         read-only
         DESCRIPTION    "Not allowed through SNMP"

      VARIATION         inetCidrRouteIfIndex
         ACCESS         read-only
         DESCRIPTION    "Not allowed through SNMP"

      VARIATION         inetCidrRouteType
         ACCESS         read-only
         DESCRIPTION    "Not allowed through SNMP"

      VARIATION         inetCidrRouteProto
         ACCESS         read-only
         DESCRIPTION    "Not allowed through SNMP"

      VARIATION         inetCidrRouteAge
         ACCESS         read-only
         DESCRIPTION    "Not allowed through SNMP"

      VARIATION         inetCidrRouteNextHopAS
         ACCESS         read-only
         DESCRIPTION    "Not allowed through SNMP"

      VARIATION         inetCidrRouteMetric1
         ACCESS         read-only
         DESCRIPTION    "Not allowed through SNMP"

      VARIATION         inetCidrRouteMetric2
         ACCESS         read-only
         DESCRIPTION    "Not allowed through SNMP"

      VARIATION         inetCidrRouteMetric3
         ACCESS         read-only
         DESCRIPTION    "Not allowed through SNMP"

      VARIATION         inetCidrRouteMetric4
         ACCESS         read-only
         DESCRIPTION    "Not allowed through SNMP"

      VARIATION         inetCidrRouteMetric5
         ACCESS         read-only
         DESCRIPTION    "Not allowed through SNMP"

      VARIATION         inetCidrRouteStatus
         ACCESS         read-only
         DESCRIPTION    "Not allowed through SNMP"

   SUPPORTS             TCP-MIB
      INCLUDES { tcp }
      VARIATION         tcpConnectionState
         ACCESS         read-only
         DESCRIPTION    "Not allowed through SNMP"

--
-- SNMP-MIB
--
   SUPPORTS             SNMPv2-MIB
      INCLUDES { snmp }

      VARIATION         snmpEnableAuthenTraps
         ACCESS         read-only
         DESCRIPTION    "Not allowed through SNMP"

--
-- SNMP-USER-BASED-SM-MIB
--
   SUPPORTS             SNMP-USER-BASED-SM-MIB
      INCLUDES { usmUser }

      VARIATION         usmUserSpinLock
         ACCESS         read-only
         DESCRIPTION    "Not allowed through SNMP"

      VARIATION         usmUserCloneFrom
         ACCESS         read-only
         DESCRIPTION    "Not allowed through SNMP"

      VARIATION         usmUserPublic
         ACCESS         read-only
         DESCRIPTION    "Not allowed through SNMP"

      VARIATION         usmUserStorageType
         ACCESS         read-only
         DESCRIPTION    "Not allowed through SNMP"

      VARIATION         usmUserStatus
         ACCESS         read-only
         DESCRIPTION    "Not allowed through SNMP"

--
-- SNMP-VIEW-BASED-ACM-MIB
--
   SUPPORTS             SNMP-VIEW-BASED-ACM-MIB
      INCLUDES { vacmMIBObjects }

      VARIATION         vacmSecurityToGroupStorageType
         ACCESS         read-only
         DESCRIPTION    "Not allowed through SNMP"

      VARIATION         vacmSecurityToGroupStatus
         ACCESS         read-only
         DESCRIPTION    "Not allowed through SNMP"

      VARIATION         vacmGroupName
         ACCESS         read-only
         DESCRIPTION    "Not allowed through SNMP"

      VARIATION         vacmAccessContextMatch
         ACCESS         read-only
         DESCRIPTION    "Not allowed through SNMP"

      VARIATION         vacmAccessReadViewName
         ACCESS         read-only
         DESCRIPTION    "Not allowed through SNMP"

      VARIATION         vacmAccessWriteViewName
         ACCESS         read-only
         DESCRIPTION    "Not allowed through SNMP"

      VARIATION         vacmAccessNotifyViewName
         ACCESS         read-only
         DESCRIPTION    "Not allowed through SNMP"

      VARIATION         vacmAccessStorageType
         ACCESS         read-only
         DESCRIPTION    "Not allowed through SNMP"

      VARIATION         vacmAccessStatus
         ACCESS         read-only
         DESCRIPTION    "Not allowed through SNMP"

      VARIATION         vacmViewTreeFamilyMask
         ACCESS         read-only
         DESCRIPTION    "Not allowed through SNMP"

      VARIATION         vacmViewTreeFamilyType
         ACCESS         read-only
         DESCRIPTION    "Not allowed through SNMP"

      VARIATION         vacmViewTreeFamilyStorageType
         ACCESS         read-only
         DESCRIPTION    "Not allowed through SNMP"

      VARIATION         vacmViewTreeFamilyStatus
         ACCESS         read-only
         DESCRIPTION    "Not allowed through SNMP"

--
-- FC-MIB
--
   SUPPORTS             FCMGMT-MIB
      INCLUDES { connSet }

      VARIATION         connUnitUrl
         ACCESS         read-only
         DESCRIPTION    "Not allowed through SNMP"

      VARIATION         systemURL
         ACCESS         read-only
         DESCRIPTION    "Not allowed through SNMP"

      VARIATION         connUnitContact
         SYNTAX DisplayString (SIZE(1..64))
         DESCRIPTION    "1 to 64 characters"
      
      VARIATION         connUnitName
         SYNTAX DisplayString (SIZE(1..32))
         DESCRIPTION    "1 to 32 characters"

      VARIATION         connUnitLocation
         SYNTAX DisplayString (SIZE(1..64))
         DESCRIPTION    "1 to 64 characters"

      VARIATION         connUnitPortName
         SYNTAX DisplayString (SIZE(1..32))
         DESCRIPTION    "1 to 32 characters"
--
-- FE-MIB
--
   SUPPORTS             FIBRE-CHANNEL-FE-MIB
      INCLUDES { fcFeConfigGroup, fcFeStatusGroup, fcFeErrorGroup }

      VARIATION         fcFeFabricName
         ACCESS         read-only
         DESCRIPTION    "Not allowed through SNMP"

      VARIATION         fcFeElementName
         ACCESS         read-only
         DESCRIPTION    "Not allowed through SNMP"

      VARIATION         fcFeModuleLastChange
         ACCESS         not-implemented
         DESCRIPTION    "Not implemented"

      VARIATION         fcFeModuleName
         ACCESS         read-only
         DESCRIPTION    "Not allowed through SNMP"

      VARIATION         fcFxPortBbCreditAvailable
         ACCESS         not-implemented
         DESCRIPTION    "Not implemented"

      VARIATION         fcFxPortAdminMode
         ACCESS         not-implemented
         DESCRIPTION    "Not implemented"

      VARIATION         fcFxPortPhysLastChange
         ACCESS         not-implemented
         DESCRIPTION    "Not implemented"

      VARIATION         fcFxPortFcphVersionAgreed
         ACCESS         not-implemented
         DESCRIPTION    "Not implemented"

      VARIATION         fcFxPortNxPortBbCredit
         ACCESS         not-implemented
         DESCRIPTION    "Not implemented"

      VARIATION         fcFxPortNxPortRxDataFieldSize
         ACCESS         not-implemented
         DESCRIPTION    "Not implemented"

      VARIATION         fcFxPortConnectedNxPort
         ACCESS         not-implemented
         DESCRIPTION    "Not implemented"

      VARIATION         fcFxPortBbCreditModel
         ACCESS         read-only
         DESCRIPTION    "Not allowed through SNMP"

      VARIATION         fcFxPortSigLosses
         ACCESS         not-implemented
         DESCRIPTION    "Not implemented"

      VARIATION         fcFxPortDelimiterErrors
         ACCESS         not-implemented
         DESCRIPTION    "Not implemented"

      VARIATION         fcFxPortC1InFrames
         ACCESS         not-implemented
         DESCRIPTION    "Not implemented"

      VARIATION         fcFxPortC1OutFrames
         ACCESS         not-implemented
         DESCRIPTION    "Not implemented"

      VARIATION         fcFxPortC1InOctets
         ACCESS         not-implemented
         DESCRIPTION    "Not implemented"

      VARIATION         fcFxPortC1OutOctets
         ACCESS         not-implemented
         DESCRIPTION    "Not implemented"

      VARIATION         fcFxPortC1Discards
         ACCESS         not-implemented
         DESCRIPTION    "Not implemented"

      VARIATION         fcFxPortC1FbsyFrames
         ACCESS         not-implemented
         DESCRIPTION    "Not implemented"

      VARIATION         fcFxPortC1FrjtFrames
         ACCESS         not-implemented
         DESCRIPTION    "Not implemented"

      VARIATION         fcFxPortC1InConnections
         ACCESS         not-implemented
         DESCRIPTION    "Not implemented"

      VARIATION         fcFxPortC1OutConnections
         ACCESS         not-implemented
         DESCRIPTION    "Not implemented"

      VARIATION         fcFxPortC1ConnTime
         ACCESS         not-implemented
         DESCRIPTION    "Not implemented"

   ::= { qlgcSANBox2Capability 1 }

END

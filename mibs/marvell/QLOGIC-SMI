-- QLOGIC-SMI.my: QLogic Enterprise Structure of Management Information
--
-- Copyright 1994-2006 QLogic Corporation
-- All Rights Reserved

QLOGIC-SMI DEFINITIONS ::= BEGIN

IMPORTS
    MODULE-IDENTITY, OBJECT-IDENTITY, 
    enterprises
    FROM SNMPv2-SMI
    ;

qlogic MODULE-IDENTITY
    LAST-UPDATED  "200610110000Z" -- October 11, 2006
    ORGANIZATION  "QLogic Corp."
    CONTACT-INFO
    "
    QLogic Customer Service (SNMP)
    Postal: 26650 Aliso Viejo Parkway
            Aliso Viejo, California 92656
            USA
    Tel: +1 952-932-4040

    E-mail: support@qlogic.com
    "
    DESCRIPTION
        "The Structure of Management Information for the
        QLogic enterprise."

    REVISION      "200610110000Z" -- October 11, 2006
    DESCRIPTION
        "Commented out the definition of ancorExperimental to remove
        conflicts with declarations in the QLOGIC-MIB"

    REVISION      "200610060000Z" -- October 6, 2006
    DESCRIPTION
        "Added sanBox9000. Declared some values as never to be used
        historical."

    REVISION      "200507080000Z" -- July 8, 2005
    DESCRIPTION
        "Initial version of this MIB module."

::= { enterprises 3873 }    -- assigned by IANA

qlogicProducts OBJECT-IDENTITY
    STATUS        current
    DESCRIPTION
        "qlogicProducts is the root OBJECT IDENTIFIER from
        which sysObjectID values are assigned.  Actual
        values are defined in QLOGIC-PRODUCTS-MIB."
::= { qlogic 1 }

qlogicModules OBJECT-IDENTITY
    STATUS        current
    DESCRIPTION
        "qlogicModules provides a root object identifier
        from which MODULE-IDENTITY values may be assigned."
::= { qlogic 2 }

qlogicMgmt OBJECT-IDENTITY
    STATUS        current
    DESCRIPTION
        "qlogicMgmt is the main subtree for new MIB
                development."
::= { qlogic 3 }

qlogicAgentCapability OBJECT-IDENTITY
    STATUS        current
    DESCRIPTION
        "qlogicAgentCapability provides a root object identifier
        from which AGENT-CAPABILITIES values may be assigned."
::= { qlogic 4 }

qlogicOtherEnterprises OBJECT-IDENTITY
    STATUS        current
    DESCRIPTION
        "To provide a root object identifier from which MIBs 
        produced by other companies may be placed.  MIBs produced
        by other enterprises are typicially implemented with the
        object identifiers as defined in the MIB, but if the MIB
        is deemed to be uncontrolled, we may reroot the MIB at this
        subtree in order to have a controlled version."
::= { qlogic 5 }

qlogicExperimental OBJECT-IDENTITY
    STATUS        current
    DESCRIPTION
        "qlogicExperiment provides a root object identifier
        from which experimental MIBs may be temporarily
        based.  MIBs are typicially based here if they
        fall in one of two categories
        1) are IETF work-in-process MIBs which have not
        been assigned a permanent object identifier by
        the IANA.
        2) are qlogic work-in-process which has not been
        assigned a permanent object identifier by the
        qlogic assigned number authority, typicially because
        the MIB is not ready for deployment.

        NOTE WELL:  support for MIBs in the qlogicExperiment
        subtree will be deleted when a permanent object
        identifier assignment is made."
::= { qlogic 6 }

-- Most of the QLogic SNMP support until the initial creation of this
-- document has taken place under the enterprise number of a QLogic
-- daughter company (Ancor). 
--
-- The following defines the existing tree of numbers in use. The 
-- numbers defined here are valid as long as is necessary; HOWEVER,
-- no new numbers can be assigned from this tree as of the initial
-- revision of this document.

ancor OBJECT IDENTIFIER ::= { enterprises 1663 } -- assigned by IANA

ancorOidTree OBJECT IDENTIFIER ::= { ancor 1 }

products OBJECT IDENTIFIER ::= { ancorOidTree 1 }

networkComponents OBJECT IDENTIFIER ::= { products 1 }

fibreChannelSwitches OBJECT IDENTIFIER ::= { networkComponents 1 }

-- fibreChannelSwitches { networkComponents 1 } :
-- The following (10) are as of the initial revision of this document unsupported
-- however, the numbers are taken.
-- fcs266FibreSwitch16 OBJECT IDENTIFIER ::= { fibreChannelSwitches 1 } FCS 266 Fibre Switch 16 ports
-- fcs266FibreSwitch64 OBJECT IDENTIFIER ::= { fibreChannelSwitches 2 } FCS 266 Fibre Switch 64 ports
-- fcs1062GigabitFibreSwitch OBJECT IDENTIFIER ::= { fibreChannelSwitches 3 } FCS 1062 Gigabit Fibre Switch
-- gigWorksMKII16 OBJECT IDENTIFIER ::= { fibreChannelSwitches 4 } GigWorks MKII-16 Switch
-- gigWorksMKII8 OBJECT IDENTIFIER ::= { fibreChannelSwitches 5 } GigWorks MKII-8 Switch
-- sanboxMKIISL OBJECT IDENTIFIER ::= { fibreChannelSwitches 6 } SANbox MKII-SL Switch
-- sanboxMKII16 OBJECT IDENTIFIER ::= { fibreChannelSwitches 7 } SANbox MKII-16 Switch
-- sanboxMKII8 OBJECT IDENTIFIER ::= { fibreChannelSwitches 8 } SANbox MKII-8 Switch
-- sanbox64PortDirector OBJECT IDENTIFIER ::= { fibreChannelSwitches 9 } SANbox 64 Port Director
-- sanbox128PortDirector OBJECT IDENTIFIER ::= { fibreChannelSwitches 10 } SANbox 128 Port Director
-- The following (30) are, except as marked, are supported in some way as of the
-- initial revision of this document.
sanboxTwo16Port OBJECT IDENTIFIER ::= { fibreChannelSwitches 11 } -- SANbox2 16 Port Switch
sanboxTwo64Port OBJECT IDENTIFIER ::= { fibreChannelSwitches 12 } -- SANbox2-64 FC Switch ("Jupiter")
oemConnectrixSCQ OBJECT IDENTIFIER ::= { fibreChannelSwitches 13 } -- Connectrix-SCQ (Spider-1, 16 Port Blade)
sanboxTwo8Port OBJECT IDENTIFIER ::= { fibreChannelSwitches 14 } -- SANbox2 8 Port Half-Wide Switch
oemIBM2G8PortSwitch OBJECT IDENTIFIER ::= { fibreChannelSwitches 15 } -- IBM 2G 8 Port Switch
oemIBMSwitchBlade OBJECT IDENTIFIER ::= { fibreChannelSwitches 16 } -- IBM Switch Blade
sanbox5200 OBJECT IDENTIFIER ::= { fibreChannelSwitches 17 } -- SANbox 5200 (Amazon 8,12,16,20)
oemGenericSwitchBlade OBJECT IDENTIFIER ::= { fibreChannelSwitches 18 } -- Generic SwitchBlade
sanbox3000 OBJECT IDENTIFIER ::= { fibreChannelSwitches 19 } -- SANbox 3000 (Laguna 8)
sanbox3100 OBJECT IDENTIFIER ::= { fibreChannelSwitches 20 } -- SANbox 3100 (Laguna 16)
oemIBMSwitchBlade20 OBJECT IDENTIFIER ::= { fibreChannelSwitches 21 } -- IBM Switch Blade-20
oemGenericSwitchBlade20 OBJECT IDENTIFIER ::= { fibreChannelSwitches 22 } -- Generic SwitchBlade-20
sanbox5600 OBJECT IDENTIFIER ::= { fibreChannelSwitches 23 } -- SANbox 5600 (Amazon 4)
sanbox5602 OBJECT IDENTIFIER ::= { fibreChannelSwitches 24 } -- SANbox 5602 (Amazon 4HA)
sanbox3600 OBJECT IDENTIFIER ::= { fibreChannelSwitches 25 } -- SANbox 3600 (Galpin20)
sanbox3602 OBJECT IDENTIFIER ::= { fibreChannelSwitches 26 } -- SANbox 3602 (Galpin20-HA)
sanbox1400 OBJECT IDENTIFIER ::= { fibreChannelSwitches 27 } -- SANbox 1400 (Amber)
-- OBJECT IDENTIFIER ::= { fibreChannelSwitches 28 } historical
oemDellBlade OBJECT IDENTIFIER ::= { fibreChannelSwitches 29 } -- Dell Blade (Glacier)
sanbox5202 OBJECT IDENTIFIER ::= { fibreChannelSwitches 30 } -- SANbox 5202 (Amazon-HA 8,12,16,20)
oemHPStorageWorks28qFCSwitch OBJECT IDENTIFIER ::= { fibreChannelSwitches 31 } -- HP StorageWorks 2/8q FC Switch
oemEngenioESHIC OBJECT IDENTIFIER ::= { fibreChannelSwitches 32 } -- Engenio ESHIC (Vermillion)
sanBox9000 OBJECT IDENTIFIER ::= { fibreChannelSwitches 33 }
oemIBM4GSwitchBlade20 OBJECT IDENTIFIER ::= { fibreChannelSwitches 34 } -- 4G IBM Switch Blade-20 (Clover)
oemGeneric4GSwitchBlade20 OBJECT IDENTIFIER ::= { fibreChannelSwitches 35 } -- 4Gig Generic Switch Blade-20
-- OBJECT IDENTIFIER ::= { fibreChannelSwitches 36 } historical
oemHPMcDATAMode4GSwitch OBJECT IDENTIFIER ::= { fibreChannelSwitches 37 } -- HP CUBE
oemMcDATASwitchBlade20 OBJECT IDENTIFIER ::= { fibreChannelSwitches 38 } -- McDATA - IBM Switch Blade-20
oemMcDATA4GSwitchBlade20 OBJECT IDENTIFIER ::= { fibreChannelSwitches 39 } -- McDATA -Clover - 4G IBM Switch Blade-20
-- OBJECT IDENTIFIER ::= { fibreChannelSwitches 40 } historical
-- OBJECT IDENTIFIER ::= { fibreChannelSwitches 41 } historical
-- The reserved identifiers will be added when the products are released
-- or dropped. No others will be added to this list (ie, 41 is the final
-- value).
-- Please see the QLOGIC-PRODUCTS MIB for the newest product IDs.

fibreChannelSwitchModules OBJECT IDENTIFIER ::= { networkComponents 2 }

-- fcs266FibreSwitchPortModule OBJECT IDENTIFIER ::= { fibreChannelSwitchModules 1 }
-- fcs266FibreSwitchPowerSupply OBJECT IDENTIFIER ::= { fibreChannelSwitchModules 2 }
-- fcs266FibreSwitchMultistageSoftware has same OID as fcs266FibreSwitchPowerSupply

-- fibreChannelSwitchFirmware has same OID as fibreChannelSwitchModules

networkGateways OBJECT IDENTIFIER ::= { products 2 }

-- network gateways
-- fibreLink OBJECT IDENTIFIER ::= { networkGateways 1 }
-- fcs266FibreLinkSystem OBJECT IDENTIFIER ::= { fibreLink 1 }
-- fcs1062FibreLinkSystem has same OID as fcs266FibreLinkSystem
-- fibreLinkExpansionModules OBJECT IDENTIFIER ::= { networkGateways 2 }
-- fcs266MPREnetExpansionModule  OBJECT IDENTIFIER ::= { fibreLinkExpansionModules 1 }
-- fcs266MPRTknRingExpansionModule  OBJECT IDENTIFIER ::= { fibreLinkExpansionModules 2 }
-- fcs266MPRFddiExpansionModule  OBJECT IDENTIFIER ::= { fibreLinkExpansionModules 3 }
-- fcs266MPRAtmExpansionModule  OBJECT IDENTIFIER ::= { fibreLinkExpansionModules 4 }

networkInterfaces OBJECT IDENTIFIER ::= { products 3 }

-- adapters OBJECT IDENTIFIER ::= { networkInterfaces 1 }

-- eisa OBJECT IDENTIFIER ::= { adapters 1 }
-- fcs266EisaAdapter OBJECT IDENTIFIER ::= { eisa 1 } FCS 266 EISA Adapter
-- mca OBJECT IDENTIFIER ::= { adapters 2 }
-- fcs266McaAdapter OBJECT IDENTIFIER ::= { mca 1 } FCS 266 MCA Adapter
-- vme OBJECT IDENTIFIER ::= { adapters 3 }
-- fcs266Vme6UAdapter OBJECT IDENTIFIER ::= { vme 1 } FCS 266 VME/64 6UAdapter
-- fcs266Vme9UAdapter OBJECT IDENTIFIER ::= { vme 2 } FCS 266 SGI VME/64 9U Adapter
-- sbus OBJECT IDENTIFIER ::= { adapters 4 }
-- fcs266SbusAdapter OBJECT IDENTIFIER ::= { sbus 1 } FCS 266 SBus Adapter
-- fcs1062SbusAdapter OBJECT IDENTIFIER ::= { sbus 2 } FCS 1062/266 SBus Adapter
-- pci OBJECT IDENTIFIER ::= { adapters 5 }
-- fcs266PciAdapter OBJECT IDENTIFIER ::= { pci 1 } FCS 266 PCI Adapter
-- fcs1062PciAdapter OBJECT IDENTIFIER ::= { pci 2 } FCS 1062/266 PCI Adapter
-- fcs1062MultiMediaPciAdapter OBJECT IDENTIFIER ::= { pci 3 } FCS 1062 Multiimedia PCI Adapter

-- drivers OBJECT IDENTIFIER ::= { networkInterfaces 2 }
-- eisa OBJECT IDENTIFIER ::= { drivers 1 }
-- novell312 OBJECT IDENTIFIER ::= { eisa 1 } Novell 3.12
-- hpux OBJECT IDENTIFIER ::= { eisa 2 } HPUX
-- irix53 OBJECT IDENTIFIER ::= { eisa 3 } IRIX 5.3
-- mca object identifier ::= { drivers 2 }
-- novell312 OBJECT IDENTIFIER ::= { mca 1 } Novell 3.12
-- aix325 OBJECT IDENTIFIER ::= { mca 2 } AIX 3.2.5
-- vme object identifier ::= { drivers 3 }
-- irix53  OBJECT IDENTIFIER ::= { vme 1 } IRIX 5.3
-- sbus object identifier ::= { drivers 4 }
-- solaris2324 OBJECT IDENTIFIER ::= { sbus 1 } Solaris 2.3 & 2.4
-- pci object identifier ::= { drivers 5 }
-- novell312 OBJECT IDENTIFIER ::= { pci 1 } Novell 3.12

networkManagement OBJECT IDENTIFIER ::= { products 4 }
-- proxyAgents OBJECT IDENTIFIER ::= { networkManagement 1 }
-- fcsview10  OBJECT IDENTIFIER ::= { proxyAgents 1 }

enterpriseMIB OBJECT IDENTIFIER ::= { ancorOidTree 2 }

-- fibreChannelSwitches OBJECT IDENTIFIER ::= { enterpriseMIB 1 }
-- objects under fibreChannelSwitches ignored

-- obsoleted OBJECT IDENTIFIER ::= { enterpriseMIB 2 }

-- these two MIBs use hard-coded (pre-SMI) values to link up to
-- the Ancor enterprise, they are not needed but included for reference
-- I do not know as of yet, whether these MIBs are in use or not.
-- ancorNameServiceMib OBJECT IDENTIFIER ::= { enterpriseMIB 3 }
-- ancorFabricLoopMib OBJECT IDENTIFIER ::= { enterpriseMIB 4 }

-- ancorExperimental OBJECT IDENTIFIER ::= { ancorOidTree 3 }
-- FC Loop OBJECT IDENTIFIER ::= {ancorExperimental 1 }
-- MKIIAccountingX OBJECT IDENTIFIER ::= {ancorExperimental 2 }
-- Testing OBJECT IDENTIFIER ::= {ancorExperimental 3 }
-- Traps OBJECT IDENTIFIER ::= {ancorExperimental 4 }
-- Zoning OBJECT IDENTIFIER ::= {ancorExperimental 5 }
-- Configuration OBJECT IDENTIFIER ::= {ancorExperimental 6 }
-- Name Service OBJECT IDENTIFIER ::= {ancorExperimental 7 }
-- Diagnostics OBJECT IDENTIFIER ::= {ancorExperimental 8 }
-- II-Cons OBJECT IDENTIFIER ::= {ancorExperimental 9 }

-- As far as I can tell, this is the only actual existing, in-use
-- QLogic proprietary MIB. It has hard-coded the following information
-- so it is given here for reference/completeness.
-- QlSB2PortControl OBJECT IDENTIFIER ::= {ancorExperimental 10 } SANbox2 Port Control MIB

END

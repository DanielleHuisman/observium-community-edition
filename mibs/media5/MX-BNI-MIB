-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************

MX-BNI-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

bniMIB MODULE-IDENTITY
 LAST-UPDATED   "1910210000Z"
 ORGANIZATION " Mediatrix Telecom, Inc. "
 CONTACT-INFO " Mediatrix Telecom, Inc.
                4229, Garlock Street
                Sherbrooke (Quebec)
                Canada
                Phone: (819) 829-8749
                "
 DESCRIPTION  " Basic Network Interfaces

                The Basic Network Interfaces (BNI) service manages the layer 3
                network interfaces.
                "
 ::= { mediatrixServices 200 }

bniMIBObjects OBJECT IDENTIFIER ::= { bniMIB 1 }

-- ****************************************************************************

-- Group:DHCP Client Configuration

-- ****************************************************************************

dhcpClientGroup OBJECT IDENTIFIER
 ::= { bniMIBObjects 200 }
 -- Scalar:DHCPv4 Client Identifier Presentation

 dhcpClientIdentifierPresentation OBJECT-TYPE
  SYNTAX        INTEGER { disabled(100) , macAscii(200) , macBinary(300) }
  MAX-ACCESS    read-write
  STATUS        current
  DESCRIPTION " DHCPv4 Client Identifier Presentation

                The method to use to present the value of the Client
                Identifier (Option 61) field through a DHCPv4 request.

                  * Disabled: The Client Identifier option is not presented in
                    a DHCPv4 request.
                  * MacAscii: The Client Identifier value is presented as the
                    client MAC address in ASCII format. The MAC address is
                    represented in lowercase.
                  * MacBinary: The Client Identifier value is presented as the
                    client MAC address in binary format.

                "
  DEFVAL        { macAscii }
  ::= { dhcpClientGroup 100 }

 -- Scalar:DHCPv4 Client Duplicate IP Address Detection Enable

 dhcpClientDuplicateIpAddressDetectionEnable OBJECT-TYPE
  SYNTAX        MxEnableState
  MAX-ACCESS    read-write
  STATUS        current
  DESCRIPTION " DHCPv4 Client Duplicate IP Address Detection Enable

                Defines if duplicate address detection must be performed
                before using a received DHCPv4 IP address.

                  * Enable: Verifies that the received DHCPv4 IP address is
                    not already used on the network. If it is already used on
                    the network, a DHCPv4 DECLINE is sent to the DHCPv4 server
                    and the DHCPv4 process is restarted after 10 to 20
                    seconds.
                  * Disable: The received DHCPv4 IP address is used without
                    verification.

                "
  DEFVAL        { disable }
  ::= { dhcpClientGroup 200 }

 -- Scalar:DHCPv4 Classless Static Route Option

 dhcpClientClasslessStaticRouteOption OBJECT-TYPE
  SYNTAX        INTEGER { none(100) , request(200) }
  MAX-ACCESS    read-write
  STATUS        current
  DESCRIPTION " DHCPv4 Classless Static Route Option

                Defines if the Classless Static Route Option is enabled.

                  * Request: The device requests the Classless Static Route
                    Option 121.
                  * None: Routes received from the DHCP server are ignored.

                "
  DEFVAL        { none }
  ::= { dhcpClientGroup 300 }

 -- Scalar:DHCPv4 User Class Option

 dhcpClientUserClass OBJECT-TYPE
  SYNTAX        OCTET STRING ( SIZE(0..254) )
  MAX-ACCESS    read-write
  STATUS        current
  DESCRIPTION " DHCPv4 User Class Option

                Defines if the User Class Route Option is enabled.

                List of User Class value to be sent over Option 77. User class
                value items are separated by a comma and items must not be
                empty. Hexadecimal values are supported using the '\xXX'
                format where XX is the hexadecimal value. When the parameter
                is empty, user class option is not sent.

                "
  DEFVAL        { "" }
  ::= { dhcpClientGroup 400 }

-- End of group:DHCP Client Configuration

-- ****************************************************************************

-- Group:PPP Configuration

-- ****************************************************************************

pppIpcpGroup OBJECT IDENTIFIER
 ::= { bniMIBObjects 400 }
 -- Scalar:Service Name

 pppServiceName OBJECT-TYPE
  SYNTAX        OCTET STRING ( SIZE(0..64) )
  MAX-ACCESS    read-write
  STATUS        current
  DESCRIPTION " Service Name

                Name of the service requested to the access concentrator (AC)
                when establishing the next PPPoE connection.

                This string is used as the Service-Name field of the PADI
                packet broadcasted to the access concentrators. See RFC 2516
                section 5.1 for details.

                "
  DEFVAL        { "" }
  ::= { pppIpcpGroup 100 }

 -- Scalar:Retry Interval

 pppRetryInterval OBJECT-TYPE
  SYNTAX        Unsigned32 ( 1..900 )
  MAX-ACCESS    read-write
  STATUS        current
  DESCRIPTION " Retry Interval

                Interval, in seconds, between connection attempts. A
                connection is automatically retried when it fails due to a
                transient error. The only error type considered non-transient
                is a configuration error.
                "
  DEFVAL        { 10 }
  ::= { pppIpcpGroup 200 }

 -- Scalar:Authentication Protocol

 pppAuthenticationProtocol OBJECT-TYPE
  SYNTAX        INTEGER { pap(100) , chap(200) }
  MAX-ACCESS    read-write
  STATUS        current
  DESCRIPTION " Authentication Protocol

                Authentication protocol to use for authenticating the system
                to the PPP peer.

                  * Pap: Use the Password Authentication Protocol.
                  * Chap: Use the Challenge Handshake Authentication Protocol.

                "
  DEFVAL        { chap }
  ::= { pppIpcpGroup 300 }

 -- Scalar:User Name

 pppIdentity OBJECT-TYPE
  SYNTAX        OCTET STRING ( SIZE(0..64) )
  MAX-ACCESS    read-write
  STATUS        current
  DESCRIPTION " User Name

                Name that identifies the system to the PPP peer during the
                authentication process.
                "
  DEFVAL        { "" }
  ::= { pppIpcpGroup 400 }

 -- Scalar:Password

 pppSecret OBJECT-TYPE
  SYNTAX        OCTET STRING ( SIZE(0..64) )
  MAX-ACCESS    read-write
  STATUS        current
  DESCRIPTION " Password

                Secret that identifies the system to the PPP peer during the
                authentication process.

                Whatever the value defined, this parameter always displays
                '*****'.

                "
  DEFVAL        { "" }
  ::= { pppIpcpGroup 500 }

-- End of group:PPP Configuration

-- ****************************************************************************

-- Group:ICMP Configuration

-- ****************************************************************************

icmpGroup OBJECT IDENTIFIER
 ::= { bniMIBObjects 500 }
 -- Scalar:ICMP Redirect

 icmpRedirect OBJECT-TYPE
  SYNTAX        INTEGER { acceptIpv4AndIpv6(100) , acceptIpv4Only(200) }
  MAX-ACCESS    read-write
  STATUS        current
  DESCRIPTION " ICMP Redirect

                ICMP redirect are used to inform a host to send packets on an
                alternate route.

                This parameter allows to control the unit behavior when
                receiving ICMP redirects.

                  * AcceptIpv4AndIpv6: The redirection is applied for both
                    IPv4 and IPv6.
                  * AcceptIpv4Only: The redirection is applied for IPv4 only.

                "
  DEFVAL        { acceptIpv4AndIpv6 }
  ::= { icmpGroup 100 }

-- End of group:ICMP Configuration

-- ****************************************************************************

-- Group:IP Configuration

-- ****************************************************************************

ipGroup OBJECT IDENTIFIER
 ::= { bniMIBObjects 600 }
 -- Scalar:IP TTL value

 ipTtlValue OBJECT-TYPE
  SYNTAX        Unsigned32 ( 64..255 )
  MAX-ACCESS    read-write
  STATUS        current
  DESCRIPTION " IP TTL value

                Specifies the IP traffic default Time-To-Live (TTL) value on
                all network interfaces. The TTL is effectively the maximum
                number of network hops allowed before the IP packet is dropped
                by the network.

                Supported only for IPv4.

                "
  DEFVAL        { 64 }
  ::= { ipGroup 100 }

-- End of group:IP Configuration

-- *****************************************************************************

-- Table:Interfaces Configuration

-- *****************************************************************************

networkInterfacesTable OBJECT-TYPE
 SYNTAX                    SEQUENCE OF NetworkInterfacesEntry
 MAX-ACCESS                not-accessible
 STATUS                    current
 DESCRIPTION            "  Interfaces Configuration

                           This table configures the network interfaces.
                           "
 ::= { bniMIBObjects 1000 }
 networkInterfacesEntry OBJECT-TYPE
  SYNTAX        NetworkInterfacesEntry
  MAX-ACCESS    not-accessible
  STATUS        current
  DESCRIPTION " A row in table Interfaces Configuration. "
  INDEX         {
                  networkInterfacesIdx
                }

  ::= { networkInterfacesTable 1 }

 NetworkInterfacesEntry ::= SEQUENCE
 {
   networkInterfacesIdx                 Unsigned32,
   networkInterfacesInterfaceName       OCTET STRING,
   networkInterfacesLinkName            OCTET STRING,
   networkInterfacesConnectionType      INTEGER,
   networkInterfacesStaticIpAddr        MxIpAddrMask,
   networkInterfacesStaticDefaultRouter MxIpAddress,
   networkInterfacesActivation          MxEnableState,
   networkInterfacesPriority            Unsigned32,
   networkInterfacesConfigStatus        INTEGER,
   networkInterfacesDelete              INTEGER
 }

 -- Columnar:Interface Name

 networkInterfacesInterfaceName OBJECT-TYPE
  SYNTAX        OCTET STRING ( SIZE(0..50) )
  MAX-ACCESS    read-write
  STATUS        current
  DESCRIPTION " Interface Name

                Network interface name. This parameter is case sensitive. Note
                that using the special values 'All', 'Loop', 'LoopV6' and
                'Rescue' are not allowed.
                "
  ::= { networkInterfacesEntry 100 }

 -- Columnar:Link Interface

 networkInterfacesLinkName OBJECT-TYPE
  SYNTAX        OCTET STRING ( SIZE(0..50) )
  MAX-ACCESS    read-write
  STATUS        current
  DESCRIPTION " Link Interface

                Name of the link interface associated with the network
                interface.
                "
  ::= { networkInterfacesEntry 200 }

 -- Columnar:Connection Type

 networkInterfacesConnectionType OBJECT-TYPE
  SYNTAX        INTEGER { ipDhcp(100) , ipStatic(200) , ip6AutoConf(225) ,
                ip6Static(250) , pppIpcp(300) }
  MAX-ACCESS    read-write
  STATUS        current
  DESCRIPTION " Connection Type

                Connection type of the network interface.

                  * IpDhcp: IPv4 connection, address and network mask are
                    provided by a DHCP server.
                  * IpStatic: IPv4 connection, address and network mask are
                    configured by the column NetworkInterfaces.StaticIpAddr.
                  * Ip6AutoConf: IPv6 state-less auto-configuration.
                  * Ip6Static: IPv6 connection, address and network mask are
                    configured by the column NetworkInterfaces.StaticIpAddr.
                  * PppIpcp: IPv4 over PPP connection, address and network mask
                    are provided by the PPP peer using IPCP.

                DHCP servers and PPP peers may provide a list of DNS to use. If
                that is the case, the DNS are forwarded to the Host
                Configuration service where they can be used.
                "
  DEFVAL        { ipStatic }
  ::= { networkInterfacesEntry 250 }

 -- Columnar:Static IP Address

 networkInterfacesStaticIpAddr OBJECT-TYPE
  SYNTAX        MxIpAddrMask
  MAX-ACCESS    read-write
  STATUS        current
  DESCRIPTION " Static IP Address

                IP address and network mask of the network interface when the
                ConnectionType parameter is set to 'ipStatic'.

                "
  DEFVAL        { "192.168.0.10/24" }
  ::= { networkInterfacesEntry 300 }

 -- Columnar:Static Default Router

 networkInterfacesStaticDefaultRouter OBJECT-TYPE
  SYNTAX        MxIpAddress
  MAX-ACCESS    read-write
  STATUS        current
  DESCRIPTION " Static Default Router

                IP address of the default router for the network interface when
                the ConnectionType parameter is set to 'ipStatic' or
                'ip6Static'.

                "
  DEFVAL        { "" }
  ::= { networkInterfacesEntry 350 }

 -- Columnar:Activation

 networkInterfacesActivation OBJECT-TYPE
  SYNTAX        MxEnableState
  MAX-ACCESS    read-write
  STATUS        current
  DESCRIPTION " Activation

                Activate the network interface.

                  * Enable: The system should activate the network interface.
                  * Disable: The system should not activate the network
                    interface.

                Tells whether the system should activate the network interface
                or not. The actual status of network interfaces is shown in the
                NetworkInterfacesStatus table.

                "
  DEFVAL        { disable }
  ::= { networkInterfacesEntry 400 }

 -- Columnar:Priority

 networkInterfacesPriority OBJECT-TYPE
  SYNTAX        Unsigned32 ( 0..100 )
  MAX-ACCESS    read-write
  STATUS        current
  DESCRIPTION " Priority

                Prioritize the network interface. In case of address conflicts
                between two or more network interfaces, the network interface
                with the highest priority will remain enabled and all other
                interfaces are set to invalid configuration. If the priority is
                the same, only the first enabled network interface will be able
                to use the IP address. When a conflict ends, all network
                interfaces concerned automatically return to an operational
                state.

                The actual status of network interfaces is shown in the
                NetworkInterfacesStatus table.

                "
  DEFVAL        { 50 }
  ::= { networkInterfacesEntry 450 }

 -- Columnar:Config Status

 networkInterfacesConfigStatus OBJECT-TYPE
  SYNTAX        INTEGER { validConfig(100) , emptyInterfaceName(200),
                duplicateInterfaceName(300) , invalidLinkName(400) ,
                invalidStaticIpAddr(500) , multipleDynamicOnSameLink(600) }
  MAX-ACCESS    read-only
  STATUS        current
  DESCRIPTION " Config Status

                Configuration status of the row.

                It indicates whether the configuration of the row is valid or
                not.

                  * ValidConfig: This entry is valid.
                  * EmptyInterfaceName: This entry is not valid because the
                    InterfaceName parameter is empty.
                  * DuplicateInterfaceName: This entry is not valid because the
                    InterfaceName parameter is already used.
                  * InvalidLinkName: This entry is not valid because the
                    LinkName parameter is either empty or refers to an
                    inexistent link.
                  * InvalidStaticIpAddr: This entry is not valid because the
                    StaticIpAddr parameter is either invalid or conflicts with
                    another network IP address.
                  * MultipleDynamicOnSameLink: This entry is not valid because
                    there is dynamic connection configured on the same link
                    multiple times. May result in unexpected behavior.

                "
  ::= { networkInterfacesEntry 480 }

 -- Index:Idx

 networkInterfacesIdx OBJECT-TYPE
  SYNTAX        Unsigned32
  MAX-ACCESS    read-only
  STATUS        current
  DESCRIPTION " Idx

                Unique identifier of the row in the table.
                "
  ::= { networkInterfacesEntry 50 }

 -- Row command:Delete

 networkInterfacesDelete OBJECT-TYPE
  SYNTAX        INTEGER { noOp(0), delete(10) }
  MAX-ACCESS    read-write
  STATUS        current
  DESCRIPTION " Delete

                Deletes the network interface and removes it from the system.
                "
  DEFVAL        { noOp }
  ::= { networkInterfacesEntry 500 }

-- End of table:Interfaces Configuration

-- *****************************************************************************

-- Table:Interfaces Status

-- *****************************************************************************

networkInterfacesStatusTable OBJECT-TYPE
 SYNTAX        SEQUENCE OF NetworkInterfacesStatusEntry
 MAX-ACCESS    not-accessible
 STATUS        current
 DESCRIPTION " Interfaces Status

               This table displays the status of all currently enabled network
               interfaces, including interfaces with an invalid configuration
               or waiting for a response.
               "
 ::= { bniMIBObjects 2000 }
 networkInterfacesStatusEntry OBJECT-TYPE
  SYNTAX        NetworkInterfacesStatusEntry
  MAX-ACCESS    not-accessible
  STATUS        current
  DESCRIPTION " A row in table Interfaces Status. "
  INDEX         {
                  networkInterfacesStatusIdx
                }

  ::= { networkInterfacesStatusTable 1 }

 NetworkInterfacesStatusEntry ::= SEQUENCE
 {
   networkInterfacesStatusIdx                Unsigned32,
   networkInterfacesStatusInterfaceName      OCTET STRING,
   networkInterfacesStatusInterfaceStatus    INTEGER,
   networkInterfacesStatusLinkName           OCTET STRING,
   networkInterfacesStatusIpAddr             MxIpAddrMask,
   networkInterfacesStatusDefaultRouter      OCTET STRING,
   networkInterfacesStatusConnectionUptime   Unsigned32,
   networkInterfacesStatusVlanOverrideEnable MxEnableState
 }

 -- Columnar:Interface Name

 networkInterfacesStatusInterfaceName OBJECT-TYPE
  SYNTAX           OCTET STRING
  MAX-ACCESS       read-only
  STATUS           current
  DESCRIPTION    " Interface Name

                   Network interface name.
                   "
  ::= { networkInterfacesStatusEntry 100 }

 -- Columnar:Network Interface Status

 networkInterfacesStatusInterfaceStatus OBJECT-TYPE
  SYNTAX        INTEGER { invalidConfig(200) , networkConflict(225) , linkDown
                (250) , waitingResponse(300) , active(400) }
  MAX-ACCESS    read-only
  STATUS        current
  DESCRIPTION " Network Interface Status

                Displays the operational status of the network interface.

                  * InvalidConfig: The interface is not operational because its
                    configuration is not valid.
                  * NetworkConflict: The interface is configured with an IP
                    address that is already used on the network.
                  * LinkDown: The interface is configured with a link that has
                    no connectivity.
                  * WaitingResponse: The interface is not operational because a
                    response from a peer or server is required.
                  * Active: The interface is operational.

                "
  ::= { networkInterfacesStatusEntry 150 }

 -- Columnar:Link Interface

 networkInterfacesStatusLinkName OBJECT-TYPE
  SYNTAX        OCTET STRING
  MAX-ACCESS    read-only
  STATUS        current
  DESCRIPTION " Link Interface

                Name of the link interface associated with the network
                interface.
                "
  ::= { networkInterfacesStatusEntry 200 }

 -- Columnar:IP Address Status

 networkInterfacesStatusIpAddr OBJECT-TYPE
  SYNTAX        MxIpAddrMask
  MAX-ACCESS    read-only
  STATUS        current
  DESCRIPTION " IP Address Status

                Current IP address and network mask of the network interface.
                "
  ::= { networkInterfacesStatusEntry 300 }

 -- Columnar:Default Router

 networkInterfacesStatusDefaultRouter OBJECT-TYPE
  SYNTAX        OCTET STRING
  MAX-ACCESS    read-only
  STATUS        current
  DESCRIPTION " Default Router

                Current default router of the network interface.
                "
  ::= { networkInterfacesStatusEntry 400 }

 -- Index:Idx

 networkInterfacesStatusIdx OBJECT-TYPE
  SYNTAX        Unsigned32
  MAX-ACCESS    read-only
  STATUS        current
  DESCRIPTION " Idx

                Unique identifier of the row in the table.
                "
  ::= { networkInterfacesStatusEntry 50 }

 -- Columnar:Connection Uptime

 networkInterfacesStatusConnectionUptime OBJECT-TYPE
  SYNTAX        Unsigned32
  MAX-ACCESS    read-only
  STATUS        current
  DESCRIPTION " Connection Uptime

                The time, in seconds, for which this IP interface has been
                connected.

                If the IP interface is using DHCP, this is the time for which
                the DHCP client has been only in the Bound or Renewing states
                and the lower-layer interface has continuously maintained a
                link.

                If the IP interface is using static addressing, this is the
                time for which the lower-layer interface has continuously
                maintained a link.

                "
  ::= { networkInterfacesStatusEntry 500 }

 -- Columnar:VLAN Override Enable

 networkInterfacesStatusVlanOverrideEnable OBJECT-TYPE
  SYNTAX        MxEnableState
  MAX-ACCESS    read-only
  STATUS        current
  DESCRIPTION " VLAN Override Enable

                Indicates if the VLAN ID of the current network interface has
                been overridden by the values received from the LLDP protocol.

                  * Enable: The network interface VLAN configuration is
                    overridden by LLDP.
                  * Disable: The network interface VLAN configuration is not
                    overridden.

                "
  ::= { networkInterfacesStatusEntry 600 }

-- End of table:Interfaces Status

-- ****************************************************************************

-- Group:Statistics

-- ****************************************************************************

statisticsGroup OBJECT IDENTIFIER
 ::= { bniMIBObjects 10000 }
 -- ***************************************************************************
 
 -- Table:Network Interfaces

 -- ***************************************************************************
 
 interfaceStatisticsTable OBJECT-TYPE
  SYNTAX        SEQUENCE OF InterfaceStatisticsEntry
  MAX-ACCESS    not-accessible
  STATUS        current
  DESCRIPTION " Network Interfaces

                This table contains the statistics for each network interface.
                "
  ::= { statisticsGroup 100 }
  interfaceStatisticsEntry OBJECT-TYPE
   SYNTAX        InterfaceStatisticsEntry
   MAX-ACCESS    not-accessible
   STATUS        current
   DESCRIPTION " A row in table Network Interfaces. "
   INDEX         {
                   interfaceStatisticsLinkName
                 }

   ::= { interfaceStatisticsTable 1 }

  InterfaceStatisticsEntry ::= SEQUENCE
  {
    interfaceStatisticsLinkName    OCTET STRING,
    interfaceStatisticsTxBytes     MxUInt64,
    interfaceStatisticsRxBytes     MxUInt64,
    interfaceStatisticsTxPackets   MxUInt64,
    interfaceStatisticsRxPackets   MxUInt64,
    interfaceStatisticsRxErrors    MxUInt64,
    interfaceStatisticsCollectTime Unsigned32,
    interfaceStatisticsResetStat   INTEGER
  }

  -- Index:Link Interface

  interfaceStatisticsLinkName OBJECT-TYPE
   SYNTAX        OCTET STRING
   MAX-ACCESS    read-only
   STATUS        current
   DESCRIPTION " Link Interface

                 Name of the link interface associated with the network
                 interface.
                 "
   ::= { interfaceStatisticsEntry 100 }

  -- Columnar:Statistics Collect Time

  interfaceStatisticsCollectTime OBJECT-TYPE
   SYNTAX        Unsigned32
   MAX-ACCESS    read-only
   STATUS        current
   DESCRIPTION " Statistics Collect Time

                 Time, in seconds, since the network statistics were last
                 reset.
                 "
   ::= { interfaceStatisticsEntry 10000 }

  -- Row command:Reset

  interfaceStatisticsResetStat OBJECT-TYPE
   SYNTAX        INTEGER { noOp(0), resetStat(10) }
   MAX-ACCESS    read-write
   STATUS        current
   DESCRIPTION " Reset

                 Reset all statistics parameters for this interface.
                 "
   DEFVAL        { noOp }
   ::= { interfaceStatisticsEntry 11000 }

  -- Columnar:Bytes Transmitted

  interfaceStatisticsTxBytes OBJECT-TYPE
   SYNTAX        MxUInt64
   MAX-ACCESS    read-only
   STATUS        current
   DESCRIPTION " Bytes Transmitted

                 Total number of bytes transmitted on the interface at the
                 link level.
                 "
   ::= { interfaceStatisticsEntry 200 }

  -- Columnar:Bytes Received

  interfaceStatisticsRxBytes OBJECT-TYPE
   SYNTAX        MxUInt64
   MAX-ACCESS    read-only
   STATUS        current
   DESCRIPTION " Bytes Received

                 Total number of bytes received on this interface at the link
                 level.
                 "
   ::= { interfaceStatisticsEntry 300 }

  -- Columnar:IP Packets Transmitted

  interfaceStatisticsTxPackets OBJECT-TYPE
   SYNTAX        MxUInt64
   MAX-ACCESS    read-only
   STATUS        current
   DESCRIPTION " IP Packets Transmitted

                 Total number of IP packets transmitted on this interface.
                 "
   ::= { interfaceStatisticsEntry 400 }

  -- Columnar:IP Packets Received

  interfaceStatisticsRxPackets OBJECT-TYPE
   SYNTAX        MxUInt64
   MAX-ACCESS    read-only
   STATUS        current
   DESCRIPTION " IP Packets Received

                 Total number of IP packets received on this interface.
                 "
   ::= { interfaceStatisticsEntry 500 }

  -- Columnar:IP Packets Discarded

  interfaceStatisticsRxErrors OBJECT-TYPE
   SYNTAX        MxUInt64
   MAX-ACCESS    read-only
   STATUS        current
   DESCRIPTION " IP Packets Discarded

                 Total number of IP packets discarded on this interface.
                 "
   ::= { interfaceStatisticsEntry 600 }

 -- End of table:Network Interfaces

-- End of group:Statistics

-- ****************************************************************************

-- Group:Notification Messages Configuration

-- ****************************************************************************

notificationsGroup OBJECT IDENTIFIER
 ::= { bniMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with a 'Informational' and
                    higher severity are issued.
                  * Warning: Notification messages with a 'Warning' and higher
                    severity are issued.
                  * Error: Notification messages with an 'Error' and higher
                    severity are issued.
                  * Critical: Notification messages with a 'Critical' severity
                    are issued.

                "
  DEFVAL        { warning }
  ::= { notificationsGroup 100 }

-- End of group:Notification Messages Configuration

-- ****************************************************************************

-- Group:Configuration Settings

-- ****************************************************************************

configurationGroup OBJECT IDENTIFIER
 ::= { bniMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for the
                configuration to fully take effect.

                  * Yes: Service needs to be restarted.
                  * No: Service does not need to be restarted.

                Services can be restarted by using the
                Scm.ServiceCommands.Restart command.

                "
  ::= { configurationGroup 100 }

-- End of group:Configuration Settings

END

-- **SDOC***********************************************************************
-- *****************************************************************************
--
--             Copyright(c) 2004-2005 Mediatrix Telecom, Inc.
--
--  NOTICE:
--   This document contains information that is confidential and proprietary
--   to Mediatrix Telecom, Inc.
--
--   Mediatrix Telecom, Inc. reserves all rights to this document as well as
--   to the Intellectual Property of the document and the technology and
--   know-how that it includes and represents.
--
--   This publication cannot be reproduced, neither in whole nor in part, in
--   any form whatsoever without written prior approval by
--   Mediatrix Telecom, Inc.
--
--   Mediatrix Telecom, Inc. reserves the right to revise this publication
--   and make changes at any time and without the obligation to notify any
--   person and/or entity of such revisions and/or changes.
--
-- *****************************************************************************
-- **EDOC***********************************************************************

MX-CORNET-SYSTEM-MIB
DEFINITIONS ::= BEGIN

IMPORTS
        MODULE-IDENTITY,
        OBJECT-IDENTITY,
        OBJECT-TYPE,
        NOTIFICATION-TYPE,
        Unsigned32
    FROM SNMPv2-SMI
        OBJECT-GROUP,
        MODULE-COMPLIANCE,
        NOTIFICATION-GROUP
    FROM SNMPv2-CONF
        ifIndex
    FROM RFC1213-MIB
        corNet,
        ipAddressStatusCorNet,
        ipAddressConfigCorNet,
        ipAddressConfigCorNetStatic
    FROM MX-CORNET-MIB
        ipAddressStatus,
        ipAddressConfig,
        mediatrixMgmt
    FROM MX-SMI
        MxAdvancedIpPort,
        MxIpHostName,
        MxIpPort,
        MxEnableState
    FROM MX-TC;

corNetSystemMIB MODULE-IDENTITY
    LAST-UPDATED "200607170000Z"
    ORGANIZATION "Mediatrix Telecom, Inc."
    CONTACT-INFO "Mediatrix Telecom, Inc.
                  4229, Garlock Street
                  Sherbrooke (Quebec)
                  Canada
                  Phone: (819) 829-8749"
    DESCRIPTION  "This MIB contains CorNet system configuration objects for CorNet units."


    -- *************************************************************************
    -- Revision history
    -- *************************************************************************

    REVISION    "200607170000Z"
    DESCRIPTION "Added the corNetSystemServices group to manage the new HiPath 4000
                 services."
    REVISION    "200512020000Z"
    DESCRIPTION "Add the variable corNetSystemDataVoiceOnlyModeEnable."
    REVISION    "200507070000Z"
    DESCRIPTION "Add the variable corNetSystemDataRfc2833DefaultPayloadType and
                 corNetSystemDataRfc2198DefaultPayloadType."
    REVISION    "200506270000Z"
    DESCRIPTION "Modify the description of the corNetSystemSecurityPassword.
                 Added corNetSystemSecurityLevel and corNetSystemDataIfTable."
    REVISION    "200506100000Z"
    DESCRIPTION "Modified description of corNetSystemFaultManagementTrapsMaximumPacketsLostRatio."
    REVISION    "200505160000Z"
    DESCRIPTION "Added corNetSystemSecurityIfTable."
    REVISION    "200505060000Z"
    DESCRIPTION "Added:
                      corNetSystemFaultManagementTrapsEnable,
                      corNetSystemFaultManagementTrapsReportDelay,
                      corNetSystemFaultManagementTrapsComputePeriod,
                      corNetSystemFaultManagementTrapsMaximumPacketsLostRatio,
                      corNetSystemFaultManagementTrapsMaximumJitterBufferOverrunRatio,
                      corNetSystemFaultManagementTrapsMaximumJitterBufferUnderrunRatio,
                      ipAddressConfigCorNetFaultManagementHost,
                      ipAddressConfigCorNetFaultManagementTrapPort,
                      ipAddressStatusCorNetFaultManagementHost,
                      ipAddressStatusCorNetFaultManagementTrapPort,
                      corNetFaultManagementJitterBufferStatus,
                      corNetFaultManagementPacketsLostStatus,
                      corNetFaultManagementRebootTrap,
                      corNetFaultManagementAuthenticationFailureTrap,
                      corNetFaultManagementLanTrap,
                      corNetFaultManagementPacketsLostTrap,
                      corNetFaultManagementJitterBufferTrap
                      "
    REVISION    "200406150000Z"
    DESCRIPTION "Creation."
    ::= { corNet 1 }

corNetSystemMIBObjects  OBJECT IDENTIFIER ::= { corNetSystemMIB 1 }
corNetSystemConformance OBJECT IDENTIFIER ::= { corNetSystemMIB 2 }
corNetSystemEvents OBJECT IDENTIFIER ::= { corNetSystemMIB 3 }

    -- *************************************************************************
    -- CorNet system registration
    -- *************************************************************************
    corNetSystemRegistration OBJECT IDENTIFIER ::= { corNetSystemMIBObjects 10 }

        corNetSystemRegistrationIfTable OBJECT-TYPE
        SYNTAX      SEQUENCE OF CorNetSystemRegistrationIfEntry
        MAX-ACCESS  not-accessible
        STATUS      current
        DESCRIPTION "This table holds configuration for the registration of CorNet units. Each row
                     is used to configure a single line of the unit."
        ::= { corNetSystemRegistration 10 }

        corNetSystemRegistrationIfEntry OBJECT-TYPE
            SYNTAX      CorNetSystemRegistrationIfEntry
            MAX-ACCESS  not-accessible
            STATUS      current
            DESCRIPTION "Each row is used to configure the registration of a single line."
            INDEX       { ifIndex }
            ::= { corNetSystemRegistrationIfTable 1 }

            CorNetSystemRegistrationIfEntry ::= SEQUENCE
                {
                    corNetSystemRegSubscriberNumber OCTET STRING,
                    corNetSystemRegLocationIdentifierNumber OCTET STRING
                }

        corNetSystemRegSubscriberNumber OBJECT-TYPE
            SYNTAX      OCTET STRING (SIZE (0..20))
            MAX-ACCESS  read-write
            STATUS      current
            DESCRIPTION "The E.164 alias of the line. Each line must be configured with a unique
                         Subscriber Number. The Subscriber Number can’t be left empty.

                         The line of the CorNet unit provides its Subscriber Number to the CorNet PBX
                         during the registration process."
            DEFVAL { "" }
            ::=  {  corNetSystemRegistrationIfEntry 10 }

        corNetSystemRegLocationIdentifierNumber OBJECT-TYPE
            SYNTAX      OCTET STRING (SIZE (0..20))
            MAX-ACCESS  read-write
            STATUS      current
            DESCRIPTION "The Location Identifier Number describes the physical location of the CorNet
                         unit line. The CorNet PBX uses this information to route emergency calls. The
                         Location Identification Number may be left empty.

                         The line provides its Location Identifier Number to the CorNet PBX during the
                         registration process.

                         If the line provides a Location Identifier Number to the CorNet PBX, the CorNet
                         PBX uses this information to route emergency calls.

                         If the line doesn’t provide a Location Identifier Number to the CorNet PBX, the
                         CorNet PBX doesn’t guarantee the correct routing of emergency calls."
            DEFVAL { "" }
            ::=  {  corNetSystemRegistrationIfEntry 20 }


    -- *************************************************************************
    -- CorNet system initialization
    -- *************************************************************************
    corNetSystemInitialization OBJECT IDENTIFIER ::= { corNetSystemMIBObjects 20 }

        corNetSystemInitializationIfTable OBJECT-TYPE
        SYNTAX      SEQUENCE OF CorNetSystemInitializationIfEntry
        MAX-ACCESS  not-accessible
        STATUS      current
        DESCRIPTION "This table holds configuration for the initialization of CorNet units. Each row
                     is used to configure a single line of the unit."
        ::= { corNetSystemInitialization 10 }

        corNetSystemInitializationIfEntry OBJECT-TYPE
            SYNTAX      CorNetSystemInitializationIfEntry
            MAX-ACCESS  not-accessible
            STATUS      current
            DESCRIPTION "Each row is used to configure the initialization of a single line."
            INDEX       { ifIndex }
            ::= { corNetSystemInitializationIfTable 1 }

            CorNetSystemInitializationIfEntry ::= SEQUENCE
                {
                    corNetSystemInitEmergencyNumber OCTET STRING
                }

        corNetSystemInitEmergencyNumber OBJECT-TYPE
            SYNTAX      OCTET STRING (SIZE (0..20))
            MAX-ACCESS  read-write
            STATUS      current
            DESCRIPTION "The Emergency Number is used by the CorNet PBX to route emergency calls. The
                         Emergency Number may be left empty.

                         The line provides its Emergency Number to the CorNet PBX during the
                         initialization process.

                         If the line provides an Emergency Number to the CorNet PBX, the CorNet PBX uses
                         this information to route emergency calls.

                         If the line doesn’t provide an Emergency Number to the CorNet PBX, the CorNet
                         PBX doesn’t guarantee the correct routing of emergency calls."
            DEFVAL { "" }
            ::=  {  corNetSystemInitializationIfEntry 10 }


    -- *************************************************************************
    -- CorNet system security
    -- *************************************************************************
    corNetSystemSecurity OBJECT IDENTIFIER ::= { corNetSystemMIBObjects 25 }

        corNetSystemSecurityIfTable OBJECT-TYPE
        SYNTAX      SEQUENCE OF CorNetSystemSecurityIfEntry
        MAX-ACCESS  not-accessible
        STATUS      current
        DESCRIPTION "This table holds the configuration for the security of CorNet units. Each row
                     is used to configure a single line of the unit."
        ::= { corNetSystemSecurity 10 }

        corNetSystemSecurityIfEntry OBJECT-TYPE
            SYNTAX      CorNetSystemSecurityIfEntry
            MAX-ACCESS  not-accessible
            STATUS      current
            DESCRIPTION "Each row is used to configure the security of a single line."
            INDEX       { ifIndex }
            ::= { corNetSystemSecurityIfTable 1 }

            CorNetSystemSecurityIfEntry ::= SEQUENCE
                {
                    corNetSystemSecurityPassword OCTET STRING,
                    corNetSystemSecurityLevel INTEGER
                }

        corNetSystemSecurityPassword OBJECT-TYPE
            SYNTAX      OCTET STRING (SIZE (0..20))
            MAX-ACCESS  read-write
            STATUS      current
            DESCRIPTION "The security password used by an endpoint.

                         The security is used in:
                          - Authentication of CorNet registration.
                          - Message integrity of CorNet signaling.
                          - H.235 security in H.323 signaling.

                         The endpoint does not use security when this field is empty."
            DEFVAL { "" }
            ::=  {  corNetSystemSecurityIfEntry 10 }

        corNetSystemSecurityLevel OBJECT-TYPE
            SYNTAX      INTEGER {
                                    none(0),
                                    reduced(1),
                                    full(2)
                                }
            MAX-ACCESS  read-write
            STATUS      current
            DESCRIPTION "The security level used by an endpoint:

                         none (0): The endpoint doesn't use security.

                         reduced (1): The endpoint uses the reduced security profile. In this
                         profile, the endpoint uses authentication in the CorNet registration,
                         message integrity in outgoing CorNet signaling and H.235 security
                         in H.323 signaling.

                         full (2): The endpoint uses the full security profile. In this
                         profile, the endpoint uses authentication in the CorNet registration,
                         message integrity in outgoing/incoming CorNet signaling and H.235
                         security in H.323 signaling.

                         The endpoint uses security level 'none (0)' when the variable
                         corNetSystemSecurityPassword is empty."
            DEFVAL { none }
            ::=  {  corNetSystemSecurityIfEntry 50 }


    -- *************************************************************************
    -- CorNet system Fault Management
    -- *************************************************************************

    corNetSystemFaultManagement OBJECT IDENTIFIER ::= { corNetSystemMIBObjects 30 }

         --
         -- CorNet system Fault Management Traps Configuration
         --

            corNetSystemFaultManagementTrapsEnable OBJECT-TYPE
                SYNTAX      MxEnableState
                MAX-ACCESS  read-write
                STATUS      current
                DESCRIPTION "When enabled, the Fault Management traps are sent to
                             the Fault Management Host whenever a defined trigger is hit."
                DEFVAL { enable }
                ::=  {  corNetSystemFaultManagement 10 }

            corNetSystemFaultManagementTrapsComputePeriod OBJECT-TYPE
                SYNTAX      Unsigned32 (1..30)
                MAX-ACCESS  read-write
                STATUS      current
                DESCRIPTION "Indicates the interval at which a faulty condition is computed.

                             For example, the packets lost ratio is computed after each
                             corNetSystemFaultManagementTrapsComputePeriod. If the packets lost ratio
                             is greater than corNetSystemFaultManagementtrapsMaximumPacketsLostRatio
                             then a SNMP trap is sent to the Fault Management Host.
                             The same trap will not be sent again to the Fault Management Host until
                             the corNetSystemFaultManagementTrapsReportDelay elapses.

                             This value is expressed in seconds (s).
                             "
                DEFVAL { 5 }
                ::=  {  corNetSystemFaultManagement 20 }

            corNetSystemFaultManagementTrapsReportDelay OBJECT-TYPE
                SYNTAX      Unsigned32 (1..60)
                MAX-ACCESS  read-write
                STATUS      current
                DESCRIPTION "Indicates the time to wait before a given trap is sent again to indicate either:

                             - the faulty condition is still present.
                             - the faulty condition is not present anymore.

                             This value is expressed in minutes (min)."
                DEFVAL { 1 }
                ::=  {  corNetSystemFaultManagement 30 }

            corNetSystemFaultManagementTrapsMaximumPacketsLostRatio OBJECT-TYPE
                SYNTAX      Unsigned32 (1..100)
                MAX-ACCESS  read-write
                STATUS      current
                DESCRIPTION "Indicates the maximum acceptable percentage of the ratio

                             (number of RTP packets lost) /
                             (number of RTP packets received + number of RTP packets lost during a corNetSystemFaultManagementTrapsComputePeriod)

                             before a packet lost trap is sent to the Fault Management Host.

                             This value is expressed in percentage (%)."
                DEFVAL { 1 }
                ::=  {  corNetSystemFaultManagement 40 }

            corNetSystemFaultManagementTrapsMaximumJitterBufferOverrunRatio OBJECT-TYPE
                SYNTAX      Unsigned32 (1..100)
                MAX-ACCESS  read-write
                STATUS      current
                DESCRIPTION "Indicates the maximum acceptable percentage of the ratio

                             (time duration the jitter buffer is overrunning) /
                             (corNetSystemFaultManagementTrapsComputePeriod)

                             before a jitter buffer trap is sent to the Fault Management Host.

                             This value is expressed in percentage (%). "
                DEFVAL { 1 }
                ::=  {  corNetSystemFaultManagement 50 }

            corNetSystemFaultManagementTrapsMaximumJitterBufferUnderrunRatio OBJECT-TYPE
                SYNTAX      Unsigned32 (1..100)
                MAX-ACCESS  read-write
                STATUS      current
                DESCRIPTION "Indicates the maximum acceptable percentage of the ratio

                             (time duration the jitter buffer is underrunning) /
                             (corNetSystemFaultManagementTrapsComputePeriod)

                             before a jitter buffer trap is sent to the Fault Management Host.

                             This value is expressed in percentage (%)."
                DEFVAL { 1 }
                ::=  {  corNetSystemFaultManagement 60 }

    -- *************************************************************************
    -- CorNet system data
    -- *************************************************************************

    corNetSystemData OBJECT IDENTIFIER ::= { corNetSystemMIBObjects 50 }

        corNetSystemDataIfTable OBJECT-TYPE
        SYNTAX      SEQUENCE OF CorNetSystemDataIfEntry
        MAX-ACCESS  not-accessible
        STATUS      current
        DESCRIPTION "This table holds the configuration for the data of CorNet units. Each row
                     is used to configure a single line of the unit."
        ::= { corNetSystemData 10 }

        corNetSystemDataIfEntry OBJECT-TYPE
            SYNTAX      CorNetSystemDataIfEntry
            MAX-ACCESS  not-accessible
            STATUS      current
            DESCRIPTION "Each row is used to configure the data of a single line."
            INDEX       { ifIndex }
            ::= { corNetSystemDataIfTable 1 }

            CorNetSystemDataIfEntry ::= SEQUENCE
                {
                    corNetSystemDataRfc2198RedundancyLevel Unsigned32,
                    corNetSystemDataRfc2198DefaultPayloadType Unsigned32,
                    corNetSystemDataRfc2833DefaultPayloadType Unsigned32,
                    corNetSystemDataVoiceOnlyModeEnable MxEnableState
                }

        corNetSystemDataRfc2198RedundancyLevel OBJECT-TYPE
            SYNTAX      Unsigned32 (0..5)
            MAX-ACCESS  read-write
            STATUS      current
            DESCRIPTION "Sets the redundancy level used in the RFC 2198.

                         This variable is used to duplicate the RFC 2833 fax/modem tones."
            DEFVAL { 0 }
            ::=  {  corNetSystemDataIfEntry 50 }

        corNetSystemDataRfc2198DefaultPayloadType OBJECT-TYPE
                SYNTAX      Unsigned32 (96..127)
                MAX-ACCESS  read-write
                STATUS      current
                DESCRIPTION "Default payload type used for RFC 2198.  This payload type is applied
                             for both receiving and sending packets.

                             The RFC 2198 is only enable if:
                             1) The RFC 2833 is enabled.  The redundancy is only applied to duplicate
                                the RFC 2833 fax/modem tones.
                             2) The remote entity supports the RFC 2198."
                DEFVAL      { 99 }
                ::= { corNetSystemDataIfEntry 70 }

        corNetSystemDataRfc2833DefaultPayloadType OBJECT-TYPE
                SYNTAX      Unsigned32 (96..127)
                MAX-ACCESS  read-write
                STATUS      current
                DESCRIPTION "This variable sets the payload type of the RFC 2833 events that is supported
                             by the unit.  This value will be inserted in the dynamicRTPPayloadType field
                             in the H.225 TerminalCapabilitySet message.

                             For example,

                             CASE 1:

                             1)    If corNetSystemDataRfc2833DefaultPayloadType = 98
                             2)    If dynamicRTPPayloadType = 101

                             The unit will send RFC 2833 events with payload type 101.  Also, the unit
                             will decode a RFC 2833 event with payload type 98.

                             CASE 2:

                             1)    If corNetSystemDataRfc2833DefaultPayloadType = 98
                             2)    If dynamicRTPPayloadType is not found in the received H.225
                                   TerminalCapabilitySet message.

                             The RFC 2833 will be disabled in the unit."
                DEFVAL      { 98 }
                ::= { corNetSystemDataIfEntry 90 }

        corNetSystemDataVoiceOnlyModeEnable OBJECT-TYPE
                SYNTAX      MxEnableState
                MAX-ACCESS  read-write
                STATUS      current
                DESCRIPTION "This variable defines whether the fax/modem tone is detected or not.

                             enable: Fax/Modem tones will not be detected (voice only);
                             disable: Fax/Modem tones will be detected (voice/fax/modem)."
                DEFVAL      { disable }
                ::= { corNetSystemDataIfEntry 150 }

    -- *************************************************************************
    -- CorNet system Services
    -- *************************************************************************

    corNetSystemServices OBJECT IDENTIFIER ::= { corNetSystemMIBObjects 100 }

        corNetSystemServicesTable OBJECT-TYPE
        SYNTAX      SEQUENCE OF CorNetSystemServicesEntry
        MAX-ACCESS  not-accessible
        STATUS      current
        DESCRIPTION "This table holds the parameters defining access to the services offered
                     by the CorNet gatekeeper, indexed by service entry number.

                     Note that these services are only recognized when the
                     corNetSystemCallFeaturesEnable variable is enabled."
        ::= { corNetSystemServices 100 }

        corNetSystemServicesEntry OBJECT-TYPE
            SYNTAX      CorNetSystemServicesEntry
            MAX-ACCESS  not-accessible
            STATUS      current
            DESCRIPTION "Each row is used to configure a single service."
            INDEX       {
                            corNetSystemServicesIndex
                        }
            ::= { corNetSystemServicesTable 1 }

            CorNetSystemServicesEntry ::= SEQUENCE
                {
                    corNetSystemServicesIndex             Unsigned32,
                    corNetSystemServiceName               OCTET STRING,
                    corNetSystemServiceEnable             MxEnableState,
                    corNetSystemServiceKbKeyCode          Unsigned32,
                    corNetSystemServiceActivationSequence OCTET STRING,
                    corNetSystemService2StageFlag         INTEGER,
                    corNetSystemServiceFirstDigitTimer    Unsigned32
                }

            corNetSystemServicesIndex OBJECT-TYPE
                SYNTAX  Unsigned32 (1..10)
                MAX-ACCESS  read-only
                STATUS      current
                DESCRIPTION "Accepted service index for this row."
                ::= { corNetSystemServicesEntry 5 }

            corNetSystemServiceName OBJECT-TYPE
                SYNTAX  OCTET STRING (SIZE(0..127))
                MAX-ACCESS  read-write
                STATUS      current
                DESCRIPTION "A character string identifying the service.
                             Only used for display purposes in the configuration
                             interface."
                DEFVAL      { "" }
                ::= { corNetSystemServicesEntry 10 }

            corNetSystemServiceEnable OBJECT-TYPE
                SYNTAX      MxEnableState
                MAX-ACCESS  read-write
                STATUS      current
                DESCRIPTION "Used to activate/deactivate the corresponding service."
                DEFVAL { disable }
                ::=  {  corNetSystemServicesEntry 15 }

            corNetSystemServiceKbKeyCode OBJECT-TYPE
                SYNTAX  Unsigned32 (0..63)
                MAX-ACCESS  read-write
                STATUS      current
                DESCRIPTION "The feature code identifying the service in
                             the CorNet server."
                DEFVAL { 0 }
                ::= { corNetSystemServicesEntry 20 }

            corNetSystemServiceActivationSequence OBJECT-TYPE
                SYNTAX  OCTET STRING (SIZE(0..63))
                MAX-ACCESS  read-write
                STATUS      current
                DESCRIPTION "A string making up a digit map that the user needs to
                             dial when requesting the service.
                             The formal digit map syntax, as summarized here, is taken from
                             RFC 2705:

                             DigitMap = DigitString  / '(' DigitStringList ')'
                             DigitStringList = DigitString 0*( '|' DigitString )
                             DigitString = 1*(DigitStringElement)
                             DigitStringElement = DigitPosition ['.']
                             DigitPosition = DigitMapLetter / DigitMapRange
                             DigitMapLetter = DIGIT / '#' / '*' / 'A' / 'B' / 'C' / 'D' / 'T'
                             DigitMapRange =  'x' / '[' 1*DigitLetter ']'
                             DigitLetter ::= *((DIGIT '-' DIGIT ) / DigitMapLetter)

                             where 'x' means 'any digit' and '.' means 'any occurrence of the
                             previous element'."
                DEFVAL      { "" }
                ::= { corNetSystemServicesEntry 25 }

            corNetSystemService2StageFlag OBJECT-TYPE
                SYNTAX  INTEGER {
                             no(0),
                             yes(1)
                            }
                MAX-ACCESS  read-write
                STATUS      current
                DESCRIPTION "The boolean flag used to distinguish between the services
                             that only require the user to enter the activation sequence
                             and those which necessitate further dialling from the user
                             once the server has responded to the service request.

                             no: The dialling of the activation sequence is all that is needed
                                 to request the service.

                             yes: Following the service request, the server signals
                                  the user and awaits the entry of further data.  These
                                  services make use of the corNetSystemServices2StageEndingMethod,
                                  corNetSystemServices2StageTimeout and corNetSystemServices2StageEndKey
                                  variables to establish how the end of second stage dialling is detected."
                DEFVAL      { no }
                ::= { corNetSystemServicesEntry 30 }

            corNetSystemServiceFirstDigitTimer OBJECT-TYPE
                SYNTAX  Unsigned32 (1000..180000)
                MAX-ACCESS   read-write
                STATUS       current
                DESCRIPTION "Applies to the second stage of two-stage services.
                             This is the amount of time to wait (in milliseconds) for user input
                             while in the second stage of a service request.  If the delay expires,
                             the service request is cancelled altogether.  This avoids
                             waiting forever after the user has dialled an activation
                             sequence for a two-stage service."
                DEFVAL      { 20000 }
                ::= { corNetSystemServicesEntry 35 }

    -- *************************************************************************
    -- CorNet System Services global parameters
    -- *************************************************************************
    corNetSystemCallFeaturesEnable OBJECT-TYPE
        SYNTAX      MxEnableState
        MAX-ACCESS  read-write
        STATUS      current
        DESCRIPTION "This is the master switch to enable all service requests.
                     When enabled, the dialled DTMFs are compared against the activation
                     sequences contained in corNetSystemServicesTable.  If a match is found,
                     the corresponding feature code is sent to the gatekeeper via a
                     KB_KEY request.
                     When disabled, or if no match can be found, each DTMF dialled is
                     blindly relayed to the gatekeeper."
        DEFVAL { disable }
        ::=  {  corNetSystemServices 150 }

    corNetSystemServices2StageEndingMethod OBJECT-TYPE
        SYNTAX  INTEGER {
                     timer(0),
                     endCharacter(1)
                    }
        MAX-ACCESS  read-write
        STATUS      current
        DESCRIPTION "The method that will be used to determine that second stage dialling
                     is complete.  After this point, any DTMF entered will be sent in-band.

                     timer: Second stage dialling will end when a period of time equal
                            to that specified in corNetSystemServices2StageTimeout elapses
                            without any keys being pressed.

                     endCharacter: Second stage dialling will end as soon as the character
                                   contained in corNetSystemServices2StageEndKey is
                                   entered by the user."
        DEFVAL      { timer }
        ::= { corNetSystemServices 200 }

    corNetSystemServices2StageTimeout OBJECT-TYPE
        SYNTAX  Unsigned32 (500..10000)
        MAX-ACCESS   read-write
        STATUS       current
        DESCRIPTION "The amount of time to wait (in milliseconds) after a DTMF entry
                     before deciding that 2nd stage dialling is over."
        DEFVAL      { 4000 }
        ::= { corNetSystemServices 250 }

    corNetSystemServices2StageEndKey OBJECT-TYPE
        SYNTAX  OCTET STRING (SIZE(1..1))
        MAX-ACCESS  read-write
        STATUS      current
        DESCRIPTION "The DTMF key that will end all second stage dialling sequences."
        DEFVAL      { "#" }
        ::= { corNetSystemServices 300 }

    corNetSystemServicesTimeoutInterDigit OBJECT-TYPE
        SYNTAX  Unsigned32 (500..10000)
        MAX-ACCESS   read-write
        STATUS       current
        DESCRIPTION "The timeout associated with the 'T' character in the digit maps
                     contained in corNetSystemServiceActivationSequence strings.
                     (see the definition of corNetSystemServicesTable)

                     The 'T' digit is used to express a time lapse between the detection of two DTMFs.

                     This value is expressed in milliseconds (ms)."
        DEFVAL      { 4000 }
        ::= { corNetSystemServices 350 }

    -- *************************************************************************
    -- CorNet Fault Management status
    -- *************************************************************************
    corNetFaultManagementStatus OBJECT IDENTIFIER ::= { mediatrixMgmt 80 }

        corNetFaultManagementPacketsLostStatus OBJECT-TYPE
            SYNTAX      INTEGER {
                                    normal(0),
                                    error(1)
                                }
            MAX-ACCESS  read-only
            STATUS      current
            DESCRIPTION "
                         Indicates if the corNetSystemFaultManagementTrapsMaximumPacketsLostRatio
                         is exceeded ( error(1) ) or if it is within normal value ( normal(0) ).

                         "
            DEFVAL { normal }
            ::=  {  corNetFaultManagementStatus 5 }

        corNetFaultManagementJitterBufferStatus OBJECT-TYPE
            SYNTAX      INTEGER {
                                    normal(0),
                                    overrun(1),
                                    underrun(2)
                                }
            MAX-ACCESS  read-only
            STATUS      current
            DESCRIPTION "
                         Indicates if the
                         corNetSystemFaultManagementTrapsMaximumJitterBufferOverrunRatio is exceeded
                         ( overrun(1) ) or if
                         corNetSystemFaultManagementTrapsMaximumJitterBufferUnderrunRatio is exceeded
                         ( underrun(2) ) or if
                         it is within normal value ( normal(0) ).
                         "
            DEFVAL { normal }
            ::=  {  corNetFaultManagementStatus 10 }


    -- *************************************************************************
    -- CorNet IP address status
    -- *************************************************************************
    ipAddressStatusCorNetPbxIfTable OBJECT-TYPE
        SYNTAX      SEQUENCE OF IpAddressStatusCorNetPbxIfEntry
        MAX-ACCESS  not-accessible
        STATUS      current
        DESCRIPTION "This table holds the actual configuration used by the lines to register with a
                     CorNet PBX."
        ::= { ipAddressStatusCorNet 10 }

        ipAddressStatusCorNetPbxIfEntry OBJECT-TYPE
            SYNTAX      IpAddressStatusCorNetPbxIfEntry
            MAX-ACCESS  not-accessible
            STATUS      current
            DESCRIPTION "Each row holds the IP address and the CorNet signaling port of a CorNet PBX. The
                         line is actually using this configuration to register with a CorNet PBX."
            INDEX       { ifIndex }
            ::= { ipAddressStatusCorNetPbxIfTable 1 }

            IpAddressStatusCorNetPbxIfEntry ::= SEQUENCE
                {
                    ipAddressStatusCorNetPbxHost MxIpHostName,
                    ipAddressStatusCorNetPbxPort MxIpPort
                }

            ipAddressStatusCorNetPbxHost OBJECT-TYPE
                SYNTAX      MxIpHostName
                MAX-ACCESS  read-only
                STATUS      current
                DESCRIPTION "The IP address or domain name of the CorNet PBX to which the line is
                             configured to register."
                DEFVAL { "" }
                ::=  {  ipAddressStatusCorNetPbxIfEntry 10 }

            ipAddressStatusCorNetPbxPort OBJECT-TYPE
                SYNTAX      MxIpPort
                MAX-ACCESS  read-only
                STATUS      current
                DESCRIPTION "The CorNet signaling port of the CorNet PBX to which the line is
                             configured to register."
                DEFVAL { 4060 }
                ::=  { ipAddressStatusCorNetPbxIfEntry 20 }

    -- *******************************************
    -- CorNet Fault Management ip Address Status
    -- *******************************************

            ipAddressStatusCorNetFaultManagementHost OBJECT-TYPE
                SYNTAX      MxIpHostName
                MAX-ACCESS  read-only
                STATUS      current
                DESCRIPTION "The IP address or domain name of the CorNet Fault Management Host
                             to which SNMP traps related to the Fault Management are sent."
                DEFVAL { "" }
                ::=  {  ipAddressStatusCorNet 20 }

            ipAddressStatusCorNetFaultManagementTrapPort OBJECT-TYPE
                SYNTAX      MxIpPort
                MAX-ACCESS  read-only
                STATUS      current
                DESCRIPTION "The CorNet Fault Management Host IP port on which the
                             SNMP traps related to the Fault Management are sent."
                DEFVAL { 162 }
                ::=  { ipAddressStatusCorNet 30 }

    -- *************************************************************************
    -- CorNet IP address config
    -- *************************************************************************
    ipAddressConfigCorNetPbxIfTable OBJECT-TYPE
        SYNTAX      SEQUENCE OF IpAddressConfigCorNetPbxIfEntry
        MAX-ACCESS  not-accessible
        STATUS      current
        DESCRIPTION "This table holds the configuration for the registration of the lines with a
                     CorNet PBX."
        ::= { ipAddressConfigCorNetStatic 10 }

        ipAddressConfigCorNetPbxIfEntry OBJECT-TYPE
            SYNTAX      IpAddressConfigCorNetPbxIfEntry
            MAX-ACCESS  not-accessible
            STATUS      current
            DESCRIPTION "Each row is used to configure the IP address and the CorNet signaling port of a
                         CorNet PBX. The line uses this configuration to register with a CorNet PBX."
            INDEX       { ifIndex }
            ::= { ipAddressConfigCorNetPbxIfTable 1 }

            IpAddressConfigCorNetPbxIfEntry ::= SEQUENCE
                {
                    ipAddressConfigCorNetPbxHost MxIpHostName,
                    ipAddressConfigCorNetPbxPort MxIpPort
                }

            ipAddressConfigCorNetPbxHost OBJECT-TYPE
                SYNTAX      MxIpHostName
                MAX-ACCESS  read-write
                STATUS      current
                DESCRIPTION "The IP address or domain name of the CorNet PBX to which the line registers."
                DEFVAL { "" }
                ::=  {  ipAddressConfigCorNetPbxIfEntry 10 }

            ipAddressConfigCorNetPbxPort OBJECT-TYPE
                SYNTAX      MxIpPort
                MAX-ACCESS  read-write
                STATUS      current
                DESCRIPTION "The CorNet signaling port used by the CorNet PBX."
                DEFVAL { 4060 }
                ::=  {  ipAddressConfigCorNetPbxIfEntry 20 }

    -- *******************************************
    -- CorNet Fault Management IP address config
    -- *******************************************

            ipAddressConfigCorNetFaultManagementHost OBJECT-TYPE
                SYNTAX      MxIpHostName
                MAX-ACCESS  read-write
                STATUS      current
                DESCRIPTION "The IP address or domain name of the CorNet Fault Management Host
                             to which SNMP traps related to the Fault Management are sent."
                DEFVAL { "" }
                ::=  {  ipAddressConfigCorNetStatic 20 }

            ipAddressConfigCorNetFaultManagementTrapPort OBJECT-TYPE
                SYNTAX      MxIpPort
                MAX-ACCESS  read-write
                STATUS      current
                DESCRIPTION "The CorNet Fault Management Host IP port on which the
                             SNMP traps related to the Fault Management are sent."
                DEFVAL { 162 }
                ::=  {  ipAddressConfigCorNetStatic 30 }

    -- *************************************************************************
    -- Conformance information
    -- *************************************************************************
    corNetSystemCompliances OBJECT IDENTIFIER ::= { corNetSystemConformance 1 }

        corNetSystemBasicComplVer1 MODULE-COMPLIANCE
            STATUS      current
            DESCRIPTION "This is a list of conformance groups. These conformance groups contain the name
                         of objects necessary to adequately configure a CorNet unit."
            MODULE      -- MX-CORNET-SYSTEM-MIB
            MANDATORY-GROUPS {
                               corNetSystemRegistrationGroupVer1,
                               corNetSystemInitializationGroupVer1,
                               corNetSystemSecurityGroupVer1,
                               corNetSystemFaultManagementGroupVer1,
                               corNetSystemDataGroupVer1,
                               corNetSystemServicesGroupVer1
                             }
            ::= { corNetSystemCompliances 5 }

    -- *************************************************************************
    -- MIB variable grouping
    -- *************************************************************************
    corNetSystemGroups OBJECT IDENTIFIER ::= { corNetSystemConformance 2 }

        corNetSystemRegistrationGroupVer1 OBJECT-GROUP
            OBJECTS {
                      corNetSystemRegSubscriberNumber,
                      corNetSystemRegLocationIdentifierNumber
                    }
            STATUS      current
            DESCRIPTION "A list of objects used to configure the registration of a CorNet unit."
            ::= { corNetSystemGroups 5 }

        corNetSystemInitializationGroupVer1 OBJECT-GROUP
            OBJECTS {
                      corNetSystemInitEmergencyNumber
                    }
            STATUS      current
            DESCRIPTION "A list of objects used to configure the initialization of a CorNet unit."
            ::= { corNetSystemGroups 10 }

        corNetSystemSecurityGroupVer1 OBJECT-GROUP
            OBJECTS {
                      corNetSystemSecurityPassword,
                      corNetSystemSecurityLevel
                    }
            STATUS      current
            DESCRIPTION "A list of objects used to configure the security of a CorNet unit."
            ::= { corNetSystemGroups 13 }

       corNetSystemFaultManagementGroupVer1 OBJECT-GROUP
            OBJECTS {
                      corNetSystemFaultManagementTrapsEnable,
                      corNetSystemFaultManagementTrapsComputePeriod,
                      corNetSystemFaultManagementTrapsReportDelay,
                      corNetSystemFaultManagementTrapsMaximumPacketsLostRatio,
                      corNetSystemFaultManagementTrapsMaximumJitterBufferOverrunRatio,
                      corNetSystemFaultManagementTrapsMaximumJitterBufferUnderrunRatio,
                      corNetFaultManagementPacketsLostStatus,
                      corNetFaultManagementJitterBufferStatus,
                      ipAddressConfigCorNetFaultManagementHost,
                      ipAddressConfigCorNetFaultManagementTrapPort,
                      ipAddressStatusCorNetFaultManagementHost,
                      ipAddressStatusCorNetFaultManagementTrapPort
                    }
            STATUS      current
            DESCRIPTION "A list of objects used to configure the fault management of a CorNet unit."
            ::= { corNetSystemGroups 15 }

       corNetSystemFaultManagementNotificationsGroupVer1 NOTIFICATION-GROUP
            NOTIFICATIONS {
                            corNetFaultManagementRebootTrap,
                            corNetFaultManagementAuthenticationFailureTrap,
                            corNetFaultManagementLanTrap,
                            corNetFaultManagementPacketsLostTrap,
                            corNetFaultManagementJitterBufferTrap
                         }
            STATUS      current
            DESCRIPTION "A list of objects necessary to realize the Notification for the Fault Management."
            ::= { corNetSystemGroups 20 }

       corNetSystemDataGroupVer1 OBJECT-GROUP
            OBJECTS {
                      corNetSystemDataRfc2198RedundancyLevel,
                      corNetSystemDataRfc2198DefaultPayloadType,
                      corNetSystemDataRfc2833DefaultPayloadType,
                      corNetSystemDataVoiceOnlyModeEnable
                    }
            STATUS      current
            DESCRIPTION "A list of objects used to configure the data of a CorNet unit."
            ::= { corNetSystemGroups 50 }

       corNetSystemServicesGroupVer1 OBJECT-GROUP
            OBJECTS {
                      corNetSystemServicesIndex,
                      corNetSystemServiceName,
                      corNetSystemServiceEnable,
                      corNetSystemServiceKbKeyCode,
                      corNetSystemServiceActivationSequence,
                      corNetSystemService2StageFlag,
                      corNetSystemServiceFirstDigitTimer,
                      corNetSystemCallFeaturesEnable,
                      corNetSystemServices2StageEndingMethod,
                      corNetSystemServices2StageTimeout,
                      corNetSystemServices2StageEndKey,
                      corNetSystemServicesTimeoutInterDigit
                    }
            STATUS      current
            DESCRIPTION "A list of objects used to configure the data of a CorNet unit."
            ::= { corNetSystemGroups 100 }

    -- *************************************************************************
    -- CorNet System Events
    -- *************************************************************************
    corNetSystemFaultManagementNotifications OBJECT IDENTIFIER ::= { corNetSystemEvents 5 }

        --
        -- CorNet system Fault Management Traps
        --

            corNetFaultManagementRebootTrap NOTIFICATION-TYPE
                OBJECTS     {
                                sysObjectID,
                                sysMacAddress
                            }
                STATUS      current
                DESCRIPTION "Indicates to the Fault Management Host that the unit has rebooted
                             This trap includes the sysObjectID and sysMacAddress."
                ::= { corNetSystemFaultManagementNotifications 1050 }

            corNetFaultManagementAuthenticationFailureTrap NOTIFICATION-TYPE
                OBJECTS     {
                                sysObjectID,
                                sysMacAddress
                            }
                STATUS      current
                DESCRIPTION "Indicates to the Fault Management Host that an SNMP authentication failure
                             occurred.  This trap includes the sysObjectID and sysMacAddress."
                ::= { corNetSystemFaultManagementNotifications 1150 }

            corNetFaultManagementLanTrap NOTIFICATION-TYPE
                OBJECTS     {
                                sysObjectID,
                                sysMacAddress
                            }
                STATUS      current
                DESCRIPTION "Indicates to the Fault Management Host that the LAN error was detected.
                             This trap includes the sysObjectID and the sysMacAddress."
                ::= { corNetSystemFaultManagementNotifications 1250 }

            corNetFaultManagementPacketsLostTrap NOTIFICATION-TYPE
                OBJECTS     {
                                sysObjectID,
                                sysMacAddress,
                                corNetFaultManagementPacketsLostStatus
                            }
                STATUS      current
                DESCRIPTION "Indicates to the Fault Management Host that:

                               1) the corNetSystemFaultManagementTrapsMaximumPacketsLostRatio
                                  has been exceeded.

                                                       OR

                               2) the RTP packets lost ratio returns within the normal limit (i.e. under the
                                  value of corNetSystemFaultManagementTrapsMaximumPacketsLostRatio).

                             A packet lost trap indicating condition #2 is sent only if a packet lost trap
                             indicating condition #1 has been previously sent.

                             condition #1 is indicated by:
                             corNetFaultManagementPacketsLostStatus = error (1)

                             condition #2 is indicated by:
                             corNetFaultManagementPacketsLostStatus = normal (0)

                             This trap includes the sysObjectID, the sysMacAddress and the
                             corNetFaultManagementPacketsLostStatus."
                ::= { corNetSystemFaultManagementNotifications 1350 }

            corNetFaultManagementJitterBufferTrap NOTIFICATION-TYPE
                OBJECTS     {
                                sysObjectID,
                                sysMacAddress,
                                corNetFaultManagementJitterBufferStatus
                            }
                STATUS      current
                DESCRIPTION "Indicates to the Fault Management Host that:

                               1) the corNetSystemFaultManagementTrapsMaximumJitterBufferOverrunRatio
                                  has been exceeded.

                                                       OR

                               2) the corNetSystemFaultManagementTrapsMaximumJitterBufferUnderrunRatio
                                  has been exceeded.

                                                       OR

                               3) the overrun/underrun ratios return within the normal limit (i.e. under the value of
                                  corNetSystemFaultManagementTrapsMaximumJitterBufferOverrunRatio
                                  and corNetSystemFaultManagementTrapsMaximumJitterBufferUnderrunRatio).

                             A jitter buffer trap indicating condition #3 is sent only if a jitter buffer trap
                             indicating condition #1 or #2 has been previously sent.

                             condition #1 is indicated by:
                             corNetFaultManagementJitterBufferStatus = overrun (1)

                             condition #2 is indicated by:
                             corNetFaultManagementJitterBufferStatus = underrun (2)

                             condition #3 is indicated by:
                             corNetFaultManagementJitterBufferStatus = normal (0)

                             This trap includes the sysObjectID, the sysMacAddress and the
                             corNetFaultManagementJitterBufferStatus."
                ::= { corNetSystemFaultManagementNotifications 1450 }


END

-- ****************************************************************************
-- ****************************************************************************
--
--  File: MX-DEBUG-MIB.my
--
--  Package: MediatrixMibs
--
-- ****************************************************************************
-- ****************************************************************************
--
--      Copyright(c) 2001-2005 Mediatrix Telecom, Inc.
--      Copyright(c) 2007 Media5 Corporation. ("Media5")
--
--  NOTICE:
--   This document contains information that is confidential and proprietary
--   to Media5.
--
--   Media5 reserves all rights to this document as well as to the Intellectual
--   Property of the document and the technology and know-how that it includes
--   and represents.
--
--   This publication cannot be reproduced, neither in whole nor in part, in
--   any form whatsoever without written prior approval by Media5.
--
--   Media5 reserves the right to revise this publication and make changes at
--   any time and without the obligation to notify any person and/or entity of
--   such revisions and/or changes.
--
-- ****************************************************************************
-- ****************************************************************************

MX-DEBUG-MIB
DEFINITIONS ::= BEGIN

IMPORTS
        MODULE-IDENTITY,
        OBJECT-TYPE,
        Unsigned32
    FROM SNMPv2-SMI
        MODULE-COMPLIANCE,
        OBJECT-GROUP
    FROM SNMPv2-CONF
        MxIpHostName,
        MxIpPort
    FROM MX-TC
        mediatrixExperimental
    FROM MX-SMI;

mxDebugMIB MODULE-IDENTITY
    LAST-UPDATED "0911270000Z"
    ORGANIZATION "Mediatrix Telecom, Inc."
    CONTACT-INFO "Mediatrix Telecom, Inc.
                  4229, Garlock Street
                  Sherbrooke (Quebec)
                  Canada
                  Phone: (819) 829-8749
                  "
    DESCRIPTION "This MIB contains debug-related objects for Mediatrix products."

    -- ************************************************************************
    -- Revision history
    -- ************************************************************************
    REVISION    "0911270000Z"
    DESCRIPTION "Added mxDebugPcmCaptureEndpointNumber variable."
    REVISION    "0808220000Z"
    DESCRIPTION "Added group of mxDebugDspStats variables."
    REVISION    "0805210000Z"
    DESCRIPTION "Modify description of mxDebugFaxRelayForDspToSyslog
                 and mxDebugFaxRelayFromDspToSyslog variables"
    REVISION    "0710240000Z"
    DESCRIPTION "Specify to refer to documentation for
                 mxDebugPcmCaptureEnable variable"
    REVISION    "0207050000Z"
    DESCRIPTION "December 7, 2005
                    Added the MIB variable:
                            pcmCaptureEnable  to mxDebugPcmCaptureEnable
                 July 5, 2002
                    Renamed signalingLog        to mxDebugSignalingLog
                            signalingLogEnable  to mxDebugSignalingLogEnable
                            signalingLogHost    to mxDebugSignalingLogHost
                            signalingLogPort    to mxDebugSignalingLogPort
                    to align with the coding guidelines
                 June 26, 2002
                    Added the OBJECT IDENTIFIERs:
                        - mxDebugFax
                    Added the MIB variables:
                        - mxDebugT38OutgoingToSyslog
                        - mxDebugT38IncomingToSyslog
                        - mxDebugFaxRelayForDspToSyslog
                        - mxDebugFaxRelayFromDspToSyslog
                    Added Conformance and OBJECT-GROUPs
                 August 03, 2001
                    Creation"
    ::= { mediatrixExperimental 5 }

mxDebugMIBObjects  OBJECT IDENTIFIER ::= { mxDebugMIB 1 }
mxDebugConformance OBJECT IDENTIFIER ::= { mxDebugMIB 2 }

mxDebugSignalingLog             OBJECT IDENTIFIER  ::= { mxDebugMIBObjects  5 }

    mxDebugSignalingLogEnable OBJECT-TYPE
        SYNTAX      INTEGER {
                              disable(0),
                              enable(1)
                            }
        MAX-ACCESS  read-write
        STATUS      current
        DESCRIPTION "Enable the logging client debugging tool for IP telephony
                     signaling."
        DEFVAL      { disable }
        ::=  {  mxDebugSignalingLog  1  }

    mxDebugSignalingLogHost OBJECT-TYPE
        SYNTAX      MxIpHostName
        MAX-ACCESS  read-write
        STATUS      current
        DESCRIPTION "Logging client IP address or domain name."
        DEFVAL { "192.168.0.10" }
        ::=  {  mxDebugSignalingLog  2 }

    mxDebugSignalingLogPort OBJECT-TYPE
        SYNTAX      MxIpPort
        MAX-ACCESS  read-write
        STATUS      current
        DESCRIPTION "Logging client IP port number."
        DEFVAL      { 6000 }
        ::=  {  mxDebugSignalingLog  3  }

    -- ********************************************************************
    -- Fax debugging
    -- ********************************************************************
mxDebugFax              OBJECT IDENTIFIER  ::= { mxDebugMIBObjects  10 }

    -- ********************************************************************
    -- T.38 debugging using syslog
    -- ********************************************************************
    mxDebugT38OutgoingToSyslog OBJECT-TYPE
        SYNTAX      INTEGER {
                              disable(0),
                              enable(1)
                            }
        MAX-ACCESS  read-write
        STATUS      current
        DESCRIPTION "Syslog T.38 outgoing data"
        DEFVAL      { disable }
        ::=  {  mxDebugFax  5  }

    mxDebugT38IncomingToSyslog OBJECT-TYPE
        SYNTAX      INTEGER {
                              disable(0),
                              enable(1)
                            }
        MAX-ACCESS  read-write
        STATUS      current
        DESCRIPTION "Syslog T.38 incoming data"
        DEFVAL { disable }
        ::=  {  mxDebugFax  6 }

    -- ********************************************************************
    -- Fax relay debugging using syslog
    -- ********************************************************************
    mxDebugFaxRelayForDspToSyslog OBJECT-TYPE
        SYNTAX      INTEGER {
                              disable(0),
                              enable(1)
                            }
        MAX-ACCESS  read-write
        STATUS      current
        DESCRIPTION "Syslog fax relay data sent to DSPs

                     This variable's semantics are different depending on
                     protocol and/or hardware platforms.
                     Please refer to the documentation shipped with your
                     device for more details."
        DEFVAL      { disable }
        ::=  {  mxDebugFax  15 }

    mxDebugFaxRelayFromDspToSyslog OBJECT-TYPE
        SYNTAX      INTEGER {
                              disable(0),
                              enable(1)
                            }
        MAX-ACCESS  read-write
        STATUS      current
        DESCRIPTION "Syslog fax relay data received from DSPs

                     This variable's semantics are different depending on
                     protocol and/or hardware platforms.
                     Please refer to the documentation shipped with your
                     device for more details."
        DEFVAL      { disable }
        ::=  {  mxDebugFax  16 }

    -- ********************************************************************
    -- PCM capture debugging
    -- ********************************************************************
mxDebugPcmCapture              OBJECT IDENTIFIER  ::= { mxDebugMIBObjects  60 }

    mxDebugPcmCaptureEnable OBJECT-TYPE
        SYNTAX      INTEGER {
                              disable(0),
                              enable(1)
                            }
        MAX-ACCESS  read-write
        STATUS      current
        DESCRIPTION "Enable PCM capture for port 1 and 2 or on the port
                     number defined in the mxDebugPcmCaptureEndpointNumber variable.

                     This variable's semantics are different depending on
                     protocol and/or hardware platforms.
                     Please refer to the documentation shipped with your
                     device for more details."
        DEFVAL      { disable }
        ::=  {  mxDebugPcmCapture  5  }

    mxDebugPcmCaptureIpAddress OBJECT-TYPE
        SYNTAX      MxIpHostName
        MAX-ACCESS  read-write
        STATUS      current
        DESCRIPTION "PCM capture client IP address."
        DEFVAL { "192.168.10.1" }
        ::=  {  mxDebugPcmCapture  10 }

    mxDebugPcmCaptureEndpointNumber OBJECT-TYPE
        SYNTAX      Unsigned32(1..65535)
        MAX-ACCESS  read-write
        STATUS      current
        DESCRIPTION "PCM capture endpoint number.

                     This variable's semantics are different depending on
                     protocol and/or hardware platforms.
                     Please refer to the documentation shipped with your
                     device for more details."
        DEFVAL { 1 }
        ::=  {  mxDebugPcmCapture  20 }

    -- ********************************************************************
    -- DSP Stats
    -- ********************************************************************
mxDebugDspStats              OBJECT IDENTIFIER  ::= { mxDebugMIBObjects  70 }

    mxDebugDspStatsEnable OBJECT-TYPE
        SYNTAX      INTEGER {
                              disable(0),
                              enable(1)
                            }
        MAX-ACCESS  read-write
        STATUS      current
        DESCRIPTION "Activates the DSP statistics.
                     When enabled, in-call statistics from the DSP channels
                     are sent to the syslog.

                     See the DspStatsInterval and DspStatsFilter variables for
                     more configuration.

                     This variable's semantics are different depending on
                     protocol and/or hardware platforms.
                     Please refer to the documentation shipped with your
                     device for more details.

                     WARNING: Enabling the DSP channel statistics might slow
                     down the system and reduce voice quality. Use only for
                     debugging or troubleshooting purposes."
        DEFVAL      { disable }
        ::=  {  mxDebugDspStats  5  }

    mxDebugDspStatsInterval OBJECT-TYPE
        SYNTAX      Unsigned32(0..3600)
        MAX-ACCESS  read-write
        STATUS      current
        DESCRIPTION "The time interval, in seconds, between each statistics
                     request. When greater than 0, it outputs the statistics at
                     the interval specified, and at channel closing.

                     When the interval is 0, it outputs the statistics only
                     during channel closure.

                     This variable's semantics are different depending on
                     protocol and/or hardware platforms.
                     Please refer to the documentation shipped with your
                     device for more details."
        DEFVAL { 0 }
        ::=  {  mxDebugDspStats  10 }

    mxDebugDspStatsFilter OBJECT-TYPE
        SYNTAX      Unsigned32
        MAX-ACCESS  read-write
        STATUS      current
        DESCRIPTION "Sum of the numerical values of required statistics. The
                     statistics numerical values are:

                     * DIM_STAT_ID_EC_DBG (1): Echo Canceller.
                     * DIM_STAT_ID_ERROR (2): Error.
                     * DIM_STAT_ID_FAX_RELAY (4): Fax T38.
                     * DIM_STAT_ID_RX_TX (8): Transmit/Receive.
                     * DIM_STAT_ID_SEC_RTP (16): Security SRTP.
                     * DIM_STAT_ID_VAD (32): Voice Activity Detection. [Mediatrix 4102 only]
                     * DIM_STAT_ID_VQMON (64): Voice Quality Monitor. [All platforms except 4102]
                     * DIM_STAT_ID_VP (128): Voice Playout.

                     Examples:
                     * 8 means DIM_STAT_ID_RX_TX statistics only.
                     * 12 means DIM_STAT_ID_FAX_RELAY and DIM_STAT_ID_RX_TX.
                     * 255 means all groups.

                     This variable's semantics are different depending on
                     protocol and/or hardware platforms.
                     Please refer to the documentation shipped with your
                     device for more details.

                     WARNING: Requesting a lot of statistics might slow down the
                     system and reduce voice quality. Use only for debugging or
                     troubleshooting purposes."
        DEFVAL { 0 }
        ::=  {  mxDebugDspStats  15 }

    -- ************************************************************************
    -- Conformance information
    -- ************************************************************************
    mxDebugCompliances OBJECT IDENTIFIER ::= { mxDebugConformance 1 }

    mxDebugComplVer1 MODULE-COMPLIANCE
        STATUS      current
        DESCRIPTION
            "List of groups required to support debug parameters."
        MODULE -- This Module
            MANDATORY-GROUPS {
                                 mxDebugSignalingLogGroupVer1,
                                 mxDebugFaxGroupVer1,
                                 mxDebugPcmCaptureGroupVer1
                             }
        ::= { mxDebugCompliances 10 }

    -- ************************************************************************
    -- MIB variable grouping
    -- ************************************************************************
    mxDebugGroups OBJECT IDENTIFIER ::= { mxDebugConformance 2 }

    mxDebugSignalingLogGroupVer1 OBJECT-GROUP
        OBJECTS {
                    mxDebugSignalingLogEnable,
                    mxDebugSignalingLogHost,
                    mxDebugSignalingLogPort
                }
        STATUS current
        DESCRIPTION
            "A collection of objects that defines a list related to signaling log."
        ::= { mxDebugGroups 10 }

    mxDebugFaxGroupVer1 OBJECT-GROUP
        OBJECTS {
                    mxDebugT38OutgoingToSyslog,
                    mxDebugT38IncomingToSyslog,
                    mxDebugFaxRelayForDspToSyslog,
                    mxDebugFaxRelayFromDspToSyslog
                }
        STATUS current
        DESCRIPTION
            "A collection of objects that defines the T.38 syslog activation"
        ::= { mxDebugGroups 20 }

    mxDebugPcmCaptureGroupVer1 OBJECT-GROUP
        OBJECTS {
                    mxDebugPcmCaptureEnable,
                    mxDebugPcmCaptureIpAddress
                }
        STATUS current
        DESCRIPTION
            "A collection of objects that defines the PCM capture activation"
        ::= { mxDebugGroups 30 }

END

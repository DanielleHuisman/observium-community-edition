-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************

MX-EAM-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

eamMIB MODULE-IDENTITY
 LAST-UPDATED   "1910210000Z"
 ORGANIZATION " Mediatrix Telecom, Inc. "
 CONTACT-INFO " Mediatrix Telecom, Inc.
                4229, Garlock Street
                Sherbrooke (Quebec)
                Canada
                Phone: (819) 829-8749
                "
 DESCRIPTION  " E&M Channel Associated Signaling

                The E&M Channel Associated Signaling (EAM) service manages the
                E&M CAS telephony interfaces.
                "
 ::= { mediatrixServices 1880 }

eamMIBObjects OBJECT IDENTIFIER ::= { eamMIB 1 }

-- ****************************************************************************

-- Group:E&M Configuration

-- ****************************************************************************

eamGroup OBJECT IDENTIFIER
 ::= { eamMIBObjects 100 }
 -- ***************************************************************************
 
 -- Table:E&M Channel Associated Signaling

 -- ***************************************************************************
 
 eamTable OBJECT-TYPE
  SYNTAX        SEQUENCE OF EamEntry
  MAX-ACCESS    not-accessible
  STATUS        current
  DESCRIPTION " E&M Channel Associated Signaling

                Configuration parameters related to the E&M channel associated
                signaling on this managed device.
                "
  ::= { eamGroup 100 }
  eamEntry OBJECT-TYPE
   SYNTAX        EamEntry
   MAX-ACCESS    not-accessible
   STATUS        current
   DESCRIPTION " A row in table E&M Channel Associated Signaling. "
   INDEX         {
                   eamName
                 }

   ::= { eamTable 1 }

  EamEntry ::= SEQUENCE
  {
    eamName                      OCTET STRING,
    eamChannelRange              OCTET STRING,
    eamChannelAllocationStrategy INTEGER,
    eamMaxActiveCalls            Unsigned32,
    eamEncodingScheme            INTEGER,
    eamSignalingType             INTEGER,
    eamDigitAttenuation          Unsigned32
  }

  -- Index:Name

  eamName OBJECT-TYPE
   SYNTAX        OCTET STRING
   MAX-ACCESS    read-only
   STATUS        current
   DESCRIPTION " Name

                 Name that identifies the interface.
                 "
   ::= { eamEntry 100 }

  -- Columnar:Channel Range

  eamChannelRange OBJECT-TYPE
   SYNTAX        OCTET STRING ( SIZE(1..10) )
   MAX-ACCESS    read-write
   STATUS        current
   DESCRIPTION " Channel Range

                 Defines the range of active bearer channels.
                 "
   DEFVAL        { "1-24" }
   ::= { eamEntry 200 }

  -- Columnar:Channel Allocation Strategy

  eamChannelAllocationStrategy OBJECT-TYPE
   SYNTAX        INTEGER { ascending(100) , descending(200) ,
                 roundRobinAscending(300) , roundRobinDescending(400) }
   MAX-ACCESS    read-write
   STATUS        current
   DESCRIPTION " Channel Allocation Strategy

                 Defines the strategy for selecting bearer channels. Available
                 strategies are:

                   * Ascending: select the lowest-numbered non-busy bearer
                     channel
                   * Descending: select the highest-numbered non-busy bearer
                     channel
                   * RoundRobinAscending: use a cyclic round-robin search;
                     starting from the bearer channel that follows the bearer
                     channel used for the last call, select the
                     lowest-numbered non-busy bearer channel
                   * RoundRobinDescending: use a cyclic round-robin search;
                     starting from the bearer channel that precedes the bearer
                     channel used for the last call, select the
                     highest-numbered non-busy bearer channel

                 "
   DEFVAL        { ascending }
   ::= { eamEntry 300 }

  -- Columnar:Maximum Active Calls

  eamMaxActiveCalls OBJECT-TYPE
   SYNTAX        Unsigned32 ( 0..30 )
   MAX-ACCESS    read-write
   STATUS        current
   DESCRIPTION " Maximum Active Calls

                 Defines the maximum number of active calls on the interface.

                 Note: The special value 0 indicates no maximum number of
                 active calls.

                 "
   DEFVAL        { 0 }
   ::= { eamEntry 400 }

  -- Columnar:Encoding Scheme

  eamEncodingScheme OBJECT-TYPE
   SYNTAX        INTEGER { g711alaw(100) , g711ulaw(200) }
   MAX-ACCESS    read-write
   STATUS        current
   DESCRIPTION " Encoding Scheme

                 Defines the voice encoding scheme in the bearer capabilities.
                 "
   DEFVAL        { g711alaw }
   ::= { eamEntry 500 }

  -- Columnar:Signaling Type

  eamSignalingType OBJECT-TYPE
   SYNTAX        INTEGER { winkStart(100) , immediateStart(200) , fgb(300) ,
                 fgd(400) }
   MAX-ACCESS    read-write
   STATUS        current
   DESCRIPTION " Signaling Type

                 Identifies the E&M signaling type.

                   * E&M Wink start: Set configuration parameters for basic
                     Wink Start signaling. After setting SignalingType,
                     individual configuration parameters can be overriden for
                     detail adjustment.
                   * E&M Immediate Start: Set configuration parameters for
                     basic Immediate Start signaling. After setting
                     SignalingType, individual configuration parameters can be
                     overriden for detail adjustment.
                   * E&M Feature Group B: Set configuration parameters for the
                     Feature Group B signaling defined by National Exchange
                     Carrier Association. After setting SignalingType,
                     individual configuration parameters can be overriden for
                     detail adjustment.
                   * E&M Feature Group D: Set configuration parameters for the
                     Feature Group D signaling defined by National Exchange
                     Carrier Association. After setting SignalingType,
                     individual configuration parameters can be overriden for
                     detail adjustment.

                 "
   DEFVAL        { winkStart }
   ::= { eamEntry 600 }

  -- Columnar:Digit Attenuation

  eamDigitAttenuation OBJECT-TYPE
   SYNTAX        Unsigned32 ( 0..20 )
   MAX-ACCESS    read-write
   STATUS        current
   DESCRIPTION " Digit Attenuation

                 Additional attenuation in dB for MFR1/DTMF digits generation.
                 By default, MFR1/DTMF digits generation power is determined
                 by variant selection. This parameter provides a mean to
                 reduce this power.
                 "
   DEFVAL        { 0 }
   ::= { eamEntry 700 }

 -- End of table:E&M Channel Associated Signaling

 -- ***************************************************************************
 
 -- Table:E&M Signaling Variants

 -- ***************************************************************************
 
 eamSignalingVariantsTable OBJECT-TYPE
  SYNTAX        SEQUENCE OF EamSignalingVariantsEntry
  MAX-ACCESS    not-accessible
  STATUS        current
  DESCRIPTION " E&M Signaling Variants

                This table allows to override or retrieve the default
                signaling settings for E&M signaling parameters. This table is
                effective only if the OverrideDefault parameter is Enabled. If
                the OverrideDefault parameter is Disabled, any change in this
                table has no effects.

                "
  ::= { eamGroup 200 }
  eamSignalingVariantsEntry OBJECT-TYPE
   SYNTAX        EamSignalingVariantsEntry
   MAX-ACCESS    not-accessible
   STATUS        current
   DESCRIPTION " A row in table E&M Signaling Variants. "
   INDEX         {
                   eamSignalingVariantsInterfaceName
                 }

   ::= { eamSignalingVariantsTable 1 }

  EamSignalingVariantsEntry ::= SEQUENCE
  {
    eamSignalingVariantsInterfaceName             OCTET STRING,
    eamSignalingVariantsOverrideDefault           MxEnableState,
    eamSignalingVariantsBitsBCD                   Integer32,
    eamSignalingVariantsDnisLength                Unsigned32,
    eamSignalingVariantsAniLength                 Unsigned32,
    eamSignalingVariantsIncomingRegisterSignaling INTEGER,
    eamSignalingVariantsOutgoingRegisterSignaling INTEGER,
    eamSignalingVariantsIncomingDialMap           OCTET STRING,
    eamSignalingVariantsOutgoingDialMap           OCTET STRING,
    eamSignalingVariantsWaitWink                  MxEnableState,
    eamSignalingVariantsWaitWinkAck               MxEnableState,
    eamSignalingVariantsSendWink                  MxEnableState,
    eamSignalingVariantsSendWinkAck               MxEnableState,
    eamSignalingVariantsResetSpecific             INTEGER
  }

  -- Index:Interface Name

  eamSignalingVariantsInterfaceName OBJECT-TYPE
   SYNTAX         OCTET STRING
   MAX-ACCESS     read-only
   STATUS         current
   DESCRIPTION  " Interface Name

                  Identifies the interface.
                  "
   ::= { eamSignalingVariantsEntry 100 }

  -- Columnar:Wait Wink

  eamSignalingVariantsWaitWink OBJECT-TYPE
   SYNTAX        MxEnableState
   MAX-ACCESS    read-write
   STATUS        current
   DESCRIPTION " Wait Wink

                 Defines whether or not the outgoing register should wait for
                 a wink before proceeding with digit transmission.
                 "
   DEFVAL        { enable }
   ::= { eamSignalingVariantsEntry 1000 }

  -- Columnar:Wait Wink Ack

  eamSignalingVariantsWaitWinkAck OBJECT-TYPE
   SYNTAX        MxEnableState
   MAX-ACCESS    read-write
   STATUS        current
   DESCRIPTION " Wait Wink Ack

                 Defines whether or not the outgoing register should wait for
                 a wink acknowledge after all digit reception.
                 "
   DEFVAL        { disable }
   ::= { eamSignalingVariantsEntry 1100 }

  -- Columnar:Send Wink

  eamSignalingVariantsSendWink OBJECT-TYPE
   SYNTAX        MxEnableState
   MAX-ACCESS    read-write
   STATUS        current
   DESCRIPTION " Send Wink

                 Defines whether or not the incoming register should send a
                 wink to notify the remote side that digit information can be
                 sent.
                 "
   DEFVAL        { enable }
   ::= { eamSignalingVariantsEntry 1200 }

  -- Columnar:Send Wink Ack

  eamSignalingVariantsSendWinkAck OBJECT-TYPE
   SYNTAX        MxEnableState
   MAX-ACCESS    read-write
   STATUS        current
   DESCRIPTION " Send Wink Ack

                 Defines whether or not the incoming register should send a
                 wink to acknowledge the receipt of all digits.
                 "
   DEFVAL        { disable }
   ::= { eamSignalingVariantsEntry 1300 }

  -- Columnar:Override Default

  eamSignalingVariantsOverrideDefault OBJECT-TYPE
   SYNTAX        MxEnableState
   MAX-ACCESS    read-write
   STATUS        current
   DESCRIPTION " Override Default

                 Overrides the default settings of E&M Signaling parameters
                 for the SignalingType and InterfaceName.

                   * Disable: The interface uses the default configuration
                     associated with the selected Signaling Type. The
                     configuration set in the current row has no effect on the
                     default configuration of the selected Signaling Type.
                     Refer to the technical documentation to get the default
                     configurations of the various Signaling Types.
                   * Enable: The interface uses the specific signaling
                     configuration as defined in the current row. To retrieve
                     the default configuration associated with the current
                     Signaling Type, the command implemented by the
                     ResetSpecific parameter MUST be issued.

                 "
   DEFVAL        { disable }
   ::= { eamSignalingVariantsEntry 200 }

  -- Row command:Reset Specific

  eamSignalingVariantsResetSpecific OBJECT-TYPE
   SYNTAX        INTEGER { noOp(0), resetSpecific(10) }
   MAX-ACCESS    read-write
   STATUS        current
   DESCRIPTION " Reset Specific

                 Resets specific settings of E&M Signaling parameters with the
                 default signaling settings. This command is used to retrieve
                 the default configuration of the selected Signaling Type set
                 in the SignalingType parameter.

                 "
   DEFVAL        { noOp }
   ::= { eamSignalingVariantsEntry 2000 }

  -- Columnar:BCD Bits

  eamSignalingVariantsBitsBCD OBJECT-TYPE
   SYNTAX        Integer32 ( 0..8 )
   MAX-ACCESS    read-write
   STATUS        current
   DESCRIPTION " BCD Bits

                 Settings of the B, C and D bits when the device transmits
                 line signals. B, C and D bits of received line signals are
                 ignored by the device.

                 BCD bits definition

                   * 0..7: BCD bits are set to the specified value.
                   * 8: BCD bits follow the A bit.

                 Note: On E1-CAS, the ABCD bits pair cannot be set to '0000'.
                 If the BCD bits pair is set to '000' or to follow the A bit,
                 then the BCD bits pair is set to '001' instead.

                 "
   DEFVAL        { 8 }
   ::= { eamSignalingVariantsEntry 300 }

  -- Columnar:DNIS Length

  eamSignalingVariantsDnisLength OBJECT-TYPE
   SYNTAX        Unsigned32 ( 0..20 )
   MAX-ACCESS    read-write
   STATUS        current
   DESCRIPTION " DNIS Length

                 Defines the expected length of the DNIS. DNIS (Dialed Number
                 Identification Service) is the called party or the
                 destination number.

                   * 0: Variable DNIS length used.
                   * 1..20: Number indicates the specific DNIS length
                     expected.

                 "
   DEFVAL        { 0 }
   ::= { eamSignalingVariantsEntry 400 }

  -- Columnar:ANI Length

  eamSignalingVariantsAniLength OBJECT-TYPE
   SYNTAX        Unsigned32 ( 0..20 )
   MAX-ACCESS    read-write
   STATUS        current
   DESCRIPTION " ANI Length

                 Defines the expected length of the ANI. ANI (Automatic Number
                 Identification) is the number of the calling party.

                   * 0 : Variable ANI length.
                   * 1..20 : Specific ANI length.

                 "
   DEFVAL        { 0 }
   ::= { eamSignalingVariantsEntry 500 }

  -- Columnar:Incoming Register Signaling

  eamSignalingVariantsIncomingRegisterSignaling OBJECT-TYPE
   SYNTAX        INTEGER { mfR1(100) , dtmf(200) }
   MAX-ACCESS    read-write
   STATUS        current
   DESCRIPTION " Incoming Register Signaling

                 Defines the incoming register signaling method.

                   * MfR1: Multi Frequency - R1.
                   * Dtmf: Dual Tone Multi Frequency.

                 "
   DEFVAL        { dtmf }
   ::= { eamSignalingVariantsEntry 600 }

  -- Columnar:Outgoing Register Signaling

  eamSignalingVariantsOutgoingRegisterSignaling OBJECT-TYPE
   SYNTAX        INTEGER { mfR1(100) , dtmf(200) }
   MAX-ACCESS    read-write
   STATUS        current
   DESCRIPTION " Outgoing Register Signaling

                 Defines the outgoing register signaling method.

                   * MfR1: Multi Frequency - R1.
                   * Dtmf: Dual Tone Multi Frequency.

                 "
   DEFVAL        { dtmf }
   ::= { eamSignalingVariantsEntry 700 }

  -- Columnar:Incoming Dial Map

  eamSignalingVariantsIncomingDialMap OBJECT-TYPE
   SYNTAX        OCTET STRING ( SIZE(0..255) )
   MAX-ACCESS    read-write
   STATUS        current
   DESCRIPTION " Incoming Dial Map

                 Defines the dial map expression to match against on the
                 incoming side. The dial map expression uses a special format
                 using macros that enables the user to construct a custom dial
                 map using the ANI, DNIS and other special tones as separator.

                 Dial map macros:

                   * %dnis : DNIS (Dialed Number Identification Service).
                   * %ani : ANI (Automatic Number Identification).
                   * %kp : KP (start-of-pulsing) tone (MF R1 only).
                   * %st : ST (end-of-pulsing) tone (MF R1 only).
                   * %t : Interdigit timeout.
                   * A,B,C,D,*,# : Control tones (DTMF only).
                   * A,B,C,D,E : Control tones (MF R1 only).

                 Examples:

                   * %dnis*%ani : (dnis)*(ani)
                   * %kp%dnis%st%kp%ani%st : KP(dnis)STKP(ani)ST
                   * A%dnisBA%aniB : A(dnis)BA(ani)B

                 "
   DEFVAL        { "%dnis%t" }
   ::= { eamSignalingVariantsEntry 800 }

  -- Columnar:Outgoing Dial Map

  eamSignalingVariantsOutgoingDialMap OBJECT-TYPE
   SYNTAX        OCTET STRING ( SIZE(0..255) )
   MAX-ACCESS    read-write
   STATUS        current
   DESCRIPTION " Outgoing Dial Map

                 Defines the dial map format for the outgoing dial string. The
                 dial string generation uses a special format using macros
                 that enables the user to construct a custom dial string using
                 the ANI, DNIS and other specials tones used as separator. The
                 dial string uses regular expression to replace the macros
                 with the proper call parameter value.

                 Dial map macros:

                   * %dnis : DNIS (Dialed Number Identification Service).
                   * %ani : ANI (Automatic Number Identification).
                   * %kp : KP (start-of-pulsing) tone (MF R1 only).
                   * %st : ST (end-of-pulsing) tone (MF R1 only).
                   * %t : Interdigit timeout.
                   * A,B,C,D,*,# : Control tones (DTMF only).
                   * A,B,C,D,E : Control tones (MF R1 only).

                 Examples : ANI=1234 DNIS=6789 KP=A ST=D

                   * %dnis*%ani : 6789*1234
                   * %kp%dnis%st%kp%ani%st : A6789DA1234D
                   * A%dnisBA%aniB : A6789BA1234B

                 "
   DEFVAL        { "%dnis%t" }
   ::= { eamSignalingVariantsEntry 900 }

 -- End of table:E&M Signaling Variants

 -- ***************************************************************************
 
 -- Table:E&M Signaling Timer Variants

 -- ***************************************************************************
 
 eamTimerVariantsTable OBJECT-TYPE
  SYNTAX        SEQUENCE OF EamTimerVariantsEntry
  MAX-ACCESS    not-accessible
  STATUS        current
  DESCRIPTION " E&M Signaling Timer Variants

                This table allows to override or retrieve the default
                signaling setting for E&M Timers.
                "
  ::= { eamGroup 300 }
  eamTimerVariantsEntry OBJECT-TYPE
   SYNTAX        EamTimerVariantsEntry
   MAX-ACCESS    not-accessible
   STATUS        current
   DESCRIPTION " A row in table E&M Signaling Timer Variants. "
   INDEX         {
                   eamTimerVariantsInterfaceName
                 }

   ::= { eamTimerVariantsTable 1 }

  EamTimerVariantsEntry ::= SEQUENCE
  {
    eamTimerVariantsInterfaceName           OCTET STRING,
    eamTimerVariantsOverrideDefault         MxEnableState,
    eamTimerVariantsBwdWaitPreWinkTimeout   Integer32,
    eamTimerVariantsBwdSendWinkTimeout      Integer32,
    eamTimerVariantsBwdWait1stDigitTimeout  Integer32,
    eamTimerVariantsBwdClearBackwardTimeout Integer32,
    eamTimerVariantsBwdDigitCompleteTimeout Integer32,
    eamTimerVariantsFwdWaitWinkTimeout      Integer32,
    eamTimerVariantsFwdWaitMaxWinkOnTimeout Integer32,
    eamTimerVariantsFwdWaitPreDialTimeout   Integer32,
    eamTimerVariantsFwdWaitAnswerTimeout    Integer32,
    eamTimerVariantsFwdClearForwardTimeout  Integer32,
    eamTimerVariantsReleaseGuardTimeout     Integer32,
    eamTimerVariantsResetSpecific           INTEGER
  }

  -- Index:Interface Name

  eamTimerVariantsInterfaceName OBJECT-TYPE
   SYNTAX        OCTET STRING
   MAX-ACCESS    read-only
   STATUS        current
   DESCRIPTION " Interface Name

                 Identifies the interface.
                 "
   ::= { eamTimerVariantsEntry 100 }

  -- Columnar:Wait PreDial Timeout

  eamTimerVariantsFwdWaitPreDialTimeout OBJECT-TYPE
   SYNTAX        Integer32 ( 0..5000 )
   MAX-ACCESS    read-write
   STATUS        current
   DESCRIPTION " Wait PreDial Timeout

                 The amount of time an outgoing register waits after the wink
                 to start dialing.

                 This value is expressed in milliseconds (ms).

                 "
   DEFVAL        { 140 }
   ::= { eamTimerVariantsEntry 1000 }

  -- Columnar:Wait Answer Timeout

  eamTimerVariantsFwdWaitAnswerTimeout OBJECT-TYPE
   SYNTAX        Integer32 ( 0..300000 )
   MAX-ACCESS    read-write
   STATUS        current
   DESCRIPTION " Wait Answer Timeout

                 The maximum time an outgoing register waits for the call to
                 be answered.

                 This value is expressed in milliseconds (ms).

                 "
   DEFVAL        { 180000 }
   ::= { eamTimerVariantsEntry 1100 }

  -- Columnar:Clear Forward Timeout

  eamTimerVariantsFwdClearForwardTimeout OBJECT-TYPE
   SYNTAX        Integer32 ( 0..30000 )
   MAX-ACCESS    read-write
   STATUS        current
   DESCRIPTION " Clear Forward Timeout

                 The maximum time an outgoing register waits after sending a
                 clear forward line signal before transiting to the idle
                 state.

                 This value is expressed in milliseconds (ms).

                 "
   DEFVAL        { 2000 }
   ::= { eamTimerVariantsEntry 1200 }

  -- Columnar:Release Guard Timeout

  eamTimerVariantsReleaseGuardTimeout OBJECT-TYPE
   SYNTAX        Integer32 ( 0..10000 )
   MAX-ACCESS    read-write
   STATUS        current
   DESCRIPTION " Release Guard Timeout

                 Maximum time a register waits after sending an idle line
                 signal to prevent a new seizure of the line.

                 This value is expressed in milliseconds (ms).

                 "
   DEFVAL        { 200 }
   ::= { eamTimerVariantsEntry 1300 }

  -- Row command:Reset Specific

  eamTimerVariantsResetSpecific OBJECT-TYPE
   SYNTAX        INTEGER { noOp(0), resetSpecific(10) }
   MAX-ACCESS    read-write
   STATUS        current
   DESCRIPTION " Reset Specific

                 Resets specific settings of E&M Timers parameters with the
                 default signaling type settings. This command is used to
                 retrieve the default configuration of the selected Signaling
                 Type set in the SignalingType parameter.

                 "
   DEFVAL        { noOp }
   ::= { eamTimerVariantsEntry 1900 }

  -- Columnar:Override Default

  eamTimerVariantsOverrideDefault OBJECT-TYPE
   SYNTAX        MxEnableState
   MAX-ACCESS    read-write
   STATUS        current
   DESCRIPTION " Override Default

                 Overrides the default settings of E&M Signaling parameters
                 for the SignalingType and InterfaceName.

                   * Disable: The interface uses the default configuration
                     associated with the selected Signaling Type. The
                     configuration set in the current row has no effect on the
                     default configuration of the selected Signaling Type.
                     Refer to the technical documentation to get the default
                     configurations of the various Signaling Types.
                   * Enable: The interface uses the specific signaling
                     configuration as defined in the current row. To retrieve
                     the default configuration associated with the current
                     Signaling Type, the command implemented by the
                     ResetSpecific parameter MUST be issued.

                 "
   DEFVAL        { disable }
   ::= { eamTimerVariantsEntry 200 }

  -- Columnar:Seizure Ack Timeout

  eamTimerVariantsBwdWaitPreWinkTimeout OBJECT-TYPE
   SYNTAX        Integer32 ( 0..2000 )
   MAX-ACCESS    read-write
   STATUS        current
   DESCRIPTION " Seizure Ack Timeout

                 Amount of time an incoming register waits before sending the
                 wink that acknowledges the seizure.

                 This value is expressed in milliseconds (ms).

                 "
   DEFVAL        { 50 }
   ::= { eamTimerVariantsEntry 300 }

  -- Columnar:Send Wink Timeout

  eamTimerVariantsBwdSendWinkTimeout OBJECT-TYPE
   SYNTAX        Integer32 ( 0..5000 )
   MAX-ACCESS    read-write
   STATUS        current
   DESCRIPTION " Send Wink Timeout

                 Duration of the wink signal applied by the incoming register
                 to signal seizure acknowledgment.

                 This value is expressed in milliseconds (ms).

                 "
   DEFVAL        { 200 }
   ::= { eamTimerVariantsEntry 400 }

  -- Columnar:Wait 1st Digit Timeout

  eamTimerVariantsBwdWait1stDigitTimeout OBJECT-TYPE
   SYNTAX        Integer32 ( 0..20000 )
   MAX-ACCESS    read-write
   STATUS        current
   DESCRIPTION " Wait 1st Digit Timeout

                 Maximum time an incoming register waits for the first
                 incoming digit after the line seizure.

                 This value is expressed in milliseconds (ms).

                 "
   DEFVAL        { 10000 }
   ::= { eamTimerVariantsEntry 500 }

  -- Columnar:Clear Backward Timeout

  eamTimerVariantsBwdClearBackwardTimeout OBJECT-TYPE
   SYNTAX        Integer32 ( 0..30000 )
   MAX-ACCESS    read-write
   STATUS        current
   DESCRIPTION " Clear Backward Timeout

                 The maximum time an incoming register waits after sending a
                 clear backward line signal before transiting to the idle
                 state.

                 This value is expressed in milliseconds (ms).

                 "
   DEFVAL        { 2000 }
   ::= { eamTimerVariantsEntry 600 }

  -- Columnar:Digit Complete Timeout

  eamTimerVariantsBwdDigitCompleteTimeout OBJECT-TYPE
   SYNTAX        Integer32 ( 0..15000 )
   MAX-ACCESS    read-write
   STATUS        current
   DESCRIPTION " Digit Complete Timeout

                 The maximum time the incoming register waits for the next
                 digit before considering the digit sequence as completed.

                 This value is expressed in milliseconds (ms).

                 "
   DEFVAL        { 4000 }
   ::= { eamTimerVariantsEntry 700 }

  -- Columnar:Wait Wink Timeout

  eamTimerVariantsFwdWaitWinkTimeout OBJECT-TYPE
   SYNTAX        Integer32 ( 0..10000 )
   MAX-ACCESS    read-write
   STATUS        current
   DESCRIPTION " Wait Wink Timeout

                 Maximum time an outgoing register waits for seizure
                 acknowledgement after seizing the line.

                 This value is expressed in milliseconds (ms).

                 "
   DEFVAL        { 5000 }
   ::= { eamTimerVariantsEntry 800 }

  -- Columnar:Wait Max Wink On Timeout

  eamTimerVariantsFwdWaitMaxWinkOnTimeout OBJECT-TYPE
   SYNTAX        Integer32 ( 0..10000 )
   MAX-ACCESS    read-write
   STATUS        current
   DESCRIPTION " Wait Max Wink On Timeout

                 The maximum time an outgoing register waits for the seizure
                 acknowledgment wink to complete.

                 This value is expressed in milliseconds (ms).

                 "
   DEFVAL        { 5000 }
   ::= { eamTimerVariantsEntry 900 }

 -- End of table:E&M Signaling Timer Variants

 -- ***************************************************************************
 
 -- Table:E&M Digit Timer Variants

 -- ***************************************************************************
 
 eamDigitTimerVariantsTable OBJECT-TYPE
  SYNTAX        SEQUENCE OF EamDigitTimerVariantsEntry
  MAX-ACCESS    not-accessible
  STATUS        current
  DESCRIPTION " E&M Digit Timer Variants

                This table allows to override or retrieve the default
                signaling type setting for E&M Digit Timers.
                "
  ::= { eamGroup 400 }
  eamDigitTimerVariantsEntry OBJECT-TYPE
   SYNTAX        EamDigitTimerVariantsEntry
   MAX-ACCESS    not-accessible
   STATUS        current
   DESCRIPTION " A row in table E&M Digit Timer Variants. "
   INDEX         {
                   eamDigitTimerVariantsInterfaceName
                 }

   ::= { eamDigitTimerVariantsTable 1 }

  EamDigitTimerVariantsEntry ::= SEQUENCE
  {
    eamDigitTimerVariantsInterfaceName   OCTET STRING,
    eamDigitTimerVariantsOverrideDefault MxEnableState,
    eamDigitTimerVariantsKPOnTimeout     Integer32,
    eamDigitTimerVariantsKPOffTimeout    Integer32,
    eamDigitTimerVariantsResetSpecific   INTEGER
  }

  -- Index:Interface Name

  eamDigitTimerVariantsInterfaceName OBJECT-TYPE
   SYNTAX          OCTET STRING
   MAX-ACCESS      read-only
   STATUS          current
   DESCRIPTION   " Interface Name

                   Identifies the interface.
                   "
   ::= { eamDigitTimerVariantsEntry 100 }

  -- Columnar:Override Default

  eamDigitTimerVariantsOverrideDefault OBJECT-TYPE
   SYNTAX        MxEnableState
   MAX-ACCESS    read-write
   STATUS        current
   DESCRIPTION " Override Default

                 Overrides the default settings of E&M Signaling parameters
                 for the SignalingType and InterfaceName.

                   * Disable: The interface uses the default configuration
                     associated with the selected Signaling Type. The
                     configuration set in the current row has no effect on the
                     default configuration of the selected Signaling Type.
                     Refer to the technical documentation to get the default
                     configurations of the various Signaling Types.
                   * Enable: The interface uses the specific signaling
                     configuration as defined in the current row. To retrieve
                     the default configuration associated with the current
                     Signaling Type, the command implemented by the
                     ResetSpecific parameter MUST be issued.

                 "
   DEFVAL        { disable }
   ::= { eamDigitTimerVariantsEntry 200 }

  -- Columnar:Duration of the MF R1 KP signal

  eamDigitTimerVariantsKPOnTimeout OBJECT-TYPE
   SYNTAX        Integer32 ( 0..10000 )
   MAX-ACCESS    read-write
   STATUS        current
   DESCRIPTION " Duration of the MF R1 KP signal

                 The time during which the MF R1 KP tone is on.

                 This value is expressed in milliseconds (ms).

                 "
   DEFVAL        { 100 }
   ::= { eamDigitTimerVariantsEntry 300 }

  -- Columnar:Duration of the off portion of the MF R1 KP signal

  eamDigitTimerVariantsKPOffTimeout OBJECT-TYPE
   SYNTAX        Integer32 ( 0..10000 )
   MAX-ACCESS    read-write
   STATUS        current
   DESCRIPTION " Duration of the off portion of the MF R1 KP signal

                 The duration of the pause after the MF R1 KP tone.

                 This value is expressed in milliseconds (ms).

                 "
   DEFVAL        { 68 }
   ::= { eamDigitTimerVariantsEntry 400 }

  -- Row command:Reset Specific

  eamDigitTimerVariantsResetSpecific OBJECT-TYPE
   SYNTAX        INTEGER { noOp(0), resetSpecific(10) }
   MAX-ACCESS    read-write
   STATUS        current
   DESCRIPTION " Reset Specific

                 Resets specific settings of E&M Digit Timers parameters with
                 the default signaling type settings. This command is used to
                 retrieve the default configuration of the selected Signaling
                 Type set in the SignalingType parameter.

                 "
   DEFVAL        { noOp }
   ::= { eamDigitTimerVariantsEntry 900 }

 -- End of table:E&M Digit Timer Variants

 -- ***************************************************************************
 
 -- Table:E&M Link Timer Variants

 -- ***************************************************************************
 
 eamLinkTimerVariantsTable OBJECT-TYPE
  SYNTAX        SEQUENCE OF EamLinkTimerVariantsEntry
  MAX-ACCESS    not-accessible
  STATUS        current
  DESCRIPTION " E&M Link Timer Variants

                This table allows to override or retrieve the default
                signaling type setting for E&M Link Timers.
                "
  ::= { eamGroup 500 }
  eamLinkTimerVariantsEntry OBJECT-TYPE
   SYNTAX        EamLinkTimerVariantsEntry
   MAX-ACCESS    not-accessible
   STATUS        current
   DESCRIPTION " A row in table E&M Link Timer Variants. "
   INDEX         {
                   eamLinkTimerVariantsInterfaceName
                 }

   ::= { eamLinkTimerVariantsTable 1 }

  EamLinkTimerVariantsEntry ::= SEQUENCE
  {
    eamLinkTimerVariantsInterfaceName              OCTET STRING,
    eamLinkTimerVariantsOverrideDefault            MxEnableState,
    eamLinkTimerVariantsLinkActivationTimeout      Integer32,
    eamLinkTimerVariantsLinkActivationRetryTimeout Integer32,
    eamLinkTimerVariantsResetSpecific              INTEGER
  }

  -- Index:Interface Name

  eamLinkTimerVariantsInterfaceName OBJECT-TYPE
   SYNTAX         OCTET STRING
   MAX-ACCESS     read-only
   STATUS         current
   DESCRIPTION  " Interface Name

                  Identifies the interface.
                  "
   ::= { eamLinkTimerVariantsEntry 100 }

  -- Columnar:Override Default

  eamLinkTimerVariantsOverrideDefault OBJECT-TYPE
   SYNTAX        MxEnableState
   MAX-ACCESS    read-write
   STATUS        current
   DESCRIPTION " Override Default

                 Overrides the default settings of E&M Signaling parameters
                 for the SignalingType and InterfaceName.

                   * Disable: The interface uses the default configuration
                     associated with the selected Signaling Type. The
                     configuration set in the current row has no effect on the
                     default configuration of the selected Signaling Type.
                     Refer to the technical documentation to get the default
                     configurations of the various Signaling Types.
                   * Enable: The interface uses the specific signaling
                     configuration as defined in the current row. To retrieve
                     the default configuration associated with the current
                     Signaling Type, the command implemented by the
                     ResetSpecific parameter MUST be issued.

                 "
   DEFVAL        { disable }
   ::= { eamLinkTimerVariantsEntry 200 }

  -- Columnar:Link Activation Timeout

  eamLinkTimerVariantsLinkActivationTimeout OBJECT-TYPE
   SYNTAX        Integer32 ( 0..10000 )
   MAX-ACCESS    read-write
   STATUS        current
   DESCRIPTION " Link Activation Timeout

                 The maximum time the unit waits for an activation indication
                 coming from the physical link. The activation indication is
                 used to indicate that the physical layer connection has been
                 activated.

                 This value is expressed in milliseconds (ms).

                 "
   DEFVAL        { 1000 }
   ::= { eamLinkTimerVariantsEntry 300 }

  -- Columnar:Link Activation Retry Timeout

  eamLinkTimerVariantsLinkActivationRetryTimeout OBJECT-TYPE
   SYNTAX        Integer32 ( 0..10000 )
   MAX-ACCESS    read-write
   STATUS        current
   DESCRIPTION " Link Activation Retry Timeout

                 The maximum time the unit waits before attempting to
                 reestablish the physical link. The attempt is made when the
                 physical layer connection has been deactivated.

                 This value is expressed in milliseconds (ms).

                 "
   DEFVAL        { 3000 }
   ::= { eamLinkTimerVariantsEntry 400 }

  -- Row command:Reset Specific

  eamLinkTimerVariantsResetSpecific OBJECT-TYPE
   SYNTAX        INTEGER { noOp(0), resetSpecific(10) }
   MAX-ACCESS    read-write
   STATUS        current
   DESCRIPTION " Reset Specific

                 Resets specific settings of E&M Link Timers parameters with
                 the default signaling settings. This command is used to
                 retrieve the default signaling configuration set in the
                 SignalingType parameter.

                 "
   DEFVAL        { noOp }
   ::= { eamLinkTimerVariantsEntry 900 }

 -- End of table:E&M Link Timer Variants

 -- ***************************************************************************
 
 -- Table:E&M Signaling Tone Variants

 -- ***************************************************************************
 
 eamToneVariantsTable OBJECT-TYPE
  SYNTAX        SEQUENCE OF EamToneVariantsEntry
  MAX-ACCESS    not-accessible
  STATUS        current
  DESCRIPTION " E&M Signaling Tone Variants

                This table allows to override or retrieve the default
                signaling setting for E&M Tone variants.
                "
  ::= { eamGroup 600 }
  eamToneVariantsEntry OBJECT-TYPE
   SYNTAX        EamToneVariantsEntry
   MAX-ACCESS    not-accessible
   STATUS        current
   DESCRIPTION " A row in table E&M Signaling Tone Variants. "
   INDEX         {
                   eamToneVariantsInterfaceName
                 }

   ::= { eamToneVariantsTable 1 }

  EamToneVariantsEntry ::= SEQUENCE
  {
    eamToneVariantsInterfaceName   OCTET STRING,
    eamToneVariantsOverrideDefault MxEnableState,
    eamToneVariantsKpTone          INTEGER,
    eamToneVariantsStTone          INTEGER,
    eamToneVariantsResetSpecific   INTEGER
  }

  -- Index:Interface Name

  eamToneVariantsInterfaceName OBJECT-TYPE
   SYNTAX        OCTET STRING
   MAX-ACCESS    read-only
   STATUS        current
   DESCRIPTION " Interface Name

                 Identifies the interface.
                 "
   ::= { eamToneVariantsEntry 100 }

  -- Columnar:Override Default

  eamToneVariantsOverrideDefault OBJECT-TYPE
   SYNTAX        MxEnableState
   MAX-ACCESS    read-write
   STATUS        current
   DESCRIPTION " Override Default

                 Overrides the default settings of E&M Signaling parameters
                 for the SignalingType and InterfaceName.

                   * Disable: The interface uses the default configuration
                     associated with the selected Signaling Type. The
                     configuration set in the current row has no effect on the
                     default configuration of the selected Signaling Type.
                     Refer to the technical documentation to get the default
                     configurations of the various Signaling Types.
                   * Enable: The interface uses the specific signaling
                     configuration as defined in the current row. To retrieve
                     the default configuration associated with the current
                     Signaling Type, the command implemented by the
                     ResetSpecific parameter MUST be issued.

                 "
   DEFVAL        { disable }
   ::= { eamToneVariantsEntry 200 }

  -- Columnar:KP (start-of-pulsing) Tone

  eamToneVariantsKpTone OBJECT-TYPE
   SYNTAX        INTEGER { none(100) , mF0(200) , mF1(300) , mF2(400) , mF3
                 (500) , mF4(600) , mF5(700) , mF6(800) , mF7(900) , mF8(1000)
                 , mF9(1100) , mF10(1200) , mF11(1300) , mF12(1400) , mF13
                 (1500) , mF14(1600) }
   MAX-ACCESS    read-write
   STATUS        current
   DESCRIPTION " KP (start-of-pulsing) Tone

                 Specifies the KP (start-of-pulsing) signal.

                   * None : No tone used.
                   * MF0..MF14 : MF R1 Tone

                 "
   DEFVAL        { mF10 }
   ::= { eamToneVariantsEntry 300 }

  -- Columnar:ST (end-of-pulsing) Tone

  eamToneVariantsStTone OBJECT-TYPE
   SYNTAX        INTEGER { none(100) , mF0(200) , mF1(300) , mF2(400) , mF3
                 (500) , mF4(600) , mF5(700) , mF6(800) , mF7(900) , mF8(1000)
                 , mF9(1100) , mF10(1200) , mF11(1300) , mF12(1400) , mF13
                 (1500) , mF14(1600) }
   MAX-ACCESS    read-write
   STATUS        current
   DESCRIPTION " ST (end-of-pulsing) Tone

                 Specifies the ST (end-of-pulsing) signal.

                   * None : No tone used.
                   * MF0..MF14 : MF R1 Tone

                 "
   DEFVAL        { mF13 }
   ::= { eamToneVariantsEntry 400 }

  -- Row command:Reset Specific

  eamToneVariantsResetSpecific OBJECT-TYPE
   SYNTAX        INTEGER { noOp(0), resetSpecific(10) }
   MAX-ACCESS    read-write
   STATUS        current
   DESCRIPTION " Reset Specific

                 Resets specific settings of E&M Tones parameters with the
                 default signaling settings. This command is used to retrieve
                 the default signaling configuration set in the SignalingType
                 parameter.

                 "
   DEFVAL        { noOp }
   ::= { eamToneVariantsEntry 900 }

 -- End of table:E&M Signaling Tone Variants

-- End of group:E&M Configuration

-- ****************************************************************************

-- Group:Bearer Channel Configuration

-- ****************************************************************************

bearerChannelGroup OBJECT IDENTIFIER
 ::= { eamMIBObjects 200 }
 -- ***************************************************************************
 
 -- Table:Bearer Channel Info

 -- ***************************************************************************
 
 bearerChannelInfoTable OBJECT-TYPE
  SYNTAX        SEQUENCE OF BearerChannelInfoEntry
  MAX-ACCESS    not-accessible
  STATUS        current
  DESCRIPTION " Bearer Channel Info

                Port-specific operational, statistics, and active call data
                for B channels.
                "
  ::= { bearerChannelGroup 100 }
  bearerChannelInfoEntry OBJECT-TYPE
   SYNTAX        BearerChannelInfoEntry
   MAX-ACCESS    not-accessible
   STATUS        current
   DESCRIPTION " A row in table Bearer Channel Info. "
   INDEX         {
                   bearerChannelInfoIndex
                 }

   ::= { bearerChannelInfoTable 1 }

  BearerChannelInfoEntry ::= SEQUENCE
  {
    bearerChannelInfoIndex OCTET STRING,
    bearerChannelInfoState INTEGER
  }

  -- Index:Index

  bearerChannelInfoIndex OBJECT-TYPE
   SYNTAX        OCTET STRING
   MAX-ACCESS    read-only
   STATUS        current
   DESCRIPTION " Index

                 Identifies the Bearer Channel..
                 "
   ::= { bearerChannelInfoEntry 100 }

  -- Columnar:State

  bearerChannelInfoState OBJECT-TYPE
   SYNTAX        INTEGER { idle(100) , inUse(200) , maintenance(300) , error
                 (400) , disabled(500) }
   MAX-ACCESS    read-only
   STATUS        current
   DESCRIPTION " State

                 The current call control state for this channel:

                   * Idle: The channel is available
                   * InUse: The channel is currently used
                   * Maintenance: Maintenance state, temporarily unavailable
                   * Error: Error on this channel
                   * Disabled: The channel is disabled

                 "
   ::= { bearerChannelInfoEntry 200 }

 -- End of table:Bearer Channel Info

-- End of group:Bearer Channel Configuration

-- ****************************************************************************

-- Group:Signaling Channel Configuration

-- ****************************************************************************

physicalGroup OBJECT IDENTIFIER
 ::= { eamMIBObjects 300 }
 -- ***************************************************************************
 
 -- Table:Physical Link Information

 -- ***************************************************************************
 
 physicalLinkInfoTable OBJECT-TYPE
  SYNTAX        SEQUENCE OF PhysicalLinkInfoEntry
  MAX-ACCESS    not-accessible
  STATUS        current
  DESCRIPTION " Physical Link Information

                The physical link information table contains status
                information for all interfaces on this managed device.
                "
  ::= { physicalGroup 100 }
  physicalLinkInfoEntry OBJECT-TYPE
   SYNTAX        PhysicalLinkInfoEntry
   MAX-ACCESS    not-accessible
   STATUS        current
   DESCRIPTION " A row in table Physical Link Information. "
   INDEX         {
                   physicalLinkInfoInterfaceName
                 }

   ::= { physicalLinkInfoTable 1 }

  PhysicalLinkInfoEntry ::= SEQUENCE
  {
    physicalLinkInfoInterfaceName OCTET STRING,
    physicalLinkInfoState         INTEGER
  }

  -- Index:Interface Name

  physicalLinkInfoInterfaceName OBJECT-TYPE
   SYNTAX        OCTET STRING
   MAX-ACCESS    read-only
   STATUS        current
   DESCRIPTION " Interface Name

                 Identifies the interface.
                 "
   ::= { physicalLinkInfoEntry 100 }

  -- Columnar:State

  physicalLinkInfoState OBJECT-TYPE
   SYNTAX        INTEGER { up(100) , down(200) }
   MAX-ACCESS    read-only
   STATUS        current
   DESCRIPTION " State

                 The layer 1 state for this interface:

                   * Up: Layer 1 connectivity.
                   * Down: No layer 1 connectivity. The interface might be in
                     this state because no cable is plugged in or a pinout
                     problem is detected.

                 "
   ::= { physicalLinkInfoEntry 200 }

 -- End of table:Physical Link Information

 -- ***************************************************************************
 
 -- Table:Physical Link

 -- ***************************************************************************
 
 physicalLinkTable OBJECT-TYPE
  SYNTAX        SEQUENCE OF PhysicalLinkEntry
  MAX-ACCESS    not-accessible
  STATUS        current
  DESCRIPTION " Physical Link

                The physical link table containing configuration and
                operational parameters for all interfaces on this managed
                device.
                "
  ::= { physicalGroup 200 }
  physicalLinkEntry OBJECT-TYPE
   SYNTAX        PhysicalLinkEntry
   MAX-ACCESS    not-accessible
   STATUS        current
   DESCRIPTION " A row in table Physical Link. "
   INDEX         {
                   physicalLinkInterfaceName
                 }

   ::= { physicalLinkTable 1 }

  PhysicalLinkEntry ::= SEQUENCE
  {
    physicalLinkInterfaceName          OCTET STRING,
    physicalLinkLineCoding             INTEGER,
    physicalLinkLineFraming            INTEGER,
    physicalLinkClockMode              INTEGER,
    physicalLinkMonitorLinkStateEnable MxEnableState,
    physicalLinkPortPinout             INTEGER
  }

  -- Index:Interface Name

  physicalLinkInterfaceName OBJECT-TYPE
   SYNTAX        OCTET STRING
   MAX-ACCESS    read-only
   STATUS        current
   DESCRIPTION " Interface Name

                 Identifies the interface.
                 "
   ::= { physicalLinkEntry 100 }

  -- Columnar:Line Coding

  physicalLinkLineCoding OBJECT-TYPE
   SYNTAX        INTEGER { b8zs(100) , hdb3(200) , ami(300) }
   MAX-ACCESS    read-write
   STATUS        current
   DESCRIPTION " Line Coding

                 Defines the transmission encoding of bits:

                   * B8ZS: Bipolar with 8-Zeros Substitution (T1 lines)
                   * HDB3: High-Density Bipolar with 3-zeros (E1 lines)
                   * AMI: Alternate Mark Inversion (E1 and T1 lines)

                 For further information, see ITU-T Recommendation G.703.
                 "
   DEFVAL        { b8zs }
   ::= { physicalLinkEntry 200 }

  -- Columnar:Line Framing

  physicalLinkLineFraming OBJECT-TYPE
   SYNTAX        INTEGER { sf(100) , esf(200) , crc4(300) , noCrc4(400) }
   MAX-ACCESS    read-write
   STATUS        current
   DESCRIPTION " Line Framing

                 Defines the frame format:

                   * SF: Super frame. Sometimes known as D4 (T1 lines)
                   * ESF: Extended super frame (T1 lines)
                   * CRC4: Cyclic redundancy check 4 (E1 lines)
                   * NO-CRC4: No Cyclic redundancy check 4 (E1 lines)

                 For further information, see ITU-T Recommendation G.704.
                 "
   DEFVAL        { esf }
   ::= { physicalLinkEntry 300 }

  -- Columnar:Clock Mode

  physicalLinkClockMode OBJECT-TYPE
   SYNTAX        INTEGER { master(100) , slave(200) }
   MAX-ACCESS    read-write
   STATUS        current
   DESCRIPTION " Clock Mode

                 A port can either generate the clocking for the line or
                 accept the clock from the line. The options master or slave
                 determine the clocking method:

                   * Master: Generates clock
                   * Slave: Accepts clock

                 "
   DEFVAL        { slave }
   ::= { physicalLinkEntry 400 }

  -- Columnar:Monitor Link State Enable

  physicalLinkMonitorLinkStateEnable OBJECT-TYPE
   SYNTAX        MxEnableState
   MAX-ACCESS    read-write
   STATUS        current
   DESCRIPTION " Monitor Link State Enable

                 Monitors the physical link state of an E&M interface.

                 Enable: An E&M endpoint's operational state is affected by
                 its interface physical link state. When the link state of an
                 E&M interface is down, the operational state of its matching
                 endpoint becomes 'disable'.

                 Disable: An E&M endpoint's operational state is not affected
                 by its interface physical link state.

                 "
   DEFVAL        { enable }
   ::= { physicalLinkEntry 500 }

  -- Columnar:Port Pinout

  physicalLinkPortPinout OBJECT-TYPE
   SYNTAX        INTEGER { auto(100) , master(200) , slave(300) }
   MAX-ACCESS    read-write
   STATUS        current
   DESCRIPTION " Port Pinout

                 Defines the port pinout:

                   * Auto: The pinout is set according to the clock mode.
                   * Master: Force the pinout to Master regardless of the
                     clock mode.
                   * Slave: Force the pinout to Slave regardless of the clock
                     mode.

                 See the PhysicalLink.ClockMode parameter for a description of
                 the clock mode.

                 "
   DEFVAL        { auto }
   ::= { physicalLinkEntry 600 }

 -- End of table:Physical Link

-- End of group:Signaling Channel Configuration

-- ****************************************************************************

-- Group:Automatic Configuration

-- ****************************************************************************

autoConfigure OBJECT IDENTIFIER
 ::= { eamMIBObjects 400 }
 -- Scalar:Auto Configure Status

 autoConfigureStatus OBJECT-TYPE
  SYNTAX        INTEGER { idle(100) , sensing(200) }
  MAX-ACCESS    read-only
  STATUS        current
  DESCRIPTION " Auto Configure Status

                Indicates the current status of the E&M automatic
                configuration mechanism.

                  * Idle: The automatic configuration mechanism is ready to be
                    started.
                  * Sensing: The automatic configuration mechanism is
                    currently started and is testing different E&M
                    configurations to obtain a link up.

                "
  ::= { autoConfigure 100 }

 -- Scalar:Last Auto Configure Result

 lastAutoConfigureResult OBJECT-TYPE
  SYNTAX        INTEGER { none(100) , success(200) , fail(300) , aborted(400)
                }
  MAX-ACCESS    read-only
  STATUS        current
  DESCRIPTION " Last Auto Configure Result

                Result of the last E&M automatic configuration.

                  * None: No result is available.
                  * Success: The last automatic configuration succeeded.
                  * Fail: The last automatic configuration failed.
                  * Aborted: The last automatic configuration has been
                    cancelled by the user.

                "
  ::= { autoConfigure 200 }

-- End of group:Automatic Configuration

-- ****************************************************************************

-- Group:Notification Messages Configuration

-- ****************************************************************************

notificationsGroup OBJECT IDENTIFIER
 ::= { eamMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with a 'Informational' and
                    higher severity are issued.
                  * Warning: Notification messages with a 'Warning' and higher
                    severity are issued.
                  * Error: Notification messages with an 'Error' and higher
                    severity are issued.
                  * Critical: Notification messages with a 'Critical' severity
                    are issued.

                "
  DEFVAL        { warning }
  ::= { notificationsGroup 100 }

-- End of group:Notification Messages Configuration

-- ****************************************************************************

-- Group:Configuration Settings

-- ****************************************************************************

configurationGroup OBJECT IDENTIFIER
 ::= { eamMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for the
                configuration to fully take effect.

                  * Yes: Service needs to be restarted.
                  * No: Service does not need to be restarted.

                Services can be restarted by using the
                Scm.ServiceCommands.Restart command.

                "
  ::= { configurationGroup 100 }

-- End of group:Configuration Settings

END

-- **SDOC***********************************************************************
-- *****************************************************************************
--
--      Copyright(c) 2004-2005 Mediatrix Telecom, Inc.
--      Copyright(c) 2008 Media5 Corporation. ("Media5")
--
--  NOTICE:
--   This document contains information that is confidential and proprietary
--   to Media5.
--
--   Media5 reserves all rights to this document as well as to the Intellectual
--   Property of the document and the technology and know-how that it includes
--   and represents.
--
--   This publication cannot be reproduced, neither in whole nor in part, in
--   any form whatsoever without written prior approval by Media5.
--
--   Media5 reserves the right to revise this publication and make changes at
--   any time and without the obligation to notify any person and/or entity of
--   such revisions and/or changes.
--
-- *****************************************************************************
-- *****************************************************************************
--
-- Configuration of signaling and telephony attributes of a H.323 unit. Applies
-- to H.323 terminals and H.323 gateways.
--
-- A H.323 terminal is a unit with only FXS ports. A H.323 gateway is a unit
-- with only FXO ports.
--
-- *****************************************************************************
-- **EDOC***********************************************************************

MX-H323-ATTRIBUTES-MIB
DEFINITIONS ::= BEGIN

IMPORTS
        OBJECT-TYPE,
        MODULE-IDENTITY,
        OBJECT-IDENTITY,
        Unsigned32
    FROM SNMPv2-SMI
        OBJECT-GROUP,
        NOTIFICATION-GROUP,
        MODULE-COMPLIANCE
    FROM SNMPv2-CONF
        MxEnableState,
        MxIpAddress,
        MxIpPort,
        MxIpDhcpSiteSpecificCode
    FROM MX-TC
        ifIndex
    FROM RFC1213-MIB
        h323,
        ipAddressStatusH323,
        ipAddressConfigH323Static,
        ipAddressConfigH323Dhcp
    FROM MX-H323-MIB;

h323AttributesMIB MODULE-IDENTITY
    LAST-UPDATED "200803050000Z"
    ORGANIZATION "Mediatrix Telecom, Inc."
    CONTACT-INFO "Mediatrix Telecom, Inc.
                  4229, Garlock Street
                  Sherbrooke (Quebec)
                  Canada
                  Phone: (819) 829-8749
                  "
    DESCRIPTION "This MIB contains H.323 configuration objects."

    -- *************************************************************************
    -- Revision history
    -- *************************************************************************
    REVISION    "200808250000Z"
    DESCRIPTION "Correction of h323AttributesCalledPartyNumberTypeOfNumber enum syntax"
    
    REVISION    "200803050000Z"
    DESCRIPTION "Addition of privateNumber in h323AttributesCalledPartyNumberTypeOfNumber."

    REVISION    "200501180000Z"
    DESCRIPTION "Addition of h323AttributesVoiceCapabilitySendingMethod."

    REVISION    "200410150000Z"
    DESCRIPTION "Addition of h323AttributesParallelH245Enable."

    REVISION    "200407140000Z"
    DESCRIPTION "Addition of Unsigned32 in IMPORTS list."

    REVISION    "200401210000Z"
    DESCRIPTION "Addition of h323AttributesQ931CalledPartyNumberTable."

    REVISION    "200311050000Z"
    DESCRIPTION "Addition of h323AttributesQ931,
                 h323AttributesQ931BearerCapability and
                 h323AttributesInformationTransferCapability."

    REVISION    "200305050000Z"
    DESCRIPTION "Added h323AttributesDirectGatewayCallHost. Removed
                 h323DirectGatewayCallHost, h323DirectGatewayCallPort,
                 h323DirectGatewayCallDhcpSiteSpecificCode and
                 h323DirectGatewayCallStaticPort."

    REVISION    "200303040000Z"
    DESCRIPTION "Creation"
    ::= { h323 5 }

    -- *************************************************************************
    -- General H323 signaling configuration
    -- *************************************************************************

h323AttributesMIBObjects  OBJECT IDENTIFIER ::= { h323AttributesMIB 1 }
h323AttributesConformance OBJECT IDENTIFIER ::= { h323AttributesMIB 2 }


    -- *************************************************************************
    -- H.323 Q.931 attributes
    -- *************************************************************************

    h323AttributesQ931 OBJECT IDENTIFIER ::= { h323AttributesMIBObjects 1 }

        h323AttributesQ931BearerCapability OBJECT IDENTIFIER ::= { h323AttributesQ931 5 }

            h323AttributesInformationTransferCapability OBJECT-TYPE
                SYNTAX      INTEGER {
                                      speech(0),
                                      unrestrictedDigitalInformation(1),
                                      restrictedDigitalInformation(2),
                                      audio31kHz(3),
                                      udita(4),
                                      video(5)
                                    }
                MAX-ACCESS  read-write
                STATUS      current
                DESCRIPTION "Indicates the type of calls made by the H.323 unit. This value is used to set the
                             information transfer capability field of the bearer capability element of the SETUP
                             message (Q.931 header).

                             This information may help the called endpoint to take actions based on the nature of the
                             media stream to be established (voice-only call or data call or video call). This
                             information may impact the called endpoint on its decision to accept the call. For
                             example, a SCN gateway may not have access to enough bandwidth in order to accept a new IP
                             to SCN data call.

                             For calls between endpoints that are both on the IP network, this information may be
                             ignored by the called endpoint. This information is mostly used by SCN gateways and ISDN
                             gateways. The value of this variable should be changed only when necessary, in order to
                             adapt to third-party systems.

                             When receiving a call, this H.323 unit ignores the value of the information transfer
                             capability field.

                             speech                         : Indicates a voice-only call.

                             unrestrictedDigitalInformation : Unrestricted Digital Information (64 kbps). Indicates an
                                                              audiovisual call.

                             restrictedDigitalInformation   : Restricted Digital Information (56 kbps). Indicates an
                                                              audiovisual call.

                             audio31kHz                     : 3.1 kHz audio. Indicates a voice-only call.

                             udita                          : Unrestricted Digital Information with
                                                              Tones/Announcements. Indicates an audiovisual call.

                             video                          : Indicates an audiovisual call.

                             'speech' and 'audio31kHz' are the choices that best represent the capabilities of this
                             H.323 unit.

                             Even though this H.323 unit does not support any video capability,
                             'unrestrictedDigitalInformation', 'restrictedDigitalInformation', 'udita' and 'video'
                             are provided in order to increase interoperability with third-party systems.

                             'unrestrictedDigitalInformation' is the default value for backward compatibility issues.

                             Please refer to ITU-T Recommendation Q.931 and ITU-T Recommendation H.225.0 for more
                             information on bearer capabilities."
                DEFVAL { unrestrictedDigitalInformation }
                ::=  {  h323AttributesQ931BearerCapability 5 }


        -- *********************************************************************
        -- H.323 Signaling attributes table
        -- *********************************************************************

        h323AttributesQ931CalledPartyNumberTable OBJECT-TYPE
            SYNTAX      SEQUENCE OF H323AttributesQ931CalledPartyNumberEntry
            MAX-ACCESS  not-accessible
            STATUS      current
            DESCRIPTION "This table holds the configuration for the 'called party number' information
                         element. This information element is used by H.323 units. This configuration
                         applies to both terminal and gateway lines."
            ::= { h323AttributesQ931 15 }

            h323AttributesQ931CalledPartyNumberEntry OBJECT-TYPE
                SYNTAX      H323AttributesQ931CalledPartyNumberEntry
                MAX-ACCESS  not-accessible
                STATUS      current
                DESCRIPTION "A row in the h323AttributesQ931CalledPartyNumberTable. It contains the
                             configuration for the 'called party number' information element."
                INDEX       {
                                h323AttributesCalledPartyNumberIndex
                            }
                ::= { h323AttributesQ931CalledPartyNumberTable 1 }

                H323AttributesQ931CalledPartyNumberEntry ::= SEQUENCE
                    {
                        h323AttributesCalledPartyNumberIndex        Unsigned32,
                        h323AttributesCalledPartyNumberEnable       MxEnableState,
                        h323AttributesCalledPartyNumberDigitMap     OCTET STRING,
                        h323AttributesCalledPartyNumberTypeOfNumber INTEGER
                    }

                h323AttributesCalledPartyNumberIndex OBJECT-TYPE
                    SYNTAX      Unsigned32
                    MAX-ACCESS  read-only
                    STATUS      current
                    DESCRIPTION "Index of the h323AttributesQ931CalledPartyNumberTable."
                    ::=  { h323AttributesQ931CalledPartyNumberEntry 1 }

                h323AttributesCalledPartyNumberEnable OBJECT-TYPE
                    SYNTAX      MxEnableState
                    MAX-ACCESS  read-write
                    STATUS      current
                    DESCRIPTION "This variable is related to the 'called party number' information element
                                 (Q.931 header of the SETUP message).

                                 When all the digit maps are disabled, the 'type of number' field is set to
                                 'National number' and the 'numbering plan identification' field is set to
                                 'ISDN/telephony numbering plan'.

                                 When one or more digit maps are enabled but there is no match between the
                                 number dialed by the local user and the digit maps that are enabled, the
                                 'type of number' and the 'numbering plan identification' fields are both set
                                 to 'Unknown'.

                                 disable : the digit map is not used to set the value of the 'type of number'
                                           field.

                                 enable  : the digit map is used to set the value of the 'type of number'
                                           field."
                    DEFVAL { disable }
                    ::=  { h323AttributesQ931CalledPartyNumberEntry 5 }

                h323AttributesCalledPartyNumberDigitMap OBJECT-TYPE
                    SYNTAX      OCTET STRING (SIZE(0..63))
                    MAX-ACCESS  read-write
                    STATUS      current
                    DESCRIPTION "This variable is related to the 'called party number' information element
                                 (Q.931 header of the SETUP message).

                                 This digit map is associated with a 'type of number' value.

                                 At the beginning of an outgoing call, the destination of the call is compared
                                 with the digit maps from this table. The destination of the call is the number
                                 dialed by the local user. If there is a match, the 'type of number' value
                                 (associated with the matching digit map) is used to set the 'type of number'
                                 field. Only the digit maps that are enabled are used in the comparison."
                    DEFVAL { "" }
                    ::=  { h323AttributesQ931CalledPartyNumberEntry 10 }

                h323AttributesCalledPartyNumberTypeOfNumber OBJECT-TYPE
                    SYNTAX      INTEGER {
                                          internationalNumber(0),
                                          nationalNumber(1),
                                          subscriberNumber(2),
                                          privateNumber(3),
                                          unknown(4)
                                        }
                    MAX-ACCESS  read-write
                    STATUS      current
                    DESCRIPTION "This variable is related to the 'called party number' information element
                                 (Q.931 header of the SETUP message).

                                 This variable indicates the 'type of number' value associated with a digit map.

                                 internationalNumber : indicates that the call destination is an international
                                                       number. An international number consists of a Country Code
                                                       (CC), an optional National Destination Code (NDC) followed
                                                       by a Subscriber Number (SN). For this value, the
                                                       'type of number' field is set to 'International number' and
                                                       the 'numbering plan identification' field is set to
                                                       'ISDN/telephony numbering plan'.

                                 nationalNumber      : indicates that the call destination is a national number.
                                                       A national number consists of a National Destination Code
                                                       (NDC) followed by a Subscriber Number (SN). For this value,
                                                       the 'type of number' field is set to 'National number' and
                                                       the 'numbering plan identification' field is set to
                                                       'ISDN/telephony numbering plan'.

                                 subscriberNumber    : indicates that the call destination is a local number. A
                                                       subscriber number identifies a unique subscriber in a
                                                       network or a numbering area. For this value, the
                                                       'type of number' field is set to 'Subscriber number' and
                                                       the 'numbering plan identification' field is set to
                                                       'ISDN/telephony numbering plan'.
                                                       
                                 privateNumber       : indicates that the call destination is a private number. 
                                                       For this value, the 'type of number' field is set to 
                                                       'Unknown' and the 'numbering plan identification' field 
                                                       is set to 'Private numbering plan'.

                                 unknown             : indicates that the call destination is a number specific to
                                                       a network. The number is part of a dialing plan specific to
                                                       some network. For this value, the 'type of number' and the
                                                       'numbering plan identification' fields are set to 'Unknown'.

                                 Please refer to ITU-T Recommendation E.164 for more information on
                                 international, national and subscriber numbers.

                                 Please refer to ITU-T Recommendation Q.931 for more information on the
                                 'called party number' information element."
                    DEFVAL { nationalNumber }
                    ::=  { h323AttributesQ931CalledPartyNumberEntry 15 }


    -- *************************************************************************
    -- H.323 Signaling attributes table
    -- *************************************************************************

    h323IfSignalingAttributesTable OBJECT-TYPE
        SYNTAX      SEQUENCE OF H323IfSignalingAttributesEntry
        MAX-ACCESS  not-accessible
        STATUS      current
        DESCRIPTION "This table holds signaling attributes of a H.323 unit. This configuration
                     applies to both terminal and gateway lines.

                     Each row is used to configure the signaling attributes of one line."
        ::= { h323AttributesMIBObjects 5 }

        h323IfSignalingAttributesEntry OBJECT-TYPE
            SYNTAX      H323IfSignalingAttributesEntry
            MAX-ACCESS  not-accessible
            STATUS      current
            DESCRIPTION "Each row is used to configure the signaling attributes of one line."
            INDEX       { ifIndex }
            ::= { h323IfSignalingAttributesTable 1 }

            H323IfSignalingAttributesEntry ::= SEQUENCE
                {
                    h323AttributesEarlyH245Enable              MxEnableState,
                    h323AttributesH245TunnelingEnable          MxEnableState,
                    h323AttributesFastConnectEnable            MxEnableState,
                    h323AttributesParallelH245Enable           MxEnableState,
                    h323AttributesVoiceCapabilitySendingMethod INTEGER
                }

        h323AttributesEarlyH245Enable OBJECT-TYPE
            SYNTAX      MxEnableState
            MAX-ACCESS  read-write
            STATUS      current
            DESCRIPTION "With the early H.245 procedure, the line includes its H.245 address in the SETUP
                         message (when making a call) or in the CONNECT message (when receiving a call).
                         This H.245 address may be used by the remote endpoint to open a H.245
                         connection. The H.245 connection may be opened before the call is connected,
                         thus the qualification of 'early' H.245.

                         disable : the line does not use the early H.245 procedure.

                         enable  : the line uses the early H.245 procedure."
            DEFVAL { enable }
            ::=  {  h323IfSignalingAttributesEntry 5 }

        h323AttributesH245TunnelingEnable OBJECT-TYPE
            SYNTAX      MxEnableState
            MAX-ACCESS  read-write
            STATUS      current
            DESCRIPTION "When tunneling is enabled, the line sends H.245 messages within Q.931 messages.

                         When H.245 is enabled and the line is the calling endpoint:

                            - The line offers the use of H.245 tunneling by setting the h245Tunneling
                              field to true in the SETUP message.

                            - If the called endpoint accepts the use of H.245 tunneling, the line sets
                              the h245Tunneling field to true in every subsequent Q.931 messages.

                            - If the called endpoint refuses the use of H.245 tunneling, the line stops
                              using H.245 tunneling. The line considers the H.245 messages sent in the
                              SETUP message as ignored by the called endpoint.

                         When H.245 is disabled and the line is the calling endpoint:

                            - The line does not offer the use of H.245 tunneling. The line sets the
                              h245Tunneling field to false in every Q.931 messages.

                         When H.245 is enabled and the line is the called endpoint:

                            - When offered, the line accepts the use of H.245 tunneling. The line sets
                              the h245Tunneling field to true in the first Q.931 message sent as
                              response to the SETUP message. The line sets the h245Tunneling field to
                              true in every subsequent Q.931 messages.

                         When H.245 is disabled and the line is the called endpoint:

                            - When offered, the line refuses the use of H.245 tunneling. The line sets
                              the h245Tunneling field to false in every Q.931 messages.

                         When the line is the called endpoint, it does not use H.245 tunneling if it was
                         not offered by the calling endpoint.

                         disable : the line does not use H.245 tunneling.

                         enable  : the line uses H.245 tunneling."
            DEFVAL { disable }
            ::=  {  h323IfSignalingAttributesEntry 10 }

        h323AttributesFastConnectEnable OBJECT-TYPE
            SYNTAX      MxEnableState
            MAX-ACCESS  read-write
            STATUS      current
            DESCRIPTION "The Fast Connect procedure allows two H.323 endpoints to establish a call with
                         as few as one round-trip message exchange, enabling immediate media stream
                         delivery upon call connection.

                         When making a call, the line includes the fastStart element in the SETUP
                         message.

                         When receiving a call, the line includes the fastStart element in the ALERTING
                         message.

                         The fastStart element contains the voice and data capabilities supported by the
                         line.

                         disable : the line does not use the Fast Connect procedure.

                         enable  : the line uses the Fast Connect procedure."
            DEFVAL { enable }
            ::=  {  h323IfSignalingAttributesEntry 15 }

        h323AttributesParallelH245Enable OBJECT-TYPE
            SYNTAX      MxEnableState
            MAX-ACCESS  read-write
            STATUS      current
            DESCRIPTION "The parallel H.245 procedure allows a line to include all the following elements
                         in the SETUP message:

                             - fastStart channels

                             - terminalCapabilitySet message

                             - masterSlaveDetermination message

                         The terminalCapabilitySet and masterSlaveDetermination messages are included in
                         the parallelH245Control field of the SETUP message.

                         At the same time as sending fastStart channels, the parallel H.245 procedure is
                         useful to send capabilities that can’t be described in a fastStart channel.
                         Examples of such capabilities are the UserInputIndication capability and the RTP
                         payload types. Also, the parallel H.245 procedure accelerates the call
                         establishment when the called endpoint doesn’t support the Fast Connect
                         procedure.

                         In order to include a parallelH245Control field in the SETUP message, the
                         Fast Connect procedure must be enabled. See the h323AttributesFastConnectEnable
                         variable.

                         disable : the line does not use the parallel H.245 procedure.

                         enable  : the line uses the parallel H.245 procedure."
            DEFVAL { disable }
            ::=  {  h323IfSignalingAttributesEntry 20 }

        h323AttributesVoiceCapabilitySendingMethod OBJECT-TYPE
            SYNTAX      INTEGER {
                                  abbreviated(0),
                                  detailed(1)
                                }
            MAX-ACCESS  read-write
            STATUS      current
            DESCRIPTION "Indicates how the line constructs the fastStart element and the
                         terminalCapabilitySet message. This variable applies only to the fastStart
                         element of the SETUP message. This applies to all the terminalCapabilitySet
                         messages. This variable applies only to voice capabilities.

                         abbreviated : In the fastStart element, for each voice capability enabled, the
                                       line sends a forward OpenLogicalChannel structure with the minimum
                                       packetization period and a reverse OpenLogicalChannel structure
                                       with the maximum packetization period.

                                       In the terminalCapabilitySet message, for each voice capability
                                       enabled, the line sends a 'transmit and receive' AudioCapability
                                       structure with the maximum packetization period.

                         detailed    : In the fastStart element, for each voice capability enabled, the
                                       line sends a forward and a reverse OpenLogicalChannel structure
                                       for each packetization period step.

                                       In the terminalCapabilitySet message, for each voice capability
                                       enabled, the line sends a 'transmit and receive' AudioCapability
                                       structure for each packetization period step.

                         Each voice capability is configured with a minimum packetization period and a
                         maximum packetization period. The following table explains the concept of
                         packetization period step.

                         Voice capability family   Packetization period step
                         =======================   =========================
                         G.711                     One packetization period step at every 10 ms between
                                                   the minimum and the maximum packetization periods. For
                                                   example, if the minimum packetization period is 10 ms
                                                   and the maximum packetization period is 30 ms, the
                                                   steps are 10, 20 and 30.

                         G.729                     One packetization period step at every 10 ms between
                                                   the minimum and the maximum packetization periods. For
                                                   example, if the minimum packetization period is 40 ms
                                                   and the maximum packetization period is 50 ms, the
                                                   steps are 40 and 50.

                         G.723	                   One packetization period step at every 30 ms between
                                                   the minimum and the maximum packetization periods. For
                                                   example, if the minimum packetization period is 60 ms
                                                   and the maximum packetization period is 120 ms, the
                                                   steps are 60, 90 and 120.

                         The line can send a maximum of 20 voice capabilities:

                             - fastStart element: a maximum of 40 openLogicalChannel structures can be
                               sent in the fastStart element (20 forward openLogicalChannel structures
                               and 20 reverse openLogicalChannel structures). Each voice capability is
                               described by one forward and one reverse openLogicalChannel structure.

                             - terminalCapabilitySet message: a maximum of 20 AudioCapability structures
                               can be sent in the terminalCapabilitySet message. Each voice capability is
                               described by one AudioCapability structure.

                         If more than 20 voice capabilities are enabled by the configuration, only the
                         first 20 voice capabilities are sent. This restriction only applies to voice
                         capabilities and it has no impact on the non-voice capabilities."
            DEFVAL { detailed }
            ::=  {  h323IfSignalingAttributesEntry 25 }


    -- *************************************************************************
    -- H.323 telephony attributes table
    -- *************************************************************************

    h323IfTelephonyAttributesTable OBJECT-TYPE
        SYNTAX      SEQUENCE OF H323IfTelephonyAttributesEntry
        MAX-ACCESS  not-accessible
        STATUS      current
        DESCRIPTION "This table holds telephony attributes of a H.323 unit. This configuration
                     applies to both terminal and gateway lines.

                     Each row is used to configure the telephony attributes of one line."
        ::= { h323AttributesMIBObjects 10 }

        h323IfTelephonyAttributesEntry OBJECT-TYPE
            SYNTAX      H323IfTelephonyAttributesEntry
            MAX-ACCESS  not-accessible
            STATUS      current
            DESCRIPTION "Each row is used to configure the telephony attributes of one line."
            INDEX       { ifIndex }
            ::= { h323IfTelephonyAttributesTable 1 }

            H323IfTelephonyAttributesEntry ::= SEQUENCE
                {
                    h323AttributesDirectGatewayCallEnable MxEnableState,
                    h323AttributesDirectGatewayCallHost MxIpAddress
                }

        h323AttributesDirectGatewayCallEnable OBJECT-TYPE
            SYNTAX      MxEnableState
            MAX-ACCESS  read-write
            STATUS      current
            DESCRIPTION "The 'Direct Gateway Call' is a Mediatrix proprietary procedure. The line is
                         configured with the IP address of a gateway.

                         This procedure applies only to lines that are not configured to register:

                            - The unit is configured with the multiple registration method and the
                              registration for the line is disabled.

                            OR

                            - The unit is configured with the none registration method.

                         This procedure allows the use of a gateway without the presence of a
                         gatekeeper. The user simply dials a telephone number. The new outgoing call
                         goes directly to the gateway. The telephone number is the call destination on
                         the SCN side. This procedure is not used if the user dials an IP address before
                         dialing a telephone number.

                         disable : the line does not use the 'Direct Gateway Call' procedure.

                         enable  : the line uses the 'Direct Gateway Call' procedure."
            DEFVAL { disable }
            ::=  {  h323IfTelephonyAttributesEntry 5 }

        h323AttributesDirectGatewayCallHost OBJECT-TYPE
        SYNTAX      MxIpAddress
        MAX-ACCESS  read-write
        STATUS      current
        DESCRIPTION "The IP address of the gateway used in the 'Direct Gateway Call' procedure.

                     The 'Direct Gateway Call' is a Mediatrix proprietary procedure. It allows the
                     use of a gateway without the presence of a gatekeeper. The user simply dials a
                     telephone number. The new outgoing call goes directly to the gateway. The
                     telephone number is the call destination on the SCN side. This procedure is not
                     used if the user dials an IP address before dialing a telephone number.

                     This procedure applies only to lines with the following configuration:

                        - Multiple registration method

                        - Registration disabled"
        DEFVAL { "" }
            ::=  {  h323IfTelephonyAttributesEntry 10 }

    -- *************************************************************************
    -- Conformance information
    -- *************************************************************************

    h323AttributesCompliances OBJECT IDENTIFIER ::= { h323AttributesConformance 1 }

        h323AttributesBasicComplVer1 MODULE-COMPLIANCE
            STATUS      current
            DESCRIPTION "This is a list of conformance groups. These conformance groups contain the name
                         of objects necessary to adequately configure a H.323 unit."
            MODULE      -- MX-H323-ATTRIBUTES-MIB
            MANDATORY-GROUPS {
                               h323AttributesSignalingGroupVer1,
                               h323AttributesTelephonyGroupVer1,
                               h323AttributesQ931GroupVer1
                             }
            ::= { h323AttributesCompliances 5 }

    -- *************************************************************************
    -- MIB variable grouping
    -- *************************************************************************

    h323AttributesGroups OBJECT IDENTIFIER ::= { h323AttributesConformance 2 }

        h323AttributesSignalingGroupVer1 OBJECT-GROUP
            OBJECTS {
                        h323AttributesEarlyH245Enable,
                        h323AttributesH245TunnelingEnable,
                        h323AttributesFastConnectEnable,
                        h323AttributesParallelH245Enable,
                        h323AttributesVoiceCapabilitySendingMethod
                    }
            STATUS      current
            DESCRIPTION "A list of objects used to configure some call signaling features of a H.323
                         unit."
            ::= { h323AttributesGroups 5 }

        h323AttributesTelephonyGroupVer1 OBJECT-GROUP
            OBJECTS {
                       h323AttributesDirectGatewayCallEnable,
                       h323AttributesDirectGatewayCallHost
                    }
            STATUS      current
            DESCRIPTION "A list of objects used to configure the 'Direct Gateway Call' procedure for a
                         H.323 unit."
            ::= { h323AttributesGroups 10 }

        h323AttributesQ931GroupVer1 OBJECT-GROUP
            OBJECTS {
                       h323AttributesInformationTransferCapability,
                       h323AttributesCalledPartyNumberIndex,
                       h323AttributesCalledPartyNumberEnable,
                       h323AttributesCalledPartyNumberDigitMap,
                       h323AttributesCalledPartyNumberTypeOfNumber
                    }
            STATUS      current
            DESCRIPTION "A list of objects used to configure some Q.931 features of a H.323 unit."
            ::= { h323AttributesGroups 15 }

END

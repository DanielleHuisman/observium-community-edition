-- ****************************************************************************
-- ****************************************************************************
--
--  File: MX-H323-EXPERIMENTAL-MIB.my
--
--  Package: MediatrixMibs
--
-- ****************************************************************************
-- ****************************************************************************
--
--      Copyright(c) 2007 Media5 Corporation
--
--  NOTICE:
--   This document contains information that is confidential and proprietary to
--   Media5 Corporation.
--
--   Media5 Corporation reserves all rights to this document as well as to the
--   Intellectual Property of the document and the technology and know-how that
--   it includes and represents.
--
--   This publication cannot be reproduced, neither in whole nor in part, in any
--   form whatsoever without prior written approval by Media5 Corporation.
--
--   Media5 Corporation reserves the right to revise this publication and make
--   changes at any time and without the obligation to notify any person and/or
--   entity of such revisions and/or changes.
--
-- ****************************************************************************
-- ****************************************************************************

MX-H323-EXPERIMENTAL-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
        MxIpHostName,
        MxEnableState
    FROM MX-TC
        mediatrixExperimental
    FROM MX-SMI;

h323ExperimentalMIB MODULE-IDENTITY
    LAST-UPDATED "200704060000Z"
    ORGANIZATION "Mediatrix Telecom, Inc."
    CONTACT-INFO "Mediatrix Telecom, Inc.
                  4229, Garlock Street
                  Sherbrooke (Quebec)
                  Canada
                  Phone: (819) 829-8749
                  "
    DESCRIPTION "This MIB contains H.323 experimental and interopability configuration objects."

    -- ************************************************************************
    -- Revision history
    -- ************************************************************************
    REVISION    "200704060000Z"
    DESCRIPTION "Corrected the example in the description of variable h323AliasTypeRestriction."

    REVISION    "200503250000Z"
    DESCRIPTION "Added the h323AddT38MediaControlChannel variable."

    REVISION    "200503250000Z"
    DESCRIPTION "Added the h323UseEvenT38Port variable."

    REVISION    "200410040000Z"
    DESCRIPTION "Added the h323AcceleratedRequestedLogicalChannel variable."

    REVISION    "200408030000Z"
    DESCRIPTION "Added the h323AliasTypeRestriction variable."

    REVISION    "200310200000Z"
    DESCRIPTION "Addition of the h323VoiceIfCodecTable"

    REVISION    "200310060000Z"
    DESCRIPTION "Creation"

    ::= { mediatrixExperimental 60 }

h323ExperimentalMIBObjects   OBJECT IDENTIFIER ::= { h323ExperimentalMIB 1 }
h323ExperimentalConformance  OBJECT IDENTIFIER ::= { h323ExperimentalMIB 2 }


    -- ************************************************************************
    -- Interopability Group
    -- ************************************************************************
    h323Interop OBJECT IDENTIFIER ::= { h323ExperimentalMIBObjects 5 }

        h323RegAsGateway OBJECT-TYPE
            SYNTAX      MxEnableState
            MAX-ACCESS  read-write
            STATUS      current
            DESCRIPTION "Indicates if the unit registers as a gateway.

                         This variable applies only to H.323 terminal. A H.323 terminal is an H.323 unit
                         with only FXS ports.

                         disable : the unit registers as a H.323 terminal.

                         enable  : the unit registers as a gateway. The unit registers with an empty
                                   supported voice prefix (gateway field of the registrationRequest
                                   message). Certain gatekeepers require this distinctive feature.
                                   From the user point of view, this behavior is transparent and has no
                                   impact on the use of the unit."
            DEFVAL { disable }
            ::=  { h323Interop 5 }

        h323AliasTypeRestriction OBJECT-TYPE
            SYNTAX      MxEnableState
            MAX-ACCESS  read-write
            STATUS      current
            DESCRIPTION "This configuration compares the aliases from the unit with the destination
			aliases of the incoming call. This configuration applies only to:

			 - units with FXS ports
			 - units with no group of lines
			 - aliases of type E.164 and party number.

                        When the unit receives an incoming IP call, it compares the aliases
                        from its configuration with the destination aliases of the incoming call.
                        There must be at least one common alias in the destination of the call and
                        the configuration of the unit. This comparison is used to select the
                        line that will handle the incoming call.

                        There are two levels of comparison:

                        1.	Type of the aliases.

                        2.	Value of the aliases.

                        enable : Both the type and the value of the aliases are compared. This
                        applies to all aliases of all types.

                        disable   : For the aliases of type E.164 or party number, only the value
                        of the aliases is compared. For the aliases of other types, both the type
                        and value of the aliases are compared.

                        For instance, a unit with two FXS ports is configured with the following
                        aliases:

                        -	FXS port 1: alias of type E.164 defined as ‘1111’.

                        -	FXS port 2: alias of type E.164 defined as ‘2222’.

                        The unit receives an incoming IP call with a public subscriber number alias
                        (party number) as its destination. The public subscriber number is ‘1111’.

                        If h323AliasTypeRestriction is enabled, the call is rejected because the unit
                        is not configured with a public subscriber number equal to ‘1111’. Both the
                        type and the value of the alias are compared.

                        If h323AliasTypeRestriction is disabled, the call is accepted because the unit is
                        configured with an E.164 alias equal to ‘1111’. Only the value of the alias is
                        compared."

            DEFVAL { enable }
            ::=  { h323Interop 15 }

        h323AcceleratedRequestedLogicalChannel  OBJECT-TYPE
            SYNTAX      MxEnableState
            MAX-ACCESS  read-write
            STATUS      current
            DESCRIPTION "Modifies the H.245 OpenLogicalChannel timing during the Request Mode
                          negotiation.

                          If h323AcceleratedRequestedLogicalChannel is enabled,
                          the application immediately opens its new logical channel when receiving
                          the H.245 RequestMode or RequestModeAck.

                          If h323AcceleratedRequestedLogicalChannel is disabled,
                          even if the H.245 RequestMode or RequestModeAck is received, the application
                          opens its new logical channel only when the H.323 stack definitively closes the
                          last channel used.  This mechanism ensures to have only one logical channel
                          opened at any given time."

            DEFVAL { disable }
            ::=  { h323Interop 18 }

    -- *************************************************************************
    -- H.323 voice codec table
    -- *************************************************************************
    h323VoiceIfCodecTable  OBJECT-TYPE
        SYNTAX      SEQUENCE OF H323VoiceIfCodecEntry
        MAX-ACCESS  not-accessible
        STATUS      current
        DESCRIPTION "This table holds codec parameters specific to the H.323 protocol."
        ::= { h323Interop 20 }

        h323VoiceIfCodecEntry OBJECT-TYPE
            SYNTAX      H323VoiceIfCodecEntry
            MAX-ACCESS  not-accessible
            STATUS      current
            DESCRIPTION "Each row is used to configure the codec parameters of one line."
            INDEX       { ifIndex }
            ::= { h323VoiceIfCodecTable 1 }

            H323VoiceIfCodecEntry ::= SEQUENCE
                {
                    h323VoiceIfCodecG729Enable  MxEnableState
                }

        h323VoiceIfCodecG729Enable OBJECT-TYPE
            SYNTAX      MxEnableState
            MAX-ACCESS  read-write
            STATUS      current
            DESCRIPTION "Indicates if the g729 audio capability is enabled.

                         This variable is used in conjunction with the following variables (from
                         voiceIfMIB):

                             voiceIfCodecG729Enable                  : Indicates if the g729AnnexA audio
                                                                       capability is enabled.

                             voiceIfG729VoiceActivityDetectionEnable : Indicates if the Voice Activity
                                                                       Detection (VAD, silence
                                                                       suppression in Annex B) is enabled
                                                                       for the G.729 audio capabilities.

                             voiceIfCodecG729MinPTime                : Minimum packetization period for
                                                                       the G.729 audio capabilities
                                                                       (expressed in milliseconds).

                             voiceIfCodecG729MaxPTime                : Maximum packetization period for
                                                                       the G.729 audio capabilities
                                                                       (expressed in milliseconds).

                         The values of voiceIfCodecG729MinPTime and voiceIfCodecG729MaxPTime are used for
                         all the G.729 audio capabilities.

                         The following table shows the possible sets of G.729 audio capabilities.

                         g729AnnexA    g729       VAD        capability set
                         ----------    ----       ---        --------------

                         disable       disable    disable    { no G.729 audio codec }

                         enable        disable    disable    { g729AnnexA }

                         disable       enable     disable    { g729 }

                         enable        enable     disable    { g729AnnexA, g729 }

                         enable        disable    enable     { g729AnnexAwAnnexB, g729AnnexA }

                         disable       enable     enable     { g729wAnnexB, g729 }

                         enable        enable     enable     { g729AnnexAwAnnexB, g729AnnexA, g729wAnnexB, g729 }"
            DEFVAL { disable }
            ::=  {  h323VoiceIfCodecEntry 5 }

        h323AddT38MediaControlChannel OBJECT-TYPE
            SYNTAX      MxEnableState
            MAX-ACCESS  read-write
            STATUS      current
            DESCRIPTION "Enables or disables the mediaControlChannel address in the H.245
                         openLogicalChannelAck message.

                         disable : Remove the mediaControlChannel address in the H.245
                                   openLogicalChannelAck message.

                         enable  : Add the mediaControlChannel address in the H.245
                                   openLogicalChannelAck message."

            DEFVAL { disable }
            ::=  { h323Interop 50 }

        h323UseEvenT38Port OBJECT-TYPE
            SYNTAX      MxEnableState
            MAX-ACCESS  read-write
            STATUS      current
            DESCRIPTION "Defines if the odd lines use an even T.38 port.

                         disable : The unit uses both even and odd T.38 ports.  For example, line 1
                                   uses T.38 port 6001 and line 2 uses T.38 port 6002.

                         enable  : The unit uses only even T.38 ports.  For example, line 1
                                   uses T.38 port 6002 and line 2 uses T.38 port 6004."

            DEFVAL { disable }
            ::=  { h323Interop 100 }


    -- ************************************************************************
    -- Conformance information
    -- ************************************************************************
    h323ExperimentalCompliances OBJECT IDENTIFIER ::= { h323ExperimentalConformance 1 }

    h323ExperimentalBasicComplVer1 MODULE-COMPLIANCE
        STATUS      current
        DESCRIPTION "Minimal definitions for the H.323 experimental group."
        MODULE -- This Module
            MANDATORY-GROUPS {
                                h323ExperimentalGroupVer1
                             }
        ::= { h323ExperimentalCompliances 5 }

    -- ************************************************************************
    -- MIB variable grouping
    -- ************************************************************************
    h323ExperimentalGroups OBJECT IDENTIFIER ::= { h323ExperimentalConformance 2 }

    h323ExperimentalGroupVer1 OBJECT-GROUP
        OBJECTS {
                    h323RegAsGateway,
                    h323AddT38MediaControlChannel,
                    h323UseEvenT38Port,
                    h323VoiceIfCodecG729Enable,
                    h323AliasTypeRestriction,
                    h323AcceleratedRequestedLogicalChannel
                }
        STATUS      current
        DESCRIPTION "This group holds the objects that define the H.323
                     experimental group."
        ::= { h323ExperimentalGroups 5 }

END

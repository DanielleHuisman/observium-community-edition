-- ****************************************************************************
-- ****************************************************************************
--
--      Copyright(c) 2011 Media5 Corporation. ("Media5")
--
--  NOTICE:
--   This document contains information that is confidential and proprietary
--   to Media5.
--
--   Media5 reserves all rights to this document as well as to the Intellectual
--   Property of the document and the technology and know-how that it includes
--   and represents.
--
--   This publication cannot be reproduced, neither in whole nor in part, in
--   any form whatsoever without written prior approval by Media5.
--
--   Media5 reserves the right to revise this publication and make changes at
--   any time and without the obligation to notify any person and/or entity of
--   such revisions and/or changes.
--
-- ****************************************************************************
-- ****************************************************************************

MX-INTEROP-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
        mediatrixExperimental
    FROM MX-SMI;

mxInteropMIB MODULE-IDENTITY
    LAST-UPDATED "1101210000Z"
    ORGANIZATION "Media5 Corporation"
    CONTACT-INFO "Media5 Corporation
                  4229, Garlock Street
                  Sherbrooke (Quebec)
                  Canada
                  Phone: (819) 829-8749
                  "
    DESCRIPTION "This MIB contains Mediatrix interoperability configuration objects."

    -- ************************************************************************
    -- Revision history
    -- ************************************************************************
    REVISION    "1101210000Z"
    DESCRIPTION "January 21th, 2011 Creation"
    ::= { mediatrixExperimental 3 }

mxInteropMIBObjects  OBJECT IDENTIFIER ::= { mxInteropMIB 1 }
mxInteropConformance OBJECT IDENTIFIER ::= { mxInteropMIB 2 }

    -- ************************************************************************
    -- MX Interop Variables
    -- ************************************************************************
    mxInteropHttpUAHeaderConfig OBJECT-TYPE
        SYNTAX      OCTET STRING (SIZE(0..255))
        MAX-ACCESS  read-write
        STATUS      current
        DESCRIPTION "Customize the HTTP User-Agent header value of HTTP request.

                     The following macros are replaced by their representation:

                     %version%: Version of the application.
                     %mac%: Unit MAC address (lowercase).
                     %rev%: Hardware revision number.
                     %product%: Product name.
                     %%: A '%' sign."
        DEFVAL      { "%product%" }
        ::= { mxInteropMIBObjects  10 }


    -- ************************************************************************
    -- Conformance information
    -- ************************************************************************
    mxInteropCompliances OBJECT IDENTIFIER ::= { mxInteropConformance 1 }

    mxInteropBasicComplVer1 MODULE-COMPLIANCE
        STATUS      current
        DESCRIPTION "Minimal definitions for the MX Interop group."
        MODULE -- This Module
            MANDATORY-GROUPS {
                                mxInteropGroupVer1
                             }
        ::= { mxInteropCompliances 1 }


    -- ************************************************************************
    -- MIB variable grouping
    -- ************************************************************************
    mxInteropGroups OBJECT IDENTIFIER ::= { mxInteropConformance 2 }

    mxInteropGroupVer1 OBJECT-GROUP
        OBJECTS {
                    mxInteropHttpUAHeaderConfig
                }
        STATUS      current
        DESCRIPTION "This group holds the objects that define the
                     MX Interop group."
        ::= { mxInteropGroups 5 }
END

-- **SDOC***********************************************************************
-- *****************************************************************************
--
--              Copyright(c) 2007 Media5 Corporation
--              Copyright(c) 2008 Media5 Corporation ("Media5")
--
--  NOTICE:
--   This document contains information that is confidential and proprietary to
--   Media5.
--
--   Media5 reserves all rights to this document as well as to the Intellectual
--   Property of the document and the technology and know-how that it includes
--   and represents.
--
--   This publication cannot be reproduced, neither in whole nor in part, in any
--   form whatsoever without prior written approval by Media5.
--
--   Media5 reserves the right to revise this publication and make changes at
--   any time and without the obligation to notify any person and/or entity of
--   such revisions and/or changes.
--
-- *****************************************************************************
-- **EDOC***********************************************************************

MX-PRODUCT-NAMING-MIB
DEFINITIONS ::= BEGIN

IMPORTS
        MODULE-IDENTITY,
        OBJECT-TYPE
    FROM SNMPv2-SMI
        MODULE-COMPLIANCE,
        OBJECT-GROUP
    FROM SNMPv2-CONF
        mediatrixProducts
    FROM MX-SMI;

productNamingMIB MODULE-IDENTITY
    LAST-UPDATED "201106280000Z"
    ORGANIZATION "Mediatrix Telecom"
    CONTACT-INFO "Mediatrix Telecom
                  4229, Garlock Street
                  Sherbrooke (Quebec)
                  Canada, J1L 2C8
                  Phone: (819) 829-8749
                  http://www.mediatrix.com"
    DESCRIPTION  "This MIB is used to customize the names of Mediatrix products."


    -- *************************************************************************
    -- Revision history
    -- *************************************************************************
    REVISION    "201106280000Z"
    DESCRIPTION "Added Mediatrix LP16 and LP24 product names."
    REVISION    "200910010000Z"
    DESCRIPTION "Corrected productNaming4104Plus product name."
    REVISION    "200808120000Z"
    DESCRIPTION "Added the Ciena LE46 VM product name."
    REVISION    "200806170000Z"
    DESCRIPTION "Added Mediatrix 4104 Plus product name."
    REVISION    "200712110000Z"
    DESCRIPTION "Added Mediatrix 4102 and 0102 product name."
    REVISION    "200703210000Z"
    DESCRIPTION "Added Mediatrix 4104 product name."
    REVISION    "200701080000Z"
    DESCRIPTION "Added Mediatrix 4108, 4116 and 4124 product names."
    REVISION    "200506230000Z"
    DESCRIPTION "Added Mediatrix Liaison 312 and 322 product names."
    REVISION    "200504150000Z"
    DESCRIPTION "Added Mediatrix Liaison 512 and 522 product names."
    REVISION    "200402020000Z"
    DESCRIPTION "Added Mediatrix 2102 product name"
    REVISION    "200302250000Z"
    DESCRIPTION "Creation."
    ::= { mediatrixProducts 1000 }

productNamingMIBObjects OBJECT IDENTIFIER ::= { productNamingMIB 1 }
productNamingConformance OBJECT IDENTIFIER ::= { productNamingMIB 5 }


    -- *************************************************************************
    -- PlatformName variables.
    -- *************************************************************************
    productNamingPlatformName OBJECT-TYPE
        SYNTAX      OCTET STRING (SIZE(0..255))
        MAX-ACCESS  read-only
        STATUS      current
        DESCRIPTION "This object contains the product name for this IAD."
        DEFVAL      { "" }
        ::= { productNamingMIBObjects  15 }

    -- *************************************************************************
    -- PlatformNames variables.
    -- *************************************************************************
    productNamingPlatforms OBJECT IDENTIFIER ::= { productNamingMIBObjects 20 }

    productNaming1102 OBJECT-TYPE
        SYNTAX      OCTET STRING (SIZE(0..127))
        MAX-ACCESS  read-only
        STATUS      current
        DESCRIPTION "This object represents the custom product name for a
                     Mediatrix 1102 hardware platform."
        DEFVAL      { "Mediatrix 1102" }
        ::= { productNamingPlatforms  5 }

    productNaming1104 OBJECT-TYPE
        SYNTAX      OCTET STRING (SIZE(0..127))
        MAX-ACCESS  read-only
        STATUS      current
        DESCRIPTION "This object represents the custom product name for a
                     Mediatrix 1104 hardware platform."
        DEFVAL      { "Mediatrix 1104" }
        ::= { productNamingPlatforms  10 }

    productNaming1124 OBJECT-TYPE
        SYNTAX      OCTET STRING (SIZE(0..127))
        MAX-ACCESS  read-only
        STATUS      current
        DESCRIPTION "This object represents the custom product name for a
                     Mediatrix 1124 hardware platform."
        DEFVAL      { "Mediatrix 1124" }
        ::= { productNamingPlatforms  15 }

    productNaming1204 OBJECT-TYPE
        SYNTAX      OCTET STRING (SIZE(0..127))
        MAX-ACCESS  read-only
        STATUS      current
        DESCRIPTION "This object represents the custom product name for a
                     Mediatrix 1204 hardware platform."
        DEFVAL      { "Mediatrix 1204" }
        ::= { productNamingPlatforms  20 }

    productNaming2102 OBJECT-TYPE
        SYNTAX      OCTET STRING (SIZE(0..127))
        MAX-ACCESS  read-only
        STATUS      current
        DESCRIPTION "This object represents the custom product name for a
                     Mediatrix 2102 hardware platform."
        DEFVAL      { "Mediatrix 2102" }
        ::= { productNamingPlatforms  25 }

    productNamingLiaison312 OBJECT-TYPE
        SYNTAX      OCTET STRING (SIZE(0..127))
        MAX-ACCESS  read-only
        STATUS      current
        DESCRIPTION "This object represents the custom product name for a
                     Mediatrix Liaison 312 hardware platform:
                     WAN: Ethernet
                     LAN: Ethernet
                     Bypass: Not available"
        DEFVAL      { "Mediatrix Liaison 312" }
        ::= { productNamingPlatforms  30 }

    productNamingLiaison322 OBJECT-TYPE
        SYNTAX      OCTET STRING (SIZE(0..127))
        MAX-ACCESS  read-only
        STATUS      current
        DESCRIPTION "This object represents the custom product name for a
                     Mediatrix Liaison 322 hardware platform:
                     WAN: Ethernet
                     LAN: Ethernet
                     Bypass: Available"
        DEFVAL      { "Mediatrix Liaison 322" }
        ::= { productNamingPlatforms  35 }

    productNamingLiaison512 OBJECT-TYPE
        SYNTAX      OCTET STRING (SIZE(0..127))
        MAX-ACCESS  read-only
        STATUS      current
        DESCRIPTION "This object represents the custom product name for a
                     Mediatrix Liaison 512 hardware platform:
                     WAN: ADSL
                     LAN: Ethernet
                     Bypass: Not available"
        DEFVAL      { "Mediatrix Liaison 512" }
        ::= { productNamingPlatforms  75 }

    productNamingLiaison522 OBJECT-TYPE
        SYNTAX      OCTET STRING (SIZE(0..127))
        MAX-ACCESS  read-only
        STATUS      current
        DESCRIPTION "This object represents the custom product name for a
                     Mediatrix Liaison 522 hardware platform:
                     WAN: ADSL
                     LAN: Ethernet
                     Bypass: Available"
        DEFVAL      { "Mediatrix Liaison 522" }
        ::= { productNamingPlatforms  80 }

    productNaming0102 OBJECT-TYPE
        SYNTAX      OCTET STRING (SIZE(0..127))
        MAX-ACCESS  read-only
        STATUS      current
        DESCRIPTION "This object represents the custom product name for a
                     Mediatrix 0102 hardware platform."
        DEFVAL      { "Mediatrix 0102" }
        ::= { productNamingPlatforms  83 }

    productNaming4102 OBJECT-TYPE
        SYNTAX      OCTET STRING (SIZE(0..127))
        MAX-ACCESS  read-only
        STATUS      current
        DESCRIPTION "This object represents the custom product name for a
                     Mediatrix 4102 hardware platform."
        DEFVAL      { "Mediatrix 4102" }
        ::= { productNamingPlatforms  84 }

    productNaming4104 OBJECT-TYPE
        SYNTAX      OCTET STRING (SIZE(0..127))
        MAX-ACCESS  read-only
        STATUS      current
        DESCRIPTION "This object represents the custom product name for a
                     Mediatrix 4104 hardware platform."
        DEFVAL      { "Mediatrix 4104" }
        ::= { productNamingPlatforms  85 }

    productNaming4104Plus OBJECT-TYPE
        SYNTAX      OCTET STRING (SIZE(0..127))
        MAX-ACCESS  read-only
        STATUS      current
        DESCRIPTION "This object represents the custom product name for a
                     Mediatrix 4104plus hardware platform."
        DEFVAL      { "Mediatrix 4104plus" }
        ::= { productNamingPlatforms  88 }

    productNaming4108 OBJECT-TYPE
        SYNTAX      OCTET STRING (SIZE(0..127))
        MAX-ACCESS  read-only
        STATUS      current
        DESCRIPTION "This object represents the custom product name for a
                     Mediatrix 4108 hardware platform."
        DEFVAL      { "Mediatrix 4108" }
        ::= { productNamingPlatforms  90 }

    productNaming4116 OBJECT-TYPE
        SYNTAX      OCTET STRING (SIZE(0..127))
        MAX-ACCESS  read-only
        STATUS      current
        DESCRIPTION "This object represents the custom product name for a
                     Mediatrix 4116 hardware platform."
        DEFVAL      { "Mediatrix 4116" }
        ::= { productNamingPlatforms  95 }

    productNaming4124 OBJECT-TYPE
        SYNTAX      OCTET STRING (SIZE(0..127))
        MAX-ACCESS  read-only
        STATUS      current
        DESCRIPTION "This object represents the custom product name for a
                     Mediatrix 4124 hardware platform."
        DEFVAL      { "Mediatrix 4124" }
        ::= { productNamingPlatforms  100 }

    productNamingLP16 OBJECT-TYPE
        SYNTAX      OCTET STRING (SIZE(0..127))
        MAX-ACCESS  read-only
        STATUS      current
        DESCRIPTION "This object represents the custom product name for a
                     Mediatrix LP16 hardware platform."
        DEFVAL      { "Mediatrix LP16" }
        ::= { productNamingPlatforms  105 }

    productNamingLP24 OBJECT-TYPE
        SYNTAX      OCTET STRING (SIZE(0..127))
        MAX-ACCESS  read-only
        STATUS      current
        DESCRIPTION "This object represents the custom product name for a
                     Mediatrix LP24 hardware platform."
        DEFVAL      { "Mediatrix LP24" }
        ::= { productNamingPlatforms  110 }

    ----------------------------------------------------------------------
    -- IMPORTANT INTERNAL NOTE:
    -- The "plus" product should be written in lowercase without space.
    -- e.g. : 4104plus, 4402plus, etc. See CR28409 in SIP5.0 for details.
    ----------------------------------------------------------------------
    -- productNaming44XXplus OBJECT-TYPE
    -- SYNTAX      OCTET STRING (SIZE(0..127))
    -- MAX-ACCESS  read-only
    -- STATUS      current
    -- DESCRIPTION "This object represents the custom product name for a
    --              Mediatrix 4XXXplus hardware platform."
    -- DEFVAL      { "Mediatrix 4XXXplus" }
    -- ::= { productNamingPlatforms  YZ }

    productNamingLE46VM OBJECT-TYPE
        SYNTAX      OCTET STRING (SIZE(0..127))
        MAX-ACCESS  read-only
        STATUS      current
        DESCRIPTION "This object represents the custom product name for the Mediatrix
                     Voice Module on the Ciena LE-46 hardware platform."
        DEFVAL      { "Ciena LE46 VM" }
        ::= { productNamingPlatforms  120 }


    -- *************************************************************************
    -- Conformance information
    -- *************************************************************************
    productNamingCompliances OBJECT IDENTIFIER ::= { productNamingConformance 1 }

    productNamingComplVer1 MODULE-COMPLIANCE
        STATUS      current
        DESCRIPTION
            "List of groups required to support product naming customization."
        MODULE  -- This Module
            MANDATORY-GROUPS {
                                productNamingPlatformsVer1
                             }
        ::= { productNamingCompliances 1 }

    -- *************************************************************************
    --  MIB variable grouping
    -- *************************************************************************
    productNamingGroups OBJECT IDENTIFIER ::= { productNamingConformance 5 }

    productNamingPlatformsVer1 OBJECT-GROUP
        OBJECTS {
                    productNamingPlatformName,
                    productNaming1102,
                    productNaming1104,
                    productNaming1124,
                    productNaming1204,
                    productNaming2102,
                    productNamingLiaison512,
                    productNamingLiaison522,
                    productNaming0102,
                    productNaming4102,
                    productNaming4104,
                    productNaming4104Plus,
                    productNaming4108,
                    productNaming4116,
                    productNaming4124,
                    productNamingLP16,
                    productNamingLP24,
                    productNamingLE46VM
                }
        STATUS current
        DESCRIPTION
            "A collection of objects that defines the characteristics of
            product naming customization."
        ::= { productNamingGroups 10 }
END

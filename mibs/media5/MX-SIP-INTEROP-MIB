-- ****************************************************************************
-- ****************************************************************************
--
--  File: MX-SIP-INTEROP-MIB.my
--
--  Package: MediatrixMibs
--
-- ****************************************************************************
-- ****************************************************************************
--
--      Copyright(c) 2002-2005 Mediatrix Telecom, Inc.
--      Copyright(c) 2007 Media5 Corporation. ("Media5")
--
--  NOTICE:
--   This document contains information that is confidential and proprietary
--   to Media5.
--
--   Media5 reserves all rights to this document as well as to the Intellectual
--   Property of the document and the technology and know-how that it includes
--   and represents.
--
--   This publication cannot be reproduced, neither in whole nor in part, in
--   any form whatsoever without written prior approval by Media5.
--
--   Media5 reserves the right to revise this publication and make changes at
--   any time and without the obligation to notify any person and/or entity of
--   such revisions and/or changes.
--
-- ****************************************************************************
-- ****************************************************************************

MX-SIP-INTEROP-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
         MxEnableState
    FROM MX-TC
        mediatrixExperimental
    FROM MX-SMI;

sipInteropMIB MODULE-IDENTITY
    LAST-UPDATED "201012100000Z"
    ORGANIZATION "Mediatrix Telecom"
    CONTACT-INFO "Mediatrix Telecom
                  4229, Garlock Street
                  Sherbrooke (Quebec)
                  Canada
                  Phone: (819) 829-8749
                  "
    DESCRIPTION "This MIB contains SIP interoperability configuration objects."

    -- ************************************************************************
    -- Revision history
    -- ************************************************************************
    REVISION    "201012100000Z"
    DESCRIPTION "Added sipInteropUAHeaderConfig."
    REVISION    "201010050000Z"
    DESCRIPTION "Added sipInteropAutomaticRejectionCode."
    REVISION    "200910280000Z"
    DESCRIPTION "Added sipInteropBehaviorOnT38InviteRejectedWith606."
    REVISION    "200909300000Z"
    DESCRIPTION "Added sipInteropSipOptionsMethodSupport."
    REVISION    "200908100000Z"
    DESCRIPTION "Added sipInteropAllowMultipleActiveMediaInAnswer."
    REVISION    "200904230000Z"
    DESCRIPTION "Added sipInteropFromUriDomainSelection."
    REVISION    "200903270000Z"
    DESCRIPTION "Added sipInteropIgnoreMediaRenegotiationAfterCngDetection."
    REVISION    "200811260000Z"
    DESCRIPTION "Added sipInteropT38NoSignalBehavior."
    REVISION    "200811180000Z"
    DESCRIPTION "Added sipInteropOnHoldAnswerSdpStreamDirection. Updated
                 and sipInteropOnHoldSdpStreamDirection."
    REVISION    "200810310000Z"
    DESCRIPTION "Fix typo in sipInteropConferenceServerMechanism."
    REVISION    "200810170000Z"
    DESCRIPTION "Added sipInteropConferenceServerMecanism."
    REVISION    "200806120000Z"
    DESCRIPTION "Updated sipInteropTransferVersion."
    REVISION    "200803030000Z"
    DESCRIPTION "Added InteropEscapePoundInSipUriUsername."
    REVISION    "200801110000Z"
    DESCRIPTION "Added sipInteropIgnoreUsernameParam."
    REVISION    "200708080000Z"
    DESCRIPTION "Added sipInteropMwiMessageSummaryValidation."
    REVISION    "200708060000Z"
    DESCRIPTION "Added sipInteropAllowAsymmetricDtmfPayloadType and updated
                 sipInteropUseDtmfPayloadTypeFoundInAnswer."
    REVISION    "200708010000Z"
    DESCRIPTION "Added sipInteropCallWaitingToneControlViaSipInfo."
    REVISION    "200707180000Z"
    DESCRIPTION "Added sipInteropUsePAssertedHeader."
    REVISION    "200707030000Z"
    DESCRIPTION "Added sipInteropUseSipDomainInRequestURI."
    REVISION    "200706200000Z"
    DESCRIPTION "Added sipInteropRetryFailedRegistration."
    REVISION    "200706140000Z"
    DESCRIPTION "Updated sipInteropRegisterHomeDomainHostOverride."
    REVISION    "200705280000Z"
    DESCRIPTION "Added sipInteropRegisterHomeDomainHostOverride."
    REVISION    "200705030000Z"
    DESCRIPTION "Added sipInteropUseItuT38Format."
    REVISION    "200704180000Z"
    DESCRIPTION "Added sipInteropDefaultPublicationExpiration."
    REVISION    "200702020000Z"
    DESCRIPTION "Addition of the sipInteropInternationalCodeMapping group to hold
                 sipInteropInternationalCodeMappingEnable and
                 sipInteropInternationalCodeMappingString"
    REVISION    "200702230000Z"
    DESCRIPTION "Added sipInteropRemoveOutboundProxyRouteHeader."
    REVISION    "200605240000Z"
    DESCRIPTION "Added sipInteropAckUnsupportedInfoRequests."
    REVISION    "200510070000Z"
    DESCRIPTION "Added sipInteropProxyAuthenticationUriParametersEnable."
    REVISION    "200506280000Z"
    DESCRIPTION "Modified the sipInteropSymmetricUdpSourcePortEnable and
                 sipInteropMaxForwardsValue descriptions."
    REVISION    "200505200000Z"
    DESCRIPTION "Added sipInteropUseDtmfPayloadTypeFoundInAnswer."
    REVISION    "200501250000Z"
    DESCRIPTION "Added sipInteropIgnoreViaBranchIdInCancelEnable."
    REVISION    "200501100000Z"
    DESCRIPTION "Added sipInteropAuthenticationQop."
    REVISION    "200412220000Z"
    DESCRIPTION "Added sipInteropRingingResponseCode."
    REVISION    "200411020000Z"
    DESCRIPTION "Added sipInteropDefaultRegistrationExpiration."
    REVISION    "200410250000Z"
    DESCRIPTION "Added sipInteropBranchMatchingMethod."
    REVISION    "200410040000Z"
    DESCRIPTION "Added sipInteropDtmfTransportBySipProtocol,
                 sipInteropDtmfTransportMethod and sipInteropDtmfTransportDuration."
    REVISION    "200409290000Z"
    DESCRIPTION "Added sipInteropRejectCodeForNoRessource."
    REVISION    "200409210000Z"
    DESCRIPTION "Added sipInteropLockDnsSrvRecordPerCallEnable and
                 sipInteropReuseCredentialEnable."
    REVISION    "200407280000Z"
    DESCRIPTION "Added sipInteropReferredByConfig"
    REVISION    "200406140000Z"
    DESCRIPTION "Updated sipInteropOnHoldSdpStreamDirection description."
    REVISION    "200406020000Z"
    DESCRIPTION "Added sipInteropSdpOriginLineSessionIDAndVersionMaxLength."
    REVISION    "200404270000Z"
    DESCRIPTION "Added sipInteropSdpDirectionAttributeEnable and updated the
                 sipInteropOnHoldSdpStreamDirection description."
    REVISION    "200404210000Z"
    DESCRIPTION "Added sipInteropLocalRingOnProvisionalResponse"
    REVISION    "200403250000Z"
    DESCRIPTION "Added sipInteropOnHoldSdpStreamDirection"
    REVISION    "200402130000Z"
    DESCRIPTION "Added sipInteropSendUAHeaderEnable"
    REVISION    "200311170000Z"
    DESCRIPTION "Fixed typo in sipInteropReplacesVersion variable."
    REVISION    "200311060000Z"
    DESCRIPTION "Added sipInteropMaxForwardsValue variable."
    REVISION    "200311050000Z"
    DESCRIPTION "Added sipInteropSymmetricUdpSourcePortEnable variable."
    REVISION    "200311030000Z"
    DESCRIPTION "Added sipInteropReplacesVersion variable."
    REVISION    "200303110000Z"
    DESCRIPTION "Updated sipInteropTransmissionTimeout description."
    REVISION    "200210280000Z"
    DESCRIPTION "Added sipInteropTransmissionTimeout variable."
    REVISION    "200210160000Z"
    DESCRIPTION "Added variables sipInteropTransferVersion and
                 sipInteropSessionTimerVersion."
    REVISION    "200210010000Z"
    DESCRIPTION "Created"
    ::= { mediatrixExperimental 20 }

sipInteropMIBObjects  OBJECT IDENTIFIER ::= { sipInteropMIB 1 }
sipInteropConformance OBJECT IDENTIFIER ::= { sipInteropMIB 2 }

    -- ************************************************************************
    -- Sip Interop Variables
    -- ************************************************************************
    sipInteropReplacesConfig OBJECT-TYPE
        SYNTAX      INTEGER {
                             doNotUseReplaces(0),
                             useReplacesWithRequire(1),
                             useReplacesNoRequire(2)
                            }
        MAX-ACCESS  read-write
        STATUS      current
        DESCRIPTION "Configures usage of the Replaces header mechanism used in a
                     transfer. When supported by the target of the transfer, Replaces
                     ensures a more seamless transfer by permitting the initiating party
                     to effectively replace a current call by another instead of
                     disconnecting the call to be replaced and creating a second
                     call.

                     doNotUseReplaces :
                        The Replaces header is not used.

                     useReplacesWithRequire :
                        The Replaces header is used. It can be seen in the Refer-To
                        header found in the REFER request sent by the transferor.
                        It can also be seen in the INVITE sent by the transferee.
                        The target that supports Replaces will use its information
                        to merge the new INVITE with an existing call specified in
                        the Replaces header.

                        The transferee will require the use of the replaces extension
                        for proper completion of the transfer. If the replaces extension
                        is not supported by the target of the transfer, the unit
                        will go into a fallback algorithm to retry the transfer
                        using replaces, by reversing the roles of the target and
                        the transferee (by resending the REFER to the initial target
                        instead of the initial transferee). As a last resort (if none
                        of the participants supports replaces), the transfer will
                        be carried out without using the replaces extension.


                     useReplacesNoRequire :
                        The Replaces header is used. It can be seen in the Refer-To
                        header found in the REFER request sent by the transferor.
                        It can also be seen in the INVITE sent by the transferee.
                        The target that supports Replaces will use its information
                        to merge the new INVITE with an existing call specified in
                        the Replaces header.

                        This will disable the transfer fallback. The replaces
                        information will still be present, but no check will be
                        made that it is effectively used to complete the transfer."
        DEFVAL      { useReplacesWithRequire }
        ::= { sipInteropMIBObjects  5 }


    sipInteropTransferVersion OBJECT-TYPE
        SYNTAX      INTEGER {
                             transfer02(0),
                             transfer05UsingRefer02(1),
                             sippingTransfer01UsingReferRfc3515(2)
                            }
        MAX-ACCESS  read-write
        STATUS      current
        DESCRIPTION "Selects the version of the transfer draft that the unit will
                     use. The provisioned version is used for initiating transfers
                     and receiving them. Transfer versions other than those provisioned
                     will not work.

                     transfer02 :
                        The unit will execute transfers using the methods described
                        in the now expired draft-ietf-sip-cc-transfer-02.txt.
                        This draft was obsoleted. Its use is deprecated and
                        this setting should be used for backward compatibility
                        issues only.

                     transfer05UsingRefer02 :
                        The unit will execute transfers using the methods described
                        in the more recent draft-ietf-sip-cc-transfer-05.txt.
                        This draft version contains several enhancements over the
                        previous ones. Among others, it is possible to use the
                        replaces header to provide a more seamless attended transfer
                        to the user. This method also uses draft-ietf-sip-refer-02.txt.
                        This setting should be used if you don't need to interop
                        with transfer02-enabled parties.

                     sippingTransfer01UsingReferRfc3515 :
                        The unit executes transfers by using the methods described in
                        draft-ietf-sipping-cc-transfer-01.txt. This draft version is more
                        recent than Transfer02 and Transfer05UsingRefer02. This method
                        also uses RFC 3515 - The Session Initiation Protocol (SIP) Refer Method."
        DEFVAL      { transfer05UsingRefer02 }
        ::= { sipInteropMIBObjects  10 }


    sipInteropSessionTimerVersion OBJECT-TYPE
        SYNTAX      INTEGER {
                             sessionTimer04(0),
                             sessionTimer08(1)
                            }
        MAX-ACCESS  read-write
        STATUS      current
        DESCRIPTION "Selects the version of the session timer draft that the unit
                     will use. Session timer versions other than those provisioned
                     may not work because of backward compatibility issues between
                     the versions.

                     sessionTimer04 :
                        The unit will use the session timer extension as described
                        in the now expired draft-ietf-sip-session-timer-04.txt.
                        This draft was obsoleted. Its use is deprecated and
                        this setting should be used for backward compatibility
                        issues only.

                     sessionTimer08 :
                        The unit will use the session timer extension as described
                        in the more recent draft-ietf-sip-session-timer-08.txt.
                        This draft version contains several enhancements over the
                        previous ones, including the use of the Min-SE header.
                        This setting should be used if you don't need
                        to interoperate with session timer v4-enabled parties."
        DEFVAL      { sessionTimer08 }
        ::= { sipInteropMIBObjects  15 }


    sipInteropTransmissionTimeout OBJECT-TYPE
        SYNTAX      Unsigned32 ( 1..32 )
        MAX-ACCESS  read-write
        STATUS      current
        DESCRIPTION "Changes the time to wait for a response or an ACK before considering a
                     transaction timed out. This corresponds to timers B, F and H for all transport
                     protocols and timer J for UDP. These timers are defined in section A of RFC3261.

                     This timeout will affect the number of retransmissions. Retransmissions continue
                     to follow the timing guidelines found in RFC3261.

                     For example, if using DNS SRV and multiple entries are present, this value will
                     be the time spent waiting for answers from each entry.

                     This value is expressed in seconds (s)."
        DEFVAL      { 32 }
        ::= { sipInteropMIBObjects  20 }


    sipInteropReplacesVersion OBJECT-TYPE
        SYNTAX      INTEGER {
                             replaces01(0),
                             replaces03(1)
                            }
        MAX-ACCESS  read-write
        STATUS      current
        DESCRIPTION "Selects the version of the ietf-sip-replaces draft to conform to. The
                     provisioned version affects the way blind transfers are executed.

                     replaces01 :
                        When following the sip-replaces-01 draft, the Transferor is allowed to use a
                        REFER with Replaces when proceeding to initiate a blind transfer. This, in turn,
                        results in the Transferee including a Replaces header in its INVITE to the
                        Transfer Target.

                     replaces03 :
                        The sip-replaces-03 draft forbids the use of Replaces in the case of a blind
                        transfer.  When initiating one, the Transferor first CANCELs its call with the
                        Target and then issues a REFER without Replaces to the Transferee."
        DEFVAL      { replaces01 }
        ::= { sipInteropMIBObjects  25 }

    sipInteropSymmetricUdpSourcePortEnable OBJECT-TYPE
        SYNTAX      MxEnableState
        MAX-ACCESS  read-write
        STATUS      current
        DESCRIPTION "Indicates whether the unit always uses the same local port when sending SIP
                     traffic over UDP.

                     Symmetric UDP ports are sometimes needed to traverse NAT/Firewall devices.

                     Note that when changing this setting, all destinations are automatically thrown
                     out of the penalty box, when applicable.

                     enable :
                        SIP signaling sent over UDP originates from the same port as the port on which
                        the user agent is listening. This is configured in MX-SIP-MIB's sipPort
                        variable. When enabled, ICMP messages are not processed, which means that
                        unreachable targets will take longer to detect.

                     disable :
                        SIP signaling over UDP uses a randomly-generated originating port. ICMP
                        errors are processed correctly.

                     This variable's semantics are different depending on the software version.
                     Please refer to the documentation shipped with your device for more
                     details."

        DEFVAL      { enable }
        ::=  { sipInteropMIBObjects  30 }

    sipInteropMaxForwardsValue OBJECT-TYPE
        SYNTAX      INTEGER ( -1..200 )
        MAX-ACCESS  read-write
        STATUS      current
        DESCRIPTION "Sets the value that will be used in the Max-Forwards header, in conformance
                     with RFC3261.

                     When this value is positive, the Max-Forwards header is inserted in sent SIP
                     requests.

                     To disable inclusion of this header in SIP requests, set the value to '-1'.

                     This variable's semantics are different depending on the software version.
                     Please refer to the documentation shipped with your device for more
                     details."

        DEFVAL      { -1 }
        ::=  { sipInteropMIBObjects  35 }

    sipInteropAutomaticRejectionCode OBJECT-TYPE
        SYNTAX      Unsigned32 ( 400..699 )
        MAX-ACCESS  read-write
        STATUS      current
        DESCRIPTION "Configures the SIP code to use when rejecting a call once the
                     timer specified in telephonyAttributesCallDirectionRestriction
                     elapses.

                     Examples of possible SIP code:

                     400: Bad Request
                     401: Unauthorized
                     402: Payment required
                     403: Forbidden
                     404: Not found
                     405: Method not allowed
                     406: Not acceptable
                     407: Proxy authentication required
                     408: Request timeout
                     410: Gone
                     413: Request Entity too long
                     414: Request-URI too long
                     415: Unsupported media type
                     416: Unsupported URI Scheme
                     420: Bad extension
                     421: Extension Required
                     423: Interval Too Brief
                     480: Temporarily unavailable
                     481: Call/Transaction Does not Exist
                     482: Loop Detected
                     483: Too many hops
                     484: Address incomplete
                     485: Ambiguous
                     486: Busy here
                     500: Server internal error
                     501: Not implemented
                     502: Bad gateway
                     503: Service unavailable
                     504: Server time-out
                     504: Version Not Supported
                     513: Message Too Large
                     600: Busy everywhere
                     603: Decline
                     604: Does not exist anywhere
                     "
        DEFVAL      { 480 }
        ::= { sipInteropMIBObjects  40 }

      sipInteropSendUAHeaderEnable OBJECT-TYPE
        SYNTAX      MxEnableState
        MAX-ACCESS  read-write
        STATUS      current
        DESCRIPTION "Enables/Disables sending of the SIP User-Agent header.

                     Note: The unit must be rebooted to apply the modification."
        DEFVAL      { enable }
        ::=  { sipInteropMIBObjects  50 }

      sipInteropUAHeaderConfig OBJECT-TYPE
        SYNTAX      OCTET STRING (SIZE(0..255))
        MAX-ACCESS  read-write
        STATUS      current
        DESCRIPTION "Customize the SIP User-Agent header value.

                     The following macros are replaced by their representation:

                     %version%: Version of the application.
                     %mac%: Unit MAC address (lowercase).
                     %rev%: Hardware revision number.
                     %product%: Product name.
                     %%: A '%' sign.

                     Note: The unit must be rebooted to apply the modification."
        DEFVAL      { "MxSipApp/%version%" }
        ::=  { sipInteropMIBObjects  55 }

    sipInteropSdpDirectionAttributeEnable OBJECT-TYPE
        SYNTAX      MxEnableState
        MAX-ACCESS  read-write
        STATUS      current
        DESCRIPTION "Indicates if the SDP direction attribute is present in the initial
                     INVITE sent by the unit and if the direction attribute present
                     in the SDP received from the peer is ignored or not.

                     disable :
                      - No direction attribute is present in the SDP sent by the unit.
                      - Any direction attribute found in the SDP received from the peer
                        is ignored by the unit.
                      - To put an endpoint on hold, a SDP containing a connection address
                        of '0.0.0.0' is sent.
                      The method to put a session on hold is in conformance with RFC 2543.

                     enable :
                      - The unit always sends the direction attribute in the SDP of the
                        initial INVITE.
                      - The initial handshake determines if the peer supports the direction
                        attribute or not.
                      - If present in the SDP, the direction attribute is preferred over the
                        connection address to transmit session modification information.
                      This method is in conformance with RFC 3264."
        DEFVAL      { enable }
        ::= { sipInteropMIBObjects  75 }

    sipInteropAllowMultipleActiveMediaInAnswer OBJECT-TYPE
        SYNTAX      MxEnableState
        MAX-ACCESS  read-write
        STATUS      current
        DESCRIPTION "Determines the behaviour of the device when answering a request
                     offering more than one active media.

                     disable : The answer contains only one active media. The media
                               specified as active in the answer is the top-most matching
                               one in the offer. Other medias are set to inactive.

                     enable : Each matching active media in the offer is specified as
                              active in the answer. Other medias are set to inactive."
        DEFVAL      { enable }
        ::= { sipInteropMIBObjects  95 }

    sipInteropOnHoldSdpStreamDirection OBJECT-TYPE
        SYNTAX      INTEGER {
                             inactive(0),
                             sendonly(1)
                            }
        MAX-ACCESS  read-write
        STATUS      current
        DESCRIPTION "Indicates the direction attribute and the meaning of the
                     connection address '0.0.0.0' sent in the SDP when putting
                     an endpoint on hold.

                     inactive :
                        The stream is put on hold by marking it as inactive.

                     sendonly :
                        The stream is put on hold by marking it as sendonly.
                        This method is in conformance with RFC 3264.

                     This configuration has no effect if the
                     sipInteropSdpDirectionAttributeEnable
                     variable is set to 'Disable'."
        DEFVAL      { inactive }
        ::= { sipInteropMIBObjects  100 }

    sipInteropOnHoldAnswerSdpStreamDirection OBJECT-TYPE
        SYNTAX      INTEGER {
                             inactive(0),
                             recvonly(1)
                            }
        MAX-ACCESS  read-write
        STATUS      current
        DESCRIPTION "Indicates how to set the direction attribute and the
                     connection address in the SDP when answering a hold offer
                     with the direction attribute 'sendonly'.

                     inactive :
                        The stream is marked as inactive and the connection
                        address is set to '0.0.0.0'.

                     revconly :
                        If the stream is currently active or receive only, the
                        stream is marked as recvonly and the connection address
                        is set to the IP address of the unit. If the stream is
                        currently send only or inactive, the stream is marked as
                        inactive and the connection address is set to '0.0.0.0'.
                        This method is in conformance with RFC 3264.

                     In both cases, no direction attribute is present in the SDP
                     if the sipInteropSdpDirectionAttributeEnable variable is
                     set to 'Disable'."
        DEFVAL      { recvonly }
        ::= { sipInteropMIBObjects  105 }

    sipInteropIgnoreMediaRenegotiationAfterCngDetection OBJECT-TYPE
        SYNTAX      MxEnableState
        MAX-ACCESS  read-write
        STATUS      current
        DESCRIPTION "Configures the behaviour of the unit when being re-invited
                     after a CNG detection.

                     disable :
                        Re-invites are processed normally; they are replied
                        positively or negatively depending on the unit's codec
                        configuration.

                     enable :
                        Re-invites are replied positively but the resulting
                        negotiated codecs are ignored. When a CED is detected,
                        the data codec selection procedure is applied using the
                        initial negotiated codecs.

                     This configuration has no effect if the
                     dataIfCngToneDetectionEnable variable is set to 'Enable'.

                     This variable's semantics are different depending on protocol
                     and/or hardware platforms.
                     Please refer to the documentation for more details."
        DEFVAL      { disable }
        ::= { sipInteropMIBObjects  110 }

    sipInteropMwiMessageSummaryValidation OBJECT-TYPE
        SYNTAX      MxEnableState
        MAX-ACCESS  read-write
        STATUS      current
        DESCRIPTION "Indicates how Message Waiting Indicator notifications must
                     be validated.

                     enable:
                        In order to have the Message Waiting Indicator activated,
                        the SIP notification must meet all of the following
                        requirements:

                        1 - 'Messages-Waiting' must be set to yes.
                        2 - The message waiting media type must contain 'voice-message'.
                        3 - The number of new messages must be greater than or equal to 1.

                     disable:
                        In order to have the Message Waiting Indicator activated,
                        the SIP notification must meet the following requirement:
                        'Messages-Waiting' must be set to yes.

                     Note that only Message Waiting notifications for an established
                     subscription are affected. Message Waiting notifications
                     without subscription always behaves as described in 'disable'."
        DEFVAL      { enable }
        ::= { sipInteropMIBObjects  125 }

    sipInteropSipOptionsMethodSupport OBJECT-TYPE
        SYNTAX      INTEGER {
                             none(0),
                             alwaysOk(1)
                            }
        MAX-ACCESS  read-write
        STATUS      current
        DESCRIPTION "Determines the behaviour of the device when answering a
                     SIP OPTIONS request.

                     none :
                        The unit responds with an error 405 Method not allowed.

                     alwaysOk :
                        The unit responds with a 200 OK regardless of the
                        content of the OPTIONS request."
        DEFVAL      { none }
        ::= { sipInteropMIBObjects  130 }

    sipInteropLocalRingOnProvisionalResponse OBJECT-TYPE
        SYNTAX      MxEnableState
        MAX-ACCESS  read-write
        STATUS      current
        DESCRIPTION "Specifies if the local ring should be started on reception
                     of a '18x Provisional' response without SDP.

                     Note that this variable does not affect the behaviour in case
                     where the '18x Provisional' response contains SDP.

                     disable :
                        The local ring will not be started on a '18x Provisional'
                        response without SDP, except for a '180 Ringing' message.

                     enable :
                        The local ring will be started on any '18x Provisional'
                        response without SDP."
        DEFVAL      { disable }
        ::= { sipInteropMIBObjects  150 }

    sipInteropCallWaitingToneControlViaSipInfo OBJECT-TYPE
        SYNTAX      MxEnableState
        MAX-ACCESS  read-write
        STATUS      current
        DESCRIPTION "Indicates if the call waiting tone can be controlled via the
                     SIP INFO method with the content type 'application/broadsoft'.

                     The controlled call waiting tone is played through the
                     telephony interface.

                     disable:
                        The application rejects the SIP INFO with the content type
                        'application/broadsoft'.

                     enable:
                        SIP INFO with the content type 'application/broadsoft' is
                        accepted and the call waiting tone is started or stopped
                        according to the body. The INFO method is also included in
                        the 'Allow' SIP header."
        DEFVAL      { disable }
        ::= { sipInteropMIBObjects  175 }

    sipInteropSdpOriginLineSessionIDAndVersionMaxLength OBJECT-TYPE
        SYNTAX      INTEGER {
                             max-32bits(10),
                             max-64bits(20)
                            }
        MAX-ACCESS  read-write
        STATUS      current
        DESCRIPTION "The maximum length of the session ID and the session version
                     number in the origin line (o=) of the SDP.

                     max-32bits :
                        The session ID and the session version number are represented
                        with a 32 bit integer. They have a maximum length of 10 digits.

                     max-64bits :
                        The session ID and the session version number are represented
                        with a 64 bit integer. They have a maximum length of 20 digits."
        DEFVAL      { max-64bits }
        ::= { sipInteropMIBObjects  200 }

    sipInteropIgnoreUsernameParam OBJECT-TYPE
        SYNTAX      MxEnableState
        MAX-ACCESS  read-write
        STATUS      current
        DESCRIPTION "Controls whether or not the username parameter is ignored
                     when routing an incoming SIP call to a line.

                     disable:
                        The username parameter is not ignored when routing an
                        incoming SIP call to a line. The parameter is considered
                        as part of the username.

                     enable:
                        The username parameter is ignored when routing an
                        incoming SIP call to a line."
        DEFVAL { disable }
        ::= { sipInteropMIBObjects 210 }

    sipInteropEscapePoundInSipUriUsername OBJECT-TYPE
        SYNTAX      MxEnableState
        MAX-ACCESS  read-write
        STATUS      current
        DESCRIPTION "Determines whether or not the pound character (#) must be
                     escaped in the username part of a SIP URI.

                     disable:
                        Pound character (#) is not escaped in the username part of a SIP URI.

                     enable:
                        Pound character (#) is escaped in the username part of a SIP URI.

                     Note: RFC 3261 specifies that the pound character (#) needs to
                     be escaped in the username part of a SIP URI."
        DEFVAL { enable }
        ::= { sipInteropMIBObjects 215 }

    sipInteropRegisterHomeDomainHostOverride OBJECT-TYPE
        SYNTAX      OCTET STRING (SIZE(0..255))
        MAX-ACCESS  read-write
        STATUS      current
        DESCRIPTION "Home domain override configuration. If not empty, the
                     address of record in the REGISTER uses this string
                     instead of the SIP domain or home domain proxy host (refer
                     to the variables 'sipDomain' and
                     'sipHomeDomainProxyStaticHost')."
        DEFVAL      { "" }
        ::= { sipInteropMIBObjects  225 }

    sipInteropRetryFailedRegistration OBJECT-TYPE
        SYNTAX      MxEnableState
        MAX-ACCESS  read-write
        STATUS      current
        DESCRIPTION "Controls whether or not failed registration attempts are retried periodically.

                     disable :
                        No retries are performed following a failed registration attempt.
                        Manual intervention is required for the port to attempt registration again.

                     enable :
                        A failure to register a port to the SIP Registrar triggers an
                        automatic retry every 2 minutes."
        DEFVAL      { enable }
        ::= { sipInteropMIBObjects  235 }

    sipInteropUseSipDomainInRequestURI OBJECT-TYPE
        SYNTAX      MxEnableState
        MAX-ACCESS  read-write
        STATUS      current
        DESCRIPTION "Controls whether or not the request URI is built using the SIP Domain.

                     disable :
                        The request URI is built using the home domain proxy host.
                        (refer to the variable 'sipHomeDomainProxyStaticHost')

                     enable :
                        The request URI is built using the sipDomain, if one is specified,
                        for all SIP methods with the exception of REGISTER and PUBLISH.
                        The parameter maddr is also added to the Request URI with the
                        value of the home domain proxy host.
                        (refer to the variable 'sipDomain' and 'sipHomeDomainProxyStaticHost')"
        DEFVAL      { disable }
        ::= { sipInteropMIBObjects  240 }

    sipInteropReferredByConfig OBJECT-TYPE
        SYNTAX      INTEGER {
                             useSipStackDefault(0),
                             useLocalUrl(1)
                            }
        MAX-ACCESS  read-write
        STATUS      current
        DESCRIPTION "Configures usage of the Referred-By field used in a
                     SIP REFER message.

                     useSipStackDefault :
                        Let the SIP stack populate the Referred-By header field.

                     useLocalUrl :
                        Use the local URL to populate the Referred-By header field."
        DEFVAL      { useSipStackDefault }
        ::= { sipInteropMIBObjects  250 }

    sipInteropConferenceServerMechanism OBJECT-TYPE
        SYNTAX      INTEGER {
                             rfc4579WithoutErrorRecovery(0),
                             rfc4579WithErrorRecovery(1)
                            }
        MAX-ACCESS  read-write
        STATUS      current
        DESCRIPTION "Determines the mechanism used to establish a conference
                     and how the participants are connected to the
                     conference server.

                     rfc4579WithoutErrorRecovery :
                        The connection with the conference server is made as
                        defined in RFC 4579. The participants are connected to the
                        conference server by sending the REFERs simultaneously.
                        The connection with the participant is terminated if the
                        participant fails to complete the REFER.

                     rfc4579WithErrorRecovery :
                        The connection with the conference server is made as
                        defined in RFC 4579. The participants are connected to the
                        conference server by sending the REFERs sequentially.
                        The REFER is not sent to the second participant and
                        the call stays in the same state if the first participant
                        fails to complete the REFER.

                     This variable only has an effect when sipConferenceType
                     is set to conferenceServer."
        DEFVAL      { rfc4579WithErrorRecovery }
        ::= { sipInteropMIBObjects  255 }

    sipInteropUseItuT38Format OBJECT-TYPE
        SYNTAX      MxEnableState
        MAX-ACCESS  read-write
        STATUS      current
        DESCRIPTION "Determines the format used, in the SDP portion of SIP packets, to advertise
                     the unit's T.38 capabilities.

                     disable :
                        Support for the boolean T.38 parameters T38FaxFillBitRemoval,
                        T38FaxTranscodingMMR and T38FaxTranscodingJBIG
                        is advertised by associating a value of 0 (unsupported)
                        or 1 (supported) with the parameter in the following manner:

                            a=T38FaxFillBitRemoval:0
                            a=T38FaxTranscodingMMR:0
                            a=T38FaxTranscodingJBIG:0

                     enable :
                        Support for the above T.38 parameters is advertised in conformance with ITU-T
                        Recommendation T.38, section D.2.3.  The presence of the parameter in the SDP
                        indicates support for it (without the need for an associated value), while its
                        absence means that it is not supported."
        DEFVAL      { disable }
        ::= { sipInteropMIBObjects  275 }

    sipInteropT38NoSignalBehavior OBJECT-TYPE
        SYNTAX      INTEGER {
                             receivingReInvite(0),
                             receivingAck(1)
                            }
        MAX-ACCESS  read-write
        STATUS      current
        DESCRIPTION "Determines when the unit starts sending T.38 no-signal
                     packets when being Re-Invited to switch from voice to T.38.

                     receivingReInvite :
                        The unit starts sending T.38 no-signal packets when
                        receiving the Re-Invite.

                     receivingAck :
                        The unit waits until the ACK to its 200 OK has been
                        received before sending T.38 no-signal packets.

                     This configuration has no effect if the
                     dataIfT38NoSignalEnable variable is set to 'Disable'."
        DEFVAL      { receivingReInvite }
        ::= { sipInteropMIBObjects  285 }

    sipInteropBehaviorOnT38InviteRejectedWith606 OBJECT-TYPE
            SYNTAX      INTEGER {
                             dropCall(1),
                             usePreviousMediaNegotiation(4)
                            }
            MAX-ACCESS  read-write
            STATUS      current
            DESCRIPTION "Behavior of the device when receiving a 606 SIP error
                         response to an INVITE for T.38 fax.

                         dropCall:
                            The call is dropped by sending a BYE.

                         usePreviousMediaNegotiation:
                            No re-INVITE is sent and the audio codec from the last
                            successful negotiation is used. For the remainder of the
                            call, T.38 is disabled and fax detection may trigger a switch
                            to a clear channel codec that was available in the last
                            successful negotiation."
            DEFVAL { dropCall }
            ::=  { sipInteropMIBObjects 290 }


    sipInteropLockDnsSrvRecordPerCallEnable OBJECT-TYPE
        SYNTAX      MxEnableState
        MAX-ACCESS  read-write
        STATUS      current
        DESCRIPTION "Configures the behavior of the DNS SRV feature.

                     disable :
                        The behavior follows RFC 3263.

                     enable :
                        All messages during a call or registration use the same
                        SRV record."
        DEFVAL      { disable }
        ::= { sipInteropMIBObjects  300 }

    sipInteropRemoveOutboundProxyRouteHeader OBJECT-TYPE
        SYNTAX      MxEnableState
        MAX-ACCESS  read-write
        STATUS      current
        DESCRIPTION "Determines whether or not SIP requests sent to the proxy contain a
                     Route header displaying the proxy's address.  It is only effective
                     when an outbound proxy host is configured (see sipOutboundProxyStaticHost
                     or sipOutboundProxyDhcpSiteSpecificCode).
                     It is useful when interoperating with SIP servers that do not conform
                     to RFC 3261's recommended practice concerning outbound proxy
                     usage.

                     disable :
                        Default behaviour.  SIP requests sent to the outbound proxy
                        contain a Route header, as per RFC 3261's recommendation.

                     enable :
                        SIP requests are routed to the outbound proxy without inserting
                        a Route header in the SIP packet."
        DEFVAL      { disable }
        ::= { sipInteropMIBObjects  325 }

    sipInteropReuseCredentialEnable OBJECT-TYPE
        SYNTAX      MxEnableState
        MAX-ACCESS  read-write
        STATUS      current
        DESCRIPTION "Configures how to reuse the credential in different transactions
                     of the same call or registration.

                     disable :
                        Do not reuse the credential negociated in previous transactions.

                     enable :
                        Reuse the credential negotiated in previous transactions."
        DEFVAL      { enable }
        ::= { sipInteropMIBObjects  350 }

    sipInteropUsePAssertedHeader OBJECT-TYPE
        SYNTAX      MxEnableState
        MAX-ACCESS  read-write
        STATUS      current
        DESCRIPTION "Enables the extraction of caller ID information from the
                     P-Asserted-Identity header (a SIP extension described in RFC 3325).

                     disable :
                        Caller ID data is based on the value assigned to the From header of
                        the incoming SIP request.

                     enable :
                        The unit first attempts to get the caller ID information from the
                        P-Asserted-Identity header, if present.  In case of failure, it
                        falls back to the content of the From header."
        DEFVAL      { disable }
        ::= { sipInteropMIBObjects  360 }

    sipInteropRingingResponseCode OBJECT-TYPE
        SYNTAX      INTEGER {
                             send180Ringing(0),
                             send183WithSdp(1)
                            }
        MAX-ACCESS  read-write
        STATUS      current
        DESCRIPTION "Configures the response code sent back when the endpoint starts
                     ringing.

                     send180Ringing :
                        Send out a '180 Ringing' response without a body.

                     send183WithSdp :
                        Return a '183 Session Progress' packet with SDP
                        (needed if the endpoint is required to generate ringback
                        on connection)."
        DEFVAL      { send180Ringing }
        ::= { sipInteropMIBObjects  375 }

    sipInteropRejectCodeForNoRessource OBJECT-TYPE
        SYNTAX      INTEGER {
                             temporarilyUnavailable(0),
                             busyHere(1)
                            }
        MAX-ACCESS  read-write
        STATUS      current
        DESCRIPTION "Configures the rejection code used when all lines of the group
                     are unavailable.

                     temporarilyUnavailable :
                        The '480 Temporarily Unavailable' rejection code is used.

                     busyHere :
                        The '486 Busy Here' rejection code is used."
        DEFVAL      { temporarilyUnavailable }
        ::= { sipInteropMIBObjects  400 }

    sipInteropAckUnsupportedInfoRequests OBJECT-TYPE
        SYNTAX      MxEnableState
        MAX-ACCESS  read-write
        STATUS      current
        DESCRIPTION "Determines the unit's behavior upon reception of an unknown
                     type of INFO request.

                     disable :
                        Unknown INFO requests trigger a 415 Unsupported Media Type
                        response.

                     enable :
                        Reception of unknown INFO requests is acknowledged with a
                        200 OK response."
        DEFVAL      { disable }
        ::= { sipInteropMIBObjects  415 }

    sipInteropBranchMatchingMethod OBJECT-TYPE
        SYNTAX      INTEGER {
                             rfc2543(0),
                             rfc3261(1)
                            }
        MAX-ACCESS  read-write
        STATUS      current
        DESCRIPTION "Configures the method used to match incoming SIP packets with
                     a branch.

                     rfc2543 :
                        Follows the method described in RFC2543 (section 10.1.2).

                     rfc3261 :
                        Follows the method described in RFC3261 (section 8.1.1.7)."
        DEFVAL      { rfc3261 }
        ::= { sipInteropMIBObjects  425 }

    sipInteropIgnoreViaBranchIdInCancelEnable OBJECT-TYPE
        SYNTAX      MxEnableState
        MAX-ACCESS  read-write
        STATUS      current
        DESCRIPTION "Specifies whether the SIP stack's transaction matching procedure
                     ignores the Via header field's branch parameter in CANCEL requests
                     with no To tag.

                     disable :
                        The transaction matching procedure behaves according to section
                        17.2.3 of RFC3261.

                     enable :
                        The branch parameter is not used as a transaction matching
                        criterion for CANCEL requests with no To tag."
        DEFVAL      { disable }
        ::= { sipInteropMIBObjects  432 }

    sipInteropDefaultRegistrationExpiration OBJECT-TYPE
        SYNTAX      Unsigned32 ( 1..86400 )
        MAX-ACCESS  read-write
        STATUS      current
        DESCRIPTION "Configures the default registration expiration. This value is used when
                     the contact in a registration response contains no expires or the expires
                     is badly formatted. In this case, the delay before a re-REGISTER is the
                     value set in the sipInteropDefaultRegistrationExpiration variable minus
                     the value set in the sipReRegistrationTime variable.

                     The recommended value in RFC3261 (section 10.2) is 3600.

                     This value is expressed in seconds (s)."
        DEFVAL      { 3600 }
        ::= { sipInteropMIBObjects  438 }

    sipInteropDefaultPublicationExpiration OBJECT-TYPE
        SYNTAX      Unsigned32 ( 1..86400 )
        MAX-ACCESS  read-write
        STATUS      current
        DESCRIPTION "Configures the default publication expiration. This value is used when
                     a publication response contains no or a badly formatted Expires header.
                     In this case, the delay before a re-PUBLISH is the value set in the
                     sipInteropDefaultPublicationExpiration variable minus the value set in
                     the sipPublicationRefreshTime variable.

                     This value is expressed in seconds (s)."
        DEFVAL      { 3600 }
        ::= { sipInteropMIBObjects  439 }

    sipInteropAuthenticationQop OBJECT-TYPE
        SYNTAX      INTEGER {
                             auth(0),
                             auth-int(1)
                            }
        MAX-ACCESS  read-write
        STATUS      current
        DESCRIPTION "Specifies the quality of protection the SIP User Agent
                     should apply to its authentication request.

                     auth :
                        The SIP User Agent applies authentication only.

                     auth-int :
                        The SIP User Agent applies authentication with integrity
                        protection.(see RFC 2617)"
        DEFVAL      { auth }
        ::= { sipInteropMIBObjects  444 }

    sipInteropProxyAuthenticationUriParametersEnable OBJECT-TYPE
        SYNTAX      MxEnableState
        MAX-ACCESS  read-write
        STATUS      current
        DESCRIPTION "Indicates if the uri-parameters are copied from the Request-URI
                     to the level of proxy authentication.

                     enable:Copy uri-parameters to the level of proxy
                     authentication.

                     disable:Do not copy uri-parameters to the level of proxy
                     authentication. This allows reducing the SIP packet size but
                     it does not follow the recommendations of RFC 3261."
        DEFVAL      { enable }
        ::=  { sipInteropMIBObjects 445 }

    sipInteropUseDtmfPayloadTypeFoundInAnswer OBJECT-TYPE
        SYNTAX      MxEnableState
        MAX-ACCESS  read-write
        STATUS      current
        DESCRIPTION "The default behaviour when sending an initial offer
                     that contains an RFC 2833 payload type is to keep using
                     that payload type even if the response comes back with a
                     different one.  When this variable is enabled,
                     the unit rather uses the payload type found in the answer.
                     The variable does not affect the behaviour when receiving an
                     offer. The payload type is used symmetrically meaning that
                     it's used to send and receive the DTMF. Use the variable
                     sipInteropAllowAsymmetricDtmfPayloadType to allow
                     asymmetric payload type.

                     disable :
                        Keep using the initial payload type.

                     enable :
                        Use the RFC 2833 payload type found in the received
                        answer.

                     This variable only has an effect when voiceIfDtmfTransport
                     is set to outOfBandUsingRtp."
        DEFVAL      { disable }
        ::= { sipInteropMIBObjects  447 }

    sipInteropAllowAsymmetricDtmfPayloadType OBJECT-TYPE
        SYNTAX      MxEnableState
        MAX-ACCESS  read-write
        STATUS      current
        DESCRIPTION "The default behaviour when receiving an answer to an offer
                     that contained an RFC 2833 payload type is to use that
                     payload type symmetrically (to send and receive DTMF). When
                     this variable is enabled, the unit rather uses the payload
                     type that was placed in the initial offer to receive DTMF
                     but still uses the one in the response to send them.
                     The variable does not affect the behaviour when receiving
                     an offer.

                     disable :
                        Use the RFC 2833 payload type found in the received
                        answer to receive DTMF.

                     enable :
                        Keep using the initial payload type to receive DTMF.

                     This variable only has an effect when
                     sipInteropUseDtmfPayloadTypeFoundInAnswer is set to enable."
        DEFVAL      { disable }
        ::= { sipInteropMIBObjects  448 }

        sipInteropFromUriDomainSelection OBJECT-TYPE
        SYNTAX      INTEGER {
                             sipDomain(0),
                             localHostWanAddress(1),
                             localHostFqdn(2)
                            }
        MAX-ACCESS  read-write
        STATUS      current
        DESCRIPTION "Specifies the composition of the domain used in the
                     from:URI of SIP requests sent by the unit.

                     sipDomain :
                        The domain of from:URI is built from the sipDomain
                        variable. If sipDomain is empty, sipHomeDomainProxyHost
                        is used instead.

                     localHostWanAddress :
                        The domain of from:URI is built from the unit
                        address taken from the localHostWanAddress variable.

                     localHostFqdn :
                        The domain of from:URI is built from the unit's FQDN
                        taken from the localHostFqdn variable. If localHostFqdn
                        is empty, localHostWanAddress is used instead."

        DEFVAL      { sipDomain }
        ::= { sipInteropMIBObjects  449 }


sipInteropDtmfTransportBySipProtocol OBJECT IDENTIFIER ::= { sipInteropMIBObjects 450 }

    -- *************************************************************************
    -- DTMF Transport By SIP Protocol
    -- *************************************************************************
        sipInteropDtmfTransportMethod OBJECT-TYPE
            SYNTAX      INTEGER {
                                 draftChoudhuriSipInfoDigit00(0),
                                 infoDtmfRelay(1)
                                }
            MAX-ACCESS  read-write
            STATUS      current
            DESCRIPTION "Configures the method used to transmit DTMFs over the
                         SIP protocol.

                         This variable is effective only if the endpoint is configured
                         to use the DTMF out-of-band by protocol transport method
                         (outOfBandUsingSignalingProtocol; refer to the variable
                         'voiceIfDtmfTransport').


                         draftChoudhuriSipInfoDigit00 :
                            Transmits DTMFs by using the method defined in the draft
                            'draft-choudhuri-sip-info-digit-00'.

                         infoDtmfRelay :
                            Transmits DTMFs by using a custom method.

                            This custom method requires no SDP negotiation and uses
                            a SIP INFO message with a content of type
                            'application/dtmf-relay'."
            DEFVAL      { draftChoudhuriSipInfoDigit00 }
            ::= { sipInteropDtmfTransportBySipProtocol  50 }

        sipInteropDtmfTransportDuration OBJECT-TYPE
            SYNTAX      INTEGER ( 50..2000 )
            MAX-ACCESS  read-write
            STATUS      current
            DESCRIPTION "Configures the DTMF duration sent in the INFO message when
                         using the 'infoDtmfRelay' method (refer to the variable
                         'sipInteropDtmfTransportMethod').

                         This value is expressed in milliseconds (ms)."
            DEFVAL      { 100 }
            ::= { sipInteropDtmfTransportBySipProtocol  100 }

sipInteropInternationalCodeMapping OBJECT IDENTIFIER ::= { sipInteropMIBObjects 500 }

    -- *************************************************************************
    -- International Calling Code Mapping
    -- *************************************************************************
        sipInteropInternationalCodeMappingEnable OBJECT-TYPE
            SYNTAX  MxEnableState
            MAX-ACCESS  read-write
            STATUS      current
            DESCRIPTION "Instructs the FXS unit to substitute the content of the variable
                         sipInteropInternationalCodeMappingString to the '+' character that prepends
                         the caller ID of some international calling parties.

                         disable: The default value.  No substitution is performed.  The '+'
                                  character is simply removed.

                         enable: The substitution takes place."
            DEFVAL      { disable }
            ::= { sipInteropInternationalCodeMapping  50 }

        sipInteropInternationalCodeMappingString OBJECT-TYPE
            SYNTAX  OCTET STRING (SIZE(0..10))
            MAX-ACCESS  read-write
            STATUS  current
            DESCRIPTION "The character string that is substituted to the '+' character that
                         prepends some international caller IDs when the variable sipInteropInternationalCodeMappingEnable
                         is enabled."
            DEFVAL { "" }
            ::=  {  sipInteropInternationalCodeMapping  100 }

    -- ************************************************************************
    -- Conformance information
    -- ************************************************************************
    sipInteropCompliances OBJECT IDENTIFIER ::= { sipInteropConformance 1 }

    sipInteropBasicComplVer1 MODULE-COMPLIANCE
        STATUS      current
        DESCRIPTION "Minimal definitions for the SIP protocol group"
        MODULE -- This Module
            MANDATORY-GROUPS {
                                sipInteropGroupVer1
                             }
        ::= { sipInteropCompliances 1 }


    -- ************************************************************************
    -- MIB variable grouping
    -- ************************************************************************
    sipInteropGroups OBJECT IDENTIFIER ::= { sipInteropConformance 2 }

    sipInteropGroupVer1 OBJECT-GROUP
        OBJECTS {
                    sipInteropReplacesConfig,
                    sipInteropTransferVersion,
                    sipInteropSessionTimerVersion,
                    sipInteropTransmissionTimeout,
                    sipInteropReplacesVersion,
                    sipInteropSymmetricUdpSourcePortEnable,
                    sipInteropMaxForwardsValue,
                    sipInteropAutomaticRejectionCode,
                    sipInteropSendUAHeaderEnable,
                    sipInteropUAHeaderConfig,
                    sipInteropSdpDirectionAttributeEnable,
                    sipInteropAllowMultipleActiveMediaInAnswer,
                    sipInteropOnHoldSdpStreamDirection,
                    sipInteropOnHoldAnswerSdpStreamDirection,
                    sipInteropIgnoreMediaRenegotiationAfterCngDetection,
                    sipInteropMwiMessageSummaryValidation,
                    sipInteropSipOptionsMethodSupport,
                    sipInteropLocalRingOnProvisionalResponse,
                    sipInteropCallWaitingToneControlViaSipInfo,
                    sipInteropSdpOriginLineSessionIDAndVersionMaxLength,
                    sipInteropIgnoreUsernameParam,
                    sipInteropRegisterHomeDomainHostOverride,
                    sipInteropRetryFailedRegistration,
                    sipInteropReferredByConfig,
                    sipInteropConferenceServerMechanism,
                    sipInteropUseItuT38Format,
                    sipInteropT38NoSignalBehavior,
                    sipInteropBehaviorOnT38InviteRejectedWith606,
                    sipInteropLockDnsSrvRecordPerCallEnable,
                    sipInteropRemoveOutboundProxyRouteHeader,
                    sipInteropReuseCredentialEnable,
                    sipInteropUsePAssertedHeader,
                    sipInteropRingingResponseCode,
                    sipInteropRejectCodeForNoRessource,
                    sipInteropAckUnsupportedInfoRequests,
                    sipInteropBranchMatchingMethod,
                    sipInteropIgnoreViaBranchIdInCancelEnable,
                    sipInteropDefaultRegistrationExpiration,
                    sipInteropDefaultPublicationExpiration,
                    sipInteropAuthenticationQop,
                    sipInteropProxyAuthenticationUriParametersEnable,
                    sipInteropUseDtmfPayloadTypeFoundInAnswer,
                    sipInteropAllowAsymmetricDtmfPayloadType,
                    sipInteropFromUriDomainSelection,
                    sipInteropDtmfTransportMethod,
                    sipInteropDtmfTransportDuration,
                    sipInteropInternationalCodeMappingEnable,
                    sipInteropInternationalCodeMappingString
                }
        STATUS      current
        DESCRIPTION "This group holds the objects that define the
                     main unit group."
        ::= { sipInteropGroups 5 }

END

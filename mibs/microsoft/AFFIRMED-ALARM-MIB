AFFIRMED-ALARM-MIB DEFINITIONS ::= BEGIN
IMPORTS
    MODULE-IDENTITY, enterprises       FROM SNMPv2-SMI
    DateAndTime	      			         FROM SNMPv2-TC
    ItuPerceivedSeverity		             FROM ITU-ALARM-TC-MIB
    affirmedSnmpModuleIDs, affirmedSnmpObjects 	FROM AFFIRMED-SNMP-MIB;

affirmedAlarmMIB MODULE-IDENTITY
    LAST-UPDATED "201105160000Z"
    ORGANIZATION
            "Affirmed Networks, Inc."
    CONTACT-INFO
            "Affirmed Networks, Inc.
             35 Nagog Park
             Acton, MA 
             USA "

    DESCRIPTION
            "Alarm MIB objects"
    ::= { affirmedSnmpModuleIDs 1 }

affirmedAlarmObjects OBJECT IDENTIFIER ::= { affirmedSnmpObjects 1 }
affirmedAlarmSeqId OBJECT-TYPE
    SYNTAX        INTEGER
    MAX-ACCESS    read-only
    STATUS        current
    DESCRIPTION
        "This object defines the alarm sequence id"
    ::= { affirmedAlarmObjects 1 }

-- DateAndTime ::= TEXTUAL-CONVENTION
--     DISPLAY-HINT "2d-1d-1d,1d:1d:1d.1d,1a1d:1d"
--     STATUS       current
--     DESCRIPTION
--             "A date-time specification.
-- 
--             field  octets  contents                  range
--              1      1-2   year*                     0..65536
--              2       3    month                     1..12
--              3       4    day                       1..31
--              4       5    hour                      0..23
--              5       6    minutes                   0..59
--              6       7    seconds                   0..60
--                           (use 60 for leap-second)
--              7       8    deci-seconds              0..9
--              8       9    direction from UTC        '+' / '-'
--              9      10    hours from UTC*           0..13
--             10      11    minutes from UTC          0..59
--
--             * Notes:
--             - the value of year is in network-byte order
--             - daylight saving time in New Zealand is +13
--
--             For example, Tuesday May 26, 1992 at 1:30:15 PM EDT would be
--             displayed as:
--
--                             1992-5-26,13:30:15.0,-4:0
--
--            Note that if only local time is known, then timezone
--            information (fields 8-10) is not present."
--     SYNTAX       OCTET STRING (SIZE (8 | 11))

affirmedAlarmDateTime OBJECT-TYPE
    SYNTAX         OCTET STRING (SIZE(1..128))
    MAX-ACCESS    read-only
    STATUS        current
    DESCRIPTION
        "This object defines the date and time of the alarm"
    ::= { affirmedAlarmObjects 2 }

affirmedAlarmChassisName OBJECT-TYPE
    SYNTAX    OCTET STRING (SIZE(1..63))
    MAX-ACCESS read-only
    STATUS current
    DESCRIPTION
        "Name of the Affirmed Chassis where the notification originated."
    ::= { affirmedAlarmObjects 3 }

affirmedAlarmSourceId OBJECT-TYPE
    SYNTAX    OCTET STRING (SIZE(1..255))
    MAX-ACCESS read-only
    STATUS current
    DESCRIPTION
        "Alarm source identifier"
    ::= { affirmedAlarmObjects 4 }

affirmedAlarmSeverity OBJECT-TYPE
    SYNTAX    ItuPerceivedSeverity
    MAX-ACCESS read-only
    STATUS current
    DESCRIPTION
        "Alarm severity"
    ::= { affirmedAlarmObjects 5 }
affirmedAlarmRefSeqId OBJECT-TYPE
    SYNTAX        INTEGER
    MAX-ACCESS    read-only
    STATUS        current
    DESCRIPTION
        "This object defines a reference to the sequence id of the originating alarm"
    ::= { affirmedAlarmObjects 6 }

affirmedAlarmDetails OBJECT-TYPE
    SYNTAX    OCTET STRING (SIZE(1..255))
    MAX-ACCESS read-only
    STATUS current
    DESCRIPTION
        "Alarm details"
    ::= { affirmedAlarmObjects 7 }

affirmedPotentialImpact OBJECT-TYPE
    SYNTAX    OCTET STRING (SIZE(1..750))
    MAX-ACCESS read-only
    STATUS current
    DESCRIPTION
        "Potential Impact"
    ::= { affirmedAlarmObjects 8 }

affirmedCorrectiveAction OBJECT-TYPE
    SYNTAX    OCTET STRING (SIZE(1..750))
    MAX-ACCESS read-only
    STATUS current
    DESCRIPTION
        "Corrective Action"
    ::= { affirmedAlarmObjects 9 }

affirmedVmSourceIpAddress OBJECT-TYPE
    SYNTAX    OCTET STRING (SIZE(1..255))
    MAX-ACCESS read-only
    STATUS current
    DESCRIPTION
        "VM Source Ip Adress"
    ::= { affirmedAlarmObjects 10 }
affirmedVmSourceName OBJECT-TYPE
    SYNTAX    OCTET STRING (SIZE(1..255))
    MAX-ACCESS read-only
    STATUS current
    DESCRIPTION        "VM Source Name"
    ::= { affirmedAlarmObjects 11 }

name OBJECT-TYPE
    SYNTAX    OCTET STRING (SIZE(1..255))
    MAX-ACCESS read-only
    STATUS current
    DESCRIPTION
        "name"
    ::= { affirmedAlarmObjects 12 }

chassis OBJECT-TYPE
    SYNTAX    OCTET STRING (SIZE(1..255))
    MAX-ACCESS read-only
    STATUS current
    DESCRIPTION
        "chassis"
    ::= { affirmedAlarmObjects 13 }

slot OBJECT-TYPE
    SYNTAX    OCTET STRING (SIZE(1..255))
    MAX-ACCESS read-only
    STATUS current
    DESCRIPTION
        "slot"
    ::= { affirmedAlarmObjects 14 }

cpu OBJECT-TYPE
    SYNTAX    OCTET STRING (SIZE(1..255))
    MAX-ACCESS read-only
    STATUS current
    DESCRIPTION
        "cpu"
    ::= { affirmedAlarmObjects 15 }

dirname OBJECT-TYPE
    SYNTAX    OCTET STRING (SIZE(1..255))
    MAX-ACCESS read-only
    STATUS current
    DESCRIPTION
        "dirname"
    ::= { affirmedAlarmObjects 16 }

adminstate OBJECT-TYPE
    SYNTAX    OCTET STRING (SIZE(1..255))
    MAX-ACCESS read-only
    STATUS current
    DESCRIPTION
        "adminstate"
    ::= { affirmedAlarmObjects 17 }

resource OBJECT-TYPE
    SYNTAX    OCTET STRING (SIZE(1..255))
    MAX-ACCESS read-only
    STATUS current
    DESCRIPTION
        "resource"
    ::= { affirmedAlarmObjects 18 }

sensor OBJECT-TYPE
    SYNTAX    OCTET STRING (SIZE(1..255))
    MAX-ACCESS read-only
    STATUS current
    DESCRIPTION
        "sensor"
    ::= { affirmedAlarmObjects 19 }

data OBJECT-TYPE
    SYNTAX    OCTET STRING (SIZE(1..255))
    MAX-ACCESS read-only
    STATUS current
    DESCRIPTION
        "data"
    ::= { affirmedAlarmObjects 20 }

taskname OBJECT-TYPE
    SYNTAX    OCTET STRING (SIZE(1..255))
    MAX-ACCESS read-only
    STATUS current
    DESCRIPTION
        "taskname"
    ::= { affirmedAlarmObjects 21 }

cid OBJECT-TYPE
    SYNTAX    OCTET STRING (SIZE(1..255))
    MAX-ACCESS read-only
    STATUS current
    DESCRIPTION
        "cid"
    ::= { affirmedAlarmObjects 22 }

sid OBJECT-TYPE
    SYNTAX    OCTET STRING (SIZE(1..255))
    MAX-ACCESS read-only
    STATUS current
    DESCRIPTION
        "sid"
    ::= { affirmedAlarmObjects 23 }

type OBJECT-TYPE
    SYNTAX    OCTET STRING (SIZE(1..255))
    MAX-ACCESS read-only
    STATUS current
    DESCRIPTION
        "type"
    ::= { affirmedAlarmObjects 24 }

subtype OBJECT-TYPE
    SYNTAX    OCTET STRING (SIZE(1..255))
    MAX-ACCESS read-only
    STATUS current
    DESCRIPTION
        "subtype"
    ::= { affirmedAlarmObjects 25 }

level OBJECT-TYPE
    SYNTAX    OCTET STRING (SIZE(1..255))
    MAX-ACCESS read-only
    STATUS current
    DESCRIPTION
        "level"
    ::= { affirmedAlarmObjects 26 }

time OBJECT-TYPE
    SYNTAX    OCTET STRING (SIZE(1..255))
    MAX-ACCESS read-only
    STATUS current
    DESCRIPTION
        "time"
    ::= { affirmedAlarmObjects 27 }

services OBJECT-TYPE
    SYNTAX    OCTET STRING (SIZE(1..255))
    MAX-ACCESS read-only
    STATUS current
    DESCRIPTION
        "services"
    ::= { affirmedAlarmObjects 28 }

actions OBJECT-TYPE
    SYNTAX    OCTET STRING (SIZE(1..255))
    MAX-ACCESS read-only
    STATUS current
    DESCRIPTION
        "actions"
    ::= { affirmedAlarmObjects 29 }

ledname OBJECT-TYPE
    SYNTAX    OCTET STRING (SIZE(1..255))
    MAX-ACCESS read-only
    STATUS current
    DESCRIPTION
        "ledname"
    ::= { affirmedAlarmObjects 30 }

ledcolor OBJECT-TYPE
    SYNTAX    OCTET STRING (SIZE(1..255))
    MAX-ACCESS read-only
    STATUS current
    DESCRIPTION
        "ledcolor"
    ::= { affirmedAlarmObjects 31 }

usid OBJECT-TYPE
    SYNTAX    OCTET STRING (SIZE(1..255))
    MAX-ACCESS read-only
    STATUS current
    DESCRIPTION
        "usid"
    ::= { affirmedAlarmObjects 32 }

hardorsoft OBJECT-TYPE
    SYNTAX    OCTET STRING (SIZE(1..255))
    MAX-ACCESS read-only
    STATUS current
    DESCRIPTION
        "hardorsoft"
    ::= { affirmedAlarmObjects 33 }

readerrors OBJECT-TYPE
    SYNTAX    OCTET STRING (SIZE(1..255))
    MAX-ACCESS read-only
    STATUS current
    DESCRIPTION
        "readerrors"
    ::= { affirmedAlarmObjects 34 }

writeerrors OBJECT-TYPE
    SYNTAX    OCTET STRING (SIZE(1..255))
    MAX-ACCESS read-only
    STATUS current
    DESCRIPTION
        "writeerrors"
    ::= { affirmedAlarmObjects 35 }

slotnumber OBJECT-TYPE
    SYNTAX    OCTET STRING (SIZE(1..255))
    MAX-ACCESS read-only
    STATUS current
    DESCRIPTION
        "slotnumber"
    ::= { affirmedAlarmObjects 36 }

failuredescription OBJECT-TYPE
    SYNTAX    OCTET STRING (SIZE(1..255))
    MAX-ACCESS read-only
    STATUS current
    DESCRIPTION
        "failuredescription"
    ::= { affirmedAlarmObjects 37 }

suggestedrecovery OBJECT-TYPE
    SYNTAX    OCTET STRING (SIZE(1..255))
    MAX-ACCESS read-only
    STATUS current
    DESCRIPTION
        "suggestedrecovery"
    ::= { affirmedAlarmObjects 38 }

netcontext OBJECT-TYPE
    SYNTAX    OCTET STRING (SIZE(1..255))
    MAX-ACCESS read-only
    STATUS current
    DESCRIPTION
        "netcontext"
    ::= { affirmedAlarmObjects 39 }

info OBJECT-TYPE
    SYNTAX    OCTET STRING (SIZE(1..255))
    MAX-ACCESS read-only
    STATUS current
    DESCRIPTION
        "info"
    ::= { affirmedAlarmObjects 40 }

nodename OBJECT-TYPE
    SYNTAX    OCTET STRING (SIZE(1..255))
    MAX-ACCESS read-only
    STATUS current
    DESCRIPTION
        "nodename"
    ::= { affirmedAlarmObjects 41 }

realmname OBJECT-TYPE
    SYNTAX    OCTET STRING (SIZE(1..255))
    MAX-ACCESS read-only
    STATUS current
    DESCRIPTION
        "realmname"
    ::= { affirmedAlarmObjects 42 }

localhostidentity OBJECT-TYPE
    SYNTAX    OCTET STRING (SIZE(1..255))
    MAX-ACCESS read-only
    STATUS current
    DESCRIPTION
        "localhostidentity"
    ::= { affirmedAlarmObjects 43 }

peerrealmname OBJECT-TYPE
    SYNTAX    OCTET STRING (SIZE(1..255))
    MAX-ACCESS read-only
    STATUS current
    DESCRIPTION
        "peerrealmname"
    ::= { affirmedAlarmObjects 44 }

peerhostidentity OBJECT-TYPE
    SYNTAX    OCTET STRING (SIZE(1..255))
    MAX-ACCESS read-only
    STATUS current
    DESCRIPTION
        "peerhostidentity"
    ::= { affirmedAlarmObjects 45 }

peername OBJECT-TYPE
    SYNTAX    OCTET STRING (SIZE(1..255))
    MAX-ACCESS read-only
    STATUS current
    DESCRIPTION
        "peername"
    ::= { affirmedAlarmObjects 46 }

clientid OBJECT-TYPE
    SYNTAX    OCTET STRING (SIZE(1..255))
    MAX-ACCESS read-only
    STATUS current
    DESCRIPTION
        "clientid"
    ::= { affirmedAlarmObjects 47 }

servicename OBJECT-TYPE
    SYNTAX    OCTET STRING (SIZE(1..255))
    MAX-ACCESS read-only
    STATUS current
    DESCRIPTION
        "servicename"
    ::= { affirmedAlarmObjects 48 }

apnname OBJECT-TYPE
    SYNTAX    OCTET STRING (SIZE(1..255))
    MAX-ACCESS read-only
    STATUS current
    DESCRIPTION
        "apnname"
    ::= { affirmedAlarmObjects 49 }

imsi OBJECT-TYPE
    SYNTAX    OCTET STRING (SIZE(1..255))
    MAX-ACCESS read-only
    STATUS current
    DESCRIPTION
        "imsi"
    ::= { affirmedAlarmObjects 50 }

statestring OBJECT-TYPE
    SYNTAX    OCTET STRING (SIZE(1..255))
    MAX-ACCESS read-only
    STATUS current
    DESCRIPTION
        "statestring"
    ::= { affirmedAlarmObjects 51 }

filepath OBJECT-TYPE
    SYNTAX    OCTET STRING (SIZE(1..255))
    MAX-ACCESS read-only
    STATUS current
    DESCRIPTION
        "filepath"
    ::= { affirmedAlarmObjects 52 }

ip OBJECT-TYPE
    SYNTAX    OCTET STRING (SIZE(1..255))
    MAX-ACCESS read-only
    STATUS current
    DESCRIPTION
        "ip"
    ::= { affirmedAlarmObjects 53 }

port OBJECT-TYPE
    SYNTAX    OCTET STRING (SIZE(1..255))
    MAX-ACCESS read-only
    STATUS current
    DESCRIPTION
        "port"
    ::= { affirmedAlarmObjects 54 }

chassisid OBJECT-TYPE
    SYNTAX    OCTET STRING (SIZE(1..255))
    MAX-ACCESS read-only
    STATUS current
    DESCRIPTION
        "chassisid"
    ::= { affirmedAlarmObjects 55 }

slotid OBJECT-TYPE
    SYNTAX    OCTET STRING (SIZE(1..255))
    MAX-ACCESS read-only
    STATUS current
    DESCRIPTION
        "slotid"
    ::= { affirmedAlarmObjects 56 }

cpuid OBJECT-TYPE
    SYNTAX    OCTET STRING (SIZE(1..255))
    MAX-ACCESS read-only
    STATUS current
    DESCRIPTION
        "cpuid"
    ::= { affirmedAlarmObjects 57 }

prefix OBJECT-TYPE
    SYNTAX    OCTET STRING (SIZE(1..255))
    MAX-ACCESS read-only
    STATUS current
    DESCRIPTION
        "prefix"
    ::= { affirmedAlarmObjects 58 }

numpurged OBJECT-TYPE
    SYNTAX    OCTET STRING (SIZE(1..255))
    MAX-ACCESS read-only
    STATUS current
    DESCRIPTION
        "numpurged"
    ::= { affirmedAlarmObjects 59 }

node OBJECT-TYPE
    SYNTAX    OCTET STRING (SIZE(1..255))
    MAX-ACCESS read-only
    STATUS current
    DESCRIPTION
        "node"
    ::= { affirmedAlarmObjects 60 }

diskid OBJECT-TYPE
    SYNTAX    OCTET STRING (SIZE(1..255))
    MAX-ACCESS read-only
    STATUS current
    DESCRIPTION
        "diskid"
    ::= { affirmedAlarmObjects 61 }

interfacename OBJECT-TYPE
    SYNTAX    OCTET STRING (SIZE(1..255))
    MAX-ACCESS read-only
    STATUS current
    DESCRIPTION
        "interfacename"
    ::= { affirmedAlarmObjects 62 }

threshold OBJECT-TYPE
    SYNTAX    OCTET STRING (SIZE(1..255))
    MAX-ACCESS read-only
    STATUS current
    DESCRIPTION
        "threshold"
    ::= { affirmedAlarmObjects 63 }

uepoolutilization OBJECT-TYPE
    SYNTAX    OCTET STRING (SIZE(1..255))
    MAX-ACCESS read-only
    STATUS current
    DESCRIPTION
        "uepoolutilization"
    ::= { affirmedAlarmObjects 64 }

ipversiontype OBJECT-TYPE
    SYNTAX    OCTET STRING (SIZE(1..255))
    MAX-ACCESS read-only
    STATUS current
    DESCRIPTION
        "ipversiontype"
    ::= { affirmedAlarmObjects 65 }

ifindex OBJECT-TYPE
    SYNTAX    OCTET STRING (SIZE(1..255))
    MAX-ACCESS read-only
    STATUS current
    DESCRIPTION
        "ifindex"
    ::= { affirmedAlarmObjects 66 }

ifadminstatus OBJECT-TYPE
    SYNTAX    OCTET STRING (SIZE(1..255))
    MAX-ACCESS read-only
    STATUS current
    DESCRIPTION
        "ifadminstatus"
    ::= { affirmedAlarmObjects 67 }

ifoperstatus OBJECT-TYPE
    SYNTAX    OCTET STRING (SIZE(1..255))
    MAX-ACCESS read-only
    STATUS current
    DESCRIPTION
        "ifoperstatus"
    ::= { affirmedAlarmObjects 68 }

netctxtname OBJECT-TYPE
    SYNTAX    OCTET STRING (SIZE(1..255))
    MAX-ACCESS read-only
    STATUS current
    DESCRIPTION
        "netctxtname"
    ::= { affirmedAlarmObjects 69 }

peeringname OBJECT-TYPE
    SYNTAX    OCTET STRING (SIZE(1..255))
    MAX-ACCESS read-only
    STATUS current
    DESCRIPTION
        "peeringname"
    ::= { affirmedAlarmObjects 70 }

localpeeripaddr OBJECT-TYPE
    SYNTAX    OCTET STRING (SIZE(1..255))
    MAX-ACCESS read-only
    STATUS current
    DESCRIPTION
        "localpeeripaddr"
    ::= { affirmedAlarmObjects 71 }

remotepeeripaddr OBJECT-TYPE
    SYNTAX    OCTET STRING (SIZE(1..255))
    MAX-ACCESS read-only
    STATUS current
    DESCRIPTION
        "remotepeeripaddr"
    ::= { affirmedAlarmObjects 72 }

lasterrorcode OBJECT-TYPE
    SYNTAX    OCTET STRING (SIZE(1..255))
    MAX-ACCESS read-only
    STATUS current
    DESCRIPTION
        "lasterrorcode"
    ::= { affirmedAlarmObjects 73 }

lasterrosubcode OBJECT-TYPE
    SYNTAX    OCTET STRING (SIZE(1..255))
    MAX-ACCESS read-only
    STATUS current
    DESCRIPTION
        "lasterrosubcode"
    ::= { affirmedAlarmObjects 74 }

currentstate OBJECT-TYPE
    SYNTAX    OCTET STRING (SIZE(1..255))
    MAX-ACCESS read-only
    STATUS current
    DESCRIPTION
        "currentstate"
    ::= { affirmedAlarmObjects 75 }

role OBJECT-TYPE
    SYNTAX    OCTET STRING (SIZE(1..255))
    MAX-ACCESS read-only
    STATUS current
    DESCRIPTION
        "role"
    ::= { affirmedAlarmObjects 76 }

groupname OBJECT-TYPE
    SYNTAX    OCTET STRING (SIZE(1..255))
    MAX-ACCESS read-only
    STATUS current
    DESCRIPTION
        "groupname"
    ::= { affirmedAlarmObjects 77 }

operation OBJECT-TYPE
    SYNTAX    OCTET STRING (SIZE(1..255))
    MAX-ACCESS read-only
    STATUS current
    DESCRIPTION
        "operation"
    ::= { affirmedAlarmObjects 78 }

state OBJECT-TYPE
    SYNTAX    OCTET STRING (SIZE(1..255))
    MAX-ACCESS read-only
    STATUS current
    DESCRIPTION
        "state"
    ::= { affirmedAlarmObjects 79 }

status OBJECT-TYPE
    SYNTAX    OCTET STRING (SIZE(1..255))
    MAX-ACCESS read-only
    STATUS current
    DESCRIPTION
        "status"
    ::= { affirmedAlarmObjects 80 }

activesize OBJECT-TYPE
    SYNTAX    OCTET STRING (SIZE(1..255))
    MAX-ACCESS read-only
    STATUS current
    DESCRIPTION
        "activesize"
    ::= { affirmedAlarmObjects 81 }

standbysize OBJECT-TYPE
    SYNTAX    OCTET STRING (SIZE(1..255))
    MAX-ACCESS read-only
    STATUS current
    DESCRIPTION
        "standbysize"
    ::= { affirmedAlarmObjects 82 }

mcmslotnumber OBJECT-TYPE
    SYNTAX    OCTET STRING (SIZE(1..255))
    MAX-ACCESS read-only
    STATUS current
    DESCRIPTION
        "mcmslotnumber"
    ::= { affirmedAlarmObjects 83 }

requiredsize OBJECT-TYPE
    SYNTAX    OCTET STRING (SIZE(1..255))
    MAX-ACCESS read-only
    STATUS current
    DESCRIPTION
        "requiredsize"
    ::= { affirmedAlarmObjects 84 }

availablesize OBJECT-TYPE
    SYNTAX    OCTET STRING (SIZE(1..255))
    MAX-ACCESS read-only
    STATUS current
    DESCRIPTION
        "availablesize"
    ::= { affirmedAlarmObjects 85 }

reason OBJECT-TYPE
    SYNTAX    OCTET STRING (SIZE(1..255))
    MAX-ACCESS read-only
    STATUS current
    DESCRIPTION
        "reason"
    ::= { affirmedAlarmObjects 86 }

importnum OBJECT-TYPE
    SYNTAX    OCTET STRING (SIZE(1..255))
    MAX-ACCESS read-only
    STATUS current
    DESCRIPTION
        "importnum"
    ::= { affirmedAlarmObjects 87 }

resultstr OBJECT-TYPE
    SYNTAX    OCTET STRING (SIZE(1..255))
    MAX-ACCESS read-only
    STATUS current
    DESCRIPTION
        "resultstr"
    ::= { affirmedAlarmObjects 88 }

datetime OBJECT-TYPE
    SYNTAX    OCTET STRING (SIZE(1..255))
    MAX-ACCESS read-only
    STATUS current
    DESCRIPTION
        "datetime"
    ::= { affirmedAlarmObjects 89 }

fault OBJECT-TYPE
    SYNTAX    OCTET STRING (SIZE(1..255))
    MAX-ACCESS read-only
    STATUS current
    DESCRIPTION
        "fault"
    ::= { affirmedAlarmObjects 90 }

action OBJECT-TYPE
    SYNTAX    OCTET STRING (SIZE(1..255))
    MAX-ACCESS read-only
    STATUS current
    DESCRIPTION
        "action"
    ::= { affirmedAlarmObjects 91 }

unused OBJECT-TYPE
    SYNTAX    OCTET STRING (SIZE(1..255))
    MAX-ACCESS read-only
    STATUS current
    DESCRIPTION
        "unused"
    ::= { affirmedAlarmObjects 92 }

clusterid OBJECT-TYPE
    SYNTAX    OCTET STRING (SIZE(1..255))
    MAX-ACCESS read-only
    STATUS current
    DESCRIPTION
        "clusterid"
    ::= { affirmedAlarmObjects 93 }

nodeid OBJECT-TYPE
    SYNTAX    OCTET STRING (SIZE(1..255))
    MAX-ACCESS read-only
    STATUS current
    DESCRIPTION
        "nodeid"
    ::= { affirmedAlarmObjects 94 }

subsgroupname OBJECT-TYPE
    SYNTAX    OCTET STRING (SIZE(1..255))
    MAX-ACCESS read-only
    STATUS current
    DESCRIPTION
        "subsgroupname"
    ::= { affirmedAlarmObjects 95 }

subsidfilename OBJECT-TYPE
    SYNTAX    OCTET STRING (SIZE(1..255))
    MAX-ACCESS read-only
    STATUS current
    DESCRIPTION
        "subsidfilename"
    ::= { affirmedAlarmObjects 96 }

alarmid OBJECT-TYPE
    SYNTAX    OCTET STRING (SIZE(1..255))
    MAX-ACCESS read-only
    STATUS current
    DESCRIPTION
        "alarmid"
    ::= { affirmedAlarmObjects 97 }

xpath OBJECT-TYPE
    SYNTAX    OCTET STRING (SIZE(1..255))
    MAX-ACCESS read-only
    STATUS current
    DESCRIPTION
        "xpath"
    ::= { affirmedAlarmObjects 98 }

ifname OBJECT-TYPE
    SYNTAX    OCTET STRING (SIZE(1..255))
    MAX-ACCESS read-only
    STATUS current
    DESCRIPTION
        "ifname"
    ::= { affirmedAlarmObjects 99 }

sessionthreshold OBJECT-TYPE
    SYNTAX    OCTET STRING (SIZE(1..255))
    MAX-ACCESS read-only
    STATUS current
    DESCRIPTION
        "sessionthreshold"
    ::= { affirmedAlarmObjects 100 }

sessionutilization OBJECT-TYPE
    SYNTAX    OCTET STRING (SIZE(1..255))
    MAX-ACCESS read-only
    STATUS current
    DESCRIPTION
        "sessionutilization"
    ::= { affirmedAlarmObjects 101 }

ipaddressthreshold OBJECT-TYPE
    SYNTAX    OCTET STRING (SIZE(1..255))
    MAX-ACCESS read-only
    STATUS current
    DESCRIPTION
        "ipaddressthreshold"
    ::= { affirmedAlarmObjects 102 }

ipaddressutilization OBJECT-TYPE
    SYNTAX    OCTET STRING (SIZE(1..255))
    MAX-ACCESS read-only
    STATUS current
    DESCRIPTION
        "ipaddressutilization"
    ::= { affirmedAlarmObjects 103 }

portchunkthreshold OBJECT-TYPE
    SYNTAX    OCTET STRING (SIZE(1..255))
    MAX-ACCESS read-only
    STATUS current
    DESCRIPTION
        "portchunkthreshold"
    ::= { affirmedAlarmObjects 104 }

portchunkutilization OBJECT-TYPE
    SYNTAX    OCTET STRING (SIZE(1..255))
    MAX-ACCESS read-only
    STATUS current
    DESCRIPTION
        "portchunkutilization"
    ::= { affirmedAlarmObjects 105 }

parent OBJECT-TYPE
    SYNTAX    OCTET STRING (SIZE(1..255))
    MAX-ACCESS read-only
    STATUS current
    DESCRIPTION
        "parent"
    ::= { affirmedAlarmObjects 106 }

destination OBJECT-TYPE
    SYNTAX    OCTET STRING (SIZE(1..255))
    MAX-ACCESS read-only
    STATUS current
    DESCRIPTION
        "destination"
    ::= { affirmedAlarmObjects 107 }

peeripaddress OBJECT-TYPE
    SYNTAX    OCTET STRING (SIZE(1..255))
    MAX-ACCESS read-only
    STATUS current
    DESCRIPTION
        "peeripaddress"
    ::= { affirmedAlarmObjects 108 }

gatewayname OBJECT-TYPE
    SYNTAX    OCTET STRING (SIZE(1..255))
    MAX-ACCESS read-only
    STATUS current
    DESCRIPTION
        "gatewayname"
    ::= { affirmedAlarmObjects 109 }

gatewayipaddress OBJECT-TYPE
    SYNTAX    OCTET STRING (SIZE(1..255))
    MAX-ACCESS read-only
    STATUS current
    DESCRIPTION
        "gatewayipaddress"
    ::= { affirmedAlarmObjects 110 }

bfdsessiondescription OBJECT-TYPE
    SYNTAX    OCTET STRING (SIZE(1..255))
    MAX-ACCESS read-only
    STATUS current
    DESCRIPTION
        "bfdsessiondescription"
    ::= { affirmedAlarmObjects 111 }

cafilename OBJECT-TYPE
    SYNTAX    OCTET STRING (SIZE(1..255))
    MAX-ACCESS read-only
    STATUS current
    DESCRIPTION
        "cafilename"
    ::= { affirmedAlarmObjects 112 }

expirydate OBJECT-TYPE
    SYNTAX    OCTET STRING (SIZE(1..255))
    MAX-ACCESS read-only
    STATUS current
    DESCRIPTION
        "expirydate"
    ::= { affirmedAlarmObjects 113 }

index OBJECT-TYPE
    SYNTAX    OCTET STRING (SIZE(1..255))
    MAX-ACCESS read-only
    STATUS current
    DESCRIPTION
        "index"
    ::= { affirmedAlarmObjects 114 }



END

AFFIRMED-ALARMS-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedAlarmsMIB MODULE-IDENTITY
    ORGANIZATION "Affirmed Networks, Inc."
    CONTACT-INFO "Affirmed Networks, Inc. 35 Nagog Park, Acton, MA, USA"
    DESCRIPTION ""
    ::= { 1 3 6 1 4 1 37963 10 2 }

String ::= TEXTUAL-CONVENTION
    DISPLAY-HINT "1t"
    STATUS      current
    DESCRIPTION "xs:string"
    SYNTAX      OCTET STRING

affirmedAlarms OBJECT IDENTIFIER ::= { affirmedAlarmsMIB 1 }

affirmedAlarmsActiveTable OBJECT-TYPE
    SYNTAX      SEQUENCE OF AffirmedAlarmsActiveEntry
    MAX-ACCESS  not-accessible
    STATUS      current
    DESCRIPTION ""
    ::= { affirmedAlarms 1 }

affirmedAlarmsActiveEntry OBJECT-TYPE
    SYNTAX      AffirmedAlarmsActiveEntry
    MAX-ACCESS  not-accessible
    STATUS      current
    DESCRIPTION ""
    INDEX { affirmedAlarmsActiveSeqId }
        ::= { affirmedAlarmsActiveTable 1 }

AffirmedAlarmsActiveEntry ::=
    SEQUENCE {
        affirmedAlarmsActiveSeqId Unsigned32,
        affirmedAlarmsActiveTrapName String,
        affirmedAlarmsActiveXpath String,
        affirmedAlarmsActiveSnmpsev INTEGER,
        affirmedAlarmsActiveDateTime String,
        affirmedAlarmsActiveDetails String
    }

affirmedAlarmsActiveSeqId OBJECT-TYPE
    SYNTAX      Unsigned32
    MAX-ACCESS  not-accessible
    STATUS      current
    DESCRIPTION ""
    ::= { affirmedAlarmsActiveEntry 1 }

affirmedAlarmsActiveTrapName OBJECT-TYPE
    SYNTAX      String
    MAX-ACCESS  read-only
    STATUS      current
    DESCRIPTION ""
    ::= { affirmedAlarmsActiveEntry 2 }

affirmedAlarmsActiveXpath OBJECT-TYPE
    SYNTAX      String
    MAX-ACCESS  read-only
    STATUS      current
    DESCRIPTION ""
    ::= { affirmedAlarmsActiveEntry 3 }

affirmedAlarmsActiveSnmpsev OBJECT-TYPE
    SYNTAX      INTEGER {cleared(1),indeterminate(2),critical(3),major(4),minor(5),warning(6),info(7)}
    MAX-ACCESS  read-only
    STATUS      current
    DESCRIPTION ""
    ::= { affirmedAlarmsActiveEntry 4 }

affirmedAlarmsActiveDateTime OBJECT-TYPE
    SYNTAX      String
    MAX-ACCESS  read-only
    STATUS      current
    DESCRIPTION ""
    ::= { affirmedAlarmsActiveEntry 5 }

affirmedAlarmsActiveDetails OBJECT-TYPE
    SYNTAX      String
    MAX-ACCESS  read-only
    STATUS      current
    DESCRIPTION ""
    ::= { affirmedAlarmsActiveEntry 6 }

affirmedAlarmsHistoryTable OBJECT-TYPE
    SYNTAX      SEQUENCE OF AffirmedAlarmsHistoryEntry
    MAX-ACCESS  not-accessible
    STATUS      current
    DESCRIPTION ""
    ::= { affirmedAlarms 2 }

affirmedAlarmsHistoryEntry OBJECT-TYPE
    SYNTAX      AffirmedAlarmsHistoryEntry
    MAX-ACCESS  not-accessible
    STATUS      current
    DESCRIPTION ""
    INDEX { affirmedAlarmsHistorySeqId }
        ::= { affirmedAlarmsHistoryTable 1 }

AffirmedAlarmsHistoryEntry ::=
    SEQUENCE {
        affirmedAlarmsHistorySeqId Unsigned32,
        affirmedAlarmsHistoryTrapName String,
        affirmedAlarmsHistoryXpath String,
        affirmedAlarmsHistorySnmpsev INTEGER,
        affirmedAlarmsHistoryDateTime String,
        affirmedAlarmsHistoryDetails String,
        affirmedAlarmsHistoryReasonForManualClear String
    }

affirmedAlarmsHistorySeqId OBJECT-TYPE
    SYNTAX      Unsigned32
    MAX-ACCESS  not-accessible
    STATUS      current
    DESCRIPTION ""
    ::= { affirmedAlarmsHistoryEntry 1 }

affirmedAlarmsHistoryTrapName OBJECT-TYPE
    SYNTAX      String
    MAX-ACCESS  read-only
    STATUS      current
    DESCRIPTION ""
    ::= { affirmedAlarmsHistoryEntry 2 }

affirmedAlarmsHistoryXpath OBJECT-TYPE
    SYNTAX      String
    MAX-ACCESS  read-only
    STATUS      current
    DESCRIPTION ""
    ::= { affirmedAlarmsHistoryEntry 3 }

affirmedAlarmsHistorySnmpsev OBJECT-TYPE
    SYNTAX      INTEGER {cleared(1),indeterminate(2),critical(3),major(4),minor(5),warning(6),info(7)}
    MAX-ACCESS  read-only
    STATUS      current
    DESCRIPTION ""
    ::= { affirmedAlarmsHistoryEntry 4 }

affirmedAlarmsHistoryDateTime OBJECT-TYPE
    SYNTAX      String
    MAX-ACCESS  read-only
    STATUS      current
    DESCRIPTION ""
    ::= { affirmedAlarmsHistoryEntry 5 }

affirmedAlarmsHistoryDetails OBJECT-TYPE
    SYNTAX      String
    MAX-ACCESS  read-only
    STATUS      current
    DESCRIPTION ""
    ::= { affirmedAlarmsHistoryEntry 6 }

affirmedAlarmsHistoryReasonForManualClear OBJECT-TYPE
    SYNTAX      String
    MAX-ACCESS  read-only
    STATUS      current
    DESCRIPTION ""
    ::= { affirmedAlarmsHistoryEntry 7 }

END

AFFIRMED-ARP-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedArpMIB MODULE-IDENTITY
    ORGANIZATION "Affirmed Networks, Inc."
    CONTACT-INFO "Affirmed Networks, Inc. 35 Nagog Park, Acton, MA, USA"
    DESCRIPTION ""
    ::= { 1 3 6 1 4 1 37963 10 13 }

String ::= TEXTUAL-CONVENTION
    DISPLAY-HINT "1t"
    STATUS      current
    DESCRIPTION "xs:string"
    SYNTAX      OCTET STRING

affirmedArpTable OBJECT-TYPE
    SYNTAX      SEQUENCE OF AffirmedArpEntry
    MAX-ACCESS  not-accessible
    STATUS      current
    DESCRIPTION ""
    ::= { affirmedArpMIB 1 }

affirmedArpEntry OBJECT-TYPE
    SYNTAX      AffirmedArpEntry
    MAX-ACCESS  not-accessible
    STATUS      current
    DESCRIPTION ""
    INDEX { affirmedArpSlotNumber, affirmedArpCpuNum, affirmedArpNetworkContext, affirmedArpIpAddress }
        ::= { affirmedArpTable 1 }

AffirmedArpEntry ::=
    SEQUENCE {
        affirmedArpSlotNumber Unsigned32,
        affirmedArpCpuNum Unsigned32,
        affirmedArpNetworkContext String,
        affirmedArpIpAddress String,
        affirmedArpMacAddress String,
        affirmedArpFlags String
    }

affirmedArpSlotNumber OBJECT-TYPE
    SYNTAX      Unsigned32
    MAX-ACCESS  not-accessible
    STATUS      current
    DESCRIPTION ""
    ::= { affirmedArpEntry 1 }

affirmedArpCpuNum OBJECT-TYPE
    SYNTAX      Unsigned32
    MAX-ACCESS  not-accessible
    STATUS      current
    DESCRIPTION ""
    ::= { affirmedArpEntry 2 }

affirmedArpNetworkContext OBJECT-TYPE
    SYNTAX      String
    MAX-ACCESS  not-accessible
    STATUS      current
    DESCRIPTION ""
    ::= { affirmedArpEntry 3 }

affirmedArpIpAddress OBJECT-TYPE
    SYNTAX      String
    MAX-ACCESS  not-accessible
    STATUS      current
    DESCRIPTION ""
    ::= { affirmedArpEntry 4 }

affirmedArpMacAddress OBJECT-TYPE
    SYNTAX      String
    MAX-ACCESS  read-only
    STATUS      current
    DESCRIPTION ""
    ::= { affirmedArpEntry 5 }

affirmedArpFlags OBJECT-TYPE
    SYNTAX      String
    MAX-ACCESS  read-only
    STATUS      current
    DESCRIPTION ""
    ::= { affirmedArpEntry 6 }

END

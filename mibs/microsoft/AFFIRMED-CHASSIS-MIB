AFFIRMED-CHASSIS-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedChassisMIB MODULE-IDENTITY
    ORGANIZATION "Affirmed Networks, Inc."
    CONTACT-INFO "Affirmed Networks, Inc. 35 Nagog Park, Acton, MA, USA"
    DESCRIPTION ""
    ::= { 1 3 6 1 4 1 37963 10 14 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedChassisTable OBJECT-TYPE
    SYNTAX      SEQUENCE OF AffirmedChassisEntry
    MAX-ACCESS  not-accessible
    STATUS      current
    DESCRIPTION ""
    ::= { affirmedChassisMIB 1 }

affirmedChassisEntry OBJECT-TYPE
    SYNTAX      AffirmedChassisEntry
    MAX-ACCESS  not-accessible
    STATUS      current
    DESCRIPTION ""
    INDEX { affirmedChassisId }
        ::= { affirmedChassisTable 1 }

AffirmedChassisEntry ::=
    SEQUENCE {
        affirmedChassisId Integer32,
        affirmedChassisRowstatus RowStatus
    }

affirmedChassisId OBJECT-TYPE
    SYNTAX      Integer32
    MAX-ACCESS  not-accessible
    STATUS      current
    DESCRIPTION ""
    ::= { affirmedChassisEntry 1 }

affirmedChassisRowstatus OBJECT-TYPE
    SYNTAX      RowStatus
    MAX-ACCESS  read-create
    STATUS      current
    DESCRIPTION ""
    ::= { affirmedChassisEntry 2 }

affirmedChassisAdapterTable OBJECT-TYPE
    SYNTAX      SEQUENCE OF AffirmedChassisAdapterEntry
    MAX-ACCESS  not-accessible
    STATUS      current
    DESCRIPTION ""
    ::= { affirmedChassisMIB 2 }

affirmedChassisAdapterEntry OBJECT-TYPE
    SYNTAX      AffirmedChassisAdapterEntry
    MAX-ACCESS  not-accessible
    STATUS      current
    DESCRIPTION ""
    INDEX { affirmedChassisId, affirmedChassisAdapterId }
        ::= { affirmedChassisAdapterTable 1 }

AffirmedChassisAdapterEntry ::=
    SEQUENCE {
        affirmedChassisAdapterId INTEGER,
        affirmedChassisAdapterRowstatus RowStatus
    }

affirmedChassisAdapterId OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION ""
    ::= { affirmedChassisAdapterEntry 1 }

affirmedChassisAdapterRowstatus OBJECT-TYPE
    SYNTAX      RowStatus
    MAX-ACCESS  read-create
    STATUS      current
    DESCRIPTION ""
    ::= { affirmedChassisAdapterEntry 2 }

affirmedChassisAdapterDiskStatusTable OBJECT-TYPE
    SYNTAX      SEQUENCE OF AffirmedChassisAdapterDiskStatusEntry
    MAX-ACCESS  not-accessible
    STATUS      current
    DESCRIPTION ""
    ::= { affirmedChassisMIB 3 }

affirmedChassisAdapterDiskStatusEntry OBJECT-TYPE
    SYNTAX      AffirmedChassisAdapterDiskStatusEntry
    MAX-ACCESS  not-accessible
    STATUS      current
    DESCRIPTION ""
    INDEX { affirmedChassisId, affirmedChassisAdapterId, affirmedChassisAdapterDiskStatusSlot, affirmedChassisAdapterDiskStatusDisk }
        ::= { affirmedChassisAdapterDiskStatusTable 1 }

AffirmedChassisAdapterDiskStatusEntry ::=
    SEQUENCE {
        affirmedChassisAdapterDiskStatusSlot String,
        affirmedChassisAdapterDiskStatusDisk String,
        affirmedChassisAdapterDiskStatusVendor String,
        affirmedChassisAdapterDiskStatusProduct String,
        affirmedChassisAdapterDiskStatusSerialnumber String,
        affirmedChassisAdapterDiskStatusLinkstatus String,
        affirmedChassisAdapterDiskStatusLinkerror String,
        affirmedChassisAdapterDiskStatusLifeexpectthresh String,
        affirmedChassisAdapterDiskStatusLifeexpect String
    }

affirmedChassisAdapterDiskStatusSlot OBJECT-TYPE
    SYNTAX      String
    MAX-ACCESS  not-accessible
    STATUS      current
    DESCRIPTION "Slot"
    ::= { affirmedChassisAdapterDiskStatusEntry 1 }

affirmedChassisAdapterDiskStatusDisk OBJECT-TYPE
    SYNTAX      String
    MAX-ACCESS  not-accessible
    STATUS      current
    DESCRIPTION "Disk"
    ::= { affirmedChassisAdapterDiskStatusEntry 2 }

affirmedChassisAdapterDiskStatusVendor OBJECT-TYPE
    SYNTAX      String
    MAX-ACCESS  read-only
    STATUS      current
    DESCRIPTION "Disk Vendor"
    ::= { affirmedChassisAdapterDiskStatusEntry 3 }

affirmedChassisAdapterDiskStatusProduct OBJECT-TYPE
    SYNTAX      String
    MAX-ACCESS  read-only
    STATUS      current
    DESCRIPTION "Disk Product Code"
    ::= { affirmedChassisAdapterDiskStatusEntry 4 }

affirmedChassisAdapterDiskStatusSerialnumber OBJECT-TYPE
    SYNTAX      String
    MAX-ACCESS  read-only
    STATUS      current
    DESCRIPTION "Disk SerialNumber"
    ::= { affirmedChassisAdapterDiskStatusEntry 5 }

affirmedChassisAdapterDiskStatusLinkstatus OBJECT-TYPE
    SYNTAX      String
    MAX-ACCESS  read-only
    STATUS      current
    DESCRIPTION "Disk Controller Status"
    ::= { affirmedChassisAdapterDiskStatusEntry 6 }

affirmedChassisAdapterDiskStatusLinkerror OBJECT-TYPE
    SYNTAX      String
    MAX-ACCESS  read-only
    STATUS      current
    DESCRIPTION "Disk Controller Error"
    ::= { affirmedChassisAdapterDiskStatusEntry 7 }

affirmedChassisAdapterDiskStatusLifeexpectthresh OBJECT-TYPE
    SYNTAX      String
    MAX-ACCESS  read-only
    STATUS      current
    DESCRIPTION "Disk Life Expectancy Threshold"
    ::= { affirmedChassisAdapterDiskStatusEntry 8 }

affirmedChassisAdapterDiskStatusLifeexpect OBJECT-TYPE
    SYNTAX      String
    MAX-ACCESS  read-only
    STATUS      current
    DESCRIPTION "Disk Life Expectancy"
    ::= { affirmedChassisAdapterDiskStatusEntry 9 }

affirmedChassisAdapterCacheStatusTable OBJECT-TYPE
    SYNTAX      SEQUENCE OF AffirmedChassisAdapterCacheStatusEntry
    MAX-ACCESS  not-accessible
    STATUS      current
    DESCRIPTION ""
    ::= { affirmedChassisMIB 4 }

affirmedChassisAdapterCacheStatusEntry OBJECT-TYPE
    SYNTAX      AffirmedChassisAdapterCacheStatusEntry
    MAX-ACCESS  not-accessible
    STATUS      current
    DESCRIPTION ""
    INDEX { affirmedChassisId, affirmedChassisAdapterId, affirmedChassisAdapterCacheStatusSlot }
        ::= { affirmedChassisAdapterCacheStatusTable 1 }

AffirmedChassisAdapterCacheStatusEntry ::=
    SEQUENCE {
        affirmedChassisAdapterCacheStatusSlot String,
        affirmedChassisAdapterCacheStatusAdminstatus String,
        affirmedChassisAdapterCacheStatusOperstatus String,
        affirmedChassisAdapterCacheStatusSize String,
        affirmedChassisAdapterCacheStatusDisksexpected String,
        affirmedChassisAdapterCacheStatusDiskspresent String,
        affirmedChassisAdapterCacheStatusDisksincache String
    }

affirmedChassisAdapterCacheStatusSlot OBJECT-TYPE
    SYNTAX      String
    MAX-ACCESS  not-accessible
    STATUS      current
    DESCRIPTION "Cache Slot"
    ::= { affirmedChassisAdapterCacheStatusEntry 1 }

affirmedChassisAdapterCacheStatusAdminstatus OBJECT-TYPE
    SYNTAX      String
    MAX-ACCESS  read-only
    STATUS      current
    DESCRIPTION "Cache Admin Status"
    ::= { affirmedChassisAdapterCacheStatusEntry 2 }

affirmedChassisAdapterCacheStatusOperstatus OBJECT-TYPE
    SYNTAX      String
    MAX-ACCESS  read-only
    STATUS      current
    DESCRIPTION "Cache Operational Status"
    ::= { affirmedChassisAdapterCacheStatusEntry 3 }

affirmedChassisAdapterCacheStatusSize OBJECT-TYPE
    SYNTAX      String
    MAX-ACCESS  read-only
    STATUS      current
    DESCRIPTION "Cache Size"
    ::= { affirmedChassisAdapterCacheStatusEntry 4 }

affirmedChassisAdapterCacheStatusDisksexpected OBJECT-TYPE
    SYNTAX      String
    MAX-ACCESS  read-only
    STATUS      current
    DESCRIPTION "Expected number of disks composing the cache"
    ::= { affirmedChassisAdapterCacheStatusEntry 5 }

affirmedChassisAdapterCacheStatusDiskspresent OBJECT-TYPE
    SYNTAX      String
    MAX-ACCESS  read-only
    STATUS      current
    DESCRIPTION "Current number of disks present for this slot"
    ::= { affirmedChassisAdapterCacheStatusEntry 6 }

affirmedChassisAdapterCacheStatusDisksincache OBJECT-TYPE
    SYNTAX      String
    MAX-ACCESS  read-only
    STATUS      current
    DESCRIPTION "Current number of disks composing the cache"
    ::= { affirmedChassisAdapterCacheStatusEntry 7 }

affirmedChassisAdapterPortStatusTable OBJECT-TYPE
    SYNTAX      SEQUENCE OF AffirmedChassisAdapterPortStatusEntry
    MAX-ACCESS  not-accessible
    STATUS      current
    DESCRIPTION ""
    ::= { affirmedChassisMIB 5 }

affirmedChassisAdapterPortStatusEntry OBJECT-TYPE
    SYNTAX      AffirmedChassisAdapterPortStatusEntry
    MAX-ACCESS  not-accessible
    STATUS      current
    DESCRIPTION ""
    INDEX { affirmedChassisId, affirmedChassisAdapterId, affirmedChassisAdapterPortStatusPortName }
        ::= { affirmedChassisAdapterPortStatusTable 1 }

AffirmedChassisAdapterPortStatusEntry ::=
    SEQUENCE {
        affirmedChassisAdapterPortStatusPortName Integer32,
        affirmedChassisAdapterPortStatusAdminState String,
        affirmedChassisAdapterPortStatusOperState String,
        affirmedChassisAdapterPortStatusAdminSpeed String,
        affirmedChassisAdapterPortStatusOperSpeed String,
        affirmedChassisAdapterPortStatusAutoNeg String,
        affirmedChassisAdapterPortStatusDuplex String,
        affirmedChassisAdapterPortStatusStpstate String
    }

affirmedChassisAdapterPortStatusPortName OBJECT-TYPE
    SYNTAX      Integer32
    MAX-ACCESS  not-accessible
    STATUS      current
    DESCRIPTION ""
    ::= { affirmedChassisAdapterPortStatusEntry 1 }

affirmedChassisAdapterPortStatusAdminState OBJECT-TYPE
    SYNTAX      String
    MAX-ACCESS  read-only
    STATUS      current
    DESCRIPTION ""
    ::= { affirmedChassisAdapterPortStatusEntry 2 }

affirmedChassisAdapterPortStatusOperState OBJECT-TYPE
    SYNTAX      String
    MAX-ACCESS  read-only
    STATUS      current
    DESCRIPTION ""
    ::= { affirmedChassisAdapterPortStatusEntry 3 }

affirmedChassisAdapterPortStatusAdminSpeed OBJECT-TYPE
    SYNTAX      String
    MAX-ACCESS  read-only
    STATUS      deprecated
    DESCRIPTION ""
    ::= { affirmedChassisAdapterPortStatusEntry 4 }

affirmedChassisAdapterPortStatusOperSpeed OBJECT-TYPE
    SYNTAX      String
    MAX-ACCESS  read-only
    STATUS      current
    DESCRIPTION ""
    ::= { affirmedChassisAdapterPortStatusEntry 5 }

affirmedChassisAdapterPortStatusAutoNeg OBJECT-TYPE
    SYNTAX      String
    MAX-ACCESS  read-only
    STATUS      current
    DESCRIPTION ""
    ::= { affirmedChassisAdapterPortStatusEntry 6 }

affirmedChassisAdapterPortStatusDuplex OBJECT-TYPE
    SYNTAX      String
    MAX-ACCESS  read-only
    STATUS      current
    DESCRIPTION ""
    ::= { affirmedChassisAdapterPortStatusEntry 7 }

affirmedChassisAdapterPortStatusStpstate OBJECT-TYPE
    SYNTAX      String
    MAX-ACCESS  read-only
    STATUS      current
    DESCRIPTION ""
    ::= { affirmedChassisAdapterPortStatusEntry 8 }

affirmedChassisAdapterPortStatisticsTable OBJECT-TYPE
    SYNTAX      SEQUENCE OF AffirmedChassisAdapterPortStatisticsEntry
    MAX-ACCESS  not-accessible
    STATUS      current
    DESCRIPTION ""
    ::= { affirmedChassisMIB 6 }

affirmedChassisAdapterPortStatisticsEntry OBJECT-TYPE
    SYNTAX      AffirmedChassisAdapterPortStatisticsEntry
    MAX-ACCESS  not-accessible
    STATUS      current
    DESCRIPTION ""
    INDEX { affirmedChassisId, affirmedChassisAdapterId, affirmedChassisAdapterPortStatisticsPortName }
        ::= { affirmedChassisAdapterPortStatisticsTable 1 }

AffirmedChassisAdapterPortStatisticsEntry ::=
    SEQUENCE {
        affirmedChassisAdapterPortStatisticsPortName Integer32,
        affirmedChassisAdapterPortStatisticsUnicastInBound String,
        affirmedChassisAdapterPortStatisticsUnicastOutBound String,
        affirmedChassisAdapterPortStatisticsMulticastInBound String,
        affirmedChassisAdapterPortStatisticsMulticastOutBound String,
        affirmedChassisAdapterPortStatisticsBroadcastInBound String,
        affirmedChassisAdapterPortStatisticsBroadcastOutBound String
    }

affirmedChassisAdapterPortStatisticsPortName OBJECT-TYPE
    SYNTAX      Integer32
    MAX-ACCESS  not-accessible
    STATUS      current
    DESCRIPTION ""
    ::= { affirmedChassisAdapterPortStatisticsEntry 1 }

affirmedChassisAdapterPortStatisticsUnicastInBound OBJECT-TYPE
    SYNTAX      String
    MAX-ACCESS  read-only
    STATUS      current
    DESCRIPTION ""
    ::= { affirmedChassisAdapterPortStatisticsEntry 2 }

affirmedChassisAdapterPortStatisticsUnicastOutBound OBJECT-TYPE
    SYNTAX      String
    MAX-ACCESS  read-only
    STATUS      current
    DESCRIPTION ""
    ::= { affirmedChassisAdapterPortStatisticsEntry 3 }

affirmedChassisAdapterPortStatisticsMulticastInBound OBJECT-TYPE
    SYNTAX      String
    MAX-ACCESS  read-only
    STATUS      current
    DESCRIPTION ""
    ::= { affirmedChassisAdapterPortStatisticsEntry 4 }

affirmedChassisAdapterPortStatisticsMulticastOutBound OBJECT-TYPE
    SYNTAX      String
    MAX-ACCESS  read-only
    STATUS      current
    DESCRIPTION ""
    ::= { affirmedChassisAdapterPortStatisticsEntry 5 }

affirmedChassisAdapterPortStatisticsBroadcastInBound OBJECT-TYPE
    SYNTAX      String
    MAX-ACCESS  read-only
    STATUS      current
    DESCRIPTION ""
    ::= { affirmedChassisAdapterPortStatisticsEntry 6 }

affirmedChassisAdapterPortStatisticsBroadcastOutBound OBJECT-TYPE
    SYNTAX      String
    MAX-ACCESS  read-only
    STATUS      current
    DESCRIPTION ""
    ::= { affirmedChassisAdapterPortStatisticsEntry 7 }

affirmedChassisAdapterPortErrorsTable OBJECT-TYPE
    SYNTAX      SEQUENCE OF AffirmedChassisAdapterPortErrorsEntry
    MAX-ACCESS  not-accessible
    STATUS      current
    DESCRIPTION ""
    ::= { affirmedChassisMIB 7 }

affirmedChassisAdapterPortErrorsEntry OBJECT-TYPE
    SYNTAX      AffirmedChassisAdapterPortErrorsEntry
    MAX-ACCESS  not-accessible
    STATUS      current
    DESCRIPTION ""
    INDEX { affirmedChassisId, affirmedChassisAdapterId, affirmedChassisAdapterPortErrorsPortName }
        ::= { affirmedChassisAdapterPortErrorsTable 1 }

AffirmedChassisAdapterPortErrorsEntry ::=
    SEQUENCE {
        affirmedChassisAdapterPortErrorsPortName Integer32,
        affirmedChassisAdapterPortErrorsReceiveRunt String,
        affirmedChassisAdapterPortErrorsReceiveCarrier String,
        affirmedChassisAdapterPortErrorsReceiveOversize String,
        affirmedChassisAdapterPortErrorsReceiveWsa String,
        affirmedChassisAdapterPortErrorsReceiveJabbar String,
        affirmedChassisAdapterPortErrorsReceiveflr String,
        affirmedChassisAdapterPortErrorsReceiveRer String,
        affirmedChassisAdapterPortErrorsReceiveFcs String,
        affirmedChassisAdapterPortErrorsTransmiterr String,
        affirmedChassisAdapterPortErrorsTransmitTpce String,
        affirmedChassisAdapterPortErrorsTransmitTufl String
    }

affirmedChassisAdapterPortErrorsPortName OBJECT-TYPE
    SYNTAX      Integer32
    MAX-ACCESS  not-accessible
    STATUS      current
    DESCRIPTION ""
    ::= { affirmedChassisAdapterPortErrorsEntry 1 }

affirmedChassisAdapterPortErrorsReceiveRunt OBJECT-TYPE
    SYNTAX      String
    MAX-ACCESS  read-only
    STATUS      current
    DESCRIPTION ""
    ::= { affirmedChassisAdapterPortErrorsEntry 2 }

affirmedChassisAdapterPortErrorsReceiveCarrier OBJECT-TYPE
    SYNTAX      String
    MAX-ACCESS  read-only
    STATUS      current
    DESCRIPTION ""
    ::= { affirmedChassisAdapterPortErrorsEntry 3 }

affirmedChassisAdapterPortErrorsReceiveOversize OBJECT-TYPE
    SYNTAX      String
    MAX-ACCESS  read-only
    STATUS      current
    DESCRIPTION ""
    ::= { affirmedChassisAdapterPortErrorsEntry 4 }

affirmedChassisAdapterPortErrorsReceiveWsa OBJECT-TYPE
    SYNTAX      String
    MAX-ACCESS  read-only
    STATUS      current
    DESCRIPTION ""
    ::= { affirmedChassisAdapterPortErrorsEntry 5 }

affirmedChassisAdapterPortErrorsReceiveJabbar OBJECT-TYPE
    SYNTAX      String
    MAX-ACCESS  read-only
    STATUS      current
    DESCRIPTION ""
    ::= { affirmedChassisAdapterPortErrorsEntry 6 }

affirmedChassisAdapterPortErrorsReceiveflr OBJECT-TYPE
    SYNTAX      String
    MAX-ACCESS  read-only
    STATUS      current
    DESCRIPTION ""
    ::= { affirmedChassisAdapterPortErrorsEntry 7 }

affirmedChassisAdapterPortErrorsReceiveRer OBJECT-TYPE
    SYNTAX      String
    MAX-ACCESS  read-only
    STATUS      current
    DESCRIPTION ""
    ::= { affirmedChassisAdapterPortErrorsEntry 8 }

affirmedChassisAdapterPortErrorsReceiveFcs OBJECT-TYPE
    SYNTAX      String
    MAX-ACCESS  read-only
    STATUS      current
    DESCRIPTION ""
    ::= { affirmedChassisAdapterPortErrorsEntry 9 }

affirmedChassisAdapterPortErrorsTransmiterr OBJECT-TYPE
    SYNTAX      String
    MAX-ACCESS  read-only
    STATUS      current
    DESCRIPTION ""
    ::= { affirmedChassisAdapterPortErrorsEntry 10 }

affirmedChassisAdapterPortErrorsTransmitTpce OBJECT-TYPE
    SYNTAX      String
    MAX-ACCESS  read-only
    STATUS      current
    DESCRIPTION ""
    ::= { affirmedChassisAdapterPortErrorsEntry 11 }

affirmedChassisAdapterPortErrorsTransmitTufl OBJECT-TYPE
    SYNTAX      String
    MAX-ACCESS  read-only
    STATUS      current
    DESCRIPTION ""
    ::= { affirmedChassisAdapterPortErrorsEntry 12 }

affirmedChassisLedstatusTable OBJECT-TYPE
    SYNTAX      SEQUENCE OF AffirmedChassisLedstatusEntry
    MAX-ACCESS  not-accessible
    STATUS      current
    DESCRIPTION ""
    ::= { affirmedChassisMIB 8 }

affirmedChassisLedstatusEntry OBJECT-TYPE
    SYNTAX      AffirmedChassisLedstatusEntry
    MAX-ACCESS  not-accessible
    STATUS      current
    DESCRIPTION ""
    INDEX { affirmedChassisId, affirmedChassisLedstatusResource, affirmedChassisLedstatusLedname }
        ::= { affirmedChassisLedstatusTable 1 }

AffirmedChassisLedstatusEntry ::=
    SEQUENCE {
        affirmedChassisLedstatusResource Unsigned32,
        affirmedChassisLedstatusLedname String,
        affirmedChassisLedstatusSlot String,
        affirmedChassisLedstatusModuletype String,
        affirmedChassisLedstatusModulefunction String,
        affirmedChassisLedstatusLedcolor String
    }

affirmedChassisLedstatusResource OBJECT-TYPE
    SYNTAX      Unsigned32
    MAX-ACCESS  not-accessible
    STATUS      current
    DESCRIPTION ""
    ::= { affirmedChassisLedstatusEntry 1 }

affirmedChassisLedstatusLedname OBJECT-TYPE
    SYNTAX      String
    MAX-ACCESS  not-accessible
    STATUS      current
    DESCRIPTION ""
    ::= { affirmedChassisLedstatusEntry 2 }

affirmedChassisLedstatusSlot OBJECT-TYPE
    SYNTAX      String
    MAX-ACCESS  read-only
    STATUS      current
    DESCRIPTION ""
    ::= { affirmedChassisLedstatusEntry 3 }

affirmedChassisLedstatusModuletype OBJECT-TYPE
    SYNTAX      String
    MAX-ACCESS  read-only
    STATUS      current
    DESCRIPTION ""
    ::= { affirmedChassisLedstatusEntry 4 }

affirmedChassisLedstatusModulefunction OBJECT-TYPE
    SYNTAX      String
    MAX-ACCESS  read-only
    STATUS      current
    DESCRIPTION ""
    ::= { affirmedChassisLedstatusEntry 5 }

affirmedChassisLedstatusLedcolor OBJECT-TYPE
    SYNTAX      String
    MAX-ACCESS  read-only
    STATUS      current
    DESCRIPTION ""
    ::= { affirmedChassisLedstatusEntry 6 }

affirmedChassisCardTable OBJECT-TYPE
    SYNTAX      SEQUENCE OF AffirmedChassisCardEntry
    MAX-ACCESS  not-accessible
    STATUS      current
    DESCRIPTION ""
    ::= { affirmedChassisMIB 9 }

affirmedChassisCardEntry OBJECT-TYPE
    SYNTAX      AffirmedChassisCardEntry
    MAX-ACCESS  not-accessible
    STATUS      current
    DESCRIPTION ""
    INDEX { affirmedChassisId, affirmedChassisCardId }
        ::= { affirmedChassisCardTable 1 }

AffirmedChassisCardEntry ::=
    SEQUENCE {
        affirmedChassisCardId INTEGER,
        affirmedChassisCardRowstatus RowStatus
    }

affirmedChassisCardId OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION ""
    ::= { affirmedChassisCardEntry 1 }

affirmedChassisCardRowstatus OBJECT-TYPE
    SYNTAX      RowStatus
    MAX-ACCESS  read-create
    STATUS      current
    DESCRIPTION ""
    ::= { affirmedChassisCardEntry 2 }

affirmedChassisCardTaskDryupTable OBJECT-TYPE
    SYNTAX      SEQUENCE OF AffirmedChassisCardTaskDryupEntry
    MAX-ACCESS  not-accessible
    STATUS      current
    DESCRIPTION ""
    ::= { affirmedChassisMIB 20 }

affirmedChassisCardTaskDryupEntry OBJECT-TYPE
    SYNTAX      AffirmedChassisCardTaskDryupEntry
    MAX-ACCESS  not-accessible
    STATUS      current
    DESCRIPTION ""
    INDEX { affirmedChassisId, affirmedChassisCardId, affirmedChassisCardTaskDryupCpuNumber, affirmedChassisCardTaskDryupTaskname }
        ::= { affirmedChassisCardTaskDryupTable 1 }

AffirmedChassisCardTaskDryupEntry ::=
    SEQUENCE {
        affirmedChassisCardTaskDryupCpuNumber INTEGER,
        affirmedChassisCardTaskDryupTaskname String,
        affirmedChassisCardTaskDryupSvcname String,
        affirmedChassisCardTaskDryupHastate INTEGER,
        affirmedChassisCardTaskDryupOperstate INTEGER,
        affirmedChassisCardTaskDryupDryupstatus String,
        affirmedChassisCardTaskDryupDryupload Unsigned32
    }

affirmedChassisCardTaskDryupCpuNumber OBJECT-TYPE
    SYNTAX      INTEGER {cpu1(1),cpu2(2),cpu3(3),cpu4(4),cpu5(5),cpu6(6),cpu7(7),cpu8(8)}
    MAX-ACCESS  not-accessible
    STATUS      current
    DESCRIPTION ""
    ::= { affirmedChassisCardTaskDryupEntry 1 }

affirmedChassisCardTaskDryupTaskname OBJECT-TYPE
    SYNTAX      String
    MAX-ACCESS  not-accessible
    STATUS      current
    DESCRIPTION ""
    ::= { affirmedChassisCardTaskDryupEntry 2 }

affirmedChassisCardTaskDryupSvcname OBJECT-TYPE
    SYNTAX      String
    MAX-ACCESS  read-only
    STATUS      current
    DESCRIPTION ""
    ::= { affirmedChassisCardTaskDryupEntry 3 }

affirmedChassisCardTaskDryupHastate OBJECT-TYPE
    SYNTAX      INTEGER {active(1),standby(2),quiesced(3),quiescing(4),none(5),master(6),slave(7),primary(8),secondary(9)}
    MAX-ACCESS  read-only
    STATUS      current
    DESCRIPTION ""
    ::= { affirmedChassisCardTaskDryupEntry 4 }

affirmedChassisCardTaskDryupOperstate OBJECT-TYPE
    SYNTAX      INTEGER {up(101),down(102),partially-up(103),maint(104),dryup(105),congested(106),unknown(107)}
    MAX-ACCESS  read-only
    STATUS      current
    DESCRIPTION ""
    ::= { affirmedChassisCardTaskDryupEntry 5 }

affirmedChassisCardTaskDryupDryupstatus OBJECT-TYPE
    SYNTAX      String
    MAX-ACCESS  read-only
    STATUS      current
    DESCRIPTION ""
    ::= { affirmedChassisCardTaskDryupEntry 6 }

affirmedChassisCardTaskDryupDryupload OBJECT-TYPE
    SYNTAX      Unsigned32
    MAX-ACCESS  read-only
    STATUS      current
    DESCRIPTION ""
    ::= { affirmedChassisCardTaskDryupEntry 7 }

affirmedChassisCardTaskOperation-detailTable OBJECT-TYPE
    SYNTAX      SEQUENCE OF AffirmedChassisCardTaskOperation-detailEntry
    MAX-ACCESS  not-accessible
    STATUS      current
    DESCRIPTION ""
    ::= { affirmedChassisMIB 21 }

affirmedChassisCardTaskOperation-detailEntry OBJECT-TYPE
    SYNTAX      AffirmedChassisCardTaskOperation-detailEntry
    MAX-ACCESS  not-accessible
    STATUS      current
    DESCRIPTION ""
    INDEX { affirmedChassisId, affirmedChassisCardId, affirmedChassisCardTaskOperation-detailCpuNumber, affirmedChassisCardTaskOperation-detailTaskname }
        ::= { affirmedChassisCardTaskOperation-detailTable 1 }

AffirmedChassisCardTaskOperation-detailEntry ::=
    SEQUENCE {
        affirmedChassisCardTaskOperation-detailCpuNumber INTEGER,
        affirmedChassisCardTaskOperation-detailTaskname String,
        affirmedChassisCardTaskOperation-detailSvcname String,
        affirmedChassisCardTaskOperation-detailHastate INTEGER,
        affirmedChassisCardTaskOperation-detailOperstate INTEGER,
        affirmedChassisCardTaskOperation-detailOperstatereason String
    }

affirmedChassisCardTaskOperation-detailCpuNumber OBJECT-TYPE
    SYNTAX      INTEGER {cpu1(1),cpu2(2),cpu3(3),cpu4(4),cpu5(5),cpu6(6),cpu7(7),cpu8(8)}
    MAX-ACCESS  not-accessible
    STATUS      current
    DESCRIPTION ""
    ::= { affirmedChassisCardTaskOperation-detailEntry 1 }

affirmedChassisCardTaskOperation-detailTaskname OBJECT-TYPE
    SYNTAX      String
    MAX-ACCESS  not-accessible
    STATUS      current
    DESCRIPTION ""
    ::= { affirmedChassisCardTaskOperation-detailEntry 2 }

affirmedChassisCardTaskOperation-detailSvcname OBJECT-TYPE
    SYNTAX      String
    MAX-ACCESS  read-only
    STATUS      current
    DESCRIPTION ""
    ::= { affirmedChassisCardTaskOperation-detailEntry 3 }

affirmedChassisCardTaskOperation-detailHastate OBJECT-TYPE
    SYNTAX      INTEGER {active(1),standby(2),quiesced(3),quiescing(4),none(5),master(6),slave(7),primary(8),secondary(9)}
    MAX-ACCESS  read-only
    STATUS      current
    DESCRIPTION ""
    ::= { affirmedChassisCardTaskOperation-detailEntry 4 }

affirmedChassisCardTaskOperation-detailOperstate OBJECT-TYPE
    SYNTAX      INTEGER {up(101),down(102),partially-up(103),maint(104),dryup(105),congested(106),unknown(107)}
    MAX-ACCESS  read-only
    STATUS      current
    DESCRIPTION ""
    ::= { affirmedChassisCardTaskOperation-detailEntry 5 }

affirmedChassisCardTaskOperation-detailOperstatereason OBJECT-TYPE
    SYNTAX      String
    MAX-ACCESS  read-only
    STATUS      current
    DESCRIPTION ""
    ::= { affirmedChassisCardTaskOperation-detailEntry 6 }

affirmedChassisCardTaskRequested-restartsTable OBJECT-TYPE
    SYNTAX      SEQUENCE OF AffirmedChassisCardTaskRequested-restartsEntry
    MAX-ACCESS  not-accessible
    STATUS      current
    DESCRIPTION ""
    ::= { affirmedChassisMIB 35 }

affirmedChassisCardTaskRequested-restartsEntry OBJECT-TYPE
    SYNTAX      AffirmedChassisCardTaskRequested-restartsEntry
    MAX-ACCESS  not-accessible
    STATUS      current
    DESCRIPTION ""
    INDEX { affirmedChassisId, affirmedChassisCardId, affirmedChassisCardTaskRequested-restartsRestartreason, affirmedChassisCardTaskRequested-restartsTaskname }
        ::= { affirmedChassisCardTaskRequested-restartsTable 1 }

AffirmedChassisCardTaskRequested-restartsEntry ::=
    SEQUENCE {
        affirmedChassisCardTaskRequested-restartsRestartreason INTEGER,
        affirmedChassisCardTaskRequested-restartsTaskname String,
        affirmedChassisCardTaskRequested-restartsRestarttype INTEGER
    }

affirmedChassisCardTaskRequested-restartsRestartreason OBJECT-TYPE
    SYNTAX      INTEGER {kni-config-mismatch(0),isol-cpus-mismatch(1),any(2),release-mismatch(4)}
    MAX-ACCESS  not-accessible
    STATUS      current
    DESCRIPTION ""
    ::= { affirmedChassisCardTaskRequested-restartsEntry 1 }

affirmedChassisCardTaskRequested-restartsTaskname OBJECT-TYPE
    SYNTAX      String
    MAX-ACCESS  not-accessible
    STATUS      current
    DESCRIPTION ""
    ::= { affirmedChassisCardTaskRequested-restartsEntry 2 }

affirmedChassisCardTaskRequested-restartsRestarttype OBJECT-TYPE
    SYNTAX      INTEGER {task-restart(0),node-restart(1)}
    MAX-ACCESS  read-only
    STATUS      current
    DESCRIPTION ""
    ::= { affirmedChassisCardTaskRequested-restartsEntry 3 }

affirmedChassisCardTaskStatisticsTable OBJECT-TYPE
    SYNTAX      SEQUENCE OF AffirmedChassisCardTaskStatisticsEntry
    MAX-ACCESS  not-accessible
    STATUS      current
    DESCRIPTION ""
    ::= { affirmedChassisMIB 22 }

affirmedChassisCardTaskStatisticsEntry OBJECT-TYPE
    SYNTAX      AffirmedChassisCardTaskStatisticsEntry
    MAX-ACCESS  not-accessible
    STATUS      current
    DESCRIPTION ""
    INDEX { affirmedChassisId, affirmedChassisCardId, affirmedChassisCardTaskStatisticsCpuNumber, affirmedChassisCardTaskStatisticsTaskname }
        ::= { affirmedChassisCardTaskStatisticsTable 1 }

AffirmedChassisCardTaskStatisticsEntry ::=
    SEQUENCE {
        affirmedChassisCardTaskStatisticsCpuNumber INTEGER,
        affirmedChassisCardTaskStatisticsTaskname String,
        affirmedChassisCardTaskStatisticsCpuutil String,
        affirmedChassisCardTaskStatisticsMemutil String,
        affirmedChassisCardTaskStatisticsTaskutil String
    }

affirmedChassisCardTaskStatisticsCpuNumber OBJECT-TYPE
    SYNTAX      INTEGER {cpu1(1),cpu2(2),cpu3(3),cpu4(4),cpu5(5),cpu6(6),cpu7(7),cpu8(8)}
    MAX-ACCESS  not-accessible
    STATUS      current
    DESCRIPTION ""
    ::= { affirmedChassisCardTaskStatisticsEntry 1 }

affirmedChassisCardTaskStatisticsTaskname OBJECT-TYPE
    SYNTAX      String
    MAX-ACCESS  not-accessible
    STATUS      current
    DESCRIPTION ""
    ::= { affirmedChassisCardTaskStatisticsEntry 2 }

affirmedChassisCardTaskStatisticsCpuutil OBJECT-TYPE
    SYNTAX      String
    MAX-ACCESS  read-only
    STATUS      current
    DESCRIPTION ""
    ::= { affirmedChassisCardTaskStatisticsEntry 3 }

affirmedChassisCardTaskStatisticsMemutil OBJECT-TYPE
    SYNTAX      String
    MAX-ACCESS  read-only
    STATUS      current
    DESCRIPTION ""
    ::= { affirmedChassisCardTaskStatisticsEntry 4 }

affirmedChassisCardTaskStatisticsTaskutil OBJECT-TYPE
    SYNTAX      String
    MAX-ACCESS  read-only
    STATUS      current
    DESCRIPTION ""
    ::= { affirmedChassisCardTaskStatisticsEntry 5 }

affirmedChassisCardDiskSimStatusTable OBJECT-TYPE
    SYNTAX      SEQUENCE OF AffirmedChassisCardDiskSimStatusEntry
    MAX-ACCESS  not-accessible
    STATUS      current
    DESCRIPTION ""
    ::= { affirmedChassisMIB 10 }

affirmedChassisCardDiskSimStatusEntry OBJECT-TYPE
    SYNTAX      AffirmedChassisCardDiskSimStatusEntry
    MAX-ACCESS  not-accessible
    STATUS      current
    DESCRIPTION ""
    INDEX { affirmedChassisId, affirmedChassisCardId, affirmedChassisCardDiskSimStatusDiskid }
        ::= { affirmedChassisCardDiskSimStatusTable 1 }

AffirmedChassisCardDiskSimStatusEntry ::=
    SEQUENCE {
        affirmedChassisCardDiskSimStatusDiskid Unsigned32,
        affirmedChassisCardDiskSimStatusAdminstate String,
        affirmedChassisCardDiskSimStatusOperstatus String,
        affirmedChassisCardDiskSimStatusDisksize String,
        affirmedChassisCardDiskSimStatusDiskusage String,
        affirmedChassisCardDiskSimStatusDiskerror String,
        affirmedChassisCardDiskSimStatusDiskname String,
        affirmedChassisCardDiskSimStatusUsepercent String
    }

affirmedChassisCardDiskSimStatusDiskid OBJECT-TYPE
    SYNTAX      Unsigned32
    MAX-ACCESS  not-accessible
    STATUS      current
    DESCRIPTION ""
    ::= { affirmedChassisCardDiskSimStatusEntry 1 }

affirmedChassisCardDiskSimStatusAdminstate OBJECT-TYPE
    SYNTAX      String
    MAX-ACCESS  read-only
    STATUS      current
    DESCRIPTION "Admin State "
    ::= { affirmedChassisCardDiskSimStatusEntry 2 }

affirmedChassisCardDiskSimStatusOperstatus OBJECT-TYPE
    SYNTAX      String
    MAX-ACCESS  read-only
    STATUS      current
    DESCRIPTION "Operational Status "
    ::= { affirmedChassisCardDiskSimStatusEntry 3 }

affirmedChassisCardDiskSimStatusDisksize OBJECT-TYPE
    SYNTAX      String
    MAX-ACCESS  read-only
    STATUS      current
    DESCRIPTION "Disk size "
    ::= { affirmedChassisCardDiskSimStatusEntry 4 }

affirmedChassisCardDiskSimStatusDiskusage OBJECT-TYPE
    SYNTAX      String
    MAX-ACCESS  read-only
    STATUS      current
    DESCRIPTION "Disk Usage "
    ::= { affirmedChassisCardDiskSimStatusEntry 5 }

affirmedChassisCardDiskSimStatusDiskerror OBJECT-TYPE
    SYNTAX      String
    MAX-ACCESS  read-only
    STATUS      current
    DESCRIPTION "Disk Error "
    ::= { affirmedChassisCardDiskSimStatusEntry 6 }

affirmedChassisCardDiskSimStatusDiskname OBJECT-TYPE
    SYNTAX      String
    MAX-ACCESS  read-only
    STATUS      current
    DESCRIPTION "Disk Name"
    ::= { affirmedChassisCardDiskSimStatusEntry 7 }

affirmedChassisCardDiskSimStatusUsepercent OBJECT-TYPE
    SYNTAX      String
    MAX-ACCESS  read-only
    STATUS      current
    DESCRIPTION "percentage of disk space in use"
    ::= { affirmedChassisCardDiskSimStatusEntry 8 }

affirmedChassisCardServiceTable OBJECT-TYPE
    SYNTAX      SEQUENCE OF AffirmedChassisCardServiceEntry
    MAX-ACCESS  not-accessible
    STATUS      current
    DESCRIPTION ""
    ::= { affirmedChassisMIB 11 }

affirmedChassisCardServiceEntry OBJECT-TYPE
    SYNTAX      AffirmedChassisCardServiceEntry
    MAX-ACCESS  not-accessible
    STATUS      current
    DESCRIPTION ""
    INDEX { affirmedChassisId, affirmedChassisCardId, affirmedChassisCardServiceServicename }
        ::= { affirmedChassisCardServiceTable 1 }

AffirmedChassisCardServiceEntry ::=
    SEQUENCE {
        affirmedChassisCardServiceServicename String,
        affirmedChassisCardServiceOperstate String,
        affirmedChassisCardServiceTotaltask Unsigned32,
        affirmedChassisCardServiceActivetask Unsigned32,
        affirmedChassisCardServiceStandbytask Unsigned32
    }

affirmedChassisCardServiceServicename OBJECT-TYPE
    SYNTAX      String
    MAX-ACCESS  not-accessible
    STATUS      current
    DESCRIPTION ""
    ::= { affirmedChassisCardServiceEntry 1 }

affirmedChassisCardServiceOperstate OBJECT-TYPE
    SYNTAX      String
    MAX-ACCESS  read-only
    STATUS      current
    DESCRIPTION "Operational State "
    ::= { affirmedChassisCardServiceEntry 2 }

affirmedChassisCardServiceTotaltask OBJECT-TYPE
    SYNTAX      Unsigned32
    MAX-ACCESS  read-only
    STATUS      current
    DESCRIPTION ""
    ::= { affirmedChassisCardServiceEntry 3 }

affirmedChassisCardServiceActivetask OBJECT-TYPE
    SYNTAX      Unsigned32
    MAX-ACCESS  read-only
    STATUS      current
    DESCRIPTION ""
    ::= { affirmedChassisCardServiceEntry 4 }

affirmedChassisCardServiceStandbytask OBJECT-TYPE
    SYNTAX      Unsigned32
    MAX-ACCESS  read-only
    STATUS      current
    DESCRIPTION ""
    ::= { affirmedChassisCardServiceEntry 5 }

affirmedChassisCardProcessesTable OBJECT-TYPE
    SYNTAX      SEQUENCE OF AffirmedChassisCardProcessesEntry
    MAX-ACCESS  not-accessible
    STATUS      current
    DESCRIPTION ""
    ::= { affirmedChassisMIB 12 }

affirmedChassisCardProcessesEntry OBJECT-TYPE
    SYNTAX      AffirmedChassisCardProcessesEntry
    MAX-ACCESS  not-accessible
    STATUS      current
    DESCRIPTION ""
    INDEX { affirmedChassisId, affirmedChassisCardId, affirmedChassisCardProcessesCpuNumber, affirmedChassisCardProcessesTaskname }
        ::= { affirmedChassisCardProcessesTable 1 }

AffirmedChassisCardProcessesEntry ::=
    SEQUENCE {
        affirmedChassisCardProcessesCpuNumber INTEGER,
        affirmedChassisCardProcessesTaskname String,
        affirmedChassisCardProcessesSvcname String,
        affirmedChassisCardProcessesHastate INTEGER,
        affirmedChassisCardProcessesOperstate INTEGER,
        affirmedChassisCardProcessesCpuutil String,
        affirmedChassisCardProcessesMemutil String,
        affirmedChassisCardProcessesFlashutil String,
        affirmedChassisCardProcessesIpaddress String,
        affirmedChassisCardProcessesPort Unsigned32,
        affirmedChassisCardProcessesPid ConfdString,
        affirmedChassisCardProcessesRelease String,
        affirmedChassisCardProcessesCpuutilint Integer32,
        affirmedChassisCardProcessesMemutilint Integer32
    }

affirmedChassisCardProcessesCpuNumber OBJECT-TYPE
    SYNTAX      INTEGER {cpu1(1),cpu2(2),cpu3(3),cpu4(4),cpu5(5),cpu6(6),cpu7(7),cpu8(8)}
    MAX-ACCESS  not-accessible
    STATUS      current
    DESCRIPTION ""
    ::= { affirmedChassisCardProcessesEntry 1 }

affirmedChassisCardProcessesTaskname OBJECT-TYPE
    SYNTAX      String
    MAX-ACCESS  not-accessible
    STATUS      current
    DESCRIPTION ""
    ::= { affirmedChassisCardProcessesEntry 2 }

affirmedChassisCardProcessesSvcname OBJECT-TYPE
    SYNTAX      String
    MAX-ACCESS  read-only
    STATUS      current
    DESCRIPTION ""
    ::= { affirmedChassisCardProcessesEntry 3 }

affirmedChassisCardProcessesHastate OBJECT-TYPE
    SYNTAX      INTEGER {active(1),standby(2),quiesced(3),quiescing(4),none(5),master(6),slave(7),primary(8),secondary(9)}
    MAX-ACCESS  read-only
    STATUS      current
    DESCRIPTION ""
    ::= { affirmedChassisCardProcessesEntry 4 }

affirmedChassisCardProcessesOperstate OBJECT-TYPE
    SYNTAX      INTEGER {up(101),down(102),partially-up(103),maint(104),dryup(105),congested(106),unknown(107)}
    MAX-ACCESS  read-only
    STATUS      current
    DESCRIPTION ""
    ::= { affirmedChassisCardProcessesEntry 5 }

affirmedChassisCardProcessesCpuutil OBJECT-TYPE
    SYNTAX      String
    MAX-ACCESS  read-only
    STATUS      deprecated
    DESCRIPTION ""
    ::= { affirmedChassisCardProcessesEntry 6 }

affirmedChassisCardProcessesMemutil OBJECT-TYPE
    SYNTAX      String
    MAX-ACCESS  read-only
    STATUS      deprecated
    DESCRIPTION ""
    ::= { affirmedChassisCardProcessesEntry 7 }

affirmedChassisCardProcessesFlashutil OBJECT-TYPE
    SYNTAX      String
    MAX-ACCESS  read-only
    STATUS      deprecated
    DESCRIPTION ""
    ::= { affirmedChassisCardProcessesEntry 8 }

affirmedChassisCardProcessesIpaddress OBJECT-TYPE
    SYNTAX      String
    MAX-ACCESS  read-only
    STATUS      current
    DESCRIPTION ""
    ::= { affirmedChassisCardProcessesEntry 9 }

affirmedChassisCardProcessesPort OBJECT-TYPE
    SYNTAX      Unsigned32
    MAX-ACCESS  read-only
    STATUS      current
    DESCRIPTION ""
    ::= { affirmedChassisCardProcessesEntry 10 }

affirmedChassisCardProcessesPid OBJECT-TYPE
    SYNTAX      ConfdString
    MAX-ACCESS  read-only
    STATUS      current
    DESCRIPTION ""
    ::= { affirmedChassisCardProcessesEntry 11 }

affirmedChassisCardProcessesRelease OBJECT-TYPE
    SYNTAX      String
    MAX-ACCESS  read-only
    STATUS      current
    DESCRIPTION ""
    ::= { affirmedChassisCardProcessesEntry 12 }

affirmedChassisCardProcessesCpuutilint OBJECT-TYPE
    SYNTAX      Integer32
    MAX-ACCESS  read-only
    STATUS      current
    DESCRIPTION ""
    ::= { affirmedChassisCardProcessesEntry 13 }

affirmedChassisCardProcessesMemutilint OBJECT-TYPE
    SYNTAX      Integer32
    MAX-ACCESS  read-only
    STATUS      current
    DESCRIPTION ""
    ::= { affirmedChassisCardProcessesEntry 14 }

affirmedChassisCardCrashSummaryTable OBJECT-TYPE
    SYNTAX      SEQUENCE OF AffirmedChassisCardCrashSummaryEntry
    MAX-ACCESS  not-accessible
    STATUS      current
    DESCRIPTION ""
    ::= { affirmedChassisMIB 13 }

affirmedChassisCardCrashSummaryEntry OBJECT-TYPE
    SYNTAX      AffirmedChassisCardCrashSummaryEntry
    MAX-ACCESS  not-accessible
    STATUS      current
    DESCRIPTION ""
    INDEX { affirmedChassisId, affirmedChassisCardId, affirmedChassisCardCrashSummarySecondssinceepoch, affirmedChassisCardCrashSummaryCorefilename }
        ::= { affirmedChassisCardCrashSummaryTable 1 }

AffirmedChassisCardCrashSummaryEntry ::=
    SEQUENCE {
        affirmedChassisCardCrashSummarySecondssinceepoch String,
        affirmedChassisCardCrashSummaryCorefilename String,
        affirmedChassisCardCrashSummaryTime String
    }

affirmedChassisCardCrashSummarySecondssinceepoch OBJECT-TYPE
    SYNTAX      String
    MAX-ACCESS  not-accessible
    STATUS      current
    DESCRIPTION ""
    ::= { affirmedChassisCardCrashSummaryEntry 1 }

affirmedChassisCardCrashSummaryCorefilename OBJECT-TYPE
    SYNTAX      String
    MAX-ACCESS  not-accessible
    STATUS      current
    DESCRIPTION ""
    ::= { affirmedChassisCardCrashSummaryEntry 2 }

affirmedChassisCardCrashSummaryTime OBJECT-TYPE
    SYNTAX      String
    MAX-ACCESS  read-only
    STATUS      current
    DESCRIPTION ""
    ::= { affirmedChassisCardCrashSummaryEntry 3 }

affirmedChassisCardCrashDetailTable OBJECT-TYPE
    SYNTAX      SEQUENCE OF AffirmedChassisCardCrashDetailEntry
    MAX-ACCESS  not-accessible
    STATUS      current
    DESCRIPTION ""
    ::= { affirmedChassisMIB 14 }

affirmedChassisCardCrashDetailEntry OBJECT-TYPE
    SYNTAX      AffirmedChassisCardCrashDetailEntry
    MAX-ACCESS  not-accessible
    STATUS      current
    DESCRIPTION ""
    INDEX { affirmedChassisId, affirmedChassisCardId, affirmedChassisCardCrashDetailCorefilename }
        ::= { affirmedChassisCardCrashDetailTable 1 }

AffirmedChassisCardCrashDetailEntry ::=
    SEQUENCE {
        affirmedChassisCardCrashDetailCorefilename String,
        affirmedChassisCardCrashDetailTime String,
        affirmedChassisCardCrashDetailNotes String
    }

affirmedChassisCardCrashDetailCorefilename OBJECT-TYPE
    SYNTAX      String
    MAX-ACCESS  not-accessible
    STATUS      current
    DESCRIPTION ""
    ::= { affirmedChassisCardCrashDetailEntry 1 }

affirmedChassisCardCrashDetailTime OBJECT-TYPE
    SYNTAX      String
    MAX-ACCESS  read-only
    STATUS      current
    DESCRIPTION ""
    ::= { affirmedChassisCardCrashDetailEntry 2 }

affirmedChassisCardCrashDetailNotes OBJECT-TYPE
    SYNTAX      String
    MAX-ACCESS  read-only
    STATUS      current
    DESCRIPTION ""
    ::= { affirmedChassisCardCrashDetailEntry 3 }

affirmedChassisCardPortstatsTable OBJECT-TYPE
    SYNTAX      SEQUENCE OF AffirmedChassisCardPortstatsEntry
    MAX-ACCESS  not-accessible
    STATUS      current
    DESCRIPTION ""
    ::= { affirmedChassisMIB 23 }

affirmedChassisCardPortstatsEntry OBJECT-TYPE
    SYNTAX      AffirmedChassisCardPortstatsEntry
    MAX-ACCESS  not-accessible
    STATUS      current
    DESCRIPTION ""
    INDEX { affirmedChassisId, affirmedChassisCardId, affirmedChassisCardPortstatsName }
        ::= { affirmedChassisCardPortstatsTable 1 }

AffirmedChassisCardPortstatsEntry ::=
    SEQUENCE {
        affirmedChassisCardPortstatsName String,
        affirmedChassisCardPortstatsRxpkts ConfdString,
        affirmedChassisCardPortstatsRxbytes ConfdString,
        affirmedChassisCardPortstatsRxpktsdropped ConfdString,
        affirmedChassisCardPortstatsTxpkts ConfdString,
        affirmedChassisCardPortstatsTxbytes ConfdString,
        affirmedChassisCardPortstatsTxpktsdropped ConfdString,
        affirmedChassisCardPortstatsRxPps ConfdString,
        affirmedChassisCardPortstatsRxBytesPs ConfdString,
        affirmedChassisCardPortstatsTxPps ConfdString,
        affirmedChassisCardPortstatsTxBytesPs ConfdString,
        affirmedChassisCardPortstatsUtilPercent ConfdString
    }

affirmedChassisCardPortstatsName OBJECT-TYPE
    SYNTAX      String
    MAX-ACCESS  not-accessible
    STATUS      current
    DESCRIPTION "Port Name"
    ::= { affirmedChassisCardPortstatsEntry 1 }

affirmedChassisCardPortstatsRxpkts OBJECT-TYPE
    SYNTAX      ConfdString
    MAX-ACCESS  read-only
    STATUS      current
    DESCRIPTION "Number of packets received on the port"
    ::= { affirmedChassisCardPortstatsEntry 2 }

affirmedChassisCardPortstatsRxbytes OBJECT-TYPE
    SYNTAX      ConfdString
    MAX-ACCESS  read-only
    STATUS      current
    DESCRIPTION "Number of bytes received on the port"
    ::= { affirmedChassisCardPortstatsEntry 3 }

affirmedChassisCardPortstatsRxpktsdropped OBJECT-TYPE
    SYNTAX      ConfdString
    MAX-ACCESS  read-only
    STATUS      current
    DESCRIPTION "Number of received packets dropped for any reason"
    ::= { affirmedChassisCardPortstatsEntry 4 }

affirmedChassisCardPortstatsTxpkts OBJECT-TYPE
    SYNTAX      ConfdString
    MAX-ACCESS  read-only
    STATUS      current
    DESCRIPTION "Number of packets transmitted on the port"
    ::= { affirmedChassisCardPortstatsEntry 5 }

affirmedChassisCardPortstatsTxbytes OBJECT-TYPE
    SYNTAX      ConfdString
    MAX-ACCESS  read-only
    STATUS      current
    DESCRIPTION "Number of bytes transmitted on the port"
    ::= { affirmedChassisCardPortstatsEntry 6 }

affirmedChassisCardPortstatsTxpktsdropped OBJECT-TYPE
    SYNTAX      ConfdString
    MAX-ACCESS  read-only
    STATUS      current
    DESCRIPTION "Number of transmitted packets dropped for any reason"
    ::= { affirmedChassisCardPortstatsEntry 7 }

affirmedChassisCardPortstatsRxPps OBJECT-TYPE
    SYNTAX      ConfdString
    MAX-ACCESS  read-only
    STATUS      current
    DESCRIPTION "Number of Rx Packets processed per second"
    ::= { affirmedChassisCardPortstatsEntry 8 }

affirmedChassisCardPortstatsRxBytesPs OBJECT-TYPE
    SYNTAX      ConfdString
    MAX-ACCESS  read-only
    STATUS      current
    DESCRIPTION "Number of Rx Bytes processed per second"
    ::= { affirmedChassisCardPortstatsEntry 9 }

affirmedChassisCardPortstatsTxPps OBJECT-TYPE
    SYNTAX      ConfdString
    MAX-ACCESS  read-only
    STATUS      current
    DESCRIPTION "Number of Tx Packets processed per second"
    ::= { affirmedChassisCardPortstatsEntry 10 }

affirmedChassisCardPortstatsTxBytesPs OBJECT-TYPE
    SYNTAX      ConfdString
    MAX-ACCESS  read-only
    STATUS      current
    DESCRIPTION "Number of Tx Bytes processed per second"
    ::= { affirmedChassisCardPortstatsEntry 11 }

affirmedChassisCardPortstatsUtilPercent OBJECT-TYPE
    SYNTAX      ConfdString
    MAX-ACCESS  read-only
    STATUS      current
    DESCRIPTION "Interface utilization percent"
    ::= { affirmedChassisCardPortstatsEntry 12 }

affirmedChassisCardDiskPerfStatusTable OBJECT-TYPE
    SYNTAX      SEQUENCE OF AffirmedChassisCardDiskPerfStatusEntry
    MAX-ACCESS  not-accessible
    STATUS      current
    DESCRIPTION ""
    ::= { affirmedChassisMIB 26 }

affirmedChassisCardDiskPerfStatusEntry OBJECT-TYPE
    SYNTAX      AffirmedChassisCardDiskPerfStatusEntry
    MAX-ACCESS  not-accessible
    STATUS      current
    DESCRIPTION ""
    INDEX { affirmedChassisId, affirmedChassisCardId, affirmedChassisCardDiskPerfStatusDiskname }
        ::= { affirmedChassisCardDiskPerfStatusTable 1 }

AffirmedChassisCardDiskPerfStatusEntry ::=
    SEQUENCE {
        affirmedChassisCardDiskPerfStatusDiskname String,
        affirmedChassisCardDiskPerfStatusDisksize ConfdString,
        affirmedChassisCardDiskPerfStatusDiskusage ConfdString,
        affirmedChassisCardDiskPerfStatusUsepercent String
    }

affirmedChassisCardDiskPerfStatusDiskname OBJECT-TYPE
    SYNTAX      String
    MAX-ACCESS  not-accessible
    STATUS      current
    DESCRIPTION "Disk Name"
    ::= { affirmedChassisCardDiskPerfStatusEntry 1 }

affirmedChassisCardDiskPerfStatusDisksize OBJECT-TYPE
    SYNTAX      ConfdString
    MAX-ACCESS  read-only
    STATUS      current
    DESCRIPTION "Disk size "
    ::= { affirmedChassisCardDiskPerfStatusEntry 2 }

affirmedChassisCardDiskPerfStatusDiskusage OBJECT-TYPE
    SYNTAX      ConfdString
    MAX-ACCESS  read-only
    STATUS      current
    DESCRIPTION "Disk Usage "
    ::= { affirmedChassisCardDiskPerfStatusEntry 3 }

affirmedChassisCardDiskPerfStatusUsepercent OBJECT-TYPE
    SYNTAX      String
    MAX-ACCESS  read-only
    STATUS      current
    DESCRIPTION "percentage of disk space in use"
    ::= { affirmedChassisCardDiskPerfStatusEntry 4 }

affirmedChassisCardFileMgmtStatsTable OBJECT-TYPE
    SYNTAX      SEQUENCE OF AffirmedChassisCardFileMgmtStatsEntry
    MAX-ACCESS  not-accessible
    STATUS      current
    DESCRIPTION ""
    ::= { affirmedChassisMIB 27 }

affirmedChassisCardFileMgmtStatsEntry OBJECT-TYPE
    SYNTAX      AffirmedChassisCardFileMgmtStatsEntry
    MAX-ACCESS  not-accessible
    STATUS      current
    DESCRIPTION ""
    INDEX { affirmedChassisId, affirmedChassisCardId, affirmedChassisCardFileMgmtStatsCpuNumber, affirmedChassisCardFileMgmtStatsPrefix }
        ::= { affirmedChassisCardFileMgmtStatsTable 1 }

AffirmedChassisCardFileMgmtStatsEntry ::=
    SEQUENCE {
        affirmedChassisCardFileMgmtStatsCpuNumber INTEGER,
        affirmedChassisCardFileMgmtStatsPrefix String,
        affirmedChassisCardFileMgmtStatsTransferred ConfdString,
        affirmedChassisCardFileMgmtStatsPurged ConfdString,
        affirmedChassisCardFileMgmtStatsPurgedcapacity ConfdString
    }

affirmedChassisCardFileMgmtStatsCpuNumber OBJECT-TYPE
    SYNTAX      INTEGER {cpu1(1),cpu2(2),cpu3(3),cpu4(4),cpu5(5),cpu6(6),cpu7(7),cpu8(8)}
    MAX-ACCESS  not-accessible
    STATUS      current
    DESCRIPTION ""
    ::= { affirmedChassisCardFileMgmtStatsEntry 1 }

affirmedChassisCardFileMgmtStatsPrefix OBJECT-TYPE
    SYNTAX      String
    MAX-ACCESS  not-accessible
    STATUS      current
    DESCRIPTION ""
    ::= { affirmedChassisCardFileMgmtStatsEntry 2 }

affirmedChassisCardFileMgmtStatsTransferred OBJECT-TYPE
    SYNTAX      ConfdString
    MAX-ACCESS  read-only
    STATUS      current
    DESCRIPTION ""
    ::= { affirmedChassisCardFileMgmtStatsEntry 3 }

affirmedChassisCardFileMgmtStatsPurged OBJECT-TYPE
    SYNTAX      ConfdString
    MAX-ACCESS  read-only
    STATUS      current
    DESCRIPTION ""
    ::= { affirmedChassisCardFileMgmtStatsEntry 4 }

affirmedChassisCardFileMgmtStatsPurgedcapacity OBJECT-TYPE
    SYNTAX      ConfdString
    MAX-ACCESS  read-only
    STATUS      current
    DESCRIPTION ""
    ::= { affirmedChassisCardFileMgmtStatsEntry 5 }

affirmedChassisCardEdrServerStatsTable OBJECT-TYPE
    SYNTAX      SEQUENCE OF AffirmedChassisCardEdrServerStatsEntry
    MAX-ACCESS  not-accessible
    STATUS      current
    DESCRIPTION ""
    ::= { affirmedChassisMIB 30 }

affirmedChassisCardEdrServerStatsEntry OBJECT-TYPE
    SYNTAX      AffirmedChassisCardEdrServerStatsEntry
    MAX-ACCESS  not-accessible
    STATUS      current
    DESCRIPTION ""
    INDEX { affirmedChassisId, affirmedChassisCardId, affirmedChassisCardEdrServerStatsTask, affirmedChassisCardEdrServerStatsName }
        ::= { affirmedChassisCardEdrServerStatsTable 1 }

AffirmedChassisCardEdrServerStatsEntry ::=
    SEQUENCE {
        affirmedChassisCardEdrServerStatsTask String,
        affirmedChassisCardEdrServerStatsName String,
        affirmedChassisCardEdrServerStatsState String,
        affirmedChassisCardEdrServerStatsRecordsSuccess ConfdString,
        affirmedChassisCardEdrServerStatsBytesSuccess ConfdString,
        affirmedChassisCardEdrServerStatsRecordsFailed ConfdString,
        affirmedChassisCardEdrServerStatsBytesFailed ConfdString,
        affirmedChassisCardEdrServerStatsConnects ConfdString,
        affirmedChassisCardEdrServerStatsLastStateChange String
    }

affirmedChassisCardEdrServerStatsTask OBJECT-TYPE
    SYNTAX      String
    MAX-ACCESS  not-accessible
    STATUS      current
    DESCRIPTION ""
    ::= { affirmedChassisCardEdrServerStatsEntry 1 }

affirmedChassisCardEdrServerStatsName OBJECT-TYPE
    SYNTAX      String
    MAX-ACCESS  not-accessible
    STATUS      current
    DESCRIPTION ""
    ::= { affirmedChassisCardEdrServerStatsEntry 2 }

affirmedChassisCardEdrServerStatsState OBJECT-TYPE
    SYNTAX      String
    MAX-ACCESS  read-only
    STATUS      current
    DESCRIPTION ""
    ::= { affirmedChassisCardEdrServerStatsEntry 3 }

affirmedChassisCardEdrServerStatsRecordsSuccess OBJECT-TYPE
    SYNTAX      ConfdString
    MAX-ACCESS  read-only
    STATUS      current
    DESCRIPTION ""
    ::= { affirmedChassisCardEdrServerStatsEntry 4 }

affirmedChassisCardEdrServerStatsBytesSuccess OBJECT-TYPE
    SYNTAX      ConfdString
    MAX-ACCESS  read-only
    STATUS      current
    DESCRIPTION ""
    ::= { affirmedChassisCardEdrServerStatsEntry 5 }

affirmedChassisCardEdrServerStatsRecordsFailed OBJECT-TYPE
    SYNTAX      ConfdString
    MAX-ACCESS  read-only
    STATUS      current
    DESCRIPTION ""
    ::= { affirmedChassisCardEdrServerStatsEntry 6 }

affirmedChassisCardEdrServerStatsBytesFailed OBJECT-TYPE
    SYNTAX      ConfdString
    MAX-ACCESS  read-only
    STATUS      current
    DESCRIPTION ""
    ::= { affirmedChassisCardEdrServerStatsEntry 7 }

affirmedChassisCardEdrServerStatsConnects OBJECT-TYPE
    SYNTAX      ConfdString
    MAX-ACCESS  read-only
    STATUS      current
    DESCRIPTION ""
    ::= { affirmedChassisCardEdrServerStatsEntry 8 }

affirmedChassisCardEdrServerStatsLastStateChange OBJECT-TYPE
    SYNTAX      String
    MAX-ACCESS  read-only
    STATUS      current
    DESCRIPTION "Time when state was last changed"
    ::= { affirmedChassisCardEdrServerStatsEntry 9 }

affirmedChassisCardEdrClientSessionStatsTable OBJECT-TYPE
    SYNTAX      SEQUENCE OF AffirmedChassisCardEdrClientSessionStatsEntry
    MAX-ACCESS  not-accessible
    STATUS      current
    DESCRIPTION ""
    ::= { affirmedChassisMIB 31 }

affirmedChassisCardEdrClientSessionStatsEntry OBJECT-TYPE
    SYNTAX      AffirmedChassisCardEdrClientSessionStatsEntry
    MAX-ACCESS  not-accessible
    STATUS      current
    DESCRIPTION ""
    INDEX { affirmedChassisId, affirmedChassisCardId, affirmedChassisCardEdrClientSessionStatsTask }
        ::= { affirmedChassisCardEdrClientSessionStatsTable 1 }

AffirmedChassisCardEdrClientSessionStatsEntry ::=
    SEQUENCE {
        affirmedChassisCardEdrClientSessionStatsTask String,
        affirmedChassisCardEdrClientSessionStatsSessionStartSuccess ConfdString,
        affirmedChassisCardEdrClientSessionStatsSessionStopSuccess ConfdString,
        affirmedChassisCardEdrClientSessionStatsSessionAttemptSuccess ConfdString,
        affirmedChassisCardEdrClientSessionStatsSessionInterimSuccess ConfdString,
        affirmedChassisCardEdrClientSessionStatsSessionStartFailed ConfdString,
        affirmedChassisCardEdrClientSessionStatsSessionStopFailed ConfdString,
        affirmedChassisCardEdrClientSessionStatsSessionAttemptFailed ConfdString,
        affirmedChassisCardEdrClientSessionStatsSessionInterimFailed ConfdString
    }

affirmedChassisCardEdrClientSessionStatsTask OBJECT-TYPE
    SYNTAX      String
    MAX-ACCESS  not-accessible
    STATUS      current
    DESCRIPTION ""
    ::= { affirmedChassisCardEdrClientSessionStatsEntry 1 }

affirmedChassisCardEdrClientSessionStatsSessionStartSuccess OBJECT-TYPE
    SYNTAX      ConfdString
    MAX-ACCESS  read-only
    STATUS      current
    DESCRIPTION ""
    ::= { affirmedChassisCardEdrClientSessionStatsEntry 2 }

affirmedChassisCardEdrClientSessionStatsSessionStopSuccess OBJECT-TYPE
    SYNTAX      ConfdString
    MAX-ACCESS  read-only
    STATUS      current
    DESCRIPTION ""
    ::= { affirmedChassisCardEdrClientSessionStatsEntry 3 }

affirmedChassisCardEdrClientSessionStatsSessionAttemptSuccess OBJECT-TYPE
    SYNTAX      ConfdString
    MAX-ACCESS  read-only
    STATUS      current
    DESCRIPTION ""
    ::= { affirmedChassisCardEdrClientSessionStatsEntry 4 }

affirmedChassisCardEdrClientSessionStatsSessionInterimSuccess OBJECT-TYPE
    SYNTAX      ConfdString
    MAX-ACCESS  read-only
    STATUS      current
    DESCRIPTION ""
    ::= { affirmedChassisCardEdrClientSessionStatsEntry 5 }

affirmedChassisCardEdrClientSessionStatsSessionStartFailed OBJECT-TYPE
    SYNTAX      ConfdString
    MAX-ACCESS  read-only
    STATUS      current
    DESCRIPTION ""
    ::= { affirmedChassisCardEdrClientSessionStatsEntry 6 }

affirmedChassisCardEdrClientSessionStatsSessionStopFailed OBJECT-TYPE
    SYNTAX      ConfdString
    MAX-ACCESS  read-only
    STATUS      current
    DESCRIPTION ""
    ::= { affirmedChassisCardEdrClientSessionStatsEntry 7 }

affirmedChassisCardEdrClientSessionStatsSessionAttemptFailed OBJECT-TYPE
    SYNTAX      ConfdString
    MAX-ACCESS  read-only
    STATUS      current
    DESCRIPTION ""
    ::= { affirmedChassisCardEdrClientSessionStatsEntry 8 }

affirmedChassisCardEdrClientSessionStatsSessionInterimFailed OBJECT-TYPE
    SYNTAX      ConfdString
    MAX-ACCESS  read-only
    STATUS      current
    DESCRIPTION ""
    ::= { affirmedChassisCardEdrClientSessionStatsEntry 9 }

affirmedChassisCardEdrClientBearerStatsTable OBJECT-TYPE
    SYNTAX      SEQUENCE OF AffirmedChassisCardEdrClientBearerStatsEntry
    MAX-ACCESS  not-accessible
    STATUS      current
    DESCRIPTION ""
    ::= { affirmedChassisMIB 32 }

affirmedChassisCardEdrClientBearerStatsEntry OBJECT-TYPE
    SYNTAX      AffirmedChassisCardEdrClientBearerStatsEntry
    MAX-ACCESS  not-accessible
    STATUS      current
    DESCRIPTION ""
    INDEX { affirmedChassisId, affirmedChassisCardId, affirmedChassisCardEdrClientBearerStatsTask }
        ::= { affirmedChassisCardEdrClientBearerStatsTable 1 }

AffirmedChassisCardEdrClientBearerStatsEntry ::=
    SEQUENCE {
        affirmedChassisCardEdrClientBearerStatsTask String,
        affirmedChassisCardEdrClientBearerStatsBearerStartSuccess ConfdString,
        affirmedChassisCardEdrClientBearerStatsBearerStopSuccess ConfdString,
        affirmedChassisCardEdrClientBearerStatsBearerAttemptSuccess ConfdString,
        affirmedChassisCardEdrClientBearerStatsBearerInterimSuccess ConfdString,
        affirmedChassisCardEdrClientBearerStatsBearerStartFailed ConfdString,
        affirmedChassisCardEdrClientBearerStatsBearerStopFailed ConfdString,
        affirmedChassisCardEdrClientBearerStatsBearerAttemptFailed ConfdString,
        affirmedChassisCardEdrClientBearerStatsBearerInterimFailed ConfdString
    }

affirmedChassisCardEdrClientBearerStatsTask OBJECT-TYPE
    SYNTAX      String
    MAX-ACCESS  not-accessible
    STATUS      current
    DESCRIPTION ""
    ::= { affirmedChassisCardEdrClientBearerStatsEntry 1 }

affirmedChassisCardEdrClientBearerStatsBearerStartSuccess OBJECT-TYPE
    SYNTAX      ConfdString
    MAX-ACCESS  read-only
    STATUS      current
    DESCRIPTION ""
    ::= { affirmedChassisCardEdrClientBearerStatsEntry 2 }

affirmedChassisCardEdrClientBearerStatsBearerStopSuccess OBJECT-TYPE
    SYNTAX      ConfdString
    MAX-ACCESS  read-only
    STATUS      current
    DESCRIPTION ""
    ::= { affirmedChassisCardEdrClientBearerStatsEntry 3 }

affirmedChassisCardEdrClientBearerStatsBearerAttemptSuccess OBJECT-TYPE
    SYNTAX      ConfdString
    MAX-ACCESS  read-only
    STATUS      current
    DESCRIPTION ""
    ::= { affirmedChassisCardEdrClientBearerStatsEntry 4 }

affirmedChassisCardEdrClientBearerStatsBearerInterimSuccess OBJECT-TYPE
    SYNTAX      ConfdString
    MAX-ACCESS  read-only
    STATUS      current
    DESCRIPTION ""
    ::= { affirmedChassisCardEdrClientBearerStatsEntry 5 }

affirmedChassisCardEdrClientBearerStatsBearerStartFailed OBJECT-TYPE
    SYNTAX      ConfdString
    MAX-ACCESS  read-only
    STATUS      current
    DESCRIPTION ""
    ::= { affirmedChassisCardEdrClientBearerStatsEntry 6 }

affirmedChassisCardEdrClientBearerStatsBearerStopFailed OBJECT-TYPE
    SYNTAX      ConfdString
    MAX-ACCESS  read-only
    STATUS      current
    DESCRIPTION ""
    ::= { affirmedChassisCardEdrClientBearerStatsEntry 7 }

affirmedChassisCardEdrClientBearerStatsBearerAttemptFailed OBJECT-TYPE
    SYNTAX      ConfdString
    MAX-ACCESS  read-only
    STATUS      current
    DESCRIPTION ""
    ::= { affirmedChassisCardEdrClientBearerStatsEntry 8 }

affirmedChassisCardEdrClientBearerStatsBearerInterimFailed OBJECT-TYPE
    SYNTAX      ConfdString
    MAX-ACCESS  read-only
    STATUS      current
    DESCRIPTION ""
    ::= { affirmedChassisCardEdrClientBearerStatsEntry 9 }

affirmedChassisCardEdrClientFlowStatsTable OBJECT-TYPE
    SYNTAX      SEQUENCE OF AffirmedChassisCardEdrClientFlowStatsEntry
    MAX-ACCESS  not-accessible
    STATUS      current
    DESCRIPTION ""
    ::= { affirmedChassisMIB 33 }

affirmedChassisCardEdrClientFlowStatsEntry OBJECT-TYPE
    SYNTAX      AffirmedChassisCardEdrClientFlowStatsEntry
    MAX-ACCESS  not-accessible
    STATUS      current
    DESCRIPTION ""
    INDEX { affirmedChassisId, affirmedChassisCardId, affirmedChassisCardEdrClientFlowStatsTask }
        ::= { affirmedChassisCardEdrClientFlowStatsTable 1 }

AffirmedChassisCardEdrClientFlowStatsEntry ::=
    SEQUENCE {
        affirmedChassisCardEdrClientFlowStatsTask String,
        affirmedChassisCardEdrClientFlowStatsFlowStartSuccess ConfdString,
        affirmedChassisCardEdrClientFlowStatsFlowStopSuccess ConfdString,
        affirmedChassisCardEdrClientFlowStatsFlowInterimSuccess ConfdString,
        affirmedChassisCardEdrClientFlowStatsFlowStartFailed ConfdString,
        affirmedChassisCardEdrClientFlowStatsFlowStopFailed ConfdString,
        affirmedChassisCardEdrClientFlowStatsFlowInterimFailed ConfdString
    }

affirmedChassisCardEdrClientFlowStatsTask OBJECT-TYPE
    SYNTAX      String
    MAX-ACCESS  not-accessible
    STATUS      current
    DESCRIPTION ""
    ::= { affirmedChassisCardEdrClientFlowStatsEntry 1 }

affirmedChassisCardEdrClientFlowStatsFlowStartSuccess OBJECT-TYPE
    SYNTAX      ConfdString
    MAX-ACCESS  read-only
    STATUS      current
    DESCRIPTION ""
    ::= { affirmedChassisCardEdrClientFlowStatsEntry 2 }

affirmedChassisCardEdrClientFlowStatsFlowStopSuccess OBJECT-TYPE
    SYNTAX      ConfdString
    MAX-ACCESS  read-only
    STATUS      current
    DESCRIPTION ""
    ::= { affirmedChassisCardEdrClientFlowStatsEntry 3 }

affirmedChassisCardEdrClientFlowStatsFlowInterimSuccess OBJECT-TYPE
    SYNTAX      ConfdString
    MAX-ACCESS  read-only
    STATUS      current
    DESCRIPTION ""
    ::= { affirmedChassisCardEdrClientFlowStatsEntry 4 }

affirmedChassisCardEdrClientFlowStatsFlowStartFailed OBJECT-TYPE
    SYNTAX      ConfdString
    MAX-ACCESS  read-only
    STATUS      current
    DESCRIPTION ""
    ::= { affirmedChassisCardEdrClientFlowStatsEntry 5 }

affirmedChassisCardEdrClientFlowStatsFlowStopFailed OBJECT-TYPE
    SYNTAX      ConfdString
    MAX-ACCESS  read-only
    STATUS      current
    DESCRIPTION ""
    ::= { affirmedChassisCardEdrClientFlowStatsEntry 6 }

affirmedChassisCardEdrClientFlowStatsFlowInterimFailed OBJECT-TYPE
    SYNTAX      ConfdString
    MAX-ACCESS  read-only
    STATUS      current
    DESCRIPTION ""
    ::= { affirmedChassisCardEdrClientFlowStatsEntry 7 }

affirmedChassisCardEdrClientHttpStatsTable OBJECT-TYPE
    SYNTAX      SEQUENCE OF AffirmedChassisCardEdrClientHttpStatsEntry
    MAX-ACCESS  not-accessible
    STATUS      current
    DESCRIPTION ""
    ::= { affirmedChassisMIB 34 }

affirmedChassisCardEdrClientHttpStatsEntry OBJECT-TYPE
    SYNTAX      AffirmedChassisCardEdrClientHttpStatsEntry
    MAX-ACCESS  not-accessible
    STATUS      current
    DESCRIPTION ""
    INDEX { affirmedChassisId, affirmedChassisCardId, affirmedChassisCardEdrClientHttpStatsTask }
        ::= { affirmedChassisCardEdrClientHttpStatsTable 1 }

AffirmedChassisCardEdrClientHttpStatsEntry ::=
    SEQUENCE {
        affirmedChassisCardEdrClientHttpStatsTask String,
        affirmedChassisCardEdrClientHttpStatsHttpSuccess ConfdString,
        affirmedChassisCardEdrClientHttpStatsHttpFailed ConfdString
    }

affirmedChassisCardEdrClientHttpStatsTask OBJECT-TYPE
    SYNTAX      String
    MAX-ACCESS  not-accessible
    STATUS      current
    DESCRIPTION ""
    ::= { affirmedChassisCardEdrClientHttpStatsEntry 1 }

affirmedChassisCardEdrClientHttpStatsHttpSuccess OBJECT-TYPE
    SYNTAX      ConfdString
    MAX-ACCESS  read-only
    STATUS      current
    DESCRIPTION ""
    ::= { affirmedChassisCardEdrClientHttpStatsEntry 2 }

affirmedChassisCardEdrClientHttpStatsHttpFailed OBJECT-TYPE
    SYNTAX      ConfdString
    MAX-ACCESS  read-only
    STATUS      current
    DESCRIPTION ""
    ::= { affirmedChassisCardEdrClientHttpStatsEntry 3 }

affirmedChassisCardEdrClientPilotStatsTable OBJECT-TYPE
    SYNTAX      SEQUENCE OF AffirmedChassisCardEdrClientPilotStatsEntry
    MAX-ACCESS  not-accessible
    STATUS      current
    DESCRIPTION ""
    ::= { affirmedChassisMIB 36 }

affirmedChassisCardEdrClientPilotStatsEntry OBJECT-TYPE
    SYNTAX      AffirmedChassisCardEdrClientPilotStatsEntry
    MAX-ACCESS  not-accessible
    STATUS      current
    DESCRIPTION ""
    INDEX { affirmedChassisId, affirmedChassisCardId, affirmedChassisCardEdrClientPilotStatsTask }
        ::= { affirmedChassisCardEdrClientPilotStatsTable 1 }

AffirmedChassisCardEdrClientPilotStatsEntry ::=
    SEQUENCE {
        affirmedChassisCardEdrClientPilotStatsTask String,
        affirmedChassisCardEdrClientPilotStatsPilotStartSuccess ConfdString,
        affirmedChassisCardEdrClientPilotStatsPilotStopSuccess ConfdString,
        affirmedChassisCardEdrClientPilotStatsPilotNatBindingStartSuccess ConfdString,
        affirmedChassisCardEdrClientPilotStatsPilotNatBindingStopSuccess ConfdString,
        affirmedChassisCardEdrClientPilotStatsPilotRatTypeChangeSuccess ConfdString,
        affirmedChassisCardEdrClientPilotStatsPilotStartFailed ConfdString,
        affirmedChassisCardEdrClientPilotStatsPilotStopFailed ConfdString,
        affirmedChassisCardEdrClientPilotStatsPilotNatBindingStartFailed ConfdString,
        affirmedChassisCardEdrClientPilotStatsPilotNatBindingStopFailed ConfdString,
        affirmedChassisCardEdrClientPilotStatsPilotRatTypeChangeFailed ConfdString
    }

affirmedChassisCardEdrClientPilotStatsTask OBJECT-TYPE
    SYNTAX      String
    MAX-ACCESS  not-accessible
    STATUS      current
    DESCRIPTION ""
    ::= { affirmedChassisCardEdrClientPilotStatsEntry 1 }

affirmedChassisCardEdrClientPilotStatsPilotStartSuccess OBJECT-TYPE
    SYNTAX      ConfdString
    MAX-ACCESS  read-only
    STATUS      current
    DESCRIPTION ""
    ::= { affirmedChassisCardEdrClientPilotStatsEntry 2 }

affirmedChassisCardEdrClientPilotStatsPilotStopSuccess OBJECT-TYPE
    SYNTAX      ConfdString
    MAX-ACCESS  read-only
    STATUS      current
    DESCRIPTION ""
    ::= { affirmedChassisCardEdrClientPilotStatsEntry 3 }

affirmedChassisCardEdrClientPilotStatsPilotNatBindingStartSuccess OBJECT-TYPE
    SYNTAX      ConfdString
    MAX-ACCESS  read-only
    STATUS      current
    DESCRIPTION ""
    ::= { affirmedChassisCardEdrClientPilotStatsEntry 4 }

affirmedChassisCardEdrClientPilotStatsPilotNatBindingStopSuccess OBJECT-TYPE
    SYNTAX      ConfdString
    MAX-ACCESS  read-only
    STATUS      current
    DESCRIPTION ""
    ::= { affirmedChassisCardEdrClientPilotStatsEntry 5 }

affirmedChassisCardEdrClientPilotStatsPilotRatTypeChangeSuccess OBJECT-TYPE
    SYNTAX      ConfdString
    MAX-ACCESS  read-only
    STATUS      current
    DESCRIPTION ""
    ::= { affirmedChassisCardEdrClientPilotStatsEntry 6 }

affirmedChassisCardEdrClientPilotStatsPilotStartFailed OBJECT-TYPE
    SYNTAX      ConfdString
    MAX-ACCESS  read-only
    STATUS      current
    DESCRIPTION ""
    ::= { affirmedChassisCardEdrClientPilotStatsEntry 7 }

affirmedChassisCardEdrClientPilotStatsPilotStopFailed OBJECT-TYPE
    SYNTAX      ConfdString
    MAX-ACCESS  read-only
    STATUS      current
    DESCRIPTION ""
    ::= { affirmedChassisCardEdrClientPilotStatsEntry 8 }

affirmedChassisCardEdrClientPilotStatsPilotNatBindingStartFailed OBJECT-TYPE
    SYNTAX      ConfdString
    MAX-ACCESS  read-only
    STATUS      current
    DESCRIPTION ""
    ::= { affirmedChassisCardEdrClientPilotStatsEntry 9 }

affirmedChassisCardEdrClientPilotStatsPilotNatBindingStopFailed OBJECT-TYPE
    SYNTAX      ConfdString
    MAX-ACCESS  read-only
    STATUS      current
    DESCRIPTION ""
    ::= { affirmedChassisCardEdrClientPilotStatsEntry 10 }

affirmedChassisCardEdrClientPilotStatsPilotRatTypeChangeFailed OBJECT-TYPE
    SYNTAX      ConfdString
    MAX-ACCESS  read-only
    STATUS      current
    DESCRIPTION ""
    ::= { affirmedChassisCardEdrClientPilotStatsEntry 11 }

affirmedChassisCardEdrClientRTTStatsTable OBJECT-TYPE
    SYNTAX      SEQUENCE OF AffirmedChassisCardEdrClientRTTStatsEntry
    MAX-ACCESS  not-accessible
    STATUS      current
    DESCRIPTION ""
    ::= { affirmedChassisMIB 37 }

affirmedChassisCardEdrClientRTTStatsEntry OBJECT-TYPE
    SYNTAX      AffirmedChassisCardEdrClientRTTStatsEntry
    MAX-ACCESS  not-accessible
    STATUS      current
    DESCRIPTION ""
    INDEX { affirmedChassisId, affirmedChassisCardId, affirmedChassisCardEdrClientRTTStatsTask }
        ::= { affirmedChassisCardEdrClientRTTStatsTable 1 }

AffirmedChassisCardEdrClientRTTStatsEntry ::=
    SEQUENCE {
        affirmedChassisCardEdrClientRTTStatsTask String,
        affirmedChassisCardEdrClientRTTStatsRttGtpS5Success ConfdString,
        affirmedChassisCardEdrClientRTTStatsRttGtpS8Success ConfdString,
        affirmedChassisCardEdrClientRTTStatsRttGtpS11Success ConfdString,
        affirmedChassisCardEdrClientRTTStatsRttGtpS4Success ConfdString,
        affirmedChassisCardEdrClientRTTStatsRttGtpS2ASuccess ConfdString,
        affirmedChassisCardEdrClientRTTStatsRttGtpS2BSuccess ConfdString,
        affirmedChassisCardEdrClientRTTStatsRttGtpGNSuccess ConfdString,
        affirmedChassisCardEdrClientRTTStatsRttGtpGPSuccess ConfdString,
        affirmedChassisCardEdrClientRTTStatsRttDiameterGxSuccess ConfdString,
        affirmedChassisCardEdrClientRTTStatsRttDiameterGySuccess ConfdString,
        affirmedChassisCardEdrClientRTTStatsRttDiameterS6BSuccess ConfdString,
        affirmedChassisCardEdrClientRTTStatsRttGtpS5Failed ConfdString,
        affirmedChassisCardEdrClientRTTStatsRttGtpS8Failed ConfdString,
        affirmedChassisCardEdrClientRTTStatsRttGtpS11Failed ConfdString,
        affirmedChassisCardEdrClientRTTStatsRttGtpS4Failed ConfdString,
        affirmedChassisCardEdrClientRTTStatsRttGtpS2AFailed ConfdString,
        affirmedChassisCardEdrClientRTTStatsRttGtpS2BFailed ConfdString,
        affirmedChassisCardEdrClientRTTStatsRttGtpGNFailed ConfdString,
        affirmedChassisCardEdrClientRTTStatsRttGtpGPFailed ConfdString,
        affirmedChassisCardEdrClientRTTStatsRttDiameterGxFailed ConfdString,
        affirmedChassisCardEdrClientRTTStatsRttDiameterGyFailed ConfdString,
        affirmedChassisCardEdrClientRTTStatsRttDiameterS6BFailed ConfdString,
        affirmedChassisCardEdrClientRTTStatsRttDiameterSWmSuccess ConfdString,
        affirmedChassisCardEdrClientRTTStatsRttIkeSWuSuccess ConfdString,
        affirmedChassisCardEdrClientRTTStatsRttDiameterSWmFailed ConfdString,
        affirmedChassisCardEdrClientRTTStatsRttIkeSWuFailed ConfdString
    }

affirmedChassisCardEdrClientRTTStatsTask OBJECT-TYPE
    SYNTAX      String
    MAX-ACCESS  not-accessible
    STATUS      current
    DESCRIPTION ""
    ::= { affirmedChassisCardEdrClientRTTStatsEntry 1 }

affirmedChassisCardEdrClientRTTStatsRttGtpS5Success OBJECT-TYPE
    SYNTAX      ConfdString
    MAX-ACCESS  read-only
    STATUS      current
    DESCRIPTION ""
    ::= { affirmedChassisCardEdrClientRTTStatsEntry 2 }

affirmedChassisCardEdrClientRTTStatsRttGtpS8Success OBJECT-TYPE
    SYNTAX      ConfdString
    MAX-ACCESS  read-only
    STATUS      current
    DESCRIPTION ""
    ::= { affirmedChassisCardEdrClientRTTStatsEntry 3 }

affirmedChassisCardEdrClientRTTStatsRttGtpS11Success OBJECT-TYPE
    SYNTAX      ConfdString
    MAX-ACCESS  read-only
    STATUS      current
    DESCRIPTION ""
    ::= { affirmedChassisCardEdrClientRTTStatsEntry 4 }

affirmedChassisCardEdrClientRTTStatsRttGtpS4Success OBJECT-TYPE
    SYNTAX      ConfdString
    MAX-ACCESS  read-only
    STATUS      current
    DESCRIPTION ""
    ::= { affirmedChassisCardEdrClientRTTStatsEntry 5 }

affirmedChassisCardEdrClientRTTStatsRttGtpS2ASuccess OBJECT-TYPE
    SYNTAX      ConfdString
    MAX-ACCESS  read-only
    STATUS      current
    DESCRIPTION ""
    ::= { affirmedChassisCardEdrClientRTTStatsEntry 6 }

affirmedChassisCardEdrClientRTTStatsRttGtpS2BSuccess OBJECT-TYPE
    SYNTAX      ConfdString
    MAX-ACCESS  read-only
    STATUS      current
    DESCRIPTION ""
    ::= { affirmedChassisCardEdrClientRTTStatsEntry 7 }

affirmedChassisCardEdrClientRTTStatsRttGtpGNSuccess OBJECT-TYPE
    SYNTAX      ConfdString
    MAX-ACCESS  read-only
    STATUS      current
    DESCRIPTION ""
    ::= { affirmedChassisCardEdrClientRTTStatsEntry 8 }

affirmedChassisCardEdrClientRTTStatsRttGtpGPSuccess OBJECT-TYPE
    SYNTAX      ConfdString
    MAX-ACCESS  read-only
    STATUS      current
    DESCRIPTION ""
    ::= { affirmedChassisCardEdrClientRTTStatsEntry 9 }

affirmedChassisCardEdrClientRTTStatsRttDiameterGxSuccess OBJECT-TYPE
    SYNTAX      ConfdString
    MAX-ACCESS  read-only
    STATUS      current
    DESCRIPTION ""
    ::= { affirmedChassisCardEdrClientRTTStatsEntry 10 }

affirmedChassisCardEdrClientRTTStatsRttDiameterGySuccess OBJECT-TYPE
    SYNTAX      ConfdString
    MAX-ACCESS  read-only
    STATUS      current
    DESCRIPTION ""
    ::= { affirmedChassisCardEdrClientRTTStatsEntry 11 }

affirmedChassisCardEdrClientRTTStatsRttDiameterS6BSuccess OBJECT-TYPE
    SYNTAX      ConfdString
    MAX-ACCESS  read-only
    STATUS      current
    DESCRIPTION ""
    ::= { affirmedChassisCardEdrClientRTTStatsEntry 12 }

affirmedChassisCardEdrClientRTTStatsRttGtpS5Failed OBJECT-TYPE
    SYNTAX      ConfdString
    MAX-ACCESS  read-only
    STATUS      current
    DESCRIPTION ""
    ::= { affirmedChassisCardEdrClientRTTStatsEntry 13 }

affirmedChassisCardEdrClientRTTStatsRttGtpS8Failed OBJECT-TYPE
    SYNTAX      ConfdString
    MAX-ACCESS  read-only
    STATUS      current
    DESCRIPTION ""
    ::= { affirmedChassisCardEdrClientRTTStatsEntry 14 }

affirmedChassisCardEdrClientRTTStatsRttGtpS11Failed OBJECT-TYPE
    SYNTAX      ConfdString
    MAX-ACCESS  read-only
    STATUS      current
    DESCRIPTION ""
    ::= { affirmedChassisCardEdrClientRTTStatsEntry 15 }

affirmedChassisCardEdrClientRTTStatsRttGtpS4Failed OBJECT-TYPE
    SYNTAX      ConfdString
    MAX-ACCESS  read-only
    STATUS      current
    DESCRIPTION ""
    ::= { affirmedChassisCardEdrClientRTTStatsEntry 16 }

affirmedChassisCardEdrClientRTTStatsRttGtpS2AFailed OBJECT-TYPE
    SYNTAX      ConfdString
    MAX-ACCESS  read-only
    STATUS      current
    DESCRIPTION ""
    ::= { affirmedChassisCardEdrClientRTTStatsEntry 17 }

affirmedChassisCardEdrClientRTTStatsRttGtpS2BFailed OBJECT-TYPE
    SYNTAX      ConfdString
    MAX-ACCESS  read-only
    STATUS      current
    DESCRIPTION ""
    ::= { affirmedChassisCardEdrClientRTTStatsEntry 18 }

affirmedChassisCardEdrClientRTTStatsRttGtpGNFailed OBJECT-TYPE
    SYNTAX      ConfdString
    MAX-ACCESS  read-only
    STATUS      current
    DESCRIPTION ""
    ::= { affirmedChassisCardEdrClientRTTStatsEntry 19 }

affirmedChassisCardEdrClientRTTStatsRttGtpGPFailed OBJECT-TYPE
    SYNTAX      ConfdString
    MAX-ACCESS  read-only
    STATUS      current
    DESCRIPTION ""
    ::= { affirmedChassisCardEdrClientRTTStatsEntry 20 }

affirmedChassisCardEdrClientRTTStatsRttDiameterGxFailed OBJECT-TYPE
    SYNTAX      ConfdString
    MAX-ACCESS  read-only
    STATUS      current
    DESCRIPTION ""
    ::= { affirmedChassisCardEdrClientRTTStatsEntry 21 }

affirmedChassisCardEdrClientRTTStatsRttDiameterGyFailed OBJECT-TYPE
    SYNTAX      ConfdString
    MAX-ACCESS  read-only
    STATUS      current
    DESCRIPTION ""
    ::= { affirmedChassisCardEdrClientRTTStatsEntry 22 }

affirmedChassisCardEdrClientRTTStatsRttDiameterS6BFailed OBJECT-TYPE
    SYNTAX      ConfdString
    MAX-ACCESS  read-only
    STATUS      current
    DESCRIPTION ""
    ::= { affirmedChassisCardEdrClientRTTStatsEntry 23 }

affirmedChassisCardEdrClientRTTStatsRttDiameterSWmSuccess OBJECT-TYPE
    SYNTAX      ConfdString
    MAX-ACCESS  read-only
    STATUS      current
    DESCRIPTION ""
    ::= { affirmedChassisCardEdrClientRTTStatsEntry 24 }

affirmedChassisCardEdrClientRTTStatsRttIkeSWuSuccess OBJECT-TYPE
    SYNTAX      ConfdString
    MAX-ACCESS  read-only
    STATUS      current
    DESCRIPTION ""
    ::= { affirmedChassisCardEdrClientRTTStatsEntry 25 }

affirmedChassisCardEdrClientRTTStatsRttDiameterSWmFailed OBJECT-TYPE
    SYNTAX      ConfdString
    MAX-ACCESS  read-only
    STATUS      current
    DESCRIPTION ""
    ::= { affirmedChassisCardEdrClientRTTStatsEntry 26 }

affirmedChassisCardEdrClientRTTStatsRttIkeSWuFailed OBJECT-TYPE
    SYNTAX      ConfdString
    MAX-ACCESS  read-only
    STATUS      current
    DESCRIPTION ""
    ::= { affirmedChassisCardEdrClientRTTStatsEntry 27 }

affirmedChassisCardPortdetailsTable OBJECT-TYPE
    SYNTAX      SEQUENCE OF AffirmedChassisCardPortdetailsEntry
    MAX-ACCESS  not-accessible
    STATUS      current
    DESCRIPTION ""
    ::= { affirmedChassisMIB 39 }

affirmedChassisCardPortdetailsEntry OBJECT-TYPE
    SYNTAX      AffirmedChassisCardPortdetailsEntry
    MAX-ACCESS  not-accessible
    STATUS      current
    DESCRIPTION ""
    INDEX { affirmedChassisId, affirmedChassisCardId, affirmedChassisCardPortdetailsInterfacename }
        ::= { affirmedChassisCardPortdetailsTable 1 }

AffirmedChassisCardPortdetailsEntry ::=
    SEQUENCE {
        affirmedChassisCardPortdetailsInterfacename String,
        affirmedChassisCardPortdetailsMac String,
        affirmedChassisCardPortdetailsLinkStatus String,
        affirmedChassisCardPortdetailsRecoveryProgress String,
        affirmedChassisCardPortdetailsPci String,
        affirmedChassisCardPortdetailsDriverInfo String,
        affirmedChassisCardPortdetailsRxQsz ConfdString,
        affirmedChassisCardPortdetailsTxQsz ConfdString,
        affirmedChassisCardPortdetailsLinkSpeed ConfdString,
        affirmedChassisCardPortdetailsRecoveryCount ConfdString
    }

affirmedChassisCardPortdetailsInterfacename OBJECT-TYPE
    SYNTAX      String
    MAX-ACCESS  not-accessible
    STATUS      current
    DESCRIPTION "interface name"
    ::= { affirmedChassisCardPortdetailsEntry 1 }

affirmedChassisCardPortdetailsMac OBJECT-TYPE
    SYNTAX      String
    MAX-ACCESS  read-only
    STATUS      current
    DESCRIPTION "MAC id of the interface"
    ::= { affirmedChassisCardPortdetailsEntry 2 }

affirmedChassisCardPortdetailsLinkStatus OBJECT-TYPE
    SYNTAX      String
    MAX-ACCESS  read-only
    STATUS      current
    DESCRIPTION "Link Status of the interface"
    ::= { affirmedChassisCardPortdetailsEntry 3 }

affirmedChassisCardPortdetailsRecoveryProgress OBJECT-TYPE
    SYNTAX      String
    MAX-ACCESS  read-only
    STATUS      current
    DESCRIPTION "View if the recovery is in progress"
    ::= { affirmedChassisCardPortdetailsEntry 4 }

affirmedChassisCardPortdetailsPci OBJECT-TYPE
    SYNTAX      String
    MAX-ACCESS  read-only
    STATUS      current
    DESCRIPTION "PCI address of the interface"
    ::= { affirmedChassisCardPortdetailsEntry 5 }

affirmedChassisCardPortdetailsDriverInfo OBJECT-TYPE
    SYNTAX      String
    MAX-ACCESS  read-only
    STATUS      current
    DESCRIPTION "Driver Details of the interface"
    ::= { affirmedChassisCardPortdetailsEntry 6 }

affirmedChassisCardPortdetailsRxQsz OBJECT-TYPE
    SYNTAX      ConfdString
    MAX-ACCESS  read-only
    STATUS      current
    DESCRIPTION "RX Queue Size"
    ::= { affirmedChassisCardPortdetailsEntry 7 }

affirmedChassisCardPortdetailsTxQsz OBJECT-TYPE
    SYNTAX      ConfdString
    MAX-ACCESS  read-only
    STATUS      current
    DESCRIPTION "TX Queue size"
    ::= { affirmedChassisCardPortdetailsEntry 8 }

affirmedChassisCardPortdetailsLinkSpeed OBJECT-TYPE
    SYNTAX      ConfdString
    MAX-ACCESS  read-only
    STATUS      current
    DESCRIPTION "Link speed of the interface"
    ::= { affirmedChassisCardPortdetailsEntry 9 }

affirmedChassisCardPortdetailsRecoveryCount OBJECT-TYPE
    SYNTAX      ConfdString
    MAX-ACCESS  read-only
    STATUS      current
    DESCRIPTION "Link speed of the interface"
    ::= { affirmedChassisCardPortdetailsEntry 10 }

affirmedChassisCardPortcorestatsTable OBJECT-TYPE
    SYNTAX      SEQUENCE OF AffirmedChassisCardPortcorestatsEntry
    MAX-ACCESS  not-accessible
    STATUS      current
    DESCRIPTION ""
    ::= { affirmedChassisMIB 40 }

affirmedChassisCardPortcorestatsEntry OBJECT-TYPE
    SYNTAX      AffirmedChassisCardPortcorestatsEntry
    MAX-ACCESS  not-accessible
    STATUS      current
    DESCRIPTION ""
    INDEX { affirmedChassisId, affirmedChassisCardId, affirmedChassisCardPortcorestatsInterfacename, affirmedChassisCardPortcorestatsCoreindex }
        ::= { affirmedChassisCardPortcorestatsTable 1 }

AffirmedChassisCardPortcorestatsEntry ::=
    SEQUENCE {
        affirmedChassisCardPortcorestatsInterfacename String,
        affirmedChassisCardPortcorestatsCoreindex Unsigned32,
        affirmedChassisCardPortcorestatsCoretype String,
        affirmedChassisCardPortcorestatsLbQpkts ConfdString,
        affirmedChassisCardPortcorestatsLbQdrops ConfdString,
        affirmedChassisCardPortcorestatsLbRnglvl ConfdString,
        affirmedChassisCardPortcorestatsLbRngsz ConfdString,
        affirmedChassisCardPortcorestatsTxQpkts ConfdString,
        affirmedChassisCardPortcorestatsTxQdrops ConfdString,
        affirmedChassisCardPortcorestatsTxRnglvl ConfdString,
        affirmedChassisCardPortcorestatsTxRngsz ConfdString,
        affirmedChassisCardPortcorestatsTxQhmrk ConfdString
    }

affirmedChassisCardPortcorestatsInterfacename OBJECT-TYPE
    SYNTAX      String
    MAX-ACCESS  not-accessible
    STATUS      current
    DESCRIPTION "interface name"
    ::= { affirmedChassisCardPortcorestatsEntry 1 }

affirmedChassisCardPortcorestatsCoreindex OBJECT-TYPE
    SYNTAX      Unsigned32
    MAX-ACCESS  not-accessible
    STATUS      current
    DESCRIPTION "Index of the CPU"
    ::= { affirmedChassisCardPortcorestatsEntry 2 }

affirmedChassisCardPortcorestatsCoretype OBJECT-TYPE
    SYNTAX      String
    MAX-ACCESS  read-only
    STATUS      current
    DESCRIPTION "core type"
    ::= { affirmedChassisCardPortcorestatsEntry 3 }

affirmedChassisCardPortcorestatsLbQpkts OBJECT-TYPE
    SYNTAX      ConfdString
    MAX-ACCESS  read-only
    STATUS      current
    DESCRIPTION "Total Pacekets on the LB queue"
    ::= { affirmedChassisCardPortcorestatsEntry 4 }

affirmedChassisCardPortcorestatsLbQdrops OBJECT-TYPE
    SYNTAX      ConfdString
    MAX-ACCESS  read-only
    STATUS      current
    DESCRIPTION "Drops on the LB queue"
    ::= { affirmedChassisCardPortcorestatsEntry 5 }

affirmedChassisCardPortcorestatsLbRnglvl OBJECT-TYPE
    SYNTAX      ConfdString
    MAX-ACCESS  read-only
    STATUS      current
    DESCRIPTION "Ring Level of the LB queue"
    ::= { affirmedChassisCardPortcorestatsEntry 6 }

affirmedChassisCardPortcorestatsLbRngsz OBJECT-TYPE
    SYNTAX      ConfdString
    MAX-ACCESS  read-only
    STATUS      current
    DESCRIPTION "Ring Size of the LB queue"
    ::= { affirmedChassisCardPortcorestatsEntry 7 }

affirmedChassisCardPortcorestatsTxQpkts OBJECT-TYPE
    SYNTAX      ConfdString
    MAX-ACCESS  read-only
    STATUS      current
    DESCRIPTION "Total Pacekets on the TX queue"
    ::= { affirmedChassisCardPortcorestatsEntry 8 }

affirmedChassisCardPortcorestatsTxQdrops OBJECT-TYPE
    SYNTAX      ConfdString
    MAX-ACCESS  read-only
    STATUS      current
    DESCRIPTION "Drops on the TX queue"
    ::= { affirmedChassisCardPortcorestatsEntry 9 }

affirmedChassisCardPortcorestatsTxRnglvl OBJECT-TYPE
    SYNTAX      ConfdString
    MAX-ACCESS  read-only
    STATUS      current
    DESCRIPTION "Ring Level of the TX queue"
    ::= { affirmedChassisCardPortcorestatsEntry 10 }

affirmedChassisCardPortcorestatsTxRngsz OBJECT-TYPE
    SYNTAX      ConfdString
    MAX-ACCESS  read-only
    STATUS      current
    DESCRIPTION "Ring Size of the TX queue"
    ::= { affirmedChassisCardPortcorestatsEntry 11 }

affirmedChassisCardPortcorestatsTxQhmrk OBJECT-TYPE
    SYNTAX      ConfdString
    MAX-ACCESS  read-only
    STATUS      current
    DESCRIPTION "Hi mark noted on the TX queue"
    ::= { affirmedChassisCardPortcorestatsEntry 12 }

affirmedChassisCardCorestatsTable OBJECT-TYPE
    SYNTAX      SEQUENCE OF AffirmedChassisCardCorestatsEntry
    MAX-ACCESS  not-accessible
    STATUS      current
    DESCRIPTION ""
    ::= { affirmedChassisMIB 41 }

affirmedChassisCardCorestatsEntry OBJECT-TYPE
    SYNTAX      AffirmedChassisCardCorestatsEntry
    MAX-ACCESS  not-accessible
    STATUS      current
    DESCRIPTION ""
    INDEX { affirmedChassisId, affirmedChassisCardId, affirmedChassisCardCorestatsCoreCpu }
        ::= { affirmedChassisCardCorestatsTable 1 }

AffirmedChassisCardCorestatsEntry ::=
    SEQUENCE {
        affirmedChassisCardCorestatsCoreCpu Unsigned32,
        affirmedChassisCardCorestatsCoreType String,
        affirmedChassisCardCorestatsCpuUtil String,
        affirmedChassisCardCorestatsFpcpuUtil String,
        affirmedChassisCardCorestatsDrops String,
        affirmedChassisCardCorestatsRxPkts ConfdString,
        affirmedChassisCardCorestatsTxPkts ConfdString,
        affirmedChassisCardCorestatsHdSendsTolb ConfdString
    }

affirmedChassisCardCorestatsCoreCpu OBJECT-TYPE
    SYNTAX      Unsigned32
    MAX-ACCESS  not-accessible
    STATUS      current
    DESCRIPTION "core number"
    ::= { affirmedChassisCardCorestatsEntry 1 }

affirmedChassisCardCorestatsCoreType OBJECT-TYPE
    SYNTAX      String
    MAX-ACCESS  read-only
    STATUS      current
    DESCRIPTION "core role"
    ::= { affirmedChassisCardCorestatsEntry 2 }

affirmedChassisCardCorestatsCpuUtil OBJECT-TYPE
    SYNTAX      String
    MAX-ACCESS  read-only
    STATUS      current
    DESCRIPTION "core utilization"
    ::= { affirmedChassisCardCorestatsEntry 3 }

affirmedChassisCardCorestatsFpcpuUtil OBJECT-TYPE
    SYNTAX      String
    MAX-ACCESS  read-only
    STATUS      current
    DESCRIPTION "core utilization by the fast-path"
    ::= { affirmedChassisCardCorestatsEntry 4 }

affirmedChassisCardCorestatsDrops OBJECT-TYPE
    SYNTAX      String
    MAX-ACCESS  read-only
    STATUS      current
    DESCRIPTION "Drops on the core due to utilization"
    ::= { affirmedChassisCardCorestatsEntry 5 }

affirmedChassisCardCorestatsRxPkts OBJECT-TYPE
    SYNTAX      ConfdString
    MAX-ACCESS  read-only
    STATUS      current
    DESCRIPTION "Total Packets received"
    ::= { affirmedChassisCardCorestatsEntry 6 }

affirmedChassisCardCorestatsTxPkts OBJECT-TYPE
    SYNTAX      ConfdString
    MAX-ACCESS  read-only
    STATUS      current
    DESCRIPTION "Total Packets transmitted"
    ::= { affirmedChassisCardCorestatsEntry 7 }

affirmedChassisCardCorestatsHdSendsTolb OBJECT-TYPE
    SYNTAX      ConfdString
    MAX-ACCESS  read-only
    STATUS      current
    DESCRIPTION "Packets sent from HD core to LB"
    ::= { affirmedChassisCardCorestatsEntry 8 }

affirmedChassisCardCoreinterfacestatsTable OBJECT-TYPE
    SYNTAX      SEQUENCE OF AffirmedChassisCardCoreinterfacestatsEntry
    MAX-ACCESS  not-accessible
    STATUS      current
    DESCRIPTION ""
    ::= { affirmedChassisMIB 42 }

affirmedChassisCardCoreinterfacestatsEntry OBJECT-TYPE
    SYNTAX      AffirmedChassisCardCoreinterfacestatsEntry
    MAX-ACCESS  not-accessible
    STATUS      current
    DESCRIPTION ""
    INDEX { affirmedChassisId, affirmedChassisCardId, affirmedChassisCardCoreinterfacestatsCoreCpu, affirmedChassisCardCoreinterfacestatsPort }
        ::= { affirmedChassisCardCoreinterfacestatsTable 1 }

AffirmedChassisCardCoreinterfacestatsEntry ::=
    SEQUENCE {
        affirmedChassisCardCoreinterfacestatsCoreCpu Unsigned32,
        affirmedChassisCardCoreinterfacestatsPort Unsigned32,
        affirmedChassisCardCoreinterfacestatsCoreType String,
        affirmedChassisCardCoreinterfacestatsRxPkts ConfdString,
        affirmedChassisCardCoreinterfacestatsRxAvgBurstsz ConfdString,
        affirmedChassisCardCoreinterfacestatsTxPkts ConfdString,
        affirmedChassisCardCoreinterfacestatsTxAvgBurstsz ConfdString,
        affirmedChassisCardCoreinterfacestatsTxDrops ConfdString
    }

affirmedChassisCardCoreinterfacestatsCoreCpu OBJECT-TYPE
    SYNTAX      Unsigned32
    MAX-ACCESS  not-accessible
    STATUS      current
    DESCRIPTION "core cpu number"
    ::= { affirmedChassisCardCoreinterfacestatsEntry 1 }

affirmedChassisCardCoreinterfacestatsPort OBJECT-TYPE
    SYNTAX      Unsigned32
    MAX-ACCESS  not-accessible
    STATUS      current
    DESCRIPTION "port number"
    ::= { affirmedChassisCardCoreinterfacestatsEntry 2 }

affirmedChassisCardCoreinterfacestatsCoreType OBJECT-TYPE
    SYNTAX      String
    MAX-ACCESS  read-only
    STATUS      current
    DESCRIPTION "core role"
    ::= { affirmedChassisCardCoreinterfacestatsEntry 3 }

affirmedChassisCardCoreinterfacestatsRxPkts OBJECT-TYPE
    SYNTAX      ConfdString
    MAX-ACCESS  read-only
    STATUS      current
    DESCRIPTION "Total Packets received"
    ::= { affirmedChassisCardCoreinterfacestatsEntry 4 }

affirmedChassisCardCoreinterfacestatsRxAvgBurstsz OBJECT-TYPE
    SYNTAX      ConfdString
    MAX-ACCESS  read-only
    STATUS      current
    DESCRIPTION "Average RX burst size"
    ::= { affirmedChassisCardCoreinterfacestatsEntry 5 }

affirmedChassisCardCoreinterfacestatsTxPkts OBJECT-TYPE
    SYNTAX      ConfdString
    MAX-ACCESS  read-only
    STATUS      current
    DESCRIPTION "Total Packets TX"
    ::= { affirmedChassisCardCoreinterfacestatsEntry 6 }

affirmedChassisCardCoreinterfacestatsTxAvgBurstsz OBJECT-TYPE
    SYNTAX      ConfdString
    MAX-ACCESS  read-only
    STATUS      current
    DESCRIPTION "Average TX burst size"
    ::= { affirmedChassisCardCoreinterfacestatsEntry 7 }

affirmedChassisCardCoreinterfacestatsTxDrops OBJECT-TYPE
    SYNTAX      ConfdString
    MAX-ACCESS  read-only
    STATUS      current
    DESCRIPTION "Drops on TX"
    ::= { affirmedChassisCardCoreinterfacestatsEntry 8 }

affirmedChassisCardCoreringstatsTable OBJECT-TYPE
    SYNTAX      SEQUENCE OF AffirmedChassisCardCoreringstatsEntry
    MAX-ACCESS  not-accessible
    STATUS      current
    DESCRIPTION ""
    ::= { affirmedChassisMIB 43 }

affirmedChassisCardCoreringstatsEntry OBJECT-TYPE
    SYNTAX      AffirmedChassisCardCoreringstatsEntry
    MAX-ACCESS  not-accessible
    STATUS      current
    DESCRIPTION ""
    INDEX { affirmedChassisId, affirmedChassisCardId, affirmedChassisCardCoreringstatsShdcore, affirmedChassisCardCoreringstatsIocore, affirmedChassisCardCoreringstatsQueueType }
        ::= { affirmedChassisCardCoreringstatsTable 1 }

AffirmedChassisCardCoreringstatsEntry ::=
    SEQUENCE {
        affirmedChassisCardCoreringstatsShdcore Unsigned32,
        affirmedChassisCardCoreringstatsIocore Unsigned32,
        affirmedChassisCardCoreringstatsQueueType String,
        affirmedChassisCardCoreringstatsRxQpkts ConfdString,
        affirmedChassisCardCoreringstatsRxQdrops ConfdString,
        affirmedChassisCardCoreringstatsRxRngsz ConfdString
    }

affirmedChassisCardCoreringstatsShdcore OBJECT-TYPE
    SYNTAX      Unsigned32
    MAX-ACCESS  not-accessible
    STATUS      current
    DESCRIPTION "hd-core number"
    ::= { affirmedChassisCardCoreringstatsEntry 1 }

affirmedChassisCardCoreringstatsIocore OBJECT-TYPE
    SYNTAX      Unsigned32
    MAX-ACCESS  not-accessible
    STATUS      current
    DESCRIPTION "io-core number"
    ::= { affirmedChassisCardCoreringstatsEntry 2 }

affirmedChassisCardCoreringstatsQueueType OBJECT-TYPE
    SYNTAX      String
    MAX-ACCESS  not-accessible
    STATUS      current
    DESCRIPTION "cos ring"
    ::= { affirmedChassisCardCoreringstatsEntry 3 }

affirmedChassisCardCoreringstatsRxQpkts OBJECT-TYPE
    SYNTAX      ConfdString
    MAX-ACCESS  read-only
    STATUS      current
    DESCRIPTION "Total Pacekets on the RX queue"
    ::= { affirmedChassisCardCoreringstatsEntry 4 }

affirmedChassisCardCoreringstatsRxQdrops OBJECT-TYPE
    SYNTAX      ConfdString
    MAX-ACCESS  read-only
    STATUS      current
    DESCRIPTION "Packets dropped on the RX queue"
    ::= { affirmedChassisCardCoreringstatsEntry 5 }

affirmedChassisCardCoreringstatsRxRngsz OBJECT-TYPE
    SYNTAX      ConfdString
    MAX-ACCESS  read-only
    STATUS      current
    DESCRIPTION "Ring Size of the RX queue"
    ::= { affirmedChassisCardCoreringstatsEntry 6 }

affirmedChassisCardMemstatsTable OBJECT-TYPE
    SYNTAX      SEQUENCE OF AffirmedChassisCardMemstatsEntry
    MAX-ACCESS  not-accessible
    STATUS      current
    DESCRIPTION ""
    ::= { affirmedChassisMIB 44 }

affirmedChassisCardMemstatsEntry OBJECT-TYPE
    SYNTAX      AffirmedChassisCardMemstatsEntry
    MAX-ACCESS  not-accessible
    STATUS      current
    DESCRIPTION ""
    INDEX { affirmedChassisId, affirmedChassisCardId, affirmedChassisCardMemstatsSocket }
        ::= { affirmedChassisCardMemstatsTable 1 }

AffirmedChassisCardMemstatsEntry ::=
    SEQUENCE {
        affirmedChassisCardMemstatsSocket Unsigned32,
        affirmedChassisCardMemstatsTotalMemory ConfdString,
        affirmedChassisCardMemstatsMemSegments ConfdString,
        affirmedChassisCardMemstatsMaxMemSegment ConfdString,
        affirmedChassisCardMemstatsHeapBytes ConfdString,
        affirmedChassisCardMemstatsHeapBytesAlloc ConfdString,
        affirmedChassisCardMemstatsNumElementsFree ConfdString,
        affirmedChassisCardMemstatsMaxFreeBlock ConfdString
    }

affirmedChassisCardMemstatsSocket OBJECT-TYPE
    SYNTAX      Unsigned32
    MAX-ACCESS  not-accessible
    STATUS      current
    DESCRIPTION "NUMA NODE"
    ::= { affirmedChassisCardMemstatsEntry 1 }

affirmedChassisCardMemstatsTotalMemory OBJECT-TYPE
    SYNTAX      ConfdString
    MAX-ACCESS  read-only
    STATUS      current
    DESCRIPTION "Total memory taken by the socket"
    ::= { affirmedChassisCardMemstatsEntry 2 }

affirmedChassisCardMemstatsMemSegments OBJECT-TYPE
    SYNTAX      ConfdString
    MAX-ACCESS  read-only
    STATUS      current
    DESCRIPTION "Number of memory segments"
    ::= { affirmedChassisCardMemstatsEntry 3 }

affirmedChassisCardMemstatsMaxMemSegment OBJECT-TYPE
    SYNTAX      ConfdString
    MAX-ACCESS  read-only
    STATUS      current
    DESCRIPTION "Maximum memory segment size"
    ::= { affirmedChassisCardMemstatsEntry 4 }

affirmedChassisCardMemstatsHeapBytes OBJECT-TYPE
    SYNTAX      ConfdString
    MAX-ACCESS  read-only
    STATUS      current
    DESCRIPTION "Total of memory on the heap"
    ::= { affirmedChassisCardMemstatsEntry 5 }

affirmedChassisCardMemstatsHeapBytesAlloc OBJECT-TYPE
    SYNTAX      ConfdString
    MAX-ACCESS  read-only
    STATUS      current
    DESCRIPTION "Allocated memory on the heap"
    ::= { affirmedChassisCardMemstatsEntry 6 }

affirmedChassisCardMemstatsNumElementsFree OBJECT-TYPE
    SYNTAX      ConfdString
    MAX-ACCESS  read-only
    STATUS      current
    DESCRIPTION "Number of free elements"
    ::= { affirmedChassisCardMemstatsEntry 7 }

affirmedChassisCardMemstatsMaxFreeBlock OBJECT-TYPE
    SYNTAX      ConfdString
    MAX-ACCESS  read-only
    STATUS      current
    DESCRIPTION "Largest Free Block"
    ::= { affirmedChassisCardMemstatsEntry 8 }

affirmedChassisCardDataplanebufferstatsTable OBJECT-TYPE
    SYNTAX      SEQUENCE OF AffirmedChassisCardDataplanebufferstatsEntry
    MAX-ACCESS  not-accessible
    STATUS      current
    DESCRIPTION ""
    ::= { affirmedChassisMIB 45 }

affirmedChassisCardDataplanebufferstatsEntry OBJECT-TYPE
    SYNTAX      AffirmedChassisCardDataplanebufferstatsEntry
    MAX-ACCESS  not-accessible
    STATUS      current
    DESCRIPTION ""
    INDEX { affirmedChassisId, affirmedChassisCardId, affirmedChassisCardDataplanebufferstatsCoreCpu }
        ::= { affirmedChassisCardDataplanebufferstatsTable 1 }

AffirmedChassisCardDataplanebufferstatsEntry ::=
    SEQUENCE {
        affirmedChassisCardDataplanebufferstatsCoreCpu Unsigned32,
        affirmedChassisCardDataplanebufferstatsRxdropsBesteffort ConfdString,
        affirmedChassisCardDataplanebufferstatsRxdropsBronze ConfdString,
        affirmedChassisCardDataplanebufferstatsRxdropsSilver ConfdString,
        affirmedChassisCardDataplanebufferstatsRxdropsGold ConfdString,
        affirmedChassisCardDataplanebufferstatsMbufsFree ConfdString,
        affirmedChassisCardDataplanebufferstatsMbufsWarningLevel ConfdString,
        affirmedChassisCardDataplanebufferstatsMbufsCriticalLevel ConfdString
    }

affirmedChassisCardDataplanebufferstatsCoreCpu OBJECT-TYPE
    SYNTAX      Unsigned32
    MAX-ACCESS  not-accessible
    STATUS      current
    DESCRIPTION "core id"
    ::= { affirmedChassisCardDataplanebufferstatsEntry 1 }

affirmedChassisCardDataplanebufferstatsRxdropsBesteffort OBJECT-TYPE
    SYNTAX      ConfdString
    MAX-ACCESS  read-only
    STATUS      current
    DESCRIPTION "RX drops due to best effort class"
    ::= { affirmedChassisCardDataplanebufferstatsEntry 2 }

affirmedChassisCardDataplanebufferstatsRxdropsBronze OBJECT-TYPE
    SYNTAX      ConfdString
    MAX-ACCESS  read-only
    STATUS      current
    DESCRIPTION "RX drops due to bronze class"
    ::= { affirmedChassisCardDataplanebufferstatsEntry 3 }

affirmedChassisCardDataplanebufferstatsRxdropsSilver OBJECT-TYPE
    SYNTAX      ConfdString
    MAX-ACCESS  read-only
    STATUS      current
    DESCRIPTION "RX drops due to silver class"
    ::= { affirmedChassisCardDataplanebufferstatsEntry 4 }

affirmedChassisCardDataplanebufferstatsRxdropsGold OBJECT-TYPE
    SYNTAX      ConfdString
    MAX-ACCESS  read-only
    STATUS      current
    DESCRIPTION "RX drops due to gold class"
    ::= { affirmedChassisCardDataplanebufferstatsEntry 5 }

affirmedChassisCardDataplanebufferstatsMbufsFree OBJECT-TYPE
    SYNTAX      ConfdString
    MAX-ACCESS  read-only
    STATUS      current
    DESCRIPTION "Unallocated MBUFs"
    ::= { affirmedChassisCardDataplanebufferstatsEntry 6 }

affirmedChassisCardDataplanebufferstatsMbufsWarningLevel OBJECT-TYPE
    SYNTAX      ConfdString
    MAX-ACCESS  read-only
    STATUS      current
    DESCRIPTION "Warning threshold for unallocated MBUFs"
    ::= { affirmedChassisCardDataplanebufferstatsEntry 7 }

affirmedChassisCardDataplanebufferstatsMbufsCriticalLevel OBJECT-TYPE
    SYNTAX      ConfdString
    MAX-ACCESS  read-only
    STATUS      current
    DESCRIPTION "Critical threshold for unallocated MBUFs"
    ::= { affirmedChassisCardDataplanebufferstatsEntry 8 }

affirmedChassisSummaryTable OBJECT-TYPE
    SYNTAX      SEQUENCE OF AffirmedChassisSummaryEntry
    MAX-ACCESS  not-accessible
    STATUS      current
    DESCRIPTION ""
    ::= { affirmedChassisMIB 15 }

affirmedChassisSummaryEntry OBJECT-TYPE
    SYNTAX      AffirmedChassisSummaryEntry
    MAX-ACCESS  not-accessible
    STATUS      current
    DESCRIPTION ""
    INDEX { affirmedChassisId, affirmedChassisSummarySlotNumber, affirmedChassisSummaryCpuNumber }
        ::= { affirmedChassisSummaryTable 1 }

AffirmedChassisSummaryEntry ::=
    SEQUENCE {
        affirmedChassisSummarySlotNumber Integer32,
        affirmedChassisSummaryCpuNumber Integer32,
        affirmedChassisSummarySlotType INTEGER,
        affirmedChassisSummarySlotModel String,
        affirmedChassisSummarySlotAdminState INTEGER,
        affirmedChassisSummarySlotHAState INTEGER,
        affirmedChassisSummaryCpuState INTEGER,
        affirmedChassisSummaryCpuuptime String,
        affirmedChassisSummaryRelease String,
        affirmedChassisSummaryNodePersonality String
    }

affirmedChassisSummarySlotNumber OBJECT-TYPE
    SYNTAX      Integer32
    MAX-ACCESS  not-accessible
    STATUS      current
    DESCRIPTION ""
    ::= { affirmedChassisSummaryEntry 1 }

affirmedChassisSummaryCpuNumber OBJECT-TYPE
    SYNTAX      Integer32
    MAX-ACCESS  not-accessible
    STATUS      current
    DESCRIPTION ""
    ::= { affirmedChassisSummaryEntry 2 }

affirmedChassisSummarySlotType OBJECT-TYPE
    SYNTAX      INTEGER {empty(0),csm(1),ssm(2),mcm(3),v-csm(9),v-ssm(10),v-mcm(11),v-uam(12)}
    MAX-ACCESS  read-only
    STATUS      current
    DESCRIPTION ""
    ::= { affirmedChassisSummaryEntry 3 }

affirmedChassisSummarySlotModel OBJECT-TYPE
    SYNTAX      String
    MAX-ACCESS  read-only
    STATUS      current
    DESCRIPTION ""
    ::= { affirmedChassisSummaryEntry 4 }

affirmedChassisSummarySlotAdminState OBJECT-TYPE
    SYNTAX      INTEGER {disabled(0),enabled(1),maintenance(2)}
    MAX-ACCESS  read-only
    STATUS      current
    DESCRIPTION ""
    ::= { affirmedChassisSummaryEntry 5 }

affirmedChassisSummarySlotHAState OBJECT-TYPE
    SYNTAX      INTEGER {active(1),standby(2),quiesced(3),quiescing(4),none(5),master(6),slave(7),primary(8),secondary(9)}
    MAX-ACCESS  read-only
    STATUS      current
    DESCRIPTION ""
    ::= { affirmedChassisSummaryEntry 6 }

affirmedChassisSummaryCpuState OBJECT-TYPE
    SYNTAX      INTEGER {up(0),down(1),maint(2),faulted(3),dryup(4),unsupported(5),alarmed(6)}
    MAX-ACCESS  read-only
    STATUS      current
    DESCRIPTION ""
    ::= { affirmedChassisSummaryEntry 7 }

affirmedChassisSummaryCpuuptime OBJECT-TYPE
    SYNTAX      String
    MAX-ACCESS  read-only
    STATUS      current
    DESCRIPTION ""
    ::= { affirmedChassisSummaryEntry 8 }

affirmedChassisSummaryRelease OBJECT-TYPE
    SYNTAX      String
    MAX-ACCESS  read-only
    STATUS      current
    DESCRIPTION ""
    ::= { affirmedChassisSummaryEntry 9 }

affirmedChassisSummaryNodePersonality OBJECT-TYPE
    SYNTAX      String
    MAX-ACCESS  read-only
    STATUS      current
    DESCRIPTION ""
    ::= { affirmedChassisSummaryEntry 10 }

affirmedChassisStatsTable OBJECT-TYPE
    SYNTAX      SEQUENCE OF AffirmedChassisStatsEntry
    MAX-ACCESS  not-accessible
    STATUS      current
    DESCRIPTION ""
    ::= { affirmedChassisMIB 16 }

affirmedChassisStatsEntry OBJECT-TYPE
    SYNTAX      AffirmedChassisStatsEntry
    MAX-ACCESS  not-accessible
    STATUS      current
    DESCRIPTION ""
    INDEX { affirmedChassisId, affirmedChassisStatsSlot, affirmedChassisStatsCpuNum }
        ::= { affirmedChassisStatsTable 1 }

AffirmedChassisStatsEntry ::=
    SEQUENCE {
        affirmedChassisStatsSlot Unsigned32,
        affirmedChassisStatsCpuNum Unsigned32,
        affirmedChassisStatsCpuutil String,
        affirmedChassisStatsMemutil String,
        affirmedChassisStatsPidtotal Unsigned32,
        affirmedChassisStatsIsolcpuutilnorm String,
        affirmedChassisStatsGeneralcpuutil String,
        affirmedChassisStatsIsolcpuutilnormmax String,
        affirmedChassisStatsApplicationload String,
        affirmedChassisStatsOverallload String
    }

affirmedChassisStatsSlot OBJECT-TYPE
    SYNTAX      Unsigned32
    MAX-ACCESS  not-accessible
    STATUS      current
    DESCRIPTION ""
    ::= { affirmedChassisStatsEntry 1 }

affirmedChassisStatsCpuNum OBJECT-TYPE
    SYNTAX      Unsigned32
    MAX-ACCESS  not-accessible
    STATUS      current
    DESCRIPTION ""
    ::= { affirmedChassisStatsEntry 2 }

affirmedChassisStatsCpuutil OBJECT-TYPE
    SYNTAX      String
    MAX-ACCESS  read-only
    STATUS      current
    DESCRIPTION "CPU Utilization"
    ::= { affirmedChassisStatsEntry 3 }

affirmedChassisStatsMemutil OBJECT-TYPE
    SYNTAX      String
    MAX-ACCESS  read-only
    STATUS      current
    DESCRIPTION "Memory Utilization"
    ::= { affirmedChassisStatsEntry 4 }

affirmedChassisStatsPidtotal OBJECT-TYPE
    SYNTAX      Unsigned32
    MAX-ACCESS  read-only
    STATUS      current
    DESCRIPTION "Process Count"
    ::= { affirmedChassisStatsEntry 5 }

affirmedChassisStatsIsolcpuutilnorm OBJECT-TYPE
    SYNTAX      String
    MAX-ACCESS  read-only
    STATUS      current
    DESCRIPTION "Isolated CPU Utilization Normalized"
    ::= { affirmedChassisStatsEntry 6 }

affirmedChassisStatsGeneralcpuutil OBJECT-TYPE
    SYNTAX      String
    MAX-ACCESS  read-only
    STATUS      current
    DESCRIPTION "General (non-isolated) CPU Utilization"
    ::= { affirmedChassisStatsEntry 7 }

affirmedChassisStatsIsolcpuutilnormmax OBJECT-TYPE
    SYNTAX      String
    MAX-ACCESS  read-only
    STATUS      current
    DESCRIPTION "Isolated CPU Utilization Normalized Maximum"
    ::= { affirmedChassisStatsEntry 8 }

affirmedChassisStatsApplicationload OBJECT-TYPE
    SYNTAX      String
    MAX-ACCESS  read-only
    STATUS      current
    DESCRIPTION "Application Load"
    ::= { affirmedChassisStatsEntry 9 }

affirmedChassisStatsOverallload OBJECT-TYPE
    SYNTAX      String
    MAX-ACCESS  read-only
    STATUS      current
    DESCRIPTION "Overall Load"
    ::= { affirmedChassisStatsEntry 10 }

affirmedChassisModuleTable OBJECT-TYPE
    SYNTAX      SEQUENCE OF AffirmedChassisModuleEntry
    MAX-ACCESS  not-accessible
    STATUS      current
    DESCRIPTION ""
    ::= { affirmedChassisMIB 17 }

affirmedChassisModuleEntry OBJECT-TYPE
    SYNTAX      AffirmedChassisModuleEntry
    MAX-ACCESS  not-accessible
    STATUS      current
    DESCRIPTION ""
    INDEX { affirmedChassisId, affirmedChassisModuleSlot, affirmedChassisModuleResource }
        ::= { affirmedChassisModuleTable 1 }

AffirmedChassisModuleEntry ::=
    SEQUENCE {
        affirmedChassisModuleSlot Unsigned32,
        affirmedChassisModuleResource Unsigned32,
        affirmedChassisModuleModuleType String,
        affirmedChassisModuleModuleFunction String,
        affirmedChassisModuleModuleStatus String,
        affirmedChassisModuleSerialNumber String,
        affirmedChassisModulePartNumber String,
        affirmedChassisModuleHardwareRev String,
        affirmedChassisModuleFirmwareRev String
    }

affirmedChassisModuleSlot OBJECT-TYPE
    SYNTAX      Unsigned32
    MAX-ACCESS  not-accessible
    STATUS      current
    DESCRIPTION ""
    ::= { affirmedChassisModuleEntry 1 }

affirmedChassisModuleResource OBJECT-TYPE
    SYNTAX      Unsigned32
    MAX-ACCESS  not-accessible
    STATUS      current
    DESCRIPTION ""
    ::= { affirmedChassisModuleEntry 2 }

affirmedChassisModuleModuleType OBJECT-TYPE
    SYNTAX      String
    MAX-ACCESS  read-only
    STATUS      current
    DESCRIPTION ""
    ::= { affirmedChassisModuleEntry 3 }

affirmedChassisModuleModuleFunction OBJECT-TYPE
    SYNTAX      String
    MAX-ACCESS  read-only
    STATUS      current
    DESCRIPTION ""
    ::= { affirmedChassisModuleEntry 4 }

affirmedChassisModuleModuleStatus OBJECT-TYPE
    SYNTAX      String
    MAX-ACCESS  read-only
    STATUS      current
    DESCRIPTION ""
    ::= { affirmedChassisModuleEntry 5 }

affirmedChassisModuleSerialNumber OBJECT-TYPE
    SYNTAX      String
    MAX-ACCESS  read-only
    STATUS      current
    DESCRIPTION ""
    ::= { affirmedChassisModuleEntry 6 }

affirmedChassisModulePartNumber OBJECT-TYPE
    SYNTAX      String
    MAX-ACCESS  read-only
    STATUS      current
    DESCRIPTION ""
    ::= { affirmedChassisModuleEntry 7 }

affirmedChassisModuleHardwareRev OBJECT-TYPE
    SYNTAX      String
    MAX-ACCESS  read-only
    STATUS      current
    DESCRIPTION ""
    ::= { affirmedChassisModuleEntry 8 }

affirmedChassisModuleFirmwareRev OBJECT-TYPE
    SYNTAX      String
    MAX-ACCESS  read-only
    STATUS      current
    DESCRIPTION ""
    ::= { affirmedChassisModuleEntry 9 }

affirmedChassisSensorTable OBJECT-TYPE
    SYNTAX      SEQUENCE OF AffirmedChassisSensorEntry
    MAX-ACCESS  not-accessible
    STATUS      current
    DESCRIPTION ""
    ::= { affirmedChassisMIB 18 }

affirmedChassisSensorEntry OBJECT-TYPE
    SYNTAX      AffirmedChassisSensorEntry
    MAX-ACCESS  not-accessible
    STATUS      current
    DESCRIPTION ""
    INDEX { affirmedChassisId, affirmedChassisSensorResource, affirmedChassisSensorSensornum }
        ::= { affirmedChassisSensorTable 1 }

AffirmedChassisSensorEntry ::=
    SEQUENCE {
        affirmedChassisSensorResource Unsigned32,
        affirmedChassisSensorSensornum Unsigned32,
        affirmedChassisSensorSlot Unsigned32,
        affirmedChassisSensorModuletype String,
        affirmedChassisSensorModulefunction String,
        affirmedChassisSensorSensordata String,
        affirmedChassisSensorSensorstate String,
        affirmedChassisSensorSensordesc String
    }

affirmedChassisSensorResource OBJECT-TYPE
    SYNTAX      Unsigned32
    MAX-ACCESS  not-accessible
    STATUS      current
    DESCRIPTION ""
    ::= { affirmedChassisSensorEntry 1 }

affirmedChassisSensorSensornum OBJECT-TYPE
    SYNTAX      Unsigned32
    MAX-ACCESS  not-accessible
    STATUS      current
    DESCRIPTION ""
    ::= { affirmedChassisSensorEntry 2 }

affirmedChassisSensorSlot OBJECT-TYPE
    SYNTAX      Unsigned32
    MAX-ACCESS  read-only
    STATUS      current
    DESCRIPTION ""
    ::= { affirmedChassisSensorEntry 3 }

affirmedChassisSensorModuletype OBJECT-TYPE
    SYNTAX      String
    MAX-ACCESS  read-only
    STATUS      current
    DESCRIPTION ""
    ::= { affirmedChassisSensorEntry 4 }

affirmedChassisSensorModulefunction OBJECT-TYPE
    SYNTAX      String
    MAX-ACCESS  read-only
    STATUS      current
    DESCRIPTION ""
    ::= { affirmedChassisSensorEntry 5 }

affirmedChassisSensorSensordata OBJECT-TYPE
    SYNTAX      String
    MAX-ACCESS  read-only
    STATUS      current
    DESCRIPTION "Display the sensor data"
    ::= { affirmedChassisSensorEntry 6 }

affirmedChassisSensorSensorstate OBJECT-TYPE
    SYNTAX      String
    MAX-ACCESS  read-only
    STATUS      current
    DESCRIPTION "Display the sensor state"
    ::= { affirmedChassisSensorEntry 7 }

affirmedChassisSensorSensordesc OBJECT-TYPE
    SYNTAX      String
    MAX-ACCESS  read-only
    STATUS      current
    DESCRIPTION "Display the sensor type"
    ::= { affirmedChassisSensorEntry 8 }

affirmedChassisAlarmTable OBJECT-TYPE
    SYNTAX      SEQUENCE OF AffirmedChassisAlarmEntry
    MAX-ACCESS  not-accessible
    STATUS      current
    DESCRIPTION ""
    ::= { affirmedChassisMIB 19 }

affirmedChassisAlarmEntry OBJECT-TYPE
    SYNTAX      AffirmedChassisAlarmEntry
    MAX-ACCESS  not-accessible
    STATUS      current
    DESCRIPTION ""
    INDEX { affirmedChassisId, affirmedChassisAlarmResource, affirmedChassisAlarmSensor }
        ::= { affirmedChassisAlarmTable 1 }

AffirmedChassisAlarmEntry ::=
    SEQUENCE {
        affirmedChassisAlarmResource Unsigned32,
        affirmedChassisAlarmSensor Unsigned32,
        affirmedChassisAlarmSlot Unsigned32,
        affirmedChassisAlarmAlarmState String
    }

affirmedChassisAlarmResource OBJECT-TYPE
    SYNTAX      Unsigned32
    MAX-ACCESS  not-accessible
    STATUS      current
    DESCRIPTION ""
    ::= { affirmedChassisAlarmEntry 1 }

affirmedChassisAlarmSensor OBJECT-TYPE
    SYNTAX      Unsigned32
    MAX-ACCESS  not-accessible
    STATUS      current
    DESCRIPTION "Display the sensor "
    ::= { affirmedChassisAlarmEntry 2 }

affirmedChassisAlarmSlot OBJECT-TYPE
    SYNTAX      Unsigned32
    MAX-ACCESS  read-only
    STATUS      current
    DESCRIPTION ""
    ::= { affirmedChassisAlarmEntry 3 }

affirmedChassisAlarmAlarmState OBJECT-TYPE
    SYNTAX      String
    MAX-ACCESS  read-only
    STATUS      current
    DESCRIPTION "Display the alarm State"
    ::= { affirmedChassisAlarmEntry 4 }

affirmedChassisTnd-totalTable OBJECT-TYPE
    SYNTAX      SEQUENCE OF AffirmedChassisTnd-totalEntry
    MAX-ACCESS  not-accessible
    STATUS      current
    DESCRIPTION ""
    ::= { affirmedChassisMIB 24 }

affirmedChassisTnd-totalEntry OBJECT-TYPE
    SYNTAX      AffirmedChassisTnd-totalEntry
    MAX-ACCESS  not-accessible
    STATUS      current
    DESCRIPTION ""
    INDEX { affirmedChassisId, affirmedChassisTnd-totalNode, affirmedChassisTnd-totalCpuNum }
        ::= { affirmedChassisTnd-totalTable 1 }

AffirmedChassisTnd-totalEntry ::=
    SEQUENCE {
        affirmedChassisTnd-totalNode Unsigned32,
        affirmedChassisTnd-totalCpuNum Unsigned32,
        affirmedChassisTnd-totalRxEthIomToIom ConfdString,
        affirmedChassisTnd-totalRxEthIomToIomMhopBfd ConfdString,
        affirmedChassisTnd-totalRxEthWfmToGifm ConfdString,
        affirmedChassisTnd-totalRxEthGifmToWfm ConfdString,
        affirmedChassisTnd-totalRxEthGnfmToWfm ConfdString,
        affirmedChassisTnd-totalRxEthWfmToGnfm ConfdString,
        affirmedChassisTnd-totalRxAnData ConfdString,
        affirmedChassisTnd-totalRxAnLinux ConfdString,
        affirmedChassisTnd-totalRxSpmSecmRsaPkts ConfdString,
        affirmedChassisTnd-totalRxSecmSecmPkts ConfdString,
        affirmedChassisTnd-totalRxSecmIomPkts ConfdString,
        affirmedChassisTnd-totalTxSecmSpmRsa ConfdString,
        affirmedChassisTnd-totalTxWfdhcpGwPkts ConfdString,
        affirmedChassisTnd-totalRxWfdhcpGwPkts ConfdString,
        affirmedChassisTnd-totalRxWfmccPkt ConfdString,
        affirmedChassisTnd-totalTxFabric1Pkts ConfdString,
        affirmedChassisTnd-totalTxFabric2Pkts ConfdString,
        affirmedChassisTnd-totalRxIpPkt ConfdString,
        affirmedChassisTnd-totalTxIpPkt ConfdString,
        affirmedChassisTnd-totalLinked ConfdString,
        affirmedChassisTnd-totalFragmented ConfdString,
        affirmedChassisTnd-totalReassembled ConfdString,
        affirmedChassisTnd-totalDescriptorErrored ConfdString,
        affirmedChassisTnd-totalTxTndKncPktsOk ConfdString,
        affirmedChassisTnd-totalTxTndAndataPktsOk ConfdString,
        affirmedChassisTnd-totalTxIomWfAccessPktsOk ConfdString,
        affirmedChassisTnd-totalTxWfIomAccessPktsOk ConfdString,
        affirmedChassisTnd-totalTxIomWfCorePktsOk ConfdString,
        affirmedChassisTnd-totalTxWfIomCorePktsOk ConfdString,
        affirmedChassisTnd-totalTxIomIomPktsOk ConfdString,
        affirmedChassisTnd-totalTxIomIomMhopBfdPktsOk ConfdString,
        affirmedChassisTnd-totalTxSecmSpmPktsOk ConfdString,
        affirmedChassisTnd-totalTxSecmSecmPktsOk ConfdString,
        affirmedChassisTnd-totalTxSecmIomPktsOk ConfdString,
        affirmedChassisTnd-totalTxErr ConfdString,
        affirmedChassisTnd-totalRxErr ConfdString,
        affirmedChassisTnd-totalRxErr1 ConfdString,
        affirmedChassisTnd-totalRxErr2 ConfdString,
        affirmedChassisTnd-totalRxDisc ConfdString,
        affirmedChassisTnd-totalRxDisc1 ConfdString,
        affirmedChassisTnd-totalRxDisc2 ConfdString,
        affirmedChassisTnd-totalRxGnpErr ConfdString,
        affirmedChassisTnd-totalRxGnpDisc ConfdString,
        affirmedChassisTnd-totalTxWfdhcpGwPktsErr ConfdString,
        affirmedChassisTnd-totalRxWfdhcpGwPktsErr ConfdString,
        affirmedChassisTnd-totalRxWfmccUnknownIntf ConfdString,
        affirmedChassisTnd-totalRxWfmccCfgMismatch ConfdString,
        affirmedChassisTnd-totalRxWfmccPktParseErr ConfdString,
        affirmedChassisTnd-totalRxWfmccSessionidGetErr ConfdString,
        affirmedChassisTnd-totalFragmentErr ConfdString,
        affirmedChassisTnd-totalTxTndKncPktsErr ConfdString,
        affirmedChassisTnd-totalTxTndAndataPktsErr ConfdString,
        affirmedChassisTnd-totalTxIomWfAccessPktsErr ConfdString,
        affirmedChassisTnd-totalTxWfIomAccessPktsErr ConfdString,
        affirmedChassisTnd-totalTxIomWfCorePktsErr ConfdString,
        affirmedChassisTnd-totalTxWfIomCorePktsErr ConfdString,
        affirmedChassisTnd-totalTxIomIomPktsErr ConfdString,
        affirmedChassisTnd-totalTxIomIomMhopBfdPktsErr ConfdString,
        affirmedChassisTnd-totalTxSecmSpmPktsErr ConfdString,
        affirmedChassisTnd-totalTxSecmSecmPktsErr ConfdString,
        affirmedChassisTnd-totalTxSecmIomPktsErr ConfdString,
        affirmedChassisTnd-totalSynNoMetadataPkts ConfdString
    }

affirmedChassisTnd-totalNode OBJECT-TYPE
    SYNTAX      Unsigned32
    MAX-ACCESS  not-accessible
    STATUS      current
    DESCRIPTION "node number"
    ::= { affirmedChassisTnd-totalEntry 1 }

affirmedChassisTnd-totalCpuNum OBJECT-TYPE
    SYNTAX      Unsigned32
    MAX-ACCESS  not-accessible
    STATUS      current
    DESCRIPTION "cpu number"
    ::= { affirmedChassisTnd-totalEntry 2 }

affirmedChassisTnd-totalRxEthIomToIom OBJECT-TYPE
    SYNTAX      ConfdString
    MAX-ACCESS  read-only
    STATUS      current
    DESCRIPTION "Number of IOM to IOM packets received"
    ::= { affirmedChassisTnd-totalEntry 3 }

affirmedChassisTnd-totalRxEthIomToIomMhopBfd OBJECT-TYPE
    SYNTAX      ConfdString
    MAX-ACCESS  read-only
    STATUS      current
    DESCRIPTION "Number of IOM to IOM multihop BFD packets received"
    ::= { affirmedChassisTnd-totalEntry 4 }

affirmedChassisTnd-totalRxEthWfmToGifm OBJECT-TYPE
    SYNTAX      ConfdString
    MAX-ACCESS  read-only
    STATUS      current
    DESCRIPTION "Number of WorkFlow to IOM Upstream (Gi) packets received"
    ::= { affirmedChassisTnd-totalEntry 5 }

affirmedChassisTnd-totalRxEthGifmToWfm OBJECT-TYPE
    SYNTAX      ConfdString
    MAX-ACCESS  read-only
    STATUS      current
    DESCRIPTION "Number of (Gi) IOM to WorkFlow Downstream packets received"
    ::= { affirmedChassisTnd-totalEntry 6 }

affirmedChassisTnd-totalRxEthGnfmToWfm OBJECT-TYPE
    SYNTAX      ConfdString
    MAX-ACCESS  read-only
    STATUS      current
    DESCRIPTION "Number of (Gn) IOM to WorkFlow Upstream packets received"
    ::= { affirmedChassisTnd-totalEntry 7 }

affirmedChassisTnd-totalRxEthWfmToGnfm OBJECT-TYPE
    SYNTAX      ConfdString
    MAX-ACCESS  read-only
    STATUS      current
    DESCRIPTION "Number of WorkFlow to IOM (Gn) Downstream packets received"
    ::= { affirmedChassisTnd-totalEntry 8 }

affirmedChassisTnd-totalRxAnData OBJECT-TYPE
    SYNTAX      ConfdString
    MAX-ACCESS  read-only
    STATUS      current
    DESCRIPTION "Number of CSM to SSM tnd application data packets received"
    ::= { affirmedChassisTnd-totalEntry 9 }

affirmedChassisTnd-totalRxAnLinux OBJECT-TYPE
    SYNTAX      ConfdString
    MAX-ACCESS  read-only
    STATUS      current
    DESCRIPTION "Number of CSM to SSM gnp and egress kernel packets received"
    ::= { affirmedChassisTnd-totalEntry 10 }

affirmedChassisTnd-totalRxSpmSecmRsaPkts OBJECT-TYPE
    SYNTAX      ConfdString
    MAX-ACCESS  read-only
    STATUS      current
    DESCRIPTION "Number of SPM to SECM RSA helper requests"
    ::= { affirmedChassisTnd-totalEntry 11 }

affirmedChassisTnd-totalRxSecmSecmPkts OBJECT-TYPE
    SYNTAX      ConfdString
    MAX-ACCESS  read-only
    STATUS      current
    DESCRIPTION "Number of SECM to SECM packets received"
    ::= { affirmedChassisTnd-totalEntry 12 }

affirmedChassisTnd-totalRxSecmIomPkts OBJECT-TYPE
    SYNTAX      ConfdString
    MAX-ACCESS  read-only
    STATUS      current
    DESCRIPTION "Number of SECM to IOM packets received"
    ::= { affirmedChassisTnd-totalEntry 13 }

affirmedChassisTnd-totalTxSecmSpmRsa OBJECT-TYPE
    SYNTAX      ConfdString
    MAX-ACCESS  read-only
    STATUS      current
    DESCRIPTION "Number of SECM to SPM RSA helper responses"
    ::= { affirmedChassisTnd-totalEntry 14 }

affirmedChassisTnd-totalTxWfdhcpGwPkts OBJECT-TYPE
    SYNTAX      ConfdString
    MAX-ACCESS  read-only
    STATUS      current
    DESCRIPTION "Number of WorkFlow DHCP packets sent to gateway"
    ::= { affirmedChassisTnd-totalEntry 15 }

affirmedChassisTnd-totalRxWfdhcpGwPkts OBJECT-TYPE
    SYNTAX      ConfdString
    MAX-ACCESS  read-only
    STATUS      current
    DESCRIPTION "Number of WorkFlow DHCP packets received from gateway"
    ::= { affirmedChassisTnd-totalEntry 16 }

affirmedChassisTnd-totalRxWfmccPkt OBJECT-TYPE
    SYNTAX      ConfdString
    MAX-ACCESS  read-only
    STATUS      current
    DESCRIPTION "Number of IOM to Workflow MCC subscriber-unaware packets received"
    ::= { affirmedChassisTnd-totalEntry 17 }

affirmedChassisTnd-totalTxFabric1Pkts OBJECT-TYPE
    SYNTAX      ConfdString
    MAX-ACCESS  read-only
    STATUS      current
    DESCRIPTION "ATCA: Number of transmits on fabric A"
    ::= { affirmedChassisTnd-totalEntry 18 }

affirmedChassisTnd-totalTxFabric2Pkts OBJECT-TYPE
    SYNTAX      ConfdString
    MAX-ACCESS  read-only
    STATUS      current
    DESCRIPTION "ATCA: Number of transmits on fabric B"
    ::= { affirmedChassisTnd-totalEntry 19 }

affirmedChassisTnd-totalRxIpPkt OBJECT-TYPE
    SYNTAX      ConfdString
    MAX-ACCESS  read-only
    STATUS      current
    DESCRIPTION "Number of standard ethernet packets received"
    ::= { affirmedChassisTnd-totalEntry 20 }

affirmedChassisTnd-totalTxIpPkt OBJECT-TYPE
    SYNTAX      ConfdString
    MAX-ACCESS  read-only
    STATUS      current
    DESCRIPTION "Number of standard ethernet transmits"
    ::= { affirmedChassisTnd-totalEntry 21 }

affirmedChassisTnd-totalLinked OBJECT-TYPE
    SYNTAX      ConfdString
    MAX-ACCESS  read-only
    STATUS      current
    DESCRIPTION "Number of transmit failures because descriptors are linked"
    ::= { affirmedChassisTnd-totalEntry 22 }

affirmedChassisTnd-totalFragmented OBJECT-TYPE
    SYNTAX      ConfdString
    MAX-ACCESS  read-only
    STATUS      current
    DESCRIPTION "Number of transmit packets that were fragmented"
    ::= { affirmedChassisTnd-totalEntry 23 }

affirmedChassisTnd-totalReassembled OBJECT-TYPE
    SYNTAX      ConfdString
    MAX-ACCESS  read-only
    STATUS      current
    DESCRIPTION "Number of received packets that were reassembled"
    ::= { affirmedChassisTnd-totalEntry 24 }

affirmedChassisTnd-totalDescriptorErrored OBJECT-TYPE
    SYNTAX      ConfdString
    MAX-ACCESS  read-only
    STATUS      current
    DESCRIPTION "Number of transmit failures because of descriptors errors"
    ::= { affirmedChassisTnd-totalEntry 25 }

affirmedChassisTnd-totalTxTndKncPktsOk OBJECT-TYPE
    SYNTAX      ConfdString
    MAX-ACCESS  read-only
    STATUS      current
    DESCRIPTION "Number of successful KNC (GNP) transmits"
    ::= { affirmedChassisTnd-totalEntry 26 }

affirmedChassisTnd-totalTxTndAndataPktsOk OBJECT-TYPE
    SYNTAX      ConfdString
    MAX-ACCESS  read-only
    STATUS      current
    DESCRIPTION "Number of successful SSM to CSM tnd application transmits"
    ::= { affirmedChassisTnd-totalEntry 27 }

affirmedChassisTnd-totalTxIomWfAccessPktsOk OBJECT-TYPE
    SYNTAX      ConfdString
    MAX-ACCESS  read-only
    STATUS      current
    DESCRIPTION "Number of successful IOM to Workflow upstream transmits"
    ::= { affirmedChassisTnd-totalEntry 28 }

affirmedChassisTnd-totalTxWfIomAccessPktsOk OBJECT-TYPE
    SYNTAX      ConfdString
    MAX-ACCESS  read-only
    STATUS      current
    DESCRIPTION "Number of successful Workflow to IOM downstream transmits"
    ::= { affirmedChassisTnd-totalEntry 29 }

affirmedChassisTnd-totalTxIomWfCorePktsOk OBJECT-TYPE
    SYNTAX      ConfdString
    MAX-ACCESS  read-only
    STATUS      current
    DESCRIPTION "Number of successful IOM to Workflow downstream transmits"
    ::= { affirmedChassisTnd-totalEntry 30 }

affirmedChassisTnd-totalTxWfIomCorePktsOk OBJECT-TYPE
    SYNTAX      ConfdString
    MAX-ACCESS  read-only
    STATUS      current
    DESCRIPTION "Number of successful Workflow to IOM upstream transmits"
    ::= { affirmedChassisTnd-totalEntry 31 }

affirmedChassisTnd-totalTxIomIomPktsOk OBJECT-TYPE
    SYNTAX      ConfdString
    MAX-ACCESS  read-only
    STATUS      current
    DESCRIPTION "Number of successful IOM to IOM upstream transmits"
    ::= { affirmedChassisTnd-totalEntry 32 }

affirmedChassisTnd-totalTxIomIomMhopBfdPktsOk OBJECT-TYPE
    SYNTAX      ConfdString
    MAX-ACCESS  read-only
    STATUS      current
    DESCRIPTION "Number of successful IOM to IOM multihop BFD transmits"
    ::= { affirmedChassisTnd-totalEntry 33 }

affirmedChassisTnd-totalTxSecmSpmPktsOk OBJECT-TYPE
    SYNTAX      ConfdString
    MAX-ACCESS  read-only
    STATUS      current
    DESCRIPTION "Number of successful SECM to SPM transmits"
    ::= { affirmedChassisTnd-totalEntry 34 }

affirmedChassisTnd-totalTxSecmSecmPktsOk OBJECT-TYPE
    SYNTAX      ConfdString
    MAX-ACCESS  read-only
    STATUS      current
    DESCRIPTION "Number of successful SECM to SECM transmits"
    ::= { affirmedChassisTnd-totalEntry 35 }

affirmedChassisTnd-totalTxSecmIomPktsOk OBJECT-TYPE
    SYNTAX      ConfdString
    MAX-ACCESS  read-only
    STATUS      current
    DESCRIPTION "Number of successful SECM to IOM transmits"
    ::= { affirmedChassisTnd-totalEntry 36 }

affirmedChassisTnd-totalTxErr OBJECT-TYPE
    SYNTAX      ConfdString
    MAX-ACCESS  read-only
    STATUS      current
    DESCRIPTION "Total number of transmit errors"
    ::= { affirmedChassisTnd-totalEntry 37 }

affirmedChassisTnd-totalRxErr OBJECT-TYPE
    SYNTAX      ConfdString
    MAX-ACCESS  read-only
    STATUS      current
    DESCRIPTION "Number of errored packets received with bad or no interface information"
    ::= { affirmedChassisTnd-totalEntry 38 }

affirmedChassisTnd-totalRxErr1 OBJECT-TYPE
    SYNTAX      ConfdString
    MAX-ACCESS  read-only
    STATUS      current
    DESCRIPTION "Number of errored packets received on fabric A"
    ::= { affirmedChassisTnd-totalEntry 39 }

affirmedChassisTnd-totalRxErr2 OBJECT-TYPE
    SYNTAX      ConfdString
    MAX-ACCESS  read-only
    STATUS      current
    DESCRIPTION "Number of errored packets received on fabric B"
    ::= { affirmedChassisTnd-totalEntry 40 }

affirmedChassisTnd-totalRxDisc OBJECT-TYPE
    SYNTAX      ConfdString
    MAX-ACCESS  read-only
    STATUS      current
    DESCRIPTION "Number of packets discarded with bad or no interface information"
    ::= { affirmedChassisTnd-totalEntry 41 }

affirmedChassisTnd-totalRxDisc1 OBJECT-TYPE
    SYNTAX      ConfdString
    MAX-ACCESS  read-only
    STATUS      current
    DESCRIPTION "Number of discarded packets received on fabric A"
    ::= { affirmedChassisTnd-totalEntry 42 }

affirmedChassisTnd-totalRxDisc2 OBJECT-TYPE
    SYNTAX      ConfdString
    MAX-ACCESS  read-only
    STATUS      current
    DESCRIPTION "Number of discarded packets received on fabric B"
    ::= { affirmedChassisTnd-totalEntry 43 }

affirmedChassisTnd-totalRxGnpErr OBJECT-TYPE
    SYNTAX      ConfdString
    MAX-ACCESS  read-only
    STATUS      current
    DESCRIPTION "Number of GNP neighbor discovery errored packets received"
    ::= { affirmedChassisTnd-totalEntry 44 }

affirmedChassisTnd-totalRxGnpDisc OBJECT-TYPE
    SYNTAX      ConfdString
    MAX-ACCESS  read-only
    STATUS      current
    DESCRIPTION "Number of GNP neighbor discovery packets received and discarded"
    ::= { affirmedChassisTnd-totalEntry 45 }

affirmedChassisTnd-totalTxWfdhcpGwPktsErr OBJECT-TYPE
    SYNTAX      ConfdString
    MAX-ACCESS  read-only
    STATUS      current
    DESCRIPTION "Number of errors sending WorkFlow DHCP transmits to gateway"
    ::= { affirmedChassisTnd-totalEntry 46 }

affirmedChassisTnd-totalRxWfdhcpGwPktsErr OBJECT-TYPE
    SYNTAX      ConfdString
    MAX-ACCESS  read-only
    STATUS      current
    DESCRIPTION "Number of errored WorkFlow DHCP packets received from gateway"
    ::= { affirmedChassisTnd-totalEntry 47 }

affirmedChassisTnd-totalRxWfmccUnknownIntf OBJECT-TYPE
    SYNTAX      ConfdString
    MAX-ACCESS  read-only
    STATUS      current
    DESCRIPTION "Number of IOM to WF MCC subscriber-unaware receives with bad ifIndex"
    ::= { affirmedChassisTnd-totalEntry 48 }

affirmedChassisTnd-totalRxWfmccCfgMismatch OBJECT-TYPE
    SYNTAX      ConfdString
    MAX-ACCESS  read-only
    STATUS      current
    DESCRIPTION "Number of IOM to WF MCC subscriber-unaware receives with cfg mismatch"
    ::= { affirmedChassisTnd-totalEntry 49 }

affirmedChassisTnd-totalRxWfmccPktParseErr OBJECT-TYPE
    SYNTAX      ConfdString
    MAX-ACCESS  read-only
    STATUS      current
    DESCRIPTION "Number of IOM to WF MCC subscriber-unaware receives with bad L3L4 hdr"
    ::= { affirmedChassisTnd-totalEntry 50 }

affirmedChassisTnd-totalRxWfmccSessionidGetErr OBJECT-TYPE
    SYNTAX      ConfdString
    MAX-ACCESS  read-only
    STATUS      current
    DESCRIPTION "Number of IOM to WF MCC subscriber-unaware receives with bad session"
    ::= { affirmedChassisTnd-totalEntry 51 }

affirmedChassisTnd-totalFragmentErr OBJECT-TYPE
    SYNTAX      ConfdString
    MAX-ACCESS  read-only
    STATUS      current
    DESCRIPTION "Number of failures trying to fragment a packet for transmit"
    ::= { affirmedChassisTnd-totalEntry 52 }

affirmedChassisTnd-totalTxTndKncPktsErr OBJECT-TYPE
    SYNTAX      ConfdString
    MAX-ACCESS  read-only
    STATUS      current
    DESCRIPTION "Number of KNC (GNP) transmit failures"
    ::= { affirmedChassisTnd-totalEntry 53 }

affirmedChassisTnd-totalTxTndAndataPktsErr OBJECT-TYPE
    SYNTAX      ConfdString
    MAX-ACCESS  read-only
    STATUS      current
    DESCRIPTION "Number of SSM to CSM tnd application transmit failures"
    ::= { affirmedChassisTnd-totalEntry 54 }

affirmedChassisTnd-totalTxIomWfAccessPktsErr OBJECT-TYPE
    SYNTAX      ConfdString
    MAX-ACCESS  read-only
    STATUS      current
    DESCRIPTION "Number of IOM to Workflow upstream transmit failures"
    ::= { affirmedChassisTnd-totalEntry 55 }

affirmedChassisTnd-totalTxWfIomAccessPktsErr OBJECT-TYPE
    SYNTAX      ConfdString
    MAX-ACCESS  read-only
    STATUS      current
    DESCRIPTION "Number of Workflow to IOM downstream transmit failures"
    ::= { affirmedChassisTnd-totalEntry 56 }

affirmedChassisTnd-totalTxIomWfCorePktsErr OBJECT-TYPE
    SYNTAX      ConfdString
    MAX-ACCESS  read-only
    STATUS      current
    DESCRIPTION "Number of IOM to Workflow downstream transmit failures"
    ::= { affirmedChassisTnd-totalEntry 57 }

affirmedChassisTnd-totalTxWfIomCorePktsErr OBJECT-TYPE
    SYNTAX      ConfdString
    MAX-ACCESS  read-only
    STATUS      current
    DESCRIPTION "Number of Workflow to IOM upstream transmit failures"
    ::= { affirmedChassisTnd-totalEntry 58 }

affirmedChassisTnd-totalTxIomIomPktsErr OBJECT-TYPE
    SYNTAX      ConfdString
    MAX-ACCESS  read-only
    STATUS      current
    DESCRIPTION "Number of IOM to IOM upstream transmit failures"
    ::= { affirmedChassisTnd-totalEntry 59 }

affirmedChassisTnd-totalTxIomIomMhopBfdPktsErr OBJECT-TYPE
    SYNTAX      ConfdString
    MAX-ACCESS  read-only
    STATUS      current
    DESCRIPTION "Number of IOM to IOM multihop BFD transmit failures"
    ::= { affirmedChassisTnd-totalEntry 60 }

affirmedChassisTnd-totalTxSecmSpmPktsErr OBJECT-TYPE
    SYNTAX      ConfdString
    MAX-ACCESS  read-only
    STATUS      current
    DESCRIPTION "Number of SECM to SPM transmits"
    ::= { affirmedChassisTnd-totalEntry 61 }

affirmedChassisTnd-totalTxSecmSecmPktsErr OBJECT-TYPE
    SYNTAX      ConfdString
    MAX-ACCESS  read-only
    STATUS      current
    DESCRIPTION "Number of SECM to SECM transmit failures"
    ::= { affirmedChassisTnd-totalEntry 62 }

affirmedChassisTnd-totalTxSecmIomPktsErr OBJECT-TYPE
    SYNTAX      ConfdString
    MAX-ACCESS  read-only
    STATUS      current
    DESCRIPTION "Number of SECM to IOM transmit failures"
    ::= { affirmedChassisTnd-totalEntry 63 }

affirmedChassisTnd-totalSynNoMetadataPkts OBJECT-TYPE
    SYNTAX      ConfdString
    MAX-ACCESS  read-only
    STATUS      current
    DESCRIPTION "Number of SYN packets without metadata"
    ::= { affirmedChassisTnd-totalEntry 64 }

affirmedChassisTnd-peerTable OBJECT-TYPE
    SYNTAX      SEQUENCE OF AffirmedChassisTnd-peerEntry
    MAX-ACCESS  not-accessible
    STATUS      current
    DESCRIPTION ""
    ::= { affirmedChassisMIB 25 }

affirmedChassisTnd-peerEntry OBJECT-TYPE
    SYNTAX      AffirmedChassisTnd-peerEntry
    MAX-ACCESS  not-accessible
    STATUS      current
    DESCRIPTION ""
    INDEX { affirmedChassisId, affirmedChassisTnd-peerNode, affirmedChassisTnd-peerCpuNum, affirmedChassisTnd-peerPeernode, affirmedChassisTnd-peerPeercpu }
        ::= { affirmedChassisTnd-peerTable 1 }

AffirmedChassisTnd-peerEntry ::=
    SEQUENCE {
        affirmedChassisTnd-peerNode Unsigned32,
        affirmedChassisTnd-peerCpuNum Unsigned32,
        affirmedChassisTnd-peerPeernode Unsigned32,
        affirmedChassisTnd-peerPeercpu Unsigned32,
        affirmedChassisTnd-peerRxEthIomToIom ConfdString,
        affirmedChassisTnd-peerRxEthIomToIomMhopBfd ConfdString,
        affirmedChassisTnd-peerRxEthWfmToGifm ConfdString,
        affirmedChassisTnd-peerRxEthGifmToWfm ConfdString,
        affirmedChassisTnd-peerRxEthGnfmToWfm ConfdString,
        affirmedChassisTnd-peerRxEthWfmToGnfm ConfdString,
        affirmedChassisTnd-peerRxAnData ConfdString,
        affirmedChassisTnd-peerRxAnLinux ConfdString,
        affirmedChassisTnd-peerRxSpmSecmRsaPkts ConfdString,
        affirmedChassisTnd-peerRxSecmSecmPkts ConfdString,
        affirmedChassisTnd-peerRxSecmIomPkts ConfdString,
        affirmedChassisTnd-peerTxSecmSpmRsa ConfdString,
        affirmedChassisTnd-peerTxWfdhcpGwPkts ConfdString,
        affirmedChassisTnd-peerRxWfdhcpGwPkts ConfdString,
        affirmedChassisTnd-peerRxWfmccPkt ConfdString,
        affirmedChassisTnd-peerTxFabric1Pkts ConfdString,
        affirmedChassisTnd-peerTxFabric2Pkts ConfdString,
        affirmedChassisTnd-peerRxIpPkt ConfdString,
        affirmedChassisTnd-peerTxIpPkt ConfdString,
        affirmedChassisTnd-peerLinked ConfdString,
        affirmedChassisTnd-peerFragmented ConfdString,
        affirmedChassisTnd-peerReassembled ConfdString,
        affirmedChassisTnd-peerDescriptorErrored ConfdString,
        affirmedChassisTnd-peerTxTndKncPktsOk ConfdString,
        affirmedChassisTnd-peerTxTndAndataPktsOk ConfdString,
        affirmedChassisTnd-peerTxIomWfAccessPktsOk ConfdString,
        affirmedChassisTnd-peerTxWfIomAccessPktsOk ConfdString,
        affirmedChassisTnd-peerTxIomWfCorePktsOk ConfdString,
        affirmedChassisTnd-peerTxWfIomCorePktsOk ConfdString,
        affirmedChassisTnd-peerTxIomIomPktsOk ConfdString,
        affirmedChassisTnd-peerTxIomIomMhopBfdPktsOk ConfdString,
        affirmedChassisTnd-peerTxSecmSpmPktsOk ConfdString,
        affirmedChassisTnd-peerTxSecmSecmPktsOk ConfdString,
        affirmedChassisTnd-peerTxSecmIomPktsOk ConfdString,
        affirmedChassisTnd-peerTxErr ConfdString,
        affirmedChassisTnd-peerRxErr ConfdString,
        affirmedChassisTnd-peerRxErr1 ConfdString,
        affirmedChassisTnd-peerRxErr2 ConfdString,
        affirmedChassisTnd-peerRxDisc ConfdString,
        affirmedChassisTnd-peerRxDisc1 ConfdString,
        affirmedChassisTnd-peerRxDisc2 ConfdString,
        affirmedChassisTnd-peerRxGnpErr ConfdString,
        affirmedChassisTnd-peerRxGnpDisc ConfdString,
        affirmedChassisTnd-peerTxWfdhcpGwPktsErr ConfdString,
        affirmedChassisTnd-peerRxWfdhcpGwPktsErr ConfdString,
        affirmedChassisTnd-peerRxWfmccUnknownIntf ConfdString,
        affirmedChassisTnd-peerRxWfmccCfgMismatch ConfdString,
        affirmedChassisTnd-peerRxWfmccPktParseErr ConfdString,
        affirmedChassisTnd-peerRxWfmccSessionidGetErr ConfdString,
        affirmedChassisTnd-peerFragmentErr ConfdString,
        affirmedChassisTnd-peerTxTndKncPktsErr ConfdString,
        affirmedChassisTnd-peerTxTndAndataPktsErr ConfdString,
        affirmedChassisTnd-peerTxIomWfAccessPktsErr ConfdString,
        affirmedChassisTnd-peerTxWfIomAccessPktsErr ConfdString,
        affirmedChassisTnd-peerTxIomWfCorePktsErr ConfdString,
        affirmedChassisTnd-peerTxWfIomCorePktsErr ConfdString,
        affirmedChassisTnd-peerTxIomIomPktsErr ConfdString,
        affirmedChassisTnd-peerTxIomIomMhopBfdPktsErr ConfdString,
        affirmedChassisTnd-peerTxSecmSpmPktsErr ConfdString,
        affirmedChassisTnd-peerTxSecmSecmPktsErr ConfdString,
        affirmedChassisTnd-peerTxSecmIomPktsErr ConfdString,
        affirmedChassisTnd-peerSynNoMetadataPkts ConfdString
    }

affirmedChassisTnd-peerNode OBJECT-TYPE
    SYNTAX      Unsigned32
    MAX-ACCESS  not-accessible
    STATUS      current
    DESCRIPTION "node number"
    ::= { affirmedChassisTnd-peerEntry 1 }

affirmedChassisTnd-peerCpuNum OBJECT-TYPE
    SYNTAX      Unsigned32
    MAX-ACCESS  not-accessible
    STATUS      current
    DESCRIPTION "cpu number"
    ::= { affirmedChassisTnd-peerEntry 2 }

affirmedChassisTnd-peerPeernode OBJECT-TYPE
    SYNTAX      Unsigned32
    MAX-ACCESS  not-accessible
    STATUS      current
    DESCRIPTION "peer node number"
    ::= { affirmedChassisTnd-peerEntry 3 }

affirmedChassisTnd-peerPeercpu OBJECT-TYPE
    SYNTAX      Unsigned32
    MAX-ACCESS  not-accessible
    STATUS      current
    DESCRIPTION "peer cpu number"
    ::= { affirmedChassisTnd-peerEntry 4 }

affirmedChassisTnd-peerRxEthIomToIom OBJECT-TYPE
    SYNTAX      ConfdString
    MAX-ACCESS  read-only
    STATUS      current
    DESCRIPTION "Number of IOM to IOM packets received"
    ::= { affirmedChassisTnd-peerEntry 5 }

affirmedChassisTnd-peerRxEthIomToIomMhopBfd OBJECT-TYPE
    SYNTAX      ConfdString
    MAX-ACCESS  read-only
    STATUS      current
    DESCRIPTION "Number of IOM to IOM multihop BFD packets received"
    ::= { affirmedChassisTnd-peerEntry 6 }

affirmedChassisTnd-peerRxEthWfmToGifm OBJECT-TYPE
    SYNTAX      ConfdString
    MAX-ACCESS  read-only
    STATUS      current
    DESCRIPTION "Number of WorkFlow to IOM Upstream (Gi) packets received"
    ::= { affirmedChassisTnd-peerEntry 7 }

affirmedChassisTnd-peerRxEthGifmToWfm OBJECT-TYPE
    SYNTAX      ConfdString
    MAX-ACCESS  read-only
    STATUS      current
    DESCRIPTION "Number of (Gi) IOM to WorkFlow Downstream packets received"
    ::= { affirmedChassisTnd-peerEntry 8 }

affirmedChassisTnd-peerRxEthGnfmToWfm OBJECT-TYPE
    SYNTAX      ConfdString
    MAX-ACCESS  read-only
    STATUS      current
    DESCRIPTION "Number of (Gn) IOM to WorkFlow Upstream packets received"
    ::= { affirmedChassisTnd-peerEntry 9 }

affirmedChassisTnd-peerRxEthWfmToGnfm OBJECT-TYPE
    SYNTAX      ConfdString
    MAX-ACCESS  read-only
    STATUS      current
    DESCRIPTION "Number of WorkFlow to IOM (Gn) Downstream packets received"
    ::= { affirmedChassisTnd-peerEntry 10 }

affirmedChassisTnd-peerRxAnData OBJECT-TYPE
    SYNTAX      ConfdString
    MAX-ACCESS  read-only
    STATUS      current
    DESCRIPTION "Number of CSM to SSM tnd application data packets received"
    ::= { affirmedChassisTnd-peerEntry 11 }

affirmedChassisTnd-peerRxAnLinux OBJECT-TYPE
    SYNTAX      ConfdString
    MAX-ACCESS  read-only
    STATUS      current
    DESCRIPTION "Number of CSM to SSM gnp and egress kernel packets received"
    ::= { affirmedChassisTnd-peerEntry 12 }

affirmedChassisTnd-peerRxSpmSecmRsaPkts OBJECT-TYPE
    SYNTAX      ConfdString
    MAX-ACCESS  read-only
    STATUS      current
    DESCRIPTION "Number of SPM to SECM RSA helper requests"
    ::= { affirmedChassisTnd-peerEntry 13 }

affirmedChassisTnd-peerRxSecmSecmPkts OBJECT-TYPE
    SYNTAX      ConfdString
    MAX-ACCESS  read-only
    STATUS      current
    DESCRIPTION "Number of SECM to SECM packets received"
    ::= { affirmedChassisTnd-peerEntry 14 }

affirmedChassisTnd-peerRxSecmIomPkts OBJECT-TYPE
    SYNTAX      ConfdString
    MAX-ACCESS  read-only
    STATUS      current
    DESCRIPTION "Number of SECM to IOM packets received"
    ::= { affirmedChassisTnd-peerEntry 15 }

affirmedChassisTnd-peerTxSecmSpmRsa OBJECT-TYPE
    SYNTAX      ConfdString
    MAX-ACCESS  read-only
    STATUS      current
    DESCRIPTION "Number of SECM to SPM RSA helper responses"
    ::= { affirmedChassisTnd-peerEntry 16 }

affirmedChassisTnd-peerTxWfdhcpGwPkts OBJECT-TYPE
    SYNTAX      ConfdString
    MAX-ACCESS  read-only
    STATUS      current
    DESCRIPTION "Number of WorkFlow DHCP packets sent to gateway"
    ::= { affirmedChassisTnd-peerEntry 17 }

affirmedChassisTnd-peerRxWfdhcpGwPkts OBJECT-TYPE
    SYNTAX      ConfdString
    MAX-ACCESS  read-only
    STATUS      current
    DESCRIPTION "Number of WorkFlow DHCP packets received from gateway"
    ::= { affirmedChassisTnd-peerEntry 18 }

affirmedChassisTnd-peerRxWfmccPkt OBJECT-TYPE
    SYNTAX      ConfdString
    MAX-ACCESS  read-only
    STATUS      current
    DESCRIPTION "Number of IOM to Workflow MCC subscriber-unaware packets received"
    ::= { affirmedChassisTnd-peerEntry 19 }

affirmedChassisTnd-peerTxFabric1Pkts OBJECT-TYPE
    SYNTAX      ConfdString
    MAX-ACCESS  read-only
    STATUS      current
    DESCRIPTION "ATCA: Number of transmits on fabric A"
    ::= { affirmedChassisTnd-peerEntry 20 }

affirmedChassisTnd-peerTxFabric2Pkts OBJECT-TYPE
    SYNTAX      ConfdString
    MAX-ACCESS  read-only
    STATUS      current
    DESCRIPTION "ATCA: Number of transmits on fabric B"
    ::= { affirmedChassisTnd-peerEntry 21 }

affirmedChassisTnd-peerRxIpPkt OBJECT-TYPE
    SYNTAX      ConfdString
    MAX-ACCESS  read-only
    STATUS      current
    DESCRIPTION "Number of standard ethernet packets received"
    ::= { affirmedChassisTnd-peerEntry 22 }

affirmedChassisTnd-peerTxIpPkt OBJECT-TYPE
    SYNTAX      ConfdString
    MAX-ACCESS  read-only
    STATUS      current
    DESCRIPTION "Number of standard ethernet transmits"
    ::= { affirmedChassisTnd-peerEntry 23 }

affirmedChassisTnd-peerLinked OBJECT-TYPE
    SYNTAX      ConfdString
    MAX-ACCESS  read-only
    STATUS      current
    DESCRIPTION "Number of transmit failures because descriptors are linked"
    ::= { affirmedChassisTnd-peerEntry 24 }

affirmedChassisTnd-peerFragmented OBJECT-TYPE
    SYNTAX      ConfdString
    MAX-ACCESS  read-only
    STATUS      current
    DESCRIPTION "Number of transmit packets that were fragmented"
    ::= { affirmedChassisTnd-peerEntry 25 }

affirmedChassisTnd-peerReassembled OBJECT-TYPE
    SYNTAX      ConfdString
    MAX-ACCESS  read-only
    STATUS      current
    DESCRIPTION "Number of received packets that were reassembled"
    ::= { affirmedChassisTnd-peerEntry 26 }

affirmedChassisTnd-peerDescriptorErrored OBJECT-TYPE
    SYNTAX      ConfdString
    MAX-ACCESS  read-only
    STATUS      current
    DESCRIPTION "Number of transmit failures because of descriptors errors"
    ::= { affirmedChassisTnd-peerEntry 27 }

affirmedChassisTnd-peerTxTndKncPktsOk OBJECT-TYPE
    SYNTAX      ConfdString
    MAX-ACCESS  read-only
    STATUS      current
    DESCRIPTION "Number of successful KNC (GNP) transmits"
    ::= { affirmedChassisTnd-peerEntry 28 }

affirmedChassisTnd-peerTxTndAndataPktsOk OBJECT-TYPE
    SYNTAX      ConfdString
    MAX-ACCESS  read-only
    STATUS      current
    DESCRIPTION "Number of successful SSM to CSM tnd application transmits"
    ::= { affirmedChassisTnd-peerEntry 29 }

affirmedChassisTnd-peerTxIomWfAccessPktsOk OBJECT-TYPE
    SYNTAX      ConfdString
    MAX-ACCESS  read-only
    STATUS      current
    DESCRIPTION "Number of successful IOM to Workflow upstream transmits"
    ::= { affirmedChassisTnd-peerEntry 30 }

affirmedChassisTnd-peerTxWfIomAccessPktsOk OBJECT-TYPE
    SYNTAX      ConfdString
    MAX-ACCESS  read-only
    STATUS      current
    DESCRIPTION "Number of successful Workflow to IOM downstream transmits"
    ::= { affirmedChassisTnd-peerEntry 31 }

affirmedChassisTnd-peerTxIomWfCorePktsOk OBJECT-TYPE
    SYNTAX      ConfdString
    MAX-ACCESS  read-only
    STATUS      current
    DESCRIPTION "Number of successful IOM to Workflow downstream transmits"
    ::= { affirmedChassisTnd-peerEntry 32 }

affirmedChassisTnd-peerTxWfIomCorePktsOk OBJECT-TYPE
    SYNTAX      ConfdString
    MAX-ACCESS  read-only
    STATUS      current
    DESCRIPTION "Number of successful Workflow to IOM upstream transmits"
    ::= { affirmedChassisTnd-peerEntry 33 }

affirmedChassisTnd-peerTxIomIomPktsOk OBJECT-TYPE
    SYNTAX      ConfdString
    MAX-ACCESS  read-only
    STATUS      current
    DESCRIPTION "Number of successful IOM to IOM upstream transmits"
    ::= { affirmedChassisTnd-peerEntry 34 }

affirmedChassisTnd-peerTxIomIomMhopBfdPktsOk OBJECT-TYPE
    SYNTAX      ConfdString
    MAX-ACCESS  read-only
    STATUS      current
    DESCRIPTION "Number of successful IOM to IOM multihop BFD transmits"
    ::= { affirmedChassisTnd-peerEntry 35 }

affirmedChassisTnd-peerTxSecmSpmPktsOk OBJECT-TYPE
    SYNTAX      ConfdString
    MAX-ACCESS  read-only
    STATUS      current
    DESCRIPTION "Number of successful SECM to SPM transmits"
    ::= { affirmedChassisTnd-peerEntry 36 }

affirmedChassisTnd-peerTxSecmSecmPktsOk OBJECT-TYPE
    SYNTAX      ConfdString
    MAX-ACCESS  read-only
    STATUS      current
    DESCRIPTION "Number of successful SECM to SECM transmits"
    ::= { affirmedChassisTnd-peerEntry 37 }

affirmedChassisTnd-peerTxSecmIomPktsOk OBJECT-TYPE
    SYNTAX      ConfdString
    MAX-ACCESS  read-only
    STATUS      current
    DESCRIPTION "Number of successful SECM to IOM transmits"
    ::= { affirmedChassisTnd-peerEntry 38 }

affirmedChassisTnd-peerTxErr OBJECT-TYPE
    SYNTAX      ConfdString
    MAX-ACCESS  read-only
    STATUS      current
    DESCRIPTION "Total number of transmit errors"
    ::= { affirmedChassisTnd-peerEntry 39 }

affirmedChassisTnd-peerRxErr OBJECT-TYPE
    SYNTAX      ConfdString
    MAX-ACCESS  read-only
    STATUS      current
    DESCRIPTION "Number of errored packets received with bad or no interface information"
    ::= { affirmedChassisTnd-peerEntry 40 }

affirmedChassisTnd-peerRxErr1 OBJECT-TYPE
    SYNTAX      ConfdString
    MAX-ACCESS  read-only
    STATUS      current
    DESCRIPTION "Number of errored packets received on fabric A"
    ::= { affirmedChassisTnd-peerEntry 41 }

affirmedChassisTnd-peerRxErr2 OBJECT-TYPE
    SYNTAX      ConfdString
    MAX-ACCESS  read-only
    STATUS      current
    DESCRIPTION "Number of errored packets received on fabric B"
    ::= { affirmedChassisTnd-peerEntry 42 }

affirmedChassisTnd-peerRxDisc OBJECT-TYPE
    SYNTAX      ConfdString
    MAX-ACCESS  read-only
    STATUS      current
    DESCRIPTION "Number of packets discarded with bad or no interface information"
    ::= { affirmedChassisTnd-peerEntry 43 }

affirmedChassisTnd-peerRxDisc1 OBJECT-TYPE
    SYNTAX      ConfdString
    MAX-ACCESS  read-only
    STATUS      current
    DESCRIPTION "Number of discarded packets received on fabric A"
    ::= { affirmedChassisTnd-peerEntry 44 }

affirmedChassisTnd-peerRxDisc2 OBJECT-TYPE
    SYNTAX      ConfdString
    MAX-ACCESS  read-only
    STATUS      current
    DESCRIPTION "Number of discarded packets received on fabric B"
    ::= { affirmedChassisTnd-peerEntry 45 }

affirmedChassisTnd-peerRxGnpErr OBJECT-TYPE
    SYNTAX      ConfdString
    MAX-ACCESS  read-only
    STATUS      current
    DESCRIPTION "Number of GNP neighbor discovery errored packets received"
    ::= { affirmedChassisTnd-peerEntry 46 }

affirmedChassisTnd-peerRxGnpDisc OBJECT-TYPE
    SYNTAX      ConfdString
    MAX-ACCESS  read-only
    STATUS      current
    DESCRIPTION "Number of GNP neighbor discovery packets received and discarded"
    ::= { affirmedChassisTnd-peerEntry 47 }

affirmedChassisTnd-peerTxWfdhcpGwPktsErr OBJECT-TYPE
    SYNTAX      ConfdString
    MAX-ACCESS  read-only
    STATUS      current
    DESCRIPTION "Number of errors sending WorkFlow DHCP transmits to gateway"
    ::= { affirmedChassisTnd-peerEntry 48 }

affirmedChassisTnd-peerRxWfdhcpGwPktsErr OBJECT-TYPE
    SYNTAX      ConfdString
    MAX-ACCESS  read-only
    STATUS      current
    DESCRIPTION "Number of errored WorkFlow DHCP packets received from gateway"
    ::= { affirmedChassisTnd-peerEntry 49 }

affirmedChassisTnd-peerRxWfmccUnknownIntf OBJECT-TYPE
    SYNTAX      ConfdString
    MAX-ACCESS  read-only
    STATUS      current
    DESCRIPTION "Number of IOM to WF MCC subscriber-unaware receives with bad ifIndex"
    ::= { affirmedChassisTnd-peerEntry 50 }

affirmedChassisTnd-peerRxWfmccCfgMismatch OBJECT-TYPE
    SYNTAX      ConfdString
    MAX-ACCESS  read-only
    STATUS      current
    DESCRIPTION "Number of IOM to WF MCC subscriber-unaware receives with cfg mismatch"
    ::= { affirmedChassisTnd-peerEntry 51 }

affirmedChassisTnd-peerRxWfmccPktParseErr OBJECT-TYPE
    SYNTAX      ConfdString
    MAX-ACCESS  read-only
    STATUS      current
    DESCRIPTION "Number of IOM to WF MCC subscriber-unaware receives with bad L3L4 hdr"
    ::= { affirmedChassisTnd-peerEntry 52 }

affirmedChassisTnd-peerRxWfmccSessionidGetErr OBJECT-TYPE
    SYNTAX      ConfdString
    MAX-ACCESS  read-only
    STATUS      current
    DESCRIPTION "Number of IOM to WF MCC subscriber-unaware receives with bad session"
    ::= { affirmedChassisTnd-peerEntry 53 }

affirmedChassisTnd-peerFragmentErr OBJECT-TYPE
    SYNTAX      ConfdString
    MAX-ACCESS  read-only
    STATUS      current
    DESCRIPTION "Number of failures trying to fragment a packet for transmit"
    ::= { affirmedChassisTnd-peerEntry 54 }

affirmedChassisTnd-peerTxTndKncPktsErr OBJECT-TYPE
    SYNTAX      ConfdString
    MAX-ACCESS  read-only
    STATUS      current
    DESCRIPTION "Number of KNC (GNP) transmit failures"
    ::= { affirmedChassisTnd-peerEntry 55 }

affirmedChassisTnd-peerTxTndAndataPktsErr OBJECT-TYPE
    SYNTAX      ConfdString
    MAX-ACCESS  read-only
    STATUS      current
    DESCRIPTION "Number of SSM to CSM tnd application transmit failures"
    ::= { affirmedChassisTnd-peerEntry 56 }

affirmedChassisTnd-peerTxIomWfAccessPktsErr OBJECT-TYPE
    SYNTAX      ConfdString
    MAX-ACCESS  read-only
    STATUS      current
    DESCRIPTION "Number of IOM to Workflow upstream transmit failures"
    ::= { affirmedChassisTnd-peerEntry 57 }

affirmedChassisTnd-peerTxWfIomAccessPktsErr OBJECT-TYPE
    SYNTAX      ConfdString
    MAX-ACCESS  read-only
    STATUS      current
    DESCRIPTION "Number of Workflow to IOM downstream transmit failures"
    ::= { affirmedChassisTnd-peerEntry 58 }

affirmedChassisTnd-peerTxIomWfCorePktsErr OBJECT-TYPE
    SYNTAX      ConfdString
    MAX-ACCESS  read-only
    STATUS      current
    DESCRIPTION "Number of IOM to Workflow downstream transmit failures"
    ::= { affirmedChassisTnd-peerEntry 59 }

affirmedChassisTnd-peerTxWfIomCorePktsErr OBJECT-TYPE
    SYNTAX      ConfdString
    MAX-ACCESS  read-only
    STATUS      current
    DESCRIPTION "Number of Workflow to IOM upstream transmit failures"
    ::= { affirmedChassisTnd-peerEntry 60 }

affirmedChassisTnd-peerTxIomIomPktsErr OBJECT-TYPE
    SYNTAX      ConfdString
    MAX-ACCESS  read-only
    STATUS      current
    DESCRIPTION "Number of IOM to IOM upstream transmit failures"
    ::= { affirmedChassisTnd-peerEntry 61 }

affirmedChassisTnd-peerTxIomIomMhopBfdPktsErr OBJECT-TYPE
    SYNTAX      ConfdString
    MAX-ACCESS  read-only
    STATUS      current
    DESCRIPTION "Number of IOM to IOM multihop BFD transmit failures"
    ::= { affirmedChassisTnd-peerEntry 62 }

affirmedChassisTnd-peerTxSecmSpmPktsErr OBJECT-TYPE
    SYNTAX      ConfdString
    MAX-ACCESS  read-only
    STATUS      current
    DESCRIPTION "Number of SECM to SPM transmits"
    ::= { affirmedChassisTnd-peerEntry 63 }

affirmedChassisTnd-peerTxSecmSecmPktsErr OBJECT-TYPE
    SYNTAX      ConfdString
    MAX-ACCESS  read-only
    STATUS      current
    DESCRIPTION "Number of SECM to SECM transmit failures"
    ::= { affirmedChassisTnd-peerEntry 64 }

affirmedChassisTnd-peerTxSecmIomPktsErr OBJECT-TYPE
    SYNTAX      ConfdString
    MAX-ACCESS  read-only
    STATUS      current
    DESCRIPTION "Number of SECM to IOM transmit failures"
    ::= { affirmedChassisTnd-peerEntry 65 }

affirmedChassisTnd-peerSynNoMetadataPkts OBJECT-TYPE
    SYNTAX      ConfdString
    MAX-ACCESS  read-only
    STATUS      current
    DESCRIPTION "Number of SYN packets without metadata"
    ::= { affirmedChassisTnd-peerEntry 66 }

affirmedChassisAudit-summaryTable OBJECT-TYPE
    SYNTAX      SEQUENCE OF AffirmedChassisAudit-summaryEntry
    MAX-ACCESS  not-accessible
    STATUS      current
    DESCRIPTION ""
    ::= { affirmedChassisMIB 28 }

affirmedChassisAudit-summaryEntry OBJECT-TYPE
    SYNTAX      AffirmedChassisAudit-summaryEntry
    MAX-ACCESS  not-accessible
    STATUS      current
    DESCRIPTION ""
    INDEX { affirmedChassisId, IMPLIED affirmedChassisAudit-summaryTask }
        ::= { affirmedChassisAudit-summaryTable 1 }

AffirmedChassisAudit-summaryEntry ::=
    SEQUENCE {
        affirmedChassisAudit-summaryTask String,
        affirmedChassisAudit-summaryNumberAgents Unsigned32,
        affirmedChassisAudit-summaryNumberAuditsRegistered Unsigned32,
        affirmedChassisAudit-summaryNumberErrorRows Unsigned32,
        affirmedChassisAudit-summaryLastAudited String
    }

affirmedChassisAudit-summaryTask OBJECT-TYPE
    SYNTAX      String
    MAX-ACCESS  not-accessible
    STATUS      current
    DESCRIPTION ""
    ::= { affirmedChassisAudit-summaryEntry 1 }

affirmedChassisAudit-summaryNumberAgents OBJECT-TYPE
    SYNTAX      Unsigned32
    MAX-ACCESS  read-only
    STATUS      current
    DESCRIPTION ""
    ::= { affirmedChassisAudit-summaryEntry 2 }

affirmedChassisAudit-summaryNumberAuditsRegistered OBJECT-TYPE
    SYNTAX      Unsigned32
    MAX-ACCESS  read-only
    STATUS      current
    DESCRIPTION ""
    ::= { affirmedChassisAudit-summaryEntry 3 }

affirmedChassisAudit-summaryNumberErrorRows OBJECT-TYPE
    SYNTAX      Unsigned32
    MAX-ACCESS  read-only
    STATUS      current
    DESCRIPTION ""
    ::= { affirmedChassisAudit-summaryEntry 4 }

affirmedChassisAudit-summaryLastAudited OBJECT-TYPE
    SYNTAX      String
    MAX-ACCESS  read-only
    STATUS      current
    DESCRIPTION ""
    ::= { affirmedChassisAudit-summaryEntry 5 }

affirmedChassisAudit-detailTable OBJECT-TYPE
    SYNTAX      SEQUENCE OF AffirmedChassisAudit-detailEntry
    MAX-ACCESS  not-accessible
    STATUS      current
    DESCRIPTION ""
    ::= { affirmedChassisMIB 29 }

affirmedChassisAudit-detailEntry OBJECT-TYPE
    SYNTAX      AffirmedChassisAudit-detailEntry
    MAX-ACCESS  not-accessible
    STATUS      current
    DESCRIPTION ""
    INDEX { affirmedChassisId, affirmedChassisAudit-detailTask, affirmedChassisAudit-detailAgentName, affirmedChassisAudit-detailAgentId, IMPLIED affirmedChassisAudit-detailXpath }
        ::= { affirmedChassisAudit-detailTable 1 }

AffirmedChassisAudit-detailEntry ::=
    SEQUENCE {
        affirmedChassisAudit-detailTask String,
        affirmedChassisAudit-detailAgentName String,
        affirmedChassisAudit-detailAgentId String,
        affirmedChassisAudit-detailXpath String,
        affirmedChassisAudit-detailErrorDescription String,
        affirmedChassisAudit-detailRepairAttempted String
    }

affirmedChassisAudit-detailTask OBJECT-TYPE
    SYNTAX      String
    MAX-ACCESS  not-accessible
    STATUS      current
    DESCRIPTION ""
    ::= { affirmedChassisAudit-detailEntry 1 }

affirmedChassisAudit-detailAgentName OBJECT-TYPE
    SYNTAX      String
    MAX-ACCESS  not-accessible
    STATUS      current
    DESCRIPTION ""
    ::= { affirmedChassisAudit-detailEntry 2 }

affirmedChassisAudit-detailAgentId OBJECT-TYPE
    SYNTAX      String
    MAX-ACCESS  not-accessible
    STATUS      current
    DESCRIPTION ""
    ::= { affirmedChassisAudit-detailEntry 3 }

affirmedChassisAudit-detailXpath OBJECT-TYPE
    SYNTAX      String
    MAX-ACCESS  not-accessible
    STATUS      current
    DESCRIPTION ""
    ::= { affirmedChassisAudit-detailEntry 4 }

affirmedChassisAudit-detailErrorDescription OBJECT-TYPE
    SYNTAX      String
    MAX-ACCESS  read-only
    STATUS      current
    DESCRIPTION ""
    ::= { affirmedChassisAudit-detailEntry 5 }

affirmedChassisAudit-detailRepairAttempted OBJECT-TYPE
    SYNTAX      String
    MAX-ACCESS  read-only
    STATUS      current
    DESCRIPTION ""
    ::= { affirmedChassisAudit-detailEntry 6 }

affirmedChassisCore-layoutTable OBJECT-TYPE
    SYNTAX      SEQUENCE OF AffirmedChassisCore-layoutEntry
    MAX-ACCESS  not-accessible
    STATUS      current
    DESCRIPTION ""
    ::= { affirmedChassisMIB 38 }

affirmedChassisCore-layoutEntry OBJECT-TYPE
    SYNTAX      AffirmedChassisCore-layoutEntry
    MAX-ACCESS  not-accessible
    STATUS      current
    DESCRIPTION ""
    INDEX { affirmedChassisId, affirmedChassisCore-layoutSlot }
        ::= { affirmedChassisCore-layoutTable 1 }

AffirmedChassisCore-layoutEntry ::=
    SEQUENCE {
        affirmedChassisCore-layoutSlot Unsigned32,
        affirmedChassisCore-layoutTotalCores ConfdString,
        affirmedChassisCore-layoutLinuxCores String,
        affirmedChassisCore-layoutIoCores String,
        affirmedChassisCore-layoutKniCores String,
        affirmedChassisCore-layoutAsmHdCores String,
        affirmedChassisCore-layoutSsmHdCores String,
        affirmedChassisCore-layoutNumProxyCores ConfdString,
        affirmedChassisCore-layoutIsolCpus String,
        affirmedChassisCore-layoutProxyCores String
    }

affirmedChassisCore-layoutSlot OBJECT-TYPE
    SYNTAX      Unsigned32
    MAX-ACCESS  not-accessible
    STATUS      current
    DESCRIPTION "slot number"
    ::= { affirmedChassisCore-layoutEntry 1 }

affirmedChassisCore-layoutTotalCores OBJECT-TYPE
    SYNTAX      ConfdString
    MAX-ACCESS  read-only
    STATUS      current
    DESCRIPTION "Total number of cores in the VM"
    ::= { affirmedChassisCore-layoutEntry 2 }

affirmedChassisCore-layoutLinuxCores OBJECT-TYPE
    SYNTAX      String
    MAX-ACCESS  read-only
    STATUS      current
    DESCRIPTION "Cores reserved for Linux"
    ::= { affirmedChassisCore-layoutEntry 3 }

affirmedChassisCore-layoutIoCores OBJECT-TYPE
    SYNTAX      String
    MAX-ACCESS  read-only
    STATUS      current
    DESCRIPTION "Cores reserved for I/O"
    ::= { affirmedChassisCore-layoutEntry 4 }

affirmedChassisCore-layoutKniCores OBJECT-TYPE
    SYNTAX      String
    MAX-ACCESS  read-only
    STATUS      current
    DESCRIPTION "Cores reserved for KNI"
    ::= { affirmedChassisCore-layoutEntry 5 }

affirmedChassisCore-layoutAsmHdCores OBJECT-TYPE
    SYNTAX      String
    MAX-ACCESS  read-only
    STATUS      current
    DESCRIPTION "Cores reserved for ASM HD"
    ::= { affirmedChassisCore-layoutEntry 6 }

affirmedChassisCore-layoutSsmHdCores OBJECT-TYPE
    SYNTAX      String
    MAX-ACCESS  read-only
    STATUS      current
    DESCRIPTION "Cores reserved for SSM HD"
    ::= { affirmedChassisCore-layoutEntry 7 }

affirmedChassisCore-layoutNumProxyCores OBJECT-TYPE
    SYNTAX      ConfdString
    MAX-ACCESS  read-only
    STATUS      deprecated
    DESCRIPTION "Cores reserved for PROXY"
    ::= { affirmedChassisCore-layoutEntry 8 }

affirmedChassisCore-layoutIsolCpus OBJECT-TYPE
    SYNTAX      String
    MAX-ACCESS  read-only
    STATUS      current
    DESCRIPTION "isolcpus"
    ::= { affirmedChassisCore-layoutEntry 9 }

affirmedChassisCore-layoutProxyCores OBJECT-TYPE
    SYNTAX      String
    MAX-ACCESS  read-only
    STATUS      current
    DESCRIPTION "Cores reserved for Proxy"
    ::= { affirmedChassisCore-layoutEntry 10 }

END

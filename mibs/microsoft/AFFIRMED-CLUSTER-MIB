AFFIRMED-CLUSTER-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedClusterMIB MODULE-IDENTITY
    ORGANIZATION "Affirmed Networks, Inc."
    CONTACT-INFO "Affirmed Networks, Inc. 35 Nagog Park, Acton, MA, USA"
    DESCRIPTION ""
    ::= { 1 3 6 1 4 1 37963 10 11 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedClusterTable OBJECT-TYPE
    SYNTAX      SEQUENCE OF AffirmedClusterEntry
    MAX-ACCESS  not-accessible
    STATUS      current
    DESCRIPTION ""
    ::= { affirmedClusterMIB 1 }

affirmedClusterEntry OBJECT-TYPE
    SYNTAX      AffirmedClusterEntry
    MAX-ACCESS  not-accessible
    STATUS      current
    DESCRIPTION ""
    INDEX { affirmedClusterId }
        ::= { affirmedClusterTable 1 }

AffirmedClusterEntry ::=
    SEQUENCE {
        affirmedClusterId Integer32,
        affirmedClusterRowstatus RowStatus
    }

affirmedClusterId OBJECT-TYPE
    SYNTAX      Integer32
    MAX-ACCESS  not-accessible
    STATUS      current
    DESCRIPTION ""
    ::= { affirmedClusterEntry 1 }

affirmedClusterRowstatus OBJECT-TYPE
    SYNTAX      RowStatus
    MAX-ACCESS  read-create
    STATUS      current
    DESCRIPTION ""
    ::= { affirmedClusterEntry 2 }

affirmedClusterDataProtectionSwitchingStatusTable OBJECT-TYPE
    SYNTAX      SEQUENCE OF AffirmedClusterDataProtectionSwitchingStatusEntry
    MAX-ACCESS  not-accessible
    STATUS      current
    DESCRIPTION ""
    ::= { affirmedClusterMIB 2 }

affirmedClusterDataProtectionSwitchingStatusEntry OBJECT-TYPE
    SYNTAX      AffirmedClusterDataProtectionSwitchingStatusEntry
    MAX-ACCESS  not-accessible
    STATUS      current
    DESCRIPTION ""
    INDEX { affirmedClusterId, affirmedClusterDataProtectionSwitchingStatusNodeid }
        ::= { affirmedClusterDataProtectionSwitchingStatusTable 1 }

AffirmedClusterDataProtectionSwitchingStatusEntry ::=
    SEQUENCE {
        affirmedClusterDataProtectionSwitchingStatusNodeid Unsigned32,
        affirmedClusterDataProtectionSwitchingStatusUsingport INTEGER,
        affirmedClusterDataProtectionSwitchingStatusNumswitchover Unsigned32,
        affirmedClusterDataProtectionSwitchingStatusLastswitchover ConfdString,
        affirmedClusterDataProtectionSwitchingStatusPathbitMapA String,
        affirmedClusterDataProtectionSwitchingStatusPathbitMapB String,
        affirmedClusterDataProtectionSwitchingStatusSwitchovercause String
    }

affirmedClusterDataProtectionSwitchingStatusNodeid OBJECT-TYPE
    SYNTAX      Unsigned32
    MAX-ACCESS  not-accessible
    STATUS      current
    DESCRIPTION "node id"
    ::= { affirmedClusterDataProtectionSwitchingStatusEntry 1 }

affirmedClusterDataProtectionSwitchingStatusUsingport OBJECT-TYPE
    SYNTAX      INTEGER {port-A(0),port-B(1),port-A-B(2)}
    MAX-ACCESS  read-only
    STATUS      current
    DESCRIPTION "Using Port"
    ::= { affirmedClusterDataProtectionSwitchingStatusEntry 2 }

affirmedClusterDataProtectionSwitchingStatusNumswitchover OBJECT-TYPE
    SYNTAX      Unsigned32
    MAX-ACCESS  read-only
    STATUS      current
    DESCRIPTION "Number of switchover events"
    ::= { affirmedClusterDataProtectionSwitchingStatusEntry 3 }

affirmedClusterDataProtectionSwitchingStatusLastswitchover OBJECT-TYPE
    SYNTAX      ConfdString
    MAX-ACCESS  read-only
    STATUS      current
    DESCRIPTION "Elapsed time since most recent switchover in Ms"
    ::= { affirmedClusterDataProtectionSwitchingStatusEntry 4 }

affirmedClusterDataProtectionSwitchingStatusPathbitMapA OBJECT-TYPE
    SYNTAX      String
    MAX-ACCESS  read-only
    STATUS      current
    DESCRIPTION "Bitmap of reachable nodes over port A"
    ::= { affirmedClusterDataProtectionSwitchingStatusEntry 5 }

affirmedClusterDataProtectionSwitchingStatusPathbitMapB OBJECT-TYPE
    SYNTAX      String
    MAX-ACCESS  read-only
    STATUS      current
    DESCRIPTION "Bitmap of reachable nodes over port B"
    ::= { affirmedClusterDataProtectionSwitchingStatusEntry 6 }

affirmedClusterDataProtectionSwitchingStatusSwitchovercause OBJECT-TYPE
    SYNTAX      String
    MAX-ACCESS  read-only
    STATUS      current
    DESCRIPTION "Cause of most recent switchover"
    ::= { affirmedClusterDataProtectionSwitchingStatusEntry 7 }

affirmedClusterDataProtectionSwitchingLinkTable OBJECT-TYPE
    SYNTAX      SEQUENCE OF AffirmedClusterDataProtectionSwitchingLinkEntry
    MAX-ACCESS  not-accessible
    STATUS      current
    DESCRIPTION ""
    ::= { affirmedClusterMIB 3 }

affirmedClusterDataProtectionSwitchingLinkEntry OBJECT-TYPE
    SYNTAX      AffirmedClusterDataProtectionSwitchingLinkEntry
    MAX-ACCESS  not-accessible
    STATUS      current
    DESCRIPTION ""
    INDEX { affirmedClusterId, affirmedClusterDataProtectionSwitchingLinkNodeid, affirmedClusterDataProtectionSwitchingLinkPeernodeid }
        ::= { affirmedClusterDataProtectionSwitchingLinkTable 1 }

AffirmedClusterDataProtectionSwitchingLinkEntry ::=
    SEQUENCE {
        affirmedClusterDataProtectionSwitchingLinkNodeid Unsigned32,
        affirmedClusterDataProtectionSwitchingLinkPeernodeid Unsigned32,
        affirmedClusterDataProtectionSwitchingLinkLastrxportA Unsigned32,
        affirmedClusterDataProtectionSwitchingLinkLastrxportB Unsigned32,
        affirmedClusterDataProtectionSwitchingLinkLastrxtxportA Unsigned32,
        affirmedClusterDataProtectionSwitchingLinkRxhistportA Unsigned32,
        affirmedClusterDataProtectionSwitchingLinkRxtxhistportA Unsigned32,
        affirmedClusterDataProtectionSwitchingLinkLastrxtxportB Unsigned32,
        affirmedClusterDataProtectionSwitchingLinkRxhistportB Unsigned32,
        affirmedClusterDataProtectionSwitchingLinkRxtxhistportB Unsigned32
    }

affirmedClusterDataProtectionSwitchingLinkNodeid OBJECT-TYPE
    SYNTAX      Unsigned32
    MAX-ACCESS  not-accessible
    STATUS      current
    DESCRIPTION "local node id"
    ::= { affirmedClusterDataProtectionSwitchingLinkEntry 1 }

affirmedClusterDataProtectionSwitchingLinkPeernodeid OBJECT-TYPE
    SYNTAX      Unsigned32
    MAX-ACCESS  not-accessible
    STATUS      current
    DESCRIPTION "peer node id"
    ::= { affirmedClusterDataProtectionSwitchingLinkEntry 2 }

affirmedClusterDataProtectionSwitchingLinkLastrxportA OBJECT-TYPE
    SYNTAX      Unsigned32
    MAX-ACCESS  read-only
    STATUS      current
    DESCRIPTION "Last Rx port A"
    ::= { affirmedClusterDataProtectionSwitchingLinkEntry 3 }

affirmedClusterDataProtectionSwitchingLinkLastrxportB OBJECT-TYPE
    SYNTAX      Unsigned32
    MAX-ACCESS  read-only
    STATUS      current
    DESCRIPTION "Last Rx port B"
    ::= { affirmedClusterDataProtectionSwitchingLinkEntry 4 }

affirmedClusterDataProtectionSwitchingLinkLastrxtxportA OBJECT-TYPE
    SYNTAX      Unsigned32
    MAX-ACCESS  read-only
    STATUS      current
    DESCRIPTION "Last Rx+Tx port A"
    ::= { affirmedClusterDataProtectionSwitchingLinkEntry 5 }

affirmedClusterDataProtectionSwitchingLinkRxhistportA OBJECT-TYPE
    SYNTAX      Unsigned32
    MAX-ACCESS  read-only
    STATUS      current
    DESCRIPTION "5 minute percent Rx port A"
    ::= { affirmedClusterDataProtectionSwitchingLinkEntry 6 }

affirmedClusterDataProtectionSwitchingLinkRxtxhistportA OBJECT-TYPE
    SYNTAX      Unsigned32
    MAX-ACCESS  read-only
    STATUS      current
    DESCRIPTION "5 minute percent Rx+Tx port A"
    ::= { affirmedClusterDataProtectionSwitchingLinkEntry 7 }

affirmedClusterDataProtectionSwitchingLinkLastrxtxportB OBJECT-TYPE
    SYNTAX      Unsigned32
    MAX-ACCESS  read-only
    STATUS      current
    DESCRIPTION "Last Rx+Tx port B"
    ::= { affirmedClusterDataProtectionSwitchingLinkEntry 8 }

affirmedClusterDataProtectionSwitchingLinkRxhistportB OBJECT-TYPE
    SYNTAX      Unsigned32
    MAX-ACCESS  read-only
    STATUS      current
    DESCRIPTION "5 minute percent Rx port B"
    ::= { affirmedClusterDataProtectionSwitchingLinkEntry 9 }

affirmedClusterDataProtectionSwitchingLinkRxtxhistportB OBJECT-TYPE
    SYNTAX      Unsigned32
    MAX-ACCESS  read-only
    STATUS      current
    DESCRIPTION "5 minute percent Rx+Tx port B"
    ::= { affirmedClusterDataProtectionSwitchingLinkEntry 10 }

affirmedClusterBaseProtectionSwitchingStatusTable OBJECT-TYPE
    SYNTAX      SEQUENCE OF AffirmedClusterBaseProtectionSwitchingStatusEntry
    MAX-ACCESS  not-accessible
    STATUS      current
    DESCRIPTION ""
    ::= { affirmedClusterMIB 4 }

affirmedClusterBaseProtectionSwitchingStatusEntry OBJECT-TYPE
    SYNTAX      AffirmedClusterBaseProtectionSwitchingStatusEntry
    MAX-ACCESS  not-accessible
    STATUS      current
    DESCRIPTION ""
    INDEX { affirmedClusterId, affirmedClusterBaseProtectionSwitchingStatusNodeid }
        ::= { affirmedClusterBaseProtectionSwitchingStatusTable 1 }

AffirmedClusterBaseProtectionSwitchingStatusEntry ::=
    SEQUENCE {
        affirmedClusterBaseProtectionSwitchingStatusNodeid Unsigned32,
        affirmedClusterBaseProtectionSwitchingStatusUsingport INTEGER,
        affirmedClusterBaseProtectionSwitchingStatusNumswitchover Unsigned32,
        affirmedClusterBaseProtectionSwitchingStatusLastswitchover ConfdString,
        affirmedClusterBaseProtectionSwitchingStatusPathbitMapA String,
        affirmedClusterBaseProtectionSwitchingStatusPathbitMapB String,
        affirmedClusterBaseProtectionSwitchingStatusSwitchovercause String
    }

affirmedClusterBaseProtectionSwitchingStatusNodeid OBJECT-TYPE
    SYNTAX      Unsigned32
    MAX-ACCESS  not-accessible
    STATUS      current
    DESCRIPTION "node id"
    ::= { affirmedClusterBaseProtectionSwitchingStatusEntry 1 }

affirmedClusterBaseProtectionSwitchingStatusUsingport OBJECT-TYPE
    SYNTAX      INTEGER {port-A(0),port-B(1),port-A-B(2)}
    MAX-ACCESS  read-only
    STATUS      current
    DESCRIPTION "Using Port"
    ::= { affirmedClusterBaseProtectionSwitchingStatusEntry 2 }

affirmedClusterBaseProtectionSwitchingStatusNumswitchover OBJECT-TYPE
    SYNTAX      Unsigned32
    MAX-ACCESS  read-only
    STATUS      current
    DESCRIPTION "Number of switchover events"
    ::= { affirmedClusterBaseProtectionSwitchingStatusEntry 3 }

affirmedClusterBaseProtectionSwitchingStatusLastswitchover OBJECT-TYPE
    SYNTAX      ConfdString
    MAX-ACCESS  read-only
    STATUS      current
    DESCRIPTION "Elapsed time since most recent switchover in Ms"
    ::= { affirmedClusterBaseProtectionSwitchingStatusEntry 4 }

affirmedClusterBaseProtectionSwitchingStatusPathbitMapA OBJECT-TYPE
    SYNTAX      String
    MAX-ACCESS  read-only
    STATUS      current
    DESCRIPTION "Bitmap of reachable nodes over port A"
    ::= { affirmedClusterBaseProtectionSwitchingStatusEntry 5 }

affirmedClusterBaseProtectionSwitchingStatusPathbitMapB OBJECT-TYPE
    SYNTAX      String
    MAX-ACCESS  read-only
    STATUS      current
    DESCRIPTION "Bitmap of reachable nodes over port B"
    ::= { affirmedClusterBaseProtectionSwitchingStatusEntry 6 }

affirmedClusterBaseProtectionSwitchingStatusSwitchovercause OBJECT-TYPE
    SYNTAX      String
    MAX-ACCESS  read-only
    STATUS      current
    DESCRIPTION "Cause of most recent switchover"
    ::= { affirmedClusterBaseProtectionSwitchingStatusEntry 7 }

affirmedClusterBaseProtectionSwitchingLinkTable OBJECT-TYPE
    SYNTAX      SEQUENCE OF AffirmedClusterBaseProtectionSwitchingLinkEntry
    MAX-ACCESS  not-accessible
    STATUS      current
    DESCRIPTION ""
    ::= { affirmedClusterMIB 5 }

affirmedClusterBaseProtectionSwitchingLinkEntry OBJECT-TYPE
    SYNTAX      AffirmedClusterBaseProtectionSwitchingLinkEntry
    MAX-ACCESS  not-accessible
    STATUS      current
    DESCRIPTION ""
    INDEX { affirmedClusterId, affirmedClusterBaseProtectionSwitchingLinkNodeid, affirmedClusterBaseProtectionSwitchingLinkPeernodeid }
        ::= { affirmedClusterBaseProtectionSwitchingLinkTable 1 }

AffirmedClusterBaseProtectionSwitchingLinkEntry ::=
    SEQUENCE {
        affirmedClusterBaseProtectionSwitchingLinkNodeid Unsigned32,
        affirmedClusterBaseProtectionSwitchingLinkPeernodeid Unsigned32,
        affirmedClusterBaseProtectionSwitchingLinkLastrxportA Unsigned32,
        affirmedClusterBaseProtectionSwitchingLinkLastrxportB Unsigned32,
        affirmedClusterBaseProtectionSwitchingLinkLastrxtxportA Unsigned32,
        affirmedClusterBaseProtectionSwitchingLinkRxhistportA Unsigned32,
        affirmedClusterBaseProtectionSwitchingLinkRxtxhistportA Unsigned32,
        affirmedClusterBaseProtectionSwitchingLinkLastrxtxportB Unsigned32,
        affirmedClusterBaseProtectionSwitchingLinkRxhistportB Unsigned32,
        affirmedClusterBaseProtectionSwitchingLinkRxtxhistportB Unsigned32
    }

affirmedClusterBaseProtectionSwitchingLinkNodeid OBJECT-TYPE
    SYNTAX      Unsigned32
    MAX-ACCESS  not-accessible
    STATUS      current
    DESCRIPTION "local node id"
    ::= { affirmedClusterBaseProtectionSwitchingLinkEntry 1 }

affirmedClusterBaseProtectionSwitchingLinkPeernodeid OBJECT-TYPE
    SYNTAX      Unsigned32
    MAX-ACCESS  not-accessible
    STATUS      current
    DESCRIPTION "peer node id"
    ::= { affirmedClusterBaseProtectionSwitchingLinkEntry 2 }

affirmedClusterBaseProtectionSwitchingLinkLastrxportA OBJECT-TYPE
    SYNTAX      Unsigned32
    MAX-ACCESS  read-only
    STATUS      current
    DESCRIPTION "Last Rx port A"
    ::= { affirmedClusterBaseProtectionSwitchingLinkEntry 3 }

affirmedClusterBaseProtectionSwitchingLinkLastrxportB OBJECT-TYPE
    SYNTAX      Unsigned32
    MAX-ACCESS  read-only
    STATUS      current
    DESCRIPTION "Last Rx port B"
    ::= { affirmedClusterBaseProtectionSwitchingLinkEntry 4 }

affirmedClusterBaseProtectionSwitchingLinkLastrxtxportA OBJECT-TYPE
    SYNTAX      Unsigned32
    MAX-ACCESS  read-only
    STATUS      current
    DESCRIPTION "Last Rx+Tx port A"
    ::= { affirmedClusterBaseProtectionSwitchingLinkEntry 5 }

affirmedClusterBaseProtectionSwitchingLinkRxhistportA OBJECT-TYPE
    SYNTAX      Unsigned32
    MAX-ACCESS  read-only
    STATUS      current
    DESCRIPTION "5 minute percent Rx port A"
    ::= { affirmedClusterBaseProtectionSwitchingLinkEntry 6 }

affirmedClusterBaseProtectionSwitchingLinkRxtxhistportA OBJECT-TYPE
    SYNTAX      Unsigned32
    MAX-ACCESS  read-only
    STATUS      current
    DESCRIPTION "5 minute percent Rx+Tx port A"
    ::= { affirmedClusterBaseProtectionSwitchingLinkEntry 7 }

affirmedClusterBaseProtectionSwitchingLinkLastrxtxportB OBJECT-TYPE
    SYNTAX      Unsigned32
    MAX-ACCESS  read-only
    STATUS      current
    DESCRIPTION "Last Rx+Tx port B"
    ::= { affirmedClusterBaseProtectionSwitchingLinkEntry 8 }

affirmedClusterBaseProtectionSwitchingLinkRxhistportB OBJECT-TYPE
    SYNTAX      Unsigned32
    MAX-ACCESS  read-only
    STATUS      current
    DESCRIPTION "5 minute percent Rx port B"
    ::= { affirmedClusterBaseProtectionSwitchingLinkEntry 9 }

affirmedClusterBaseProtectionSwitchingLinkRxtxhistportB OBJECT-TYPE
    SYNTAX      Unsigned32
    MAX-ACCESS  read-only
    STATUS      current
    DESCRIPTION "5 minute percent Rx+Tx port B"
    ::= { affirmedClusterBaseProtectionSwitchingLinkEntry 10 }

END

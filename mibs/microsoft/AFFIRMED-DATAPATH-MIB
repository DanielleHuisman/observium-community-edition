AFFIRMED-DATAPATH-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedDatapathMIB MODULE-IDENTITY
    ORGANIZATION "Affirmed Networks, Inc."
    CONTACT-INFO "Affirmed Networks, Inc. 35 Nagog Park, Acton, MA, USA"
    DESCRIPTION ""
    ::= { 1 3 6 1 4 1 37963 10 22 }

ConfdString ::= TEXTUAL-CONVENTION
    DISPLAY-HINT "1t"
    STATUS      current
    DESCRIPTION "xs: and confd: types mapped to strings"
    SYNTAX      OCTET STRING

affirmedPerf-statistics OBJECT IDENTIFIER ::= { affirmedDatapathMIB 2 }

affirmedPerf-statisticsIpfrag OBJECT IDENTIFIER ::= { affirmedPerf-statistics 1 }

affirmedPerf-statisticsIpfragModule-statsTable OBJECT-TYPE
    SYNTAX      SEQUENCE OF AffirmedPerf-statisticsIpfragModule-statsEntry
    MAX-ACCESS  not-accessible
    STATUS      current
    DESCRIPTION ""
    ::= { affirmedPerf-statisticsIpfrag 1 }

affirmedPerf-statisticsIpfragModule-statsEntry OBJECT-TYPE
    SYNTAX      AffirmedPerf-statisticsIpfragModule-statsEntry
    MAX-ACCESS  not-accessible
    STATUS      current
    DESCRIPTION ""
    INDEX { affirmedPerf-statisticsIpfragModule-statsChassis, affirmedPerf-statisticsIpfragModule-statsSlot }
        ::= { affirmedPerf-statisticsIpfragModule-statsTable 1 }

AffirmedPerf-statisticsIpfragModule-statsEntry ::=
    SEQUENCE {
        affirmedPerf-statisticsIpfragModule-statsChassis Unsigned32,
        affirmedPerf-statisticsIpfragModule-statsSlot Unsigned32,
        affirmedPerf-statisticsIpfragModule-statsNumFragIpv4PktRcvd ConfdString,
        affirmedPerf-statisticsIpfragModule-statsNumIpv4FragAged ConfdString,
        affirmedPerf-statisticsIpfragModule-statsNumReassembledIpv4Pkt ConfdString,
        affirmedPerf-statisticsIpfragModule-statsNumRefragmentIpv4Pkt ConfdString,
        affirmedPerf-statisticsIpfragModule-statsNumFragIpv6PktRcvd ConfdString,
        affirmedPerf-statisticsIpfragModule-statsNumIpv6FragAged ConfdString,
        affirmedPerf-statisticsIpfragModule-statsNumReassembledIpv6Pkt ConfdString,
        affirmedPerf-statisticsIpfragModule-statsNumRefragmentIpv6Pkt ConfdString,
        affirmedPerf-statisticsIpfragModule-statsNumGetBufferFail ConfdString
    }

affirmedPerf-statisticsIpfragModule-statsChassis OBJECT-TYPE
    SYNTAX      Unsigned32
    MAX-ACCESS  not-accessible
    STATUS      current
    DESCRIPTION "chassis id"
    ::= { affirmedPerf-statisticsIpfragModule-statsEntry 1 }

affirmedPerf-statisticsIpfragModule-statsSlot OBJECT-TYPE
    SYNTAX      Unsigned32
    MAX-ACCESS  not-accessible
    STATUS      current
    DESCRIPTION "slot id"
    ::= { affirmedPerf-statisticsIpfragModule-statsEntry 2 }

affirmedPerf-statisticsIpfragModule-statsNumFragIpv4PktRcvd OBJECT-TYPE
    SYNTAX      ConfdString
    MAX-ACCESS  read-only
    STATUS      current
    DESCRIPTION "Total number of fragmented IPv4 packets received"
    ::= { affirmedPerf-statisticsIpfragModule-statsEntry 3 }

affirmedPerf-statisticsIpfragModule-statsNumIpv4FragAged OBJECT-TYPE
    SYNTAX      ConfdString
    MAX-ACCESS  read-only
    STATUS      current
    DESCRIPTION "Total number of IPv4 fragment reassembly CB aged"
    ::= { affirmedPerf-statisticsIpfragModule-statsEntry 4 }

affirmedPerf-statisticsIpfragModule-statsNumReassembledIpv4Pkt OBJECT-TYPE
    SYNTAX      ConfdString
    MAX-ACCESS  read-only
    STATUS      current
    DESCRIPTION "Total number of IPv4 fragment reassembly complete"
    ::= { affirmedPerf-statisticsIpfragModule-statsEntry 5 }

affirmedPerf-statisticsIpfragModule-statsNumRefragmentIpv4Pkt OBJECT-TYPE
    SYNTAX      ConfdString
    MAX-ACCESS  read-only
    STATUS      current
    DESCRIPTION "Total number of IPv4 refragment attempts"
    ::= { affirmedPerf-statisticsIpfragModule-statsEntry 6 }

affirmedPerf-statisticsIpfragModule-statsNumFragIpv6PktRcvd OBJECT-TYPE
    SYNTAX      ConfdString
    MAX-ACCESS  read-only
    STATUS      current
    DESCRIPTION "Total number of fragmented IPv6 packets received"
    ::= { affirmedPerf-statisticsIpfragModule-statsEntry 7 }

affirmedPerf-statisticsIpfragModule-statsNumIpv6FragAged OBJECT-TYPE
    SYNTAX      ConfdString
    MAX-ACCESS  read-only
    STATUS      current
    DESCRIPTION "Total number of IPv6 fragment reassembly CB aged"
    ::= { affirmedPerf-statisticsIpfragModule-statsEntry 8 }

affirmedPerf-statisticsIpfragModule-statsNumReassembledIpv6Pkt OBJECT-TYPE
    SYNTAX      ConfdString
    MAX-ACCESS  read-only
    STATUS      current
    DESCRIPTION "Total number of IPv6 fragment reassembly complete"
    ::= { affirmedPerf-statisticsIpfragModule-statsEntry 9 }

affirmedPerf-statisticsIpfragModule-statsNumRefragmentIpv6Pkt OBJECT-TYPE
    SYNTAX      ConfdString
    MAX-ACCESS  read-only
    STATUS      current
    DESCRIPTION "Total number of IPv6 refragment attempts"
    ::= { affirmedPerf-statisticsIpfragModule-statsEntry 10 }

affirmedPerf-statisticsIpfragModule-statsNumGetBufferFail OBJECT-TYPE
    SYNTAX      ConfdString
    MAX-ACCESS  read-only
    STATUS      current
    DESCRIPTION "Total number of getBuffer attempts failure"
    ::= { affirmedPerf-statisticsIpfragModule-statsEntry 11 }

END

AFFIRMED-DATAPLANESTATS-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedDataplaneStatsMIB MODULE-IDENTITY
    ORGANIZATION "Affirmed Networks, Inc."
    CONTACT-INFO "Affirmed Networks, Inc. 35 Nagog Park, Acton, MA, USA"
    DESCRIPTION ""
    ::= { 1 3 6 1 4 1 37963 10 17 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedDataplane OBJECT IDENTIFIER ::= { affirmedDataplaneStatsMIB 1 }

affirmedDataplaneApnDataStatsTable OBJECT-TYPE
    SYNTAX      SEQUENCE OF AffirmedDataplaneApnDataStatsEntry
    MAX-ACCESS  not-accessible
    STATUS      deprecated
    DESCRIPTION ""
    ::= { affirmedDataplane 1 }

affirmedDataplaneApnDataStatsEntry OBJECT-TYPE
    SYNTAX      AffirmedDataplaneApnDataStatsEntry
    MAX-ACCESS  not-accessible
    STATUS      deprecated
    DESCRIPTION ""
    INDEX { affirmedDataplaneApnDataStatsName }
        ::= { affirmedDataplaneApnDataStatsTable 1 }

AffirmedDataplaneApnDataStatsEntry ::=
    SEQUENCE {
        affirmedDataplaneApnDataStatsName String,
        affirmedDataplaneApnDataStatsUplinkPackets ConfdString,
        affirmedDataplaneApnDataStatsUplinkBytes ConfdString,
        affirmedDataplaneApnDataStatsUplinkDropPackets ConfdString,
        affirmedDataplaneApnDataStatsUplinkDropBytes ConfdString,
        affirmedDataplaneApnDataStatsDownlinkPackets ConfdString,
        affirmedDataplaneApnDataStatsDownlinkBytes ConfdString,
        affirmedDataplaneApnDataStatsDownlinkDropPackets ConfdString,
        affirmedDataplaneApnDataStatsDownlinkDropBytes ConfdString
    }

affirmedDataplaneApnDataStatsName OBJECT-TYPE
    SYNTAX      String
    MAX-ACCESS  not-accessible
    STATUS      current
    DESCRIPTION "APN Name"
    ::= { affirmedDataplaneApnDataStatsEntry 1 }

affirmedDataplaneApnDataStatsUplinkPackets OBJECT-TYPE
    SYNTAX      ConfdString
    MAX-ACCESS  read-only
    STATUS      current
    DESCRIPTION "uplink packets received"
    ::= { affirmedDataplaneApnDataStatsEntry 2 }

affirmedDataplaneApnDataStatsUplinkBytes OBJECT-TYPE
    SYNTAX      ConfdString
    MAX-ACCESS  read-only
    STATUS      current
    DESCRIPTION "uplink bytes received"
    ::= { affirmedDataplaneApnDataStatsEntry 3 }

affirmedDataplaneApnDataStatsUplinkDropPackets OBJECT-TYPE
    SYNTAX      ConfdString
    MAX-ACCESS  read-only
    STATUS      current
    DESCRIPTION "uplink packets dropped"
    ::= { affirmedDataplaneApnDataStatsEntry 4 }

affirmedDataplaneApnDataStatsUplinkDropBytes OBJECT-TYPE
    SYNTAX      ConfdString
    MAX-ACCESS  read-only
    STATUS      current
    DESCRIPTION "uplink bytes dropped"
    ::= { affirmedDataplaneApnDataStatsEntry 5 }

affirmedDataplaneApnDataStatsDownlinkPackets OBJECT-TYPE
    SYNTAX      ConfdString
    MAX-ACCESS  read-only
    STATUS      current
    DESCRIPTION "downlink packets received"
    ::= { affirmedDataplaneApnDataStatsEntry 6 }

affirmedDataplaneApnDataStatsDownlinkBytes OBJECT-TYPE
    SYNTAX      ConfdString
    MAX-ACCESS  read-only
    STATUS      current
    DESCRIPTION "downlink bytes received"
    ::= { affirmedDataplaneApnDataStatsEntry 7 }

affirmedDataplaneApnDataStatsDownlinkDropPackets OBJECT-TYPE
    SYNTAX      ConfdString
    MAX-ACCESS  read-only
    STATUS      current
    DESCRIPTION "downlink packets dropped"
    ::= { affirmedDataplaneApnDataStatsEntry 8 }

affirmedDataplaneApnDataStatsDownlinkDropBytes OBJECT-TYPE
    SYNTAX      ConfdString
    MAX-ACCESS  read-only
    STATUS      current
    DESCRIPTION "downlink bytes dropped"
    ::= { affirmedDataplaneApnDataStatsEntry 9 }

END

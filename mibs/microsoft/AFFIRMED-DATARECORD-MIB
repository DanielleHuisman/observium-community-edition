AFFIRMED-DATARECORD-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedDatarecordMIB MODULE-IDENTITY
    ORGANIZATION "Affirmed Networks, Inc."
    CONTACT-INFO "Affirmed Networks, Inc. 35 Nagog Park, Acton, MA, USA"
    DESCRIPTION ""
    ::= { 1 3 6 1 4 1 37963 10 21 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedDatarecord OBJECT IDENTIFIER ::= { affirmedDatarecordMIB 1 }

affirmedDatarecordStatisticsTable OBJECT-TYPE
    SYNTAX      SEQUENCE OF AffirmedDatarecordStatisticsEntry
    MAX-ACCESS  not-accessible
    STATUS      current
    DESCRIPTION ""
    ::= { affirmedDatarecord 1 }

affirmedDatarecordStatisticsEntry OBJECT-TYPE
    SYNTAX      AffirmedDatarecordStatisticsEntry
    MAX-ACCESS  not-accessible
    STATUS      current
    DESCRIPTION ""
    INDEX { affirmedDatarecordStatisticsAgent }
        ::= { affirmedDatarecordStatisticsTable 1 }

AffirmedDatarecordStatisticsEntry ::=
    SEQUENCE {
        affirmedDatarecordStatisticsAgent String,
        affirmedDatarecordStatisticsRecordsWritten ConfdString,
        affirmedDatarecordStatisticsRecordsFailed ConfdString
    }

affirmedDatarecordStatisticsAgent OBJECT-TYPE
    SYNTAX      String
    MAX-ACCESS  not-accessible
    STATUS      current
    DESCRIPTION "Name of Agent task"
    ::= { affirmedDatarecordStatisticsEntry 1 }

affirmedDatarecordStatisticsRecordsWritten OBJECT-TYPE
    SYNTAX      ConfdString
    MAX-ACCESS  read-only
    STATUS      current
    DESCRIPTION "Total Number of records written to disk"
    ::= { affirmedDatarecordStatisticsEntry 2 }

affirmedDatarecordStatisticsRecordsFailed OBJECT-TYPE
    SYNTAX      ConfdString
    MAX-ACCESS  read-only
    STATUS      current
    DESCRIPTION "Total Records failed"
    ::= { affirmedDatarecordStatisticsEntry 3 }

affirmedDatarecordDetailTable OBJECT-TYPE
    SYNTAX      SEQUENCE OF AffirmedDatarecordDetailEntry
    MAX-ACCESS  not-accessible
    STATUS      current
    DESCRIPTION ""
    ::= { affirmedDatarecord 2 }

affirmedDatarecordDetailEntry OBJECT-TYPE
    SYNTAX      AffirmedDatarecordDetailEntry
    MAX-ACCESS  not-accessible
    STATUS      current
    DESCRIPTION ""
    INDEX { affirmedDatarecordDetailAgent, affirmedDatarecordDetailSource }
        ::= { affirmedDatarecordDetailTable 1 }

AffirmedDatarecordDetailEntry ::=
    SEQUENCE {
        affirmedDatarecordDetailAgent String,
        affirmedDatarecordDetailSource String,
        affirmedDatarecordDetailRecordsAttempted ConfdString,
        affirmedDatarecordDetailRecordsFailed ConfdString,
        affirmedDatarecordDetailRecordsSucceeded ConfdString,
        affirmedDatarecordDetailRecordsWritten ConfdString,
        affirmedDatarecordDetailRecordsWriteFailed ConfdString
    }

affirmedDatarecordDetailAgent OBJECT-TYPE
    SYNTAX      String
    MAX-ACCESS  not-accessible
    STATUS      current
    DESCRIPTION "Name of agent task receiving the records"
    ::= { affirmedDatarecordDetailEntry 1 }

affirmedDatarecordDetailSource OBJECT-TYPE
    SYNTAX      String
    MAX-ACCESS  not-accessible
    STATUS      current
    DESCRIPTION "Name of task generating the records"
    ::= { affirmedDatarecordDetailEntry 2 }

affirmedDatarecordDetailRecordsAttempted OBJECT-TYPE
    SYNTAX      ConfdString
    MAX-ACCESS  read-only
    STATUS      current
    DESCRIPTION "Data Records Attempts made"
    ::= { affirmedDatarecordDetailEntry 3 }

affirmedDatarecordDetailRecordsFailed OBJECT-TYPE
    SYNTAX      ConfdString
    MAX-ACCESS  read-only
    STATUS      current
    DESCRIPTION "Number of records for which send to agent failed"
    ::= { affirmedDatarecordDetailEntry 4 }

affirmedDatarecordDetailRecordsSucceeded OBJECT-TYPE
    SYNTAX      ConfdString
    MAX-ACCESS  read-only
    STATUS      current
    DESCRIPTION "Number of records for which send to agent succeeded"
    ::= { affirmedDatarecordDetailEntry 5 }

affirmedDatarecordDetailRecordsWritten OBJECT-TYPE
    SYNTAX      ConfdString
    MAX-ACCESS  read-only
    STATUS      current
    DESCRIPTION "Number of records written to disk"
    ::= { affirmedDatarecordDetailEntry 6 }

affirmedDatarecordDetailRecordsWriteFailed OBJECT-TYPE
    SYNTAX      ConfdString
    MAX-ACCESS  read-only
    STATUS      current
    DESCRIPTION "Number of records for which write failed"
    ::= { affirmedDatarecordDetailEntry 7 }

END

AFFIRMED-EXTSTORAGE-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedExtstorageMIB MODULE-IDENTITY
    ORGANIZATION "Affirmed Networks, Inc."
    CONTACT-INFO "Affirmed Networks, Inc. 35 Nagog Park, Acton, MA, USA"
    DESCRIPTION ""
    ::= { 1 3 6 1 4 1 37963 10 20 }

String ::= TEXTUAL-CONVENTION
    DISPLAY-HINT "1t"
    STATUS      current
    DESCRIPTION "xs:string"
    SYNTAX      OCTET STRING

affirmedExtstorage OBJECT IDENTIFIER ::= { affirmedExtstorageMIB 1 }

affirmedExtstorageStatusTable OBJECT-TYPE
    SYNTAX      SEQUENCE OF AffirmedExtstorageStatusEntry
    MAX-ACCESS  not-accessible
    STATUS      current
    DESCRIPTION ""
    ::= { affirmedExtstorage 1 }

affirmedExtstorageStatusEntry OBJECT-TYPE
    SYNTAX      AffirmedExtstorageStatusEntry
    MAX-ACCESS  not-accessible
    STATUS      current
    DESCRIPTION ""
    INDEX { affirmedExtstorageStatusState, affirmedExtstorageStatusChassis, affirmedExtstorageStatusSlot }
        ::= { affirmedExtstorageStatusTable 1 }

AffirmedExtstorageStatusEntry ::=
    SEQUENCE {
        affirmedExtstorageStatusState INTEGER,
        affirmedExtstorageStatusChassis Unsigned32,
        affirmedExtstorageStatusSlot Unsigned32,
        affirmedExtstorageStatusAdminstate String,
        affirmedExtstorageStatusOperstatus String,
        affirmedExtstorageStatusDiskPartition String,
        affirmedExtstorageStatusCurrentOperation String,
        affirmedExtstorageStatusCurrentState String
    }

affirmedExtstorageStatusState OBJECT-TYPE
    SYNTAX      INTEGER {active(1),standby(2),n-a(3)}
    MAX-ACCESS  not-accessible
    STATUS      current
    DESCRIPTION ""
    ::= { affirmedExtstorageStatusEntry 1 }

affirmedExtstorageStatusChassis OBJECT-TYPE
    SYNTAX      Unsigned32
    MAX-ACCESS  not-accessible
    STATUS      current
    DESCRIPTION ""
    ::= { affirmedExtstorageStatusEntry 2 }

affirmedExtstorageStatusSlot OBJECT-TYPE
    SYNTAX      Unsigned32
    MAX-ACCESS  not-accessible
    STATUS      current
    DESCRIPTION ""
    ::= { affirmedExtstorageStatusEntry 3 }

affirmedExtstorageStatusAdminstate OBJECT-TYPE
    SYNTAX      String
    MAX-ACCESS  read-only
    STATUS      current
    DESCRIPTION "Admin State "
    ::= { affirmedExtstorageStatusEntry 4 }

affirmedExtstorageStatusOperstatus OBJECT-TYPE
    SYNTAX      String
    MAX-ACCESS  read-only
    STATUS      current
    DESCRIPTION "Operational Status "
    ::= { affirmedExtstorageStatusEntry 5 }

affirmedExtstorageStatusDiskPartition OBJECT-TYPE
    SYNTAX      String
    MAX-ACCESS  read-only
    STATUS      current
    DESCRIPTION "Current ext-storage disk partition"
    ::= { affirmedExtstorageStatusEntry 6 }

affirmedExtstorageStatusCurrentOperation OBJECT-TYPE
    SYNTAX      String
    MAX-ACCESS  read-only
    STATUS      current
    DESCRIPTION "Current disk operation"
    ::= { affirmedExtstorageStatusEntry 7 }

affirmedExtstorageStatusCurrentState OBJECT-TYPE
    SYNTAX      String
    MAX-ACCESS  read-only
    STATUS      current
    DESCRIPTION "Current disk operation state"
    ::= { affirmedExtstorageStatusEntry 8 }

END

AFFIRMED-FM-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedFmMIB MODULE-IDENTITY
    ORGANIZATION "Affirmed Networks, Inc."
    CONTACT-INFO "Affirmed Networks, Inc. 35 Nagog Park, Acton, MA, USA"
    DESCRIPTION ""
    ::= { 1 3 6 1 4 1 37963 10 5 }

String ::= TEXTUAL-CONVENTION
    DISPLAY-HINT "1t"
    STATUS      current
    DESCRIPTION "xs:string"
    SYNTAX      OCTET STRING

affirmedFm OBJECT IDENTIFIER ::= { affirmedFmMIB 1 }

affirmedFmHistoryTable OBJECT-TYPE
    SYNTAX      SEQUENCE OF AffirmedFmHistoryEntry
    MAX-ACCESS  not-accessible
    STATUS      current
    DESCRIPTION ""
    ::= { affirmedFm 1 }

affirmedFmHistoryEntry OBJECT-TYPE
    SYNTAX      AffirmedFmHistoryEntry
    MAX-ACCESS  not-accessible
    STATUS      current
    DESCRIPTION ""
    INDEX { affirmedFmHistoryDateTime, affirmedFmHistorySlotNumber, affirmedFmHistoryCpuNumber }
        ::= { affirmedFmHistoryTable 1 }

AffirmedFmHistoryEntry ::=
    SEQUENCE {
        affirmedFmHistoryDateTime String,
        affirmedFmHistorySlotNumber Integer32,
        affirmedFmHistoryCpuNumber Integer32,
        affirmedFmHistoryFaultAction String
    }

affirmedFmHistoryDateTime OBJECT-TYPE
    SYNTAX      String
    MAX-ACCESS  not-accessible
    STATUS      current
    DESCRIPTION ""
    ::= { affirmedFmHistoryEntry 1 }

affirmedFmHistorySlotNumber OBJECT-TYPE
    SYNTAX      Integer32
    MAX-ACCESS  not-accessible
    STATUS      current
    DESCRIPTION ""
    ::= { affirmedFmHistoryEntry 2 }

affirmedFmHistoryCpuNumber OBJECT-TYPE
    SYNTAX      Integer32
    MAX-ACCESS  not-accessible
    STATUS      current
    DESCRIPTION ""
    ::= { affirmedFmHistoryEntry 3 }

affirmedFmHistoryFaultAction OBJECT-TYPE
    SYNTAX      String
    MAX-ACCESS  read-only
    STATUS      current
    DESCRIPTION ""
    ::= { affirmedFmHistoryEntry 4 }

END

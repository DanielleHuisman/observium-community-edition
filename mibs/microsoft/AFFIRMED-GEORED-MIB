AFFIRMED-GEORED-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedGeoredMIB MODULE-IDENTITY
    ORGANIZATION "Affirmed Networks, Inc."
    CONTACT-INFO "Affirmed Networks, Inc. 35 Nagog Park, Acton, MA, USA"
    DESCRIPTION ""
    ::= { 1 3 6 1 4 1 37963 10 7 }

String ::= TEXTUAL-CONVENTION
    DISPLAY-HINT "1t"
    STATUS      current
    DESCRIPTION "xs:string"
    SYNTAX      OCTET STRING

affirmedGeographicRedundancy OBJECT IDENTIFIER ::= { affirmedGeoredMIB 1 }

affirmedGeographicRedundancyRedundancyGroupStatsTable OBJECT-TYPE
    SYNTAX      SEQUENCE OF AffirmedGeographicRedundancyRedundancyGroupStatsEntry
    MAX-ACCESS  not-accessible
    STATUS      current
    DESCRIPTION ""
    ::= { affirmedGeographicRedundancy 1 }

affirmedGeographicRedundancyRedundancyGroupStatsEntry OBJECT-TYPE
    SYNTAX      AffirmedGeographicRedundancyRedundancyGroupStatsEntry
    MAX-ACCESS  not-accessible
    STATUS      current
    DESCRIPTION ""
    INDEX { affirmedGeographicRedundancyRedundancyGroupStatsName }
        ::= { affirmedGeographicRedundancyRedundancyGroupStatsTable 1 }

AffirmedGeographicRedundancyRedundancyGroupStatsEntry ::=
    SEQUENCE {
        affirmedGeographicRedundancyRedundancyGroupStatsName String,
        affirmedGeographicRedundancyRedundancyGroupStatsAdminState INTEGER,
        affirmedGeographicRedundancyRedundancyGroupStatsGroupId Unsigned32,
        affirmedGeographicRedundancyRedundancyGroupStatsConfiguredHaState INTEGER,
        affirmedGeographicRedundancyRedundancyGroupStatsHaMode INTEGER,
        affirmedGeographicRedundancyRedundancyGroupStatsActualHAState INTEGER,
        affirmedGeographicRedundancyRedundancyGroupStatsRuntimeHAState INTEGER,
        affirmedGeographicRedundancyRedundancyGroupStatsOperState INTEGER,
        affirmedGeographicRedundancyRedundancyGroupStatsNumSyncRecords Unsigned32,
        affirmedGeographicRedundancyRedundancyGroupStatsPeerConnectionStatus INTEGER,
        affirmedGeographicRedundancyRedundancyGroupStatsPeerRuntimeHAState INTEGER,
        affirmedGeographicRedundancyRedundancyGroupStatsPeerOperState INTEGER,
        affirmedGeographicRedundancyRedundancyGroupStatsPeerNumSyncRecords Unsigned32
    }

affirmedGeographicRedundancyRedundancyGroupStatsName OBJECT-TYPE
    SYNTAX      String
    MAX-ACCESS  not-accessible
    STATUS      current
    DESCRIPTION "Redundancy Name"
    ::= { affirmedGeographicRedundancyRedundancyGroupStatsEntry 1 }

affirmedGeographicRedundancyRedundancyGroupStatsAdminState OBJECT-TYPE
    SYNTAX      INTEGER {disabled(0),enabled(1)}
    MAX-ACCESS  read-only
    STATUS      current
    DESCRIPTION "Active state"
    ::= { affirmedGeographicRedundancyRedundancyGroupStatsEntry 2 }

affirmedGeographicRedundancyRedundancyGroupStatsGroupId OBJECT-TYPE
    SYNTAX      Unsigned32
    MAX-ACCESS  read-only
    STATUS      current
    DESCRIPTION "Unique group id[1..7], must match with peer"
    ::= { affirmedGeographicRedundancyRedundancyGroupStatsEntry 3 }

affirmedGeographicRedundancyRedundancyGroupStatsConfiguredHaState OBJECT-TYPE
    SYNTAX      INTEGER {primary(1),secondary(2)}
    MAX-ACCESS  read-only
    STATUS      current
    DESCRIPTION "This instance Configured HA state. Intended backup role"
    ::= { affirmedGeographicRedundancyRedundancyGroupStatsEntry 4 }

affirmedGeographicRedundancyRedundancyGroupStatsHaMode OBJECT-TYPE
    SYNTAX      INTEGER {warm-manual(1),hot-auto(2),hot-manual(3)}
    MAX-ACCESS  read-only
    STATUS      current
    DESCRIPTION "This instance Configured HA mode, warm or hot (synchronized) with automatic or manual failover"
    ::= { affirmedGeographicRedundancyRedundancyGroupStatsEntry 5 }

affirmedGeographicRedundancyRedundancyGroupStatsActualHAState OBJECT-TYPE
    SYNTAX      INTEGER {active(1),standby(2)}
    MAX-ACCESS  read-only
    STATUS      current
    DESCRIPTION "The manually configured HA state."
    ::= { affirmedGeographicRedundancyRedundancyGroupStatsEntry 6 }

affirmedGeographicRedundancyRedundancyGroupStatsRuntimeHAState OBJECT-TYPE
    SYNTAX      INTEGER {electing(0),active(1),standby(2)}
    MAX-ACCESS  read-only
    STATUS      current
    DESCRIPTION "Runtime HA state"
    ::= { affirmedGeographicRedundancyRedundancyGroupStatsEntry 7 }

affirmedGeographicRedundancyRedundancyGroupStatsOperState OBJECT-TYPE
    SYNTAX      INTEGER {up(101),down(102),partially-up(103),maint(104),dryup(105),congested(106),unknown(107)}
    MAX-ACCESS  read-only
    STATUS      current
    DESCRIPTION "Operational Status"
    ::= { affirmedGeographicRedundancyRedundancyGroupStatsEntry 8 }

affirmedGeographicRedundancyRedundancyGroupStatsNumSyncRecords OBJECT-TYPE
    SYNTAX      Unsigned32
    MAX-ACCESS  read-only
    STATUS      current
    DESCRIPTION "Total number of records to exchange (synchronize) with Geographic Redundancy peer node"
    ::= { affirmedGeographicRedundancyRedundancyGroupStatsEntry 9 }

affirmedGeographicRedundancyRedundancyGroupStatsPeerConnectionStatus OBJECT-TYPE
    SYNTAX      INTEGER {up(101),down(102),partially-up(103),maint(104),dryup(105),congested(106),unknown(107)}
    MAX-ACCESS  read-only
    STATUS      current
    DESCRIPTION "Geographic Redundancy peer node connection status"
    ::= { affirmedGeographicRedundancyRedundancyGroupStatsEntry 10 }

affirmedGeographicRedundancyRedundancyGroupStatsPeerRuntimeHAState OBJECT-TYPE
    SYNTAX      INTEGER {unknown(0),active(1),standby(2)}
    MAX-ACCESS  read-only
    STATUS      current
    DESCRIPTION "Peer Runtime HA state"
    ::= { affirmedGeographicRedundancyRedundancyGroupStatsEntry 11 }

affirmedGeographicRedundancyRedundancyGroupStatsPeerOperState OBJECT-TYPE
    SYNTAX      INTEGER {up(101),down(102),partially-up(103),maint(104),dryup(105),congested(106),unknown(107)}
    MAX-ACCESS  read-only
    STATUS      current
    DESCRIPTION "Peer Operational Status"
    ::= { affirmedGeographicRedundancyRedundancyGroupStatsEntry 12 }

affirmedGeographicRedundancyRedundancyGroupStatsPeerNumSyncRecords OBJECT-TYPE
    SYNTAX      Unsigned32
    MAX-ACCESS  read-only
    STATUS      current
    DESCRIPTION "Peer Total number of records exchanged (synchronize) with Geographic Redundancy peer node"
    ::= { affirmedGeographicRedundancyRedundancyGroupStatsEntry 13 }

affirmedGeographicRedundancyRedundancyGroupSecurityStatsTable OBJECT-TYPE
    SYNTAX      SEQUENCE OF AffirmedGeographicRedundancyRedundancyGroupSecurityStatsEntry
    MAX-ACCESS  not-accessible
    STATUS      current
    DESCRIPTION ""
    ::= { affirmedGeographicRedundancy 5 }

affirmedGeographicRedundancyRedundancyGroupSecurityStatsEntry OBJECT-TYPE
    SYNTAX      AffirmedGeographicRedundancyRedundancyGroupSecurityStatsEntry
    MAX-ACCESS  not-accessible
    STATUS      current
    DESCRIPTION ""
    INDEX { affirmedGeographicRedundancyRedundancyGroupSecurityStatsName }
        ::= { affirmedGeographicRedundancyRedundancyGroupSecurityStatsTable 1 }

AffirmedGeographicRedundancyRedundancyGroupSecurityStatsEntry ::=
    SEQUENCE {
        affirmedGeographicRedundancyRedundancyGroupSecurityStatsName String,
        affirmedGeographicRedundancyRedundancyGroupSecurityStatsNumSyncRecordsSpm Unsigned32,
        affirmedGeographicRedundancyRedundancyGroupSecurityStatsPeerNumSyncRecordsSpm Unsigned32
    }

affirmedGeographicRedundancyRedundancyGroupSecurityStatsName OBJECT-TYPE
    SYNTAX      String
    MAX-ACCESS  not-accessible
    STATUS      current
    DESCRIPTION "Redundancy Name"
    ::= { affirmedGeographicRedundancyRedundancyGroupSecurityStatsEntry 1 }

affirmedGeographicRedundancyRedundancyGroupSecurityStatsNumSyncRecordsSpm OBJECT-TYPE
    SYNTAX      Unsigned32
    MAX-ACCESS  read-only
    STATUS      current
    DESCRIPTION "Total number of security records to exchange (synchronize) with Geographic Redundancy peer node"
    ::= { affirmedGeographicRedundancyRedundancyGroupSecurityStatsEntry 2 }

affirmedGeographicRedundancyRedundancyGroupSecurityStatsPeerNumSyncRecordsSpm OBJECT-TYPE
    SYNTAX      Unsigned32
    MAX-ACCESS  read-only
    STATUS      current
    DESCRIPTION "Peer Total number of security records to exchange (synchronize) with Geographic Redundancy peer node"
    ::= { affirmedGeographicRedundancyRedundancyGroupSecurityStatsEntry 3 }

affirmedGeographicRedundancyRedundancyNetHealthStatsTable OBJECT-TYPE
    SYNTAX      SEQUENCE OF AffirmedGeographicRedundancyRedundancyNetHealthStatsEntry
    MAX-ACCESS  not-accessible
    STATUS      current
    DESCRIPTION ""
    ::= { affirmedGeographicRedundancy 2 }

affirmedGeographicRedundancyRedundancyNetHealthStatsEntry OBJECT-TYPE
    SYNTAX      AffirmedGeographicRedundancyRedundancyNetHealthStatsEntry
    MAX-ACCESS  not-accessible
    STATUS      current
    DESCRIPTION ""
    INDEX { affirmedGeographicRedundancyRedundancyNetHealthStatsName, affirmedGeographicRedundancyRedundancyNetHealthStatsNetHealthType, affirmedGeographicRedundancyRedundancyNetHealthStatsNetHealthLnk }
        ::= { affirmedGeographicRedundancyRedundancyNetHealthStatsTable 1 }

AffirmedGeographicRedundancyRedundancyNetHealthStatsEntry ::=
    SEQUENCE {
        affirmedGeographicRedundancyRedundancyNetHealthStatsName String,
        affirmedGeographicRedundancyRedundancyNetHealthStatsNetHealthType INTEGER,
        affirmedGeographicRedundancyRedundancyNetHealthStatsNetHealthLnk INTEGER,
        affirmedGeographicRedundancyRedundancyNetHealthStatsNetHealthStatus INTEGER,
        affirmedGeographicRedundancyRedundancyNetHealthStatsNetHealthPeerStatus INTEGER
    }

affirmedGeographicRedundancyRedundancyNetHealthStatsName OBJECT-TYPE
    SYNTAX      String
    MAX-ACCESS  not-accessible
    STATUS      current
    DESCRIPTION "Redundancy Group Name"
    ::= { affirmedGeographicRedundancyRedundancyNetHealthStatsEntry 1 }

affirmedGeographicRedundancyRedundancyNetHealthStatsNetHealthType OBJECT-TYPE
    SYNTAX      INTEGER {shared(0),private(1)}
    MAX-ACCESS  not-accessible
    STATUS      current
    DESCRIPTION "Type"
    ::= { affirmedGeographicRedundancyRedundancyNetHealthStatsEntry 2 }

affirmedGeographicRedundancyRedundancyNetHealthStatsNetHealthLnk OBJECT-TYPE
    SYNTAX      INTEGER {none(0),aAA(1),pCRF(2),oCS(3),s6B(4),sTA(5),sWM(6),rMG(7),pFCP(9)}
    MAX-ACCESS  not-accessible
    STATUS      current
    DESCRIPTION "Link Service"
    ::= { affirmedGeographicRedundancyRedundancyNetHealthStatsEntry 3 }

affirmedGeographicRedundancyRedundancyNetHealthStatsNetHealthStatus OBJECT-TYPE
    SYNTAX      INTEGER {unknown(0),up(1),down(2)}
    MAX-ACCESS  read-only
    STATUS      current
    DESCRIPTION "Local Status"
    ::= { affirmedGeographicRedundancyRedundancyNetHealthStatsEntry 4 }

affirmedGeographicRedundancyRedundancyNetHealthStatsNetHealthPeerStatus OBJECT-TYPE
    SYNTAX      INTEGER {unknown(0),up(1),down(2)}
    MAX-ACCESS  read-only
    STATUS      current
    DESCRIPTION "Peer Status"
    ::= { affirmedGeographicRedundancyRedundancyNetHealthStatsEntry 5 }

affirmedGeographicRedundancyRedundancySwitchoverStatsTable OBJECT-TYPE
    SYNTAX      SEQUENCE OF AffirmedGeographicRedundancyRedundancySwitchoverStatsEntry
    MAX-ACCESS  not-accessible
    STATUS      current
    DESCRIPTION ""
    ::= { affirmedGeographicRedundancy 3 }

affirmedGeographicRedundancyRedundancySwitchoverStatsEntry OBJECT-TYPE
    SYNTAX      AffirmedGeographicRedundancyRedundancySwitchoverStatsEntry
    MAX-ACCESS  not-accessible
    STATUS      current
    DESCRIPTION ""
    INDEX { affirmedGeographicRedundancyRedundancySwitchoverStatsName, affirmedGeographicRedundancyRedundancySwitchoverStatsSwitchoverType }
        ::= { affirmedGeographicRedundancyRedundancySwitchoverStatsTable 1 }

AffirmedGeographicRedundancyRedundancySwitchoverStatsEntry ::=
    SEQUENCE {
        affirmedGeographicRedundancyRedundancySwitchoverStatsName String,
        affirmedGeographicRedundancyRedundancySwitchoverStatsSwitchoverType INTEGER,
        affirmedGeographicRedundancyRedundancySwitchoverStatsHaMode INTEGER,
        affirmedGeographicRedundancyRedundancySwitchoverStatsNetHealthLnk INTEGER,
        affirmedGeographicRedundancyRedundancySwitchoverStatsPeerConnectionStatus INTEGER,
        affirmedGeographicRedundancyRedundancySwitchoverStatsNumSyncRecords Unsigned32,
        affirmedGeographicRedundancyRedundancySwitchoverStatsSwitchoverDuration Unsigned32,
        affirmedGeographicRedundancyRedundancySwitchoverStatsControlPacketRcvdSec Unsigned32,
        affirmedGeographicRedundancyRedundancySwitchoverStatsDataPacketRcvdSec Unsigned32,
        affirmedGeographicRedundancyRedundancySwitchoverStatsSwitchoverTime String
    }

affirmedGeographicRedundancyRedundancySwitchoverStatsName OBJECT-TYPE
    SYNTAX      String
    MAX-ACCESS  not-accessible
    STATUS      current
    DESCRIPTION "Redundancy Group Name"
    ::= { affirmedGeographicRedundancyRedundancySwitchoverStatsEntry 1 }

affirmedGeographicRedundancyRedundancySwitchoverStatsSwitchoverType OBJECT-TYPE
    SYNTAX      INTEGER {standby-to-active(0),active-to-standby(1)}
    MAX-ACCESS  not-accessible
    STATUS      current
    DESCRIPTION "Switchover Type"
    ::= { affirmedGeographicRedundancyRedundancySwitchoverStatsEntry 2 }

affirmedGeographicRedundancyRedundancySwitchoverStatsHaMode OBJECT-TYPE
    SYNTAX      INTEGER {warm-manual(1),hot-auto(2),hot-manual(3)}
    MAX-ACCESS  read-only
    STATUS      current
    DESCRIPTION "Switchover mode, warm or hot"
    ::= { affirmedGeographicRedundancyRedundancySwitchoverStatsEntry 3 }

affirmedGeographicRedundancyRedundancySwitchoverStatsNetHealthLnk OBJECT-TYPE
    SYNTAX      INTEGER {none(0),aAA(1),pCRF(2),oCS(3),s6B(4),sTA(5),sWM(6),rMG(7),pFCP(9)}
    MAX-ACCESS  read-only
    STATUS      current
    DESCRIPTION "Switchover Link"
    ::= { affirmedGeographicRedundancyRedundancySwitchoverStatsEntry 4 }

affirmedGeographicRedundancyRedundancySwitchoverStatsPeerConnectionStatus OBJECT-TYPE
    SYNTAX      INTEGER {up(101),down(102),partially-up(103),maint(104),dryup(105),congested(106),unknown(107)}
    MAX-ACCESS  read-only
    STATUS      current
    DESCRIPTION "Geographic Redundancy peer node connection status"
    ::= { affirmedGeographicRedundancyRedundancySwitchoverStatsEntry 5 }

affirmedGeographicRedundancyRedundancySwitchoverStatsNumSyncRecords OBJECT-TYPE
    SYNTAX      Unsigned32
    MAX-ACCESS  read-only
    STATUS      current
    DESCRIPTION "Total number of records at time of switchover"
    ::= { affirmedGeographicRedundancyRedundancySwitchoverStatsEntry 6 }

affirmedGeographicRedundancyRedundancySwitchoverStatsSwitchoverDuration OBJECT-TYPE
    SYNTAX      Unsigned32
    MAX-ACCESS  read-only
    STATUS      current
    DESCRIPTION "Switchover duration in seconds"
    ::= { affirmedGeographicRedundancyRedundancySwitchoverStatsEntry 7 }

affirmedGeographicRedundancyRedundancySwitchoverStatsControlPacketRcvdSec OBJECT-TYPE
    SYNTAX      Unsigned32
    MAX-ACCESS  read-only
    STATUS      current
    DESCRIPTION "First control packet received after switchover in seconds"
    ::= { affirmedGeographicRedundancyRedundancySwitchoverStatsEntry 8 }

affirmedGeographicRedundancyRedundancySwitchoverStatsDataPacketRcvdSec OBJECT-TYPE
    SYNTAX      Unsigned32
    MAX-ACCESS  read-only
    STATUS      current
    DESCRIPTION "First data packet received after switchover in seconds"
    ::= { affirmedGeographicRedundancyRedundancySwitchoverStatsEntry 9 }

affirmedGeographicRedundancyRedundancySwitchoverStatsSwitchoverTime OBJECT-TYPE
    SYNTAX      String
    MAX-ACCESS  read-only
    STATUS      current
    DESCRIPTION "Switchover Time"
    ::= { affirmedGeographicRedundancyRedundancySwitchoverStatsEntry 10 }

affirmedGeographicRedundancyBgpPeeringMonitoringStatusTable OBJECT-TYPE
    SYNTAX      SEQUENCE OF AffirmedGeographicRedundancyBgpPeeringMonitoringStatusEntry
    MAX-ACCESS  not-accessible
    STATUS      current
    DESCRIPTION ""
    ::= { affirmedGeographicRedundancy 4 }

affirmedGeographicRedundancyBgpPeeringMonitoringStatusEntry OBJECT-TYPE
    SYNTAX      AffirmedGeographicRedundancyBgpPeeringMonitoringStatusEntry
    MAX-ACCESS  not-accessible
    STATUS      current
    DESCRIPTION ""
    INDEX { affirmedGeographicRedundancyBgpPeeringMonitoringStatusChassis, affirmedGeographicRedundancyBgpPeeringMonitoringStatusSlot }
        ::= { affirmedGeographicRedundancyBgpPeeringMonitoringStatusTable 1 }

AffirmedGeographicRedundancyBgpPeeringMonitoringStatusEntry ::=
    SEQUENCE {
        affirmedGeographicRedundancyBgpPeeringMonitoringStatusChassis Unsigned32,
        affirmedGeographicRedundancyBgpPeeringMonitoringStatusSlot Unsigned32,
        affirmedGeographicRedundancyBgpPeeringMonitoringStatusOutput String
    }

affirmedGeographicRedundancyBgpPeeringMonitoringStatusChassis OBJECT-TYPE
    SYNTAX      Unsigned32
    MAX-ACCESS  not-accessible
    STATUS      current
    DESCRIPTION ""
    ::= { affirmedGeographicRedundancyBgpPeeringMonitoringStatusEntry 1 }

affirmedGeographicRedundancyBgpPeeringMonitoringStatusSlot OBJECT-TYPE
    SYNTAX      Unsigned32
    MAX-ACCESS  not-accessible
    STATUS      current
    DESCRIPTION ""
    ::= { affirmedGeographicRedundancyBgpPeeringMonitoringStatusEntry 2 }

affirmedGeographicRedundancyBgpPeeringMonitoringStatusOutput OBJECT-TYPE
    SYNTAX      String
    MAX-ACCESS  read-only
    STATUS      current
    DESCRIPTION ""
    ::= { affirmedGeographicRedundancyBgpPeeringMonitoringStatusEntry 3 }

END

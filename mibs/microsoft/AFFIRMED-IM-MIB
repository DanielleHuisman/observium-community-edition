AFFIRMED-IM-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedImMIB MODULE-IDENTITY
    ORGANIZATION "Affirmed Networks, Inc."
    CONTACT-INFO "Affirmed Networks, Inc. 35 Nagog Park, Acton, MA, USA"
    DESCRIPTION ""
    ::= { 1 3 6 1 4 1 37963 10 1 }

String ::= TEXTUAL-CONVENTION
    DISPLAY-HINT "1t"
    STATUS      current
    DESCRIPTION "xs:string"
    SYNTAX      OCTET STRING

affirmedIm OBJECT IDENTIFIER ::= { affirmedImMIB 1 }

affirmedImStatusTable OBJECT-TYPE
    SYNTAX      SEQUENCE OF AffirmedImStatusEntry
    MAX-ACCESS  not-accessible
    STATUS      current
    DESCRIPTION ""
    ::= { affirmedIm 1 }

affirmedImStatusEntry OBJECT-TYPE
    SYNTAX      AffirmedImStatusEntry
    MAX-ACCESS  not-accessible
    STATUS      current
    DESCRIPTION ""
    INDEX { affirmedImStatusState, affirmedImStatusChassis, affirmedImStatusSlot, affirmedImStatusCpu }
        ::= { affirmedImStatusTable 1 }

AffirmedImStatusEntry ::=
    SEQUENCE {
        affirmedImStatusState INTEGER,
        affirmedImStatusChassis Unsigned32,
        affirmedImStatusSlot Unsigned32,
        affirmedImStatusCpu Unsigned32,
        affirmedImStatusAdminVersion String,
        affirmedImStatusOperationalVersion String,
        affirmedImStatusActivationStatus String,
        affirmedImStatusRollbackVersion String,
        affirmedImStatusPreparedVersion String
    }

affirmedImStatusState OBJECT-TYPE
    SYNTAX      INTEGER {active(1),standby(2),n-a(3)}
    MAX-ACCESS  not-accessible
    STATUS      current
    DESCRIPTION ""
    ::= { affirmedImStatusEntry 1 }

affirmedImStatusChassis OBJECT-TYPE
    SYNTAX      Unsigned32
    MAX-ACCESS  not-accessible
    STATUS      current
    DESCRIPTION ""
    ::= { affirmedImStatusEntry 2 }

affirmedImStatusSlot OBJECT-TYPE
    SYNTAX      Unsigned32
    MAX-ACCESS  not-accessible
    STATUS      current
    DESCRIPTION ""
    ::= { affirmedImStatusEntry 3 }

affirmedImStatusCpu OBJECT-TYPE
    SYNTAX      Unsigned32
    MAX-ACCESS  not-accessible
    STATUS      current
    DESCRIPTION ""
    ::= { affirmedImStatusEntry 4 }

affirmedImStatusAdminVersion OBJECT-TYPE
    SYNTAX      String
    MAX-ACCESS  read-only
    STATUS      current
    DESCRIPTION "Current upgrade admin version"
    ::= { affirmedImStatusEntry 5 }

affirmedImStatusOperationalVersion OBJECT-TYPE
    SYNTAX      String
    MAX-ACCESS  read-only
    STATUS      current
    DESCRIPTION "Version currently running"
    ::= { affirmedImStatusEntry 6 }

affirmedImStatusActivationStatus OBJECT-TYPE
    SYNTAX      String
    MAX-ACCESS  read-only
    STATUS      current
    DESCRIPTION "Activation status"
    ::= { affirmedImStatusEntry 7 }

affirmedImStatusRollbackVersion OBJECT-TYPE
    SYNTAX      String
    MAX-ACCESS  read-only
    STATUS      current
    DESCRIPTION "Version available for rollback"
    ::= { affirmedImStatusEntry 8 }

affirmedImStatusPreparedVersion OBJECT-TYPE
    SYNTAX      String
    MAX-ACCESS  read-only
    STATUS      current
    DESCRIPTION "Version extracted and ready for upgrade"
    ::= { affirmedImStatusEntry 9 }

affirmedImModifierStatusTable OBJECT-TYPE
    SYNTAX      SEQUENCE OF AffirmedImModifierStatusEntry
    MAX-ACCESS  not-accessible
    STATUS      current
    DESCRIPTION ""
    ::= { affirmedIm 2 }

affirmedImModifierStatusEntry OBJECT-TYPE
    SYNTAX      AffirmedImModifierStatusEntry
    MAX-ACCESS  not-accessible
    STATUS      current
    DESCRIPTION ""
    INDEX { affirmedImModifierStatusReleaserole, affirmedImModifierStatusRelease, affirmedImModifierStatusModifier }
        ::= { affirmedImModifierStatusTable 1 }

AffirmedImModifierStatusEntry ::=
    SEQUENCE {
        affirmedImModifierStatusReleaserole INTEGER,
        affirmedImModifierStatusRelease String,
        affirmedImModifierStatusModifier INTEGER,
        affirmedImModifierStatusOperationalVersion String,
        affirmedImModifierStatusRollbackVersion String,
        affirmedImModifierStatusOriginalVersion String
    }

affirmedImModifierStatusReleaserole OBJECT-TYPE
    SYNTAX      INTEGER {rollback(1),operational(2),prepared(3)}
    MAX-ACCESS  not-accessible
    STATUS      current
    DESCRIPTION ""
    ::= { affirmedImModifierStatusEntry 1 }

affirmedImModifierStatusRelease OBJECT-TYPE
    SYNTAX      String
    MAX-ACCESS  not-accessible
    STATUS      current
    DESCRIPTION ""
    ::= { affirmedImModifierStatusEntry 2 }

affirmedImModifierStatusModifier OBJECT-TYPE
    SYNTAX      INTEGER {dpisig(1),hwpart(2),maint(3),plugin(4)}
    MAX-ACCESS  not-accessible
    STATUS      current
    DESCRIPTION ""
    ::= { affirmedImModifierStatusEntry 3 }

affirmedImModifierStatusOperationalVersion OBJECT-TYPE
    SYNTAX      String
    MAX-ACCESS  read-only
    STATUS      current
    DESCRIPTION "Release modifier version currently running"
    ::= { affirmedImModifierStatusEntry 4 }

affirmedImModifierStatusRollbackVersion OBJECT-TYPE
    SYNTAX      String
    MAX-ACCESS  read-only
    STATUS      current
    DESCRIPTION "Release modifier version available for rollback"
    ::= { affirmedImModifierStatusEntry 5 }

affirmedImModifierStatusOriginalVersion OBJECT-TYPE
    SYNTAX      String
    MAX-ACCESS  read-only
    STATUS      current
    DESCRIPTION "Release modifier version shipped with this release version"
    ::= { affirmedImModifierStatusEntry 6 }

affirmedImAgentStatusTable OBJECT-TYPE
    SYNTAX      SEQUENCE OF AffirmedImAgentStatusEntry
    MAX-ACCESS  not-accessible
    STATUS      current
    DESCRIPTION ""
    ::= { affirmedIm 3 }

affirmedImAgentStatusEntry OBJECT-TYPE
    SYNTAX      AffirmedImAgentStatusEntry
    MAX-ACCESS  not-accessible
    STATUS      current
    DESCRIPTION ""
    INDEX { affirmedImAgentStatusChassis, affirmedImAgentStatusSlot, affirmedImAgentStatusCpu, affirmedImAgentStatusState }
        ::= { affirmedImAgentStatusTable 1 }

AffirmedImAgentStatusEntry ::=
    SEQUENCE {
        affirmedImAgentStatusChassis Unsigned32,
        affirmedImAgentStatusSlot Unsigned32,
        affirmedImAgentStatusCpu Unsigned32,
        affirmedImAgentStatusState INTEGER,
        affirmedImAgentStatusExpseqid String,
        affirmedImAgentStatusMasseqid String,
        affirmedImAgentStatusPrevrfs String,
        affirmedImAgentStatusPrevtos String,
        affirmedImAgentStatusCurrrfs String,
        affirmedImAgentStatusCurrtos String,
        affirmedImAgentStatusSandrfs String,
        affirmedImAgentStatusSandtos String,
        affirmedImAgentStatusGrubrfs String,
        affirmedImAgentStatusAgentstatus INTEGER,
        affirmedImAgentStatusMsg String
    }

affirmedImAgentStatusChassis OBJECT-TYPE
    SYNTAX      Unsigned32
    MAX-ACCESS  not-accessible
    STATUS      current
    DESCRIPTION ""
    ::= { affirmedImAgentStatusEntry 1 }

affirmedImAgentStatusSlot OBJECT-TYPE
    SYNTAX      Unsigned32
    MAX-ACCESS  not-accessible
    STATUS      current
    DESCRIPTION ""
    ::= { affirmedImAgentStatusEntry 2 }

affirmedImAgentStatusCpu OBJECT-TYPE
    SYNTAX      Unsigned32
    MAX-ACCESS  not-accessible
    STATUS      current
    DESCRIPTION ""
    ::= { affirmedImAgentStatusEntry 3 }

affirmedImAgentStatusState OBJECT-TYPE
    SYNTAX      INTEGER {expected(1),actual(2)}
    MAX-ACCESS  not-accessible
    STATUS      current
    DESCRIPTION ""
    ::= { affirmedImAgentStatusEntry 4 }

affirmedImAgentStatusExpseqid OBJECT-TYPE
    SYNTAX      String
    MAX-ACCESS  read-only
    STATUS      current
    DESCRIPTION ""
    ::= { affirmedImAgentStatusEntry 5 }

affirmedImAgentStatusMasseqid OBJECT-TYPE
    SYNTAX      String
    MAX-ACCESS  read-only
    STATUS      current
    DESCRIPTION ""
    ::= { affirmedImAgentStatusEntry 6 }

affirmedImAgentStatusPrevrfs OBJECT-TYPE
    SYNTAX      String
    MAX-ACCESS  read-only
    STATUS      current
    DESCRIPTION ""
    ::= { affirmedImAgentStatusEntry 7 }

affirmedImAgentStatusPrevtos OBJECT-TYPE
    SYNTAX      String
    MAX-ACCESS  read-only
    STATUS      current
    DESCRIPTION ""
    ::= { affirmedImAgentStatusEntry 8 }

affirmedImAgentStatusCurrrfs OBJECT-TYPE
    SYNTAX      String
    MAX-ACCESS  read-only
    STATUS      current
    DESCRIPTION ""
    ::= { affirmedImAgentStatusEntry 9 }

affirmedImAgentStatusCurrtos OBJECT-TYPE
    SYNTAX      String
    MAX-ACCESS  read-only
    STATUS      current
    DESCRIPTION ""
    ::= { affirmedImAgentStatusEntry 10 }

affirmedImAgentStatusSandrfs OBJECT-TYPE
    SYNTAX      String
    MAX-ACCESS  read-only
    STATUS      current
    DESCRIPTION ""
    ::= { affirmedImAgentStatusEntry 11 }

affirmedImAgentStatusSandtos OBJECT-TYPE
    SYNTAX      String
    MAX-ACCESS  read-only
    STATUS      current
    DESCRIPTION ""
    ::= { affirmedImAgentStatusEntry 12 }

affirmedImAgentStatusGrubrfs OBJECT-TYPE
    SYNTAX      String
    MAX-ACCESS  read-only
    STATUS      current
    DESCRIPTION ""
    ::= { affirmedImAgentStatusEntry 13 }

affirmedImAgentStatusAgentstatus OBJECT-TYPE
    SYNTAX      INTEGER {n-a(0),working(1),waiting(2),done(3),error(4),info(5),retry(6)}
    MAX-ACCESS  read-only
    STATUS      current
    DESCRIPTION ""
    ::= { affirmedImAgentStatusEntry 14 }

affirmedImAgentStatusMsg OBJECT-TYPE
    SYNTAX      String
    MAX-ACCESS  read-only
    STATUS      current
    DESCRIPTION ""
    ::= { affirmedImAgentStatusEntry 15 }

END

AFFIRMED-INFRASTRUCTURE-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedInfrastructureMIB MODULE-IDENTITY
    ORGANIZATION "Affirmed Networks, Inc."
    CONTACT-INFO "Affirmed Networks, Inc. 35 Nagog Park, Acton, MA, USA"
    DESCRIPTION ""
    ::= { 1 3 6 1 4 1 37963 10 10 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedInfrastructure OBJECT IDENTIFIER ::= { affirmedInfrastructureMIB 1 }

affirmedInfrastructureFilemgmt OBJECT IDENTIFIER ::= { affirmedInfrastructure 1 }

affirmedInfrastructureNtpserver OBJECT IDENTIFIER ::= { affirmedInfrastructure 3 }

affirmedInfrastructurePeeroverloadcontrol OBJECT IDENTIFIER ::= { affirmedInfrastructure 2 }

affirmedInfrastructureEdr OBJECT IDENTIFIER ::= { affirmedInfrastructure 4 }

affirmedInfrastructureFilemgmtFileMgmtStatsTable OBJECT-TYPE
    SYNTAX      SEQUENCE OF AffirmedInfrastructureFilemgmtFileMgmtStatsEntry
    MAX-ACCESS  not-accessible
    STATUS      deprecated
    DESCRIPTION ""
    ::= { affirmedInfrastructureFilemgmt 1 }

affirmedInfrastructureFilemgmtFileMgmtStatsEntry OBJECT-TYPE
    SYNTAX      AffirmedInfrastructureFilemgmtFileMgmtStatsEntry
    MAX-ACCESS  not-accessible
    STATUS      deprecated
    DESCRIPTION ""
    INDEX { affirmedInfrastructureFilemgmtFileMgmtStatsPrefix }
        ::= { affirmedInfrastructureFilemgmtFileMgmtStatsTable 1 }

AffirmedInfrastructureFilemgmtFileMgmtStatsEntry ::=
    SEQUENCE {
        affirmedInfrastructureFilemgmtFileMgmtStatsPrefix String,
        affirmedInfrastructureFilemgmtFileMgmtStatsTransferred ConfdString,
        affirmedInfrastructureFilemgmtFileMgmtStatsPurged ConfdString,
        affirmedInfrastructureFilemgmtFileMgmtStatsPurgedcapacity ConfdString
    }

affirmedInfrastructureFilemgmtFileMgmtStatsPrefix OBJECT-TYPE
    SYNTAX      String
    MAX-ACCESS  not-accessible
    STATUS      current
    DESCRIPTION ""
    ::= { affirmedInfrastructureFilemgmtFileMgmtStatsEntry 1 }

affirmedInfrastructureFilemgmtFileMgmtStatsTransferred OBJECT-TYPE
    SYNTAX      ConfdString
    MAX-ACCESS  read-only
    STATUS      current
    DESCRIPTION ""
    ::= { affirmedInfrastructureFilemgmtFileMgmtStatsEntry 2 }

affirmedInfrastructureFilemgmtFileMgmtStatsPurged OBJECT-TYPE
    SYNTAX      ConfdString
    MAX-ACCESS  read-only
    STATUS      current
    DESCRIPTION ""
    ::= { affirmedInfrastructureFilemgmtFileMgmtStatsEntry 3 }

affirmedInfrastructureFilemgmtFileMgmtStatsPurgedcapacity OBJECT-TYPE
    SYNTAX      ConfdString
    MAX-ACCESS  read-only
    STATUS      current
    DESCRIPTION ""
    ::= { affirmedInfrastructureFilemgmtFileMgmtStatsEntry 4 }

affirmedInfrastructureNtpserverStatusTable OBJECT-TYPE
    SYNTAX      SEQUENCE OF AffirmedInfrastructureNtpserverStatusEntry
    MAX-ACCESS  not-accessible
    STATUS      current
    DESCRIPTION ""
    ::= { affirmedInfrastructureNtpserver 1 }

affirmedInfrastructureNtpserverStatusEntry OBJECT-TYPE
    SYNTAX      AffirmedInfrastructureNtpserverStatusEntry
    MAX-ACCESS  not-accessible
    STATUS      current
    DESCRIPTION ""
    INDEX { affirmedInfrastructureNtpserverStatusRemote }
        ::= { affirmedInfrastructureNtpserverStatusTable 1 }

AffirmedInfrastructureNtpserverStatusEntry ::=
    SEQUENCE {
        affirmedInfrastructureNtpserverStatusRemote String,
        affirmedInfrastructureNtpserverStatusSync String,
        affirmedInfrastructureNtpserverStatusRefid String,
        affirmedInfrastructureNtpserverStatusSt Integer32,
        affirmedInfrastructureNtpserverStatusT String,
        affirmedInfrastructureNtpserverStatusWhen Integer32,
        affirmedInfrastructureNtpserverStatusPoll Integer32,
        affirmedInfrastructureNtpserverStatusReach Integer32,
        affirmedInfrastructureNtpserverStatusDelay String,
        affirmedInfrastructureNtpserverStatusOffset String,
        affirmedInfrastructureNtpserverStatusJitter String
    }

affirmedInfrastructureNtpserverStatusRemote OBJECT-TYPE
    SYNTAX      String
    MAX-ACCESS  not-accessible
    STATUS      current
    DESCRIPTION "Peer specified in the ntp configuration"
    ::= { affirmedInfrastructureNtpserverStatusEntry 1 }

affirmedInfrastructureNtpserverStatusSync OBJECT-TYPE
    SYNTAX      String
    MAX-ACCESS  read-only
    STATUS      current
    DESCRIPTION "time source sync status"
    ::= { affirmedInfrastructureNtpserverStatusEntry 2 }

affirmedInfrastructureNtpserverStatusRefid OBJECT-TYPE
    SYNTAX      String
    MAX-ACCESS  read-only
    STATUS      current
    DESCRIPTION "remote source's synchronization source"
    ::= { affirmedInfrastructureNtpserverStatusEntry 3 }

affirmedInfrastructureNtpserverStatusSt OBJECT-TYPE
    SYNTAX      Integer32
    MAX-ACCESS  read-only
    STATUS      current
    DESCRIPTION "stratum level of the source"
    ::= { affirmedInfrastructureNtpserverStatusEntry 4 }

affirmedInfrastructureNtpserverStatusT OBJECT-TYPE
    SYNTAX      String
    MAX-ACCESS  read-only
    STATUS      current
    DESCRIPTION "type"
    ::= { affirmedInfrastructureNtpserverStatusEntry 5 }

affirmedInfrastructureNtpserverStatusWhen OBJECT-TYPE
    SYNTAX      Integer32
    MAX-ACCESS  read-only
    STATUS      current
    DESCRIPTION "number of seconds passed since last response"
    ::= { affirmedInfrastructureNtpserverStatusEntry 6 }

affirmedInfrastructureNtpserverStatusPoll OBJECT-TYPE
    SYNTAX      Integer32
    MAX-ACCESS  read-only
    STATUS      current
    DESCRIPTION "polling interval, in seconds, for source"
    ::= { affirmedInfrastructureNtpserverStatusEntry 7 }

affirmedInfrastructureNtpserverStatusReach OBJECT-TYPE
    SYNTAX      Integer32
    MAX-ACCESS  read-only
    STATUS      current
    DESCRIPTION "indicates success/failure to reach source, 377 all attempts successful"
    ::= { affirmedInfrastructureNtpserverStatusEntry 8 }

affirmedInfrastructureNtpserverStatusDelay OBJECT-TYPE
    SYNTAX      String
    MAX-ACCESS  read-only
    STATUS      current
    DESCRIPTION "indicates the roundtrip time, in milliseconds, to receive a reply"
    ::= { affirmedInfrastructureNtpserverStatusEntry 9 }

affirmedInfrastructureNtpserverStatusOffset OBJECT-TYPE
    SYNTAX      String
    MAX-ACCESS  read-only
    STATUS      current
    DESCRIPTION "indicates the time difference, in milliseconds, between the client server and source"
    ::= { affirmedInfrastructureNtpserverStatusEntry 10 }

affirmedInfrastructureNtpserverStatusJitter OBJECT-TYPE
    SYNTAX      String
    MAX-ACCESS  read-only
    STATUS      current
    DESCRIPTION "indicates the difference, in milliseconds, between two samples"
    ::= { affirmedInfrastructureNtpserverStatusEntry 11 }

affirmedInfrastructurePeeroverloadcontrolPacerSummaryRatesTable OBJECT-TYPE
    SYNTAX      SEQUENCE OF AffirmedInfrastructurePeeroverloadcontrolPacerSummaryRatesEntry
    MAX-ACCESS  not-accessible
    STATUS      current
    DESCRIPTION ""
    ::= { affirmedInfrastructurePeeroverloadcontrol 1 }

affirmedInfrastructurePeeroverloadcontrolPacerSummaryRatesEntry OBJECT-TYPE
    SYNTAX      AffirmedInfrastructurePeeroverloadcontrolPacerSummaryRatesEntry
    MAX-ACCESS  not-accessible
    STATUS      current
    DESCRIPTION ""
    INDEX { affirmedInfrastructurePeeroverloadcontrolPacerSummaryRatesPacername, affirmedInfrastructurePeeroverloadcontrolPacerSummaryRatesInstancename, affirmedInfrastructurePeeroverloadcontrolPacerSummaryRatesInterval }
        ::= { affirmedInfrastructurePeeroverloadcontrolPacerSummaryRatesTable 1 }

AffirmedInfrastructurePeeroverloadcontrolPacerSummaryRatesEntry ::=
    SEQUENCE {
        affirmedInfrastructurePeeroverloadcontrolPacerSummaryRatesPacername String,
        affirmedInfrastructurePeeroverloadcontrolPacerSummaryRatesInstancename String,
        affirmedInfrastructurePeeroverloadcontrolPacerSummaryRatesInterval Integer32,
        affirmedInfrastructurePeeroverloadcontrolPacerSummaryRatesRate Unsigned32,
        affirmedInfrastructurePeeroverloadcontrolPacerSummaryRatesHighrate Unsigned32,
        affirmedInfrastructurePeeroverloadcontrolPacerSummaryRatesMediumrate Unsigned32,
        affirmedInfrastructurePeeroverloadcontrolPacerSummaryRatesLowrate Unsigned32
    }

affirmedInfrastructurePeeroverloadcontrolPacerSummaryRatesPacername OBJECT-TYPE
    SYNTAX      String
    MAX-ACCESS  not-accessible
    STATUS      current
    DESCRIPTION ""
    ::= { affirmedInfrastructurePeeroverloadcontrolPacerSummaryRatesEntry 1 }

affirmedInfrastructurePeeroverloadcontrolPacerSummaryRatesInstancename OBJECT-TYPE
    SYNTAX      String
    MAX-ACCESS  not-accessible
    STATUS      current
    DESCRIPTION ""
    ::= { affirmedInfrastructurePeeroverloadcontrolPacerSummaryRatesEntry 2 }

affirmedInfrastructurePeeroverloadcontrolPacerSummaryRatesInterval OBJECT-TYPE
    SYNTAX      Integer32
    MAX-ACCESS  not-accessible
    STATUS      current
    DESCRIPTION ""
    ::= { affirmedInfrastructurePeeroverloadcontrolPacerSummaryRatesEntry 3 }

affirmedInfrastructurePeeroverloadcontrolPacerSummaryRatesRate OBJECT-TYPE
    SYNTAX      Unsigned32
    MAX-ACCESS  read-only
    STATUS      current
    DESCRIPTION ""
    ::= { affirmedInfrastructurePeeroverloadcontrolPacerSummaryRatesEntry 4 }

affirmedInfrastructurePeeroverloadcontrolPacerSummaryRatesHighrate OBJECT-TYPE
    SYNTAX      Unsigned32
    MAX-ACCESS  read-only
    STATUS      current
    DESCRIPTION ""
    ::= { affirmedInfrastructurePeeroverloadcontrolPacerSummaryRatesEntry 5 }

affirmedInfrastructurePeeroverloadcontrolPacerSummaryRatesMediumrate OBJECT-TYPE
    SYNTAX      Unsigned32
    MAX-ACCESS  read-only
    STATUS      current
    DESCRIPTION ""
    ::= { affirmedInfrastructurePeeroverloadcontrolPacerSummaryRatesEntry 6 }

affirmedInfrastructurePeeroverloadcontrolPacerSummaryRatesLowrate OBJECT-TYPE
    SYNTAX      Unsigned32
    MAX-ACCESS  read-only
    STATUS      current
    DESCRIPTION ""
    ::= { affirmedInfrastructurePeeroverloadcontrolPacerSummaryRatesEntry 7 }

affirmedInfrastructurePeeroverloadcontrolPacerConfigsTable OBJECT-TYPE
    SYNTAX      SEQUENCE OF AffirmedInfrastructurePeeroverloadcontrolPacerConfigsEntry
    MAX-ACCESS  not-accessible
    STATUS      current
    DESCRIPTION ""
    ::= { affirmedInfrastructurePeeroverloadcontrol 2 }

affirmedInfrastructurePeeroverloadcontrolPacerConfigsEntry OBJECT-TYPE
    SYNTAX      AffirmedInfrastructurePeeroverloadcontrolPacerConfigsEntry
    MAX-ACCESS  not-accessible
    STATUS      current
    DESCRIPTION ""
    INDEX { affirmedInfrastructurePeeroverloadcontrolPacerConfigsPacername, affirmedInfrastructurePeeroverloadcontrolPacerConfigsInstancename }
        ::= { affirmedInfrastructurePeeroverloadcontrolPacerConfigsTable 1 }

AffirmedInfrastructurePeeroverloadcontrolPacerConfigsEntry ::=
    SEQUENCE {
        affirmedInfrastructurePeeroverloadcontrolPacerConfigsPacername String,
        affirmedInfrastructurePeeroverloadcontrolPacerConfigsInstancename String,
        affirmedInfrastructurePeeroverloadcontrolPacerConfigsMaxsupported Integer32,
        affirmedInfrastructurePeeroverloadcontrolPacerConfigsFailurerate Unsigned32,
        affirmedInfrastructurePeeroverloadcontrolPacerConfigsIncrate Unsigned32,
        affirmedInfrastructurePeeroverloadcontrolPacerConfigsDecrate Unsigned32,
        affirmedInfrastructurePeeroverloadcontrolPacerConfigsHighpriincrate Unsigned32,
        affirmedInfrastructurePeeroverloadcontrolPacerConfigsHighpridecrate Unsigned32,
        affirmedInfrastructurePeeroverloadcontrolPacerConfigsMediumpriincrate Unsigned32,
        affirmedInfrastructurePeeroverloadcontrolPacerConfigsMediumpridecrate Unsigned32,
        affirmedInfrastructurePeeroverloadcontrolPacerConfigsLowpriincrate Unsigned32,
        affirmedInfrastructurePeeroverloadcontrolPacerConfigsLowpridecrate Unsigned32,
        affirmedInfrastructurePeeroverloadcontrolPacerConfigsTimeinterval Integer32
    }

affirmedInfrastructurePeeroverloadcontrolPacerConfigsPacername OBJECT-TYPE
    SYNTAX      String
    MAX-ACCESS  not-accessible
    STATUS      current
    DESCRIPTION ""
    ::= { affirmedInfrastructurePeeroverloadcontrolPacerConfigsEntry 1 }

affirmedInfrastructurePeeroverloadcontrolPacerConfigsInstancename OBJECT-TYPE
    SYNTAX      String
    MAX-ACCESS  not-accessible
    STATUS      current
    DESCRIPTION ""
    ::= { affirmedInfrastructurePeeroverloadcontrolPacerConfigsEntry 2 }

affirmedInfrastructurePeeroverloadcontrolPacerConfigsMaxsupported OBJECT-TYPE
    SYNTAX      Integer32
    MAX-ACCESS  read-only
    STATUS      current
    DESCRIPTION ""
    ::= { affirmedInfrastructurePeeroverloadcontrolPacerConfigsEntry 3 }

affirmedInfrastructurePeeroverloadcontrolPacerConfigsFailurerate OBJECT-TYPE
    SYNTAX      Unsigned32
    MAX-ACCESS  read-only
    STATUS      current
    DESCRIPTION ""
    ::= { affirmedInfrastructurePeeroverloadcontrolPacerConfigsEntry 4 }

affirmedInfrastructurePeeroverloadcontrolPacerConfigsIncrate OBJECT-TYPE
    SYNTAX      Unsigned32
    MAX-ACCESS  read-only
    STATUS      current
    DESCRIPTION ""
    ::= { affirmedInfrastructurePeeroverloadcontrolPacerConfigsEntry 5 }

affirmedInfrastructurePeeroverloadcontrolPacerConfigsDecrate OBJECT-TYPE
    SYNTAX      Unsigned32
    MAX-ACCESS  read-only
    STATUS      current
    DESCRIPTION ""
    ::= { affirmedInfrastructurePeeroverloadcontrolPacerConfigsEntry 6 }

affirmedInfrastructurePeeroverloadcontrolPacerConfigsHighpriincrate OBJECT-TYPE
    SYNTAX      Unsigned32
    MAX-ACCESS  read-only
    STATUS      current
    DESCRIPTION ""
    ::= { affirmedInfrastructurePeeroverloadcontrolPacerConfigsEntry 7 }

affirmedInfrastructurePeeroverloadcontrolPacerConfigsHighpridecrate OBJECT-TYPE
    SYNTAX      Unsigned32
    MAX-ACCESS  read-only
    STATUS      current
    DESCRIPTION ""
    ::= { affirmedInfrastructurePeeroverloadcontrolPacerConfigsEntry 8 }

affirmedInfrastructurePeeroverloadcontrolPacerConfigsMediumpriincrate OBJECT-TYPE
    SYNTAX      Unsigned32
    MAX-ACCESS  read-only
    STATUS      current
    DESCRIPTION ""
    ::= { affirmedInfrastructurePeeroverloadcontrolPacerConfigsEntry 9 }

affirmedInfrastructurePeeroverloadcontrolPacerConfigsMediumpridecrate OBJECT-TYPE
    SYNTAX      Unsigned32
    MAX-ACCESS  read-only
    STATUS      current
    DESCRIPTION ""
    ::= { affirmedInfrastructurePeeroverloadcontrolPacerConfigsEntry 10 }

affirmedInfrastructurePeeroverloadcontrolPacerConfigsLowpriincrate OBJECT-TYPE
    SYNTAX      Unsigned32
    MAX-ACCESS  read-only
    STATUS      current
    DESCRIPTION ""
    ::= { affirmedInfrastructurePeeroverloadcontrolPacerConfigsEntry 11 }

affirmedInfrastructurePeeroverloadcontrolPacerConfigsLowpridecrate OBJECT-TYPE
    SYNTAX      Unsigned32
    MAX-ACCESS  read-only
    STATUS      current
    DESCRIPTION ""
    ::= { affirmedInfrastructurePeeroverloadcontrolPacerConfigsEntry 12 }

affirmedInfrastructurePeeroverloadcontrolPacerConfigsTimeinterval OBJECT-TYPE
    SYNTAX      Integer32
    MAX-ACCESS  read-only
    STATUS      current
    DESCRIPTION ""
    ::= { affirmedInfrastructurePeeroverloadcontrolPacerConfigsEntry 13 }

affirmedInfrastructurePeeroverloadcontrolPacerSummaryCountersTable OBJECT-TYPE
    SYNTAX      SEQUENCE OF AffirmedInfrastructurePeeroverloadcontrolPacerSummaryCountersEntry
    MAX-ACCESS  not-accessible
    STATUS      current
    DESCRIPTION ""
    ::= { affirmedInfrastructurePeeroverloadcontrol 3 }

affirmedInfrastructurePeeroverloadcontrolPacerSummaryCountersEntry OBJECT-TYPE
    SYNTAX      AffirmedInfrastructurePeeroverloadcontrolPacerSummaryCountersEntry
    MAX-ACCESS  not-accessible
    STATUS      current
    DESCRIPTION ""
    INDEX { affirmedInfrastructurePeeroverloadcontrolPacerSummaryCountersPacername, affirmedInfrastructurePeeroverloadcontrolPacerSummaryCountersInstancename, affirmedInfrastructurePeeroverloadcontrolPacerSummaryCountersInterval }
        ::= { affirmedInfrastructurePeeroverloadcontrolPacerSummaryCountersTable 1 }

AffirmedInfrastructurePeeroverloadcontrolPacerSummaryCountersEntry ::=
    SEQUENCE {
        affirmedInfrastructurePeeroverloadcontrolPacerSummaryCountersPacername String,
        affirmedInfrastructurePeeroverloadcontrolPacerSummaryCountersInstancename String,
        affirmedInfrastructurePeeroverloadcontrolPacerSummaryCountersInterval Integer32,
        affirmedInfrastructurePeeroverloadcontrolPacerSummaryCountersFailurerate Unsigned32,
        affirmedInfrastructurePeeroverloadcontrolPacerSummaryCountersSuccesses Unsigned32,
        affirmedInfrastructurePeeroverloadcontrolPacerSummaryCountersFailures Unsigned32,
        affirmedInfrastructurePeeroverloadcontrolPacerSummaryCountersCredits Unsigned32,
        affirmedInfrastructurePeeroverloadcontrolPacerSummaryCountersRejects Unsigned32
    }

affirmedInfrastructurePeeroverloadcontrolPacerSummaryCountersPacername OBJECT-TYPE
    SYNTAX      String
    MAX-ACCESS  not-accessible
    STATUS      current
    DESCRIPTION ""
    ::= { affirmedInfrastructurePeeroverloadcontrolPacerSummaryCountersEntry 1 }

affirmedInfrastructurePeeroverloadcontrolPacerSummaryCountersInstancename OBJECT-TYPE
    SYNTAX      String
    MAX-ACCESS  not-accessible
    STATUS      current
    DESCRIPTION ""
    ::= { affirmedInfrastructurePeeroverloadcontrolPacerSummaryCountersEntry 2 }

affirmedInfrastructurePeeroverloadcontrolPacerSummaryCountersInterval OBJECT-TYPE
    SYNTAX      Integer32
    MAX-ACCESS  not-accessible
    STATUS      current
    DESCRIPTION ""
    ::= { affirmedInfrastructurePeeroverloadcontrolPacerSummaryCountersEntry 3 }

affirmedInfrastructurePeeroverloadcontrolPacerSummaryCountersFailurerate OBJECT-TYPE
    SYNTAX      Unsigned32
    MAX-ACCESS  read-only
    STATUS      current
    DESCRIPTION ""
    ::= { affirmedInfrastructurePeeroverloadcontrolPacerSummaryCountersEntry 4 }

affirmedInfrastructurePeeroverloadcontrolPacerSummaryCountersSuccesses OBJECT-TYPE
    SYNTAX      Unsigned32
    MAX-ACCESS  read-only
    STATUS      current
    DESCRIPTION ""
    ::= { affirmedInfrastructurePeeroverloadcontrolPacerSummaryCountersEntry 5 }

affirmedInfrastructurePeeroverloadcontrolPacerSummaryCountersFailures OBJECT-TYPE
    SYNTAX      Unsigned32
    MAX-ACCESS  read-only
    STATUS      current
    DESCRIPTION ""
    ::= { affirmedInfrastructurePeeroverloadcontrolPacerSummaryCountersEntry 6 }

affirmedInfrastructurePeeroverloadcontrolPacerSummaryCountersCredits OBJECT-TYPE
    SYNTAX      Unsigned32
    MAX-ACCESS  read-only
    STATUS      current
    DESCRIPTION ""
    ::= { affirmedInfrastructurePeeroverloadcontrolPacerSummaryCountersEntry 7 }

affirmedInfrastructurePeeroverloadcontrolPacerSummaryCountersRejects OBJECT-TYPE
    SYNTAX      Unsigned32
    MAX-ACCESS  read-only
    STATUS      current
    DESCRIPTION ""
    ::= { affirmedInfrastructurePeeroverloadcontrolPacerSummaryCountersEntry 8 }

affirmedInfrastructurePeeroverloadcontrolPacerSummaryCountersCumTable OBJECT-TYPE
    SYNTAX      SEQUENCE OF AffirmedInfrastructurePeeroverloadcontrolPacerSummaryCountersCumEntry
    MAX-ACCESS  not-accessible
    STATUS      current
    DESCRIPTION ""
    ::= { affirmedInfrastructurePeeroverloadcontrol 4 }

affirmedInfrastructurePeeroverloadcontrolPacerSummaryCountersCumEntry OBJECT-TYPE
    SYNTAX      AffirmedInfrastructurePeeroverloadcontrolPacerSummaryCountersCumEntry
    MAX-ACCESS  not-accessible
    STATUS      current
    DESCRIPTION ""
    INDEX { affirmedInfrastructurePeeroverloadcontrolPacerSummaryCountersCumPacername, affirmedInfrastructurePeeroverloadcontrolPacerSummaryCountersCumInstancename }
        ::= { affirmedInfrastructurePeeroverloadcontrolPacerSummaryCountersCumTable 1 }

AffirmedInfrastructurePeeroverloadcontrolPacerSummaryCountersCumEntry ::=
    SEQUENCE {
        affirmedInfrastructurePeeroverloadcontrolPacerSummaryCountersCumPacername String,
        affirmedInfrastructurePeeroverloadcontrolPacerSummaryCountersCumInstancename String,
        affirmedInfrastructurePeeroverloadcontrolPacerSummaryCountersCumSuccesses Unsigned32,
        affirmedInfrastructurePeeroverloadcontrolPacerSummaryCountersCumFailures Unsigned32,
        affirmedInfrastructurePeeroverloadcontrolPacerSummaryCountersCumCredits Unsigned32,
        affirmedInfrastructurePeeroverloadcontrolPacerSummaryCountersCumRejects Unsigned32
    }

affirmedInfrastructurePeeroverloadcontrolPacerSummaryCountersCumPacername OBJECT-TYPE
    SYNTAX      String
    MAX-ACCESS  not-accessible
    STATUS      current
    DESCRIPTION ""
    ::= { affirmedInfrastructurePeeroverloadcontrolPacerSummaryCountersCumEntry 1 }

affirmedInfrastructurePeeroverloadcontrolPacerSummaryCountersCumInstancename OBJECT-TYPE
    SYNTAX      String
    MAX-ACCESS  not-accessible
    STATUS      current
    DESCRIPTION ""
    ::= { affirmedInfrastructurePeeroverloadcontrolPacerSummaryCountersCumEntry 2 }

affirmedInfrastructurePeeroverloadcontrolPacerSummaryCountersCumSuccesses OBJECT-TYPE
    SYNTAX      Unsigned32
    MAX-ACCESS  read-only
    STATUS      current
    DESCRIPTION ""
    ::= { affirmedInfrastructurePeeroverloadcontrolPacerSummaryCountersCumEntry 3 }

affirmedInfrastructurePeeroverloadcontrolPacerSummaryCountersCumFailures OBJECT-TYPE
    SYNTAX      Unsigned32
    MAX-ACCESS  read-only
    STATUS      current
    DESCRIPTION ""
    ::= { affirmedInfrastructurePeeroverloadcontrolPacerSummaryCountersCumEntry 4 }

affirmedInfrastructurePeeroverloadcontrolPacerSummaryCountersCumCredits OBJECT-TYPE
    SYNTAX      Unsigned32
    MAX-ACCESS  read-only
    STATUS      current
    DESCRIPTION ""
    ::= { affirmedInfrastructurePeeroverloadcontrolPacerSummaryCountersCumEntry 5 }

affirmedInfrastructurePeeroverloadcontrolPacerSummaryCountersCumRejects OBJECT-TYPE
    SYNTAX      Unsigned32
    MAX-ACCESS  read-only
    STATUS      current
    DESCRIPTION ""
    ::= { affirmedInfrastructurePeeroverloadcontrolPacerSummaryCountersCumEntry 6 }

affirmedInfrastructurePeeroverloadcontrolPacerCountersTable OBJECT-TYPE
    SYNTAX      SEQUENCE OF AffirmedInfrastructurePeeroverloadcontrolPacerCountersEntry
    MAX-ACCESS  not-accessible
    STATUS      current
    DESCRIPTION ""
    ::= { affirmedInfrastructurePeeroverloadcontrol 5 }

affirmedInfrastructurePeeroverloadcontrolPacerCountersEntry OBJECT-TYPE
    SYNTAX      AffirmedInfrastructurePeeroverloadcontrolPacerCountersEntry
    MAX-ACCESS  not-accessible
    STATUS      current
    DESCRIPTION ""
    INDEX { affirmedInfrastructurePeeroverloadcontrolPacerCountersPacername, affirmedInfrastructurePeeroverloadcontrolPacerCountersInstancename, affirmedInfrastructurePeeroverloadcontrolPacerCountersInterval }
        ::= { affirmedInfrastructurePeeroverloadcontrolPacerCountersTable 1 }

AffirmedInfrastructurePeeroverloadcontrolPacerCountersEntry ::=
    SEQUENCE {
        affirmedInfrastructurePeeroverloadcontrolPacerCountersPacername String,
        affirmedInfrastructurePeeroverloadcontrolPacerCountersInstancename String,
        affirmedInfrastructurePeeroverloadcontrolPacerCountersInterval Integer32,
        affirmedInfrastructurePeeroverloadcontrolPacerCountersHighsuccesses Unsigned32,
        affirmedInfrastructurePeeroverloadcontrolPacerCountersMediumsuccesses Unsigned32,
        affirmedInfrastructurePeeroverloadcontrolPacerCountersLowsuccesses Unsigned32,
        affirmedInfrastructurePeeroverloadcontrolPacerCountersHighfailures Unsigned32,
        affirmedInfrastructurePeeroverloadcontrolPacerCountersMediumfailures Unsigned32,
        affirmedInfrastructurePeeroverloadcontrolPacerCountersLowfailures Unsigned32,
        affirmedInfrastructurePeeroverloadcontrolPacerCountersHighcredits Unsigned32,
        affirmedInfrastructurePeeroverloadcontrolPacerCountersMediumcredits Unsigned32,
        affirmedInfrastructurePeeroverloadcontrolPacerCountersLowcredits Unsigned32,
        affirmedInfrastructurePeeroverloadcontrolPacerCountersHighrejects Unsigned32,
        affirmedInfrastructurePeeroverloadcontrolPacerCountersMediumrejects Unsigned32,
        affirmedInfrastructurePeeroverloadcontrolPacerCountersLowrejects Unsigned32
    }

affirmedInfrastructurePeeroverloadcontrolPacerCountersPacername OBJECT-TYPE
    SYNTAX      String
    MAX-ACCESS  not-accessible
    STATUS      current
    DESCRIPTION ""
    ::= { affirmedInfrastructurePeeroverloadcontrolPacerCountersEntry 1 }

affirmedInfrastructurePeeroverloadcontrolPacerCountersInstancename OBJECT-TYPE
    SYNTAX      String
    MAX-ACCESS  not-accessible
    STATUS      current
    DESCRIPTION ""
    ::= { affirmedInfrastructurePeeroverloadcontrolPacerCountersEntry 2 }

affirmedInfrastructurePeeroverloadcontrolPacerCountersInterval OBJECT-TYPE
    SYNTAX      Integer32
    MAX-ACCESS  not-accessible
    STATUS      current
    DESCRIPTION ""
    ::= { affirmedInfrastructurePeeroverloadcontrolPacerCountersEntry 3 }

affirmedInfrastructurePeeroverloadcontrolPacerCountersHighsuccesses OBJECT-TYPE
    SYNTAX      Unsigned32
    MAX-ACCESS  read-only
    STATUS      current
    DESCRIPTION ""
    ::= { affirmedInfrastructurePeeroverloadcontrolPacerCountersEntry 4 }

affirmedInfrastructurePeeroverloadcontrolPacerCountersMediumsuccesses OBJECT-TYPE
    SYNTAX      Unsigned32
    MAX-ACCESS  read-only
    STATUS      current
    DESCRIPTION ""
    ::= { affirmedInfrastructurePeeroverloadcontrolPacerCountersEntry 5 }

affirmedInfrastructurePeeroverloadcontrolPacerCountersLowsuccesses OBJECT-TYPE
    SYNTAX      Unsigned32
    MAX-ACCESS  read-only
    STATUS      current
    DESCRIPTION ""
    ::= { affirmedInfrastructurePeeroverloadcontrolPacerCountersEntry 6 }

affirmedInfrastructurePeeroverloadcontrolPacerCountersHighfailures OBJECT-TYPE
    SYNTAX      Unsigned32
    MAX-ACCESS  read-only
    STATUS      current
    DESCRIPTION ""
    ::= { affirmedInfrastructurePeeroverloadcontrolPacerCountersEntry 7 }

affirmedInfrastructurePeeroverloadcontrolPacerCountersMediumfailures OBJECT-TYPE
    SYNTAX      Unsigned32
    MAX-ACCESS  read-only
    STATUS      current
    DESCRIPTION ""
    ::= { affirmedInfrastructurePeeroverloadcontrolPacerCountersEntry 8 }

affirmedInfrastructurePeeroverloadcontrolPacerCountersLowfailures OBJECT-TYPE
    SYNTAX      Unsigned32
    MAX-ACCESS  read-only
    STATUS      current
    DESCRIPTION ""
    ::= { affirmedInfrastructurePeeroverloadcontrolPacerCountersEntry 9 }

affirmedInfrastructurePeeroverloadcontrolPacerCountersHighcredits OBJECT-TYPE
    SYNTAX      Unsigned32
    MAX-ACCESS  read-only
    STATUS      current
    DESCRIPTION ""
    ::= { affirmedInfrastructurePeeroverloadcontrolPacerCountersEntry 10 }

affirmedInfrastructurePeeroverloadcontrolPacerCountersMediumcredits OBJECT-TYPE
    SYNTAX      Unsigned32
    MAX-ACCESS  read-only
    STATUS      current
    DESCRIPTION ""
    ::= { affirmedInfrastructurePeeroverloadcontrolPacerCountersEntry 11 }

affirmedInfrastructurePeeroverloadcontrolPacerCountersLowcredits OBJECT-TYPE
    SYNTAX      Unsigned32
    MAX-ACCESS  read-only
    STATUS      current
    DESCRIPTION ""
    ::= { affirmedInfrastructurePeeroverloadcontrolPacerCountersEntry 12 }

affirmedInfrastructurePeeroverloadcontrolPacerCountersHighrejects OBJECT-TYPE
    SYNTAX      Unsigned32
    MAX-ACCESS  read-only
    STATUS      current
    DESCRIPTION ""
    ::= { affirmedInfrastructurePeeroverloadcontrolPacerCountersEntry 13 }

affirmedInfrastructurePeeroverloadcontrolPacerCountersMediumrejects OBJECT-TYPE
    SYNTAX      Unsigned32
    MAX-ACCESS  read-only
    STATUS      current
    DESCRIPTION ""
    ::= { affirmedInfrastructurePeeroverloadcontrolPacerCountersEntry 14 }

affirmedInfrastructurePeeroverloadcontrolPacerCountersLowrejects OBJECT-TYPE
    SYNTAX      Unsigned32
    MAX-ACCESS  read-only
    STATUS      current
    DESCRIPTION ""
    ::= { affirmedInfrastructurePeeroverloadcontrolPacerCountersEntry 15 }

affirmedInfrastructurePeeroverloadcontrolPacerCountersCumTable OBJECT-TYPE
    SYNTAX      SEQUENCE OF AffirmedInfrastructurePeeroverloadcontrolPacerCountersCumEntry
    MAX-ACCESS  not-accessible
    STATUS      current
    DESCRIPTION ""
    ::= { affirmedInfrastructurePeeroverloadcontrol 6 }

affirmedInfrastructurePeeroverloadcontrolPacerCountersCumEntry OBJECT-TYPE
    SYNTAX      AffirmedInfrastructurePeeroverloadcontrolPacerCountersCumEntry
    MAX-ACCESS  not-accessible
    STATUS      current
    DESCRIPTION ""
    INDEX { affirmedInfrastructurePeeroverloadcontrolPacerCountersCumPacername, affirmedInfrastructurePeeroverloadcontrolPacerCountersCumInstancename }
        ::= { affirmedInfrastructurePeeroverloadcontrolPacerCountersCumTable 1 }

AffirmedInfrastructurePeeroverloadcontrolPacerCountersCumEntry ::=
    SEQUENCE {
        affirmedInfrastructurePeeroverloadcontrolPacerCountersCumPacername String,
        affirmedInfrastructurePeeroverloadcontrolPacerCountersCumInstancename String,
        affirmedInfrastructurePeeroverloadcontrolPacerCountersCumHighsuccesses Unsigned32,
        affirmedInfrastructurePeeroverloadcontrolPacerCountersCumMediumsuccesses Unsigned32,
        affirmedInfrastructurePeeroverloadcontrolPacerCountersCumLowsuccesses Unsigned32,
        affirmedInfrastructurePeeroverloadcontrolPacerCountersCumHighfailures Unsigned32,
        affirmedInfrastructurePeeroverloadcontrolPacerCountersCumMediumfailures Unsigned32,
        affirmedInfrastructurePeeroverloadcontrolPacerCountersCumLowfailures Unsigned32,
        affirmedInfrastructurePeeroverloadcontrolPacerCountersCumHighcredits Unsigned32,
        affirmedInfrastructurePeeroverloadcontrolPacerCountersCumMediumcredits Unsigned32,
        affirmedInfrastructurePeeroverloadcontrolPacerCountersCumLowcredits Unsigned32,
        affirmedInfrastructurePeeroverloadcontrolPacerCountersCumHighrejects Unsigned32,
        affirmedInfrastructurePeeroverloadcontrolPacerCountersCumMediumrejects Unsigned32,
        affirmedInfrastructurePeeroverloadcontrolPacerCountersCumLowrejects Unsigned32
    }

affirmedInfrastructurePeeroverloadcontrolPacerCountersCumPacername OBJECT-TYPE
    SYNTAX      String
    MAX-ACCESS  not-accessible
    STATUS      current
    DESCRIPTION ""
    ::= { affirmedInfrastructurePeeroverloadcontrolPacerCountersCumEntry 1 }

affirmedInfrastructurePeeroverloadcontrolPacerCountersCumInstancename OBJECT-TYPE
    SYNTAX      String
    MAX-ACCESS  not-accessible
    STATUS      current
    DESCRIPTION ""
    ::= { affirmedInfrastructurePeeroverloadcontrolPacerCountersCumEntry 2 }

affirmedInfrastructurePeeroverloadcontrolPacerCountersCumHighsuccesses OBJECT-TYPE
    SYNTAX      Unsigned32
    MAX-ACCESS  read-only
    STATUS      current
    DESCRIPTION ""
    ::= { affirmedInfrastructurePeeroverloadcontrolPacerCountersCumEntry 3 }

affirmedInfrastructurePeeroverloadcontrolPacerCountersCumMediumsuccesses OBJECT-TYPE
    SYNTAX      Unsigned32
    MAX-ACCESS  read-only
    STATUS      current
    DESCRIPTION ""
    ::= { affirmedInfrastructurePeeroverloadcontrolPacerCountersCumEntry 4 }

affirmedInfrastructurePeeroverloadcontrolPacerCountersCumLowsuccesses OBJECT-TYPE
    SYNTAX      Unsigned32
    MAX-ACCESS  read-only
    STATUS      current
    DESCRIPTION ""
    ::= { affirmedInfrastructurePeeroverloadcontrolPacerCountersCumEntry 5 }

affirmedInfrastructurePeeroverloadcontrolPacerCountersCumHighfailures OBJECT-TYPE
    SYNTAX      Unsigned32
    MAX-ACCESS  read-only
    STATUS      current
    DESCRIPTION ""
    ::= { affirmedInfrastructurePeeroverloadcontrolPacerCountersCumEntry 6 }

affirmedInfrastructurePeeroverloadcontrolPacerCountersCumMediumfailures OBJECT-TYPE
    SYNTAX      Unsigned32
    MAX-ACCESS  read-only
    STATUS      current
    DESCRIPTION ""
    ::= { affirmedInfrastructurePeeroverloadcontrolPacerCountersCumEntry 7 }

affirmedInfrastructurePeeroverloadcontrolPacerCountersCumLowfailures OBJECT-TYPE
    SYNTAX      Unsigned32
    MAX-ACCESS  read-only
    STATUS      current
    DESCRIPTION ""
    ::= { affirmedInfrastructurePeeroverloadcontrolPacerCountersCumEntry 8 }

affirmedInfrastructurePeeroverloadcontrolPacerCountersCumHighcredits OBJECT-TYPE
    SYNTAX      Unsigned32
    MAX-ACCESS  read-only
    STATUS      current
    DESCRIPTION ""
    ::= { affirmedInfrastructurePeeroverloadcontrolPacerCountersCumEntry 9 }

affirmedInfrastructurePeeroverloadcontrolPacerCountersCumMediumcredits OBJECT-TYPE
    SYNTAX      Unsigned32
    MAX-ACCESS  read-only
    STATUS      current
    DESCRIPTION ""
    ::= { affirmedInfrastructurePeeroverloadcontrolPacerCountersCumEntry 10 }

affirmedInfrastructurePeeroverloadcontrolPacerCountersCumLowcredits OBJECT-TYPE
    SYNTAX      Unsigned32
    MAX-ACCESS  read-only
    STATUS      current
    DESCRIPTION ""
    ::= { affirmedInfrastructurePeeroverloadcontrolPacerCountersCumEntry 11 }

affirmedInfrastructurePeeroverloadcontrolPacerCountersCumHighrejects OBJECT-TYPE
    SYNTAX      Unsigned32
    MAX-ACCESS  read-only
    STATUS      current
    DESCRIPTION ""
    ::= { affirmedInfrastructurePeeroverloadcontrolPacerCountersCumEntry 12 }

affirmedInfrastructurePeeroverloadcontrolPacerCountersCumMediumrejects OBJECT-TYPE
    SYNTAX      Unsigned32
    MAX-ACCESS  read-only
    STATUS      current
    DESCRIPTION ""
    ::= { affirmedInfrastructurePeeroverloadcontrolPacerCountersCumEntry 13 }

affirmedInfrastructurePeeroverloadcontrolPacerCountersCumLowrejects OBJECT-TYPE
    SYNTAX      Unsigned32
    MAX-ACCESS  read-only
    STATUS      current
    DESCRIPTION ""
    ::= { affirmedInfrastructurePeeroverloadcontrolPacerCountersCumEntry 14 }

affirmedInfrastructureEdrEdrServerAggrStatsTable OBJECT-TYPE
    SYNTAX      SEQUENCE OF AffirmedInfrastructureEdrEdrServerAggrStatsEntry
    MAX-ACCESS  not-accessible
    STATUS      deprecated
    DESCRIPTION ""
    ::= { affirmedInfrastructureEdr 1 }

affirmedInfrastructureEdrEdrServerAggrStatsEntry OBJECT-TYPE
    SYNTAX      AffirmedInfrastructureEdrEdrServerAggrStatsEntry
    MAX-ACCESS  not-accessible
    STATUS      deprecated
    DESCRIPTION ""
    INDEX { affirmedInfrastructureEdrEdrServerAggrStatsNetworkContext, affirmedInfrastructureEdrEdrServerAggrStatsName }
        ::= { affirmedInfrastructureEdrEdrServerAggrStatsTable 1 }

AffirmedInfrastructureEdrEdrServerAggrStatsEntry ::=
    SEQUENCE {
        affirmedInfrastructureEdrEdrServerAggrStatsNetworkContext String,
        affirmedInfrastructureEdrEdrServerAggrStatsName String,
        affirmedInfrastructureEdrEdrServerAggrStatsState String,
        affirmedInfrastructureEdrEdrServerAggrStatsRecordsSuccess ConfdString,
        affirmedInfrastructureEdrEdrServerAggrStatsBytesSuccess ConfdString,
        affirmedInfrastructureEdrEdrServerAggrStatsRecordsFailed ConfdString,
        affirmedInfrastructureEdrEdrServerAggrStatsBytesFailed ConfdString,
        affirmedInfrastructureEdrEdrServerAggrStatsConnects ConfdString,
        affirmedInfrastructureEdrEdrServerAggrStatsLastStateChange Unsigned32
    }

affirmedInfrastructureEdrEdrServerAggrStatsNetworkContext OBJECT-TYPE
    SYNTAX      String
    MAX-ACCESS  not-accessible
    STATUS      current
    DESCRIPTION "Network Context name associated with this EDR server"
    ::= { affirmedInfrastructureEdrEdrServerAggrStatsEntry 1 }

affirmedInfrastructureEdrEdrServerAggrStatsName OBJECT-TYPE
    SYNTAX      String
    MAX-ACCESS  not-accessible
    STATUS      current
    DESCRIPTION "EDR server name"
    ::= { affirmedInfrastructureEdrEdrServerAggrStatsEntry 2 }

affirmedInfrastructureEdrEdrServerAggrStatsState OBJECT-TYPE
    SYNTAX      String
    MAX-ACCESS  read-only
    STATUS      current
    DESCRIPTION "EDR server state"
    ::= { affirmedInfrastructureEdrEdrServerAggrStatsEntry 3 }

affirmedInfrastructureEdrEdrServerAggrStatsRecordsSuccess OBJECT-TYPE
    SYNTAX      ConfdString
    MAX-ACCESS  read-only
    STATUS      current
    DESCRIPTION "Number of records sent successfully"
    ::= { affirmedInfrastructureEdrEdrServerAggrStatsEntry 4 }

affirmedInfrastructureEdrEdrServerAggrStatsBytesSuccess OBJECT-TYPE
    SYNTAX      ConfdString
    MAX-ACCESS  read-only
    STATUS      current
    DESCRIPTION "Number of bytes sent successfully"
    ::= { affirmedInfrastructureEdrEdrServerAggrStatsEntry 5 }

affirmedInfrastructureEdrEdrServerAggrStatsRecordsFailed OBJECT-TYPE
    SYNTAX      ConfdString
    MAX-ACCESS  read-only
    STATUS      current
    DESCRIPTION "Number of records failed"
    ::= { affirmedInfrastructureEdrEdrServerAggrStatsEntry 6 }

affirmedInfrastructureEdrEdrServerAggrStatsBytesFailed OBJECT-TYPE
    SYNTAX      ConfdString
    MAX-ACCESS  read-only
    STATUS      current
    DESCRIPTION "Number of bytes failed"
    ::= { affirmedInfrastructureEdrEdrServerAggrStatsEntry 7 }

affirmedInfrastructureEdrEdrServerAggrStatsConnects OBJECT-TYPE
    SYNTAX      ConfdString
    MAX-ACCESS  read-only
    STATUS      current
    DESCRIPTION "Number of times connected"
    ::= { affirmedInfrastructureEdrEdrServerAggrStatsEntry 8 }

affirmedInfrastructureEdrEdrServerAggrStatsLastStateChange OBJECT-TYPE
    SYNTAX      Unsigned32
    MAX-ACCESS  read-only
    STATUS      current
    DESCRIPTION "Time of last state change"
    ::= { affirmedInfrastructureEdrEdrServerAggrStatsEntry 9 }

affirmedInfrastructureEdrEdrServerAggrStats2Table OBJECT-TYPE
    SYNTAX      SEQUENCE OF AffirmedInfrastructureEdrEdrServerAggrStats2Entry
    MAX-ACCESS  not-accessible
    STATUS      current
    DESCRIPTION ""
    ::= { affirmedInfrastructureEdr 6 }

affirmedInfrastructureEdrEdrServerAggrStats2Entry OBJECT-TYPE
    SYNTAX      AffirmedInfrastructureEdrEdrServerAggrStats2Entry
    MAX-ACCESS  not-accessible
    STATUS      current
    DESCRIPTION ""
    INDEX { affirmedInfrastructureEdrEdrServerAggrStats2NetworkContext, affirmedInfrastructureEdrEdrServerAggrStats2Name }
        ::= { affirmedInfrastructureEdrEdrServerAggrStats2Table 1 }

AffirmedInfrastructureEdrEdrServerAggrStats2Entry ::=
    SEQUENCE {
        affirmedInfrastructureEdrEdrServerAggrStats2NetworkContext String,
        affirmedInfrastructureEdrEdrServerAggrStats2Name String,
        affirmedInfrastructureEdrEdrServerAggrStats2RecordsSuccess ConfdString,
        affirmedInfrastructureEdrEdrServerAggrStats2BytesSuccess ConfdString,
        affirmedInfrastructureEdrEdrServerAggrStats2RecordsFailed ConfdString,
        affirmedInfrastructureEdrEdrServerAggrStats2BytesFailed ConfdString,
        affirmedInfrastructureEdrEdrServerAggrStats2Connects ConfdString
    }

affirmedInfrastructureEdrEdrServerAggrStats2NetworkContext OBJECT-TYPE
    SYNTAX      String
    MAX-ACCESS  not-accessible
    STATUS      current
    DESCRIPTION "Network Context name associated with this EDR server"
    ::= { affirmedInfrastructureEdrEdrServerAggrStats2Entry 1 }

affirmedInfrastructureEdrEdrServerAggrStats2Name OBJECT-TYPE
    SYNTAX      String
    MAX-ACCESS  not-accessible
    STATUS      current
    DESCRIPTION "EDR server name"
    ::= { affirmedInfrastructureEdrEdrServerAggrStats2Entry 2 }

affirmedInfrastructureEdrEdrServerAggrStats2RecordsSuccess OBJECT-TYPE
    SYNTAX      ConfdString
    MAX-ACCESS  read-only
    STATUS      current
    DESCRIPTION "Number of records sent successfully"
    ::= { affirmedInfrastructureEdrEdrServerAggrStats2Entry 3 }

affirmedInfrastructureEdrEdrServerAggrStats2BytesSuccess OBJECT-TYPE
    SYNTAX      ConfdString
    MAX-ACCESS  read-only
    STATUS      current
    DESCRIPTION "Number of bytes sent successfully"
    ::= { affirmedInfrastructureEdrEdrServerAggrStats2Entry 4 }

affirmedInfrastructureEdrEdrServerAggrStats2RecordsFailed OBJECT-TYPE
    SYNTAX      ConfdString
    MAX-ACCESS  read-only
    STATUS      current
    DESCRIPTION "Number of records failed"
    ::= { affirmedInfrastructureEdrEdrServerAggrStats2Entry 5 }

affirmedInfrastructureEdrEdrServerAggrStats2BytesFailed OBJECT-TYPE
    SYNTAX      ConfdString
    MAX-ACCESS  read-only
    STATUS      current
    DESCRIPTION "Number of bytes failed"
    ::= { affirmedInfrastructureEdrEdrServerAggrStats2Entry 6 }

affirmedInfrastructureEdrEdrServerAggrStats2Connects OBJECT-TYPE
    SYNTAX      ConfdString
    MAX-ACCESS  read-only
    STATUS      current
    DESCRIPTION "Number of times connected"
    ::= { affirmedInfrastructureEdrEdrServerAggrStats2Entry 7 }

affirmedInfrastructureEdrEdrSessionAggrStatsTable OBJECT-TYPE
    SYNTAX      SEQUENCE OF AffirmedInfrastructureEdrEdrSessionAggrStatsEntry
    MAX-ACCESS  not-accessible
    STATUS      current
    DESCRIPTION ""
    ::= { affirmedInfrastructureEdr 2 }

affirmedInfrastructureEdrEdrSessionAggrStatsEntry OBJECT-TYPE
    SYNTAX      AffirmedInfrastructureEdrEdrSessionAggrStatsEntry
    MAX-ACCESS  not-accessible
    STATUS      current
    DESCRIPTION ""
    INDEX { affirmedInfrastructureEdrEdrSessionAggrStatsNetworkContext, affirmedInfrastructureEdrEdrSessionAggrStatsName }
        ::= { affirmedInfrastructureEdrEdrSessionAggrStatsTable 1 }

AffirmedInfrastructureEdrEdrSessionAggrStatsEntry ::=
    SEQUENCE {
        affirmedInfrastructureEdrEdrSessionAggrStatsNetworkContext String,
        affirmedInfrastructureEdrEdrSessionAggrStatsName String,
        affirmedInfrastructureEdrEdrSessionAggrStatsSessionStartSuccess ConfdString,
        affirmedInfrastructureEdrEdrSessionAggrStatsSessionStopSuccess ConfdString,
        affirmedInfrastructureEdrEdrSessionAggrStatsSessionAttemptSuccess ConfdString,
        affirmedInfrastructureEdrEdrSessionAggrStatsSessionInterimSuccess ConfdString,
        affirmedInfrastructureEdrEdrSessionAggrStatsSessionStartFailed ConfdString,
        affirmedInfrastructureEdrEdrSessionAggrStatsSessionStopFailed ConfdString,
        affirmedInfrastructureEdrEdrSessionAggrStatsSessionAttemptFailed ConfdString,
        affirmedInfrastructureEdrEdrSessionAggrStatsSessionInterimFailed ConfdString
    }

affirmedInfrastructureEdrEdrSessionAggrStatsNetworkContext OBJECT-TYPE
    SYNTAX      String
    MAX-ACCESS  not-accessible
    STATUS      current
    DESCRIPTION "Network Context name associated with this EDR server"
    ::= { affirmedInfrastructureEdrEdrSessionAggrStatsEntry 1 }

affirmedInfrastructureEdrEdrSessionAggrStatsName OBJECT-TYPE
    SYNTAX      String
    MAX-ACCESS  not-accessible
    STATUS      current
    DESCRIPTION "EDR server name"
    ::= { affirmedInfrastructureEdrEdrSessionAggrStatsEntry 2 }

affirmedInfrastructureEdrEdrSessionAggrStatsSessionStartSuccess OBJECT-TYPE
    SYNTAX      ConfdString
    MAX-ACCESS  read-only
    STATUS      current
    DESCRIPTION "Number of session start records sent successfully"
    ::= { affirmedInfrastructureEdrEdrSessionAggrStatsEntry 3 }

affirmedInfrastructureEdrEdrSessionAggrStatsSessionStopSuccess OBJECT-TYPE
    SYNTAX      ConfdString
    MAX-ACCESS  read-only
    STATUS      current
    DESCRIPTION "Number of session stop records sent successfully"
    ::= { affirmedInfrastructureEdrEdrSessionAggrStatsEntry 4 }

affirmedInfrastructureEdrEdrSessionAggrStatsSessionAttemptSuccess OBJECT-TYPE
    SYNTAX      ConfdString
    MAX-ACCESS  read-only
    STATUS      current
    DESCRIPTION "Number of session attempt records sent successfully"
    ::= { affirmedInfrastructureEdrEdrSessionAggrStatsEntry 5 }

affirmedInfrastructureEdrEdrSessionAggrStatsSessionInterimSuccess OBJECT-TYPE
    SYNTAX      ConfdString
    MAX-ACCESS  read-only
    STATUS      current
    DESCRIPTION "Number of session interim records sent successfully"
    ::= { affirmedInfrastructureEdrEdrSessionAggrStatsEntry 6 }

affirmedInfrastructureEdrEdrSessionAggrStatsSessionStartFailed OBJECT-TYPE
    SYNTAX      ConfdString
    MAX-ACCESS  read-only
    STATUS      current
    DESCRIPTION "Number of session start records failed"
    ::= { affirmedInfrastructureEdrEdrSessionAggrStatsEntry 7 }

affirmedInfrastructureEdrEdrSessionAggrStatsSessionStopFailed OBJECT-TYPE
    SYNTAX      ConfdString
    MAX-ACCESS  read-only
    STATUS      current
    DESCRIPTION "Number of session stop records failed"
    ::= { affirmedInfrastructureEdrEdrSessionAggrStatsEntry 8 }

affirmedInfrastructureEdrEdrSessionAggrStatsSessionAttemptFailed OBJECT-TYPE
    SYNTAX      ConfdString
    MAX-ACCESS  read-only
    STATUS      current
    DESCRIPTION "Number of session attempt records failed"
    ::= { affirmedInfrastructureEdrEdrSessionAggrStatsEntry 9 }

affirmedInfrastructureEdrEdrSessionAggrStatsSessionInterimFailed OBJECT-TYPE
    SYNTAX      ConfdString
    MAX-ACCESS  read-only
    STATUS      current
    DESCRIPTION "Number of session interim records failed"
    ::= { affirmedInfrastructureEdrEdrSessionAggrStatsEntry 10 }

affirmedInfrastructureEdrEdrBearerAggrStatsTable OBJECT-TYPE
    SYNTAX      SEQUENCE OF AffirmedInfrastructureEdrEdrBearerAggrStatsEntry
    MAX-ACCESS  not-accessible
    STATUS      current
    DESCRIPTION ""
    ::= { affirmedInfrastructureEdr 3 }

affirmedInfrastructureEdrEdrBearerAggrStatsEntry OBJECT-TYPE
    SYNTAX      AffirmedInfrastructureEdrEdrBearerAggrStatsEntry
    MAX-ACCESS  not-accessible
    STATUS      current
    DESCRIPTION ""
    INDEX { affirmedInfrastructureEdrEdrBearerAggrStatsNetworkContext, affirmedInfrastructureEdrEdrBearerAggrStatsName }
        ::= { affirmedInfrastructureEdrEdrBearerAggrStatsTable 1 }

AffirmedInfrastructureEdrEdrBearerAggrStatsEntry ::=
    SEQUENCE {
        affirmedInfrastructureEdrEdrBearerAggrStatsNetworkContext String,
        affirmedInfrastructureEdrEdrBearerAggrStatsName String,
        affirmedInfrastructureEdrEdrBearerAggrStatsBearerStartSuccess ConfdString,
        affirmedInfrastructureEdrEdrBearerAggrStatsBearerStopSuccess ConfdString,
        affirmedInfrastructureEdrEdrBearerAggrStatsBearerAttemptSuccess ConfdString,
        affirmedInfrastructureEdrEdrBearerAggrStatsBearerInterimSuccess ConfdString,
        affirmedInfrastructureEdrEdrBearerAggrStatsBearerStartFailed ConfdString,
        affirmedInfrastructureEdrEdrBearerAggrStatsBearerStopFailed ConfdString,
        affirmedInfrastructureEdrEdrBearerAggrStatsBearerAttemptFailed ConfdString,
        affirmedInfrastructureEdrEdrBearerAggrStatsBearerInterimFailed ConfdString
    }

affirmedInfrastructureEdrEdrBearerAggrStatsNetworkContext OBJECT-TYPE
    SYNTAX      String
    MAX-ACCESS  not-accessible
    STATUS      current
    DESCRIPTION "Network Context name associated with this EDR server"
    ::= { affirmedInfrastructureEdrEdrBearerAggrStatsEntry 1 }

affirmedInfrastructureEdrEdrBearerAggrStatsName OBJECT-TYPE
    SYNTAX      String
    MAX-ACCESS  not-accessible
    STATUS      current
    DESCRIPTION "EDR server name"
    ::= { affirmedInfrastructureEdrEdrBearerAggrStatsEntry 2 }

affirmedInfrastructureEdrEdrBearerAggrStatsBearerStartSuccess OBJECT-TYPE
    SYNTAX      ConfdString
    MAX-ACCESS  read-only
    STATUS      current
    DESCRIPTION "Number of bearer start records sent successfully"
    ::= { affirmedInfrastructureEdrEdrBearerAggrStatsEntry 3 }

affirmedInfrastructureEdrEdrBearerAggrStatsBearerStopSuccess OBJECT-TYPE
    SYNTAX      ConfdString
    MAX-ACCESS  read-only
    STATUS      current
    DESCRIPTION "Number of bearer stop records sent successfully"
    ::= { affirmedInfrastructureEdrEdrBearerAggrStatsEntry 4 }

affirmedInfrastructureEdrEdrBearerAggrStatsBearerAttemptSuccess OBJECT-TYPE
    SYNTAX      ConfdString
    MAX-ACCESS  read-only
    STATUS      current
    DESCRIPTION "Number of bearer attempt records sent successfully"
    ::= { affirmedInfrastructureEdrEdrBearerAggrStatsEntry 5 }

affirmedInfrastructureEdrEdrBearerAggrStatsBearerInterimSuccess OBJECT-TYPE
    SYNTAX      ConfdString
    MAX-ACCESS  read-only
    STATUS      current
    DESCRIPTION "Number of bearer interim records sent successfully"
    ::= { affirmedInfrastructureEdrEdrBearerAggrStatsEntry 6 }

affirmedInfrastructureEdrEdrBearerAggrStatsBearerStartFailed OBJECT-TYPE
    SYNTAX      ConfdString
    MAX-ACCESS  read-only
    STATUS      current
    DESCRIPTION "Number of bearer start records failed"
    ::= { affirmedInfrastructureEdrEdrBearerAggrStatsEntry 7 }

affirmedInfrastructureEdrEdrBearerAggrStatsBearerStopFailed OBJECT-TYPE
    SYNTAX      ConfdString
    MAX-ACCESS  read-only
    STATUS      current
    DESCRIPTION "Number of bearer stop records failed"
    ::= { affirmedInfrastructureEdrEdrBearerAggrStatsEntry 8 }

affirmedInfrastructureEdrEdrBearerAggrStatsBearerAttemptFailed OBJECT-TYPE
    SYNTAX      ConfdString
    MAX-ACCESS  read-only
    STATUS      current
    DESCRIPTION "Number of bearer attempt records failed"
    ::= { affirmedInfrastructureEdrEdrBearerAggrStatsEntry 9 }

affirmedInfrastructureEdrEdrBearerAggrStatsBearerInterimFailed OBJECT-TYPE
    SYNTAX      ConfdString
    MAX-ACCESS  read-only
    STATUS      current
    DESCRIPTION "Number of bearer interim records failed"
    ::= { affirmedInfrastructureEdrEdrBearerAggrStatsEntry 10 }

affirmedInfrastructureEdrEdrFlowAggrStatsTable OBJECT-TYPE
    SYNTAX      SEQUENCE OF AffirmedInfrastructureEdrEdrFlowAggrStatsEntry
    MAX-ACCESS  not-accessible
    STATUS      current
    DESCRIPTION ""
    ::= { affirmedInfrastructureEdr 4 }

affirmedInfrastructureEdrEdrFlowAggrStatsEntry OBJECT-TYPE
    SYNTAX      AffirmedInfrastructureEdrEdrFlowAggrStatsEntry
    MAX-ACCESS  not-accessible
    STATUS      current
    DESCRIPTION ""
    INDEX { affirmedInfrastructureEdrEdrFlowAggrStatsNetworkContext, affirmedInfrastructureEdrEdrFlowAggrStatsName }
        ::= { affirmedInfrastructureEdrEdrFlowAggrStatsTable 1 }

AffirmedInfrastructureEdrEdrFlowAggrStatsEntry ::=
    SEQUENCE {
        affirmedInfrastructureEdrEdrFlowAggrStatsNetworkContext String,
        affirmedInfrastructureEdrEdrFlowAggrStatsName String,
        affirmedInfrastructureEdrEdrFlowAggrStatsFlowStartSuccess ConfdString,
        affirmedInfrastructureEdrEdrFlowAggrStatsFlowStopSuccess ConfdString,
        affirmedInfrastructureEdrEdrFlowAggrStatsFlowInterimSuccess ConfdString,
        affirmedInfrastructureEdrEdrFlowAggrStatsFlowStartFailed ConfdString,
        affirmedInfrastructureEdrEdrFlowAggrStatsFlowStopFailed ConfdString,
        affirmedInfrastructureEdrEdrFlowAggrStatsFlowInterimFailed ConfdString
    }

affirmedInfrastructureEdrEdrFlowAggrStatsNetworkContext OBJECT-TYPE
    SYNTAX      String
    MAX-ACCESS  not-accessible
    STATUS      current
    DESCRIPTION "Network Context name associated with this EDR server"
    ::= { affirmedInfrastructureEdrEdrFlowAggrStatsEntry 1 }

affirmedInfrastructureEdrEdrFlowAggrStatsName OBJECT-TYPE
    SYNTAX      String
    MAX-ACCESS  not-accessible
    STATUS      current
    DESCRIPTION "EDR server name"
    ::= { affirmedInfrastructureEdrEdrFlowAggrStatsEntry 2 }

affirmedInfrastructureEdrEdrFlowAggrStatsFlowStartSuccess OBJECT-TYPE
    SYNTAX      ConfdString
    MAX-ACCESS  read-only
    STATUS      current
    DESCRIPTION "Number of flow start records sent successfully"
    ::= { affirmedInfrastructureEdrEdrFlowAggrStatsEntry 3 }

affirmedInfrastructureEdrEdrFlowAggrStatsFlowStopSuccess OBJECT-TYPE
    SYNTAX      ConfdString
    MAX-ACCESS  read-only
    STATUS      current
    DESCRIPTION "Number of flow stop records sent successfully"
    ::= { affirmedInfrastructureEdrEdrFlowAggrStatsEntry 4 }

affirmedInfrastructureEdrEdrFlowAggrStatsFlowInterimSuccess OBJECT-TYPE
    SYNTAX      ConfdString
    MAX-ACCESS  read-only
    STATUS      current
    DESCRIPTION "Number of flow interim records sent successfully"
    ::= { affirmedInfrastructureEdrEdrFlowAggrStatsEntry 5 }

affirmedInfrastructureEdrEdrFlowAggrStatsFlowStartFailed OBJECT-TYPE
    SYNTAX      ConfdString
    MAX-ACCESS  read-only
    STATUS      current
    DESCRIPTION "Number of flow start records failed"
    ::= { affirmedInfrastructureEdrEdrFlowAggrStatsEntry 6 }

affirmedInfrastructureEdrEdrFlowAggrStatsFlowStopFailed OBJECT-TYPE
    SYNTAX      ConfdString
    MAX-ACCESS  read-only
    STATUS      current
    DESCRIPTION "Number of flow stop records failed"
    ::= { affirmedInfrastructureEdrEdrFlowAggrStatsEntry 7 }

affirmedInfrastructureEdrEdrFlowAggrStatsFlowInterimFailed OBJECT-TYPE
    SYNTAX      ConfdString
    MAX-ACCESS  read-only
    STATUS      current
    DESCRIPTION "Number of flow interim records failed"
    ::= { affirmedInfrastructureEdrEdrFlowAggrStatsEntry 8 }

affirmedInfrastructureEdrEdrHttpAggrStatsTable OBJECT-TYPE
    SYNTAX      SEQUENCE OF AffirmedInfrastructureEdrEdrHttpAggrStatsEntry
    MAX-ACCESS  not-accessible
    STATUS      current
    DESCRIPTION ""
    ::= { affirmedInfrastructureEdr 5 }

affirmedInfrastructureEdrEdrHttpAggrStatsEntry OBJECT-TYPE
    SYNTAX      AffirmedInfrastructureEdrEdrHttpAggrStatsEntry
    MAX-ACCESS  not-accessible
    STATUS      current
    DESCRIPTION ""
    INDEX { affirmedInfrastructureEdrEdrHttpAggrStatsNetworkContext, affirmedInfrastructureEdrEdrHttpAggrStatsName }
        ::= { affirmedInfrastructureEdrEdrHttpAggrStatsTable 1 }

AffirmedInfrastructureEdrEdrHttpAggrStatsEntry ::=
    SEQUENCE {
        affirmedInfrastructureEdrEdrHttpAggrStatsNetworkContext String,
        affirmedInfrastructureEdrEdrHttpAggrStatsName String,
        affirmedInfrastructureEdrEdrHttpAggrStatsHttpSuccess ConfdString,
        affirmedInfrastructureEdrEdrHttpAggrStatsHttpFailed ConfdString
    }

affirmedInfrastructureEdrEdrHttpAggrStatsNetworkContext OBJECT-TYPE
    SYNTAX      String
    MAX-ACCESS  not-accessible
    STATUS      current
    DESCRIPTION "Network Context name associated with this EDR server"
    ::= { affirmedInfrastructureEdrEdrHttpAggrStatsEntry 1 }

affirmedInfrastructureEdrEdrHttpAggrStatsName OBJECT-TYPE
    SYNTAX      String
    MAX-ACCESS  not-accessible
    STATUS      current
    DESCRIPTION "EDR server name"
    ::= { affirmedInfrastructureEdrEdrHttpAggrStatsEntry 2 }

affirmedInfrastructureEdrEdrHttpAggrStatsHttpSuccess OBJECT-TYPE
    SYNTAX      ConfdString
    MAX-ACCESS  read-only
    STATUS      current
    DESCRIPTION "Number of http records sent successfully"
    ::= { affirmedInfrastructureEdrEdrHttpAggrStatsEntry 3 }

affirmedInfrastructureEdrEdrHttpAggrStatsHttpFailed OBJECT-TYPE
    SYNTAX      ConfdString
    MAX-ACCESS  read-only
    STATUS      current
    DESCRIPTION "Number of http records failed"
    ::= { affirmedInfrastructureEdrEdrHttpAggrStatsEntry 4 }

affirmedInfrastructureEdrEdrPilotAggrStatsTable OBJECT-TYPE
    SYNTAX      SEQUENCE OF AffirmedInfrastructureEdrEdrPilotAggrStatsEntry
    MAX-ACCESS  not-accessible
    STATUS      current
    DESCRIPTION ""
    ::= { affirmedInfrastructureEdr 7 }

affirmedInfrastructureEdrEdrPilotAggrStatsEntry OBJECT-TYPE
    SYNTAX      AffirmedInfrastructureEdrEdrPilotAggrStatsEntry
    MAX-ACCESS  not-accessible
    STATUS      current
    DESCRIPTION ""
    INDEX { affirmedInfrastructureEdrEdrPilotAggrStatsNetworkContext, affirmedInfrastructureEdrEdrPilotAggrStatsName }
        ::= { affirmedInfrastructureEdrEdrPilotAggrStatsTable 1 }

AffirmedInfrastructureEdrEdrPilotAggrStatsEntry ::=
    SEQUENCE {
        affirmedInfrastructureEdrEdrPilotAggrStatsNetworkContext String,
        affirmedInfrastructureEdrEdrPilotAggrStatsName String,
        affirmedInfrastructureEdrEdrPilotAggrStatsPilotStartSuccess ConfdString,
        affirmedInfrastructureEdrEdrPilotAggrStatsPilotStopSuccess ConfdString,
        affirmedInfrastructureEdrEdrPilotAggrStatsPilotNatBindingStartSuccess ConfdString,
        affirmedInfrastructureEdrEdrPilotAggrStatsPilotNatBindingStopSuccess ConfdString,
        affirmedInfrastructureEdrEdrPilotAggrStatsPilotRatTypeChangeSuccess ConfdString,
        affirmedInfrastructureEdrEdrPilotAggrStatsPilotStartFailed ConfdString,
        affirmedInfrastructureEdrEdrPilotAggrStatsPilotStopFailed ConfdString,
        affirmedInfrastructureEdrEdrPilotAggrStatsPilotNatBindingStartFailed ConfdString,
        affirmedInfrastructureEdrEdrPilotAggrStatsPilotNatBindingStopFailed ConfdString,
        affirmedInfrastructureEdrEdrPilotAggrStatsPilotRatTypeChangeFailed ConfdString
    }

affirmedInfrastructureEdrEdrPilotAggrStatsNetworkContext OBJECT-TYPE
    SYNTAX      String
    MAX-ACCESS  not-accessible
    STATUS      current
    DESCRIPTION "Network Context name associated with this EDR server"
    ::= { affirmedInfrastructureEdrEdrPilotAggrStatsEntry 1 }

affirmedInfrastructureEdrEdrPilotAggrStatsName OBJECT-TYPE
    SYNTAX      String
    MAX-ACCESS  not-accessible
    STATUS      current
    DESCRIPTION "EDR server name"
    ::= { affirmedInfrastructureEdrEdrPilotAggrStatsEntry 2 }

affirmedInfrastructureEdrEdrPilotAggrStatsPilotStartSuccess OBJECT-TYPE
    SYNTAX      ConfdString
    MAX-ACCESS  read-only
    STATUS      current
    DESCRIPTION "Number of pilot start records sent successfully"
    ::= { affirmedInfrastructureEdrEdrPilotAggrStatsEntry 3 }

affirmedInfrastructureEdrEdrPilotAggrStatsPilotStopSuccess OBJECT-TYPE
    SYNTAX      ConfdString
    MAX-ACCESS  read-only
    STATUS      current
    DESCRIPTION "Number of pilot stop records sent successfully"
    ::= { affirmedInfrastructureEdrEdrPilotAggrStatsEntry 4 }

affirmedInfrastructureEdrEdrPilotAggrStatsPilotNatBindingStartSuccess OBJECT-TYPE
    SYNTAX      ConfdString
    MAX-ACCESS  read-only
    STATUS      current
    DESCRIPTION "Number of pilot nat binding start records sent successfully"
    ::= { affirmedInfrastructureEdrEdrPilotAggrStatsEntry 5 }

affirmedInfrastructureEdrEdrPilotAggrStatsPilotNatBindingStopSuccess OBJECT-TYPE
    SYNTAX      ConfdString
    MAX-ACCESS  read-only
    STATUS      current
    DESCRIPTION "Number of pilot nat binding stop records sent successfully"
    ::= { affirmedInfrastructureEdrEdrPilotAggrStatsEntry 6 }

affirmedInfrastructureEdrEdrPilotAggrStatsPilotRatTypeChangeSuccess OBJECT-TYPE
    SYNTAX      ConfdString
    MAX-ACCESS  read-only
    STATUS      current
    DESCRIPTION "Number of pilot rat type change records sent successfully"
    ::= { affirmedInfrastructureEdrEdrPilotAggrStatsEntry 7 }

affirmedInfrastructureEdrEdrPilotAggrStatsPilotStartFailed OBJECT-TYPE
    SYNTAX      ConfdString
    MAX-ACCESS  read-only
    STATUS      current
    DESCRIPTION "Number of pilot start records failed"
    ::= { affirmedInfrastructureEdrEdrPilotAggrStatsEntry 8 }

affirmedInfrastructureEdrEdrPilotAggrStatsPilotStopFailed OBJECT-TYPE
    SYNTAX      ConfdString
    MAX-ACCESS  read-only
    STATUS      current
    DESCRIPTION "Number of pilot stop records failed"
    ::= { affirmedInfrastructureEdrEdrPilotAggrStatsEntry 9 }

affirmedInfrastructureEdrEdrPilotAggrStatsPilotNatBindingStartFailed OBJECT-TYPE
    SYNTAX      ConfdString
    MAX-ACCESS  read-only
    STATUS      current
    DESCRIPTION "Number of pilot nat binding start records failed"
    ::= { affirmedInfrastructureEdrEdrPilotAggrStatsEntry 10 }

affirmedInfrastructureEdrEdrPilotAggrStatsPilotNatBindingStopFailed OBJECT-TYPE
    SYNTAX      ConfdString
    MAX-ACCESS  read-only
    STATUS      current
    DESCRIPTION "Number of pilot nat binding stop records failed"
    ::= { affirmedInfrastructureEdrEdrPilotAggrStatsEntry 11 }

affirmedInfrastructureEdrEdrPilotAggrStatsPilotRatTypeChangeFailed OBJECT-TYPE
    SYNTAX      ConfdString
    MAX-ACCESS  read-only
    STATUS      current
    DESCRIPTION "Number of pilot rat type change records failed"
    ::= { affirmedInfrastructureEdrEdrPilotAggrStatsEntry 12 }

affirmedInfrastructureEdrEdrRTTAggrStatsTable OBJECT-TYPE
    SYNTAX      SEQUENCE OF AffirmedInfrastructureEdrEdrRTTAggrStatsEntry
    MAX-ACCESS  not-accessible
    STATUS      current
    DESCRIPTION ""
    ::= { affirmedInfrastructureEdr 8 }

affirmedInfrastructureEdrEdrRTTAggrStatsEntry OBJECT-TYPE
    SYNTAX      AffirmedInfrastructureEdrEdrRTTAggrStatsEntry
    MAX-ACCESS  not-accessible
    STATUS      current
    DESCRIPTION ""
    INDEX { affirmedInfrastructureEdrEdrRTTAggrStatsNetworkContext, affirmedInfrastructureEdrEdrRTTAggrStatsName }
        ::= { affirmedInfrastructureEdrEdrRTTAggrStatsTable 1 }

AffirmedInfrastructureEdrEdrRTTAggrStatsEntry ::=
    SEQUENCE {
        affirmedInfrastructureEdrEdrRTTAggrStatsNetworkContext String,
        affirmedInfrastructureEdrEdrRTTAggrStatsName String,
        affirmedInfrastructureEdrEdrRTTAggrStatsRttGtpS5Success ConfdString,
        affirmedInfrastructureEdrEdrRTTAggrStatsRttGtpS8Success ConfdString,
        affirmedInfrastructureEdrEdrRTTAggrStatsRttGtpS11Success ConfdString,
        affirmedInfrastructureEdrEdrRTTAggrStatsRttGtpS4Success ConfdString,
        affirmedInfrastructureEdrEdrRTTAggrStatsRttGtpS2ASuccess ConfdString,
        affirmedInfrastructureEdrEdrRTTAggrStatsRttGtpS2BSuccess ConfdString,
        affirmedInfrastructureEdrEdrRTTAggrStatsRttGtpGNSuccess ConfdString,
        affirmedInfrastructureEdrEdrRTTAggrStatsRttGtpGPSuccess ConfdString,
        affirmedInfrastructureEdrEdrRTTAggrStatsRttDiameterGxSuccess ConfdString,
        affirmedInfrastructureEdrEdrRTTAggrStatsRttDiameterGySuccess ConfdString,
        affirmedInfrastructureEdrEdrRTTAggrStatsRttDiameterS6BSuccess ConfdString,
        affirmedInfrastructureEdrEdrRTTAggrStatsRttGtpS5Failed ConfdString,
        affirmedInfrastructureEdrEdrRTTAggrStatsRttGtpS8Failed ConfdString,
        affirmedInfrastructureEdrEdrRTTAggrStatsRttGtpS11Failed ConfdString,
        affirmedInfrastructureEdrEdrRTTAggrStatsRttGtpS4Failed ConfdString,
        affirmedInfrastructureEdrEdrRTTAggrStatsRttGtpS2AFailed ConfdString,
        affirmedInfrastructureEdrEdrRTTAggrStatsRttGtpS2BFailed ConfdString,
        affirmedInfrastructureEdrEdrRTTAggrStatsRttGtpGNFailed ConfdString,
        affirmedInfrastructureEdrEdrRTTAggrStatsRttGtpGPFailed ConfdString,
        affirmedInfrastructureEdrEdrRTTAggrStatsRttDiameterGxFailed ConfdString,
        affirmedInfrastructureEdrEdrRTTAggrStatsRttDiameterGyFailed ConfdString,
        affirmedInfrastructureEdrEdrRTTAggrStatsRttDiameterS6BFailed ConfdString,
        affirmedInfrastructureEdrEdrRTTAggrStatsRttDiameterSWmSuccess ConfdString,
        affirmedInfrastructureEdrEdrRTTAggrStatsRttIkeSWuSuccess ConfdString,
        affirmedInfrastructureEdrEdrRTTAggrStatsRttDiameterSWmFailed ConfdString,
        affirmedInfrastructureEdrEdrRTTAggrStatsRttIkeSwuFailed ConfdString
    }

affirmedInfrastructureEdrEdrRTTAggrStatsNetworkContext OBJECT-TYPE
    SYNTAX      String
    MAX-ACCESS  not-accessible
    STATUS      current
    DESCRIPTION "Network Context name associated with this EDR server"
    ::= { affirmedInfrastructureEdrEdrRTTAggrStatsEntry 1 }

affirmedInfrastructureEdrEdrRTTAggrStatsName OBJECT-TYPE
    SYNTAX      String
    MAX-ACCESS  not-accessible
    STATUS      current
    DESCRIPTION "EDR server name"
    ::= { affirmedInfrastructureEdrEdrRTTAggrStatsEntry 2 }

affirmedInfrastructureEdrEdrRTTAggrStatsRttGtpS5Success OBJECT-TYPE
    SYNTAX      ConfdString
    MAX-ACCESS  read-only
    STATUS      current
    DESCRIPTION "Number of rtt GTP S5 records sent successfully"
    ::= { affirmedInfrastructureEdrEdrRTTAggrStatsEntry 3 }

affirmedInfrastructureEdrEdrRTTAggrStatsRttGtpS8Success OBJECT-TYPE
    SYNTAX      ConfdString
    MAX-ACCESS  read-only
    STATUS      current
    DESCRIPTION "Number of rtt GTP S8 records sent successfully"
    ::= { affirmedInfrastructureEdrEdrRTTAggrStatsEntry 4 }

affirmedInfrastructureEdrEdrRTTAggrStatsRttGtpS11Success OBJECT-TYPE
    SYNTAX      ConfdString
    MAX-ACCESS  read-only
    STATUS      current
    DESCRIPTION "Number of rtt GTP S11 records sent successfully"
    ::= { affirmedInfrastructureEdrEdrRTTAggrStatsEntry 5 }

affirmedInfrastructureEdrEdrRTTAggrStatsRttGtpS4Success OBJECT-TYPE
    SYNTAX      ConfdString
    MAX-ACCESS  read-only
    STATUS      current
    DESCRIPTION "Number of rtt GTP S4 records sent successfully"
    ::= { affirmedInfrastructureEdrEdrRTTAggrStatsEntry 6 }

affirmedInfrastructureEdrEdrRTTAggrStatsRttGtpS2ASuccess OBJECT-TYPE
    SYNTAX      ConfdString
    MAX-ACCESS  read-only
    STATUS      current
    DESCRIPTION "Number of rtt GTP S2A records sent successfully"
    ::= { affirmedInfrastructureEdrEdrRTTAggrStatsEntry 7 }

affirmedInfrastructureEdrEdrRTTAggrStatsRttGtpS2BSuccess OBJECT-TYPE
    SYNTAX      ConfdString
    MAX-ACCESS  read-only
    STATUS      current
    DESCRIPTION "Number of rtt GTP S2B records sent successfully"
    ::= { affirmedInfrastructureEdrEdrRTTAggrStatsEntry 8 }

affirmedInfrastructureEdrEdrRTTAggrStatsRttGtpGNSuccess OBJECT-TYPE
    SYNTAX      ConfdString
    MAX-ACCESS  read-only
    STATUS      current
    DESCRIPTION "Number of rtt GTP GN records sent successfully"
    ::= { affirmedInfrastructureEdrEdrRTTAggrStatsEntry 9 }

affirmedInfrastructureEdrEdrRTTAggrStatsRttGtpGPSuccess OBJECT-TYPE
    SYNTAX      ConfdString
    MAX-ACCESS  read-only
    STATUS      current
    DESCRIPTION "Number of rtt GTP GP records sent successfully"
    ::= { affirmedInfrastructureEdrEdrRTTAggrStatsEntry 10 }

affirmedInfrastructureEdrEdrRTTAggrStatsRttDiameterGxSuccess OBJECT-TYPE
    SYNTAX      ConfdString
    MAX-ACCESS  read-only
    STATUS      current
    DESCRIPTION "Number of rtt diameter gx records sent successfully"
    ::= { affirmedInfrastructureEdrEdrRTTAggrStatsEntry 11 }

affirmedInfrastructureEdrEdrRTTAggrStatsRttDiameterGySuccess OBJECT-TYPE
    SYNTAX      ConfdString
    MAX-ACCESS  read-only
    STATUS      current
    DESCRIPTION "Number of rtt diameter gy records sent successfully"
    ::= { affirmedInfrastructureEdrEdrRTTAggrStatsEntry 12 }

affirmedInfrastructureEdrEdrRTTAggrStatsRttDiameterS6BSuccess OBJECT-TYPE
    SYNTAX      ConfdString
    MAX-ACCESS  read-only
    STATUS      current
    DESCRIPTION "Number of rtt diameter S6B records sent successfully"
    ::= { affirmedInfrastructureEdrEdrRTTAggrStatsEntry 13 }

affirmedInfrastructureEdrEdrRTTAggrStatsRttGtpS5Failed OBJECT-TYPE
    SYNTAX      ConfdString
    MAX-ACCESS  read-only
    STATUS      current
    DESCRIPTION "Number of rtt GTP S5 records failed"
    ::= { affirmedInfrastructureEdrEdrRTTAggrStatsEntry 14 }

affirmedInfrastructureEdrEdrRTTAggrStatsRttGtpS8Failed OBJECT-TYPE
    SYNTAX      ConfdString
    MAX-ACCESS  read-only
    STATUS      current
    DESCRIPTION "Number of rtt GTP S8 records failed"
    ::= { affirmedInfrastructureEdrEdrRTTAggrStatsEntry 15 }

affirmedInfrastructureEdrEdrRTTAggrStatsRttGtpS11Failed OBJECT-TYPE
    SYNTAX      ConfdString
    MAX-ACCESS  read-only
    STATUS      current
    DESCRIPTION "Number of rtt GTP S11 records failed"
    ::= { affirmedInfrastructureEdrEdrRTTAggrStatsEntry 16 }

affirmedInfrastructureEdrEdrRTTAggrStatsRttGtpS4Failed OBJECT-TYPE
    SYNTAX      ConfdString
    MAX-ACCESS  read-only
    STATUS      current
    DESCRIPTION "Number of rtt GTP S4 records failed"
    ::= { affirmedInfrastructureEdrEdrRTTAggrStatsEntry 17 }

affirmedInfrastructureEdrEdrRTTAggrStatsRttGtpS2AFailed OBJECT-TYPE
    SYNTAX      ConfdString
    MAX-ACCESS  read-only
    STATUS      current
    DESCRIPTION "Number of rtt GTP S2A records failed"
    ::= { affirmedInfrastructureEdrEdrRTTAggrStatsEntry 18 }

affirmedInfrastructureEdrEdrRTTAggrStatsRttGtpS2BFailed OBJECT-TYPE
    SYNTAX      ConfdString
    MAX-ACCESS  read-only
    STATUS      current
    DESCRIPTION "Number of rtt GTP S2B records failed"
    ::= { affirmedInfrastructureEdrEdrRTTAggrStatsEntry 19 }

affirmedInfrastructureEdrEdrRTTAggrStatsRttGtpGNFailed OBJECT-TYPE
    SYNTAX      ConfdString
    MAX-ACCESS  read-only
    STATUS      current
    DESCRIPTION "Number of rtt GTP GN records failed"
    ::= { affirmedInfrastructureEdrEdrRTTAggrStatsEntry 20 }

affirmedInfrastructureEdrEdrRTTAggrStatsRttGtpGPFailed OBJECT-TYPE
    SYNTAX      ConfdString
    MAX-ACCESS  read-only
    STATUS      current
    DESCRIPTION "Number of rtt GTP GP records failed"
    ::= { affirmedInfrastructureEdrEdrRTTAggrStatsEntry 21 }

affirmedInfrastructureEdrEdrRTTAggrStatsRttDiameterGxFailed OBJECT-TYPE
    SYNTAX      ConfdString
    MAX-ACCESS  read-only
    STATUS      current
    DESCRIPTION "Number of rtt diameter gx records failed"
    ::= { affirmedInfrastructureEdrEdrRTTAggrStatsEntry 22 }

affirmedInfrastructureEdrEdrRTTAggrStatsRttDiameterGyFailed OBJECT-TYPE
    SYNTAX      ConfdString
    MAX-ACCESS  read-only
    STATUS      current
    DESCRIPTION "Number of rtt diameter gy records failed"
    ::= { affirmedInfrastructureEdrEdrRTTAggrStatsEntry 23 }

affirmedInfrastructureEdrEdrRTTAggrStatsRttDiameterS6BFailed OBJECT-TYPE
    SYNTAX      ConfdString
    MAX-ACCESS  read-only
    STATUS      current
    DESCRIPTION "Number of rtt diameter S6B records failed"
    ::= { affirmedInfrastructureEdrEdrRTTAggrStatsEntry 24 }

affirmedInfrastructureEdrEdrRTTAggrStatsRttDiameterSWmSuccess OBJECT-TYPE
    SYNTAX      ConfdString
    MAX-ACCESS  read-only
    STATUS      current
    DESCRIPTION "Number of rtt diameter SWm records sent successfully"
    ::= { affirmedInfrastructureEdrEdrRTTAggrStatsEntry 25 }

affirmedInfrastructureEdrEdrRTTAggrStatsRttIkeSWuSuccess OBJECT-TYPE
    SYNTAX      ConfdString
    MAX-ACCESS  read-only
    STATUS      current
    DESCRIPTION "Number of rtt ike SWu records sent successfully"
    ::= { affirmedInfrastructureEdrEdrRTTAggrStatsEntry 26 }

affirmedInfrastructureEdrEdrRTTAggrStatsRttDiameterSWmFailed OBJECT-TYPE
    SYNTAX      ConfdString
    MAX-ACCESS  read-only
    STATUS      current
    DESCRIPTION "Number of rtt diameter SWm records failed"
    ::= { affirmedInfrastructureEdrEdrRTTAggrStatsEntry 27 }

affirmedInfrastructureEdrEdrRTTAggrStatsRttIkeSwuFailed OBJECT-TYPE
    SYNTAX      ConfdString
    MAX-ACCESS  read-only
    STATUS      current
    DESCRIPTION "Number of rtt ike SWu records failed"
    ::= { affirmedInfrastructureEdrEdrRTTAggrStatsEntry 28 }

END

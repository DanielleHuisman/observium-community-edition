AFFIRMED-IPDATAPATH-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedIpdatapathMIB MODULE-IDENTITY
    ORGANIZATION "Affirmed Networks, Inc."
    CONTACT-INFO "Affirmed Networks, Inc. 35 Nagog Park, Acton, MA, USA"
    DESCRIPTION ""
    ::= { 1 3 6 1 4 1 37963 10 26 }

String ::= TEXTUAL-CONVENTION
    DISPLAY-HINT "1t"
    STATUS      current
    DESCRIPTION "xs:string"
    SYNTAX      OCTET STRING

affirmedIpDataPathConfig OBJECT IDENTIFIER ::= { affirmedIpdatapathMIB 1 }

affirmedIpDataPathConfigDpi OBJECT IDENTIFIER ::= { affirmedIpDataPathConfig 1 }

affirmedIpDataPathConfigDpiDpiDetectionVersionTable OBJECT-TYPE
    SYNTAX      SEQUENCE OF AffirmedIpDataPathConfigDpiDpiDetectionVersionEntry
    MAX-ACCESS  not-accessible
    STATUS      current
    DESCRIPTION ""
    ::= { affirmedIpDataPathConfigDpi 1 }

affirmedIpDataPathConfigDpiDpiDetectionVersionEntry OBJECT-TYPE
    SYNTAX      AffirmedIpDataPathConfigDpiDpiDetectionVersionEntry
    MAX-ACCESS  not-accessible
    STATUS      current
    DESCRIPTION ""
    INDEX { affirmedIpDataPathConfigDpiDpiDetectionVersionId }
        ::= { affirmedIpDataPathConfigDpiDpiDetectionVersionTable 1 }

AffirmedIpDataPathConfigDpiDpiDetectionVersionEntry ::=
    SEQUENCE {
        affirmedIpDataPathConfigDpiDpiDetectionVersionId INTEGER,
        affirmedIpDataPathConfigDpiDpiDetectionVersionDetection-version String,
        affirmedIpDataPathConfigDpiDpiDetectionVersionDetection-md5sum String,
        affirmedIpDataPathConfigDpiDpiDetectionVersionDecoder-version String,
        affirmedIpDataPathConfigDpiDpiDetectionVersionDpixml-md5sum String,
        affirmedIpDataPathConfigDpiDpiDetectionVersionCdc-detection-version String,
        affirmedIpDataPathConfigDpiDpiDetectionVersionCdc-detection-md5sum String
    }

affirmedIpDataPathConfigDpiDpiDetectionVersionId OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION ""
    ::= { affirmedIpDataPathConfigDpiDpiDetectionVersionEntry 1 }

affirmedIpDataPathConfigDpiDpiDetectionVersionDetection-version OBJECT-TYPE
    SYNTAX      String
    MAX-ACCESS  read-only
    STATUS      current
    DESCRIPTION ""
    ::= { affirmedIpDataPathConfigDpiDpiDetectionVersionEntry 2 }

affirmedIpDataPathConfigDpiDpiDetectionVersionDetection-md5sum OBJECT-TYPE
    SYNTAX      String
    MAX-ACCESS  read-only
    STATUS      current
    DESCRIPTION ""
    ::= { affirmedIpDataPathConfigDpiDpiDetectionVersionEntry 3 }

affirmedIpDataPathConfigDpiDpiDetectionVersionDecoder-version OBJECT-TYPE
    SYNTAX      String
    MAX-ACCESS  read-only
    STATUS      current
    DESCRIPTION ""
    ::= { affirmedIpDataPathConfigDpiDpiDetectionVersionEntry 4 }

affirmedIpDataPathConfigDpiDpiDetectionVersionDpixml-md5sum OBJECT-TYPE
    SYNTAX      String
    MAX-ACCESS  read-only
    STATUS      current
    DESCRIPTION ""
    ::= { affirmedIpDataPathConfigDpiDpiDetectionVersionEntry 5 }

affirmedIpDataPathConfigDpiDpiDetectionVersionCdc-detection-version OBJECT-TYPE
    SYNTAX      String
    MAX-ACCESS  read-only
    STATUS      current
    DESCRIPTION ""
    ::= { affirmedIpDataPathConfigDpiDpiDetectionVersionEntry 6 }

affirmedIpDataPathConfigDpiDpiDetectionVersionCdc-detection-md5sum OBJECT-TYPE
    SYNTAX      String
    MAX-ACCESS  read-only
    STATUS      current
    DESCRIPTION ""
    ::= { affirmedIpDataPathConfigDpiDpiDetectionVersionEntry 7 }

END

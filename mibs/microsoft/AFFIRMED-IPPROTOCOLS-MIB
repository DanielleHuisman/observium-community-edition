AFFIRMED-IPPROTOCOLS-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedIpprotocolsMIB MODULE-IDENTITY
    ORGANIZATION "Affirmed Networks, Inc."
    CONTACT-INFO "Affirmed Networks, Inc. 35 Nagog Park, Acton, MA, USA"
    DESCRIPTION ""
    ::= { 1 3 6 1 4 1 37963 10 8 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedIpProtocols OBJECT IDENTIFIER ::= { affirmedIpprotocolsMIB 1 }

affirmedIpProtocolsPolicy OBJECT IDENTIFIER ::= { affirmedIpProtocols 4 }

affirmedIpProtocolsOspfv3 OBJECT IDENTIFIER ::= { affirmedIpProtocols 6 }

affirmedIpProtocolsBfd OBJECT IDENTIFIER ::= { affirmedIpProtocols 5 }

affirmedIpProtocolsNat OBJECT IDENTIFIER ::= { affirmedIpProtocols 8 }

affirmedIpProtocolsNatGuaranteed OBJECT IDENTIFIER ::= { affirmedIpProtocolsNat 1 }

affirmedIpProtocolsNatDeterministic OBJECT IDENTIFIER ::= { affirmedIpProtocolsNat 2 }

affirmedIpProtocolsIpTcp OBJECT IDENTIFIER ::= { affirmedIpProtocols 7 }

affirmedIpProtocolsIpTcpStatistics OBJECT IDENTIFIER ::= { affirmedIpProtocolsIpTcp 1 }

affirmedIpProtocolsIpTcpStatisticsClusterLevel OBJECT IDENTIFIER ::= { affirmedIpProtocolsIpTcpStatistics 1 }

affirmedIpProtocolsIpTcpStatisticsNodeLevel OBJECT IDENTIFIER ::= { affirmedIpProtocolsIpTcpStatistics 2 }

affirmedIpProtocolsOspfv2 OBJECT IDENTIFIER ::= { affirmedIpProtocols 1 }

affirmedIpProtocolsBgpVpn OBJECT IDENTIFIER ::= { affirmedIpProtocols 2 }

affirmedIpProtocolsBgp OBJECT IDENTIFIER ::= { affirmedIpProtocols 3 }

affirmedIpProtocolsPolicyRouteMapShowTable OBJECT-TYPE
    SYNTAX      SEQUENCE OF AffirmedIpProtocolsPolicyRouteMapShowEntry
    MAX-ACCESS  not-accessible
    STATUS      current
    DESCRIPTION ""
    ::= { affirmedIpProtocolsPolicy 1 }

affirmedIpProtocolsPolicyRouteMapShowEntry OBJECT-TYPE
    SYNTAX      AffirmedIpProtocolsPolicyRouteMapShowEntry
    MAX-ACCESS  not-accessible
    STATUS      current
    DESCRIPTION ""
    INDEX { affirmedIpProtocolsPolicyRouteMapShowEntryId }
        ::= { affirmedIpProtocolsPolicyRouteMapShowTable 1 }

AffirmedIpProtocolsPolicyRouteMapShowEntry ::=
    SEQUENCE {
        affirmedIpProtocolsPolicyRouteMapShowEntryId INTEGER,
        affirmedIpProtocolsPolicyRouteMapShowOutput String
    }

affirmedIpProtocolsPolicyRouteMapShowEntryId OBJECT-TYPE
    SYNTAX      INTEGER {entry(0)}
    MAX-ACCESS  not-accessible
    STATUS      current
    DESCRIPTION ""
    ::= { affirmedIpProtocolsPolicyRouteMapShowEntry 1 }

affirmedIpProtocolsPolicyRouteMapShowOutput OBJECT-TYPE
    SYNTAX      String
    MAX-ACCESS  read-only
    STATUS      current
    DESCRIPTION ""
    ::= { affirmedIpProtocolsPolicyRouteMapShowEntry 2 }

affirmedIpProtocolsPolicyAccessListShowTable OBJECT-TYPE
    SYNTAX      SEQUENCE OF AffirmedIpProtocolsPolicyAccessListShowEntry
    MAX-ACCESS  not-accessible
    STATUS      current
    DESCRIPTION ""
    ::= { affirmedIpProtocolsPolicy 2 }

affirmedIpProtocolsPolicyAccessListShowEntry OBJECT-TYPE
    SYNTAX      AffirmedIpProtocolsPolicyAccessListShowEntry
    MAX-ACCESS  not-accessible
    STATUS      current
    DESCRIPTION ""
    INDEX { affirmedIpProtocolsPolicyAccessListShowEntryId }
        ::= { affirmedIpProtocolsPolicyAccessListShowTable 1 }

AffirmedIpProtocolsPolicyAccessListShowEntry ::=
    SEQUENCE {
        affirmedIpProtocolsPolicyAccessListShowEntryId INTEGER,
        affirmedIpProtocolsPolicyAccessListShowOutput String
    }

affirmedIpProtocolsPolicyAccessListShowEntryId OBJECT-TYPE
    SYNTAX      INTEGER {entry(0)}
    MAX-ACCESS  not-accessible
    STATUS      current
    DESCRIPTION ""
    ::= { affirmedIpProtocolsPolicyAccessListShowEntry 1 }

affirmedIpProtocolsPolicyAccessListShowOutput OBJECT-TYPE
    SYNTAX      String
    MAX-ACCESS  read-only
    STATUS      current
    DESCRIPTION ""
    ::= { affirmedIpProtocolsPolicyAccessListShowEntry 2 }

affirmedIpProtocolsPolicyPrefixListShowTable OBJECT-TYPE
    SYNTAX      SEQUENCE OF AffirmedIpProtocolsPolicyPrefixListShowEntry
    MAX-ACCESS  not-accessible
    STATUS      current
    DESCRIPTION "Show Configured Prefix Lists"
    ::= { affirmedIpProtocolsPolicy 3 }

affirmedIpProtocolsPolicyPrefixListShowEntry OBJECT-TYPE
    SYNTAX      AffirmedIpProtocolsPolicyPrefixListShowEntry
    MAX-ACCESS  not-accessible
    STATUS      current
    DESCRIPTION ""
    INDEX { affirmedIpProtocolsPolicyPrefixListShowEntryId }
        ::= { affirmedIpProtocolsPolicyPrefixListShowTable 1 }

AffirmedIpProtocolsPolicyPrefixListShowEntry ::=
    SEQUENCE {
        affirmedIpProtocolsPolicyPrefixListShowEntryId INTEGER,
        affirmedIpProtocolsPolicyPrefixListShowOutput String
    }

affirmedIpProtocolsPolicyPrefixListShowEntryId OBJECT-TYPE
    SYNTAX      INTEGER {entry(0)}
    MAX-ACCESS  not-accessible
    STATUS      current
    DESCRIPTION ""
    ::= { affirmedIpProtocolsPolicyPrefixListShowEntry 1 }

affirmedIpProtocolsPolicyPrefixListShowOutput OBJECT-TYPE
    SYNTAX      String
    MAX-ACCESS  read-only
    STATUS      current
    DESCRIPTION ""
    ::= { affirmedIpProtocolsPolicyPrefixListShowEntry 2 }

affirmedIpProtocolsPolicyPrefixListIPv6ShowTable OBJECT-TYPE
    SYNTAX      SEQUENCE OF AffirmedIpProtocolsPolicyPrefixListIPv6ShowEntry
    MAX-ACCESS  not-accessible
    STATUS      current
    DESCRIPTION "Show Configured IPV6 Prefix Lists"
    ::= { affirmedIpProtocolsPolicy 4 }

affirmedIpProtocolsPolicyPrefixListIPv6ShowEntry OBJECT-TYPE
    SYNTAX      AffirmedIpProtocolsPolicyPrefixListIPv6ShowEntry
    MAX-ACCESS  not-accessible
    STATUS      current
    DESCRIPTION ""
    INDEX { affirmedIpProtocolsPolicyPrefixListIPv6ShowEntryId }
        ::= { affirmedIpProtocolsPolicyPrefixListIPv6ShowTable 1 }

AffirmedIpProtocolsPolicyPrefixListIPv6ShowEntry ::=
    SEQUENCE {
        affirmedIpProtocolsPolicyPrefixListIPv6ShowEntryId INTEGER,
        affirmedIpProtocolsPolicyPrefixListIPv6ShowOutput String
    }

affirmedIpProtocolsPolicyPrefixListIPv6ShowEntryId OBJECT-TYPE
    SYNTAX      INTEGER {entry(0)}
    MAX-ACCESS  not-accessible
    STATUS      current
    DESCRIPTION ""
    ::= { affirmedIpProtocolsPolicyPrefixListIPv6ShowEntry 1 }

affirmedIpProtocolsPolicyPrefixListIPv6ShowOutput OBJECT-TYPE
    SYNTAX      String
    MAX-ACCESS  read-only
    STATUS      current
    DESCRIPTION ""
    ::= { affirmedIpProtocolsPolicyPrefixListIPv6ShowEntry 2 }

affirmedIpProtocolsPolicyCommunityListShowTable OBJECT-TYPE
    SYNTAX      SEQUENCE OF AffirmedIpProtocolsPolicyCommunityListShowEntry
    MAX-ACCESS  not-accessible
    STATUS      current
    DESCRIPTION "Show Configured Community Lists"
    ::= { affirmedIpProtocolsPolicy 5 }

affirmedIpProtocolsPolicyCommunityListShowEntry OBJECT-TYPE
    SYNTAX      AffirmedIpProtocolsPolicyCommunityListShowEntry
    MAX-ACCESS  not-accessible
    STATUS      current
    DESCRIPTION ""
    INDEX { affirmedIpProtocolsPolicyCommunityListShowEntryId }
        ::= { affirmedIpProtocolsPolicyCommunityListShowTable 1 }

AffirmedIpProtocolsPolicyCommunityListShowEntry ::=
    SEQUENCE {
        affirmedIpProtocolsPolicyCommunityListShowEntryId INTEGER,
        affirmedIpProtocolsPolicyCommunityListShowOutput String
    }

affirmedIpProtocolsPolicyCommunityListShowEntryId OBJECT-TYPE
    SYNTAX      INTEGER {entry(0)}
    MAX-ACCESS  not-accessible
    STATUS      current
    DESCRIPTION ""
    ::= { affirmedIpProtocolsPolicyCommunityListShowEntry 1 }

affirmedIpProtocolsPolicyCommunityListShowOutput OBJECT-TYPE
    SYNTAX      String
    MAX-ACCESS  read-only
    STATUS      current
    DESCRIPTION ""
    ::= { affirmedIpProtocolsPolicyCommunityListShowEntry 2 }

affirmedIpProtocolsPolicyAsPathListShowTable OBJECT-TYPE
    SYNTAX      SEQUENCE OF AffirmedIpProtocolsPolicyAsPathListShowEntry
    MAX-ACCESS  not-accessible
    STATUS      current
    DESCRIPTION "Show Configured ASPath Lists"
    ::= { affirmedIpProtocolsPolicy 6 }

affirmedIpProtocolsPolicyAsPathListShowEntry OBJECT-TYPE
    SYNTAX      AffirmedIpProtocolsPolicyAsPathListShowEntry
    MAX-ACCESS  not-accessible
    STATUS      current
    DESCRIPTION ""
    INDEX { affirmedIpProtocolsPolicyAsPathListShowEntryId }
        ::= { affirmedIpProtocolsPolicyAsPathListShowTable 1 }

AffirmedIpProtocolsPolicyAsPathListShowEntry ::=
    SEQUENCE {
        affirmedIpProtocolsPolicyAsPathListShowEntryId INTEGER,
        affirmedIpProtocolsPolicyAsPathListShowOutput String
    }

affirmedIpProtocolsPolicyAsPathListShowEntryId OBJECT-TYPE
    SYNTAX      INTEGER {entry(0)}
    MAX-ACCESS  not-accessible
    STATUS      current
    DESCRIPTION ""
    ::= { affirmedIpProtocolsPolicyAsPathListShowEntry 1 }

affirmedIpProtocolsPolicyAsPathListShowOutput OBJECT-TYPE
    SYNTAX      String
    MAX-ACCESS  read-only
    STATUS      current
    DESCRIPTION ""
    ::= { affirmedIpProtocolsPolicyAsPathListShowEntry 2 }

affirmedIpProtocolsOspfv3RouterTable OBJECT-TYPE
    SYNTAX      SEQUENCE OF AffirmedIpProtocolsOspfv3RouterEntry
    MAX-ACCESS  not-accessible
    STATUS      current
    DESCRIPTION "Configure and manage OSPFv3 routers"
    ::= { affirmedIpProtocolsOspfv3 1 }

affirmedIpProtocolsOspfv3RouterEntry OBJECT-TYPE
    SYNTAX      AffirmedIpProtocolsOspfv3RouterEntry
    MAX-ACCESS  not-accessible
    STATUS      current
    DESCRIPTION ""
    INDEX { affirmedIpProtocolsOspfv3RouterNetworkContext }
        ::= { affirmedIpProtocolsOspfv3RouterTable 1 }

AffirmedIpProtocolsOspfv3RouterEntry ::=
    SEQUENCE {
        affirmedIpProtocolsOspfv3RouterNetworkContext String,
        affirmedIpProtocolsOspfv3RouterRowstatus RowStatus
    }

affirmedIpProtocolsOspfv3RouterNetworkContext OBJECT-TYPE
    SYNTAX      String
    MAX-ACCESS  not-accessible
    STATUS      current
    DESCRIPTION "network context for this OSPFv3 router"
    ::= { affirmedIpProtocolsOspfv3RouterEntry 1 }

affirmedIpProtocolsOspfv3RouterRowstatus OBJECT-TYPE
    SYNTAX      RowStatus
    MAX-ACCESS  read-create
    STATUS      current
    DESCRIPTION ""
    ::= { affirmedIpProtocolsOspfv3RouterEntry 2 }

affirmedIpProtocolsOspfv3RouterShowInterfaceTable OBJECT-TYPE
    SYNTAX      SEQUENCE OF AffirmedIpProtocolsOspfv3RouterShowInterfaceEntry
    MAX-ACCESS  not-accessible
    STATUS      current
    DESCRIPTION "Show the OSPFv3 interface"
    ::= { affirmedIpProtocolsOspfv3 2 }

affirmedIpProtocolsOspfv3RouterShowInterfaceEntry OBJECT-TYPE
    SYNTAX      AffirmedIpProtocolsOspfv3RouterShowInterfaceEntry
    MAX-ACCESS  not-accessible
    STATUS      current
    DESCRIPTION ""
    INDEX { affirmedIpProtocolsOspfv3RouterNetworkContext, affirmedIpProtocolsOspfv3RouterShowInterfaceEntryId }
        ::= { affirmedIpProtocolsOspfv3RouterShowInterfaceTable 1 }

AffirmedIpProtocolsOspfv3RouterShowInterfaceEntry ::=
    SEQUENCE {
        affirmedIpProtocolsOspfv3RouterShowInterfaceEntryId INTEGER,
        affirmedIpProtocolsOspfv3RouterShowInterfaceOutput String
    }

affirmedIpProtocolsOspfv3RouterShowInterfaceEntryId OBJECT-TYPE
    SYNTAX      INTEGER {entry(0)}
    MAX-ACCESS  not-accessible
    STATUS      current
    DESCRIPTION ""
    ::= { affirmedIpProtocolsOspfv3RouterShowInterfaceEntry 1 }

affirmedIpProtocolsOspfv3RouterShowInterfaceOutput OBJECT-TYPE
    SYNTAX      String
    MAX-ACCESS  read-only
    STATUS      current
    DESCRIPTION ""
    ::= { affirmedIpProtocolsOspfv3RouterShowInterfaceEntry 2 }

affirmedIpProtocolsOspfv3RouterShowNeighborTable OBJECT-TYPE
    SYNTAX      SEQUENCE OF AffirmedIpProtocolsOspfv3RouterShowNeighborEntry
    MAX-ACCESS  not-accessible
    STATUS      current
    DESCRIPTION "Show the OSPFv3 neighbors"
    ::= { affirmedIpProtocolsOspfv3 3 }

affirmedIpProtocolsOspfv3RouterShowNeighborEntry OBJECT-TYPE
    SYNTAX      AffirmedIpProtocolsOspfv3RouterShowNeighborEntry
    MAX-ACCESS  not-accessible
    STATUS      current
    DESCRIPTION ""
    INDEX { affirmedIpProtocolsOspfv3RouterNetworkContext, affirmedIpProtocolsOspfv3RouterShowNeighborEntryId }
        ::= { affirmedIpProtocolsOspfv3RouterShowNeighborTable 1 }

AffirmedIpProtocolsOspfv3RouterShowNeighborEntry ::=
    SEQUENCE {
        affirmedIpProtocolsOspfv3RouterShowNeighborEntryId INTEGER,
        affirmedIpProtocolsOspfv3RouterShowNeighborOutput String
    }

affirmedIpProtocolsOspfv3RouterShowNeighborEntryId OBJECT-TYPE
    SYNTAX      INTEGER {entry(0)}
    MAX-ACCESS  not-accessible
    STATUS      current
    DESCRIPTION ""
    ::= { affirmedIpProtocolsOspfv3RouterShowNeighborEntry 1 }

affirmedIpProtocolsOspfv3RouterShowNeighborOutput OBJECT-TYPE
    SYNTAX      String
    MAX-ACCESS  read-only
    STATUS      current
    DESCRIPTION ""
    ::= { affirmedIpProtocolsOspfv3RouterShowNeighborEntry 2 }

affirmedIpProtocolsOspfv3RouterShowNeighborDetailTable OBJECT-TYPE
    SYNTAX      SEQUENCE OF AffirmedIpProtocolsOspfv3RouterShowNeighborDetailEntry
    MAX-ACCESS  not-accessible
    STATUS      current
    DESCRIPTION "Show the OSPFv3 neighbors details"
    ::= { affirmedIpProtocolsOspfv3 4 }

affirmedIpProtocolsOspfv3RouterShowNeighborDetailEntry OBJECT-TYPE
    SYNTAX      AffirmedIpProtocolsOspfv3RouterShowNeighborDetailEntry
    MAX-ACCESS  not-accessible
    STATUS      current
    DESCRIPTION ""
    INDEX { affirmedIpProtocolsOspfv3RouterNetworkContext, affirmedIpProtocolsOspfv3RouterShowNeighborDetailEntryId }
        ::= { affirmedIpProtocolsOspfv3RouterShowNeighborDetailTable 1 }

AffirmedIpProtocolsOspfv3RouterShowNeighborDetailEntry ::=
    SEQUENCE {
        affirmedIpProtocolsOspfv3RouterShowNeighborDetailEntryId INTEGER,
        affirmedIpProtocolsOspfv3RouterShowNeighborDetailOutput String
    }

affirmedIpProtocolsOspfv3RouterShowNeighborDetailEntryId OBJECT-TYPE
    SYNTAX      INTEGER {entry(0)}
    MAX-ACCESS  not-accessible
    STATUS      current
    DESCRIPTION ""
    ::= { affirmedIpProtocolsOspfv3RouterShowNeighborDetailEntry 1 }

affirmedIpProtocolsOspfv3RouterShowNeighborDetailOutput OBJECT-TYPE
    SYNTAX      String
    MAX-ACCESS  read-only
    STATUS      current
    DESCRIPTION ""
    ::= { affirmedIpProtocolsOspfv3RouterShowNeighborDetailEntry 2 }

affirmedIpProtocolsOspfv3RouterShowRouteTable OBJECT-TYPE
    SYNTAX      SEQUENCE OF AffirmedIpProtocolsOspfv3RouterShowRouteEntry
    MAX-ACCESS  not-accessible
    STATUS      current
    DESCRIPTION "Show the OSPFv3 routes"
    ::= { affirmedIpProtocolsOspfv3 5 }

affirmedIpProtocolsOspfv3RouterShowRouteEntry OBJECT-TYPE
    SYNTAX      AffirmedIpProtocolsOspfv3RouterShowRouteEntry
    MAX-ACCESS  not-accessible
    STATUS      current
    DESCRIPTION ""
    INDEX { affirmedIpProtocolsOspfv3RouterNetworkContext, affirmedIpProtocolsOspfv3RouterShowRouteEntryId }
        ::= { affirmedIpProtocolsOspfv3RouterShowRouteTable 1 }

AffirmedIpProtocolsOspfv3RouterShowRouteEntry ::=
    SEQUENCE {
        affirmedIpProtocolsOspfv3RouterShowRouteEntryId INTEGER,
        affirmedIpProtocolsOspfv3RouterShowRouteOutput String
    }

affirmedIpProtocolsOspfv3RouterShowRouteEntryId OBJECT-TYPE
    SYNTAX      INTEGER {entry(0)}
    MAX-ACCESS  not-accessible
    STATUS      current
    DESCRIPTION ""
    ::= { affirmedIpProtocolsOspfv3RouterShowRouteEntry 1 }

affirmedIpProtocolsOspfv3RouterShowRouteOutput OBJECT-TYPE
    SYNTAX      String
    MAX-ACCESS  read-only
    STATUS      current
    DESCRIPTION ""
    ::= { affirmedIpProtocolsOspfv3RouterShowRouteEntry 2 }

affirmedIpProtocolsOspfv3RouterShowSummaryTable OBJECT-TYPE
    SYNTAX      SEQUENCE OF AffirmedIpProtocolsOspfv3RouterShowSummaryEntry
    MAX-ACCESS  not-accessible
    STATUS      current
    DESCRIPTION "Show a summary of the OSPF processes"
    ::= { affirmedIpProtocolsOspfv3 6 }

affirmedIpProtocolsOspfv3RouterShowSummaryEntry OBJECT-TYPE
    SYNTAX      AffirmedIpProtocolsOspfv3RouterShowSummaryEntry
    MAX-ACCESS  not-accessible
    STATUS      current
    DESCRIPTION ""
    INDEX { affirmedIpProtocolsOspfv3RouterNetworkContext, affirmedIpProtocolsOspfv3RouterShowSummaryEntryId }
        ::= { affirmedIpProtocolsOspfv3RouterShowSummaryTable 1 }

AffirmedIpProtocolsOspfv3RouterShowSummaryEntry ::=
    SEQUENCE {
        affirmedIpProtocolsOspfv3RouterShowSummaryEntryId INTEGER,
        affirmedIpProtocolsOspfv3RouterShowSummaryOutput String
    }

affirmedIpProtocolsOspfv3RouterShowSummaryEntryId OBJECT-TYPE
    SYNTAX      INTEGER {entry(0)}
    MAX-ACCESS  not-accessible
    STATUS      current
    DESCRIPTION ""
    ::= { affirmedIpProtocolsOspfv3RouterShowSummaryEntry 1 }

affirmedIpProtocolsOspfv3RouterShowSummaryOutput OBJECT-TYPE
    SYNTAX      String
    MAX-ACCESS  read-only
    STATUS      current
    DESCRIPTION ""
    ::= { affirmedIpProtocolsOspfv3RouterShowSummaryEntry 2 }

affirmedIpProtocolsOspfv3RouterShowTopologyTable OBJECT-TYPE
    SYNTAX      SEQUENCE OF AffirmedIpProtocolsOspfv3RouterShowTopologyEntry
    MAX-ACCESS  not-accessible
    STATUS      current
    DESCRIPTION "Show the topology of the OSPFv3 processes"
    ::= { affirmedIpProtocolsOspfv3 7 }

affirmedIpProtocolsOspfv3RouterShowTopologyEntry OBJECT-TYPE
    SYNTAX      AffirmedIpProtocolsOspfv3RouterShowTopologyEntry
    MAX-ACCESS  not-accessible
    STATUS      current
    DESCRIPTION ""
    INDEX { affirmedIpProtocolsOspfv3RouterNetworkContext, affirmedIpProtocolsOspfv3RouterShowTopologyEntryId }
        ::= { affirmedIpProtocolsOspfv3RouterShowTopologyTable 1 }

AffirmedIpProtocolsOspfv3RouterShowTopologyEntry ::=
    SEQUENCE {
        affirmedIpProtocolsOspfv3RouterShowTopologyEntryId INTEGER,
        affirmedIpProtocolsOspfv3RouterShowTopologyOutput String
    }

affirmedIpProtocolsOspfv3RouterShowTopologyEntryId OBJECT-TYPE
    SYNTAX      INTEGER {entry(0)}
    MAX-ACCESS  not-accessible
    STATUS      current
    DESCRIPTION ""
    ::= { affirmedIpProtocolsOspfv3RouterShowTopologyEntry 1 }

affirmedIpProtocolsOspfv3RouterShowTopologyOutput OBJECT-TYPE
    SYNTAX      String
    MAX-ACCESS  read-only
    STATUS      current
    DESCRIPTION ""
    ::= { affirmedIpProtocolsOspfv3RouterShowTopologyEntry 2 }

affirmedIpProtocolsOspfv3RouterShowDBRouterDbTable OBJECT-TYPE
    SYNTAX      SEQUENCE OF AffirmedIpProtocolsOspfv3RouterShowDBRouterDbEntry
    MAX-ACCESS  not-accessible
    STATUS      current
    DESCRIPTION "Router Link States"
    ::= { affirmedIpProtocolsOspfv3 8 }

affirmedIpProtocolsOspfv3RouterShowDBRouterDbEntry OBJECT-TYPE
    SYNTAX      AffirmedIpProtocolsOspfv3RouterShowDBRouterDbEntry
    MAX-ACCESS  not-accessible
    STATUS      current
    DESCRIPTION ""
    INDEX { affirmedIpProtocolsOspfv3RouterNetworkContext, affirmedIpProtocolsOspfv3RouterShowDBRouterDbEntryId }
        ::= { affirmedIpProtocolsOspfv3RouterShowDBRouterDbTable 1 }

AffirmedIpProtocolsOspfv3RouterShowDBRouterDbEntry ::=
    SEQUENCE {
        affirmedIpProtocolsOspfv3RouterShowDBRouterDbEntryId INTEGER,
        affirmedIpProtocolsOspfv3RouterShowDBRouterDbOutput String
    }

affirmedIpProtocolsOspfv3RouterShowDBRouterDbEntryId OBJECT-TYPE
    SYNTAX      INTEGER {entry(0)}
    MAX-ACCESS  not-accessible
    STATUS      current
    DESCRIPTION ""
    ::= { affirmedIpProtocolsOspfv3RouterShowDBRouterDbEntry 1 }

affirmedIpProtocolsOspfv3RouterShowDBRouterDbOutput OBJECT-TYPE
    SYNTAX      String
    MAX-ACCESS  read-only
    STATUS      current
    DESCRIPTION ""
    ::= { affirmedIpProtocolsOspfv3RouterShowDBRouterDbEntry 2 }

affirmedIpProtocolsOspfv3RouterShowDBGraceDbTable OBJECT-TYPE
    SYNTAX      SEQUENCE OF AffirmedIpProtocolsOspfv3RouterShowDBGraceDbEntry
    MAX-ACCESS  not-accessible
    STATUS      current
    DESCRIPTION "Shows Grace-LSA in LSDB"
    ::= { affirmedIpProtocolsOspfv3 9 }

affirmedIpProtocolsOspfv3RouterShowDBGraceDbEntry OBJECT-TYPE
    SYNTAX      AffirmedIpProtocolsOspfv3RouterShowDBGraceDbEntry
    MAX-ACCESS  not-accessible
    STATUS      current
    DESCRIPTION ""
    INDEX { affirmedIpProtocolsOspfv3RouterNetworkContext, affirmedIpProtocolsOspfv3RouterShowDBGraceDbEntryId }
        ::= { affirmedIpProtocolsOspfv3RouterShowDBGraceDbTable 1 }

AffirmedIpProtocolsOspfv3RouterShowDBGraceDbEntry ::=
    SEQUENCE {
        affirmedIpProtocolsOspfv3RouterShowDBGraceDbEntryId INTEGER,
        affirmedIpProtocolsOspfv3RouterShowDBGraceDbOutput String
    }

affirmedIpProtocolsOspfv3RouterShowDBGraceDbEntryId OBJECT-TYPE
    SYNTAX      INTEGER {entry(0)}
    MAX-ACCESS  not-accessible
    STATUS      current
    DESCRIPTION ""
    ::= { affirmedIpProtocolsOspfv3RouterShowDBGraceDbEntry 1 }

affirmedIpProtocolsOspfv3RouterShowDBGraceDbOutput OBJECT-TYPE
    SYNTAX      String
    MAX-ACCESS  read-only
    STATUS      current
    DESCRIPTION ""
    ::= { affirmedIpProtocolsOspfv3RouterShowDBGraceDbEntry 2 }

affirmedIpProtocolsOspfv3RouterShowDBLinkDbTable OBJECT-TYPE
    SYNTAX      SEQUENCE OF AffirmedIpProtocolsOspfv3RouterShowDBLinkDbEntry
    MAX-ACCESS  not-accessible
    STATUS      current
    DESCRIPTION "Shows Link-LSAs in LSDB"
    ::= { affirmedIpProtocolsOspfv3 10 }

affirmedIpProtocolsOspfv3RouterShowDBLinkDbEntry OBJECT-TYPE
    SYNTAX      AffirmedIpProtocolsOspfv3RouterShowDBLinkDbEntry
    MAX-ACCESS  not-accessible
    STATUS      current
    DESCRIPTION ""
    INDEX { affirmedIpProtocolsOspfv3RouterNetworkContext, affirmedIpProtocolsOspfv3RouterShowDBLinkDbEntryId }
        ::= { affirmedIpProtocolsOspfv3RouterShowDBLinkDbTable 1 }

AffirmedIpProtocolsOspfv3RouterShowDBLinkDbEntry ::=
    SEQUENCE {
        affirmedIpProtocolsOspfv3RouterShowDBLinkDbEntryId INTEGER,
        affirmedIpProtocolsOspfv3RouterShowDBLinkDbOutput String
    }

affirmedIpProtocolsOspfv3RouterShowDBLinkDbEntryId OBJECT-TYPE
    SYNTAX      INTEGER {entry(0)}
    MAX-ACCESS  not-accessible
    STATUS      current
    DESCRIPTION ""
    ::= { affirmedIpProtocolsOspfv3RouterShowDBLinkDbEntry 1 }

affirmedIpProtocolsOspfv3RouterShowDBLinkDbOutput OBJECT-TYPE
    SYNTAX      String
    MAX-ACCESS  read-only
    STATUS      current
    DESCRIPTION ""
    ::= { affirmedIpProtocolsOspfv3RouterShowDBLinkDbEntry 2 }

affirmedIpProtocolsOspfv3RouterShowDBInterprefixDbTable OBJECT-TYPE
    SYNTAX      SEQUENCE OF AffirmedIpProtocolsOspfv3RouterShowDBInterprefixDbEntry
    MAX-ACCESS  not-accessible
    STATUS      current
    DESCRIPTION "Shows Inter-Area-Prefix LSAs"
    ::= { affirmedIpProtocolsOspfv3 11 }

affirmedIpProtocolsOspfv3RouterShowDBInterprefixDbEntry OBJECT-TYPE
    SYNTAX      AffirmedIpProtocolsOspfv3RouterShowDBInterprefixDbEntry
    MAX-ACCESS  not-accessible
    STATUS      current
    DESCRIPTION ""
    INDEX { affirmedIpProtocolsOspfv3RouterNetworkContext, affirmedIpProtocolsOspfv3RouterShowDBInterprefixDbEntryId }
        ::= { affirmedIpProtocolsOspfv3RouterShowDBInterprefixDbTable 1 }

AffirmedIpProtocolsOspfv3RouterShowDBInterprefixDbEntry ::=
    SEQUENCE {
        affirmedIpProtocolsOspfv3RouterShowDBInterprefixDbEntryId INTEGER,
        affirmedIpProtocolsOspfv3RouterShowDBInterprefixDbOutput String
    }

affirmedIpProtocolsOspfv3RouterShowDBInterprefixDbEntryId OBJECT-TYPE
    SYNTAX      INTEGER {entry(0)}
    MAX-ACCESS  not-accessible
    STATUS      current
    DESCRIPTION ""
    ::= { affirmedIpProtocolsOspfv3RouterShowDBInterprefixDbEntry 1 }

affirmedIpProtocolsOspfv3RouterShowDBInterprefixDbOutput OBJECT-TYPE
    SYNTAX      String
    MAX-ACCESS  read-only
    STATUS      current
    DESCRIPTION ""
    ::= { affirmedIpProtocolsOspfv3RouterShowDBInterprefixDbEntry 2 }

affirmedIpProtocolsOspfv3RouterShowDBInterrouterDbTable OBJECT-TYPE
    SYNTAX      SEQUENCE OF AffirmedIpProtocolsOspfv3RouterShowDBInterrouterDbEntry
    MAX-ACCESS  not-accessible
    STATUS      current
    DESCRIPTION "Shows Inter-Area-Router LSAs"
    ::= { affirmedIpProtocolsOspfv3 12 }

affirmedIpProtocolsOspfv3RouterShowDBInterrouterDbEntry OBJECT-TYPE
    SYNTAX      AffirmedIpProtocolsOspfv3RouterShowDBInterrouterDbEntry
    MAX-ACCESS  not-accessible
    STATUS      current
    DESCRIPTION ""
    INDEX { affirmedIpProtocolsOspfv3RouterNetworkContext, affirmedIpProtocolsOspfv3RouterShowDBInterrouterDbEntryId }
        ::= { affirmedIpProtocolsOspfv3RouterShowDBInterrouterDbTable 1 }

AffirmedIpProtocolsOspfv3RouterShowDBInterrouterDbEntry ::=
    SEQUENCE {
        affirmedIpProtocolsOspfv3RouterShowDBInterrouterDbEntryId INTEGER,
        affirmedIpProtocolsOspfv3RouterShowDBInterrouterDbOutput String
    }

affirmedIpProtocolsOspfv3RouterShowDBInterrouterDbEntryId OBJECT-TYPE
    SYNTAX      INTEGER {entry(0)}
    MAX-ACCESS  not-accessible
    STATUS      current
    DESCRIPTION ""
    ::= { affirmedIpProtocolsOspfv3RouterShowDBInterrouterDbEntry 1 }

affirmedIpProtocolsOspfv3RouterShowDBInterrouterDbOutput OBJECT-TYPE
    SYNTAX      String
    MAX-ACCESS  read-only
    STATUS      current
    DESCRIPTION ""
    ::= { affirmedIpProtocolsOspfv3RouterShowDBInterrouterDbEntry 2 }

affirmedIpProtocolsOspfv3RouterShowDBIntraprefixDbTable OBJECT-TYPE
    SYNTAX      SEQUENCE OF AffirmedIpProtocolsOspfv3RouterShowDBIntraprefixDbEntry
    MAX-ACCESS  not-accessible
    STATUS      current
    DESCRIPTION "Shows Intra-Area-Prefix LSAs"
    ::= { affirmedIpProtocolsOspfv3 13 }

affirmedIpProtocolsOspfv3RouterShowDBIntraprefixDbEntry OBJECT-TYPE
    SYNTAX      AffirmedIpProtocolsOspfv3RouterShowDBIntraprefixDbEntry
    MAX-ACCESS  not-accessible
    STATUS      current
    DESCRIPTION ""
    INDEX { affirmedIpProtocolsOspfv3RouterNetworkContext, affirmedIpProtocolsOspfv3RouterShowDBIntraprefixDbEntryId }
        ::= { affirmedIpProtocolsOspfv3RouterShowDBIntraprefixDbTable 1 }

AffirmedIpProtocolsOspfv3RouterShowDBIntraprefixDbEntry ::=
    SEQUENCE {
        affirmedIpProtocolsOspfv3RouterShowDBIntraprefixDbEntryId INTEGER,
        affirmedIpProtocolsOspfv3RouterShowDBIntraprefixDbOutput String
    }

affirmedIpProtocolsOspfv3RouterShowDBIntraprefixDbEntryId OBJECT-TYPE
    SYNTAX      INTEGER {entry(0)}
    MAX-ACCESS  not-accessible
    STATUS      current
    DESCRIPTION ""
    ::= { affirmedIpProtocolsOspfv3RouterShowDBIntraprefixDbEntry 1 }

affirmedIpProtocolsOspfv3RouterShowDBIntraprefixDbOutput OBJECT-TYPE
    SYNTAX      String
    MAX-ACCESS  read-only
    STATUS      current
    DESCRIPTION ""
    ::= { affirmedIpProtocolsOspfv3RouterShowDBIntraprefixDbEntry 2 }

affirmedIpProtocolsOspfv3RouterShowDBMaxageDbTable OBJECT-TYPE
    SYNTAX      SEQUENCE OF AffirmedIpProtocolsOspfv3RouterShowDBMaxageDbEntry
    MAX-ACCESS  not-accessible
    STATUS      current
    DESCRIPTION "LSAs in MaxAge list"
    ::= { affirmedIpProtocolsOspfv3 14 }

affirmedIpProtocolsOspfv3RouterShowDBMaxageDbEntry OBJECT-TYPE
    SYNTAX      AffirmedIpProtocolsOspfv3RouterShowDBMaxageDbEntry
    MAX-ACCESS  not-accessible
    STATUS      current
    DESCRIPTION ""
    INDEX { affirmedIpProtocolsOspfv3RouterNetworkContext, affirmedIpProtocolsOspfv3RouterShowDBMaxageDbEntryId }
        ::= { affirmedIpProtocolsOspfv3RouterShowDBMaxageDbTable 1 }

AffirmedIpProtocolsOspfv3RouterShowDBMaxageDbEntry ::=
    SEQUENCE {
        affirmedIpProtocolsOspfv3RouterShowDBMaxageDbEntryId INTEGER,
        affirmedIpProtocolsOspfv3RouterShowDBMaxageDbOutput String
    }

affirmedIpProtocolsOspfv3RouterShowDBMaxageDbEntryId OBJECT-TYPE
    SYNTAX      INTEGER {entry(0)}
    MAX-ACCESS  not-accessible
    STATUS      current
    DESCRIPTION ""
    ::= { affirmedIpProtocolsOspfv3RouterShowDBMaxageDbEntry 1 }

affirmedIpProtocolsOspfv3RouterShowDBMaxageDbOutput OBJECT-TYPE
    SYNTAX      String
    MAX-ACCESS  read-only
    STATUS      current
    DESCRIPTION ""
    ::= { affirmedIpProtocolsOspfv3RouterShowDBMaxageDbEntry 2 }

affirmedIpProtocolsOspfv3RouterShowDBSelforigDbTable OBJECT-TYPE
    SYNTAX      SEQUENCE OF AffirmedIpProtocolsOspfv3RouterShowDBSelforigDbEntry
    MAX-ACCESS  not-accessible
    STATUS      current
    DESCRIPTION "Self-originated link states"
    ::= { affirmedIpProtocolsOspfv3 15 }

affirmedIpProtocolsOspfv3RouterShowDBSelforigDbEntry OBJECT-TYPE
    SYNTAX      AffirmedIpProtocolsOspfv3RouterShowDBSelforigDbEntry
    MAX-ACCESS  not-accessible
    STATUS      current
    DESCRIPTION ""
    INDEX { affirmedIpProtocolsOspfv3RouterNetworkContext, affirmedIpProtocolsOspfv3RouterShowDBSelforigDbEntryId }
        ::= { affirmedIpProtocolsOspfv3RouterShowDBSelforigDbTable 1 }

AffirmedIpProtocolsOspfv3RouterShowDBSelforigDbEntry ::=
    SEQUENCE {
        affirmedIpProtocolsOspfv3RouterShowDBSelforigDbEntryId INTEGER,
        affirmedIpProtocolsOspfv3RouterShowDBSelforigDbOutput String
    }

affirmedIpProtocolsOspfv3RouterShowDBSelforigDbEntryId OBJECT-TYPE
    SYNTAX      INTEGER {entry(0)}
    MAX-ACCESS  not-accessible
    STATUS      current
    DESCRIPTION ""
    ::= { affirmedIpProtocolsOspfv3RouterShowDBSelforigDbEntry 1 }

affirmedIpProtocolsOspfv3RouterShowDBSelforigDbOutput OBJECT-TYPE
    SYNTAX      String
    MAX-ACCESS  read-only
    STATUS      current
    DESCRIPTION ""
    ::= { affirmedIpProtocolsOspfv3RouterShowDBSelforigDbEntry 2 }

affirmedIpProtocolsOspfv3RouterShowDBExternalDbTable OBJECT-TYPE
    SYNTAX      SEQUENCE OF AffirmedIpProtocolsOspfv3RouterShowDBExternalDbEntry
    MAX-ACCESS  not-accessible
    STATUS      current
    DESCRIPTION "External Link States"
    ::= { affirmedIpProtocolsOspfv3 16 }

affirmedIpProtocolsOspfv3RouterShowDBExternalDbEntry OBJECT-TYPE
    SYNTAX      AffirmedIpProtocolsOspfv3RouterShowDBExternalDbEntry
    MAX-ACCESS  not-accessible
    STATUS      current
    DESCRIPTION ""
    INDEX { affirmedIpProtocolsOspfv3RouterNetworkContext, affirmedIpProtocolsOspfv3RouterShowDBExternalDbEntryId }
        ::= { affirmedIpProtocolsOspfv3RouterShowDBExternalDbTable 1 }

AffirmedIpProtocolsOspfv3RouterShowDBExternalDbEntry ::=
    SEQUENCE {
        affirmedIpProtocolsOspfv3RouterShowDBExternalDbEntryId INTEGER,
        affirmedIpProtocolsOspfv3RouterShowDBExternalDbOutput String
    }

affirmedIpProtocolsOspfv3RouterShowDBExternalDbEntryId OBJECT-TYPE
    SYNTAX      INTEGER {entry(0)}
    MAX-ACCESS  not-accessible
    STATUS      current
    DESCRIPTION ""
    ::= { affirmedIpProtocolsOspfv3RouterShowDBExternalDbEntry 1 }

affirmedIpProtocolsOspfv3RouterShowDBExternalDbOutput OBJECT-TYPE
    SYNTAX      String
    MAX-ACCESS  read-only
    STATUS      current
    DESCRIPTION ""
    ::= { affirmedIpProtocolsOspfv3RouterShowDBExternalDbEntry 2 }

affirmedIpProtocolsOspfv3RouterShowDBNetworkDbTable OBJECT-TYPE
    SYNTAX      SEQUENCE OF AffirmedIpProtocolsOspfv3RouterShowDBNetworkDbEntry
    MAX-ACCESS  not-accessible
    STATUS      current
    DESCRIPTION "Network Link States"
    ::= { affirmedIpProtocolsOspfv3 17 }

affirmedIpProtocolsOspfv3RouterShowDBNetworkDbEntry OBJECT-TYPE
    SYNTAX      AffirmedIpProtocolsOspfv3RouterShowDBNetworkDbEntry
    MAX-ACCESS  not-accessible
    STATUS      current
    DESCRIPTION ""
    INDEX { affirmedIpProtocolsOspfv3RouterNetworkContext, affirmedIpProtocolsOspfv3RouterShowDBNetworkDbEntryId }
        ::= { affirmedIpProtocolsOspfv3RouterShowDBNetworkDbTable 1 }

AffirmedIpProtocolsOspfv3RouterShowDBNetworkDbEntry ::=
    SEQUENCE {
        affirmedIpProtocolsOspfv3RouterShowDBNetworkDbEntryId INTEGER,
        affirmedIpProtocolsOspfv3RouterShowDBNetworkDbOutput String
    }

affirmedIpProtocolsOspfv3RouterShowDBNetworkDbEntryId OBJECT-TYPE
    SYNTAX      INTEGER {entry(0)}
    MAX-ACCESS  not-accessible
    STATUS      current
    DESCRIPTION ""
    ::= { affirmedIpProtocolsOspfv3RouterShowDBNetworkDbEntry 1 }

affirmedIpProtocolsOspfv3RouterShowDBNetworkDbOutput OBJECT-TYPE
    SYNTAX      String
    MAX-ACCESS  read-only
    STATUS      current
    DESCRIPTION ""
    ::= { affirmedIpProtocolsOspfv3RouterShowDBNetworkDbEntry 2 }

affirmedIpProtocolsOspfv3RouterShowDBNssaDbTable OBJECT-TYPE
    SYNTAX      SEQUENCE OF AffirmedIpProtocolsOspfv3RouterShowDBNssaDbEntry
    MAX-ACCESS  not-accessible
    STATUS      current
    DESCRIPTION "NSSA External Link States"
    ::= { affirmedIpProtocolsOspfv3 18 }

affirmedIpProtocolsOspfv3RouterShowDBNssaDbEntry OBJECT-TYPE
    SYNTAX      AffirmedIpProtocolsOspfv3RouterShowDBNssaDbEntry
    MAX-ACCESS  not-accessible
    STATUS      current
    DESCRIPTION ""
    INDEX { affirmedIpProtocolsOspfv3RouterNetworkContext, affirmedIpProtocolsOspfv3RouterShowDBNssaDbEntryId }
        ::= { affirmedIpProtocolsOspfv3RouterShowDBNssaDbTable 1 }

AffirmedIpProtocolsOspfv3RouterShowDBNssaDbEntry ::=
    SEQUENCE {
        affirmedIpProtocolsOspfv3RouterShowDBNssaDbEntryId INTEGER,
        affirmedIpProtocolsOspfv3RouterShowDBNssaDbOutput String
    }

affirmedIpProtocolsOspfv3RouterShowDBNssaDbEntryId OBJECT-TYPE
    SYNTAX      INTEGER {entry(0)}
    MAX-ACCESS  not-accessible
    STATUS      current
    DESCRIPTION ""
    ::= { affirmedIpProtocolsOspfv3RouterShowDBNssaDbEntry 1 }

affirmedIpProtocolsOspfv3RouterShowDBNssaDbOutput OBJECT-TYPE
    SYNTAX      String
    MAX-ACCESS  read-only
    STATUS      current
    DESCRIPTION ""
    ::= { affirmedIpProtocolsOspfv3RouterShowDBNssaDbEntry 2 }

affirmedIpProtocolsOspfv3RouterShowDBDbSummaryDbTable OBJECT-TYPE
    SYNTAX      SEQUENCE OF AffirmedIpProtocolsOspfv3RouterShowDBDbSummaryDbEntry
    MAX-ACCESS  not-accessible
    STATUS      current
    DESCRIPTION "Database summary"
    ::= { affirmedIpProtocolsOspfv3 19 }

affirmedIpProtocolsOspfv3RouterShowDBDbSummaryDbEntry OBJECT-TYPE
    SYNTAX      AffirmedIpProtocolsOspfv3RouterShowDBDbSummaryDbEntry
    MAX-ACCESS  not-accessible
    STATUS      current
    DESCRIPTION ""
    INDEX { affirmedIpProtocolsOspfv3RouterNetworkContext, affirmedIpProtocolsOspfv3RouterShowDBDbSummaryDbEntryId }
        ::= { affirmedIpProtocolsOspfv3RouterShowDBDbSummaryDbTable 1 }

AffirmedIpProtocolsOspfv3RouterShowDBDbSummaryDbEntry ::=
    SEQUENCE {
        affirmedIpProtocolsOspfv3RouterShowDBDbSummaryDbEntryId INTEGER,
        affirmedIpProtocolsOspfv3RouterShowDBDbSummaryDbOutput String
    }

affirmedIpProtocolsOspfv3RouterShowDBDbSummaryDbEntryId OBJECT-TYPE
    SYNTAX      INTEGER {entry(0)}
    MAX-ACCESS  not-accessible
    STATUS      current
    DESCRIPTION ""
    ::= { affirmedIpProtocolsOspfv3RouterShowDBDbSummaryDbEntry 1 }

affirmedIpProtocolsOspfv3RouterShowDBDbSummaryDbOutput OBJECT-TYPE
    SYNTAX      String
    MAX-ACCESS  read-only
    STATUS      current
    DESCRIPTION ""
    ::= { affirmedIpProtocolsOspfv3RouterShowDBDbSummaryDbEntry 2 }

affirmedIpProtocolsBfdInstanceTable OBJECT-TYPE
    SYNTAX      SEQUENCE OF AffirmedIpProtocolsBfdInstanceEntry
    MAX-ACCESS  not-accessible
    STATUS      current
    DESCRIPTION ""
    ::= { affirmedIpProtocolsBfd 1 }

affirmedIpProtocolsBfdInstanceEntry OBJECT-TYPE
    SYNTAX      AffirmedIpProtocolsBfdInstanceEntry
    MAX-ACCESS  not-accessible
    STATUS      current
    DESCRIPTION ""
    INDEX { affirmedIpProtocolsBfdInstanceNetworkContext }
        ::= { affirmedIpProtocolsBfdInstanceTable 1 }

AffirmedIpProtocolsBfdInstanceEntry ::=
    SEQUENCE {
        affirmedIpProtocolsBfdInstanceNetworkContext String,
        affirmedIpProtocolsBfdInstanceRowstatus RowStatus
    }

affirmedIpProtocolsBfdInstanceNetworkContext OBJECT-TYPE
    SYNTAX      String
    MAX-ACCESS  not-accessible
    STATUS      current
    DESCRIPTION "Network Context for this BFD instance"
    ::= { affirmedIpProtocolsBfdInstanceEntry 1 }

affirmedIpProtocolsBfdInstanceRowstatus OBJECT-TYPE
    SYNTAX      RowStatus
    MAX-ACCESS  read-create
    STATUS      current
    DESCRIPTION ""
    ::= { affirmedIpProtocolsBfdInstanceEntry 2 }

affirmedIpProtocolsBfdInstanceShowBfdTable OBJECT-TYPE
    SYNTAX      SEQUENCE OF AffirmedIpProtocolsBfdInstanceShowBfdEntry
    MAX-ACCESS  not-accessible
    STATUS      deprecated
    DESCRIPTION ""
    ::= { affirmedIpProtocolsBfd 2 }

affirmedIpProtocolsBfdInstanceShowBfdEntry OBJECT-TYPE
    SYNTAX      AffirmedIpProtocolsBfdInstanceShowBfdEntry
    MAX-ACCESS  not-accessible
    STATUS      deprecated
    DESCRIPTION ""
    INDEX { affirmedIpProtocolsBfdInstanceNetworkContext, affirmedIpProtocolsBfdInstanceShowBfdEntryId }
        ::= { affirmedIpProtocolsBfdInstanceShowBfdTable 1 }

AffirmedIpProtocolsBfdInstanceShowBfdEntry ::=
    SEQUENCE {
        affirmedIpProtocolsBfdInstanceShowBfdEntryId INTEGER,
        affirmedIpProtocolsBfdInstanceShowBfdOutput String
    }

affirmedIpProtocolsBfdInstanceShowBfdEntryId OBJECT-TYPE
    SYNTAX      INTEGER {entry(0)}
    MAX-ACCESS  not-accessible
    STATUS      current
    DESCRIPTION ""
    ::= { affirmedIpProtocolsBfdInstanceShowBfdEntry 1 }

affirmedIpProtocolsBfdInstanceShowBfdOutput OBJECT-TYPE
    SYNTAX      String
    MAX-ACCESS  read-only
    STATUS      current
    DESCRIPTION ""
    ::= { affirmedIpProtocolsBfdInstanceShowBfdEntry 2 }

affirmedIpProtocolsBfdInstanceShowBfdSessionsTable OBJECT-TYPE
    SYNTAX      SEQUENCE OF AffirmedIpProtocolsBfdInstanceShowBfdSessionsEntry
    MAX-ACCESS  not-accessible
    STATUS      deprecated
    DESCRIPTION ""
    ::= { affirmedIpProtocolsBfd 3 }

affirmedIpProtocolsBfdInstanceShowBfdSessionsEntry OBJECT-TYPE
    SYNTAX      AffirmedIpProtocolsBfdInstanceShowBfdSessionsEntry
    MAX-ACCESS  not-accessible
    STATUS      deprecated
    DESCRIPTION ""
    INDEX { affirmedIpProtocolsBfdInstanceNetworkContext, affirmedIpProtocolsBfdInstanceShowBfdSessionsEntryId }
        ::= { affirmedIpProtocolsBfdInstanceShowBfdSessionsTable 1 }

AffirmedIpProtocolsBfdInstanceShowBfdSessionsEntry ::=
    SEQUENCE {
        affirmedIpProtocolsBfdInstanceShowBfdSessionsEntryId INTEGER,
        affirmedIpProtocolsBfdInstanceShowBfdSessionsOutput String
    }

affirmedIpProtocolsBfdInstanceShowBfdSessionsEntryId OBJECT-TYPE
    SYNTAX      INTEGER {entry(0)}
    MAX-ACCESS  not-accessible
    STATUS      current
    DESCRIPTION ""
    ::= { affirmedIpProtocolsBfdInstanceShowBfdSessionsEntry 1 }

affirmedIpProtocolsBfdInstanceShowBfdSessionsOutput OBJECT-TYPE
    SYNTAX      String
    MAX-ACCESS  read-only
    STATUS      current
    DESCRIPTION ""
    ::= { affirmedIpProtocolsBfdInstanceShowBfdSessionsEntry 2 }

affirmedIpProtocolsBfdInstanceShowBfdInterfaceTable OBJECT-TYPE
    SYNTAX      SEQUENCE OF AffirmedIpProtocolsBfdInstanceShowBfdInterfaceEntry
    MAX-ACCESS  not-accessible
    STATUS      deprecated
    DESCRIPTION ""
    ::= { affirmedIpProtocolsBfd 4 }

affirmedIpProtocolsBfdInstanceShowBfdInterfaceEntry OBJECT-TYPE
    SYNTAX      AffirmedIpProtocolsBfdInstanceShowBfdInterfaceEntry
    MAX-ACCESS  not-accessible
    STATUS      deprecated
    DESCRIPTION ""
    INDEX { affirmedIpProtocolsBfdInstanceNetworkContext, affirmedIpProtocolsBfdInstanceShowBfdInterfaceEntryId }
        ::= { affirmedIpProtocolsBfdInstanceShowBfdInterfaceTable 1 }

AffirmedIpProtocolsBfdInstanceShowBfdInterfaceEntry ::=
    SEQUENCE {
        affirmedIpProtocolsBfdInstanceShowBfdInterfaceEntryId INTEGER,
        affirmedIpProtocolsBfdInstanceShowBfdInterfaceOutput String
    }

affirmedIpProtocolsBfdInstanceShowBfdInterfaceEntryId OBJECT-TYPE
    SYNTAX      INTEGER {entry(0)}
    MAX-ACCESS  not-accessible
    STATUS      current
    DESCRIPTION ""
    ::= { affirmedIpProtocolsBfdInstanceShowBfdInterfaceEntry 1 }

affirmedIpProtocolsBfdInstanceShowBfdInterfaceOutput OBJECT-TYPE
    SYNTAX      String
    MAX-ACCESS  read-only
    STATUS      current
    DESCRIPTION ""
    ::= { affirmedIpProtocolsBfdInstanceShowBfdInterfaceEntry 2 }

affirmedIpProtocolsBfdInstanceShowBfdAllTable OBJECT-TYPE
    SYNTAX      SEQUENCE OF AffirmedIpProtocolsBfdInstanceShowBfdAllEntry
    MAX-ACCESS  not-accessible
    STATUS      deprecated
    DESCRIPTION ""
    ::= { affirmedIpProtocolsBfd 5 }

affirmedIpProtocolsBfdInstanceShowBfdAllEntry OBJECT-TYPE
    SYNTAX      AffirmedIpProtocolsBfdInstanceShowBfdAllEntry
    MAX-ACCESS  not-accessible
    STATUS      deprecated
    DESCRIPTION ""
    INDEX { affirmedIpProtocolsBfdInstanceNetworkContext, affirmedIpProtocolsBfdInstanceShowBfdAllIfname, affirmedIpProtocolsBfdInstanceShowBfdAllPeeraddr }
        ::= { affirmedIpProtocolsBfdInstanceShowBfdAllTable 1 }

AffirmedIpProtocolsBfdInstanceShowBfdAllEntry ::=
    SEQUENCE {
        affirmedIpProtocolsBfdInstanceShowBfdAllIfname String,
        affirmedIpProtocolsBfdInstanceShowBfdAllPeeraddr String,
        affirmedIpProtocolsBfdInstanceShowBfdAllSessiontype String,
        affirmedIpProtocolsBfdInstanceShowBfdAllAdminstate String,
        affirmedIpProtocolsBfdInstanceShowBfdAllOperstate String,
        affirmedIpProtocolsBfdInstanceShowBfdAllOperstatereason String,
        affirmedIpProtocolsBfdInstanceShowBfdAllProtoclients String,
        affirmedIpProtocolsBfdInstanceShowBfdAllHostingSSMid String
    }

affirmedIpProtocolsBfdInstanceShowBfdAllIfname OBJECT-TYPE
    SYNTAX      String
    MAX-ACCESS  not-accessible
    STATUS      current
    DESCRIPTION ""
    ::= { affirmedIpProtocolsBfdInstanceShowBfdAllEntry 1 }

affirmedIpProtocolsBfdInstanceShowBfdAllPeeraddr OBJECT-TYPE
    SYNTAX      String
    MAX-ACCESS  not-accessible
    STATUS      current
    DESCRIPTION ""
    ::= { affirmedIpProtocolsBfdInstanceShowBfdAllEntry 2 }

affirmedIpProtocolsBfdInstanceShowBfdAllSessiontype OBJECT-TYPE
    SYNTAX      String
    MAX-ACCESS  read-only
    STATUS      current
    DESCRIPTION ""
    ::= { affirmedIpProtocolsBfdInstanceShowBfdAllEntry 3 }

affirmedIpProtocolsBfdInstanceShowBfdAllAdminstate OBJECT-TYPE
    SYNTAX      String
    MAX-ACCESS  read-only
    STATUS      current
    DESCRIPTION ""
    ::= { affirmedIpProtocolsBfdInstanceShowBfdAllEntry 4 }

affirmedIpProtocolsBfdInstanceShowBfdAllOperstate OBJECT-TYPE
    SYNTAX      String
    MAX-ACCESS  read-only
    STATUS      current
    DESCRIPTION ""
    ::= { affirmedIpProtocolsBfdInstanceShowBfdAllEntry 5 }

affirmedIpProtocolsBfdInstanceShowBfdAllOperstatereason OBJECT-TYPE
    SYNTAX      String
    MAX-ACCESS  read-only
    STATUS      current
    DESCRIPTION ""
    ::= { affirmedIpProtocolsBfdInstanceShowBfdAllEntry 6 }

affirmedIpProtocolsBfdInstanceShowBfdAllProtoclients OBJECT-TYPE
    SYNTAX      String
    MAX-ACCESS  read-only
    STATUS      current
    DESCRIPTION ""
    ::= { affirmedIpProtocolsBfdInstanceShowBfdAllEntry 7 }

affirmedIpProtocolsBfdInstanceShowBfdAllHostingSSMid OBJECT-TYPE
    SYNTAX      String
    MAX-ACCESS  read-only
    STATUS      current
    DESCRIPTION ""
    ::= { affirmedIpProtocolsBfdInstanceShowBfdAllEntry 8 }

affirmedIpProtocolsBfdInstanceShowBfdSessionDetailTable OBJECT-TYPE
    SYNTAX      SEQUENCE OF AffirmedIpProtocolsBfdInstanceShowBfdSessionDetailEntry
    MAX-ACCESS  not-accessible
    STATUS      current
    DESCRIPTION ""
    ::= { affirmedIpProtocolsBfd 6 }

affirmedIpProtocolsBfdInstanceShowBfdSessionDetailEntry OBJECT-TYPE
    SYNTAX      AffirmedIpProtocolsBfdInstanceShowBfdSessionDetailEntry
    MAX-ACCESS  not-accessible
    STATUS      current
    DESCRIPTION ""
    INDEX { affirmedIpProtocolsBfdInstanceNetworkContext, affirmedIpProtocolsBfdInstanceShowBfdSessionDetailIfname, affirmedIpProtocolsBfdInstanceShowBfdSessionDetailPeeraddr }
        ::= { affirmedIpProtocolsBfdInstanceShowBfdSessionDetailTable 1 }

AffirmedIpProtocolsBfdInstanceShowBfdSessionDetailEntry ::=
    SEQUENCE {
        affirmedIpProtocolsBfdInstanceShowBfdSessionDetailIfname String,
        affirmedIpProtocolsBfdInstanceShowBfdSessionDetailPeeraddr String,
        affirmedIpProtocolsBfdInstanceShowBfdSessionDetailSessionuptime String,
        affirmedIpProtocolsBfdInstanceShowBfdSessionDetailLocaldisc Unsigned32,
        affirmedIpProtocolsBfdInstanceShowBfdSessionDetailRemotedisc Unsigned32,
        affirmedIpProtocolsBfdInstanceShowBfdSessionDetailRemotestate String,
        affirmedIpProtocolsBfdInstanceShowBfdSessionDetailDownstatetransitions Unsigned32,
        affirmedIpProtocolsBfdInstanceShowBfdSessionDetailInitstatetransitions Unsigned32,
        affirmedIpProtocolsBfdInstanceShowBfdSessionDetailUpstatetransitions Unsigned32,
        affirmedIpProtocolsBfdInstanceShowBfdSessionDetailNumpktsIn Unsigned32,
        affirmedIpProtocolsBfdInstanceShowBfdSessionDetailNumpktsechoin Unsigned32,
        affirmedIpProtocolsBfdInstanceShowBfdSessionDetailNumpktsechout Unsigned32,
        affirmedIpProtocolsBfdInstanceShowBfdSessionDetailNumpktserrorsin Unsigned32,
        affirmedIpProtocolsBfdInstanceShowBfdSessionDetailNumpktserrorsout Unsigned32,
        affirmedIpProtocolsBfdInstanceShowBfdSessionDetailNumpktsbadhdrlength Unsigned32,
        affirmedIpProtocolsBfdInstanceShowBfdSessionDetailNumpktsbuffermismatch Unsigned32,
        affirmedIpProtocolsBfdInstanceShowBfdSessionDetailNumpktszeromultiplier Unsigned32,
        affirmedIpProtocolsBfdInstanceShowBfdSessionDetailNumpktszeromydescriptor Unsigned32,
        affirmedIpProtocolsBfdInstanceShowBfdSessionDetailNumpktszeromintx Unsigned32,
        affirmedIpProtocolsBfdInstanceShowBfdSessionDetailNumpktsnosession Unsigned32,
        affirmedIpProtocolsBfdInstanceShowBfdSessionDetailNumpktsbadecho Unsigned32,
        affirmedIpProtocolsBfdInstanceShowBfdSessionDetailNumpktsadmindown Unsigned32,
        affirmedIpProtocolsBfdInstanceShowBfdSessionDetailNumpktsnoautherr Unsigned32,
        affirmedIpProtocolsBfdInstanceShowBfdSessionDetailNumpktshellotimererr Unsigned32,
        affirmedIpProtocolsBfdInstanceShowBfdSessionDetailNumpktsechotimererr Unsigned32,
        affirmedIpProtocolsBfdInstanceShowBfdSessionDetailNumpktsechoinacttimererr Unsigned32,
        affirmedIpProtocolsBfdInstanceShowBfdSessionDetailNumpktsinacttimererr Unsigned32
    }

affirmedIpProtocolsBfdInstanceShowBfdSessionDetailIfname OBJECT-TYPE
    SYNTAX      String
    MAX-ACCESS  not-accessible
    STATUS      current
    DESCRIPTION ""
    ::= { affirmedIpProtocolsBfdInstanceShowBfdSessionDetailEntry 1 }

affirmedIpProtocolsBfdInstanceShowBfdSessionDetailPeeraddr OBJECT-TYPE
    SYNTAX      String
    MAX-ACCESS  not-accessible
    STATUS      current
    DESCRIPTION ""
    ::= { affirmedIpProtocolsBfdInstanceShowBfdSessionDetailEntry 2 }

affirmedIpProtocolsBfdInstanceShowBfdSessionDetailSessionuptime OBJECT-TYPE
    SYNTAX      String
    MAX-ACCESS  read-only
    STATUS      current
    DESCRIPTION ""
    ::= { affirmedIpProtocolsBfdInstanceShowBfdSessionDetailEntry 3 }

affirmedIpProtocolsBfdInstanceShowBfdSessionDetailLocaldisc OBJECT-TYPE
    SYNTAX      Unsigned32
    MAX-ACCESS  read-only
    STATUS      current
    DESCRIPTION ""
    ::= { affirmedIpProtocolsBfdInstanceShowBfdSessionDetailEntry 4 }

affirmedIpProtocolsBfdInstanceShowBfdSessionDetailRemotedisc OBJECT-TYPE
    SYNTAX      Unsigned32
    MAX-ACCESS  read-only
    STATUS      current
    DESCRIPTION ""
    ::= { affirmedIpProtocolsBfdInstanceShowBfdSessionDetailEntry 5 }

affirmedIpProtocolsBfdInstanceShowBfdSessionDetailRemotestate OBJECT-TYPE
    SYNTAX      String
    MAX-ACCESS  read-only
    STATUS      current
    DESCRIPTION ""
    ::= { affirmedIpProtocolsBfdInstanceShowBfdSessionDetailEntry 6 }

affirmedIpProtocolsBfdInstanceShowBfdSessionDetailDownstatetransitions OBJECT-TYPE
    SYNTAX      Unsigned32
    MAX-ACCESS  read-only
    STATUS      current
    DESCRIPTION ""
    ::= { affirmedIpProtocolsBfdInstanceShowBfdSessionDetailEntry 7 }

affirmedIpProtocolsBfdInstanceShowBfdSessionDetailInitstatetransitions OBJECT-TYPE
    SYNTAX      Unsigned32
    MAX-ACCESS  read-only
    STATUS      current
    DESCRIPTION ""
    ::= { affirmedIpProtocolsBfdInstanceShowBfdSessionDetailEntry 8 }

affirmedIpProtocolsBfdInstanceShowBfdSessionDetailUpstatetransitions OBJECT-TYPE
    SYNTAX      Unsigned32
    MAX-ACCESS  read-only
    STATUS      current
    DESCRIPTION ""
    ::= { affirmedIpProtocolsBfdInstanceShowBfdSessionDetailEntry 9 }

affirmedIpProtocolsBfdInstanceShowBfdSessionDetailNumpktsIn OBJECT-TYPE
    SYNTAX      Unsigned32
    MAX-ACCESS  read-only
    STATUS      current
    DESCRIPTION ""
    ::= { affirmedIpProtocolsBfdInstanceShowBfdSessionDetailEntry 10 }

affirmedIpProtocolsBfdInstanceShowBfdSessionDetailNumpktsechoin OBJECT-TYPE
    SYNTAX      Unsigned32
    MAX-ACCESS  read-only
    STATUS      current
    DESCRIPTION ""
    ::= { affirmedIpProtocolsBfdInstanceShowBfdSessionDetailEntry 11 }

affirmedIpProtocolsBfdInstanceShowBfdSessionDetailNumpktsechout OBJECT-TYPE
    SYNTAX      Unsigned32
    MAX-ACCESS  read-only
    STATUS      current
    DESCRIPTION ""
    ::= { affirmedIpProtocolsBfdInstanceShowBfdSessionDetailEntry 12 }

affirmedIpProtocolsBfdInstanceShowBfdSessionDetailNumpktserrorsin OBJECT-TYPE
    SYNTAX      Unsigned32
    MAX-ACCESS  read-only
    STATUS      current
    DESCRIPTION ""
    ::= { affirmedIpProtocolsBfdInstanceShowBfdSessionDetailEntry 13 }

affirmedIpProtocolsBfdInstanceShowBfdSessionDetailNumpktserrorsout OBJECT-TYPE
    SYNTAX      Unsigned32
    MAX-ACCESS  read-only
    STATUS      current
    DESCRIPTION ""
    ::= { affirmedIpProtocolsBfdInstanceShowBfdSessionDetailEntry 14 }

affirmedIpProtocolsBfdInstanceShowBfdSessionDetailNumpktsbadhdrlength OBJECT-TYPE
    SYNTAX      Unsigned32
    MAX-ACCESS  read-only
    STATUS      current
    DESCRIPTION ""
    ::= { affirmedIpProtocolsBfdInstanceShowBfdSessionDetailEntry 15 }

affirmedIpProtocolsBfdInstanceShowBfdSessionDetailNumpktsbuffermismatch OBJECT-TYPE
    SYNTAX      Unsigned32
    MAX-ACCESS  read-only
    STATUS      current
    DESCRIPTION ""
    ::= { affirmedIpProtocolsBfdInstanceShowBfdSessionDetailEntry 16 }

affirmedIpProtocolsBfdInstanceShowBfdSessionDetailNumpktszeromultiplier OBJECT-TYPE
    SYNTAX      Unsigned32
    MAX-ACCESS  read-only
    STATUS      current
    DESCRIPTION ""
    ::= { affirmedIpProtocolsBfdInstanceShowBfdSessionDetailEntry 17 }

affirmedIpProtocolsBfdInstanceShowBfdSessionDetailNumpktszeromydescriptor OBJECT-TYPE
    SYNTAX      Unsigned32
    MAX-ACCESS  read-only
    STATUS      current
    DESCRIPTION ""
    ::= { affirmedIpProtocolsBfdInstanceShowBfdSessionDetailEntry 18 }

affirmedIpProtocolsBfdInstanceShowBfdSessionDetailNumpktszeromintx OBJECT-TYPE
    SYNTAX      Unsigned32
    MAX-ACCESS  read-only
    STATUS      current
    DESCRIPTION ""
    ::= { affirmedIpProtocolsBfdInstanceShowBfdSessionDetailEntry 19 }

affirmedIpProtocolsBfdInstanceShowBfdSessionDetailNumpktsnosession OBJECT-TYPE
    SYNTAX      Unsigned32
    MAX-ACCESS  read-only
    STATUS      current
    DESCRIPTION ""
    ::= { affirmedIpProtocolsBfdInstanceShowBfdSessionDetailEntry 20 }

affirmedIpProtocolsBfdInstanceShowBfdSessionDetailNumpktsbadecho OBJECT-TYPE
    SYNTAX      Unsigned32
    MAX-ACCESS  read-only
    STATUS      current
    DESCRIPTION ""
    ::= { affirmedIpProtocolsBfdInstanceShowBfdSessionDetailEntry 21 }

affirmedIpProtocolsBfdInstanceShowBfdSessionDetailNumpktsadmindown OBJECT-TYPE
    SYNTAX      Unsigned32
    MAX-ACCESS  read-only
    STATUS      current
    DESCRIPTION ""
    ::= { affirmedIpProtocolsBfdInstanceShowBfdSessionDetailEntry 22 }

affirmedIpProtocolsBfdInstanceShowBfdSessionDetailNumpktsnoautherr OBJECT-TYPE
    SYNTAX      Unsigned32
    MAX-ACCESS  read-only
    STATUS      current
    DESCRIPTION ""
    ::= { affirmedIpProtocolsBfdInstanceShowBfdSessionDetailEntry 23 }

affirmedIpProtocolsBfdInstanceShowBfdSessionDetailNumpktshellotimererr OBJECT-TYPE
    SYNTAX      Unsigned32
    MAX-ACCESS  read-only
    STATUS      current
    DESCRIPTION ""
    ::= { affirmedIpProtocolsBfdInstanceShowBfdSessionDetailEntry 24 }

affirmedIpProtocolsBfdInstanceShowBfdSessionDetailNumpktsechotimererr OBJECT-TYPE
    SYNTAX      Unsigned32
    MAX-ACCESS  read-only
    STATUS      current
    DESCRIPTION ""
    ::= { affirmedIpProtocolsBfdInstanceShowBfdSessionDetailEntry 25 }

affirmedIpProtocolsBfdInstanceShowBfdSessionDetailNumpktsechoinacttimererr OBJECT-TYPE
    SYNTAX      Unsigned32
    MAX-ACCESS  read-only
    STATUS      current
    DESCRIPTION ""
    ::= { affirmedIpProtocolsBfdInstanceShowBfdSessionDetailEntry 26 }

affirmedIpProtocolsBfdInstanceShowBfdSessionDetailNumpktsinacttimererr OBJECT-TYPE
    SYNTAX      Unsigned32
    MAX-ACCESS  read-only
    STATUS      current
    DESCRIPTION ""
    ::= { affirmedIpProtocolsBfdInstanceShowBfdSessionDetailEntry 27 }

affirmedIpProtocolsBfdInstanceShowBfdAllNewTable OBJECT-TYPE
    SYNTAX      SEQUENCE OF AffirmedIpProtocolsBfdInstanceShowBfdAllNewEntry
    MAX-ACCESS  not-accessible
    STATUS      deprecated
    DESCRIPTION ""
    ::= { affirmedIpProtocolsBfd 7 }

affirmedIpProtocolsBfdInstanceShowBfdAllNewEntry OBJECT-TYPE
    SYNTAX      AffirmedIpProtocolsBfdInstanceShowBfdAllNewEntry
    MAX-ACCESS  not-accessible
    STATUS      deprecated
    DESCRIPTION ""
    INDEX { affirmedIpProtocolsBfdInstanceNetworkContext, affirmedIpProtocolsBfdInstanceShowBfdAllNewIfname, affirmedIpProtocolsBfdInstanceShowBfdAllNewPeeraddr, affirmedIpProtocolsBfdInstanceShowBfdAllNewSlotid }
        ::= { affirmedIpProtocolsBfdInstanceShowBfdAllNewTable 1 }

AffirmedIpProtocolsBfdInstanceShowBfdAllNewEntry ::=
    SEQUENCE {
        affirmedIpProtocolsBfdInstanceShowBfdAllNewIfname String,
        affirmedIpProtocolsBfdInstanceShowBfdAllNewPeeraddr String,
        affirmedIpProtocolsBfdInstanceShowBfdAllNewSlotid Unsigned32,
        affirmedIpProtocolsBfdInstanceShowBfdAllNewSessiontype String,
        affirmedIpProtocolsBfdInstanceShowBfdAllNewAdminstate String,
        affirmedIpProtocolsBfdInstanceShowBfdAllNewOperstate String,
        affirmedIpProtocolsBfdInstanceShowBfdAllNewOperstatereason String,
        affirmedIpProtocolsBfdInstanceShowBfdAllNewProtoclients String,
        affirmedIpProtocolsBfdInstanceShowBfdAllNewHostingSSMid String,
        affirmedIpProtocolsBfdInstanceShowBfdAllNewUptime String
    }

affirmedIpProtocolsBfdInstanceShowBfdAllNewIfname OBJECT-TYPE
    SYNTAX      String
    MAX-ACCESS  not-accessible
    STATUS      current
    DESCRIPTION ""
    ::= { affirmedIpProtocolsBfdInstanceShowBfdAllNewEntry 1 }

affirmedIpProtocolsBfdInstanceShowBfdAllNewPeeraddr OBJECT-TYPE
    SYNTAX      String
    MAX-ACCESS  not-accessible
    STATUS      current
    DESCRIPTION ""
    ::= { affirmedIpProtocolsBfdInstanceShowBfdAllNewEntry 2 }

affirmedIpProtocolsBfdInstanceShowBfdAllNewSlotid OBJECT-TYPE
    SYNTAX      Unsigned32
    MAX-ACCESS  not-accessible
    STATUS      current
    DESCRIPTION ""
    ::= { affirmedIpProtocolsBfdInstanceShowBfdAllNewEntry 3 }

affirmedIpProtocolsBfdInstanceShowBfdAllNewSessiontype OBJECT-TYPE
    SYNTAX      String
    MAX-ACCESS  read-only
    STATUS      current
    DESCRIPTION ""
    ::= { affirmedIpProtocolsBfdInstanceShowBfdAllNewEntry 4 }

affirmedIpProtocolsBfdInstanceShowBfdAllNewAdminstate OBJECT-TYPE
    SYNTAX      String
    MAX-ACCESS  read-only
    STATUS      current
    DESCRIPTION ""
    ::= { affirmedIpProtocolsBfdInstanceShowBfdAllNewEntry 5 }

affirmedIpProtocolsBfdInstanceShowBfdAllNewOperstate OBJECT-TYPE
    SYNTAX      String
    MAX-ACCESS  read-only
    STATUS      current
    DESCRIPTION ""
    ::= { affirmedIpProtocolsBfdInstanceShowBfdAllNewEntry 6 }

affirmedIpProtocolsBfdInstanceShowBfdAllNewOperstatereason OBJECT-TYPE
    SYNTAX      String
    MAX-ACCESS  read-only
    STATUS      current
    DESCRIPTION ""
    ::= { affirmedIpProtocolsBfdInstanceShowBfdAllNewEntry 7 }

affirmedIpProtocolsBfdInstanceShowBfdAllNewProtoclients OBJECT-TYPE
    SYNTAX      String
    MAX-ACCESS  read-only
    STATUS      current
    DESCRIPTION ""
    ::= { affirmedIpProtocolsBfdInstanceShowBfdAllNewEntry 8 }

affirmedIpProtocolsBfdInstanceShowBfdAllNewHostingSSMid OBJECT-TYPE
    SYNTAX      String
    MAX-ACCESS  read-only
    STATUS      current
    DESCRIPTION ""
    ::= { affirmedIpProtocolsBfdInstanceShowBfdAllNewEntry 9 }

affirmedIpProtocolsBfdInstanceShowBfdAllNewUptime OBJECT-TYPE
    SYNTAX      String
    MAX-ACCESS  read-only
    STATUS      current
    DESCRIPTION "Displays up time of a BFD session"
    ::= { affirmedIpProtocolsBfdInstanceShowBfdAllNewEntry 10 }

affirmedIpProtocolsBfdInstanceShowBfdAll2Table OBJECT-TYPE
    SYNTAX      SEQUENCE OF AffirmedIpProtocolsBfdInstanceShowBfdAll2Entry
    MAX-ACCESS  not-accessible
    STATUS      current
    DESCRIPTION ""
    ::= { affirmedIpProtocolsBfd 8 }

affirmedIpProtocolsBfdInstanceShowBfdAll2Entry OBJECT-TYPE
    SYNTAX      AffirmedIpProtocolsBfdInstanceShowBfdAll2Entry
    MAX-ACCESS  not-accessible
    STATUS      current
    DESCRIPTION ""
    INDEX { affirmedIpProtocolsBfdInstanceNetworkContext, affirmedIpProtocolsBfdInstanceShowBfdAll2Ifname, affirmedIpProtocolsBfdInstanceShowBfdAll2Localaddr, affirmedIpProtocolsBfdInstanceShowBfdAll2Peeraddr, affirmedIpProtocolsBfdInstanceShowBfdAll2Slotid }
        ::= { affirmedIpProtocolsBfdInstanceShowBfdAll2Table 1 }

AffirmedIpProtocolsBfdInstanceShowBfdAll2Entry ::=
    SEQUENCE {
        affirmedIpProtocolsBfdInstanceShowBfdAll2Ifname String,
        affirmedIpProtocolsBfdInstanceShowBfdAll2Localaddr String,
        affirmedIpProtocolsBfdInstanceShowBfdAll2Peeraddr String,
        affirmedIpProtocolsBfdInstanceShowBfdAll2Slotid Unsigned32,
        affirmedIpProtocolsBfdInstanceShowBfdAll2Sessiontype String,
        affirmedIpProtocolsBfdInstanceShowBfdAll2Adminstate String,
        affirmedIpProtocolsBfdInstanceShowBfdAll2Operstate String,
        affirmedIpProtocolsBfdInstanceShowBfdAll2Operstatereason String,
        affirmedIpProtocolsBfdInstanceShowBfdAll2Protoclients String,
        affirmedIpProtocolsBfdInstanceShowBfdAll2HostingSSMid String,
        affirmedIpProtocolsBfdInstanceShowBfdAll2Uptime String
    }

affirmedIpProtocolsBfdInstanceShowBfdAll2Ifname OBJECT-TYPE
    SYNTAX      String
    MAX-ACCESS  not-accessible
    STATUS      current
    DESCRIPTION ""
    ::= { affirmedIpProtocolsBfdInstanceShowBfdAll2Entry 1 }

affirmedIpProtocolsBfdInstanceShowBfdAll2Localaddr OBJECT-TYPE
    SYNTAX      String
    MAX-ACCESS  not-accessible
    STATUS      current
    DESCRIPTION ""
    ::= { affirmedIpProtocolsBfdInstanceShowBfdAll2Entry 2 }

affirmedIpProtocolsBfdInstanceShowBfdAll2Peeraddr OBJECT-TYPE
    SYNTAX      String
    MAX-ACCESS  not-accessible
    STATUS      current
    DESCRIPTION ""
    ::= { affirmedIpProtocolsBfdInstanceShowBfdAll2Entry 3 }

affirmedIpProtocolsBfdInstanceShowBfdAll2Slotid OBJECT-TYPE
    SYNTAX      Unsigned32
    MAX-ACCESS  not-accessible
    STATUS      current
    DESCRIPTION ""
    ::= { affirmedIpProtocolsBfdInstanceShowBfdAll2Entry 4 }

affirmedIpProtocolsBfdInstanceShowBfdAll2Sessiontype OBJECT-TYPE
    SYNTAX      String
    MAX-ACCESS  read-only
    STATUS      current
    DESCRIPTION ""
    ::= { affirmedIpProtocolsBfdInstanceShowBfdAll2Entry 5 }

affirmedIpProtocolsBfdInstanceShowBfdAll2Adminstate OBJECT-TYPE
    SYNTAX      String
    MAX-ACCESS  read-only
    STATUS      current
    DESCRIPTION ""
    ::= { affirmedIpProtocolsBfdInstanceShowBfdAll2Entry 6 }

affirmedIpProtocolsBfdInstanceShowBfdAll2Operstate OBJECT-TYPE
    SYNTAX      String
    MAX-ACCESS  read-only
    STATUS      current
    DESCRIPTION ""
    ::= { affirmedIpProtocolsBfdInstanceShowBfdAll2Entry 7 }

affirmedIpProtocolsBfdInstanceShowBfdAll2Operstatereason OBJECT-TYPE
    SYNTAX      String
    MAX-ACCESS  read-only
    STATUS      current
    DESCRIPTION ""
    ::= { affirmedIpProtocolsBfdInstanceShowBfdAll2Entry 8 }

affirmedIpProtocolsBfdInstanceShowBfdAll2Protoclients OBJECT-TYPE
    SYNTAX      String
    MAX-ACCESS  read-only
    STATUS      current
    DESCRIPTION ""
    ::= { affirmedIpProtocolsBfdInstanceShowBfdAll2Entry 9 }

affirmedIpProtocolsBfdInstanceShowBfdAll2HostingSSMid OBJECT-TYPE
    SYNTAX      String
    MAX-ACCESS  read-only
    STATUS      current
    DESCRIPTION ""
    ::= { affirmedIpProtocolsBfdInstanceShowBfdAll2Entry 10 }

affirmedIpProtocolsBfdInstanceShowBfdAll2Uptime OBJECT-TYPE
    SYNTAX      String
    MAX-ACCESS  read-only
    STATUS      current
    DESCRIPTION "Displays up time of a BFD session"
    ::= { affirmedIpProtocolsBfdInstanceShowBfdAll2Entry 11 }

affirmedIpProtocolsNatGuaranteedNatPoolStatsTable OBJECT-TYPE
    SYNTAX      SEQUENCE OF AffirmedIpProtocolsNatGuaranteedNatPoolStatsEntry
    MAX-ACCESS  not-accessible
    STATUS      deprecated
    DESCRIPTION ""
    ::= { affirmedIpProtocolsNatGuaranteed 1 }

affirmedIpProtocolsNatGuaranteedNatPoolStatsEntry OBJECT-TYPE
    SYNTAX      AffirmedIpProtocolsNatGuaranteedNatPoolStatsEntry
    MAX-ACCESS  not-accessible
    STATUS      deprecated
    DESCRIPTION ""
    INDEX { affirmedIpProtocolsNatGuaranteedNatPoolStatsNetworkContext, affirmedIpProtocolsNatGuaranteedNatPoolStatsPoolName }
        ::= { affirmedIpProtocolsNatGuaranteedNatPoolStatsTable 1 }

AffirmedIpProtocolsNatGuaranteedNatPoolStatsEntry ::=
    SEQUENCE {
        affirmedIpProtocolsNatGuaranteedNatPoolStatsNetworkContext String,
        affirmedIpProtocolsNatGuaranteedNatPoolStatsPoolName String,
        affirmedIpProtocolsNatGuaranteedNatPoolStatsCreateSessionSuccess ConfdString,
        affirmedIpProtocolsNatGuaranteedNatPoolStatsCreateSessionFailure ConfdString,
        affirmedIpProtocolsNatGuaranteedNatPoolStatsDeleteSessionCount ConfdString,
        affirmedIpProtocolsNatGuaranteedNatPoolStatsPortChunkAllocSuccess ConfdString,
        affirmedIpProtocolsNatGuaranteedNatPoolStatsPortChunkAllocFailure ConfdString,
        affirmedIpProtocolsNatGuaranteedNatPoolStatsPortChunkDealloc ConfdString,
        affirmedIpProtocolsNatGuaranteedNatPoolStatsSessionCount ConfdString,
        affirmedIpProtocolsNatGuaranteedNatPoolStatsSessionCapacityAvail ConfdString,
        affirmedIpProtocolsNatGuaranteedNatPoolStatsSessionUtil ConfdString,
        affirmedIpProtocolsNatGuaranteedNatPoolStatsPortChunksInUse ConfdString,
        affirmedIpProtocolsNatGuaranteedNatPoolStatsPortChunkUtil ConfdString
    }

affirmedIpProtocolsNatGuaranteedNatPoolStatsNetworkContext OBJECT-TYPE
    SYNTAX      String
    MAX-ACCESS  not-accessible
    STATUS      current
    DESCRIPTION ""
    ::= { affirmedIpProtocolsNatGuaranteedNatPoolStatsEntry 1 }

affirmedIpProtocolsNatGuaranteedNatPoolStatsPoolName OBJECT-TYPE
    SYNTAX      String
    MAX-ACCESS  not-accessible
    STATUS      current
    DESCRIPTION ""
    ::= { affirmedIpProtocolsNatGuaranteedNatPoolStatsEntry 2 }

affirmedIpProtocolsNatGuaranteedNatPoolStatsCreateSessionSuccess OBJECT-TYPE
    SYNTAX      ConfdString
    MAX-ACCESS  read-only
    STATUS      deprecated
    DESCRIPTION "Number of successful session creation requests with NAT resources"
    ::= { affirmedIpProtocolsNatGuaranteedNatPoolStatsEntry 3 }

affirmedIpProtocolsNatGuaranteedNatPoolStatsCreateSessionFailure OBJECT-TYPE
    SYNTAX      ConfdString
    MAX-ACCESS  read-only
    STATUS      deprecated
    DESCRIPTION "Number of failed session creation requests with NAT resources"
    ::= { affirmedIpProtocolsNatGuaranteedNatPoolStatsEntry 4 }

affirmedIpProtocolsNatGuaranteedNatPoolStatsDeleteSessionCount OBJECT-TYPE
    SYNTAX      ConfdString
    MAX-ACCESS  read-only
    STATUS      deprecated
    DESCRIPTION "Number of session delete requests processed"
    ::= { affirmedIpProtocolsNatGuaranteedNatPoolStatsEntry 5 }

affirmedIpProtocolsNatGuaranteedNatPoolStatsPortChunkAllocSuccess OBJECT-TYPE
    SYNTAX      ConfdString
    MAX-ACCESS  read-only
    STATUS      deprecated
    DESCRIPTION "Number of successful port chunk allocations"
    ::= { affirmedIpProtocolsNatGuaranteedNatPoolStatsEntry 6 }

affirmedIpProtocolsNatGuaranteedNatPoolStatsPortChunkAllocFailure OBJECT-TYPE
    SYNTAX      ConfdString
    MAX-ACCESS  read-only
    STATUS      deprecated
    DESCRIPTION "Number of port chunk allocation failures"
    ::= { affirmedIpProtocolsNatGuaranteedNatPoolStatsEntry 7 }

affirmedIpProtocolsNatGuaranteedNatPoolStatsPortChunkDealloc OBJECT-TYPE
    SYNTAX      ConfdString
    MAX-ACCESS  read-only
    STATUS      deprecated
    DESCRIPTION "Number of port chunk resources deallocated"
    ::= { affirmedIpProtocolsNatGuaranteedNatPoolStatsEntry 8 }

affirmedIpProtocolsNatGuaranteedNatPoolStatsSessionCount OBJECT-TYPE
    SYNTAX      ConfdString
    MAX-ACCESS  read-only
    STATUS      deprecated
    DESCRIPTION "Number of sessions currently using the NAT resources"
    ::= { affirmedIpProtocolsNatGuaranteedNatPoolStatsEntry 9 }

affirmedIpProtocolsNatGuaranteedNatPoolStatsSessionCapacityAvail OBJECT-TYPE
    SYNTAX      ConfdString
    MAX-ACCESS  read-only
    STATUS      deprecated
    DESCRIPTION "Number of additional sessions possible"
    ::= { affirmedIpProtocolsNatGuaranteedNatPoolStatsEntry 10 }

affirmedIpProtocolsNatGuaranteedNatPoolStatsSessionUtil OBJECT-TYPE
    SYNTAX      ConfdString
    MAX-ACCESS  read-only
    STATUS      deprecated
    DESCRIPTION "Percentage utilization of the NAT resources based on current session count"
    ::= { affirmedIpProtocolsNatGuaranteedNatPoolStatsEntry 11 }

affirmedIpProtocolsNatGuaranteedNatPoolStatsPortChunksInUse OBJECT-TYPE
    SYNTAX      ConfdString
    MAX-ACCESS  read-only
    STATUS      deprecated
    DESCRIPTION "Number of port chunks currently allocated"
    ::= { affirmedIpProtocolsNatGuaranteedNatPoolStatsEntry 12 }

affirmedIpProtocolsNatGuaranteedNatPoolStatsPortChunkUtil OBJECT-TYPE
    SYNTAX      ConfdString
    MAX-ACCESS  read-only
    STATUS      deprecated
    DESCRIPTION "Percentage utilization of the port chunk resources"
    ::= { affirmedIpProtocolsNatGuaranteedNatPoolStatsEntry 13 }

affirmedIpProtocolsNatGuaranteedSubPoolStatsTable OBJECT-TYPE
    SYNTAX      SEQUENCE OF AffirmedIpProtocolsNatGuaranteedSubPoolStatsEntry
    MAX-ACCESS  not-accessible
    STATUS      deprecated
    DESCRIPTION ""
    ::= { affirmedIpProtocolsNatGuaranteed 2 }

affirmedIpProtocolsNatGuaranteedSubPoolStatsEntry OBJECT-TYPE
    SYNTAX      AffirmedIpProtocolsNatGuaranteedSubPoolStatsEntry
    MAX-ACCESS  not-accessible
    STATUS      deprecated
    DESCRIPTION ""
    INDEX { affirmedIpProtocolsNatGuaranteedSubPoolStatsNetworkContext, affirmedIpProtocolsNatGuaranteedSubPoolStatsPoolName, affirmedIpProtocolsNatGuaranteedSubPoolStatsSubPoolName }
        ::= { affirmedIpProtocolsNatGuaranteedSubPoolStatsTable 1 }

AffirmedIpProtocolsNatGuaranteedSubPoolStatsEntry ::=
    SEQUENCE {
        affirmedIpProtocolsNatGuaranteedSubPoolStatsNetworkContext String,
        affirmedIpProtocolsNatGuaranteedSubPoolStatsPoolName String,
        affirmedIpProtocolsNatGuaranteedSubPoolStatsSubPoolName String,
        affirmedIpProtocolsNatGuaranteedSubPoolStatsCreateSessionSuccess ConfdString,
        affirmedIpProtocolsNatGuaranteedSubPoolStatsCreateSessionFailure ConfdString,
        affirmedIpProtocolsNatGuaranteedSubPoolStatsDeleteSessionCount ConfdString,
        affirmedIpProtocolsNatGuaranteedSubPoolStatsPortChunkAllocSuccess ConfdString,
        affirmedIpProtocolsNatGuaranteedSubPoolStatsPortChunkAllocFailure ConfdString,
        affirmedIpProtocolsNatGuaranteedSubPoolStatsPortChunkDealloc ConfdString,
        affirmedIpProtocolsNatGuaranteedSubPoolStatsSessionCount ConfdString,
        affirmedIpProtocolsNatGuaranteedSubPoolStatsSessionCapacityAvail ConfdString,
        affirmedIpProtocolsNatGuaranteedSubPoolStatsSessionUtil ConfdString,
        affirmedIpProtocolsNatGuaranteedSubPoolStatsPortChunksInUse ConfdString,
        affirmedIpProtocolsNatGuaranteedSubPoolStatsPortChunkUtil ConfdString
    }

affirmedIpProtocolsNatGuaranteedSubPoolStatsNetworkContext OBJECT-TYPE
    SYNTAX      String
    MAX-ACCESS  not-accessible
    STATUS      current
    DESCRIPTION ""
    ::= { affirmedIpProtocolsNatGuaranteedSubPoolStatsEntry 1 }

affirmedIpProtocolsNatGuaranteedSubPoolStatsPoolName OBJECT-TYPE
    SYNTAX      String
    MAX-ACCESS  not-accessible
    STATUS      current
    DESCRIPTION ""
    ::= { affirmedIpProtocolsNatGuaranteedSubPoolStatsEntry 2 }

affirmedIpProtocolsNatGuaranteedSubPoolStatsSubPoolName OBJECT-TYPE
    SYNTAX      String
    MAX-ACCESS  not-accessible
    STATUS      current
    DESCRIPTION ""
    ::= { affirmedIpProtocolsNatGuaranteedSubPoolStatsEntry 3 }

affirmedIpProtocolsNatGuaranteedSubPoolStatsCreateSessionSuccess OBJECT-TYPE
    SYNTAX      ConfdString
    MAX-ACCESS  read-only
    STATUS      deprecated
    DESCRIPTION "Number of successful session creation requests with NAT resources"
    ::= { affirmedIpProtocolsNatGuaranteedSubPoolStatsEntry 4 }

affirmedIpProtocolsNatGuaranteedSubPoolStatsCreateSessionFailure OBJECT-TYPE
    SYNTAX      ConfdString
    MAX-ACCESS  read-only
    STATUS      deprecated
    DESCRIPTION "Number of failed session creation requests with NAT resources"
    ::= { affirmedIpProtocolsNatGuaranteedSubPoolStatsEntry 5 }

affirmedIpProtocolsNatGuaranteedSubPoolStatsDeleteSessionCount OBJECT-TYPE
    SYNTAX      ConfdString
    MAX-ACCESS  read-only
    STATUS      deprecated
    DESCRIPTION "Number of session delete requests processed"
    ::= { affirmedIpProtocolsNatGuaranteedSubPoolStatsEntry 6 }

affirmedIpProtocolsNatGuaranteedSubPoolStatsPortChunkAllocSuccess OBJECT-TYPE
    SYNTAX      ConfdString
    MAX-ACCESS  read-only
    STATUS      deprecated
    DESCRIPTION "Number of successful port chunk allocations"
    ::= { affirmedIpProtocolsNatGuaranteedSubPoolStatsEntry 7 }

affirmedIpProtocolsNatGuaranteedSubPoolStatsPortChunkAllocFailure OBJECT-TYPE
    SYNTAX      ConfdString
    MAX-ACCESS  read-only
    STATUS      deprecated
    DESCRIPTION "Number of port chunk allocation failures"
    ::= { affirmedIpProtocolsNatGuaranteedSubPoolStatsEntry 8 }

affirmedIpProtocolsNatGuaranteedSubPoolStatsPortChunkDealloc OBJECT-TYPE
    SYNTAX      ConfdString
    MAX-ACCESS  read-only
    STATUS      deprecated
    DESCRIPTION "Number of port chunk resources deallocated"
    ::= { affirmedIpProtocolsNatGuaranteedSubPoolStatsEntry 9 }

affirmedIpProtocolsNatGuaranteedSubPoolStatsSessionCount OBJECT-TYPE
    SYNTAX      ConfdString
    MAX-ACCESS  read-only
    STATUS      deprecated
    DESCRIPTION "Number of sessions currently using the NAT resources"
    ::= { affirmedIpProtocolsNatGuaranteedSubPoolStatsEntry 10 }

affirmedIpProtocolsNatGuaranteedSubPoolStatsSessionCapacityAvail OBJECT-TYPE
    SYNTAX      ConfdString
    MAX-ACCESS  read-only
    STATUS      deprecated
    DESCRIPTION "Number of additional sessions possible"
    ::= { affirmedIpProtocolsNatGuaranteedSubPoolStatsEntry 11 }

affirmedIpProtocolsNatGuaranteedSubPoolStatsSessionUtil OBJECT-TYPE
    SYNTAX      ConfdString
    MAX-ACCESS  read-only
    STATUS      deprecated
    DESCRIPTION "Percentage utilization of the NAT resources based on current session count"
    ::= { affirmedIpProtocolsNatGuaranteedSubPoolStatsEntry 12 }

affirmedIpProtocolsNatGuaranteedSubPoolStatsPortChunksInUse OBJECT-TYPE
    SYNTAX      ConfdString
    MAX-ACCESS  read-only
    STATUS      deprecated
    DESCRIPTION "Number of port chunks currently allocated"
    ::= { affirmedIpProtocolsNatGuaranteedSubPoolStatsEntry 13 }

affirmedIpProtocolsNatGuaranteedSubPoolStatsPortChunkUtil OBJECT-TYPE
    SYNTAX      ConfdString
    MAX-ACCESS  read-only
    STATUS      deprecated
    DESCRIPTION "Percentage utilization of the port chunk resources"
    ::= { affirmedIpProtocolsNatGuaranteedSubPoolStatsEntry 14 }

affirmedIpProtocolsNatDeterministicNatPoolStatsTable OBJECT-TYPE
    SYNTAX      SEQUENCE OF AffirmedIpProtocolsNatDeterministicNatPoolStatsEntry
    MAX-ACCESS  not-accessible
    STATUS      deprecated
    DESCRIPTION ""
    ::= { affirmedIpProtocolsNatDeterministic 1 }

affirmedIpProtocolsNatDeterministicNatPoolStatsEntry OBJECT-TYPE
    SYNTAX      AffirmedIpProtocolsNatDeterministicNatPoolStatsEntry
    MAX-ACCESS  not-accessible
    STATUS      deprecated
    DESCRIPTION ""
    INDEX { affirmedIpProtocolsNatDeterministicNatPoolStatsNetworkContext, affirmedIpProtocolsNatDeterministicNatPoolStatsPoolName }
        ::= { affirmedIpProtocolsNatDeterministicNatPoolStatsTable 1 }

AffirmedIpProtocolsNatDeterministicNatPoolStatsEntry ::=
    SEQUENCE {
        affirmedIpProtocolsNatDeterministicNatPoolStatsNetworkContext String,
        affirmedIpProtocolsNatDeterministicNatPoolStatsPoolName String,
        affirmedIpProtocolsNatDeterministicNatPoolStatsCreateSessionSuccess ConfdString,
        affirmedIpProtocolsNatDeterministicNatPoolStatsCreateSessionFailure ConfdString,
        affirmedIpProtocolsNatDeterministicNatPoolStatsDeleteSessionCount ConfdString,
        affirmedIpProtocolsNatDeterministicNatPoolStatsPortChunkAllocSuccess ConfdString,
        affirmedIpProtocolsNatDeterministicNatPoolStatsPortChunkAllocFailure ConfdString,
        affirmedIpProtocolsNatDeterministicNatPoolStatsPortChunkDealloc ConfdString,
        affirmedIpProtocolsNatDeterministicNatPoolStatsSessionCount ConfdString,
        affirmedIpProtocolsNatDeterministicNatPoolStatsSessionCapacityAvail ConfdString,
        affirmedIpProtocolsNatDeterministicNatPoolStatsSessionUtil ConfdString,
        affirmedIpProtocolsNatDeterministicNatPoolStatsPortChunksInUse ConfdString,
        affirmedIpProtocolsNatDeterministicNatPoolStatsPortChunkUtil ConfdString
    }

affirmedIpProtocolsNatDeterministicNatPoolStatsNetworkContext OBJECT-TYPE
    SYNTAX      String
    MAX-ACCESS  not-accessible
    STATUS      current
    DESCRIPTION ""
    ::= { affirmedIpProtocolsNatDeterministicNatPoolStatsEntry 1 }

affirmedIpProtocolsNatDeterministicNatPoolStatsPoolName OBJECT-TYPE
    SYNTAX      String
    MAX-ACCESS  not-accessible
    STATUS      current
    DESCRIPTION ""
    ::= { affirmedIpProtocolsNatDeterministicNatPoolStatsEntry 2 }

affirmedIpProtocolsNatDeterministicNatPoolStatsCreateSessionSuccess OBJECT-TYPE
    SYNTAX      ConfdString
    MAX-ACCESS  read-only
    STATUS      deprecated
    DESCRIPTION "Number of successful session creation requests with NAT resources"
    ::= { affirmedIpProtocolsNatDeterministicNatPoolStatsEntry 3 }

affirmedIpProtocolsNatDeterministicNatPoolStatsCreateSessionFailure OBJECT-TYPE
    SYNTAX      ConfdString
    MAX-ACCESS  read-only
    STATUS      deprecated
    DESCRIPTION "Number of failed session creation requests with NAT resources"
    ::= { affirmedIpProtocolsNatDeterministicNatPoolStatsEntry 4 }

affirmedIpProtocolsNatDeterministicNatPoolStatsDeleteSessionCount OBJECT-TYPE
    SYNTAX      ConfdString
    MAX-ACCESS  read-only
    STATUS      deprecated
    DESCRIPTION "Number of session delete requests processed"
    ::= { affirmedIpProtocolsNatDeterministicNatPoolStatsEntry 5 }

affirmedIpProtocolsNatDeterministicNatPoolStatsPortChunkAllocSuccess OBJECT-TYPE
    SYNTAX      ConfdString
    MAX-ACCESS  read-only
    STATUS      deprecated
    DESCRIPTION "Number of successful port chunk allocations"
    ::= { affirmedIpProtocolsNatDeterministicNatPoolStatsEntry 6 }

affirmedIpProtocolsNatDeterministicNatPoolStatsPortChunkAllocFailure OBJECT-TYPE
    SYNTAX      ConfdString
    MAX-ACCESS  read-only
    STATUS      deprecated
    DESCRIPTION "Number of port chunk allocation failures"
    ::= { affirmedIpProtocolsNatDeterministicNatPoolStatsEntry 7 }

affirmedIpProtocolsNatDeterministicNatPoolStatsPortChunkDealloc OBJECT-TYPE
    SYNTAX      ConfdString
    MAX-ACCESS  read-only
    STATUS      deprecated
    DESCRIPTION "Number of port chunk resources deallocated"
    ::= { affirmedIpProtocolsNatDeterministicNatPoolStatsEntry 8 }

affirmedIpProtocolsNatDeterministicNatPoolStatsSessionCount OBJECT-TYPE
    SYNTAX      ConfdString
    MAX-ACCESS  read-only
    STATUS      deprecated
    DESCRIPTION "Number of sessions currently using the NAT resources"
    ::= { affirmedIpProtocolsNatDeterministicNatPoolStatsEntry 9 }

affirmedIpProtocolsNatDeterministicNatPoolStatsSessionCapacityAvail OBJECT-TYPE
    SYNTAX      ConfdString
    MAX-ACCESS  read-only
    STATUS      deprecated
    DESCRIPTION "Number of additional sessions possible"
    ::= { affirmedIpProtocolsNatDeterministicNatPoolStatsEntry 10 }

affirmedIpProtocolsNatDeterministicNatPoolStatsSessionUtil OBJECT-TYPE
    SYNTAX      ConfdString
    MAX-ACCESS  read-only
    STATUS      deprecated
    DESCRIPTION "Percentage utilization of the NAT resources based on current session count"
    ::= { affirmedIpProtocolsNatDeterministicNatPoolStatsEntry 11 }

affirmedIpProtocolsNatDeterministicNatPoolStatsPortChunksInUse OBJECT-TYPE
    SYNTAX      ConfdString
    MAX-ACCESS  read-only
    STATUS      deprecated
    DESCRIPTION "Number of port chunks currently allocated"
    ::= { affirmedIpProtocolsNatDeterministicNatPoolStatsEntry 12 }

affirmedIpProtocolsNatDeterministicNatPoolStatsPortChunkUtil OBJECT-TYPE
    SYNTAX      ConfdString
    MAX-ACCESS  read-only
    STATUS      deprecated
    DESCRIPTION "Percentage utilization of the port chunk resources"
    ::= { affirmedIpProtocolsNatDeterministicNatPoolStatsEntry 13 }

affirmedIpProtocolsNatDeterministicSubPoolStatsTable OBJECT-TYPE
    SYNTAX      SEQUENCE OF AffirmedIpProtocolsNatDeterministicSubPoolStatsEntry
    MAX-ACCESS  not-accessible
    STATUS      deprecated
    DESCRIPTION ""
    ::= { affirmedIpProtocolsNatDeterministic 2 }

affirmedIpProtocolsNatDeterministicSubPoolStatsEntry OBJECT-TYPE
    SYNTAX      AffirmedIpProtocolsNatDeterministicSubPoolStatsEntry
    MAX-ACCESS  not-accessible
    STATUS      deprecated
    DESCRIPTION ""
    INDEX { affirmedIpProtocolsNatDeterministicSubPoolStatsNetworkContext, affirmedIpProtocolsNatDeterministicSubPoolStatsPoolName, affirmedIpProtocolsNatDeterministicSubPoolStatsSubPoolName }
        ::= { affirmedIpProtocolsNatDeterministicSubPoolStatsTable 1 }

AffirmedIpProtocolsNatDeterministicSubPoolStatsEntry ::=
    SEQUENCE {
        affirmedIpProtocolsNatDeterministicSubPoolStatsNetworkContext String,
        affirmedIpProtocolsNatDeterministicSubPoolStatsPoolName String,
        affirmedIpProtocolsNatDeterministicSubPoolStatsSubPoolName String,
        affirmedIpProtocolsNatDeterministicSubPoolStatsCreateSessionSuccess ConfdString,
        affirmedIpProtocolsNatDeterministicSubPoolStatsCreateSessionFailure ConfdString,
        affirmedIpProtocolsNatDeterministicSubPoolStatsDeleteSessionCount ConfdString,
        affirmedIpProtocolsNatDeterministicSubPoolStatsPortChunkAllocSuccess ConfdString,
        affirmedIpProtocolsNatDeterministicSubPoolStatsPortChunkAllocFailure ConfdString,
        affirmedIpProtocolsNatDeterministicSubPoolStatsPortChunkDealloc ConfdString,
        affirmedIpProtocolsNatDeterministicSubPoolStatsSessionCount ConfdString,
        affirmedIpProtocolsNatDeterministicSubPoolStatsSessionCapacityAvail ConfdString,
        affirmedIpProtocolsNatDeterministicSubPoolStatsSessionUtil ConfdString,
        affirmedIpProtocolsNatDeterministicSubPoolStatsPortChunksInUse ConfdString,
        affirmedIpProtocolsNatDeterministicSubPoolStatsPortChunkUtil ConfdString
    }

affirmedIpProtocolsNatDeterministicSubPoolStatsNetworkContext OBJECT-TYPE
    SYNTAX      String
    MAX-ACCESS  not-accessible
    STATUS      current
    DESCRIPTION ""
    ::= { affirmedIpProtocolsNatDeterministicSubPoolStatsEntry 1 }

affirmedIpProtocolsNatDeterministicSubPoolStatsPoolName OBJECT-TYPE
    SYNTAX      String
    MAX-ACCESS  not-accessible
    STATUS      current
    DESCRIPTION ""
    ::= { affirmedIpProtocolsNatDeterministicSubPoolStatsEntry 2 }

affirmedIpProtocolsNatDeterministicSubPoolStatsSubPoolName OBJECT-TYPE
    SYNTAX      String
    MAX-ACCESS  not-accessible
    STATUS      current
    DESCRIPTION ""
    ::= { affirmedIpProtocolsNatDeterministicSubPoolStatsEntry 3 }

affirmedIpProtocolsNatDeterministicSubPoolStatsCreateSessionSuccess OBJECT-TYPE
    SYNTAX      ConfdString
    MAX-ACCESS  read-only
    STATUS      deprecated
    DESCRIPTION "Number of successful session creation requests with NAT resources"
    ::= { affirmedIpProtocolsNatDeterministicSubPoolStatsEntry 4 }

affirmedIpProtocolsNatDeterministicSubPoolStatsCreateSessionFailure OBJECT-TYPE
    SYNTAX      ConfdString
    MAX-ACCESS  read-only
    STATUS      deprecated
    DESCRIPTION "Number of failed session creation requests with NAT resources"
    ::= { affirmedIpProtocolsNatDeterministicSubPoolStatsEntry 5 }

affirmedIpProtocolsNatDeterministicSubPoolStatsDeleteSessionCount OBJECT-TYPE
    SYNTAX      ConfdString
    MAX-ACCESS  read-only
    STATUS      deprecated
    DESCRIPTION "Number of session delete requests processed"
    ::= { affirmedIpProtocolsNatDeterministicSubPoolStatsEntry 6 }

affirmedIpProtocolsNatDeterministicSubPoolStatsPortChunkAllocSuccess OBJECT-TYPE
    SYNTAX      ConfdString
    MAX-ACCESS  read-only
    STATUS      deprecated
    DESCRIPTION "Number of successful port chunk allocations"
    ::= { affirmedIpProtocolsNatDeterministicSubPoolStatsEntry 7 }

affirmedIpProtocolsNatDeterministicSubPoolStatsPortChunkAllocFailure OBJECT-TYPE
    SYNTAX      ConfdString
    MAX-ACCESS  read-only
    STATUS      deprecated
    DESCRIPTION "Number of port chunk allocation failures"
    ::= { affirmedIpProtocolsNatDeterministicSubPoolStatsEntry 8 }

affirmedIpProtocolsNatDeterministicSubPoolStatsPortChunkDealloc OBJECT-TYPE
    SYNTAX      ConfdString
    MAX-ACCESS  read-only
    STATUS      deprecated
    DESCRIPTION "Number of port chunk resources deallocated"
    ::= { affirmedIpProtocolsNatDeterministicSubPoolStatsEntry 9 }

affirmedIpProtocolsNatDeterministicSubPoolStatsSessionCount OBJECT-TYPE
    SYNTAX      ConfdString
    MAX-ACCESS  read-only
    STATUS      deprecated
    DESCRIPTION "Number of sessions currently using the NAT resources"
    ::= { affirmedIpProtocolsNatDeterministicSubPoolStatsEntry 10 }

affirmedIpProtocolsNatDeterministicSubPoolStatsSessionCapacityAvail OBJECT-TYPE
    SYNTAX      ConfdString
    MAX-ACCESS  read-only
    STATUS      deprecated
    DESCRIPTION "Number of additional sessions possible"
    ::= { affirmedIpProtocolsNatDeterministicSubPoolStatsEntry 11 }

affirmedIpProtocolsNatDeterministicSubPoolStatsSessionUtil OBJECT-TYPE
    SYNTAX      ConfdString
    MAX-ACCESS  read-only
    STATUS      deprecated
    DESCRIPTION "Percentage utilization of the NAT resources based on current session count"
    ::= { affirmedIpProtocolsNatDeterministicSubPoolStatsEntry 12 }

affirmedIpProtocolsNatDeterministicSubPoolStatsPortChunksInUse OBJECT-TYPE
    SYNTAX      ConfdString
    MAX-ACCESS  read-only
    STATUS      deprecated
    DESCRIPTION "Number of port chunks currently allocated"
    ::= { affirmedIpProtocolsNatDeterministicSubPoolStatsEntry 13 }

affirmedIpProtocolsNatDeterministicSubPoolStatsPortChunkUtil OBJECT-TYPE
    SYNTAX      ConfdString
    MAX-ACCESS  read-only
    STATUS      deprecated
    DESCRIPTION "Percentage utilization of the port chunk resources"
    ::= { affirmedIpProtocolsNatDeterministicSubPoolStatsEntry 14 }

affirmedIpProtocolsNatDeterministicNatIpTable OBJECT-TYPE
    SYNTAX      SEQUENCE OF AffirmedIpProtocolsNatDeterministicNatIpEntry
    MAX-ACCESS  not-accessible
    STATUS      deprecated
    DESCRIPTION ""
    ::= { affirmedIpProtocolsNatDeterministic 3 }

affirmedIpProtocolsNatDeterministicNatIpEntry OBJECT-TYPE
    SYNTAX      AffirmedIpProtocolsNatDeterministicNatIpEntry
    MAX-ACCESS  not-accessible
    STATUS      deprecated
    DESCRIPTION ""
    INDEX { affirmedIpProtocolsNatDeterministicNatIpNcName, affirmedIpProtocolsNatDeterministicNatIpUeIp }
        ::= { affirmedIpProtocolsNatDeterministicNatIpTable 1 }

AffirmedIpProtocolsNatDeterministicNatIpEntry ::=
    SEQUENCE {
        affirmedIpProtocolsNatDeterministicNatIpNcName String,
        affirmedIpProtocolsNatDeterministicNatIpUeIp String,
        affirmedIpProtocolsNatDeterministicNatIpSummary String
    }

affirmedIpProtocolsNatDeterministicNatIpNcName OBJECT-TYPE
    SYNTAX      String
    MAX-ACCESS  not-accessible
    STATUS      current
    DESCRIPTION "Provide network context name"
    ::= { affirmedIpProtocolsNatDeterministicNatIpEntry 1 }

affirmedIpProtocolsNatDeterministicNatIpUeIp OBJECT-TYPE
    SYNTAX      String
    MAX-ACCESS  not-accessible
    STATUS      current
    DESCRIPTION ""
    ::= { affirmedIpProtocolsNatDeterministicNatIpEntry 2 }

affirmedIpProtocolsNatDeterministicNatIpSummary OBJECT-TYPE
    SYNTAX      String
    MAX-ACCESS  read-only
    STATUS      current
    DESCRIPTION ""
    ::= { affirmedIpProtocolsNatDeterministicNatIpEntry 3 }

affirmedIpProtocolsNatDeterministicUeIpTable OBJECT-TYPE
    SYNTAX      SEQUENCE OF AffirmedIpProtocolsNatDeterministicUeIpEntry
    MAX-ACCESS  not-accessible
    STATUS      deprecated
    DESCRIPTION ""
    ::= { affirmedIpProtocolsNatDeterministic 4 }

affirmedIpProtocolsNatDeterministicUeIpEntry OBJECT-TYPE
    SYNTAX      AffirmedIpProtocolsNatDeterministicUeIpEntry
    MAX-ACCESS  not-accessible
    STATUS      deprecated
    DESCRIPTION ""
    INDEX { affirmedIpProtocolsNatDeterministicUeIpNcName, affirmedIpProtocolsNatDeterministicUeIpNatIp, affirmedIpProtocolsNatDeterministicUeIpNatPort }
        ::= { affirmedIpProtocolsNatDeterministicUeIpTable 1 }

AffirmedIpProtocolsNatDeterministicUeIpEntry ::=
    SEQUENCE {
        affirmedIpProtocolsNatDeterministicUeIpNcName String,
        affirmedIpProtocolsNatDeterministicUeIpNatIp String,
        affirmedIpProtocolsNatDeterministicUeIpNatPort Unsigned32,
        affirmedIpProtocolsNatDeterministicUeIpSummary String
    }

affirmedIpProtocolsNatDeterministicUeIpNcName OBJECT-TYPE
    SYNTAX      String
    MAX-ACCESS  not-accessible
    STATUS      current
    DESCRIPTION ""
    ::= { affirmedIpProtocolsNatDeterministicUeIpEntry 1 }

affirmedIpProtocolsNatDeterministicUeIpNatIp OBJECT-TYPE
    SYNTAX      String
    MAX-ACCESS  not-accessible
    STATUS      current
    DESCRIPTION ""
    ::= { affirmedIpProtocolsNatDeterministicUeIpEntry 2 }

affirmedIpProtocolsNatDeterministicUeIpNatPort OBJECT-TYPE
    SYNTAX      Unsigned32
    MAX-ACCESS  not-accessible
    STATUS      current
    DESCRIPTION ""
    ::= { affirmedIpProtocolsNatDeterministicUeIpEntry 3 }

affirmedIpProtocolsNatDeterministicUeIpSummary OBJECT-TYPE
    SYNTAX      String
    MAX-ACCESS  read-only
    STATUS      current
    DESCRIPTION ""
    ::= { affirmedIpProtocolsNatDeterministicUeIpEntry 4 }

affirmedIpProtocolsIpTcpStatisticsClusterLevelSummaryTable OBJECT-TYPE
    SYNTAX      SEQUENCE OF AffirmedIpProtocolsIpTcpStatisticsClusterLevelSummaryEntry
    MAX-ACCESS  not-accessible
    STATUS      current
    DESCRIPTION ""
    ::= { affirmedIpProtocolsIpTcpStatisticsClusterLevel 1 }

affirmedIpProtocolsIpTcpStatisticsClusterLevelSummaryEntry OBJECT-TYPE
    SYNTAX      AffirmedIpProtocolsIpTcpStatisticsClusterLevelSummaryEntry
    MAX-ACCESS  not-accessible
    STATUS      current
    DESCRIPTION ""
    INDEX { affirmedIpProtocolsIpTcpStatisticsClusterLevelSummaryChassis }
        ::= { affirmedIpProtocolsIpTcpStatisticsClusterLevelSummaryTable 1 }

AffirmedIpProtocolsIpTcpStatisticsClusterLevelSummaryEntry ::=
    SEQUENCE {
        affirmedIpProtocolsIpTcpStatisticsClusterLevelSummaryChassis Unsigned32,
        affirmedIpProtocolsIpTcpStatisticsClusterLevelSummaryNumtcpsocketinuse ConfdString,
        affirmedIpProtocolsIpTcpStatisticsClusterLevelSummaryNumtcpsocketorphan ConfdString,
        affirmedIpProtocolsIpTcpStatisticsClusterLevelSummaryNumtcpsocketest ConfdString,
        affirmedIpProtocolsIpTcpStatisticsClusterLevelSummaryNumtcpsockettw ConfdString,
        affirmedIpProtocolsIpTcpStatisticsClusterLevelSummaryTcpmemcurinuse ConfdString,
        affirmedIpProtocolsIpTcpStatisticsClusterLevelSummaryTcpmempeakinuse ConfdString,
        affirmedIpProtocolsIpTcpStatisticsClusterLevelSummaryNumsynccookies ConfdString,
        affirmedIpProtocolsIpTcpStatisticsClusterLevelSummaryTcpmemlow ConfdString,
        affirmedIpProtocolsIpTcpStatisticsClusterLevelSummaryTcpmempressure ConfdString,
        affirmedIpProtocolsIpTcpStatisticsClusterLevelSummaryTcpmemhigh ConfdString,
        affirmedIpProtocolsIpTcpStatisticsClusterLevelSummaryNumlistenoverflows ConfdString,
        affirmedIpProtocolsIpTcpStatisticsClusterLevelSummaryNumlistendrops ConfdString,
        affirmedIpProtocolsIpTcpStatisticsClusterLevelSummaryNumactiveconnectionopenings ConfdString,
        affirmedIpProtocolsIpTcpStatisticsClusterLevelSummaryNumpassiveconnectionopenings ConfdString,
        affirmedIpProtocolsIpTcpStatisticsClusterLevelSummaryNumfailedconnectionattempts ConfdString,
        affirmedIpProtocolsIpTcpStatisticsClusterLevelSummaryNumresetsreceivedforembryonicsynrecvsockets ConfdString
    }

affirmedIpProtocolsIpTcpStatisticsClusterLevelSummaryChassis OBJECT-TYPE
    SYNTAX      Unsigned32
    MAX-ACCESS  not-accessible
    STATUS      current
    DESCRIPTION "cluster ID"
    ::= { affirmedIpProtocolsIpTcpStatisticsClusterLevelSummaryEntry 1 }

affirmedIpProtocolsIpTcpStatisticsClusterLevelSummaryNumtcpsocketinuse OBJECT-TYPE
    SYNTAX      ConfdString
    MAX-ACCESS  read-only
    STATUS      current
    DESCRIPTION "Number of TCP sockets in use"
    ::= { affirmedIpProtocolsIpTcpStatisticsClusterLevelSummaryEntry 2 }

affirmedIpProtocolsIpTcpStatisticsClusterLevelSummaryNumtcpsocketorphan OBJECT-TYPE
    SYNTAX      ConfdString
    MAX-ACCESS  read-only
    STATUS      current
    DESCRIPTION "Number of orphan TCP sockets"
    ::= { affirmedIpProtocolsIpTcpStatisticsClusterLevelSummaryEntry 3 }

affirmedIpProtocolsIpTcpStatisticsClusterLevelSummaryNumtcpsocketest OBJECT-TYPE
    SYNTAX      ConfdString
    MAX-ACCESS  read-only
    STATUS      current
    DESCRIPTION "Number of TCP sockets established"
    ::= { affirmedIpProtocolsIpTcpStatisticsClusterLevelSummaryEntry 4 }

affirmedIpProtocolsIpTcpStatisticsClusterLevelSummaryNumtcpsockettw OBJECT-TYPE
    SYNTAX      ConfdString
    MAX-ACCESS  read-only
    STATUS      current
    DESCRIPTION "Number of Time Wait TCP sockets"
    ::= { affirmedIpProtocolsIpTcpStatisticsClusterLevelSummaryEntry 5 }

affirmedIpProtocolsIpTcpStatisticsClusterLevelSummaryTcpmemcurinuse OBJECT-TYPE
    SYNTAX      ConfdString
    MAX-ACCESS  read-only
    STATUS      current
    DESCRIPTION "TCP memory currently in use(KB)"
    ::= { affirmedIpProtocolsIpTcpStatisticsClusterLevelSummaryEntry 6 }

affirmedIpProtocolsIpTcpStatisticsClusterLevelSummaryTcpmempeakinuse OBJECT-TYPE
    SYNTAX      ConfdString
    MAX-ACCESS  read-only
    STATUS      current
    DESCRIPTION "TCP memory peak in use(KB)"
    ::= { affirmedIpProtocolsIpTcpStatisticsClusterLevelSummaryEntry 7 }

affirmedIpProtocolsIpTcpStatisticsClusterLevelSummaryNumsynccookies OBJECT-TYPE
    SYNTAX      ConfdString
    MAX-ACCESS  read-only
    STATUS      current
    DESCRIPTION "Tcp event num of sent syn-cookies"
    ::= { affirmedIpProtocolsIpTcpStatisticsClusterLevelSummaryEntry 8 }

affirmedIpProtocolsIpTcpStatisticsClusterLevelSummaryTcpmemlow OBJECT-TYPE
    SYNTAX      ConfdString
    MAX-ACCESS  read-only
    STATUS      current
    DESCRIPTION "TCP memory low threshold(KB)"
    ::= { affirmedIpProtocolsIpTcpStatisticsClusterLevelSummaryEntry 9 }

affirmedIpProtocolsIpTcpStatisticsClusterLevelSummaryTcpmempressure OBJECT-TYPE
    SYNTAX      ConfdString
    MAX-ACCESS  read-only
    STATUS      current
    DESCRIPTION "TCP memory pressure threshold(KB)"
    ::= { affirmedIpProtocolsIpTcpStatisticsClusterLevelSummaryEntry 10 }

affirmedIpProtocolsIpTcpStatisticsClusterLevelSummaryTcpmemhigh OBJECT-TYPE
    SYNTAX      ConfdString
    MAX-ACCESS  read-only
    STATUS      current
    DESCRIPTION "TCP memory high threshold(KB)"
    ::= { affirmedIpProtocolsIpTcpStatisticsClusterLevelSummaryEntry 11 }

affirmedIpProtocolsIpTcpStatisticsClusterLevelSummaryNumlistenoverflows OBJECT-TYPE
    SYNTAX      ConfdString
    MAX-ACCESS  read-only
    STATUS      current
    DESCRIPTION "TCP event num listen socket overflows"
    ::= { affirmedIpProtocolsIpTcpStatisticsClusterLevelSummaryEntry 12 }

affirmedIpProtocolsIpTcpStatisticsClusterLevelSummaryNumlistendrops OBJECT-TYPE
    SYNTAX      ConfdString
    MAX-ACCESS  read-only
    STATUS      current
    DESCRIPTION "TCP event num listen socket drops"
    ::= { affirmedIpProtocolsIpTcpStatisticsClusterLevelSummaryEntry 13 }

affirmedIpProtocolsIpTcpStatisticsClusterLevelSummaryNumactiveconnectionopenings OBJECT-TYPE
    SYNTAX      ConfdString
    MAX-ACCESS  read-only
    STATUS      current
    DESCRIPTION "TCP event active socket connection openings"
    ::= { affirmedIpProtocolsIpTcpStatisticsClusterLevelSummaryEntry 14 }

affirmedIpProtocolsIpTcpStatisticsClusterLevelSummaryNumpassiveconnectionopenings OBJECT-TYPE
    SYNTAX      ConfdString
    MAX-ACCESS  read-only
    STATUS      current
    DESCRIPTION "TCP event passive socket connection openings"
    ::= { affirmedIpProtocolsIpTcpStatisticsClusterLevelSummaryEntry 15 }

affirmedIpProtocolsIpTcpStatisticsClusterLevelSummaryNumfailedconnectionattempts OBJECT-TYPE
    SYNTAX      ConfdString
    MAX-ACCESS  read-only
    STATUS      current
    DESCRIPTION "TCP event failed socket connection attempts"
    ::= { affirmedIpProtocolsIpTcpStatisticsClusterLevelSummaryEntry 16 }

affirmedIpProtocolsIpTcpStatisticsClusterLevelSummaryNumresetsreceivedforembryonicsynrecvsockets OBJECT-TYPE
    SYNTAX      ConfdString
    MAX-ACCESS  read-only
    STATUS      current
    DESCRIPTION "TCP event resets received for embryonic SYN_RECV sockets"
    ::= { affirmedIpProtocolsIpTcpStatisticsClusterLevelSummaryEntry 17 }

affirmedIpProtocolsIpTcpStatisticsNodeLevelSummaryTable OBJECT-TYPE
    SYNTAX      SEQUENCE OF AffirmedIpProtocolsIpTcpStatisticsNodeLevelSummaryEntry
    MAX-ACCESS  not-accessible
    STATUS      current
    DESCRIPTION ""
    ::= { affirmedIpProtocolsIpTcpStatisticsNodeLevel 1 }

affirmedIpProtocolsIpTcpStatisticsNodeLevelSummaryEntry OBJECT-TYPE
    SYNTAX      AffirmedIpProtocolsIpTcpStatisticsNodeLevelSummaryEntry
    MAX-ACCESS  not-accessible
    STATUS      current
    DESCRIPTION ""
    INDEX { affirmedIpProtocolsIpTcpStatisticsNodeLevelSummaryChassis, affirmedIpProtocolsIpTcpStatisticsNodeLevelSummarySlot }
        ::= { affirmedIpProtocolsIpTcpStatisticsNodeLevelSummaryTable 1 }

AffirmedIpProtocolsIpTcpStatisticsNodeLevelSummaryEntry ::=
    SEQUENCE {
        affirmedIpProtocolsIpTcpStatisticsNodeLevelSummaryChassis Unsigned32,
        affirmedIpProtocolsIpTcpStatisticsNodeLevelSummarySlot INTEGER,
        affirmedIpProtocolsIpTcpStatisticsNodeLevelSummaryNumtcpsocketinuse ConfdString,
        affirmedIpProtocolsIpTcpStatisticsNodeLevelSummaryNumtcpsocketorphan ConfdString,
        affirmedIpProtocolsIpTcpStatisticsNodeLevelSummaryNumtcpsocketest ConfdString,
        affirmedIpProtocolsIpTcpStatisticsNodeLevelSummaryNumtcpsockettw ConfdString,
        affirmedIpProtocolsIpTcpStatisticsNodeLevelSummaryTcpmemcurinuse ConfdString,
        affirmedIpProtocolsIpTcpStatisticsNodeLevelSummaryTcpmempeakinuse ConfdString,
        affirmedIpProtocolsIpTcpStatisticsNodeLevelSummaryNumsynccookies ConfdString,
        affirmedIpProtocolsIpTcpStatisticsNodeLevelSummaryTcpmemlow ConfdString,
        affirmedIpProtocolsIpTcpStatisticsNodeLevelSummaryTcpmempressure ConfdString,
        affirmedIpProtocolsIpTcpStatisticsNodeLevelSummaryTcpmemhigh ConfdString,
        affirmedIpProtocolsIpTcpStatisticsNodeLevelSummaryNumlistenoverflows ConfdString,
        affirmedIpProtocolsIpTcpStatisticsNodeLevelSummaryNumlistendrops ConfdString,
        affirmedIpProtocolsIpTcpStatisticsNodeLevelSummaryNumactiveconnectionopenings ConfdString,
        affirmedIpProtocolsIpTcpStatisticsNodeLevelSummaryNumpassiveconnectionopenings ConfdString,
        affirmedIpProtocolsIpTcpStatisticsNodeLevelSummaryNumfailedconnectionattempts ConfdString,
        affirmedIpProtocolsIpTcpStatisticsNodeLevelSummaryNumresetsreceivedforembryonicsynrecvsockets ConfdString
    }

affirmedIpProtocolsIpTcpStatisticsNodeLevelSummaryChassis OBJECT-TYPE
    SYNTAX      Unsigned32
    MAX-ACCESS  not-accessible
    STATUS      current
    DESCRIPTION "cluster number"
    ::= { affirmedIpProtocolsIpTcpStatisticsNodeLevelSummaryEntry 1 }

affirmedIpProtocolsIpTcpStatisticsNodeLevelSummarySlot OBJECT-TYPE
    SYNTAX      INTEGER {a1(1),a2(2),a3(3),a4(4),a5(5),a6(6),a7(7),a8(8),a9(9),a10(10),a11(11),a12(12),a13(13),a14(14),a15(15),a16(16),a17(17),a18(18),a19(19),a20(20),a21(21),a22(22),a23(23),a24(24),a25(25),a26(26),a27(27),a28(28),a29(29),a30(30),a31(31),a32(32),a33(33),a34(34),a35(35),a36(36),a37(37),a38(38),a39(39),a40(40),a41(41),a42(42),a43(43),a44(44),a45(45),a46(46),a47(47),a48(48),a49(49),a50(50),a51(51),a52(52),a53(53),a54(54),a55(55),a56(56),a57(57),a58(58),a59(59),a60(60),a61(61),a62(62),a63(63),a64(64),a65(65),a66(66),a67(67),a68(68),a69(69),a70(70),a71(71),a72(72),a73(73),a74(74),a75(75),a76(76),a77(77),a78(78),a79(79),a80(80),a81(81),a82(82),a83(83),a84(84),a85(85),a86(86),a87(87),a88(88),a89(89),a90(90),a91(91),a92(92),a93(93),a94(94),a95(95),a96(96),a97(97),a98(98),a99(99),a100(100),a101(101),a102(102),a103(103),a104(104),a105(105),a106(106),a107(107),a108(108),a109(109),a110(110),a111(111),a112(112),a113(113),a114(114),a115(115),a116(116),a117(117),a118(118),a119(119),a120(120),a121(121),a122(122),a123(123),a124(124),a125(125),a126(126),a127(127),a128(128)}
    MAX-ACCESS  not-accessible
    STATUS      current
    DESCRIPTION "node number"
    ::= { affirmedIpProtocolsIpTcpStatisticsNodeLevelSummaryEntry 2 }

affirmedIpProtocolsIpTcpStatisticsNodeLevelSummaryNumtcpsocketinuse OBJECT-TYPE
    SYNTAX      ConfdString
    MAX-ACCESS  read-only
    STATUS      current
    DESCRIPTION "Number of TCP sockets in use"
    ::= { affirmedIpProtocolsIpTcpStatisticsNodeLevelSummaryEntry 3 }

affirmedIpProtocolsIpTcpStatisticsNodeLevelSummaryNumtcpsocketorphan OBJECT-TYPE
    SYNTAX      ConfdString
    MAX-ACCESS  read-only
    STATUS      current
    DESCRIPTION "Number of orphan TCP sockets"
    ::= { affirmedIpProtocolsIpTcpStatisticsNodeLevelSummaryEntry 4 }

affirmedIpProtocolsIpTcpStatisticsNodeLevelSummaryNumtcpsocketest OBJECT-TYPE
    SYNTAX      ConfdString
    MAX-ACCESS  read-only
    STATUS      current
    DESCRIPTION "Number of TCP sockets established"
    ::= { affirmedIpProtocolsIpTcpStatisticsNodeLevelSummaryEntry 5 }

affirmedIpProtocolsIpTcpStatisticsNodeLevelSummaryNumtcpsockettw OBJECT-TYPE
    SYNTAX      ConfdString
    MAX-ACCESS  read-only
    STATUS      current
    DESCRIPTION "Number of Time Wait TCP sockets"
    ::= { affirmedIpProtocolsIpTcpStatisticsNodeLevelSummaryEntry 6 }

affirmedIpProtocolsIpTcpStatisticsNodeLevelSummaryTcpmemcurinuse OBJECT-TYPE
    SYNTAX      ConfdString
    MAX-ACCESS  read-only
    STATUS      current
    DESCRIPTION "TCP memory currently in use(KB)"
    ::= { affirmedIpProtocolsIpTcpStatisticsNodeLevelSummaryEntry 7 }

affirmedIpProtocolsIpTcpStatisticsNodeLevelSummaryTcpmempeakinuse OBJECT-TYPE
    SYNTAX      ConfdString
    MAX-ACCESS  read-only
    STATUS      current
    DESCRIPTION "TCP memory peak in use(KB)"
    ::= { affirmedIpProtocolsIpTcpStatisticsNodeLevelSummaryEntry 8 }

affirmedIpProtocolsIpTcpStatisticsNodeLevelSummaryNumsynccookies OBJECT-TYPE
    SYNTAX      ConfdString
    MAX-ACCESS  read-only
    STATUS      current
    DESCRIPTION "Tcp event num of sent syn-cookies"
    ::= { affirmedIpProtocolsIpTcpStatisticsNodeLevelSummaryEntry 9 }

affirmedIpProtocolsIpTcpStatisticsNodeLevelSummaryTcpmemlow OBJECT-TYPE
    SYNTAX      ConfdString
    MAX-ACCESS  read-only
    STATUS      current
    DESCRIPTION "TCP memory low threshold(KB)"
    ::= { affirmedIpProtocolsIpTcpStatisticsNodeLevelSummaryEntry 10 }

affirmedIpProtocolsIpTcpStatisticsNodeLevelSummaryTcpmempressure OBJECT-TYPE
    SYNTAX      ConfdString
    MAX-ACCESS  read-only
    STATUS      current
    DESCRIPTION "TCP memory pressure threshold(KB)"
    ::= { affirmedIpProtocolsIpTcpStatisticsNodeLevelSummaryEntry 11 }

affirmedIpProtocolsIpTcpStatisticsNodeLevelSummaryTcpmemhigh OBJECT-TYPE
    SYNTAX      ConfdString
    MAX-ACCESS  read-only
    STATUS      current
    DESCRIPTION "TCP memory high threshold(KB)"
    ::= { affirmedIpProtocolsIpTcpStatisticsNodeLevelSummaryEntry 12 }

affirmedIpProtocolsIpTcpStatisticsNodeLevelSummaryNumlistenoverflows OBJECT-TYPE
    SYNTAX      ConfdString
    MAX-ACCESS  read-only
    STATUS      current
    DESCRIPTION "TCP event num listen socket overflows"
    ::= { affirmedIpProtocolsIpTcpStatisticsNodeLevelSummaryEntry 13 }

affirmedIpProtocolsIpTcpStatisticsNodeLevelSummaryNumlistendrops OBJECT-TYPE
    SYNTAX      ConfdString
    MAX-ACCESS  read-only
    STATUS      current
    DESCRIPTION "TCP event num listen socket drops"
    ::= { affirmedIpProtocolsIpTcpStatisticsNodeLevelSummaryEntry 14 }

affirmedIpProtocolsIpTcpStatisticsNodeLevelSummaryNumactiveconnectionopenings OBJECT-TYPE
    SYNTAX      ConfdString
    MAX-ACCESS  read-only
    STATUS      current
    DESCRIPTION "TCP event active socket connection openings"
    ::= { affirmedIpProtocolsIpTcpStatisticsNodeLevelSummaryEntry 15 }

affirmedIpProtocolsIpTcpStatisticsNodeLevelSummaryNumpassiveconnectionopenings OBJECT-TYPE
    SYNTAX      ConfdString
    MAX-ACCESS  read-only
    STATUS      current
    DESCRIPTION "TCP event passive socket connection openings"
    ::= { affirmedIpProtocolsIpTcpStatisticsNodeLevelSummaryEntry 16 }

affirmedIpProtocolsIpTcpStatisticsNodeLevelSummaryNumfailedconnectionattempts OBJECT-TYPE
    SYNTAX      ConfdString
    MAX-ACCESS  read-only
    STATUS      current
    DESCRIPTION "TCP event failed socket connection attempts"
    ::= { affirmedIpProtocolsIpTcpStatisticsNodeLevelSummaryEntry 17 }

affirmedIpProtocolsIpTcpStatisticsNodeLevelSummaryNumresetsreceivedforembryonicsynrecvsockets OBJECT-TYPE
    SYNTAX      ConfdString
    MAX-ACCESS  read-only
    STATUS      current
    DESCRIPTION "TCP event resets received for embryonic SYN_RECV sockets"
    ::= { affirmedIpProtocolsIpTcpStatisticsNodeLevelSummaryEntry 18 }

affirmedIpProtocolsOspfv2RouterTable OBJECT-TYPE
    SYNTAX      SEQUENCE OF AffirmedIpProtocolsOspfv2RouterEntry
    MAX-ACCESS  not-accessible
    STATUS      current
    DESCRIPTION ""
    ::= { affirmedIpProtocolsOspfv2 1 }

affirmedIpProtocolsOspfv2RouterEntry OBJECT-TYPE
    SYNTAX      AffirmedIpProtocolsOspfv2RouterEntry
    MAX-ACCESS  not-accessible
    STATUS      current
    DESCRIPTION ""
    INDEX { affirmedIpProtocolsOspfv2RouterNetworkContext }
        ::= { affirmedIpProtocolsOspfv2RouterTable 1 }

AffirmedIpProtocolsOspfv2RouterEntry ::=
    SEQUENCE {
        affirmedIpProtocolsOspfv2RouterNetworkContext String,
        affirmedIpProtocolsOspfv2RouterRowstatus RowStatus
    }

affirmedIpProtocolsOspfv2RouterNetworkContext OBJECT-TYPE
    SYNTAX      String
    MAX-ACCESS  not-accessible
    STATUS      current
    DESCRIPTION "network context for this OSPF router"
    ::= { affirmedIpProtocolsOspfv2RouterEntry 1 }

affirmedIpProtocolsOspfv2RouterRowstatus OBJECT-TYPE
    SYNTAX      RowStatus
    MAX-ACCESS  read-create
    STATUS      current
    DESCRIPTION ""
    ::= { affirmedIpProtocolsOspfv2RouterEntry 2 }

affirmedIpProtocolsOspfv2RouterShowDBRouterTable OBJECT-TYPE
    SYNTAX      SEQUENCE OF AffirmedIpProtocolsOspfv2RouterShowDBRouterEntry
    MAX-ACCESS  not-accessible
    STATUS      current
    DESCRIPTION ""
    ::= { affirmedIpProtocolsOspfv2 2 }

affirmedIpProtocolsOspfv2RouterShowDBRouterEntry OBJECT-TYPE
    SYNTAX      AffirmedIpProtocolsOspfv2RouterShowDBRouterEntry
    MAX-ACCESS  not-accessible
    STATUS      current
    DESCRIPTION ""
    INDEX { affirmedIpProtocolsOspfv2RouterNetworkContext, affirmedIpProtocolsOspfv2RouterShowDBRouterEntryId }
        ::= { affirmedIpProtocolsOspfv2RouterShowDBRouterTable 1 }

AffirmedIpProtocolsOspfv2RouterShowDBRouterEntry ::=
    SEQUENCE {
        affirmedIpProtocolsOspfv2RouterShowDBRouterEntryId INTEGER,
        affirmedIpProtocolsOspfv2RouterShowDBRouterOutput String
    }

affirmedIpProtocolsOspfv2RouterShowDBRouterEntryId OBJECT-TYPE
    SYNTAX      INTEGER {entry(0)}
    MAX-ACCESS  not-accessible
    STATUS      current
    DESCRIPTION ""
    ::= { affirmedIpProtocolsOspfv2RouterShowDBRouterEntry 1 }

affirmedIpProtocolsOspfv2RouterShowDBRouterOutput OBJECT-TYPE
    SYNTAX      String
    MAX-ACCESS  read-only
    STATUS      current
    DESCRIPTION ""
    ::= { affirmedIpProtocolsOspfv2RouterShowDBRouterEntry 2 }

affirmedIpProtocolsOspfv2RouterShowDBAsbrSummaryTable OBJECT-TYPE
    SYNTAX      SEQUENCE OF AffirmedIpProtocolsOspfv2RouterShowDBAsbrSummaryEntry
    MAX-ACCESS  not-accessible
    STATUS      current
    DESCRIPTION ""
    ::= { affirmedIpProtocolsOspfv2 3 }

affirmedIpProtocolsOspfv2RouterShowDBAsbrSummaryEntry OBJECT-TYPE
    SYNTAX      AffirmedIpProtocolsOspfv2RouterShowDBAsbrSummaryEntry
    MAX-ACCESS  not-accessible
    STATUS      current
    DESCRIPTION ""
    INDEX { affirmedIpProtocolsOspfv2RouterNetworkContext, affirmedIpProtocolsOspfv2RouterShowDBAsbrSummaryEntryId }
        ::= { affirmedIpProtocolsOspfv2RouterShowDBAsbrSummaryTable 1 }

AffirmedIpProtocolsOspfv2RouterShowDBAsbrSummaryEntry ::=
    SEQUENCE {
        affirmedIpProtocolsOspfv2RouterShowDBAsbrSummaryEntryId INTEGER,
        affirmedIpProtocolsOspfv2RouterShowDBAsbrSummaryOutput String
    }

affirmedIpProtocolsOspfv2RouterShowDBAsbrSummaryEntryId OBJECT-TYPE
    SYNTAX      INTEGER {entry(0)}
    MAX-ACCESS  not-accessible
    STATUS      current
    DESCRIPTION ""
    ::= { affirmedIpProtocolsOspfv2RouterShowDBAsbrSummaryEntry 1 }

affirmedIpProtocolsOspfv2RouterShowDBAsbrSummaryOutput OBJECT-TYPE
    SYNTAX      String
    MAX-ACCESS  read-only
    STATUS      current
    DESCRIPTION ""
    ::= { affirmedIpProtocolsOspfv2RouterShowDBAsbrSummaryEntry 2 }

affirmedIpProtocolsOspfv2RouterShowDBExternalTable OBJECT-TYPE
    SYNTAX      SEQUENCE OF AffirmedIpProtocolsOspfv2RouterShowDBExternalEntry
    MAX-ACCESS  not-accessible
    STATUS      current
    DESCRIPTION ""
    ::= { affirmedIpProtocolsOspfv2 4 }

affirmedIpProtocolsOspfv2RouterShowDBExternalEntry OBJECT-TYPE
    SYNTAX      AffirmedIpProtocolsOspfv2RouterShowDBExternalEntry
    MAX-ACCESS  not-accessible
    STATUS      current
    DESCRIPTION ""
    INDEX { affirmedIpProtocolsOspfv2RouterNetworkContext, affirmedIpProtocolsOspfv2RouterShowDBExternalEntryId }
        ::= { affirmedIpProtocolsOspfv2RouterShowDBExternalTable 1 }

AffirmedIpProtocolsOspfv2RouterShowDBExternalEntry ::=
    SEQUENCE {
        affirmedIpProtocolsOspfv2RouterShowDBExternalEntryId INTEGER,
        affirmedIpProtocolsOspfv2RouterShowDBExternalOutput String
    }

affirmedIpProtocolsOspfv2RouterShowDBExternalEntryId OBJECT-TYPE
    SYNTAX      INTEGER {entry(0)}
    MAX-ACCESS  not-accessible
    STATUS      current
    DESCRIPTION ""
    ::= { affirmedIpProtocolsOspfv2RouterShowDBExternalEntry 1 }

affirmedIpProtocolsOspfv2RouterShowDBExternalOutput OBJECT-TYPE
    SYNTAX      String
    MAX-ACCESS  read-only
    STATUS      current
    DESCRIPTION ""
    ::= { affirmedIpProtocolsOspfv2RouterShowDBExternalEntry 2 }

affirmedIpProtocolsOspfv2RouterShowDBNetworkTable OBJECT-TYPE
    SYNTAX      SEQUENCE OF AffirmedIpProtocolsOspfv2RouterShowDBNetworkEntry
    MAX-ACCESS  not-accessible
    STATUS      current
    DESCRIPTION ""
    ::= { affirmedIpProtocolsOspfv2 5 }

affirmedIpProtocolsOspfv2RouterShowDBNetworkEntry OBJECT-TYPE
    SYNTAX      AffirmedIpProtocolsOspfv2RouterShowDBNetworkEntry
    MAX-ACCESS  not-accessible
    STATUS      current
    DESCRIPTION ""
    INDEX { affirmedIpProtocolsOspfv2RouterNetworkContext, affirmedIpProtocolsOspfv2RouterShowDBNetworkEntryId }
        ::= { affirmedIpProtocolsOspfv2RouterShowDBNetworkTable 1 }

AffirmedIpProtocolsOspfv2RouterShowDBNetworkEntry ::=
    SEQUENCE {
        affirmedIpProtocolsOspfv2RouterShowDBNetworkEntryId INTEGER,
        affirmedIpProtocolsOspfv2RouterShowDBNetworkOutput String
    }

affirmedIpProtocolsOspfv2RouterShowDBNetworkEntryId OBJECT-TYPE
    SYNTAX      INTEGER {entry(0)}
    MAX-ACCESS  not-accessible
    STATUS      current
    DESCRIPTION ""
    ::= { affirmedIpProtocolsOspfv2RouterShowDBNetworkEntry 1 }

affirmedIpProtocolsOspfv2RouterShowDBNetworkOutput OBJECT-TYPE
    SYNTAX      String
    MAX-ACCESS  read-only
    STATUS      current
    DESCRIPTION ""
    ::= { affirmedIpProtocolsOspfv2RouterShowDBNetworkEntry 2 }

affirmedIpProtocolsOspfv2RouterShowDBNssaTable OBJECT-TYPE
    SYNTAX      SEQUENCE OF AffirmedIpProtocolsOspfv2RouterShowDBNssaEntry
    MAX-ACCESS  not-accessible
    STATUS      current
    DESCRIPTION ""
    ::= { affirmedIpProtocolsOspfv2 6 }

affirmedIpProtocolsOspfv2RouterShowDBNssaEntry OBJECT-TYPE
    SYNTAX      AffirmedIpProtocolsOspfv2RouterShowDBNssaEntry
    MAX-ACCESS  not-accessible
    STATUS      current
    DESCRIPTION ""
    INDEX { affirmedIpProtocolsOspfv2RouterNetworkContext, affirmedIpProtocolsOspfv2RouterShowDBNssaEntryId }
        ::= { affirmedIpProtocolsOspfv2RouterShowDBNssaTable 1 }

AffirmedIpProtocolsOspfv2RouterShowDBNssaEntry ::=
    SEQUENCE {
        affirmedIpProtocolsOspfv2RouterShowDBNssaEntryId INTEGER,
        affirmedIpProtocolsOspfv2RouterShowDBNssaOutput String
    }

affirmedIpProtocolsOspfv2RouterShowDBNssaEntryId OBJECT-TYPE
    SYNTAX      INTEGER {entry(0)}
    MAX-ACCESS  not-accessible
    STATUS      current
    DESCRIPTION ""
    ::= { affirmedIpProtocolsOspfv2RouterShowDBNssaEntry 1 }

affirmedIpProtocolsOspfv2RouterShowDBNssaOutput OBJECT-TYPE
    SYNTAX      String
    MAX-ACCESS  read-only
    STATUS      current
    DESCRIPTION ""
    ::= { affirmedIpProtocolsOspfv2RouterShowDBNssaEntry 2 }

affirmedIpProtocolsOspfv2RouterShowDBOpaqueAreaTable OBJECT-TYPE
    SYNTAX      SEQUENCE OF AffirmedIpProtocolsOspfv2RouterShowDBOpaqueAreaEntry
    MAX-ACCESS  not-accessible
    STATUS      current
    DESCRIPTION ""
    ::= { affirmedIpProtocolsOspfv2 7 }

affirmedIpProtocolsOspfv2RouterShowDBOpaqueAreaEntry OBJECT-TYPE
    SYNTAX      AffirmedIpProtocolsOspfv2RouterShowDBOpaqueAreaEntry
    MAX-ACCESS  not-accessible
    STATUS      current
    DESCRIPTION ""
    INDEX { affirmedIpProtocolsOspfv2RouterNetworkContext, affirmedIpProtocolsOspfv2RouterShowDBOpaqueAreaEntryId }
        ::= { affirmedIpProtocolsOspfv2RouterShowDBOpaqueAreaTable 1 }

AffirmedIpProtocolsOspfv2RouterShowDBOpaqueAreaEntry ::=
    SEQUENCE {
        affirmedIpProtocolsOspfv2RouterShowDBOpaqueAreaEntryId INTEGER,
        affirmedIpProtocolsOspfv2RouterShowDBOpaqueAreaOutput String
    }

affirmedIpProtocolsOspfv2RouterShowDBOpaqueAreaEntryId OBJECT-TYPE
    SYNTAX      INTEGER {entry(0)}
    MAX-ACCESS  not-accessible
    STATUS      current
    DESCRIPTION ""
    ::= { affirmedIpProtocolsOspfv2RouterShowDBOpaqueAreaEntry 1 }

affirmedIpProtocolsOspfv2RouterShowDBOpaqueAreaOutput OBJECT-TYPE
    SYNTAX      String
    MAX-ACCESS  read-only
    STATUS      current
    DESCRIPTION ""
    ::= { affirmedIpProtocolsOspfv2RouterShowDBOpaqueAreaEntry 2 }

affirmedIpProtocolsOspfv2RouterShowDBOpaqueAsTable OBJECT-TYPE
    SYNTAX      SEQUENCE OF AffirmedIpProtocolsOspfv2RouterShowDBOpaqueAsEntry
    MAX-ACCESS  not-accessible
    STATUS      current
    DESCRIPTION ""
    ::= { affirmedIpProtocolsOspfv2 8 }

affirmedIpProtocolsOspfv2RouterShowDBOpaqueAsEntry OBJECT-TYPE
    SYNTAX      AffirmedIpProtocolsOspfv2RouterShowDBOpaqueAsEntry
    MAX-ACCESS  not-accessible
    STATUS      current
    DESCRIPTION ""
    INDEX { affirmedIpProtocolsOspfv2RouterNetworkContext, affirmedIpProtocolsOspfv2RouterShowDBOpaqueAsEntryId }
        ::= { affirmedIpProtocolsOspfv2RouterShowDBOpaqueAsTable 1 }

AffirmedIpProtocolsOspfv2RouterShowDBOpaqueAsEntry ::=
    SEQUENCE {
        affirmedIpProtocolsOspfv2RouterShowDBOpaqueAsEntryId INTEGER,
        affirmedIpProtocolsOspfv2RouterShowDBOpaqueAsOutput String
    }

affirmedIpProtocolsOspfv2RouterShowDBOpaqueAsEntryId OBJECT-TYPE
    SYNTAX      INTEGER {entry(0)}
    MAX-ACCESS  not-accessible
    STATUS      current
    DESCRIPTION ""
    ::= { affirmedIpProtocolsOspfv2RouterShowDBOpaqueAsEntry 1 }

affirmedIpProtocolsOspfv2RouterShowDBOpaqueAsOutput OBJECT-TYPE
    SYNTAX      String
    MAX-ACCESS  read-only
    STATUS      current
    DESCRIPTION ""
    ::= { affirmedIpProtocolsOspfv2RouterShowDBOpaqueAsEntry 2 }

affirmedIpProtocolsOspfv2RouterShowDBOpaqueLinkTable OBJECT-TYPE
    SYNTAX      SEQUENCE OF AffirmedIpProtocolsOspfv2RouterShowDBOpaqueLinkEntry
    MAX-ACCESS  not-accessible
    STATUS      current
    DESCRIPTION ""
    ::= { affirmedIpProtocolsOspfv2 9 }

affirmedIpProtocolsOspfv2RouterShowDBOpaqueLinkEntry OBJECT-TYPE
    SYNTAX      AffirmedIpProtocolsOspfv2RouterShowDBOpaqueLinkEntry
    MAX-ACCESS  not-accessible
    STATUS      current
    DESCRIPTION ""
    INDEX { affirmedIpProtocolsOspfv2RouterNetworkContext, affirmedIpProtocolsOspfv2RouterShowDBOpaqueLinkEntryId }
        ::= { affirmedIpProtocolsOspfv2RouterShowDBOpaqueLinkTable 1 }

AffirmedIpProtocolsOspfv2RouterShowDBOpaqueLinkEntry ::=
    SEQUENCE {
        affirmedIpProtocolsOspfv2RouterShowDBOpaqueLinkEntryId INTEGER,
        affirmedIpProtocolsOspfv2RouterShowDBOpaqueLinkOutput String
    }

affirmedIpProtocolsOspfv2RouterShowDBOpaqueLinkEntryId OBJECT-TYPE
    SYNTAX      INTEGER {entry(0)}
    MAX-ACCESS  not-accessible
    STATUS      current
    DESCRIPTION ""
    ::= { affirmedIpProtocolsOspfv2RouterShowDBOpaqueLinkEntry 1 }

affirmedIpProtocolsOspfv2RouterShowDBOpaqueLinkOutput OBJECT-TYPE
    SYNTAX      String
    MAX-ACCESS  read-only
    STATUS      current
    DESCRIPTION ""
    ::= { affirmedIpProtocolsOspfv2RouterShowDBOpaqueLinkEntry 2 }

affirmedIpProtocolsOspfv2RouterShowDBDbSummaryTable OBJECT-TYPE
    SYNTAX      SEQUENCE OF AffirmedIpProtocolsOspfv2RouterShowDBDbSummaryEntry
    MAX-ACCESS  not-accessible
    STATUS      current
    DESCRIPTION ""
    ::= { affirmedIpProtocolsOspfv2 10 }

affirmedIpProtocolsOspfv2RouterShowDBDbSummaryEntry OBJECT-TYPE
    SYNTAX      AffirmedIpProtocolsOspfv2RouterShowDBDbSummaryEntry
    MAX-ACCESS  not-accessible
    STATUS      current
    DESCRIPTION ""
    INDEX { affirmedIpProtocolsOspfv2RouterNetworkContext, affirmedIpProtocolsOspfv2RouterShowDBDbSummaryEntryId }
        ::= { affirmedIpProtocolsOspfv2RouterShowDBDbSummaryTable 1 }

AffirmedIpProtocolsOspfv2RouterShowDBDbSummaryEntry ::=
    SEQUENCE {
        affirmedIpProtocolsOspfv2RouterShowDBDbSummaryEntryId INTEGER,
        affirmedIpProtocolsOspfv2RouterShowDBDbSummaryOutput String
    }

affirmedIpProtocolsOspfv2RouterShowDBDbSummaryEntryId OBJECT-TYPE
    SYNTAX      INTEGER {entry(0)}
    MAX-ACCESS  not-accessible
    STATUS      current
    DESCRIPTION ""
    ::= { affirmedIpProtocolsOspfv2RouterShowDBDbSummaryEntry 1 }

affirmedIpProtocolsOspfv2RouterShowDBDbSummaryOutput OBJECT-TYPE
    SYNTAX      String
    MAX-ACCESS  read-only
    STATUS      current
    DESCRIPTION ""
    ::= { affirmedIpProtocolsOspfv2RouterShowDBDbSummaryEntry 2 }

affirmedIpProtocolsOspfv2RouterShowDBBriefTable OBJECT-TYPE
    SYNTAX      SEQUENCE OF AffirmedIpProtocolsOspfv2RouterShowDBBriefEntry
    MAX-ACCESS  not-accessible
    STATUS      current
    DESCRIPTION ""
    ::= { affirmedIpProtocolsOspfv2 11 }

affirmedIpProtocolsOspfv2RouterShowDBBriefEntry OBJECT-TYPE
    SYNTAX      AffirmedIpProtocolsOspfv2RouterShowDBBriefEntry
    MAX-ACCESS  not-accessible
    STATUS      current
    DESCRIPTION ""
    INDEX { affirmedIpProtocolsOspfv2RouterNetworkContext, affirmedIpProtocolsOspfv2RouterShowDBBriefEntryId }
        ::= { affirmedIpProtocolsOspfv2RouterShowDBBriefTable 1 }

AffirmedIpProtocolsOspfv2RouterShowDBBriefEntry ::=
    SEQUENCE {
        affirmedIpProtocolsOspfv2RouterShowDBBriefEntryId INTEGER,
        affirmedIpProtocolsOspfv2RouterShowDBBriefOutput String
    }

affirmedIpProtocolsOspfv2RouterShowDBBriefEntryId OBJECT-TYPE
    SYNTAX      INTEGER {entry(0)}
    MAX-ACCESS  not-accessible
    STATUS      current
    DESCRIPTION ""
    ::= { affirmedIpProtocolsOspfv2RouterShowDBBriefEntry 1 }

affirmedIpProtocolsOspfv2RouterShowDBBriefOutput OBJECT-TYPE
    SYNTAX      String
    MAX-ACCESS  read-only
    STATUS      current
    DESCRIPTION ""
    ::= { affirmedIpProtocolsOspfv2RouterShowDBBriefEntry 2 }

affirmedIpProtocolsOspfv2RouterShowInterfaceTable OBJECT-TYPE
    SYNTAX      SEQUENCE OF AffirmedIpProtocolsOspfv2RouterShowInterfaceEntry
    MAX-ACCESS  not-accessible
    STATUS      current
    DESCRIPTION ""
    ::= { affirmedIpProtocolsOspfv2 12 }

affirmedIpProtocolsOspfv2RouterShowInterfaceEntry OBJECT-TYPE
    SYNTAX      AffirmedIpProtocolsOspfv2RouterShowInterfaceEntry
    MAX-ACCESS  not-accessible
    STATUS      current
    DESCRIPTION ""
    INDEX { affirmedIpProtocolsOspfv2RouterNetworkContext, affirmedIpProtocolsOspfv2RouterShowInterfaceEntryId }
        ::= { affirmedIpProtocolsOspfv2RouterShowInterfaceTable 1 }

AffirmedIpProtocolsOspfv2RouterShowInterfaceEntry ::=
    SEQUENCE {
        affirmedIpProtocolsOspfv2RouterShowInterfaceEntryId INTEGER,
        affirmedIpProtocolsOspfv2RouterShowInterfaceOutput String
    }

affirmedIpProtocolsOspfv2RouterShowInterfaceEntryId OBJECT-TYPE
    SYNTAX      INTEGER {entry(0)}
    MAX-ACCESS  not-accessible
    STATUS      current
    DESCRIPTION ""
    ::= { affirmedIpProtocolsOspfv2RouterShowInterfaceEntry 1 }

affirmedIpProtocolsOspfv2RouterShowInterfaceOutput OBJECT-TYPE
    SYNTAX      String
    MAX-ACCESS  read-only
    STATUS      current
    DESCRIPTION ""
    ::= { affirmedIpProtocolsOspfv2RouterShowInterfaceEntry 2 }

affirmedIpProtocolsOspfv2RouterShowNeighborTable OBJECT-TYPE
    SYNTAX      SEQUENCE OF AffirmedIpProtocolsOspfv2RouterShowNeighborEntry
    MAX-ACCESS  not-accessible
    STATUS      current
    DESCRIPTION ""
    ::= { affirmedIpProtocolsOspfv2 13 }

affirmedIpProtocolsOspfv2RouterShowNeighborEntry OBJECT-TYPE
    SYNTAX      AffirmedIpProtocolsOspfv2RouterShowNeighborEntry
    MAX-ACCESS  not-accessible
    STATUS      current
    DESCRIPTION ""
    INDEX { affirmedIpProtocolsOspfv2RouterNetworkContext, affirmedIpProtocolsOspfv2RouterShowNeighborEntryId }
        ::= { affirmedIpProtocolsOspfv2RouterShowNeighborTable 1 }

AffirmedIpProtocolsOspfv2RouterShowNeighborEntry ::=
    SEQUENCE {
        affirmedIpProtocolsOspfv2RouterShowNeighborEntryId INTEGER,
        affirmedIpProtocolsOspfv2RouterShowNeighborOutput String
    }

affirmedIpProtocolsOspfv2RouterShowNeighborEntryId OBJECT-TYPE
    SYNTAX      INTEGER {entry(0)}
    MAX-ACCESS  not-accessible
    STATUS      current
    DESCRIPTION ""
    ::= { affirmedIpProtocolsOspfv2RouterShowNeighborEntry 1 }

affirmedIpProtocolsOspfv2RouterShowNeighborOutput OBJECT-TYPE
    SYNTAX      String
    MAX-ACCESS  read-only
    STATUS      current
    DESCRIPTION ""
    ::= { affirmedIpProtocolsOspfv2RouterShowNeighborEntry 2 }

affirmedIpProtocolsOspfv2RouterShowRouteTable OBJECT-TYPE
    SYNTAX      SEQUENCE OF AffirmedIpProtocolsOspfv2RouterShowRouteEntry
    MAX-ACCESS  not-accessible
    STATUS      current
    DESCRIPTION ""
    ::= { affirmedIpProtocolsOspfv2 14 }

affirmedIpProtocolsOspfv2RouterShowRouteEntry OBJECT-TYPE
    SYNTAX      AffirmedIpProtocolsOspfv2RouterShowRouteEntry
    MAX-ACCESS  not-accessible
    STATUS      current
    DESCRIPTION ""
    INDEX { affirmedIpProtocolsOspfv2RouterNetworkContext, affirmedIpProtocolsOspfv2RouterShowRouteEntryId }
        ::= { affirmedIpProtocolsOspfv2RouterShowRouteTable 1 }

AffirmedIpProtocolsOspfv2RouterShowRouteEntry ::=
    SEQUENCE {
        affirmedIpProtocolsOspfv2RouterShowRouteEntryId INTEGER,
        affirmedIpProtocolsOspfv2RouterShowRouteOutput String
    }

affirmedIpProtocolsOspfv2RouterShowRouteEntryId OBJECT-TYPE
    SYNTAX      INTEGER {entry(0)}
    MAX-ACCESS  not-accessible
    STATUS      current
    DESCRIPTION ""
    ::= { affirmedIpProtocolsOspfv2RouterShowRouteEntry 1 }

affirmedIpProtocolsOspfv2RouterShowRouteOutput OBJECT-TYPE
    SYNTAX      String
    MAX-ACCESS  read-only
    STATUS      current
    DESCRIPTION ""
    ::= { affirmedIpProtocolsOspfv2RouterShowRouteEntry 2 }

affirmedIpProtocolsOspfv2RouterShowSummaryTable OBJECT-TYPE
    SYNTAX      SEQUENCE OF AffirmedIpProtocolsOspfv2RouterShowSummaryEntry
    MAX-ACCESS  not-accessible
    STATUS      current
    DESCRIPTION ""
    ::= { affirmedIpProtocolsOspfv2 15 }

affirmedIpProtocolsOspfv2RouterShowSummaryEntry OBJECT-TYPE
    SYNTAX      AffirmedIpProtocolsOspfv2RouterShowSummaryEntry
    MAX-ACCESS  not-accessible
    STATUS      current
    DESCRIPTION ""
    INDEX { affirmedIpProtocolsOspfv2RouterNetworkContext, affirmedIpProtocolsOspfv2RouterShowSummaryEntryId }
        ::= { affirmedIpProtocolsOspfv2RouterShowSummaryTable 1 }

AffirmedIpProtocolsOspfv2RouterShowSummaryEntry ::=
    SEQUENCE {
        affirmedIpProtocolsOspfv2RouterShowSummaryEntryId INTEGER,
        affirmedIpProtocolsOspfv2RouterShowSummaryOutput String
    }

affirmedIpProtocolsOspfv2RouterShowSummaryEntryId OBJECT-TYPE
    SYNTAX      INTEGER {entry(0)}
    MAX-ACCESS  not-accessible
    STATUS      current
    DESCRIPTION ""
    ::= { affirmedIpProtocolsOspfv2RouterShowSummaryEntry 1 }

affirmedIpProtocolsOspfv2RouterShowSummaryOutput OBJECT-TYPE
    SYNTAX      String
    MAX-ACCESS  read-only
    STATUS      current
    DESCRIPTION ""
    ::= { affirmedIpProtocolsOspfv2RouterShowSummaryEntry 2 }

affirmedIpProtocolsBgpVpnRouterTable OBJECT-TYPE
    SYNTAX      SEQUENCE OF AffirmedIpProtocolsBgpVpnRouterEntry
    MAX-ACCESS  not-accessible
    STATUS      current
    DESCRIPTION ""
    ::= { affirmedIpProtocolsBgpVpn 1 }

affirmedIpProtocolsBgpVpnRouterEntry OBJECT-TYPE
    SYNTAX      AffirmedIpProtocolsBgpVpnRouterEntry
    MAX-ACCESS  not-accessible
    STATUS      current
    DESCRIPTION ""
    INDEX { affirmedIpProtocolsBgpVpnRouterNetworkContext }
        ::= { affirmedIpProtocolsBgpVpnRouterTable 1 }

AffirmedIpProtocolsBgpVpnRouterEntry ::=
    SEQUENCE {
        affirmedIpProtocolsBgpVpnRouterNetworkContext String,
        affirmedIpProtocolsBgpVpnRouterRowstatus RowStatus
    }

affirmedIpProtocolsBgpVpnRouterNetworkContext OBJECT-TYPE
    SYNTAX      String
    MAX-ACCESS  not-accessible
    STATUS      current
    DESCRIPTION "Network Context containing this BGP VPN router"
    ::= { affirmedIpProtocolsBgpVpnRouterEntry 1 }

affirmedIpProtocolsBgpVpnRouterRowstatus OBJECT-TYPE
    SYNTAX      RowStatus
    MAX-ACCESS  read-create
    STATUS      current
    DESCRIPTION ""
    ::= { affirmedIpProtocolsBgpVpnRouterEntry 2 }

affirmedIpProtocolsBgpVpnRouterSummaryTable OBJECT-TYPE
    SYNTAX      SEQUENCE OF AffirmedIpProtocolsBgpVpnRouterSummaryEntry
    MAX-ACCESS  not-accessible
    STATUS      deprecated
    DESCRIPTION ""
    ::= { affirmedIpProtocolsBgpVpn 2 }

affirmedIpProtocolsBgpVpnRouterSummaryEntry OBJECT-TYPE
    SYNTAX      AffirmedIpProtocolsBgpVpnRouterSummaryEntry
    MAX-ACCESS  not-accessible
    STATUS      deprecated
    DESCRIPTION ""
    INDEX { affirmedIpProtocolsBgpVpnRouterNetworkContext, affirmedIpProtocolsBgpVpnRouterSummaryEntryId }
        ::= { affirmedIpProtocolsBgpVpnRouterSummaryTable 1 }

AffirmedIpProtocolsBgpVpnRouterSummaryEntry ::=
    SEQUENCE {
        affirmedIpProtocolsBgpVpnRouterSummaryEntryId INTEGER,
        affirmedIpProtocolsBgpVpnRouterSummaryOutput String
    }

affirmedIpProtocolsBgpVpnRouterSummaryEntryId OBJECT-TYPE
    SYNTAX      INTEGER {entry(0)}
    MAX-ACCESS  not-accessible
    STATUS      current
    DESCRIPTION ""
    ::= { affirmedIpProtocolsBgpVpnRouterSummaryEntry 1 }

affirmedIpProtocolsBgpVpnRouterSummaryOutput OBJECT-TYPE
    SYNTAX      String
    MAX-ACCESS  read-only
    STATUS      current
    DESCRIPTION ""
    ::= { affirmedIpProtocolsBgpVpnRouterSummaryEntry 2 }

affirmedIpProtocolsBgpVpnRouterPolicyRouteMapShowTable OBJECT-TYPE
    SYNTAX      SEQUENCE OF AffirmedIpProtocolsBgpVpnRouterPolicyRouteMapShowEntry
    MAX-ACCESS  not-accessible
    STATUS      deprecated
    DESCRIPTION ""
    ::= { affirmedIpProtocolsBgpVpn 17 }

affirmedIpProtocolsBgpVpnRouterPolicyRouteMapShowEntry OBJECT-TYPE
    SYNTAX      AffirmedIpProtocolsBgpVpnRouterPolicyRouteMapShowEntry
    MAX-ACCESS  not-accessible
    STATUS      deprecated
    DESCRIPTION ""
    INDEX { affirmedIpProtocolsBgpVpnRouterNetworkContext, affirmedIpProtocolsBgpVpnRouterPolicyRouteMapShowEntryId }
        ::= { affirmedIpProtocolsBgpVpnRouterPolicyRouteMapShowTable 1 }

AffirmedIpProtocolsBgpVpnRouterPolicyRouteMapShowEntry ::=
    SEQUENCE {
        affirmedIpProtocolsBgpVpnRouterPolicyRouteMapShowEntryId INTEGER,
        affirmedIpProtocolsBgpVpnRouterPolicyRouteMapShowOutput String
    }

affirmedIpProtocolsBgpVpnRouterPolicyRouteMapShowEntryId OBJECT-TYPE
    SYNTAX      INTEGER {entry(0)}
    MAX-ACCESS  not-accessible
    STATUS      current
    DESCRIPTION ""
    ::= { affirmedIpProtocolsBgpVpnRouterPolicyRouteMapShowEntry 1 }

affirmedIpProtocolsBgpVpnRouterPolicyRouteMapShowOutput OBJECT-TYPE
    SYNTAX      String
    MAX-ACCESS  read-only
    STATUS      current
    DESCRIPTION ""
    ::= { affirmedIpProtocolsBgpVpnRouterPolicyRouteMapShowEntry 2 }

affirmedIpProtocolsBgpVpnRouterPolicyAccessListShowTable OBJECT-TYPE
    SYNTAX      SEQUENCE OF AffirmedIpProtocolsBgpVpnRouterPolicyAccessListShowEntry
    MAX-ACCESS  not-accessible
    STATUS      deprecated
    DESCRIPTION ""
    ::= { affirmedIpProtocolsBgpVpn 18 }

affirmedIpProtocolsBgpVpnRouterPolicyAccessListShowEntry OBJECT-TYPE
    SYNTAX      AffirmedIpProtocolsBgpVpnRouterPolicyAccessListShowEntry
    MAX-ACCESS  not-accessible
    STATUS      deprecated
    DESCRIPTION ""
    INDEX { affirmedIpProtocolsBgpVpnRouterNetworkContext, affirmedIpProtocolsBgpVpnRouterPolicyAccessListShowEntryId }
        ::= { affirmedIpProtocolsBgpVpnRouterPolicyAccessListShowTable 1 }

AffirmedIpProtocolsBgpVpnRouterPolicyAccessListShowEntry ::=
    SEQUENCE {
        affirmedIpProtocolsBgpVpnRouterPolicyAccessListShowEntryId INTEGER,
        affirmedIpProtocolsBgpVpnRouterPolicyAccessListShowOutput String
    }

affirmedIpProtocolsBgpVpnRouterPolicyAccessListShowEntryId OBJECT-TYPE
    SYNTAX      INTEGER {entry(0)}
    MAX-ACCESS  not-accessible
    STATUS      current
    DESCRIPTION ""
    ::= { affirmedIpProtocolsBgpVpnRouterPolicyAccessListShowEntry 1 }

affirmedIpProtocolsBgpVpnRouterPolicyAccessListShowOutput OBJECT-TYPE
    SYNTAX      String
    MAX-ACCESS  read-only
    STATUS      current
    DESCRIPTION ""
    ::= { affirmedIpProtocolsBgpVpnRouterPolicyAccessListShowEntry 2 }

affirmedIpProtocolsBgpVpnRouterPolicyPrefixListShowTable OBJECT-TYPE
    SYNTAX      SEQUENCE OF AffirmedIpProtocolsBgpVpnRouterPolicyPrefixListShowEntry
    MAX-ACCESS  not-accessible
    STATUS      deprecated
    DESCRIPTION "Show Configured Prefix Lists"
    ::= { affirmedIpProtocolsBgpVpn 19 }

affirmedIpProtocolsBgpVpnRouterPolicyPrefixListShowEntry OBJECT-TYPE
    SYNTAX      AffirmedIpProtocolsBgpVpnRouterPolicyPrefixListShowEntry
    MAX-ACCESS  not-accessible
    STATUS      deprecated
    DESCRIPTION ""
    INDEX { affirmedIpProtocolsBgpVpnRouterNetworkContext, affirmedIpProtocolsBgpVpnRouterPolicyPrefixListShowEntryId }
        ::= { affirmedIpProtocolsBgpVpnRouterPolicyPrefixListShowTable 1 }

AffirmedIpProtocolsBgpVpnRouterPolicyPrefixListShowEntry ::=
    SEQUENCE {
        affirmedIpProtocolsBgpVpnRouterPolicyPrefixListShowEntryId INTEGER,
        affirmedIpProtocolsBgpVpnRouterPolicyPrefixListShowOutput String
    }

affirmedIpProtocolsBgpVpnRouterPolicyPrefixListShowEntryId OBJECT-TYPE
    SYNTAX      INTEGER {entry(0)}
    MAX-ACCESS  not-accessible
    STATUS      current
    DESCRIPTION ""
    ::= { affirmedIpProtocolsBgpVpnRouterPolicyPrefixListShowEntry 1 }

affirmedIpProtocolsBgpVpnRouterPolicyPrefixListShowOutput OBJECT-TYPE
    SYNTAX      String
    MAX-ACCESS  read-only
    STATUS      current
    DESCRIPTION ""
    ::= { affirmedIpProtocolsBgpVpnRouterPolicyPrefixListShowEntry 2 }

affirmedIpProtocolsBgpVpnRouterPolicyPrefixListIPv6ShowTable OBJECT-TYPE
    SYNTAX      SEQUENCE OF AffirmedIpProtocolsBgpVpnRouterPolicyPrefixListIPv6ShowEntry
    MAX-ACCESS  not-accessible
    STATUS      deprecated
    DESCRIPTION "Show Configured IPV6 Prefix Lists"
    ::= { affirmedIpProtocolsBgpVpn 20 }

affirmedIpProtocolsBgpVpnRouterPolicyPrefixListIPv6ShowEntry OBJECT-TYPE
    SYNTAX      AffirmedIpProtocolsBgpVpnRouterPolicyPrefixListIPv6ShowEntry
    MAX-ACCESS  not-accessible
    STATUS      deprecated
    DESCRIPTION ""
    INDEX { affirmedIpProtocolsBgpVpnRouterNetworkContext, affirmedIpProtocolsBgpVpnRouterPolicyPrefixListIPv6ShowEntryId }
        ::= { affirmedIpProtocolsBgpVpnRouterPolicyPrefixListIPv6ShowTable 1 }

AffirmedIpProtocolsBgpVpnRouterPolicyPrefixListIPv6ShowEntry ::=
    SEQUENCE {
        affirmedIpProtocolsBgpVpnRouterPolicyPrefixListIPv6ShowEntryId INTEGER,
        affirmedIpProtocolsBgpVpnRouterPolicyPrefixListIPv6ShowOutput String
    }

affirmedIpProtocolsBgpVpnRouterPolicyPrefixListIPv6ShowEntryId OBJECT-TYPE
    SYNTAX      INTEGER {entry(0)}
    MAX-ACCESS  not-accessible
    STATUS      current
    DESCRIPTION ""
    ::= { affirmedIpProtocolsBgpVpnRouterPolicyPrefixListIPv6ShowEntry 1 }

affirmedIpProtocolsBgpVpnRouterPolicyPrefixListIPv6ShowOutput OBJECT-TYPE
    SYNTAX      String
    MAX-ACCESS  read-only
    STATUS      current
    DESCRIPTION ""
    ::= { affirmedIpProtocolsBgpVpnRouterPolicyPrefixListIPv6ShowEntry 2 }

affirmedIpProtocolsBgpVpnRouterPolicyCommunityListShowTable OBJECT-TYPE
    SYNTAX      SEQUENCE OF AffirmedIpProtocolsBgpVpnRouterPolicyCommunityListShowEntry
    MAX-ACCESS  not-accessible
    STATUS      deprecated
    DESCRIPTION "Show Configured Community Lists"
    ::= { affirmedIpProtocolsBgpVpn 21 }

affirmedIpProtocolsBgpVpnRouterPolicyCommunityListShowEntry OBJECT-TYPE
    SYNTAX      AffirmedIpProtocolsBgpVpnRouterPolicyCommunityListShowEntry
    MAX-ACCESS  not-accessible
    STATUS      deprecated
    DESCRIPTION ""
    INDEX { affirmedIpProtocolsBgpVpnRouterNetworkContext, affirmedIpProtocolsBgpVpnRouterPolicyCommunityListShowEntryId }
        ::= { affirmedIpProtocolsBgpVpnRouterPolicyCommunityListShowTable 1 }

AffirmedIpProtocolsBgpVpnRouterPolicyCommunityListShowEntry ::=
    SEQUENCE {
        affirmedIpProtocolsBgpVpnRouterPolicyCommunityListShowEntryId INTEGER,
        affirmedIpProtocolsBgpVpnRouterPolicyCommunityListShowOutput String
    }

affirmedIpProtocolsBgpVpnRouterPolicyCommunityListShowEntryId OBJECT-TYPE
    SYNTAX      INTEGER {entry(0)}
    MAX-ACCESS  not-accessible
    STATUS      current
    DESCRIPTION ""
    ::= { affirmedIpProtocolsBgpVpnRouterPolicyCommunityListShowEntry 1 }

affirmedIpProtocolsBgpVpnRouterPolicyCommunityListShowOutput OBJECT-TYPE
    SYNTAX      String
    MAX-ACCESS  read-only
    STATUS      current
    DESCRIPTION ""
    ::= { affirmedIpProtocolsBgpVpnRouterPolicyCommunityListShowEntry 2 }

affirmedIpProtocolsBgpVpnRouterPolicyAsPathListShowTable OBJECT-TYPE
    SYNTAX      SEQUENCE OF AffirmedIpProtocolsBgpVpnRouterPolicyAsPathListShowEntry
    MAX-ACCESS  not-accessible
    STATUS      deprecated
    DESCRIPTION "Show Configured ASPath Lists"
    ::= { affirmedIpProtocolsBgpVpn 22 }

affirmedIpProtocolsBgpVpnRouterPolicyAsPathListShowEntry OBJECT-TYPE
    SYNTAX      AffirmedIpProtocolsBgpVpnRouterPolicyAsPathListShowEntry
    MAX-ACCESS  not-accessible
    STATUS      deprecated
    DESCRIPTION ""
    INDEX { affirmedIpProtocolsBgpVpnRouterNetworkContext, affirmedIpProtocolsBgpVpnRouterPolicyAsPathListShowEntryId }
        ::= { affirmedIpProtocolsBgpVpnRouterPolicyAsPathListShowTable 1 }

AffirmedIpProtocolsBgpVpnRouterPolicyAsPathListShowEntry ::=
    SEQUENCE {
        affirmedIpProtocolsBgpVpnRouterPolicyAsPathListShowEntryId INTEGER,
        affirmedIpProtocolsBgpVpnRouterPolicyAsPathListShowOutput String
    }

affirmedIpProtocolsBgpVpnRouterPolicyAsPathListShowEntryId OBJECT-TYPE
    SYNTAX      INTEGER {entry(0)}
    MAX-ACCESS  not-accessible
    STATUS      current
    DESCRIPTION ""
    ::= { affirmedIpProtocolsBgpVpnRouterPolicyAsPathListShowEntry 1 }

affirmedIpProtocolsBgpVpnRouterPolicyAsPathListShowOutput OBJECT-TYPE
    SYNTAX      String
    MAX-ACCESS  read-only
    STATUS      current
    DESCRIPTION ""
    ::= { affirmedIpProtocolsBgpVpnRouterPolicyAsPathListShowEntry 2 }

affirmedIpProtocolsBgpVpnRouterIpv4UcastSummaryTable OBJECT-TYPE
    SYNTAX      SEQUENCE OF AffirmedIpProtocolsBgpVpnRouterIpv4UcastSummaryEntry
    MAX-ACCESS  not-accessible
    STATUS      deprecated
    DESCRIPTION ""
    ::= { affirmedIpProtocolsBgpVpn 3 }

affirmedIpProtocolsBgpVpnRouterIpv4UcastSummaryEntry OBJECT-TYPE
    SYNTAX      AffirmedIpProtocolsBgpVpnRouterIpv4UcastSummaryEntry
    MAX-ACCESS  not-accessible
    STATUS      deprecated
    DESCRIPTION ""
    INDEX { affirmedIpProtocolsBgpVpnRouterNetworkContext, affirmedIpProtocolsBgpVpnRouterIpv4UcastSummaryEntryId }
        ::= { affirmedIpProtocolsBgpVpnRouterIpv4UcastSummaryTable 1 }

AffirmedIpProtocolsBgpVpnRouterIpv4UcastSummaryEntry ::=
    SEQUENCE {
        affirmedIpProtocolsBgpVpnRouterIpv4UcastSummaryEntryId INTEGER,
        affirmedIpProtocolsBgpVpnRouterIpv4UcastSummaryOutput String
    }

affirmedIpProtocolsBgpVpnRouterIpv4UcastSummaryEntryId OBJECT-TYPE
    SYNTAX      INTEGER {entry(0)}
    MAX-ACCESS  not-accessible
    STATUS      current
    DESCRIPTION ""
    ::= { affirmedIpProtocolsBgpVpnRouterIpv4UcastSummaryEntry 1 }

affirmedIpProtocolsBgpVpnRouterIpv4UcastSummaryOutput OBJECT-TYPE
    SYNTAX      String
    MAX-ACCESS  read-only
    STATUS      current
    DESCRIPTION ""
    ::= { affirmedIpProtocolsBgpVpnRouterIpv4UcastSummaryEntry 2 }

affirmedIpProtocolsBgpVpnRouterIpv4UcastRouteDetailTable OBJECT-TYPE
    SYNTAX      SEQUENCE OF AffirmedIpProtocolsBgpVpnRouterIpv4UcastRouteDetailEntry
    MAX-ACCESS  not-accessible
    STATUS      current
    DESCRIPTION ""
    ::= { affirmedIpProtocolsBgpVpn 4 }

affirmedIpProtocolsBgpVpnRouterIpv4UcastRouteDetailEntry OBJECT-TYPE
    SYNTAX      AffirmedIpProtocolsBgpVpnRouterIpv4UcastRouteDetailEntry
    MAX-ACCESS  not-accessible
    STATUS      current
    DESCRIPTION ""
    INDEX { affirmedIpProtocolsBgpVpnRouterNetworkContext, affirmedIpProtocolsBgpVpnRouterIpv4UcastRouteDetailPrefix, affirmedIpProtocolsBgpVpnRouterIpv4UcastRouteDetailPrefixLength }
        ::= { affirmedIpProtocolsBgpVpnRouterIpv4UcastRouteDetailTable 1 }

AffirmedIpProtocolsBgpVpnRouterIpv4UcastRouteDetailEntry ::=
    SEQUENCE {
        affirmedIpProtocolsBgpVpnRouterIpv4UcastRouteDetailPrefix String,
        affirmedIpProtocolsBgpVpnRouterIpv4UcastRouteDetailPrefixLength Unsigned32,
        affirmedIpProtocolsBgpVpnRouterIpv4UcastRouteDetailOutput String
    }

affirmedIpProtocolsBgpVpnRouterIpv4UcastRouteDetailPrefix OBJECT-TYPE
    SYNTAX      String
    MAX-ACCESS  not-accessible
    STATUS      current
    DESCRIPTION "IPv4 prefix (A.B.C.D)"
    ::= { affirmedIpProtocolsBgpVpnRouterIpv4UcastRouteDetailEntry 1 }

affirmedIpProtocolsBgpVpnRouterIpv4UcastRouteDetailPrefixLength OBJECT-TYPE
    SYNTAX      Unsigned32
    MAX-ACCESS  not-accessible
    STATUS      current
    DESCRIPTION "Prefix length"
    ::= { affirmedIpProtocolsBgpVpnRouterIpv4UcastRouteDetailEntry 2 }

affirmedIpProtocolsBgpVpnRouterIpv4UcastRouteDetailOutput OBJECT-TYPE
    SYNTAX      String
    MAX-ACCESS  read-only
    STATUS      current
    DESCRIPTION ""
    ::= { affirmedIpProtocolsBgpVpnRouterIpv4UcastRouteDetailEntry 3 }

affirmedIpProtocolsBgpVpnRouterIpv4UcastRouteDampeningTable OBJECT-TYPE
    SYNTAX      SEQUENCE OF AffirmedIpProtocolsBgpVpnRouterIpv4UcastRouteDampeningEntry
    MAX-ACCESS  not-accessible
    STATUS      current
    DESCRIPTION ""
    ::= { affirmedIpProtocolsBgpVpn 5 }

affirmedIpProtocolsBgpVpnRouterIpv4UcastRouteDampeningEntry OBJECT-TYPE
    SYNTAX      AffirmedIpProtocolsBgpVpnRouterIpv4UcastRouteDampeningEntry
    MAX-ACCESS  not-accessible
    STATUS      current
    DESCRIPTION ""
    INDEX { affirmedIpProtocolsBgpVpnRouterNetworkContext, affirmedIpProtocolsBgpVpnRouterIpv4UcastRouteDampeningAction }
        ::= { affirmedIpProtocolsBgpVpnRouterIpv4UcastRouteDampeningTable 1 }

AffirmedIpProtocolsBgpVpnRouterIpv4UcastRouteDampeningEntry ::=
    SEQUENCE {
        affirmedIpProtocolsBgpVpnRouterIpv4UcastRouteDampeningAction INTEGER,
        affirmedIpProtocolsBgpVpnRouterIpv4UcastRouteDampeningOutput String
    }

affirmedIpProtocolsBgpVpnRouterIpv4UcastRouteDampeningAction OBJECT-TYPE
    SYNTAX      INTEGER {dampened-paths(0),flap-statistics(1),parameters(2)}
    MAX-ACCESS  not-accessible
    STATUS      current
    DESCRIPTION ""
    ::= { affirmedIpProtocolsBgpVpnRouterIpv4UcastRouteDampeningEntry 1 }

affirmedIpProtocolsBgpVpnRouterIpv4UcastRouteDampeningOutput OBJECT-TYPE
    SYNTAX      String
    MAX-ACCESS  read-only
    STATUS      current
    DESCRIPTION ""
    ::= { affirmedIpProtocolsBgpVpnRouterIpv4UcastRouteDampeningEntry 2 }

affirmedIpProtocolsBgpVpnRouterIpv6UcastSummaryTable OBJECT-TYPE
    SYNTAX      SEQUENCE OF AffirmedIpProtocolsBgpVpnRouterIpv6UcastSummaryEntry
    MAX-ACCESS  not-accessible
    STATUS      deprecated
    DESCRIPTION ""
    ::= { affirmedIpProtocolsBgpVpn 6 }

affirmedIpProtocolsBgpVpnRouterIpv6UcastSummaryEntry OBJECT-TYPE
    SYNTAX      AffirmedIpProtocolsBgpVpnRouterIpv6UcastSummaryEntry
    MAX-ACCESS  not-accessible
    STATUS      deprecated
    DESCRIPTION ""
    INDEX { affirmedIpProtocolsBgpVpnRouterNetworkContext, affirmedIpProtocolsBgpVpnRouterIpv6UcastSummaryEntryId }
        ::= { affirmedIpProtocolsBgpVpnRouterIpv6UcastSummaryTable 1 }

AffirmedIpProtocolsBgpVpnRouterIpv6UcastSummaryEntry ::=
    SEQUENCE {
        affirmedIpProtocolsBgpVpnRouterIpv6UcastSummaryEntryId INTEGER,
        affirmedIpProtocolsBgpVpnRouterIpv6UcastSummaryOutput String
    }

affirmedIpProtocolsBgpVpnRouterIpv6UcastSummaryEntryId OBJECT-TYPE
    SYNTAX      INTEGER {entry(0)}
    MAX-ACCESS  not-accessible
    STATUS      current
    DESCRIPTION ""
    ::= { affirmedIpProtocolsBgpVpnRouterIpv6UcastSummaryEntry 1 }

affirmedIpProtocolsBgpVpnRouterIpv6UcastSummaryOutput OBJECT-TYPE
    SYNTAX      String
    MAX-ACCESS  read-only
    STATUS      current
    DESCRIPTION ""
    ::= { affirmedIpProtocolsBgpVpnRouterIpv6UcastSummaryEntry 2 }

affirmedIpProtocolsBgpVpnRouterIpv6UcastRouteDetailTable OBJECT-TYPE
    SYNTAX      SEQUENCE OF AffirmedIpProtocolsBgpVpnRouterIpv6UcastRouteDetailEntry
    MAX-ACCESS  not-accessible
    STATUS      current
    DESCRIPTION ""
    ::= { affirmedIpProtocolsBgpVpn 7 }

affirmedIpProtocolsBgpVpnRouterIpv6UcastRouteDetailEntry OBJECT-TYPE
    SYNTAX      AffirmedIpProtocolsBgpVpnRouterIpv6UcastRouteDetailEntry
    MAX-ACCESS  not-accessible
    STATUS      current
    DESCRIPTION ""
    INDEX { affirmedIpProtocolsBgpVpnRouterNetworkContext, affirmedIpProtocolsBgpVpnRouterIpv6UcastRouteDetailPrefix, affirmedIpProtocolsBgpVpnRouterIpv6UcastRouteDetailPrefixLength }
        ::= { affirmedIpProtocolsBgpVpnRouterIpv6UcastRouteDetailTable 1 }

AffirmedIpProtocolsBgpVpnRouterIpv6UcastRouteDetailEntry ::=
    SEQUENCE {
        affirmedIpProtocolsBgpVpnRouterIpv6UcastRouteDetailPrefix String,
        affirmedIpProtocolsBgpVpnRouterIpv6UcastRouteDetailPrefixLength Unsigned32,
        affirmedIpProtocolsBgpVpnRouterIpv6UcastRouteDetailOutput String
    }

affirmedIpProtocolsBgpVpnRouterIpv6UcastRouteDetailPrefix OBJECT-TYPE
    SYNTAX      String
    MAX-ACCESS  not-accessible
    STATUS      current
    DESCRIPTION "IPv6 prefix"
    ::= { affirmedIpProtocolsBgpVpnRouterIpv6UcastRouteDetailEntry 1 }

affirmedIpProtocolsBgpVpnRouterIpv6UcastRouteDetailPrefixLength OBJECT-TYPE
    SYNTAX      Unsigned32
    MAX-ACCESS  not-accessible
    STATUS      current
    DESCRIPTION "IPv6 prefix length"
    ::= { affirmedIpProtocolsBgpVpnRouterIpv6UcastRouteDetailEntry 2 }

affirmedIpProtocolsBgpVpnRouterIpv6UcastRouteDetailOutput OBJECT-TYPE
    SYNTAX      String
    MAX-ACCESS  read-only
    STATUS      current
    DESCRIPTION ""
    ::= { affirmedIpProtocolsBgpVpnRouterIpv6UcastRouteDetailEntry 3 }

affirmedIpProtocolsBgpVpnRouterIpv6UcastRouteDampeningTable OBJECT-TYPE
    SYNTAX      SEQUENCE OF AffirmedIpProtocolsBgpVpnRouterIpv6UcastRouteDampeningEntry
    MAX-ACCESS  not-accessible
    STATUS      current
    DESCRIPTION ""
    ::= { affirmedIpProtocolsBgpVpn 8 }

affirmedIpProtocolsBgpVpnRouterIpv6UcastRouteDampeningEntry OBJECT-TYPE
    SYNTAX      AffirmedIpProtocolsBgpVpnRouterIpv6UcastRouteDampeningEntry
    MAX-ACCESS  not-accessible
    STATUS      current
    DESCRIPTION ""
    INDEX { affirmedIpProtocolsBgpVpnRouterNetworkContext, affirmedIpProtocolsBgpVpnRouterIpv6UcastRouteDampeningAction }
        ::= { affirmedIpProtocolsBgpVpnRouterIpv6UcastRouteDampeningTable 1 }

AffirmedIpProtocolsBgpVpnRouterIpv6UcastRouteDampeningEntry ::=
    SEQUENCE {
        affirmedIpProtocolsBgpVpnRouterIpv6UcastRouteDampeningAction INTEGER,
        affirmedIpProtocolsBgpVpnRouterIpv6UcastRouteDampeningOutput String
    }

affirmedIpProtocolsBgpVpnRouterIpv6UcastRouteDampeningAction OBJECT-TYPE
    SYNTAX      INTEGER {dampened-paths(0),flap-statistics(1),parameters(2)}
    MAX-ACCESS  not-accessible
    STATUS      current
    DESCRIPTION ""
    ::= { affirmedIpProtocolsBgpVpnRouterIpv6UcastRouteDampeningEntry 1 }

affirmedIpProtocolsBgpVpnRouterIpv6UcastRouteDampeningOutput OBJECT-TYPE
    SYNTAX      String
    MAX-ACCESS  read-only
    STATUS      current
    DESCRIPTION ""
    ::= { affirmedIpProtocolsBgpVpnRouterIpv6UcastRouteDampeningEntry 2 }

affirmedIpProtocolsBgpVpnRouterVpnv4UcastAllTable OBJECT-TYPE
    SYNTAX      SEQUENCE OF AffirmedIpProtocolsBgpVpnRouterVpnv4UcastAllEntry
    MAX-ACCESS  not-accessible
    STATUS      deprecated
    DESCRIPTION ""
    ::= { affirmedIpProtocolsBgpVpn 9 }

affirmedIpProtocolsBgpVpnRouterVpnv4UcastAllEntry OBJECT-TYPE
    SYNTAX      AffirmedIpProtocolsBgpVpnRouterVpnv4UcastAllEntry
    MAX-ACCESS  not-accessible
    STATUS      deprecated
    DESCRIPTION ""
    INDEX { affirmedIpProtocolsBgpVpnRouterNetworkContext, affirmedIpProtocolsBgpVpnRouterVpnv4UcastAllEntryId }
        ::= { affirmedIpProtocolsBgpVpnRouterVpnv4UcastAllTable 1 }

AffirmedIpProtocolsBgpVpnRouterVpnv4UcastAllEntry ::=
    SEQUENCE {
        affirmedIpProtocolsBgpVpnRouterVpnv4UcastAllEntryId INTEGER,
        affirmedIpProtocolsBgpVpnRouterVpnv4UcastAllOutput String
    }

affirmedIpProtocolsBgpVpnRouterVpnv4UcastAllEntryId OBJECT-TYPE
    SYNTAX      INTEGER {entry(0)}
    MAX-ACCESS  not-accessible
    STATUS      current
    DESCRIPTION ""
    ::= { affirmedIpProtocolsBgpVpnRouterVpnv4UcastAllEntry 1 }

affirmedIpProtocolsBgpVpnRouterVpnv4UcastAllOutput OBJECT-TYPE
    SYNTAX      String
    MAX-ACCESS  read-only
    STATUS      current
    DESCRIPTION ""
    ::= { affirmedIpProtocolsBgpVpnRouterVpnv4UcastAllEntry 2 }

affirmedIpProtocolsBgpVpnRouterVpnv4UcastRouteDetailTable OBJECT-TYPE
    SYNTAX      SEQUENCE OF AffirmedIpProtocolsBgpVpnRouterVpnv4UcastRouteDetailEntry
    MAX-ACCESS  not-accessible
    STATUS      current
    DESCRIPTION ""
    ::= { affirmedIpProtocolsBgpVpn 10 }

affirmedIpProtocolsBgpVpnRouterVpnv4UcastRouteDetailEntry OBJECT-TYPE
    SYNTAX      AffirmedIpProtocolsBgpVpnRouterVpnv4UcastRouteDetailEntry
    MAX-ACCESS  not-accessible
    STATUS      current
    DESCRIPTION ""
    INDEX { affirmedIpProtocolsBgpVpnRouterNetworkContext, affirmedIpProtocolsBgpVpnRouterVpnv4UcastRouteDetailPrefix, affirmedIpProtocolsBgpVpnRouterVpnv4UcastRouteDetailPrefixLength }
        ::= { affirmedIpProtocolsBgpVpnRouterVpnv4UcastRouteDetailTable 1 }

AffirmedIpProtocolsBgpVpnRouterVpnv4UcastRouteDetailEntry ::=
    SEQUENCE {
        affirmedIpProtocolsBgpVpnRouterVpnv4UcastRouteDetailPrefix String,
        affirmedIpProtocolsBgpVpnRouterVpnv4UcastRouteDetailPrefixLength Unsigned32,
        affirmedIpProtocolsBgpVpnRouterVpnv4UcastRouteDetailOutput String
    }

affirmedIpProtocolsBgpVpnRouterVpnv4UcastRouteDetailPrefix OBJECT-TYPE
    SYNTAX      String
    MAX-ACCESS  not-accessible
    STATUS      current
    DESCRIPTION "IPv4 prefix (A.B.C.D)"
    ::= { affirmedIpProtocolsBgpVpnRouterVpnv4UcastRouteDetailEntry 1 }

affirmedIpProtocolsBgpVpnRouterVpnv4UcastRouteDetailPrefixLength OBJECT-TYPE
    SYNTAX      Unsigned32
    MAX-ACCESS  not-accessible
    STATUS      current
    DESCRIPTION "Prefix length"
    ::= { affirmedIpProtocolsBgpVpnRouterVpnv4UcastRouteDetailEntry 2 }

affirmedIpProtocolsBgpVpnRouterVpnv4UcastRouteDetailOutput OBJECT-TYPE
    SYNTAX      String
    MAX-ACCESS  read-only
    STATUS      current
    DESCRIPTION ""
    ::= { affirmedIpProtocolsBgpVpnRouterVpnv4UcastRouteDetailEntry 3 }

affirmedIpProtocolsBgpVpnRouterVpnv6UcastAllTable OBJECT-TYPE
    SYNTAX      SEQUENCE OF AffirmedIpProtocolsBgpVpnRouterVpnv6UcastAllEntry
    MAX-ACCESS  not-accessible
    STATUS      deprecated
    DESCRIPTION ""
    ::= { affirmedIpProtocolsBgpVpn 11 }

affirmedIpProtocolsBgpVpnRouterVpnv6UcastAllEntry OBJECT-TYPE
    SYNTAX      AffirmedIpProtocolsBgpVpnRouterVpnv6UcastAllEntry
    MAX-ACCESS  not-accessible
    STATUS      deprecated
    DESCRIPTION ""
    INDEX { affirmedIpProtocolsBgpVpnRouterNetworkContext, affirmedIpProtocolsBgpVpnRouterVpnv6UcastAllEntryId }
        ::= { affirmedIpProtocolsBgpVpnRouterVpnv6UcastAllTable 1 }

AffirmedIpProtocolsBgpVpnRouterVpnv6UcastAllEntry ::=
    SEQUENCE {
        affirmedIpProtocolsBgpVpnRouterVpnv6UcastAllEntryId INTEGER,
        affirmedIpProtocolsBgpVpnRouterVpnv6UcastAllOutput String
    }

affirmedIpProtocolsBgpVpnRouterVpnv6UcastAllEntryId OBJECT-TYPE
    SYNTAX      INTEGER {entry(0)}
    MAX-ACCESS  not-accessible
    STATUS      current
    DESCRIPTION ""
    ::= { affirmedIpProtocolsBgpVpnRouterVpnv6UcastAllEntry 1 }

affirmedIpProtocolsBgpVpnRouterVpnv6UcastAllOutput OBJECT-TYPE
    SYNTAX      String
    MAX-ACCESS  read-only
    STATUS      current
    DESCRIPTION ""
    ::= { affirmedIpProtocolsBgpVpnRouterVpnv6UcastAllEntry 2 }

affirmedIpProtocolsBgpVpnRouterNeighborTable OBJECT-TYPE
    SYNTAX      SEQUENCE OF AffirmedIpProtocolsBgpVpnRouterNeighborEntry
    MAX-ACCESS  not-accessible
    STATUS      current
    DESCRIPTION ""
    ::= { affirmedIpProtocolsBgpVpn 12 }

affirmedIpProtocolsBgpVpnRouterNeighborEntry OBJECT-TYPE
    SYNTAX      AffirmedIpProtocolsBgpVpnRouterNeighborEntry
    MAX-ACCESS  not-accessible
    STATUS      current
    DESCRIPTION ""
    INDEX { affirmedIpProtocolsBgpVpnRouterNetworkContext, affirmedIpProtocolsBgpVpnRouterNeighborPeeringName }
        ::= { affirmedIpProtocolsBgpVpnRouterNeighborTable 1 }

AffirmedIpProtocolsBgpVpnRouterNeighborEntry ::=
    SEQUENCE {
        affirmedIpProtocolsBgpVpnRouterNeighborPeeringName String,
        affirmedIpProtocolsBgpVpnRouterNeighborRowstatus RowStatus
    }

affirmedIpProtocolsBgpVpnRouterNeighborPeeringName OBJECT-TYPE
    SYNTAX      String
    MAX-ACCESS  not-accessible
    STATUS      current
    DESCRIPTION "Name of the peering"
    ::= { affirmedIpProtocolsBgpVpnRouterNeighborEntry 1 }

affirmedIpProtocolsBgpVpnRouterNeighborRowstatus OBJECT-TYPE
    SYNTAX      RowStatus
    MAX-ACCESS  read-create
    STATUS      current
    DESCRIPTION ""
    ::= { affirmedIpProtocolsBgpVpnRouterNeighborEntry 2 }

affirmedIpProtocolsBgpVpnRouterNeighborDetailTable OBJECT-TYPE
    SYNTAX      SEQUENCE OF AffirmedIpProtocolsBgpVpnRouterNeighborDetailEntry
    MAX-ACCESS  not-accessible
    STATUS      deprecated
    DESCRIPTION ""
    ::= { affirmedIpProtocolsBgpVpn 13 }

affirmedIpProtocolsBgpVpnRouterNeighborDetailEntry OBJECT-TYPE
    SYNTAX      AffirmedIpProtocolsBgpVpnRouterNeighborDetailEntry
    MAX-ACCESS  not-accessible
    STATUS      deprecated
    DESCRIPTION ""
    INDEX { affirmedIpProtocolsBgpVpnRouterNetworkContext, affirmedIpProtocolsBgpVpnRouterNeighborPeeringName, affirmedIpProtocolsBgpVpnRouterNeighborDetailEntryId }
        ::= { affirmedIpProtocolsBgpVpnRouterNeighborDetailTable 1 }

AffirmedIpProtocolsBgpVpnRouterNeighborDetailEntry ::=
    SEQUENCE {
        affirmedIpProtocolsBgpVpnRouterNeighborDetailEntryId INTEGER,
        affirmedIpProtocolsBgpVpnRouterNeighborDetailOutput String
    }

affirmedIpProtocolsBgpVpnRouterNeighborDetailEntryId OBJECT-TYPE
    SYNTAX      INTEGER {entry(0)}
    MAX-ACCESS  not-accessible
    STATUS      current
    DESCRIPTION ""
    ::= { affirmedIpProtocolsBgpVpnRouterNeighborDetailEntry 1 }

affirmedIpProtocolsBgpVpnRouterNeighborDetailOutput OBJECT-TYPE
    SYNTAX      String
    MAX-ACCESS  read-only
    STATUS      current
    DESCRIPTION ""
    ::= { affirmedIpProtocolsBgpVpnRouterNeighborDetailEntry 2 }

affirmedIpProtocolsBgpVpnRouterVrfTable OBJECT-TYPE
    SYNTAX      SEQUENCE OF AffirmedIpProtocolsBgpVpnRouterVrfEntry
    MAX-ACCESS  not-accessible
    STATUS      current
    DESCRIPTION ""
    ::= { affirmedIpProtocolsBgpVpn 14 }

affirmedIpProtocolsBgpVpnRouterVrfEntry OBJECT-TYPE
    SYNTAX      AffirmedIpProtocolsBgpVpnRouterVrfEntry
    MAX-ACCESS  not-accessible
    STATUS      current
    DESCRIPTION ""
    INDEX { affirmedIpProtocolsBgpVpnRouterNetworkContext, affirmedIpProtocolsBgpVpnRouterVrfNetworkContext }
        ::= { affirmedIpProtocolsBgpVpnRouterVrfTable 1 }

AffirmedIpProtocolsBgpVpnRouterVrfEntry ::=
    SEQUENCE {
        affirmedIpProtocolsBgpVpnRouterVrfNetworkContext String,
        affirmedIpProtocolsBgpVpnRouterVrfRowstatus RowStatus
    }

affirmedIpProtocolsBgpVpnRouterVrfNetworkContext OBJECT-TYPE
    SYNTAX      String
    MAX-ACCESS  not-accessible
    STATUS      current
    DESCRIPTION "Network Context supporting this VRF"
    ::= { affirmedIpProtocolsBgpVpnRouterVrfEntry 1 }

affirmedIpProtocolsBgpVpnRouterVrfRowstatus OBJECT-TYPE
    SYNTAX      RowStatus
    MAX-ACCESS  read-create
    STATUS      current
    DESCRIPTION ""
    ::= { affirmedIpProtocolsBgpVpnRouterVrfEntry 2 }

affirmedIpProtocolsBgpVpnRouterVrfIpv4UcastLabelsTable OBJECT-TYPE
    SYNTAX      SEQUENCE OF AffirmedIpProtocolsBgpVpnRouterVrfIpv4UcastLabelsEntry
    MAX-ACCESS  not-accessible
    STATUS      deprecated
    DESCRIPTION ""
    ::= { affirmedIpProtocolsBgpVpn 15 }

affirmedIpProtocolsBgpVpnRouterVrfIpv4UcastLabelsEntry OBJECT-TYPE
    SYNTAX      AffirmedIpProtocolsBgpVpnRouterVrfIpv4UcastLabelsEntry
    MAX-ACCESS  not-accessible
    STATUS      deprecated
    DESCRIPTION ""
    INDEX { affirmedIpProtocolsBgpVpnRouterNetworkContext, affirmedIpProtocolsBgpVpnRouterVrfNetworkContext, affirmedIpProtocolsBgpVpnRouterVrfIpv4UcastLabelsEntryId }
        ::= { affirmedIpProtocolsBgpVpnRouterVrfIpv4UcastLabelsTable 1 }

AffirmedIpProtocolsBgpVpnRouterVrfIpv4UcastLabelsEntry ::=
    SEQUENCE {
        affirmedIpProtocolsBgpVpnRouterVrfIpv4UcastLabelsEntryId INTEGER,
        affirmedIpProtocolsBgpVpnRouterVrfIpv4UcastLabelsOutput String
    }

affirmedIpProtocolsBgpVpnRouterVrfIpv4UcastLabelsEntryId OBJECT-TYPE
    SYNTAX      INTEGER {entry(0)}
    MAX-ACCESS  not-accessible
    STATUS      current
    DESCRIPTION ""
    ::= { affirmedIpProtocolsBgpVpnRouterVrfIpv4UcastLabelsEntry 1 }

affirmedIpProtocolsBgpVpnRouterVrfIpv4UcastLabelsOutput OBJECT-TYPE
    SYNTAX      String
    MAX-ACCESS  read-only
    STATUS      current
    DESCRIPTION ""
    ::= { affirmedIpProtocolsBgpVpnRouterVrfIpv4UcastLabelsEntry 2 }

affirmedIpProtocolsBgpVpnRouterVrfIpv6UcastLabelsTable OBJECT-TYPE
    SYNTAX      SEQUENCE OF AffirmedIpProtocolsBgpVpnRouterVrfIpv6UcastLabelsEntry
    MAX-ACCESS  not-accessible
    STATUS      deprecated
    DESCRIPTION ""
    ::= { affirmedIpProtocolsBgpVpn 16 }

affirmedIpProtocolsBgpVpnRouterVrfIpv6UcastLabelsEntry OBJECT-TYPE
    SYNTAX      AffirmedIpProtocolsBgpVpnRouterVrfIpv6UcastLabelsEntry
    MAX-ACCESS  not-accessible
    STATUS      deprecated
    DESCRIPTION ""
    INDEX { affirmedIpProtocolsBgpVpnRouterNetworkContext, affirmedIpProtocolsBgpVpnRouterVrfNetworkContext, affirmedIpProtocolsBgpVpnRouterVrfIpv6UcastLabelsEntryId }
        ::= { affirmedIpProtocolsBgpVpnRouterVrfIpv6UcastLabelsTable 1 }

AffirmedIpProtocolsBgpVpnRouterVrfIpv6UcastLabelsEntry ::=
    SEQUENCE {
        affirmedIpProtocolsBgpVpnRouterVrfIpv6UcastLabelsEntryId INTEGER,
        affirmedIpProtocolsBgpVpnRouterVrfIpv6UcastLabelsOutput String
    }

affirmedIpProtocolsBgpVpnRouterVrfIpv6UcastLabelsEntryId OBJECT-TYPE
    SYNTAX      INTEGER {entry(0)}
    MAX-ACCESS  not-accessible
    STATUS      current
    DESCRIPTION ""
    ::= { affirmedIpProtocolsBgpVpnRouterVrfIpv6UcastLabelsEntry 1 }

affirmedIpProtocolsBgpVpnRouterVrfIpv6UcastLabelsOutput OBJECT-TYPE
    SYNTAX      String
    MAX-ACCESS  read-only
    STATUS      current
    DESCRIPTION ""
    ::= { affirmedIpProtocolsBgpVpnRouterVrfIpv6UcastLabelsEntry 2 }

affirmedIpProtocolsBgpRouterTable OBJECT-TYPE
    SYNTAX      SEQUENCE OF AffirmedIpProtocolsBgpRouterEntry
    MAX-ACCESS  not-accessible
    STATUS      current
    DESCRIPTION ""
    ::= { affirmedIpProtocolsBgp 1 }

affirmedIpProtocolsBgpRouterEntry OBJECT-TYPE
    SYNTAX      AffirmedIpProtocolsBgpRouterEntry
    MAX-ACCESS  not-accessible
    STATUS      current
    DESCRIPTION ""
    INDEX { affirmedIpProtocolsBgpRouterNetworkContext }
        ::= { affirmedIpProtocolsBgpRouterTable 1 }

AffirmedIpProtocolsBgpRouterEntry ::=
    SEQUENCE {
        affirmedIpProtocolsBgpRouterNetworkContext String,
        affirmedIpProtocolsBgpRouterRowstatus RowStatus
    }

affirmedIpProtocolsBgpRouterNetworkContext OBJECT-TYPE
    SYNTAX      String
    MAX-ACCESS  not-accessible
    STATUS      current
    DESCRIPTION "Network Context containing this BGP router"
    ::= { affirmedIpProtocolsBgpRouterEntry 1 }

affirmedIpProtocolsBgpRouterRowstatus OBJECT-TYPE
    SYNTAX      RowStatus
    MAX-ACCESS  read-create
    STATUS      current
    DESCRIPTION ""
    ::= { affirmedIpProtocolsBgpRouterEntry 2 }

affirmedIpProtocolsBgpRouterSummaryTable OBJECT-TYPE
    SYNTAX      SEQUENCE OF AffirmedIpProtocolsBgpRouterSummaryEntry
    MAX-ACCESS  not-accessible
    STATUS      deprecated
    DESCRIPTION ""
    ::= { affirmedIpProtocolsBgp 2 }

affirmedIpProtocolsBgpRouterSummaryEntry OBJECT-TYPE
    SYNTAX      AffirmedIpProtocolsBgpRouterSummaryEntry
    MAX-ACCESS  not-accessible
    STATUS      deprecated
    DESCRIPTION ""
    INDEX { affirmedIpProtocolsBgpRouterNetworkContext, affirmedIpProtocolsBgpRouterSummaryEntryId }
        ::= { affirmedIpProtocolsBgpRouterSummaryTable 1 }

AffirmedIpProtocolsBgpRouterSummaryEntry ::=
    SEQUENCE {
        affirmedIpProtocolsBgpRouterSummaryEntryId INTEGER,
        affirmedIpProtocolsBgpRouterSummaryOutput String
    }

affirmedIpProtocolsBgpRouterSummaryEntryId OBJECT-TYPE
    SYNTAX      INTEGER {entry(0)}
    MAX-ACCESS  not-accessible
    STATUS      current
    DESCRIPTION ""
    ::= { affirmedIpProtocolsBgpRouterSummaryEntry 1 }

affirmedIpProtocolsBgpRouterSummaryOutput OBJECT-TYPE
    SYNTAX      String
    MAX-ACCESS  read-only
    STATUS      current
    DESCRIPTION ""
    ::= { affirmedIpProtocolsBgpRouterSummaryEntry 2 }

affirmedIpProtocolsBgpRouterPolicyRouteMapShowTable OBJECT-TYPE
    SYNTAX      SEQUENCE OF AffirmedIpProtocolsBgpRouterPolicyRouteMapShowEntry
    MAX-ACCESS  not-accessible
    STATUS      deprecated
    DESCRIPTION ""
    ::= { affirmedIpProtocolsBgp 11 }

affirmedIpProtocolsBgpRouterPolicyRouteMapShowEntry OBJECT-TYPE
    SYNTAX      AffirmedIpProtocolsBgpRouterPolicyRouteMapShowEntry
    MAX-ACCESS  not-accessible
    STATUS      deprecated
    DESCRIPTION ""
    INDEX { affirmedIpProtocolsBgpRouterNetworkContext, affirmedIpProtocolsBgpRouterPolicyRouteMapShowEntryId }
        ::= { affirmedIpProtocolsBgpRouterPolicyRouteMapShowTable 1 }

AffirmedIpProtocolsBgpRouterPolicyRouteMapShowEntry ::=
    SEQUENCE {
        affirmedIpProtocolsBgpRouterPolicyRouteMapShowEntryId INTEGER,
        affirmedIpProtocolsBgpRouterPolicyRouteMapShowOutput String
    }

affirmedIpProtocolsBgpRouterPolicyRouteMapShowEntryId OBJECT-TYPE
    SYNTAX      INTEGER {entry(0)}
    MAX-ACCESS  not-accessible
    STATUS      current
    DESCRIPTION ""
    ::= { affirmedIpProtocolsBgpRouterPolicyRouteMapShowEntry 1 }

affirmedIpProtocolsBgpRouterPolicyRouteMapShowOutput OBJECT-TYPE
    SYNTAX      String
    MAX-ACCESS  read-only
    STATUS      current
    DESCRIPTION ""
    ::= { affirmedIpProtocolsBgpRouterPolicyRouteMapShowEntry 2 }

affirmedIpProtocolsBgpRouterPolicyAccessListShowTable OBJECT-TYPE
    SYNTAX      SEQUENCE OF AffirmedIpProtocolsBgpRouterPolicyAccessListShowEntry
    MAX-ACCESS  not-accessible
    STATUS      deprecated
    DESCRIPTION ""
    ::= { affirmedIpProtocolsBgp 12 }

affirmedIpProtocolsBgpRouterPolicyAccessListShowEntry OBJECT-TYPE
    SYNTAX      AffirmedIpProtocolsBgpRouterPolicyAccessListShowEntry
    MAX-ACCESS  not-accessible
    STATUS      deprecated
    DESCRIPTION ""
    INDEX { affirmedIpProtocolsBgpRouterNetworkContext, affirmedIpProtocolsBgpRouterPolicyAccessListShowEntryId }
        ::= { affirmedIpProtocolsBgpRouterPolicyAccessListShowTable 1 }

AffirmedIpProtocolsBgpRouterPolicyAccessListShowEntry ::=
    SEQUENCE {
        affirmedIpProtocolsBgpRouterPolicyAccessListShowEntryId INTEGER,
        affirmedIpProtocolsBgpRouterPolicyAccessListShowOutput String
    }

affirmedIpProtocolsBgpRouterPolicyAccessListShowEntryId OBJECT-TYPE
    SYNTAX      INTEGER {entry(0)}
    MAX-ACCESS  not-accessible
    STATUS      current
    DESCRIPTION ""
    ::= { affirmedIpProtocolsBgpRouterPolicyAccessListShowEntry 1 }

affirmedIpProtocolsBgpRouterPolicyAccessListShowOutput OBJECT-TYPE
    SYNTAX      String
    MAX-ACCESS  read-only
    STATUS      current
    DESCRIPTION ""
    ::= { affirmedIpProtocolsBgpRouterPolicyAccessListShowEntry 2 }

affirmedIpProtocolsBgpRouterPolicyPrefixListShowTable OBJECT-TYPE
    SYNTAX      SEQUENCE OF AffirmedIpProtocolsBgpRouterPolicyPrefixListShowEntry
    MAX-ACCESS  not-accessible
    STATUS      deprecated
    DESCRIPTION "Show Configured Prefix Lists"
    ::= { affirmedIpProtocolsBgp 13 }

affirmedIpProtocolsBgpRouterPolicyPrefixListShowEntry OBJECT-TYPE
    SYNTAX      AffirmedIpProtocolsBgpRouterPolicyPrefixListShowEntry
    MAX-ACCESS  not-accessible
    STATUS      deprecated
    DESCRIPTION ""
    INDEX { affirmedIpProtocolsBgpRouterNetworkContext, affirmedIpProtocolsBgpRouterPolicyPrefixListShowEntryId }
        ::= { affirmedIpProtocolsBgpRouterPolicyPrefixListShowTable 1 }

AffirmedIpProtocolsBgpRouterPolicyPrefixListShowEntry ::=
    SEQUENCE {
        affirmedIpProtocolsBgpRouterPolicyPrefixListShowEntryId INTEGER,
        affirmedIpProtocolsBgpRouterPolicyPrefixListShowOutput String
    }

affirmedIpProtocolsBgpRouterPolicyPrefixListShowEntryId OBJECT-TYPE
    SYNTAX      INTEGER {entry(0)}
    MAX-ACCESS  not-accessible
    STATUS      current
    DESCRIPTION ""
    ::= { affirmedIpProtocolsBgpRouterPolicyPrefixListShowEntry 1 }

affirmedIpProtocolsBgpRouterPolicyPrefixListShowOutput OBJECT-TYPE
    SYNTAX      String
    MAX-ACCESS  read-only
    STATUS      current
    DESCRIPTION ""
    ::= { affirmedIpProtocolsBgpRouterPolicyPrefixListShowEntry 2 }

affirmedIpProtocolsBgpRouterPolicyPrefixListIPv6ShowTable OBJECT-TYPE
    SYNTAX      SEQUENCE OF AffirmedIpProtocolsBgpRouterPolicyPrefixListIPv6ShowEntry
    MAX-ACCESS  not-accessible
    STATUS      deprecated
    DESCRIPTION "Show Configured IPV6 Prefix Lists"
    ::= { affirmedIpProtocolsBgp 14 }

affirmedIpProtocolsBgpRouterPolicyPrefixListIPv6ShowEntry OBJECT-TYPE
    SYNTAX      AffirmedIpProtocolsBgpRouterPolicyPrefixListIPv6ShowEntry
    MAX-ACCESS  not-accessible
    STATUS      deprecated
    DESCRIPTION ""
    INDEX { affirmedIpProtocolsBgpRouterNetworkContext, affirmedIpProtocolsBgpRouterPolicyPrefixListIPv6ShowEntryId }
        ::= { affirmedIpProtocolsBgpRouterPolicyPrefixListIPv6ShowTable 1 }

AffirmedIpProtocolsBgpRouterPolicyPrefixListIPv6ShowEntry ::=
    SEQUENCE {
        affirmedIpProtocolsBgpRouterPolicyPrefixListIPv6ShowEntryId INTEGER,
        affirmedIpProtocolsBgpRouterPolicyPrefixListIPv6ShowOutput String
    }

affirmedIpProtocolsBgpRouterPolicyPrefixListIPv6ShowEntryId OBJECT-TYPE
    SYNTAX      INTEGER {entry(0)}
    MAX-ACCESS  not-accessible
    STATUS      current
    DESCRIPTION ""
    ::= { affirmedIpProtocolsBgpRouterPolicyPrefixListIPv6ShowEntry 1 }

affirmedIpProtocolsBgpRouterPolicyPrefixListIPv6ShowOutput OBJECT-TYPE
    SYNTAX      String
    MAX-ACCESS  read-only
    STATUS      current
    DESCRIPTION ""
    ::= { affirmedIpProtocolsBgpRouterPolicyPrefixListIPv6ShowEntry 2 }

affirmedIpProtocolsBgpRouterPolicyCommunityListShowTable OBJECT-TYPE
    SYNTAX      SEQUENCE OF AffirmedIpProtocolsBgpRouterPolicyCommunityListShowEntry
    MAX-ACCESS  not-accessible
    STATUS      deprecated
    DESCRIPTION "Show Configured Community Lists"
    ::= { affirmedIpProtocolsBgp 15 }

affirmedIpProtocolsBgpRouterPolicyCommunityListShowEntry OBJECT-TYPE
    SYNTAX      AffirmedIpProtocolsBgpRouterPolicyCommunityListShowEntry
    MAX-ACCESS  not-accessible
    STATUS      deprecated
    DESCRIPTION ""
    INDEX { affirmedIpProtocolsBgpRouterNetworkContext, affirmedIpProtocolsBgpRouterPolicyCommunityListShowEntryId }
        ::= { affirmedIpProtocolsBgpRouterPolicyCommunityListShowTable 1 }

AffirmedIpProtocolsBgpRouterPolicyCommunityListShowEntry ::=
    SEQUENCE {
        affirmedIpProtocolsBgpRouterPolicyCommunityListShowEntryId INTEGER,
        affirmedIpProtocolsBgpRouterPolicyCommunityListShowOutput String
    }

affirmedIpProtocolsBgpRouterPolicyCommunityListShowEntryId OBJECT-TYPE
    SYNTAX      INTEGER {entry(0)}
    MAX-ACCESS  not-accessible
    STATUS      current
    DESCRIPTION ""
    ::= { affirmedIpProtocolsBgpRouterPolicyCommunityListShowEntry 1 }

affirmedIpProtocolsBgpRouterPolicyCommunityListShowOutput OBJECT-TYPE
    SYNTAX      String
    MAX-ACCESS  read-only
    STATUS      current
    DESCRIPTION ""
    ::= { affirmedIpProtocolsBgpRouterPolicyCommunityListShowEntry 2 }

affirmedIpProtocolsBgpRouterPolicyAsPathListShowTable OBJECT-TYPE
    SYNTAX      SEQUENCE OF AffirmedIpProtocolsBgpRouterPolicyAsPathListShowEntry
    MAX-ACCESS  not-accessible
    STATUS      deprecated
    DESCRIPTION "Show Configured ASPath Lists"
    ::= { affirmedIpProtocolsBgp 16 }

affirmedIpProtocolsBgpRouterPolicyAsPathListShowEntry OBJECT-TYPE
    SYNTAX      AffirmedIpProtocolsBgpRouterPolicyAsPathListShowEntry
    MAX-ACCESS  not-accessible
    STATUS      deprecated
    DESCRIPTION ""
    INDEX { affirmedIpProtocolsBgpRouterNetworkContext, affirmedIpProtocolsBgpRouterPolicyAsPathListShowEntryId }
        ::= { affirmedIpProtocolsBgpRouterPolicyAsPathListShowTable 1 }

AffirmedIpProtocolsBgpRouterPolicyAsPathListShowEntry ::=
    SEQUENCE {
        affirmedIpProtocolsBgpRouterPolicyAsPathListShowEntryId INTEGER,
        affirmedIpProtocolsBgpRouterPolicyAsPathListShowOutput String
    }

affirmedIpProtocolsBgpRouterPolicyAsPathListShowEntryId OBJECT-TYPE
    SYNTAX      INTEGER {entry(0)}
    MAX-ACCESS  not-accessible
    STATUS      current
    DESCRIPTION ""
    ::= { affirmedIpProtocolsBgpRouterPolicyAsPathListShowEntry 1 }

affirmedIpProtocolsBgpRouterPolicyAsPathListShowOutput OBJECT-TYPE
    SYNTAX      String
    MAX-ACCESS  read-only
    STATUS      current
    DESCRIPTION ""
    ::= { affirmedIpProtocolsBgpRouterPolicyAsPathListShowEntry 2 }

affirmedIpProtocolsBgpRouterIpv4UcastSummaryTable OBJECT-TYPE
    SYNTAX      SEQUENCE OF AffirmedIpProtocolsBgpRouterIpv4UcastSummaryEntry
    MAX-ACCESS  not-accessible
    STATUS      deprecated
    DESCRIPTION ""
    ::= { affirmedIpProtocolsBgp 3 }

affirmedIpProtocolsBgpRouterIpv4UcastSummaryEntry OBJECT-TYPE
    SYNTAX      AffirmedIpProtocolsBgpRouterIpv4UcastSummaryEntry
    MAX-ACCESS  not-accessible
    STATUS      deprecated
    DESCRIPTION ""
    INDEX { affirmedIpProtocolsBgpRouterNetworkContext, affirmedIpProtocolsBgpRouterIpv4UcastSummaryEntryId }
        ::= { affirmedIpProtocolsBgpRouterIpv4UcastSummaryTable 1 }

AffirmedIpProtocolsBgpRouterIpv4UcastSummaryEntry ::=
    SEQUENCE {
        affirmedIpProtocolsBgpRouterIpv4UcastSummaryEntryId INTEGER,
        affirmedIpProtocolsBgpRouterIpv4UcastSummaryOutput String
    }

affirmedIpProtocolsBgpRouterIpv4UcastSummaryEntryId OBJECT-TYPE
    SYNTAX      INTEGER {entry(0)}
    MAX-ACCESS  not-accessible
    STATUS      current
    DESCRIPTION ""
    ::= { affirmedIpProtocolsBgpRouterIpv4UcastSummaryEntry 1 }

affirmedIpProtocolsBgpRouterIpv4UcastSummaryOutput OBJECT-TYPE
    SYNTAX      String
    MAX-ACCESS  read-only
    STATUS      current
    DESCRIPTION ""
    ::= { affirmedIpProtocolsBgpRouterIpv4UcastSummaryEntry 2 }

affirmedIpProtocolsBgpRouterIpv4UcastRouteDetailTable OBJECT-TYPE
    SYNTAX      SEQUENCE OF AffirmedIpProtocolsBgpRouterIpv4UcastRouteDetailEntry
    MAX-ACCESS  not-accessible
    STATUS      current
    DESCRIPTION ""
    ::= { affirmedIpProtocolsBgp 4 }

affirmedIpProtocolsBgpRouterIpv4UcastRouteDetailEntry OBJECT-TYPE
    SYNTAX      AffirmedIpProtocolsBgpRouterIpv4UcastRouteDetailEntry
    MAX-ACCESS  not-accessible
    STATUS      current
    DESCRIPTION ""
    INDEX { affirmedIpProtocolsBgpRouterNetworkContext, affirmedIpProtocolsBgpRouterIpv4UcastRouteDetailPrefix, affirmedIpProtocolsBgpRouterIpv4UcastRouteDetailPrefixLength }
        ::= { affirmedIpProtocolsBgpRouterIpv4UcastRouteDetailTable 1 }

AffirmedIpProtocolsBgpRouterIpv4UcastRouteDetailEntry ::=
    SEQUENCE {
        affirmedIpProtocolsBgpRouterIpv4UcastRouteDetailPrefix String,
        affirmedIpProtocolsBgpRouterIpv4UcastRouteDetailPrefixLength Unsigned32,
        affirmedIpProtocolsBgpRouterIpv4UcastRouteDetailOutput String
    }

affirmedIpProtocolsBgpRouterIpv4UcastRouteDetailPrefix OBJECT-TYPE
    SYNTAX      String
    MAX-ACCESS  not-accessible
    STATUS      current
    DESCRIPTION "IPv4 prefix (A.B.C.D)"
    ::= { affirmedIpProtocolsBgpRouterIpv4UcastRouteDetailEntry 1 }

affirmedIpProtocolsBgpRouterIpv4UcastRouteDetailPrefixLength OBJECT-TYPE
    SYNTAX      Unsigned32
    MAX-ACCESS  not-accessible
    STATUS      current
    DESCRIPTION "Prefix length"
    ::= { affirmedIpProtocolsBgpRouterIpv4UcastRouteDetailEntry 2 }

affirmedIpProtocolsBgpRouterIpv4UcastRouteDetailOutput OBJECT-TYPE
    SYNTAX      String
    MAX-ACCESS  read-only
    STATUS      current
    DESCRIPTION ""
    ::= { affirmedIpProtocolsBgpRouterIpv4UcastRouteDetailEntry 3 }

affirmedIpProtocolsBgpRouterIpv4UcastRouteDampeningTable OBJECT-TYPE
    SYNTAX      SEQUENCE OF AffirmedIpProtocolsBgpRouterIpv4UcastRouteDampeningEntry
    MAX-ACCESS  not-accessible
    STATUS      current
    DESCRIPTION ""
    ::= { affirmedIpProtocolsBgp 5 }

affirmedIpProtocolsBgpRouterIpv4UcastRouteDampeningEntry OBJECT-TYPE
    SYNTAX      AffirmedIpProtocolsBgpRouterIpv4UcastRouteDampeningEntry
    MAX-ACCESS  not-accessible
    STATUS      current
    DESCRIPTION ""
    INDEX { affirmedIpProtocolsBgpRouterNetworkContext, affirmedIpProtocolsBgpRouterIpv4UcastRouteDampeningAction }
        ::= { affirmedIpProtocolsBgpRouterIpv4UcastRouteDampeningTable 1 }

AffirmedIpProtocolsBgpRouterIpv4UcastRouteDampeningEntry ::=
    SEQUENCE {
        affirmedIpProtocolsBgpRouterIpv4UcastRouteDampeningAction INTEGER,
        affirmedIpProtocolsBgpRouterIpv4UcastRouteDampeningOutput String
    }

affirmedIpProtocolsBgpRouterIpv4UcastRouteDampeningAction OBJECT-TYPE
    SYNTAX      INTEGER {dampened-paths(0),flap-statistics(1),parameters(2)}
    MAX-ACCESS  not-accessible
    STATUS      current
    DESCRIPTION ""
    ::= { affirmedIpProtocolsBgpRouterIpv4UcastRouteDampeningEntry 1 }

affirmedIpProtocolsBgpRouterIpv4UcastRouteDampeningOutput OBJECT-TYPE
    SYNTAX      String
    MAX-ACCESS  read-only
    STATUS      current
    DESCRIPTION ""
    ::= { affirmedIpProtocolsBgpRouterIpv4UcastRouteDampeningEntry 2 }

affirmedIpProtocolsBgpRouterIpv6UcastSummaryTable OBJECT-TYPE
    SYNTAX      SEQUENCE OF AffirmedIpProtocolsBgpRouterIpv6UcastSummaryEntry
    MAX-ACCESS  not-accessible
    STATUS      deprecated
    DESCRIPTION ""
    ::= { affirmedIpProtocolsBgp 6 }

affirmedIpProtocolsBgpRouterIpv6UcastSummaryEntry OBJECT-TYPE
    SYNTAX      AffirmedIpProtocolsBgpRouterIpv6UcastSummaryEntry
    MAX-ACCESS  not-accessible
    STATUS      deprecated
    DESCRIPTION ""
    INDEX { affirmedIpProtocolsBgpRouterNetworkContext, affirmedIpProtocolsBgpRouterIpv6UcastSummaryEntryId }
        ::= { affirmedIpProtocolsBgpRouterIpv6UcastSummaryTable 1 }

AffirmedIpProtocolsBgpRouterIpv6UcastSummaryEntry ::=
    SEQUENCE {
        affirmedIpProtocolsBgpRouterIpv6UcastSummaryEntryId INTEGER,
        affirmedIpProtocolsBgpRouterIpv6UcastSummaryOutput String
    }

affirmedIpProtocolsBgpRouterIpv6UcastSummaryEntryId OBJECT-TYPE
    SYNTAX      INTEGER {entry(0)}
    MAX-ACCESS  not-accessible
    STATUS      current
    DESCRIPTION ""
    ::= { affirmedIpProtocolsBgpRouterIpv6UcastSummaryEntry 1 }

affirmedIpProtocolsBgpRouterIpv6UcastSummaryOutput OBJECT-TYPE
    SYNTAX      String
    MAX-ACCESS  read-only
    STATUS      current
    DESCRIPTION ""
    ::= { affirmedIpProtocolsBgpRouterIpv6UcastSummaryEntry 2 }

affirmedIpProtocolsBgpRouterIpv6UcastRouteDetailTable OBJECT-TYPE
    SYNTAX      SEQUENCE OF AffirmedIpProtocolsBgpRouterIpv6UcastRouteDetailEntry
    MAX-ACCESS  not-accessible
    STATUS      current
    DESCRIPTION ""
    ::= { affirmedIpProtocolsBgp 7 }

affirmedIpProtocolsBgpRouterIpv6UcastRouteDetailEntry OBJECT-TYPE
    SYNTAX      AffirmedIpProtocolsBgpRouterIpv6UcastRouteDetailEntry
    MAX-ACCESS  not-accessible
    STATUS      current
    DESCRIPTION ""
    INDEX { affirmedIpProtocolsBgpRouterNetworkContext, affirmedIpProtocolsBgpRouterIpv6UcastRouteDetailPrefix, affirmedIpProtocolsBgpRouterIpv6UcastRouteDetailPrefixLength }
        ::= { affirmedIpProtocolsBgpRouterIpv6UcastRouteDetailTable 1 }

AffirmedIpProtocolsBgpRouterIpv6UcastRouteDetailEntry ::=
    SEQUENCE {
        affirmedIpProtocolsBgpRouterIpv6UcastRouteDetailPrefix String,
        affirmedIpProtocolsBgpRouterIpv6UcastRouteDetailPrefixLength Unsigned32,
        affirmedIpProtocolsBgpRouterIpv6UcastRouteDetailOutput String
    }

affirmedIpProtocolsBgpRouterIpv6UcastRouteDetailPrefix OBJECT-TYPE
    SYNTAX      String
    MAX-ACCESS  not-accessible
    STATUS      current
    DESCRIPTION "IPv6 prefix"
    ::= { affirmedIpProtocolsBgpRouterIpv6UcastRouteDetailEntry 1 }

affirmedIpProtocolsBgpRouterIpv6UcastRouteDetailPrefixLength OBJECT-TYPE
    SYNTAX      Unsigned32
    MAX-ACCESS  not-accessible
    STATUS      current
    DESCRIPTION "IPv6 prefix length"
    ::= { affirmedIpProtocolsBgpRouterIpv6UcastRouteDetailEntry 2 }

affirmedIpProtocolsBgpRouterIpv6UcastRouteDetailOutput OBJECT-TYPE
    SYNTAX      String
    MAX-ACCESS  read-only
    STATUS      current
    DESCRIPTION ""
    ::= { affirmedIpProtocolsBgpRouterIpv6UcastRouteDetailEntry 3 }

affirmedIpProtocolsBgpRouterIpv6UcastRouteDampeningTable OBJECT-TYPE
    SYNTAX      SEQUENCE OF AffirmedIpProtocolsBgpRouterIpv6UcastRouteDampeningEntry
    MAX-ACCESS  not-accessible
    STATUS      current
    DESCRIPTION ""
    ::= { affirmedIpProtocolsBgp 8 }

affirmedIpProtocolsBgpRouterIpv6UcastRouteDampeningEntry OBJECT-TYPE
    SYNTAX      AffirmedIpProtocolsBgpRouterIpv6UcastRouteDampeningEntry
    MAX-ACCESS  not-accessible
    STATUS      current
    DESCRIPTION ""
    INDEX { affirmedIpProtocolsBgpRouterNetworkContext, affirmedIpProtocolsBgpRouterIpv6UcastRouteDampeningAction }
        ::= { affirmedIpProtocolsBgpRouterIpv6UcastRouteDampeningTable 1 }

AffirmedIpProtocolsBgpRouterIpv6UcastRouteDampeningEntry ::=
    SEQUENCE {
        affirmedIpProtocolsBgpRouterIpv6UcastRouteDampeningAction INTEGER,
        affirmedIpProtocolsBgpRouterIpv6UcastRouteDampeningOutput String
    }

affirmedIpProtocolsBgpRouterIpv6UcastRouteDampeningAction OBJECT-TYPE
    SYNTAX      INTEGER {dampened-paths(0),flap-statistics(1),parameters(2)}
    MAX-ACCESS  not-accessible
    STATUS      current
    DESCRIPTION ""
    ::= { affirmedIpProtocolsBgpRouterIpv6UcastRouteDampeningEntry 1 }

affirmedIpProtocolsBgpRouterIpv6UcastRouteDampeningOutput OBJECT-TYPE
    SYNTAX      String
    MAX-ACCESS  read-only
    STATUS      current
    DESCRIPTION ""
    ::= { affirmedIpProtocolsBgpRouterIpv6UcastRouteDampeningEntry 2 }

affirmedIpProtocolsBgpRouterNeighborTable OBJECT-TYPE
    SYNTAX      SEQUENCE OF AffirmedIpProtocolsBgpRouterNeighborEntry
    MAX-ACCESS  not-accessible
    STATUS      current
    DESCRIPTION ""
    ::= { affirmedIpProtocolsBgp 9 }

affirmedIpProtocolsBgpRouterNeighborEntry OBJECT-TYPE
    SYNTAX      AffirmedIpProtocolsBgpRouterNeighborEntry
    MAX-ACCESS  not-accessible
    STATUS      current
    DESCRIPTION ""
    INDEX { affirmedIpProtocolsBgpRouterNetworkContext, affirmedIpProtocolsBgpRouterNeighborPeeringName }
        ::= { affirmedIpProtocolsBgpRouterNeighborTable 1 }

AffirmedIpProtocolsBgpRouterNeighborEntry ::=
    SEQUENCE {
        affirmedIpProtocolsBgpRouterNeighborPeeringName String,
        affirmedIpProtocolsBgpRouterNeighborRowstatus RowStatus
    }

affirmedIpProtocolsBgpRouterNeighborPeeringName OBJECT-TYPE
    SYNTAX      String
    MAX-ACCESS  not-accessible
    STATUS      current
    DESCRIPTION "Name of the peering"
    ::= { affirmedIpProtocolsBgpRouterNeighborEntry 1 }

affirmedIpProtocolsBgpRouterNeighborRowstatus OBJECT-TYPE
    SYNTAX      RowStatus
    MAX-ACCESS  read-create
    STATUS      current
    DESCRIPTION ""
    ::= { affirmedIpProtocolsBgpRouterNeighborEntry 2 }

affirmedIpProtocolsBgpRouterNeighborDetailTable OBJECT-TYPE
    SYNTAX      SEQUENCE OF AffirmedIpProtocolsBgpRouterNeighborDetailEntry
    MAX-ACCESS  not-accessible
    STATUS      deprecated
    DESCRIPTION ""
    ::= { affirmedIpProtocolsBgp 10 }

affirmedIpProtocolsBgpRouterNeighborDetailEntry OBJECT-TYPE
    SYNTAX      AffirmedIpProtocolsBgpRouterNeighborDetailEntry
    MAX-ACCESS  not-accessible
    STATUS      deprecated
    DESCRIPTION ""
    INDEX { affirmedIpProtocolsBgpRouterNetworkContext, affirmedIpProtocolsBgpRouterNeighborPeeringName, affirmedIpProtocolsBgpRouterNeighborDetailEntryId }
        ::= { affirmedIpProtocolsBgpRouterNeighborDetailTable 1 }

AffirmedIpProtocolsBgpRouterNeighborDetailEntry ::=
    SEQUENCE {
        affirmedIpProtocolsBgpRouterNeighborDetailEntryId INTEGER,
        affirmedIpProtocolsBgpRouterNeighborDetailOutput String
    }

affirmedIpProtocolsBgpRouterNeighborDetailEntryId OBJECT-TYPE
    SYNTAX      INTEGER {entry(0)}
    MAX-ACCESS  not-accessible
    STATUS      current
    DESCRIPTION ""
    ::= { affirmedIpProtocolsBgpRouterNeighborDetailEntry 1 }

affirmedIpProtocolsBgpRouterNeighborDetailOutput OBJECT-TYPE
    SYNTAX      String
    MAX-ACCESS  read-only
    STATUS      current
    DESCRIPTION ""
    ::= { affirmedIpProtocolsBgpRouterNeighborDetailEntry 2 }

END

AFFIRMED-LICENSE-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedLicenseMIB MODULE-IDENTITY
    ORGANIZATION "Affirmed Networks, Inc."
    CONTACT-INFO "Affirmed Networks, Inc. 35 Nagog Park, Acton, MA, USA"
    DESCRIPTION ""
    ::= { 1 3 6 1 4 1 37963 10 24 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedLicense OBJECT IDENTIFIER ::= { affirmedLicenseMIB 1 }

affirmedLicensePls-statusTable OBJECT-TYPE
    SYNTAX      SEQUENCE OF AffirmedLicensePls-statusEntry
    MAX-ACCESS  not-accessible
    STATUS      current
    DESCRIPTION ""
    ::= { affirmedLicense 1 }

affirmedLicensePls-statusEntry OBJECT-TYPE
    SYNTAX      AffirmedLicensePls-statusEntry
    MAX-ACCESS  not-accessible
    STATUS      current
    DESCRIPTION ""
    INDEX { affirmedLicensePls-statusIp-address }
        ::= { affirmedLicensePls-statusTable 1 }

AffirmedLicensePls-statusEntry ::=
    SEQUENCE {
        affirmedLicensePls-statusIp-address String,
        affirmedLicensePls-statusVersion String,
        affirmedLicensePls-statusMode String,
        affirmedLicensePls-statusState String,
        affirmedLicensePls-statusTime String,
        affirmedLicensePls-statusLock-criteria String,
        affirmedLicensePls-statusFingerprint String,
        affirmedLicensePls-statusManagement-entity String,
        affirmedLicensePls-statusManagement-state INTEGER
    }

affirmedLicensePls-statusIp-address OBJECT-TYPE
    SYNTAX      String
    MAX-ACCESS  not-accessible
    STATUS      current
    DESCRIPTION "IP Address"
    ::= { affirmedLicensePls-statusEntry 1 }

affirmedLicensePls-statusVersion OBJECT-TYPE
    SYNTAX      String
    MAX-ACCESS  read-only
    STATUS      current
    DESCRIPTION "PLS version"
    ::= { affirmedLicensePls-statusEntry 2 }

affirmedLicensePls-statusMode OBJECT-TYPE
    SYNTAX      String
    MAX-ACCESS  read-only
    STATUS      current
    DESCRIPTION "Mode of PLS"
    ::= { affirmedLicensePls-statusEntry 3 }

affirmedLicensePls-statusState OBJECT-TYPE
    SYNTAX      String
    MAX-ACCESS  read-only
    STATUS      current
    DESCRIPTION "State of PLS"
    ::= { affirmedLicensePls-statusEntry 4 }

affirmedLicensePls-statusTime OBJECT-TYPE
    SYNTAX      String
    MAX-ACCESS  read-only
    STATUS      current
    DESCRIPTION "PLS Time"
    ::= { affirmedLicensePls-statusEntry 5 }

affirmedLicensePls-statusLock-criteria OBJECT-TYPE
    SYNTAX      String
    MAX-ACCESS  read-only
    STATUS      current
    DESCRIPTION "Lock criteria"
    ::= { affirmedLicensePls-statusEntry 6 }

affirmedLicensePls-statusFingerprint OBJECT-TYPE
    SYNTAX      String
    MAX-ACCESS  read-only
    STATUS      current
    DESCRIPTION "Lock code"
    ::= { affirmedLicensePls-statusEntry 7 }

affirmedLicensePls-statusManagement-entity OBJECT-TYPE
    SYNTAX      String
    MAX-ACCESS  read-only
    STATUS      current
    DESCRIPTION "Managed entity IP Address"
    ::= { affirmedLicensePls-statusEntry 8 }

affirmedLicensePls-statusManagement-state OBJECT-TYPE
    SYNTAX      INTEGER {discovered(1),undiscovered(2)}
    MAX-ACCESS  read-only
    STATUS      current
    DESCRIPTION "Managed State"
    ::= { affirmedLicensePls-statusEntry 9 }

affirmedLicenseLm-statusTable OBJECT-TYPE
    SYNTAX      SEQUENCE OF AffirmedLicenseLm-statusEntry
    MAX-ACCESS  not-accessible
    STATUS      current
    DESCRIPTION ""
    ::= { affirmedLicense 2 }

affirmedLicenseLm-statusEntry OBJECT-TYPE
    SYNTAX      AffirmedLicenseLm-statusEntry
    MAX-ACCESS  not-accessible
    STATUS      current
    DESCRIPTION ""
    INDEX { affirmedLicenseLm-statusEntryId }
        ::= { affirmedLicenseLm-statusTable 1 }

AffirmedLicenseLm-statusEntry ::=
    SEQUENCE {
        affirmedLicenseLm-statusEntryId INTEGER,
        affirmedLicenseLm-statusState String,
        affirmedLicenseLm-statusCurrent-pls String,
        affirmedLicenseLm-statusManagement-entity String
    }

affirmedLicenseLm-statusEntryId OBJECT-TYPE
    SYNTAX      INTEGER {entry(0)}
    MAX-ACCESS  not-accessible
    STATUS      current
    DESCRIPTION ""
    ::= { affirmedLicenseLm-statusEntry 1 }

affirmedLicenseLm-statusState OBJECT-TYPE
    SYNTAX      String
    MAX-ACCESS  read-only
    STATUS      current
    DESCRIPTION "State of License Manager"
    ::= { affirmedLicenseLm-statusEntry 2 }

affirmedLicenseLm-statusCurrent-pls OBJECT-TYPE
    SYNTAX      String
    MAX-ACCESS  read-only
    STATUS      current
    DESCRIPTION "Current PLS"
    ::= { affirmedLicenseLm-statusEntry 3 }

affirmedLicenseLm-statusManagement-entity OBJECT-TYPE
    SYNTAX      String
    MAX-ACCESS  read-only
    STATUS      current
    DESCRIPTION "Current PLS"
    ::= { affirmedLicenseLm-statusEntry 4 }

affirmedLicenseServices-statusTable OBJECT-TYPE
    SYNTAX      SEQUENCE OF AffirmedLicenseServices-statusEntry
    MAX-ACCESS  not-accessible
    STATUS      current
    DESCRIPTION ""
    ::= { affirmedLicense 3 }

affirmedLicenseServices-statusEntry OBJECT-TYPE
    SYNTAX      AffirmedLicenseServices-statusEntry
    MAX-ACCESS  not-accessible
    STATUS      current
    DESCRIPTION ""
    INDEX { affirmedLicenseServices-statusFeature, affirmedLicenseServices-statusVersion }
        ::= { affirmedLicenseServices-statusTable 1 }

AffirmedLicenseServices-statusEntry ::=
    SEQUENCE {
        affirmedLicenseServices-statusFeature String,
        affirmedLicenseServices-statusVersion String,
        affirmedLicenseServices-statusSoft-limit Integer32,
        affirmedLicenseServices-statusUnit-size String,
        affirmedLicenseServices-statusStat-value ConfdString,
        affirmedLicenseServices-statusConsumed Integer32,
        affirmedLicenseServices-statusTotal-consumed Integer32,
        affirmedLicenseServices-statusLicense-state String,
        affirmedLicenseServices-statusType String,
        affirmedLicenseServices-statusSoftLimitStr String,
        affirmedLicenseServices-statusExpiration String
    }

affirmedLicenseServices-statusFeature OBJECT-TYPE
    SYNTAX      String
    MAX-ACCESS  not-accessible
    STATUS      current
    DESCRIPTION "licensable feature"
    ::= { affirmedLicenseServices-statusEntry 1 }

affirmedLicenseServices-statusVersion OBJECT-TYPE
    SYNTAX      String
    MAX-ACCESS  not-accessible
    STATUS      current
    DESCRIPTION "licensable version"
    ::= { affirmedLicenseServices-statusEntry 2 }

affirmedLicenseServices-statusSoft-limit OBJECT-TYPE
    SYNTAX      Integer32
    MAX-ACCESS  read-only
    STATUS      current
    DESCRIPTION "Soft limit slices for license"
    ::= { affirmedLicenseServices-statusEntry 3 }

affirmedLicenseServices-statusUnit-size OBJECT-TYPE
    SYNTAX      String
    MAX-ACCESS  read-only
    STATUS      current
    DESCRIPTION "Slice size multiplier"
    ::= { affirmedLicenseServices-statusEntry 4 }

affirmedLicenseServices-statusStat-value OBJECT-TYPE
    SYNTAX      ConfdString
    MAX-ACCESS  read-only
    STATUS      current
    DESCRIPTION "Current value of stat"
    ::= { affirmedLicenseServices-statusEntry 5 }

affirmedLicenseServices-statusConsumed OBJECT-TYPE
    SYNTAX      Integer32
    MAX-ACCESS  read-only
    STATUS      current
    DESCRIPTION "Number of slices held by local MCC"
    ::= { affirmedLicenseServices-statusEntry 6 }

affirmedLicenseServices-statusTotal-consumed OBJECT-TYPE
    SYNTAX      Integer32
    MAX-ACCESS  read-only
    STATUS      current
    DESCRIPTION "Number of slices held by all MCCs"
    ::= { affirmedLicenseServices-statusEntry 7 }

affirmedLicenseServices-statusLicense-state OBJECT-TYPE
    SYNTAX      String
    MAX-ACCESS  read-only
    STATUS      current
    DESCRIPTION "State of the service"
    ::= { affirmedLicenseServices-statusEntry 8 }

affirmedLicenseServices-statusType OBJECT-TYPE
    SYNTAX      String
    MAX-ACCESS  read-only
    STATUS      current
    DESCRIPTION "licensable service type"
    ::= { affirmedLicenseServices-statusEntry 9 }

affirmedLicenseServices-statusSoftLimitStr OBJECT-TYPE
    SYNTAX      String
    MAX-ACCESS  read-only
    STATUS      current
    DESCRIPTION "Soft limit slices for license"
    ::= { affirmedLicenseServices-statusEntry 10 }

affirmedLicenseServices-statusExpiration OBJECT-TYPE
    SYNTAX      String
    MAX-ACCESS  read-only
    STATUS      current
    DESCRIPTION "License lifetime expiration date or trial days remaining"
    ::= { affirmedLicenseServices-statusEntry 11 }

affirmedLicenseDetail-statusTable OBJECT-TYPE
    SYNTAX      SEQUENCE OF AffirmedLicenseDetail-statusEntry
    MAX-ACCESS  not-accessible
    STATUS      current
    DESCRIPTION ""
    ::= { affirmedLicense 4 }

affirmedLicenseDetail-statusEntry OBJECT-TYPE
    SYNTAX      AffirmedLicenseDetail-statusEntry
    MAX-ACCESS  not-accessible
    STATUS      current
    DESCRIPTION ""
    INDEX { affirmedLicenseDetail-statusFeature, affirmedLicenseDetail-statusVersion, affirmedLicenseDetail-statusHash }
        ::= { affirmedLicenseDetail-statusTable 1 }

AffirmedLicenseDetail-statusEntry ::=
    SEQUENCE {
        affirmedLicenseDetail-statusFeature String,
        affirmedLicenseDetail-statusVersion String,
        affirmedLicenseDetail-statusHash String,
        affirmedLicenseDetail-statusSoftLimitStr String,
        affirmedLicenseDetail-statusStart-date String,
        affirmedLicenseDetail-statusEnd-date String,
        affirmedLicenseDetail-statusTrial-days String,
        affirmedLicenseDetail-statusState String
    }

affirmedLicenseDetail-statusFeature OBJECT-TYPE
    SYNTAX      String
    MAX-ACCESS  not-accessible
    STATUS      current
    DESCRIPTION "license feature"
    ::= { affirmedLicenseDetail-statusEntry 1 }

affirmedLicenseDetail-statusVersion OBJECT-TYPE
    SYNTAX      String
    MAX-ACCESS  not-accessible
    STATUS      current
    DESCRIPTION "license version"
    ::= { affirmedLicenseDetail-statusEntry 2 }

affirmedLicenseDetail-statusHash OBJECT-TYPE
    SYNTAX      String
    MAX-ACCESS  not-accessible
    STATUS      current
    DESCRIPTION "license hash"
    ::= { affirmedLicenseDetail-statusEntry 3 }

affirmedLicenseDetail-statusSoftLimitStr OBJECT-TYPE
    SYNTAX      String
    MAX-ACCESS  read-only
    STATUS      current
    DESCRIPTION "Soft limit slices for license"
    ::= { affirmedLicenseDetail-statusEntry 4 }

affirmedLicenseDetail-statusStart-date OBJECT-TYPE
    SYNTAX      String
    MAX-ACCESS  read-only
    STATUS      current
    DESCRIPTION "License start date"
    ::= { affirmedLicenseDetail-statusEntry 5 }

affirmedLicenseDetail-statusEnd-date OBJECT-TYPE
    SYNTAX      String
    MAX-ACCESS  read-only
    STATUS      current
    DESCRIPTION "License end date"
    ::= { affirmedLicenseDetail-statusEntry 6 }

affirmedLicenseDetail-statusTrial-days OBJECT-TYPE
    SYNTAX      String
    MAX-ACCESS  read-only
    STATUS      current
    DESCRIPTION "License trial dates remaining"
    ::= { affirmedLicenseDetail-statusEntry 7 }

affirmedLicenseDetail-statusState OBJECT-TYPE
    SYNTAX      String
    MAX-ACCESS  read-only
    STATUS      current
    DESCRIPTION "State of the license"
    ::= { affirmedLicenseDetail-statusEntry 8 }

END

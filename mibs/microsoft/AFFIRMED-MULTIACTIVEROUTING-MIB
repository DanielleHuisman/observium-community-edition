AFFIRMED-MULTIACTIVEROUTING-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedMultiactiveroutingMIB MODULE-IDENTITY
    ORGANIZATION "Affirmed Networks, Inc."
    CONTACT-INFO "Affirmed Networks, Inc. 35 Nagog Park, Acton, MA, USA"
    DESCRIPTION ""
    ::= { 1 3 6 1 4 1 37963 10 27 }

String ::= TEXTUAL-CONVENTION
    DISPLAY-HINT "1t"
    STATUS      current
    DESCRIPTION "xs:string"
    SYNTAX      OCTET STRING

affirmedMultiActiveRouting OBJECT IDENTIFIER ::= { affirmedMultiactiveroutingMIB 1 }

affirmedMultiActiveRoutingPeerAssignmentsTable OBJECT-TYPE
    SYNTAX      SEQUENCE OF AffirmedMultiActiveRoutingPeerAssignmentsEntry
    MAX-ACCESS  not-accessible
    STATUS      current
    DESCRIPTION ""
    ::= { affirmedMultiActiveRouting 1 }

affirmedMultiActiveRoutingPeerAssignmentsEntry OBJECT-TYPE
    SYNTAX      AffirmedMultiActiveRoutingPeerAssignmentsEntry
    MAX-ACCESS  not-accessible
    STATUS      current
    DESCRIPTION ""
    INDEX { affirmedMultiActiveRoutingPeerAssignmentsChassis, affirmedMultiActiveRoutingPeerAssignmentsSlot }
        ::= { affirmedMultiActiveRoutingPeerAssignmentsTable 1 }

AffirmedMultiActiveRoutingPeerAssignmentsEntry ::=
    SEQUENCE {
        affirmedMultiActiveRoutingPeerAssignmentsChassis Unsigned32,
        affirmedMultiActiveRoutingPeerAssignmentsSlot Unsigned32,
        affirmedMultiActiveRoutingPeerAssignmentsOutput String
    }

affirmedMultiActiveRoutingPeerAssignmentsChassis OBJECT-TYPE
    SYNTAX      Unsigned32
    MAX-ACCESS  not-accessible
    STATUS      current
    DESCRIPTION ""
    ::= { affirmedMultiActiveRoutingPeerAssignmentsEntry 1 }

affirmedMultiActiveRoutingPeerAssignmentsSlot OBJECT-TYPE
    SYNTAX      Unsigned32
    MAX-ACCESS  not-accessible
    STATUS      current
    DESCRIPTION ""
    ::= { affirmedMultiActiveRoutingPeerAssignmentsEntry 2 }

affirmedMultiActiveRoutingPeerAssignmentsOutput OBJECT-TYPE
    SYNTAX      String
    MAX-ACCESS  read-only
    STATUS      current
    DESCRIPTION ""
    ::= { affirmedMultiActiveRoutingPeerAssignmentsEntry 3 }

END

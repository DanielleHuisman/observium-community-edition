AFFIRMED-NETWORKCONTEXT-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedNetworkcontextMIB MODULE-IDENTITY
    ORGANIZATION "Affirmed Networks, Inc."
    CONTACT-INFO "Affirmed Networks, Inc. 35 Nagog Park, Acton, MA, USA"
    DESCRIPTION ""
    ::= { 1 3 6 1 4 1 37963 10 4 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedNetworkContextTable OBJECT-TYPE
    SYNTAX      SEQUENCE OF AffirmedNetworkContextEntry
    MAX-ACCESS  not-accessible
    STATUS      current
    DESCRIPTION ""
    ::= { affirmedNetworkcontextMIB 1 }

affirmedNetworkContextEntry OBJECT-TYPE
    SYNTAX      AffirmedNetworkContextEntry
    MAX-ACCESS  not-accessible
    STATUS      current
    DESCRIPTION ""
    INDEX { affirmedNetworkContextName }
        ::= { affirmedNetworkContextTable 1 }

AffirmedNetworkContextEntry ::=
    SEQUENCE {
        affirmedNetworkContextName String,
        affirmedNetworkContextRowstatus RowStatus
    }

affirmedNetworkContextName OBJECT-TYPE
    SYNTAX      String
    MAX-ACCESS  not-accessible
    STATUS      current
    DESCRIPTION ""
    ::= { affirmedNetworkContextEntry 1 }

affirmedNetworkContextRowstatus OBJECT-TYPE
    SYNTAX      RowStatus
    MAX-ACCESS  read-create
    STATUS      current
    DESCRIPTION ""
    ::= { affirmedNetworkContextEntry 2 }

affirmedNetworkContextIpInterfaceStatusTable OBJECT-TYPE
    SYNTAX      SEQUENCE OF AffirmedNetworkContextIpInterfaceStatusEntry
    MAX-ACCESS  not-accessible
    STATUS      current
    DESCRIPTION ""
    ::= { affirmedNetworkcontextMIB 3 }

affirmedNetworkContextIpInterfaceStatusEntry OBJECT-TYPE
    SYNTAX      AffirmedNetworkContextIpInterfaceStatusEntry
    MAX-ACCESS  not-accessible
    STATUS      current
    DESCRIPTION ""
    INDEX { affirmedNetworkContextName, affirmedNetworkContextIpInterfaceStatusIfName }
        ::= { affirmedNetworkContextIpInterfaceStatusTable 1 }

AffirmedNetworkContextIpInterfaceStatusEntry ::=
    SEQUENCE {
        affirmedNetworkContextIpInterfaceStatusIfName String,
        affirmedNetworkContextIpInterfaceStatusIpAddress String,
        affirmedNetworkContextIpInterfaceStatusPrefix String,
        affirmedNetworkContextIpInterfaceStatusSecondaryIpAddress String,
        affirmedNetworkContextIpInterfaceStatusSecondaryPrefixLength String,
        affirmedNetworkContextIpInterfaceStatusOperStatus String,
        affirmedNetworkContextIpInterfaceStatusNumTxV4Pkts ConfdString,
        affirmedNetworkContextIpInterfaceStatusNumTxV4Bytes ConfdString,
        affirmedNetworkContextIpInterfaceStatusNumTxV4DropPkts ConfdString,
        affirmedNetworkContextIpInterfaceStatusNumTxV4DropBytes ConfdString,
        affirmedNetworkContextIpInterfaceStatusNumRxV4Pkts ConfdString,
        affirmedNetworkContextIpInterfaceStatusNumRxV4Bytes ConfdString,
        affirmedNetworkContextIpInterfaceStatusNumRxV4DropPkts ConfdString,
        affirmedNetworkContextIpInterfaceStatusNumRxV4DropBytes ConfdString,
        affirmedNetworkContextIpInterfaceStatusNumRxICMPV4Pkts ConfdString,
        affirmedNetworkContextIpInterfaceStatusNumTxV6Pkts ConfdString,
        affirmedNetworkContextIpInterfaceStatusNumTxV6Bytes ConfdString,
        affirmedNetworkContextIpInterfaceStatusNumTxV6DropPkts ConfdString,
        affirmedNetworkContextIpInterfaceStatusNumTxV6DropBytes ConfdString,
        affirmedNetworkContextIpInterfaceStatusNumRxV6Pkts ConfdString,
        affirmedNetworkContextIpInterfaceStatusNumRxV6Bytes ConfdString,
        affirmedNetworkContextIpInterfaceStatusNumRxV6DropPkts ConfdString,
        affirmedNetworkContextIpInterfaceStatusNumRxV6DropBytes ConfdString,
        affirmedNetworkContextIpInterfaceStatusNumRxICMPV6Pkts ConfdString,
        affirmedNetworkContextIpInterfaceStatusNumTxICMPV4Pkts ConfdString,
        affirmedNetworkContextIpInterfaceStatusNumTxICMPV6Pkts ConfdString,
        affirmedNetworkContextIpInterfaceStatusNumAclDropPkts ConfdString,
        affirmedNetworkContextIpInterfaceStatusNumAclDropBytes ConfdString,
        affirmedNetworkContextIpInterfaceStatusNumAclAllowPkts ConfdString,
        affirmedNetworkContextIpInterfaceStatusNumAclAllowBytes ConfdString,
        affirmedNetworkContextIpInterfaceStatusNumTxKernelV4IcmpPkts ConfdString,
        affirmedNetworkContextIpInterfaceStatusNumTxErrorIndicationPkts ConfdString,
        affirmedNetworkContextIpInterfaceStatusNumTxErrorIndicationFailurePkts ConfdString,
        affirmedNetworkContextIpInterfaceStatusNumTxErrorIndicationFabricPkts ConfdString,
        affirmedNetworkContextIpInterfaceStatusNumTxErrorIndicationRateLimitPkts ConfdString,
        affirmedNetworkContextIpInterfaceStatusNumTxV4CsmProxyPkts ConfdString,
        affirmedNetworkContextIpInterfaceStatusNumRxV4UnSuppAddrPkts ConfdString,
        affirmedNetworkContextIpInterfaceStatusNumRxV4InvalidPkts ConfdString,
        affirmedNetworkContextIpInterfaceStatusNumRxV4MulticastPkts ConfdString,
        affirmedNetworkContextIpInterfaceStatusNumRxV4CsmProxyPkts ConfdString,
        affirmedNetworkContextIpInterfaceStatusNumRxV4UeUpstreamPkts ConfdString,
        affirmedNetworkContextIpInterfaceStatusNumRxV4UeDownstreamPkts ConfdString,
        affirmedNetworkContextIpInterfaceStatusNumRxV4UeSubnetDownstreamPkts ConfdString,
        affirmedNetworkContextIpInterfaceStatusNumRxV4LoadbalancerPkts ConfdString,
        affirmedNetworkContextIpInterfaceStatusNumInvalidNatPortcounter ConfdString,
        affirmedNetworkContextIpInterfaceStatusNumRxGtpInvalidPktscounter ConfdString,
        affirmedNetworkContextIpInterfaceStatusNumTxKernelV6IcmpPkts ConfdString,
        affirmedNetworkContextIpInterfaceStatusNumTxV6CsmProxyPkts ConfdString,
        affirmedNetworkContextIpInterfaceStatusNumRxV6UnSuppAddrPkts ConfdString,
        affirmedNetworkContextIpInterfaceStatusNumRxV6InvalidPkts ConfdString,
        affirmedNetworkContextIpInterfaceStatusNumRxV6IcmpNAPkts ConfdString,
        affirmedNetworkContextIpInterfaceStatusNumRxV6IcmpTooBigPkts ConfdString,
        affirmedNetworkContextIpInterfaceStatusNumRxV6CsmProxyPkts ConfdString,
        affirmedNetworkContextIpInterfaceStatusNumRxV6UeUpstreamPkts ConfdString,
        affirmedNetworkContextIpInterfaceStatusNumRxV6UeDownstreamPkts ConfdString,
        affirmedNetworkContextIpInterfaceStatusNumRxV6UeSubnetDownstreamPkts ConfdString,
        affirmedNetworkContextIpInterfaceStatusNumRxV6LoadbalancerPkts ConfdString,
        affirmedNetworkContextIpInterfaceStatusNumAllTcpFlagsSet ConfdString,
        affirmedNetworkContextIpInterfaceStatusNumSynAckFinRstUrgPshSet ConfdString,
        affirmedNetworkContextIpInterfaceStatusNumSynRstAckUrgFlagsSet ConfdString,
        affirmedNetworkContextIpInterfaceStatusNumSynFinPshUrgFlagsSet ConfdString,
        affirmedNetworkContextIpInterfaceStatusNumFinPshUrgFlagsSet ConfdString,
        affirmedNetworkContextIpInterfaceStatusNumOnlyPshFlagSet ConfdString,
        affirmedNetworkContextIpInterfaceStatusNumOnlyFinFlagSet ConfdString,
        affirmedNetworkContextIpInterfaceStatusNumOnlyUrgFlagSet ConfdString,
        affirmedNetworkContextIpInterfaceStatusNumFinRstFlagsSet ConfdString,
        affirmedNetworkContextIpInterfaceStatusNumSynRstFlagsSet ConfdString,
        affirmedNetworkContextIpInterfaceStatusNumFinSynFlagsSet ConfdString,
        affirmedNetworkContextIpInterfaceStatusNumNoneFlagsSet ConfdString,
        affirmedNetworkContextIpInterfaceStatusNumTcpReservedBitSet ConfdString,
        affirmedNetworkContextIpInterfaceStatusNumTcpSourcePortZero ConfdString,
        affirmedNetworkContextIpInterfaceStatusNumTcpDestinationPortZero ConfdString,
        affirmedNetworkContextIpInterfaceStatusNumIncorrectTcpHeaderOffset ConfdString,
        affirmedNetworkContextIpInterfaceStatusNumIncorrectUdpHeaderPacket ConfdString,
        affirmedNetworkContextIpInterfaceStatusNumUdpSourcePortZero ConfdString,
        affirmedNetworkContextIpInterfaceStatusNumUdpDestinationPortZero ConfdString,
        affirmedNetworkContextIpInterfaceStatusNumIpv4HeaderErrorPacket ConfdString,
        affirmedNetworkContextIpInterfaceStatusNumIpv4TruncatedPackets ConfdString,
        affirmedNetworkContextIpInterfaceStatusNumIpv6HeaderErrorPackets ConfdString,
        affirmedNetworkContextIpInterfaceStatusNumMulticastIpv6AddrWithReservedValueZero ConfdString,
        affirmedNetworkContextIpInterfaceStatusNumMulticastIpv6SrcAddr ConfdString,
        affirmedNetworkContextIpInterfaceStatusNumIpv6TruncatedPacket ConfdString,
        affirmedNetworkContextIpInterfaceStatusNumWrongIpVersionPacket ConfdString,
        affirmedNetworkContextIpInterfaceStatusNumInvalidPackets ConfdString,
        affirmedNetworkContextIpInterfaceStatusNumInvalidTtlValue ConfdString,
        affirmedNetworkContextIpInterfaceStatusNumIcmpv4HeaderErrorPackets ConfdString,
        affirmedNetworkContextIpInterfaceStatusNumIcmpv4ParameterProblemTypePacket ConfdString,
        affirmedNetworkContextIpInterfaceStatusNumIcmpv4UnuseGwPacket ConfdString,
        affirmedNetworkContextIpInterfaceStatusNumAllTcpFlagsSetIpv6 ConfdString,
        affirmedNetworkContextIpInterfaceStatusNumSynAckFinRstUrgPshSetIpv6 ConfdString,
        affirmedNetworkContextIpInterfaceStatusNumSynRstAckUrgFlagsSetIpv6 ConfdString,
        affirmedNetworkContextIpInterfaceStatusNumSynFinPshUrgFlagsSetIpv6 ConfdString,
        affirmedNetworkContextIpInterfaceStatusNumFinPshUrgFlagsSetIpv6 ConfdString,
        affirmedNetworkContextIpInterfaceStatusNumOnlyPshFlagSetIpv6 ConfdString,
        affirmedNetworkContextIpInterfaceStatusNumOnlyFinFlagSetIpv6 ConfdString,
        affirmedNetworkContextIpInterfaceStatusNumOnlyUrgFlagSetIpv6 ConfdString,
        affirmedNetworkContextIpInterfaceStatusNumFinRstFlagsSetIpv6 ConfdString,
        affirmedNetworkContextIpInterfaceStatusNumSynRstFlagsSetIpv6 ConfdString,
        affirmedNetworkContextIpInterfaceStatusNumFinSynFlagsSetIpv6 ConfdString,
        affirmedNetworkContextIpInterfaceStatusNumNoneFlagsSetIpv6 ConfdString,
        affirmedNetworkContextIpInterfaceStatusNumTcpReservedBitSetIpv6 ConfdString,
        affirmedNetworkContextIpInterfaceStatusNumTcpSourcePortZeroIpv6 ConfdString,
        affirmedNetworkContextIpInterfaceStatusNumTcpDestinationPortZeroIpv6 ConfdString,
        affirmedNetworkContextIpInterfaceStatusNumIncorrectTcpHeaderOffsetIpv6 ConfdString,
        affirmedNetworkContextIpInterfaceStatusNumIncorrectUdpHeaderPacketIpv6 ConfdString,
        affirmedNetworkContextIpInterfaceStatusNumUdpSourcePortZeroIpv6 ConfdString,
        affirmedNetworkContextIpInterfaceStatusNumUdpDestinationPortZeroIpv6 ConfdString,
        affirmedNetworkContextIpInterfaceStatusNumMulticastIpv6AddrWithScopeFieldZero ConfdString,
        affirmedNetworkContextIpInterfaceStatusNumIpv6AddrPayloadlengthZero ConfdString,
        affirmedNetworkContextIpInterfaceStatusNumIpv6HopbyHopOptionEHParseFail ConfdString,
        affirmedNetworkContextIpInterfaceStatusNumIpv6HopbyHopOptionEHOrderFail ConfdString,
        affirmedNetworkContextIpInterfaceStatusNumIcmpv6HeaderErrorPackets ConfdString,
        affirmedNetworkContextIpInterfaceStatusNumIcmpv6InvalidTypePackets ConfdString,
        affirmedNetworkContextIpInterfaceStatusNumIcmpv6InvalidCodePackets ConfdString
    }

affirmedNetworkContextIpInterfaceStatusIfName OBJECT-TYPE
    SYNTAX      String
    MAX-ACCESS  not-accessible
    STATUS      current
    DESCRIPTION "IP interface name"
    ::= { affirmedNetworkContextIpInterfaceStatusEntry 1 }

affirmedNetworkContextIpInterfaceStatusIpAddress OBJECT-TYPE
    SYNTAX      String
    MAX-ACCESS  read-only
    STATUS      current
    DESCRIPTION "Address of the IP interface"
    ::= { affirmedNetworkContextIpInterfaceStatusEntry 2 }

affirmedNetworkContextIpInterfaceStatusPrefix OBJECT-TYPE
    SYNTAX      String
    MAX-ACCESS  read-only
    STATUS      current
    DESCRIPTION "Prefix length of the IP address"
    ::= { affirmedNetworkContextIpInterfaceStatusEntry 3 }

affirmedNetworkContextIpInterfaceStatusSecondaryIpAddress OBJECT-TYPE
    SYNTAX      String
    MAX-ACCESS  read-only
    STATUS      current
    DESCRIPTION "Secondary address of the IP interface"
    ::= { affirmedNetworkContextIpInterfaceStatusEntry 4 }

affirmedNetworkContextIpInterfaceStatusSecondaryPrefixLength OBJECT-TYPE
    SYNTAX      String
    MAX-ACCESS  read-only
    STATUS      current
    DESCRIPTION "Secondary prefix length of the IP address"
    ::= { affirmedNetworkContextIpInterfaceStatusEntry 5 }

affirmedNetworkContextIpInterfaceStatusOperStatus OBJECT-TYPE
    SYNTAX      String
    MAX-ACCESS  read-only
    STATUS      current
    DESCRIPTION "Interface operation status"
    ::= { affirmedNetworkContextIpInterfaceStatusEntry 6 }

affirmedNetworkContextIpInterfaceStatusNumTxV4Pkts OBJECT-TYPE
    SYNTAX      ConfdString
    MAX-ACCESS  read-only
    STATUS      current
    DESCRIPTION "Number of transmitted IPv4 packets"
    ::= { affirmedNetworkContextIpInterfaceStatusEntry 7 }

affirmedNetworkContextIpInterfaceStatusNumTxV4Bytes OBJECT-TYPE
    SYNTAX      ConfdString
    MAX-ACCESS  read-only
    STATUS      current
    DESCRIPTION "Number of transmitted IPv4 packet bytes"
    ::= { affirmedNetworkContextIpInterfaceStatusEntry 8 }

affirmedNetworkContextIpInterfaceStatusNumTxV4DropPkts OBJECT-TYPE
    SYNTAX      ConfdString
    MAX-ACCESS  read-only
    STATUS      current
    DESCRIPTION "Number of transmitted dropped IPv4 packets"
    ::= { affirmedNetworkContextIpInterfaceStatusEntry 9 }

affirmedNetworkContextIpInterfaceStatusNumTxV4DropBytes OBJECT-TYPE
    SYNTAX      ConfdString
    MAX-ACCESS  read-only
    STATUS      current
    DESCRIPTION "Number of transmitted dropped IPv4 packet bytes"
    ::= { affirmedNetworkContextIpInterfaceStatusEntry 10 }

affirmedNetworkContextIpInterfaceStatusNumRxV4Pkts OBJECT-TYPE
    SYNTAX      ConfdString
    MAX-ACCESS  read-only
    STATUS      current
    DESCRIPTION "Number of received IPv4 packets"
    ::= { affirmedNetworkContextIpInterfaceStatusEntry 11 }

affirmedNetworkContextIpInterfaceStatusNumRxV4Bytes OBJECT-TYPE
    SYNTAX      ConfdString
    MAX-ACCESS  read-only
    STATUS      current
    DESCRIPTION "Number of received IPv4 packet bytes"
    ::= { affirmedNetworkContextIpInterfaceStatusEntry 12 }

affirmedNetworkContextIpInterfaceStatusNumRxV4DropPkts OBJECT-TYPE
    SYNTAX      ConfdString
    MAX-ACCESS  read-only
    STATUS      current
    DESCRIPTION "Number of received dropped IPv4 packets"
    ::= { affirmedNetworkContextIpInterfaceStatusEntry 13 }

affirmedNetworkContextIpInterfaceStatusNumRxV4DropBytes OBJECT-TYPE
    SYNTAX      ConfdString
    MAX-ACCESS  read-only
    STATUS      current
    DESCRIPTION "Number of received dropped IPv4 packet bytes"
    ::= { affirmedNetworkContextIpInterfaceStatusEntry 14 }

affirmedNetworkContextIpInterfaceStatusNumRxICMPV4Pkts OBJECT-TYPE
    SYNTAX      ConfdString
    MAX-ACCESS  read-only
    STATUS      current
    DESCRIPTION "Number of received ICMPv4 packets"
    ::= { affirmedNetworkContextIpInterfaceStatusEntry 15 }

affirmedNetworkContextIpInterfaceStatusNumTxV6Pkts OBJECT-TYPE
    SYNTAX      ConfdString
    MAX-ACCESS  read-only
    STATUS      current
    DESCRIPTION "Number of transmitted IPv6 packets"
    ::= { affirmedNetworkContextIpInterfaceStatusEntry 16 }

affirmedNetworkContextIpInterfaceStatusNumTxV6Bytes OBJECT-TYPE
    SYNTAX      ConfdString
    MAX-ACCESS  read-only
    STATUS      current
    DESCRIPTION "Number of transmitted IPv6 packet bytes"
    ::= { affirmedNetworkContextIpInterfaceStatusEntry 17 }

affirmedNetworkContextIpInterfaceStatusNumTxV6DropPkts OBJECT-TYPE
    SYNTAX      ConfdString
    MAX-ACCESS  read-only
    STATUS      current
    DESCRIPTION "Number of transmitted dropped IPv6 packets"
    ::= { affirmedNetworkContextIpInterfaceStatusEntry 18 }

affirmedNetworkContextIpInterfaceStatusNumTxV6DropBytes OBJECT-TYPE
    SYNTAX      ConfdString
    MAX-ACCESS  read-only
    STATUS      current
    DESCRIPTION "Number of transmitted dropped IPv6 bytes"
    ::= { affirmedNetworkContextIpInterfaceStatusEntry 19 }

affirmedNetworkContextIpInterfaceStatusNumRxV6Pkts OBJECT-TYPE
    SYNTAX      ConfdString
    MAX-ACCESS  read-only
    STATUS      current
    DESCRIPTION "Number of received IPv6 packets"
    ::= { affirmedNetworkContextIpInterfaceStatusEntry 20 }

affirmedNetworkContextIpInterfaceStatusNumRxV6Bytes OBJECT-TYPE
    SYNTAX      ConfdString
    MAX-ACCESS  read-only
    STATUS      current
    DESCRIPTION "Number of received IPv6 bytes"
    ::= { affirmedNetworkContextIpInterfaceStatusEntry 21 }

affirmedNetworkContextIpInterfaceStatusNumRxV6DropPkts OBJECT-TYPE
    SYNTAX      ConfdString
    MAX-ACCESS  read-only
    STATUS      current
    DESCRIPTION "Number of received dropped IPv6 packets"
    ::= { affirmedNetworkContextIpInterfaceStatusEntry 22 }

affirmedNetworkContextIpInterfaceStatusNumRxV6DropBytes OBJECT-TYPE
    SYNTAX      ConfdString
    MAX-ACCESS  read-only
    STATUS      current
    DESCRIPTION "Number of received dropped IPv6 bytes"
    ::= { affirmedNetworkContextIpInterfaceStatusEntry 23 }

affirmedNetworkContextIpInterfaceStatusNumRxICMPV6Pkts OBJECT-TYPE
    SYNTAX      ConfdString
    MAX-ACCESS  read-only
    STATUS      current
    DESCRIPTION "Number of received ICMPv6 packets"
    ::= { affirmedNetworkContextIpInterfaceStatusEntry 24 }

affirmedNetworkContextIpInterfaceStatusNumTxICMPV4Pkts OBJECT-TYPE
    SYNTAX      ConfdString
    MAX-ACCESS  read-only
    STATUS      current
    DESCRIPTION "Number of transmitted ICMPv4 packets"
    ::= { affirmedNetworkContextIpInterfaceStatusEntry 25 }

affirmedNetworkContextIpInterfaceStatusNumTxICMPV6Pkts OBJECT-TYPE
    SYNTAX      ConfdString
    MAX-ACCESS  read-only
    STATUS      current
    DESCRIPTION "Number of transmitted ICMPv6 packets"
    ::= { affirmedNetworkContextIpInterfaceStatusEntry 26 }

affirmedNetworkContextIpInterfaceStatusNumAclDropPkts OBJECT-TYPE
    SYNTAX      ConfdString
    MAX-ACCESS  read-only
    STATUS      current
    DESCRIPTION "Number of ACL dropped packets"
    ::= { affirmedNetworkContextIpInterfaceStatusEntry 27 }

affirmedNetworkContextIpInterfaceStatusNumAclDropBytes OBJECT-TYPE
    SYNTAX      ConfdString
    MAX-ACCESS  read-only
    STATUS      current
    DESCRIPTION "Number of ACL dropped bytes"
    ::= { affirmedNetworkContextIpInterfaceStatusEntry 28 }

affirmedNetworkContextIpInterfaceStatusNumAclAllowPkts OBJECT-TYPE
    SYNTAX      ConfdString
    MAX-ACCESS  read-only
    STATUS      current
    DESCRIPTION "Number of ACL allowed packets"
    ::= { affirmedNetworkContextIpInterfaceStatusEntry 29 }

affirmedNetworkContextIpInterfaceStatusNumAclAllowBytes OBJECT-TYPE
    SYNTAX      ConfdString
    MAX-ACCESS  read-only
    STATUS      current
    DESCRIPTION "Number of ACL allowed bytes"
    ::= { affirmedNetworkContextIpInterfaceStatusEntry 30 }

affirmedNetworkContextIpInterfaceStatusNumTxKernelV4IcmpPkts OBJECT-TYPE
    SYNTAX      ConfdString
    MAX-ACCESS  read-only
    STATUS      current
    DESCRIPTION "Number of transmitted kernel IPv4 ICMP packets"
    ::= { affirmedNetworkContextIpInterfaceStatusEntry 31 }

affirmedNetworkContextIpInterfaceStatusNumTxErrorIndicationPkts OBJECT-TYPE
    SYNTAX      ConfdString
    MAX-ACCESS  read-only
    STATUS      current
    DESCRIPTION "Number of transmitted IPv4 error indication packets"
    ::= { affirmedNetworkContextIpInterfaceStatusEntry 32 }

affirmedNetworkContextIpInterfaceStatusNumTxErrorIndicationFailurePkts OBJECT-TYPE
    SYNTAX      ConfdString
    MAX-ACCESS  read-only
    STATUS      current
    DESCRIPTION "Number of transmitted IPv4 error indication failure packets"
    ::= { affirmedNetworkContextIpInterfaceStatusEntry 33 }

affirmedNetworkContextIpInterfaceStatusNumTxErrorIndicationFabricPkts OBJECT-TYPE
    SYNTAX      ConfdString
    MAX-ACCESS  read-only
    STATUS      current
    DESCRIPTION "Number of transmitted IPv4 error indication fabric packets"
    ::= { affirmedNetworkContextIpInterfaceStatusEntry 34 }

affirmedNetworkContextIpInterfaceStatusNumTxErrorIndicationRateLimitPkts OBJECT-TYPE
    SYNTAX      ConfdString
    MAX-ACCESS  read-only
    STATUS      current
    DESCRIPTION "Number of transmitted IPv4 error indication rate limit packets"
    ::= { affirmedNetworkContextIpInterfaceStatusEntry 35 }

affirmedNetworkContextIpInterfaceStatusNumTxV4CsmProxyPkts OBJECT-TYPE
    SYNTAX      ConfdString
    MAX-ACCESS  read-only
    STATUS      current
    DESCRIPTION "Number of transmitted IPv4 CSM proxy packets"
    ::= { affirmedNetworkContextIpInterfaceStatusEntry 36 }

affirmedNetworkContextIpInterfaceStatusNumRxV4UnSuppAddrPkts OBJECT-TYPE
    SYNTAX      ConfdString
    MAX-ACCESS  read-only
    STATUS      current
    DESCRIPTION "Number of received IPv4 unsupported address packets"
    ::= { affirmedNetworkContextIpInterfaceStatusEntry 37 }

affirmedNetworkContextIpInterfaceStatusNumRxV4InvalidPkts OBJECT-TYPE
    SYNTAX      ConfdString
    MAX-ACCESS  read-only
    STATUS      current
    DESCRIPTION "Number of received IPv4 invalid packets"
    ::= { affirmedNetworkContextIpInterfaceStatusEntry 38 }

affirmedNetworkContextIpInterfaceStatusNumRxV4MulticastPkts OBJECT-TYPE
    SYNTAX      ConfdString
    MAX-ACCESS  read-only
    STATUS      current
    DESCRIPTION "Number of received IPv4 multicast packets"
    ::= { affirmedNetworkContextIpInterfaceStatusEntry 39 }

affirmedNetworkContextIpInterfaceStatusNumRxV4CsmProxyPkts OBJECT-TYPE
    SYNTAX      ConfdString
    MAX-ACCESS  read-only
    STATUS      current
    DESCRIPTION "Number of received IPv4 CSM proxy packets"
    ::= { affirmedNetworkContextIpInterfaceStatusEntry 40 }

affirmedNetworkContextIpInterfaceStatusNumRxV4UeUpstreamPkts OBJECT-TYPE
    SYNTAX      ConfdString
    MAX-ACCESS  read-only
    STATUS      current
    DESCRIPTION "Number of received IPv4 UE upstreamproxy packets"
    ::= { affirmedNetworkContextIpInterfaceStatusEntry 41 }

affirmedNetworkContextIpInterfaceStatusNumRxV4UeDownstreamPkts OBJECT-TYPE
    SYNTAX      ConfdString
    MAX-ACCESS  read-only
    STATUS      current
    DESCRIPTION "Number of received IPv4 UE downstream packets"
    ::= { affirmedNetworkContextIpInterfaceStatusEntry 42 }

affirmedNetworkContextIpInterfaceStatusNumRxV4UeSubnetDownstreamPkts OBJECT-TYPE
    SYNTAX      ConfdString
    MAX-ACCESS  read-only
    STATUS      current
    DESCRIPTION "Number of received IPv4 UE subnet downstream packets"
    ::= { affirmedNetworkContextIpInterfaceStatusEntry 43 }

affirmedNetworkContextIpInterfaceStatusNumRxV4LoadbalancerPkts OBJECT-TYPE
    SYNTAX      ConfdString
    MAX-ACCESS  read-only
    STATUS      current
    DESCRIPTION "Number of received IPv4 load balancer  packets"
    ::= { affirmedNetworkContextIpInterfaceStatusEntry 44 }

affirmedNetworkContextIpInterfaceStatusNumInvalidNatPortcounter OBJECT-TYPE
    SYNTAX      ConfdString
    MAX-ACCESS  read-only
    STATUS      current
    DESCRIPTION "Number of received IPv4 packets with invalid nat port"
    ::= { affirmedNetworkContextIpInterfaceStatusEntry 45 }

affirmedNetworkContextIpInterfaceStatusNumRxGtpInvalidPktscounter OBJECT-TYPE
    SYNTAX      ConfdString
    MAX-ACCESS  read-only
    STATUS      current
    DESCRIPTION "Number of received invalid GTP packets"
    ::= { affirmedNetworkContextIpInterfaceStatusEntry 46 }

affirmedNetworkContextIpInterfaceStatusNumTxKernelV6IcmpPkts OBJECT-TYPE
    SYNTAX      ConfdString
    MAX-ACCESS  read-only
    STATUS      current
    DESCRIPTION "Number of transmitted kernal ICMPv6 packets "
    ::= { affirmedNetworkContextIpInterfaceStatusEntry 47 }

affirmedNetworkContextIpInterfaceStatusNumTxV6CsmProxyPkts OBJECT-TYPE
    SYNTAX      ConfdString
    MAX-ACCESS  read-only
    STATUS      current
    DESCRIPTION "Number of transmitted IPv6 CSM proxy packets "
    ::= { affirmedNetworkContextIpInterfaceStatusEntry 48 }

affirmedNetworkContextIpInterfaceStatusNumRxV6UnSuppAddrPkts OBJECT-TYPE
    SYNTAX      ConfdString
    MAX-ACCESS  read-only
    STATUS      current
    DESCRIPTION "Number of received IPv6 unsupported address packets"
    ::= { affirmedNetworkContextIpInterfaceStatusEntry 49 }

affirmedNetworkContextIpInterfaceStatusNumRxV6InvalidPkts OBJECT-TYPE
    SYNTAX      ConfdString
    MAX-ACCESS  read-only
    STATUS      current
    DESCRIPTION "Number of received IPv6 invalid packets"
    ::= { affirmedNetworkContextIpInterfaceStatusEntry 50 }

affirmedNetworkContextIpInterfaceStatusNumRxV6IcmpNAPkts OBJECT-TYPE
    SYNTAX      ConfdString
    MAX-ACCESS  read-only
    STATUS      current
    DESCRIPTION "Number of received ICMPv6 NA packets"
    ::= { affirmedNetworkContextIpInterfaceStatusEntry 51 }

affirmedNetworkContextIpInterfaceStatusNumRxV6IcmpTooBigPkts OBJECT-TYPE
    SYNTAX      ConfdString
    MAX-ACCESS  read-only
    STATUS      current
    DESCRIPTION "Number of received ICMPv6 too big packets"
    ::= { affirmedNetworkContextIpInterfaceStatusEntry 52 }

affirmedNetworkContextIpInterfaceStatusNumRxV6CsmProxyPkts OBJECT-TYPE
    SYNTAX      ConfdString
    MAX-ACCESS  read-only
    STATUS      current
    DESCRIPTION "Number of received IPv6 CSM proxy packets"
    ::= { affirmedNetworkContextIpInterfaceStatusEntry 53 }

affirmedNetworkContextIpInterfaceStatusNumRxV6UeUpstreamPkts OBJECT-TYPE
    SYNTAX      ConfdString
    MAX-ACCESS  read-only
    STATUS      current
    DESCRIPTION "Number of received IPv6 UE upstream packets"
    ::= { affirmedNetworkContextIpInterfaceStatusEntry 54 }

affirmedNetworkContextIpInterfaceStatusNumRxV6UeDownstreamPkts OBJECT-TYPE
    SYNTAX      ConfdString
    MAX-ACCESS  read-only
    STATUS      current
    DESCRIPTION "Number of received IPv6 UE downstream packets"
    ::= { affirmedNetworkContextIpInterfaceStatusEntry 55 }

affirmedNetworkContextIpInterfaceStatusNumRxV6UeSubnetDownstreamPkts OBJECT-TYPE
    SYNTAX      ConfdString
    MAX-ACCESS  read-only
    STATUS      current
    DESCRIPTION "Number of received IPv6 UE subnet downstream packets"
    ::= { affirmedNetworkContextIpInterfaceStatusEntry 56 }

affirmedNetworkContextIpInterfaceStatusNumRxV6LoadbalancerPkts OBJECT-TYPE
    SYNTAX      ConfdString
    MAX-ACCESS  read-only
    STATUS      current
    DESCRIPTION "Number of received IPv6 load-banancer packets"
    ::= { affirmedNetworkContextIpInterfaceStatusEntry 57 }

affirmedNetworkContextIpInterfaceStatusNumAllTcpFlagsSet OBJECT-TYPE
    SYNTAX      ConfdString
    MAX-ACCESS  read-only
    STATUS      current
    DESCRIPTION " Number of all tcp flags set packets dropped"
    ::= { affirmedNetworkContextIpInterfaceStatusEntry 58 }

affirmedNetworkContextIpInterfaceStatusNumSynAckFinRstUrgPshSet OBJECT-TYPE
    SYNTAX      ConfdString
    MAX-ACCESS  read-only
    STATUS      current
    DESCRIPTION "Number of syn,ack,fin,rst,urg,psh flags set packets dropped"
    ::= { affirmedNetworkContextIpInterfaceStatusEntry 59 }

affirmedNetworkContextIpInterfaceStatusNumSynRstAckUrgFlagsSet OBJECT-TYPE
    SYNTAX      ConfdString
    MAX-ACCESS  read-only
    STATUS      current
    DESCRIPTION "Number of syn,rst,ack,urg flags set packets dropped"
    ::= { affirmedNetworkContextIpInterfaceStatusEntry 60 }

affirmedNetworkContextIpInterfaceStatusNumSynFinPshUrgFlagsSet OBJECT-TYPE
    SYNTAX      ConfdString
    MAX-ACCESS  read-only
    STATUS      current
    DESCRIPTION "Number of syn,fin,ack,urg flags set packets dropped"
    ::= { affirmedNetworkContextIpInterfaceStatusEntry 61 }

affirmedNetworkContextIpInterfaceStatusNumFinPshUrgFlagsSet OBJECT-TYPE
    SYNTAX      ConfdString
    MAX-ACCESS  read-only
    STATUS      current
    DESCRIPTION "Number of fin,psh,urg flags set packets dropped"
    ::= { affirmedNetworkContextIpInterfaceStatusEntry 62 }

affirmedNetworkContextIpInterfaceStatusNumOnlyPshFlagSet OBJECT-TYPE
    SYNTAX      ConfdString
    MAX-ACCESS  read-only
    STATUS      current
    DESCRIPTION "Number of only psh flag set packets dropped"
    ::= { affirmedNetworkContextIpInterfaceStatusEntry 63 }

affirmedNetworkContextIpInterfaceStatusNumOnlyFinFlagSet OBJECT-TYPE
    SYNTAX      ConfdString
    MAX-ACCESS  read-only
    STATUS      current
    DESCRIPTION "Number of only fin flag set packets dropped"
    ::= { affirmedNetworkContextIpInterfaceStatusEntry 64 }

affirmedNetworkContextIpInterfaceStatusNumOnlyUrgFlagSet OBJECT-TYPE
    SYNTAX      ConfdString
    MAX-ACCESS  read-only
    STATUS      current
    DESCRIPTION "Number of only urg flag set packets dropped"
    ::= { affirmedNetworkContextIpInterfaceStatusEntry 65 }

affirmedNetworkContextIpInterfaceStatusNumFinRstFlagsSet OBJECT-TYPE
    SYNTAX      ConfdString
    MAX-ACCESS  read-only
    STATUS      current
    DESCRIPTION "Number of fin,rst flags set packets dropped"
    ::= { affirmedNetworkContextIpInterfaceStatusEntry 66 }

affirmedNetworkContextIpInterfaceStatusNumSynRstFlagsSet OBJECT-TYPE
    SYNTAX      ConfdString
    MAX-ACCESS  read-only
    STATUS      current
    DESCRIPTION "Number of syn,rst flags set packets dropped"
    ::= { affirmedNetworkContextIpInterfaceStatusEntry 67 }

affirmedNetworkContextIpInterfaceStatusNumFinSynFlagsSet OBJECT-TYPE
    SYNTAX      ConfdString
    MAX-ACCESS  read-only
    STATUS      current
    DESCRIPTION "Number of fin,syn flags set packets dropped"
    ::= { affirmedNetworkContextIpInterfaceStatusEntry 68 }

affirmedNetworkContextIpInterfaceStatusNumNoneFlagsSet OBJECT-TYPE
    SYNTAX      ConfdString
    MAX-ACCESS  read-only
    STATUS      current
    DESCRIPTION "Number of none of the TCP flags set packets dropped"
    ::= { affirmedNetworkContextIpInterfaceStatusEntry 69 }

affirmedNetworkContextIpInterfaceStatusNumTcpReservedBitSet OBJECT-TYPE
    SYNTAX      ConfdString
    MAX-ACCESS  read-only
    STATUS      current
    DESCRIPTION "Number of tcp reserved bits set packets dropped"
    ::= { affirmedNetworkContextIpInterfaceStatusEntry 70 }

affirmedNetworkContextIpInterfaceStatusNumTcpSourcePortZero OBJECT-TYPE
    SYNTAX      ConfdString
    MAX-ACCESS  read-only
    STATUS      current
    DESCRIPTION "Number of tcp source port zero packets dropped"
    ::= { affirmedNetworkContextIpInterfaceStatusEntry 71 }

affirmedNetworkContextIpInterfaceStatusNumTcpDestinationPortZero OBJECT-TYPE
    SYNTAX      ConfdString
    MAX-ACCESS  read-only
    STATUS      current
    DESCRIPTION "Number of tcp destination port zero packets dropped"
    ::= { affirmedNetworkContextIpInterfaceStatusEntry 72 }

affirmedNetworkContextIpInterfaceStatusNumIncorrectTcpHeaderOffset OBJECT-TYPE
    SYNTAX      ConfdString
    MAX-ACCESS  read-only
    STATUS      current
    DESCRIPTION "Number of incorrect tcp header offset packets dropped"
    ::= { affirmedNetworkContextIpInterfaceStatusEntry 73 }

affirmedNetworkContextIpInterfaceStatusNumIncorrectUdpHeaderPacket OBJECT-TYPE
    SYNTAX      ConfdString
    MAX-ACCESS  read-only
    STATUS      current
    DESCRIPTION "Number of incorrect udp header packets dropped"
    ::= { affirmedNetworkContextIpInterfaceStatusEntry 74 }

affirmedNetworkContextIpInterfaceStatusNumUdpSourcePortZero OBJECT-TYPE
    SYNTAX      ConfdString
    MAX-ACCESS  read-only
    STATUS      current
    DESCRIPTION "Number of udp source port zero packets dropped"
    ::= { affirmedNetworkContextIpInterfaceStatusEntry 75 }

affirmedNetworkContextIpInterfaceStatusNumUdpDestinationPortZero OBJECT-TYPE
    SYNTAX      ConfdString
    MAX-ACCESS  read-only
    STATUS      current
    DESCRIPTION "Number of udp destination port zero packets dropped"
    ::= { affirmedNetworkContextIpInterfaceStatusEntry 76 }

affirmedNetworkContextIpInterfaceStatusNumIpv4HeaderErrorPacket OBJECT-TYPE
    SYNTAX      ConfdString
    MAX-ACCESS  read-only
    STATUS      current
    DESCRIPTION "Number of ipv4 header error packets dropped"
    ::= { affirmedNetworkContextIpInterfaceStatusEntry 77 }

affirmedNetworkContextIpInterfaceStatusNumIpv4TruncatedPackets OBJECT-TYPE
    SYNTAX      ConfdString
    MAX-ACCESS  read-only
    STATUS      current
    DESCRIPTION "Number of ipv4 truncated packets dropped"
    ::= { affirmedNetworkContextIpInterfaceStatusEntry 78 }

affirmedNetworkContextIpInterfaceStatusNumIpv6HeaderErrorPackets OBJECT-TYPE
    SYNTAX      ConfdString
    MAX-ACCESS  read-only
    STATUS      current
    DESCRIPTION "Number of ipv6 header error packets dropped"
    ::= { affirmedNetworkContextIpInterfaceStatusEntry 79 }

affirmedNetworkContextIpInterfaceStatusNumMulticastIpv6AddrWithReservedValueZero OBJECT-TYPE
    SYNTAX      ConfdString
    MAX-ACCESS  read-only
    STATUS      current
    DESCRIPTION "Number of multicast ipv6 addr with reserved value zero packets dropped"
    ::= { affirmedNetworkContextIpInterfaceStatusEntry 80 }

affirmedNetworkContextIpInterfaceStatusNumMulticastIpv6SrcAddr OBJECT-TYPE
    SYNTAX      ConfdString
    MAX-ACCESS  read-only
    STATUS      current
    DESCRIPTION "Number of multicast ipv6 src addr packets dropped"
    ::= { affirmedNetworkContextIpInterfaceStatusEntry 81 }

affirmedNetworkContextIpInterfaceStatusNumIpv6TruncatedPacket OBJECT-TYPE
    SYNTAX      ConfdString
    MAX-ACCESS  read-only
    STATUS      current
    DESCRIPTION "Number of ipv6 trucated packets dropped"
    ::= { affirmedNetworkContextIpInterfaceStatusEntry 82 }

affirmedNetworkContextIpInterfaceStatusNumWrongIpVersionPacket OBJECT-TYPE
    SYNTAX      ConfdString
    MAX-ACCESS  read-only
    STATUS      current
    DESCRIPTION "Number of wrong ip version packets dropped"
    ::= { affirmedNetworkContextIpInterfaceStatusEntry 83 }

affirmedNetworkContextIpInterfaceStatusNumInvalidPackets OBJECT-TYPE
    SYNTAX      ConfdString
    MAX-ACCESS  read-only
    STATUS      current
    DESCRIPTION "Number of invalid packets dropped"
    ::= { affirmedNetworkContextIpInterfaceStatusEntry 84 }

affirmedNetworkContextIpInterfaceStatusNumInvalidTtlValue OBJECT-TYPE
    SYNTAX      ConfdString
    MAX-ACCESS  read-only
    STATUS      current
    DESCRIPTION "Number of invalid ttl value packets dropped"
    ::= { affirmedNetworkContextIpInterfaceStatusEntry 85 }

affirmedNetworkContextIpInterfaceStatusNumIcmpv4HeaderErrorPackets OBJECT-TYPE
    SYNTAX      ConfdString
    MAX-ACCESS  read-only
    STATUS      current
    DESCRIPTION "Number of icmpv4 header error packets dropped"
    ::= { affirmedNetworkContextIpInterfaceStatusEntry 86 }

affirmedNetworkContextIpInterfaceStatusNumIcmpv4ParameterProblemTypePacket OBJECT-TYPE
    SYNTAX      ConfdString
    MAX-ACCESS  read-only
    STATUS      current
    DESCRIPTION "Number of icmpv4 parameter problem type packets dropped"
    ::= { affirmedNetworkContextIpInterfaceStatusEntry 87 }

affirmedNetworkContextIpInterfaceStatusNumIcmpv4UnuseGwPacket OBJECT-TYPE
    SYNTAX      ConfdString
    MAX-ACCESS  read-only
    STATUS      current
    DESCRIPTION "Number of icmpv4 unuse gw packets dropped"
    ::= { affirmedNetworkContextIpInterfaceStatusEntry 88 }

affirmedNetworkContextIpInterfaceStatusNumAllTcpFlagsSetIpv6 OBJECT-TYPE
    SYNTAX      ConfdString
    MAX-ACCESS  read-only
    STATUS      current
    DESCRIPTION " Number of all tcp flags set Ipv6 packets dropped"
    ::= { affirmedNetworkContextIpInterfaceStatusEntry 89 }

affirmedNetworkContextIpInterfaceStatusNumSynAckFinRstUrgPshSetIpv6 OBJECT-TYPE
    SYNTAX      ConfdString
    MAX-ACCESS  read-only
    STATUS      current
    DESCRIPTION "Number of syn,ack,fin,rst,urg,psh flags set Ipv6 packets dropped"
    ::= { affirmedNetworkContextIpInterfaceStatusEntry 90 }

affirmedNetworkContextIpInterfaceStatusNumSynRstAckUrgFlagsSetIpv6 OBJECT-TYPE
    SYNTAX      ConfdString
    MAX-ACCESS  read-only
    STATUS      current
    DESCRIPTION "Number of syn,rst,ack,urg flags set Ipv6 packets dropped"
    ::= { affirmedNetworkContextIpInterfaceStatusEntry 91 }

affirmedNetworkContextIpInterfaceStatusNumSynFinPshUrgFlagsSetIpv6 OBJECT-TYPE
    SYNTAX      ConfdString
    MAX-ACCESS  read-only
    STATUS      current
    DESCRIPTION "Number of syn,fin,ack,urg flags set Ipv6 packets dropped"
    ::= { affirmedNetworkContextIpInterfaceStatusEntry 92 }

affirmedNetworkContextIpInterfaceStatusNumFinPshUrgFlagsSetIpv6 OBJECT-TYPE
    SYNTAX      ConfdString
    MAX-ACCESS  read-only
    STATUS      current
    DESCRIPTION "Number of fin,psh,urg flags set Ipv6 packets dropped"
    ::= { affirmedNetworkContextIpInterfaceStatusEntry 93 }

affirmedNetworkContextIpInterfaceStatusNumOnlyPshFlagSetIpv6 OBJECT-TYPE
    SYNTAX      ConfdString
    MAX-ACCESS  read-only
    STATUS      current
    DESCRIPTION "Number of only psh flag set Ipv6 packets dropped"
    ::= { affirmedNetworkContextIpInterfaceStatusEntry 94 }

affirmedNetworkContextIpInterfaceStatusNumOnlyFinFlagSetIpv6 OBJECT-TYPE
    SYNTAX      ConfdString
    MAX-ACCESS  read-only
    STATUS      current
    DESCRIPTION "Number of only fin flag set Ipv6 packets dropped"
    ::= { affirmedNetworkContextIpInterfaceStatusEntry 95 }

affirmedNetworkContextIpInterfaceStatusNumOnlyUrgFlagSetIpv6 OBJECT-TYPE
    SYNTAX      ConfdString
    MAX-ACCESS  read-only
    STATUS      current
    DESCRIPTION "Number of only urg flag set Ipv6 packets dropped"
    ::= { affirmedNetworkContextIpInterfaceStatusEntry 96 }

affirmedNetworkContextIpInterfaceStatusNumFinRstFlagsSetIpv6 OBJECT-TYPE
    SYNTAX      ConfdString
    MAX-ACCESS  read-only
    STATUS      current
    DESCRIPTION "Number of fin,rst flags set Ipv6 packets dropped"
    ::= { affirmedNetworkContextIpInterfaceStatusEntry 97 }

affirmedNetworkContextIpInterfaceStatusNumSynRstFlagsSetIpv6 OBJECT-TYPE
    SYNTAX      ConfdString
    MAX-ACCESS  read-only
    STATUS      current
    DESCRIPTION "Number of syn,rst flags set Ipv6 packets dropped"
    ::= { affirmedNetworkContextIpInterfaceStatusEntry 98 }

affirmedNetworkContextIpInterfaceStatusNumFinSynFlagsSetIpv6 OBJECT-TYPE
    SYNTAX      ConfdString
    MAX-ACCESS  read-only
    STATUS      current
    DESCRIPTION "Number of fin,syn flags set Ipv6 packets dropped"
    ::= { affirmedNetworkContextIpInterfaceStatusEntry 99 }

affirmedNetworkContextIpInterfaceStatusNumNoneFlagsSetIpv6 OBJECT-TYPE
    SYNTAX      ConfdString
    MAX-ACCESS  read-only
    STATUS      current
    DESCRIPTION "Number of none of the TCP flags set Ipv6 packets dropped"
    ::= { affirmedNetworkContextIpInterfaceStatusEntry 100 }

affirmedNetworkContextIpInterfaceStatusNumTcpReservedBitSetIpv6 OBJECT-TYPE
    SYNTAX      ConfdString
    MAX-ACCESS  read-only
    STATUS      current
    DESCRIPTION "Number of tcp reserved bits set Ipv6 packets dropped"
    ::= { affirmedNetworkContextIpInterfaceStatusEntry 101 }

affirmedNetworkContextIpInterfaceStatusNumTcpSourcePortZeroIpv6 OBJECT-TYPE
    SYNTAX      ConfdString
    MAX-ACCESS  read-only
    STATUS      current
    DESCRIPTION "Number of tcp source port zero Ipv6 packets dropped"
    ::= { affirmedNetworkContextIpInterfaceStatusEntry 102 }

affirmedNetworkContextIpInterfaceStatusNumTcpDestinationPortZeroIpv6 OBJECT-TYPE
    SYNTAX      ConfdString
    MAX-ACCESS  read-only
    STATUS      current
    DESCRIPTION "Number of tcp destination port zero Ipv6 packets dropped"
    ::= { affirmedNetworkContextIpInterfaceStatusEntry 103 }

affirmedNetworkContextIpInterfaceStatusNumIncorrectTcpHeaderOffsetIpv6 OBJECT-TYPE
    SYNTAX      ConfdString
    MAX-ACCESS  read-only
    STATUS      current
    DESCRIPTION "Number of incorrect tcp header offset Ipv6 packets dropped"
    ::= { affirmedNetworkContextIpInterfaceStatusEntry 104 }

affirmedNetworkContextIpInterfaceStatusNumIncorrectUdpHeaderPacketIpv6 OBJECT-TYPE
    SYNTAX      ConfdString
    MAX-ACCESS  read-only
    STATUS      current
    DESCRIPTION "Number of incorrect udp header Ipv6 packets dropped"
    ::= { affirmedNetworkContextIpInterfaceStatusEntry 105 }

affirmedNetworkContextIpInterfaceStatusNumUdpSourcePortZeroIpv6 OBJECT-TYPE
    SYNTAX      ConfdString
    MAX-ACCESS  read-only
    STATUS      current
    DESCRIPTION "Number of udp source port zero Ipv6 packets dropped"
    ::= { affirmedNetworkContextIpInterfaceStatusEntry 106 }

affirmedNetworkContextIpInterfaceStatusNumUdpDestinationPortZeroIpv6 OBJECT-TYPE
    SYNTAX      ConfdString
    MAX-ACCESS  read-only
    STATUS      current
    DESCRIPTION "Number of udp destination port Ipv6 zero packets dropped"
    ::= { affirmedNetworkContextIpInterfaceStatusEntry 107 }

affirmedNetworkContextIpInterfaceStatusNumMulticastIpv6AddrWithScopeFieldZero OBJECT-TYPE
    SYNTAX      ConfdString
    MAX-ACCESS  read-only
    STATUS      current
    DESCRIPTION "Number of multicast ipv6 addr with scope field zero packets dropped"
    ::= { affirmedNetworkContextIpInterfaceStatusEntry 108 }

affirmedNetworkContextIpInterfaceStatusNumIpv6AddrPayloadlengthZero OBJECT-TYPE
    SYNTAX      ConfdString
    MAX-ACCESS  read-only
    STATUS      current
    DESCRIPTION "Number of ipv6 addr payload length zero packets dropped"
    ::= { affirmedNetworkContextIpInterfaceStatusEntry 109 }

affirmedNetworkContextIpInterfaceStatusNumIpv6HopbyHopOptionEHParseFail OBJECT-TYPE
    SYNTAX      ConfdString
    MAX-ACCESS  read-only
    STATUS      current
    DESCRIPTION "Number of ipv6 hop by hop option EH parse fail packets dropped"
    ::= { affirmedNetworkContextIpInterfaceStatusEntry 110 }

affirmedNetworkContextIpInterfaceStatusNumIpv6HopbyHopOptionEHOrderFail OBJECT-TYPE
    SYNTAX      ConfdString
    MAX-ACCESS  read-only
    STATUS      current
    DESCRIPTION "Number of ipv6 hop by hop option EH Order fail packets dropped"
    ::= { affirmedNetworkContextIpInterfaceStatusEntry 111 }

affirmedNetworkContextIpInterfaceStatusNumIcmpv6HeaderErrorPackets OBJECT-TYPE
    SYNTAX      ConfdString
    MAX-ACCESS  read-only
    STATUS      current
    DESCRIPTION "Number of icmpv6 header error packets dropped"
    ::= { affirmedNetworkContextIpInterfaceStatusEntry 112 }

affirmedNetworkContextIpInterfaceStatusNumIcmpv6InvalidTypePackets OBJECT-TYPE
    SYNTAX      ConfdString
    MAX-ACCESS  read-only
    STATUS      current
    DESCRIPTION "Number of icmpv6 wrong type packets dropped"
    ::= { affirmedNetworkContextIpInterfaceStatusEntry 113 }

affirmedNetworkContextIpInterfaceStatusNumIcmpv6InvalidCodePackets OBJECT-TYPE
    SYNTAX      ConfdString
    MAX-ACCESS  read-only
    STATUS      current
    DESCRIPTION "Number of icmpv6 wrong code packets dropped"
    ::= { affirmedNetworkContextIpInterfaceStatusEntry 114 }

affirmedNetworkContextIpLogicalIntfStatsAclStatsTable OBJECT-TYPE
    SYNTAX      SEQUENCE OF AffirmedNetworkContextIpLogicalIntfStatsAclStatsEntry
    MAX-ACCESS  not-accessible
    STATUS      current
    DESCRIPTION ""
    ::= { affirmedNetworkcontextMIB 24 }

affirmedNetworkContextIpLogicalIntfStatsAclStatsEntry OBJECT-TYPE
    SYNTAX      AffirmedNetworkContextIpLogicalIntfStatsAclStatsEntry
    MAX-ACCESS  not-accessible
    STATUS      current
    DESCRIPTION ""
    INDEX { affirmedNetworkContextName, affirmedNetworkContextIpLogicalIntfStatsAclStatsIfName }
        ::= { affirmedNetworkContextIpLogicalIntfStatsAclStatsTable 1 }

AffirmedNetworkContextIpLogicalIntfStatsAclStatsEntry ::=
    SEQUENCE {
        affirmedNetworkContextIpLogicalIntfStatsAclStatsIfName String,
        affirmedNetworkContextIpLogicalIntfStatsAclStatsIpAddress String,
        affirmedNetworkContextIpLogicalIntfStatsAclStatsPrefix String,
        affirmedNetworkContextIpLogicalIntfStatsAclStatsSecondaryIpAddress String,
        affirmedNetworkContextIpLogicalIntfStatsAclStatsSecondaryPrefixLength String,
        affirmedNetworkContextIpLogicalIntfStatsAclStatsOperStatus String,
        affirmedNetworkContextIpLogicalIntfStatsAclStatsNumAclDropPkts1 ConfdString,
        affirmedNetworkContextIpLogicalIntfStatsAclStatsNumAclDropBytes1 ConfdString,
        affirmedNetworkContextIpLogicalIntfStatsAclStatsNumAclAllowPkts1 ConfdString,
        affirmedNetworkContextIpLogicalIntfStatsAclStatsNumAclAllowBytes1 ConfdString
    }

affirmedNetworkContextIpLogicalIntfStatsAclStatsIfName OBJECT-TYPE
    SYNTAX      String
    MAX-ACCESS  not-accessible
    STATUS      current
    DESCRIPTION "IP interface name"
    ::= { affirmedNetworkContextIpLogicalIntfStatsAclStatsEntry 1 }

affirmedNetworkContextIpLogicalIntfStatsAclStatsIpAddress OBJECT-TYPE
    SYNTAX      String
    MAX-ACCESS  read-only
    STATUS      current
    DESCRIPTION "Address of the IP interface"
    ::= { affirmedNetworkContextIpLogicalIntfStatsAclStatsEntry 2 }

affirmedNetworkContextIpLogicalIntfStatsAclStatsPrefix OBJECT-TYPE
    SYNTAX      String
    MAX-ACCESS  read-only
    STATUS      current
    DESCRIPTION "Prefix length of the IP address"
    ::= { affirmedNetworkContextIpLogicalIntfStatsAclStatsEntry 3 }

affirmedNetworkContextIpLogicalIntfStatsAclStatsSecondaryIpAddress OBJECT-TYPE
    SYNTAX      String
    MAX-ACCESS  read-only
    STATUS      current
    DESCRIPTION "Secondary address of the IP interface"
    ::= { affirmedNetworkContextIpLogicalIntfStatsAclStatsEntry 4 }

affirmedNetworkContextIpLogicalIntfStatsAclStatsSecondaryPrefixLength OBJECT-TYPE
    SYNTAX      String
    MAX-ACCESS  read-only
    STATUS      current
    DESCRIPTION "Secondary prefix length of the IP address"
    ::= { affirmedNetworkContextIpLogicalIntfStatsAclStatsEntry 5 }

affirmedNetworkContextIpLogicalIntfStatsAclStatsOperStatus OBJECT-TYPE
    SYNTAX      String
    MAX-ACCESS  read-only
    STATUS      current
    DESCRIPTION "Interface operation status"
    ::= { affirmedNetworkContextIpLogicalIntfStatsAclStatsEntry 6 }

affirmedNetworkContextIpLogicalIntfStatsAclStatsNumAclDropPkts1 OBJECT-TYPE
    SYNTAX      ConfdString
    MAX-ACCESS  read-only
    STATUS      current
    DESCRIPTION "Number of ACL drop Pkts"
    ::= { affirmedNetworkContextIpLogicalIntfStatsAclStatsEntry 7 }

affirmedNetworkContextIpLogicalIntfStatsAclStatsNumAclDropBytes1 OBJECT-TYPE
    SYNTAX      ConfdString
    MAX-ACCESS  read-only
    STATUS      current
    DESCRIPTION "Number of ACL drop Bytes"
    ::= { affirmedNetworkContextIpLogicalIntfStatsAclStatsEntry 8 }

affirmedNetworkContextIpLogicalIntfStatsAclStatsNumAclAllowPkts1 OBJECT-TYPE
    SYNTAX      ConfdString
    MAX-ACCESS  read-only
    STATUS      current
    DESCRIPTION "Number of ACL allow Pkts"
    ::= { affirmedNetworkContextIpLogicalIntfStatsAclStatsEntry 9 }

affirmedNetworkContextIpLogicalIntfStatsAclStatsNumAclAllowBytes1 OBJECT-TYPE
    SYNTAX      ConfdString
    MAX-ACCESS  read-only
    STATUS      current
    DESCRIPTION "Number of ACL allow Bytes"
    ::= { affirmedNetworkContextIpLogicalIntfStatsAclStatsEntry 10 }

affirmedNetworkContextIpLogicalIntfStatsArpStatsTable OBJECT-TYPE
    SYNTAX      SEQUENCE OF AffirmedNetworkContextIpLogicalIntfStatsArpStatsEntry
    MAX-ACCESS  not-accessible
    STATUS      current
    DESCRIPTION ""
    ::= { affirmedNetworkcontextMIB 25 }

affirmedNetworkContextIpLogicalIntfStatsArpStatsEntry OBJECT-TYPE
    SYNTAX      AffirmedNetworkContextIpLogicalIntfStatsArpStatsEntry
    MAX-ACCESS  not-accessible
    STATUS      current
    DESCRIPTION ""
    INDEX { affirmedNetworkContextName, affirmedNetworkContextIpLogicalIntfStatsArpStatsIfName }
        ::= { affirmedNetworkContextIpLogicalIntfStatsArpStatsTable 1 }

AffirmedNetworkContextIpLogicalIntfStatsArpStatsEntry ::=
    SEQUENCE {
        affirmedNetworkContextIpLogicalIntfStatsArpStatsIfName String,
        affirmedNetworkContextIpLogicalIntfStatsArpStatsIpAddress String,
        affirmedNetworkContextIpLogicalIntfStatsArpStatsPrefix String,
        affirmedNetworkContextIpLogicalIntfStatsArpStatsSecondaryIpAddress String,
        affirmedNetworkContextIpLogicalIntfStatsArpStatsSecondaryPrefixLength String,
        affirmedNetworkContextIpLogicalIntfStatsArpStatsOperStatus String,
        affirmedNetworkContextIpLogicalIntfStatsArpStatsNumRxArpPkts ConfdString,
        affirmedNetworkContextIpLogicalIntfStatsArpStatsNumArpRequestTxPkts ConfdString,
        affirmedNetworkContextIpLogicalIntfStatsArpStatsNumTxKernelArpPkts ConfdString,
        affirmedNetworkContextIpLogicalIntfStatsArpStatsNumArpQueuedPkts ConfdString,
        affirmedNetworkContextIpLogicalIntfStatsArpStatsNumArpEntryInclAdds ConfdString,
        affirmedNetworkContextIpLogicalIntfStatsArpStatsNumArpDequeuedBadPkts ConfdString,
        affirmedNetworkContextIpLogicalIntfStatsArpStatsNumArpQFreedAlready ConfdString,
        affirmedNetworkContextIpLogicalIntfStatsArpStatsNumRxArpDropPkts ConfdString,
        affirmedNetworkContextIpLogicalIntfStatsArpStatsNumArpQueueInsertFails ConfdString,
        affirmedNetworkContextIpLogicalIntfStatsArpStatsNumArpQueueFullDropPkts ConfdString,
        affirmedNetworkContextIpLogicalIntfStatsArpStatsNumArpEntryAllocFails ConfdString
    }

affirmedNetworkContextIpLogicalIntfStatsArpStatsIfName OBJECT-TYPE
    SYNTAX      String
    MAX-ACCESS  not-accessible
    STATUS      current
    DESCRIPTION "IP interface name"
    ::= { affirmedNetworkContextIpLogicalIntfStatsArpStatsEntry 1 }

affirmedNetworkContextIpLogicalIntfStatsArpStatsIpAddress OBJECT-TYPE
    SYNTAX      String
    MAX-ACCESS  read-only
    STATUS      current
    DESCRIPTION "Address of the IP interface"
    ::= { affirmedNetworkContextIpLogicalIntfStatsArpStatsEntry 2 }

affirmedNetworkContextIpLogicalIntfStatsArpStatsPrefix OBJECT-TYPE
    SYNTAX      String
    MAX-ACCESS  read-only
    STATUS      current
    DESCRIPTION "Prefix length of the IP address"
    ::= { affirmedNetworkContextIpLogicalIntfStatsArpStatsEntry 3 }

affirmedNetworkContextIpLogicalIntfStatsArpStatsSecondaryIpAddress OBJECT-TYPE
    SYNTAX      String
    MAX-ACCESS  read-only
    STATUS      current
    DESCRIPTION "Secondary address of the IP interface"
    ::= { affirmedNetworkContextIpLogicalIntfStatsArpStatsEntry 4 }

affirmedNetworkContextIpLogicalIntfStatsArpStatsSecondaryPrefixLength OBJECT-TYPE
    SYNTAX      String
    MAX-ACCESS  read-only
    STATUS      current
    DESCRIPTION "Secondary prefix length of the IP address"
    ::= { affirmedNetworkContextIpLogicalIntfStatsArpStatsEntry 5 }

affirmedNetworkContextIpLogicalIntfStatsArpStatsOperStatus OBJECT-TYPE
    SYNTAX      String
    MAX-ACCESS  read-only
    STATUS      current
    DESCRIPTION "Interface operation status"
    ::= { affirmedNetworkContextIpLogicalIntfStatsArpStatsEntry 6 }

affirmedNetworkContextIpLogicalIntfStatsArpStatsNumRxArpPkts OBJECT-TYPE
    SYNTAX      ConfdString
    MAX-ACCESS  read-only
    STATUS      current
    DESCRIPTION "Number of ARP RequestTx Pkts"
    ::= { affirmedNetworkContextIpLogicalIntfStatsArpStatsEntry 7 }

affirmedNetworkContextIpLogicalIntfStatsArpStatsNumArpRequestTxPkts OBJECT-TYPE
    SYNTAX      ConfdString
    MAX-ACCESS  read-only
    STATUS      current
    DESCRIPTION "Number of ARP Request Pkts"
    ::= { affirmedNetworkContextIpLogicalIntfStatsArpStatsEntry 8 }

affirmedNetworkContextIpLogicalIntfStatsArpStatsNumTxKernelArpPkts OBJECT-TYPE
    SYNTAX      ConfdString
    MAX-ACCESS  read-only
    STATUS      current
    DESCRIPTION "Number of Tx Kernel ARP Pkts"
    ::= { affirmedNetworkContextIpLogicalIntfStatsArpStatsEntry 9 }

affirmedNetworkContextIpLogicalIntfStatsArpStatsNumArpQueuedPkts OBJECT-TYPE
    SYNTAX      ConfdString
    MAX-ACCESS  read-only
    STATUS      current
    DESCRIPTION "Number of ARP Queued Pkts"
    ::= { affirmedNetworkContextIpLogicalIntfStatsArpStatsEntry 10 }

affirmedNetworkContextIpLogicalIntfStatsArpStatsNumArpEntryInclAdds OBJECT-TYPE
    SYNTAX      ConfdString
    MAX-ACCESS  read-only
    STATUS      current
    DESCRIPTION "Number of ARP Entry Incl Adds"
    ::= { affirmedNetworkContextIpLogicalIntfStatsArpStatsEntry 11 }

affirmedNetworkContextIpLogicalIntfStatsArpStatsNumArpDequeuedBadPkts OBJECT-TYPE
    SYNTAX      ConfdString
    MAX-ACCESS  read-only
    STATUS      current
    DESCRIPTION "Number of ARP Dequeued Bad Pkts"
    ::= { affirmedNetworkContextIpLogicalIntfStatsArpStatsEntry 12 }

affirmedNetworkContextIpLogicalIntfStatsArpStatsNumArpQFreedAlready OBJECT-TYPE
    SYNTAX      ConfdString
    MAX-ACCESS  read-only
    STATUS      current
    DESCRIPTION "Number of ARP Queue Freed Already"
    ::= { affirmedNetworkContextIpLogicalIntfStatsArpStatsEntry 13 }

affirmedNetworkContextIpLogicalIntfStatsArpStatsNumRxArpDropPkts OBJECT-TYPE
    SYNTAX      ConfdString
    MAX-ACCESS  read-only
    STATUS      current
    DESCRIPTION "Number of ARP Queue Freed Already"
    ::= { affirmedNetworkContextIpLogicalIntfStatsArpStatsEntry 14 }

affirmedNetworkContextIpLogicalIntfStatsArpStatsNumArpQueueInsertFails OBJECT-TYPE
    SYNTAX      ConfdString
    MAX-ACCESS  read-only
    STATUS      current
    DESCRIPTION "Number of ARP Queue Insert Fails"
    ::= { affirmedNetworkContextIpLogicalIntfStatsArpStatsEntry 15 }

affirmedNetworkContextIpLogicalIntfStatsArpStatsNumArpQueueFullDropPkts OBJECT-TYPE
    SYNTAX      ConfdString
    MAX-ACCESS  read-only
    STATUS      current
    DESCRIPTION "Number of ARP Queue Full Drop Pkts"
    ::= { affirmedNetworkContextIpLogicalIntfStatsArpStatsEntry 16 }

affirmedNetworkContextIpLogicalIntfStatsArpStatsNumArpEntryAllocFails OBJECT-TYPE
    SYNTAX      ConfdString
    MAX-ACCESS  read-only
    STATUS      current
    DESCRIPTION "Number of ARP Entry Alloc Fails"
    ::= { affirmedNetworkContextIpLogicalIntfStatsArpStatsEntry 17 }

affirmedNetworkContextIpLogicalIntfStatsGtpStatsTable OBJECT-TYPE
    SYNTAX      SEQUENCE OF AffirmedNetworkContextIpLogicalIntfStatsGtpStatsEntry
    MAX-ACCESS  not-accessible
    STATUS      current
    DESCRIPTION ""
    ::= { affirmedNetworkcontextMIB 26 }

affirmedNetworkContextIpLogicalIntfStatsGtpStatsEntry OBJECT-TYPE
    SYNTAX      AffirmedNetworkContextIpLogicalIntfStatsGtpStatsEntry
    MAX-ACCESS  not-accessible
    STATUS      current
    DESCRIPTION ""
    INDEX { affirmedNetworkContextName, affirmedNetworkContextIpLogicalIntfStatsGtpStatsIfName }
        ::= { affirmedNetworkContextIpLogicalIntfStatsGtpStatsTable 1 }

AffirmedNetworkContextIpLogicalIntfStatsGtpStatsEntry ::=
    SEQUENCE {
        affirmedNetworkContextIpLogicalIntfStatsGtpStatsIfName String,
        affirmedNetworkContextIpLogicalIntfStatsGtpStatsIpAddress String,
        affirmedNetworkContextIpLogicalIntfStatsGtpStatsPrefix String,
        affirmedNetworkContextIpLogicalIntfStatsGtpStatsSecondaryIpAddress String,
        affirmedNetworkContextIpLogicalIntfStatsGtpStatsSecondaryPrefixLength String,
        affirmedNetworkContextIpLogicalIntfStatsGtpStatsOperStatus String,
        affirmedNetworkContextIpLogicalIntfStatsGtpStatsNumRxV4GtpUV0DropPkts ConfdString,
        affirmedNetworkContextIpLogicalIntfStatsGtpStatsNumRxV4GtpUPortVersionMisMatchDropPkts ConfdString,
        affirmedNetworkContextIpLogicalIntfStatsGtpStatsNumRxV6GtpUV0DropPkts ConfdString,
        affirmedNetworkContextIpLogicalIntfStatsGtpStatsNumRxV6GtpUPortVersionMisMatchDropPkts ConfdString,
        affirmedNetworkContextIpLogicalIntfStatsGtpStatsNumRxGtpBadIpDropPkts ConfdString
    }

affirmedNetworkContextIpLogicalIntfStatsGtpStatsIfName OBJECT-TYPE
    SYNTAX      String
    MAX-ACCESS  not-accessible
    STATUS      current
    DESCRIPTION "IP interface name"
    ::= { affirmedNetworkContextIpLogicalIntfStatsGtpStatsEntry 1 }

affirmedNetworkContextIpLogicalIntfStatsGtpStatsIpAddress OBJECT-TYPE
    SYNTAX      String
    MAX-ACCESS  read-only
    STATUS      current
    DESCRIPTION "Address of the IP interface"
    ::= { affirmedNetworkContextIpLogicalIntfStatsGtpStatsEntry 2 }

affirmedNetworkContextIpLogicalIntfStatsGtpStatsPrefix OBJECT-TYPE
    SYNTAX      String
    MAX-ACCESS  read-only
    STATUS      current
    DESCRIPTION "Prefix length of the IP address"
    ::= { affirmedNetworkContextIpLogicalIntfStatsGtpStatsEntry 3 }

affirmedNetworkContextIpLogicalIntfStatsGtpStatsSecondaryIpAddress OBJECT-TYPE
    SYNTAX      String
    MAX-ACCESS  read-only
    STATUS      current
    DESCRIPTION "Secondary address of the IP interface"
    ::= { affirmedNetworkContextIpLogicalIntfStatsGtpStatsEntry 4 }

affirmedNetworkContextIpLogicalIntfStatsGtpStatsSecondaryPrefixLength OBJECT-TYPE
    SYNTAX      String
    MAX-ACCESS  read-only
    STATUS      current
    DESCRIPTION "Secondary prefix length of the IP address"
    ::= { affirmedNetworkContextIpLogicalIntfStatsGtpStatsEntry 5 }

affirmedNetworkContextIpLogicalIntfStatsGtpStatsOperStatus OBJECT-TYPE
    SYNTAX      String
    MAX-ACCESS  read-only
    STATUS      current
    DESCRIPTION "Interface operation status"
    ::= { affirmedNetworkContextIpLogicalIntfStatsGtpStatsEntry 6 }

affirmedNetworkContextIpLogicalIntfStatsGtpStatsNumRxV4GtpUV0DropPkts OBJECT-TYPE
    SYNTAX      ConfdString
    MAX-ACCESS  read-only
    STATUS      current
    DESCRIPTION "Number of  Rx IPv4 GTPU V0 Drop Pkts"
    ::= { affirmedNetworkContextIpLogicalIntfStatsGtpStatsEntry 7 }

affirmedNetworkContextIpLogicalIntfStatsGtpStatsNumRxV4GtpUPortVersionMisMatchDropPkts OBJECT-TYPE
    SYNTAX      ConfdString
    MAX-ACCESS  read-only
    STATUS      current
    DESCRIPTION "Number of  Rx IPv4 GTPU Port Version MisMatch Drop Pkts"
    ::= { affirmedNetworkContextIpLogicalIntfStatsGtpStatsEntry 8 }

affirmedNetworkContextIpLogicalIntfStatsGtpStatsNumRxV6GtpUV0DropPkts OBJECT-TYPE
    SYNTAX      ConfdString
    MAX-ACCESS  read-only
    STATUS      current
    DESCRIPTION "Number of  Rx IPv6 GTPU V0 Drop Pkts"
    ::= { affirmedNetworkContextIpLogicalIntfStatsGtpStatsEntry 9 }

affirmedNetworkContextIpLogicalIntfStatsGtpStatsNumRxV6GtpUPortVersionMisMatchDropPkts OBJECT-TYPE
    SYNTAX      ConfdString
    MAX-ACCESS  read-only
    STATUS      current
    DESCRIPTION "Number of  Rx IPv6 GTPU PortVersion MisMatch Drop Pkts"
    ::= { affirmedNetworkContextIpLogicalIntfStatsGtpStatsEntry 10 }

affirmedNetworkContextIpLogicalIntfStatsGtpStatsNumRxGtpBadIpDropPkts OBJECT-TYPE
    SYNTAX      ConfdString
    MAX-ACCESS  read-only
    STATUS      current
    DESCRIPTION "Number of  Rx Gtp Bad IP Drop Pkts"
    ::= { affirmedNetworkContextIpLogicalIntfStatsGtpStatsEntry 11 }

affirmedNetworkContextIpLogicalIntfStatsIpStatsTable OBJECT-TYPE
    SYNTAX      SEQUENCE OF AffirmedNetworkContextIpLogicalIntfStatsIpStatsEntry
    MAX-ACCESS  not-accessible
    STATUS      current
    DESCRIPTION ""
    ::= { affirmedNetworkcontextMIB 27 }

affirmedNetworkContextIpLogicalIntfStatsIpStatsEntry OBJECT-TYPE
    SYNTAX      AffirmedNetworkContextIpLogicalIntfStatsIpStatsEntry
    MAX-ACCESS  not-accessible
    STATUS      current
    DESCRIPTION ""
    INDEX { affirmedNetworkContextName, affirmedNetworkContextIpLogicalIntfStatsIpStatsIfName }
        ::= { affirmedNetworkContextIpLogicalIntfStatsIpStatsTable 1 }

AffirmedNetworkContextIpLogicalIntfStatsIpStatsEntry ::=
    SEQUENCE {
        affirmedNetworkContextIpLogicalIntfStatsIpStatsIfName String,
        affirmedNetworkContextIpLogicalIntfStatsIpStatsIpAddress String,
        affirmedNetworkContextIpLogicalIntfStatsIpStatsPrefix String,
        affirmedNetworkContextIpLogicalIntfStatsIpStatsSecondaryIpAddress String,
        affirmedNetworkContextIpLogicalIntfStatsIpStatsSecondaryPrefixLength String,
        affirmedNetworkContextIpLogicalIntfStatsIpStatsOperStatus String,
        affirmedNetworkContextIpLogicalIntfStatsIpStatsNumRxIpNatPkts ConfdString,
        affirmedNetworkContextIpLogicalIntfStatsIpStatsNumRxIpKncmPkts ConfdString,
        affirmedNetworkContextIpLogicalIntfStatsIpStatsNumRxIpOspfPkts ConfdString,
        affirmedNetworkContextIpLogicalIntfStatsIpStatsNumRxIpBgpPkts ConfdString,
        affirmedNetworkContextIpLogicalIntfStatsIpStatsNumRxIpBroadcastPkts ConfdString,
        affirmedNetworkContextIpLogicalIntfStatsIpStatsNumRxIpSubnetBroadcastPkts ConfdString,
        affirmedNetworkContextIpLogicalIntfStatsIpStatsNumRxIpLoopbackNetPkts ConfdString,
        affirmedNetworkContextIpLogicalIntfStatsIpStatsNumRxIpTTLExceededPkts ConfdString,
        affirmedNetworkContextIpLogicalIntfStatsIpStatsNumRxIpNoFragPkts ConfdString
    }

affirmedNetworkContextIpLogicalIntfStatsIpStatsIfName OBJECT-TYPE
    SYNTAX      String
    MAX-ACCESS  not-accessible
    STATUS      current
    DESCRIPTION "IP interface name"
    ::= { affirmedNetworkContextIpLogicalIntfStatsIpStatsEntry 1 }

affirmedNetworkContextIpLogicalIntfStatsIpStatsIpAddress OBJECT-TYPE
    SYNTAX      String
    MAX-ACCESS  read-only
    STATUS      current
    DESCRIPTION "Address of the IP interface"
    ::= { affirmedNetworkContextIpLogicalIntfStatsIpStatsEntry 2 }

affirmedNetworkContextIpLogicalIntfStatsIpStatsPrefix OBJECT-TYPE
    SYNTAX      String
    MAX-ACCESS  read-only
    STATUS      current
    DESCRIPTION "Prefix length of the IP address"
    ::= { affirmedNetworkContextIpLogicalIntfStatsIpStatsEntry 3 }

affirmedNetworkContextIpLogicalIntfStatsIpStatsSecondaryIpAddress OBJECT-TYPE
    SYNTAX      String
    MAX-ACCESS  read-only
    STATUS      current
    DESCRIPTION "Secondary address of the IP interface"
    ::= { affirmedNetworkContextIpLogicalIntfStatsIpStatsEntry 4 }

affirmedNetworkContextIpLogicalIntfStatsIpStatsSecondaryPrefixLength OBJECT-TYPE
    SYNTAX      String
    MAX-ACCESS  read-only
    STATUS      current
    DESCRIPTION "Secondary prefix length of the IP address"
    ::= { affirmedNetworkContextIpLogicalIntfStatsIpStatsEntry 5 }

affirmedNetworkContextIpLogicalIntfStatsIpStatsOperStatus OBJECT-TYPE
    SYNTAX      String
    MAX-ACCESS  read-only
    STATUS      current
    DESCRIPTION "Interface operation status"
    ::= { affirmedNetworkContextIpLogicalIntfStatsIpStatsEntry 6 }

affirmedNetworkContextIpLogicalIntfStatsIpStatsNumRxIpNatPkts OBJECT-TYPE
    SYNTAX      ConfdString
    MAX-ACCESS  read-only
    STATUS      current
    DESCRIPTION "Number of  Rx IP NAT Pkts"
    ::= { affirmedNetworkContextIpLogicalIntfStatsIpStatsEntry 7 }

affirmedNetworkContextIpLogicalIntfStatsIpStatsNumRxIpKncmPkts OBJECT-TYPE
    SYNTAX      ConfdString
    MAX-ACCESS  read-only
    STATUS      current
    DESCRIPTION "Number of  Rx IP Kncm Pkts"
    ::= { affirmedNetworkContextIpLogicalIntfStatsIpStatsEntry 8 }

affirmedNetworkContextIpLogicalIntfStatsIpStatsNumRxIpOspfPkts OBJECT-TYPE
    SYNTAX      ConfdString
    MAX-ACCESS  read-only
    STATUS      current
    DESCRIPTION "Number of  Rx IP OSPF Pkts"
    ::= { affirmedNetworkContextIpLogicalIntfStatsIpStatsEntry 9 }

affirmedNetworkContextIpLogicalIntfStatsIpStatsNumRxIpBgpPkts OBJECT-TYPE
    SYNTAX      ConfdString
    MAX-ACCESS  read-only
    STATUS      current
    DESCRIPTION "Number of  Rx IP BGP Pkts"
    ::= { affirmedNetworkContextIpLogicalIntfStatsIpStatsEntry 10 }

affirmedNetworkContextIpLogicalIntfStatsIpStatsNumRxIpBroadcastPkts OBJECT-TYPE
    SYNTAX      ConfdString
    MAX-ACCESS  read-only
    STATUS      current
    DESCRIPTION "Number of  Rx IP Broadcast Pkts"
    ::= { affirmedNetworkContextIpLogicalIntfStatsIpStatsEntry 11 }

affirmedNetworkContextIpLogicalIntfStatsIpStatsNumRxIpSubnetBroadcastPkts OBJECT-TYPE
    SYNTAX      ConfdString
    MAX-ACCESS  read-only
    STATUS      current
    DESCRIPTION "Number of  Rx IP Subnet Broadcast Pkts"
    ::= { affirmedNetworkContextIpLogicalIntfStatsIpStatsEntry 12 }

affirmedNetworkContextIpLogicalIntfStatsIpStatsNumRxIpLoopbackNetPkts OBJECT-TYPE
    SYNTAX      ConfdString
    MAX-ACCESS  read-only
    STATUS      current
    DESCRIPTION "Number of  Rx IP LoopbackNet Pkts"
    ::= { affirmedNetworkContextIpLogicalIntfStatsIpStatsEntry 13 }

affirmedNetworkContextIpLogicalIntfStatsIpStatsNumRxIpTTLExceededPkts OBJECT-TYPE
    SYNTAX      ConfdString
    MAX-ACCESS  read-only
    STATUS      current
    DESCRIPTION "Number of  Rx IP TTL Exceeded Pkts"
    ::= { affirmedNetworkContextIpLogicalIntfStatsIpStatsEntry 14 }

affirmedNetworkContextIpLogicalIntfStatsIpStatsNumRxIpNoFragPkts OBJECT-TYPE
    SYNTAX      ConfdString
    MAX-ACCESS  read-only
    STATUS      current
    DESCRIPTION "Number of  Rx IP No Frag Pkts"
    ::= { affirmedNetworkContextIpLogicalIntfStatsIpStatsEntry 15 }

affirmedNetworkContextIpLogicalIntfStatsMplsStatsTable OBJECT-TYPE
    SYNTAX      SEQUENCE OF AffirmedNetworkContextIpLogicalIntfStatsMplsStatsEntry
    MAX-ACCESS  not-accessible
    STATUS      current
    DESCRIPTION ""
    ::= { affirmedNetworkcontextMIB 28 }

affirmedNetworkContextIpLogicalIntfStatsMplsStatsEntry OBJECT-TYPE
    SYNTAX      AffirmedNetworkContextIpLogicalIntfStatsMplsStatsEntry
    MAX-ACCESS  not-accessible
    STATUS      current
    DESCRIPTION ""
    INDEX { affirmedNetworkContextName, affirmedNetworkContextIpLogicalIntfStatsMplsStatsIfName }
        ::= { affirmedNetworkContextIpLogicalIntfStatsMplsStatsTable 1 }

AffirmedNetworkContextIpLogicalIntfStatsMplsStatsEntry ::=
    SEQUENCE {
        affirmedNetworkContextIpLogicalIntfStatsMplsStatsIfName String,
        affirmedNetworkContextIpLogicalIntfStatsMplsStatsIpAddress String,
        affirmedNetworkContextIpLogicalIntfStatsMplsStatsPrefix String,
        affirmedNetworkContextIpLogicalIntfStatsMplsStatsSecondaryIpAddress String,
        affirmedNetworkContextIpLogicalIntfStatsMplsStatsSecondaryPrefixLength String,
        affirmedNetworkContextIpLogicalIntfStatsMplsStatsOperStatus String,
        affirmedNetworkContextIpLogicalIntfStatsMplsStatsNumRxMplsPkts ConfdString,
        affirmedNetworkContextIpLogicalIntfStatsMplsStatsNumRxMplsBytes ConfdString,
        affirmedNetworkContextIpLogicalIntfStatsMplsStatsNumTxMplsPkts ConfdString,
        affirmedNetworkContextIpLogicalIntfStatsMplsStatsNumTxMplsBytes ConfdString,
        affirmedNetworkContextIpLogicalIntfStatsMplsStatsNumRxMplsUnknownLabelPkts ConfdString,
        affirmedNetworkContextIpLogicalIntfStatsMplsStatsNumRxMplsDropPkts ConfdString
    }

affirmedNetworkContextIpLogicalIntfStatsMplsStatsIfName OBJECT-TYPE
    SYNTAX      String
    MAX-ACCESS  not-accessible
    STATUS      current
    DESCRIPTION "IP interface name"
    ::= { affirmedNetworkContextIpLogicalIntfStatsMplsStatsEntry 1 }

affirmedNetworkContextIpLogicalIntfStatsMplsStatsIpAddress OBJECT-TYPE
    SYNTAX      String
    MAX-ACCESS  read-only
    STATUS      current
    DESCRIPTION "Address of the IP interface"
    ::= { affirmedNetworkContextIpLogicalIntfStatsMplsStatsEntry 2 }

affirmedNetworkContextIpLogicalIntfStatsMplsStatsPrefix OBJECT-TYPE
    SYNTAX      String
    MAX-ACCESS  read-only
    STATUS      current
    DESCRIPTION "Prefix length of the IP address"
    ::= { affirmedNetworkContextIpLogicalIntfStatsMplsStatsEntry 3 }

affirmedNetworkContextIpLogicalIntfStatsMplsStatsSecondaryIpAddress OBJECT-TYPE
    SYNTAX      String
    MAX-ACCESS  read-only
    STATUS      current
    DESCRIPTION "Secondary address of the IP interface"
    ::= { affirmedNetworkContextIpLogicalIntfStatsMplsStatsEntry 4 }

affirmedNetworkContextIpLogicalIntfStatsMplsStatsSecondaryPrefixLength OBJECT-TYPE
    SYNTAX      String
    MAX-ACCESS  read-only
    STATUS      current
    DESCRIPTION "Secondary prefix length of the IP address"
    ::= { affirmedNetworkContextIpLogicalIntfStatsMplsStatsEntry 5 }

affirmedNetworkContextIpLogicalIntfStatsMplsStatsOperStatus OBJECT-TYPE
    SYNTAX      String
    MAX-ACCESS  read-only
    STATUS      current
    DESCRIPTION "Interface operation status"
    ::= { affirmedNetworkContextIpLogicalIntfStatsMplsStatsEntry 6 }

affirmedNetworkContextIpLogicalIntfStatsMplsStatsNumRxMplsPkts OBJECT-TYPE
    SYNTAX      ConfdString
    MAX-ACCESS  read-only
    STATUS      current
    DESCRIPTION "Number of Rx MPLS  Pkts"
    ::= { affirmedNetworkContextIpLogicalIntfStatsMplsStatsEntry 7 }

affirmedNetworkContextIpLogicalIntfStatsMplsStatsNumRxMplsBytes OBJECT-TYPE
    SYNTAX      ConfdString
    MAX-ACCESS  read-only
    STATUS      current
    DESCRIPTION "Number of Rx MPLS  Bytes"
    ::= { affirmedNetworkContextIpLogicalIntfStatsMplsStatsEntry 8 }

affirmedNetworkContextIpLogicalIntfStatsMplsStatsNumTxMplsPkts OBJECT-TYPE
    SYNTAX      ConfdString
    MAX-ACCESS  read-only
    STATUS      current
    DESCRIPTION "Number of Tx MPLS Pkts"
    ::= { affirmedNetworkContextIpLogicalIntfStatsMplsStatsEntry 9 }

affirmedNetworkContextIpLogicalIntfStatsMplsStatsNumTxMplsBytes OBJECT-TYPE
    SYNTAX      ConfdString
    MAX-ACCESS  read-only
    STATUS      current
    DESCRIPTION "Number of Tx MPLS Bytes"
    ::= { affirmedNetworkContextIpLogicalIntfStatsMplsStatsEntry 10 }

affirmedNetworkContextIpLogicalIntfStatsMplsStatsNumRxMplsUnknownLabelPkts OBJECT-TYPE
    SYNTAX      ConfdString
    MAX-ACCESS  read-only
    STATUS      current
    DESCRIPTION "Number of Rx MPLS  Unknown Label Pkts"
    ::= { affirmedNetworkContextIpLogicalIntfStatsMplsStatsEntry 11 }

affirmedNetworkContextIpLogicalIntfStatsMplsStatsNumRxMplsDropPkts OBJECT-TYPE
    SYNTAX      ConfdString
    MAX-ACCESS  read-only
    STATUS      current
    DESCRIPTION "Number of Rx MPLS  Drop Pkts"
    ::= { affirmedNetworkContextIpLogicalIntfStatsMplsStatsEntry 12 }

affirmedNetworkContextIpLogicalIntfStatsOtherStatsTable OBJECT-TYPE
    SYNTAX      SEQUENCE OF AffirmedNetworkContextIpLogicalIntfStatsOtherStatsEntry
    MAX-ACCESS  not-accessible
    STATUS      current
    DESCRIPTION ""
    ::= { affirmedNetworkcontextMIB 29 }

affirmedNetworkContextIpLogicalIntfStatsOtherStatsEntry OBJECT-TYPE
    SYNTAX      AffirmedNetworkContextIpLogicalIntfStatsOtherStatsEntry
    MAX-ACCESS  not-accessible
    STATUS      current
    DESCRIPTION ""
    INDEX { affirmedNetworkContextName, affirmedNetworkContextIpLogicalIntfStatsOtherStatsIfName }
        ::= { affirmedNetworkContextIpLogicalIntfStatsOtherStatsTable 1 }

AffirmedNetworkContextIpLogicalIntfStatsOtherStatsEntry ::=
    SEQUENCE {
        affirmedNetworkContextIpLogicalIntfStatsOtherStatsIfName String,
        affirmedNetworkContextIpLogicalIntfStatsOtherStatsIpAddress String,
        affirmedNetworkContextIpLogicalIntfStatsOtherStatsPrefix String,
        affirmedNetworkContextIpLogicalIntfStatsOtherStatsSecondaryIpAddress String,
        affirmedNetworkContextIpLogicalIntfStatsOtherStatsSecondaryPrefixLength String,
        affirmedNetworkContextIpLogicalIntfStatsOtherStatsOperStatus String,
        affirmedNetworkContextIpLogicalIntfStatsOtherStatsNumTxKernelPkts ConfdString,
        affirmedNetworkContextIpLogicalIntfStatsOtherStatsNumRxGwControlPkts ConfdString,
        affirmedNetworkContextIpLogicalIntfStatsOtherStatsNumRxStandbyGeoRedControlPkts ConfdString,
        affirmedNetworkContextIpLogicalIntfStatsOtherStatsNumRxDropOperDownPkts ConfdString,
        affirmedNetworkContextIpLogicalIntfStatsOtherStatsNumRxGwErrorIndicationPkts ConfdString,
        affirmedNetworkContextIpLogicalIntfStatsOtherStatsNumRxErrIndRateLimitDropPkts ConfdString,
        affirmedNetworkContextIpLogicalIntfStatsOtherStatsNumRxMccUpstreamPkts ConfdString,
        affirmedNetworkContextIpLogicalIntfStatsOtherStatsNumRxBfdPkts ConfdString,
        affirmedNetworkContextIpLogicalIntfStatsOtherStatsNumTxNoRouteDropPkts ConfdString,
        affirmedNetworkContextIpLogicalIntfStatsOtherStatsNumTxFragmentedPkts ConfdString,
        affirmedNetworkContextIpLogicalIntfStatsOtherStatsNumTxInvalidPkts ConfdString,
        affirmedNetworkContextIpLogicalIntfStatsOtherStatsNumTxNoNextHopPkts ConfdString,
        affirmedNetworkContextIpLogicalIntfStatsOtherStatsNumTxEarlyIkePktDrops ConfdString,
        affirmedNetworkContextIpLogicalIntfStatsOtherStatsNumRxGREPkts ConfdString,
        affirmedNetworkContextIpLogicalIntfStatsOtherStatsNumTunnelNotFoundPkts ConfdString,
        affirmedNetworkContextIpLogicalIntfStatsOtherStatsNumInvalidTunnelPkts ConfdString,
        affirmedNetworkContextIpLogicalIntfStatsOtherStatsNumInvalidTunnelInnerDstPkts ConfdString,
        affirmedNetworkContextIpLogicalIntfStatsOtherStatsNumRxTeIdZeroVerDataPkts ConfdString,
        affirmedNetworkContextIpLogicalIntfStatsOtherStatsNumCsmProxySynDropPkts ConfdString
    }

affirmedNetworkContextIpLogicalIntfStatsOtherStatsIfName OBJECT-TYPE
    SYNTAX      String
    MAX-ACCESS  not-accessible
    STATUS      current
    DESCRIPTION "IP interface name"
    ::= { affirmedNetworkContextIpLogicalIntfStatsOtherStatsEntry 1 }

affirmedNetworkContextIpLogicalIntfStatsOtherStatsIpAddress OBJECT-TYPE
    SYNTAX      String
    MAX-ACCESS  read-only
    STATUS      current
    DESCRIPTION "Address of the IP interface"
    ::= { affirmedNetworkContextIpLogicalIntfStatsOtherStatsEntry 2 }

affirmedNetworkContextIpLogicalIntfStatsOtherStatsPrefix OBJECT-TYPE
    SYNTAX      String
    MAX-ACCESS  read-only
    STATUS      current
    DESCRIPTION "Prefix length of the IP address"
    ::= { affirmedNetworkContextIpLogicalIntfStatsOtherStatsEntry 3 }

affirmedNetworkContextIpLogicalIntfStatsOtherStatsSecondaryIpAddress OBJECT-TYPE
    SYNTAX      String
    MAX-ACCESS  read-only
    STATUS      current
    DESCRIPTION "Secondary address of the IP interface"
    ::= { affirmedNetworkContextIpLogicalIntfStatsOtherStatsEntry 4 }

affirmedNetworkContextIpLogicalIntfStatsOtherStatsSecondaryPrefixLength OBJECT-TYPE
    SYNTAX      String
    MAX-ACCESS  read-only
    STATUS      current
    DESCRIPTION "Secondary prefix length of the IP address"
    ::= { affirmedNetworkContextIpLogicalIntfStatsOtherStatsEntry 5 }

affirmedNetworkContextIpLogicalIntfStatsOtherStatsOperStatus OBJECT-TYPE
    SYNTAX      String
    MAX-ACCESS  read-only
    STATUS      current
    DESCRIPTION "Interface operation status"
    ::= { affirmedNetworkContextIpLogicalIntfStatsOtherStatsEntry 6 }

affirmedNetworkContextIpLogicalIntfStatsOtherStatsNumTxKernelPkts OBJECT-TYPE
    SYNTAX      ConfdString
    MAX-ACCESS  read-only
    STATUS      current
    DESCRIPTION "Number of Tx Kernel Pkts "
    ::= { affirmedNetworkContextIpLogicalIntfStatsOtherStatsEntry 7 }

affirmedNetworkContextIpLogicalIntfStatsOtherStatsNumRxGwControlPkts OBJECT-TYPE
    SYNTAX      ConfdString
    MAX-ACCESS  read-only
    STATUS      current
    DESCRIPTION "Number of Rx GW Control Pkts "
    ::= { affirmedNetworkContextIpLogicalIntfStatsOtherStatsEntry 8 }

affirmedNetworkContextIpLogicalIntfStatsOtherStatsNumRxStandbyGeoRedControlPkts OBJECT-TYPE
    SYNTAX      ConfdString
    MAX-ACCESS  read-only
    STATUS      current
    DESCRIPTION "Number of Rx Standby GeoRed Control Pkts "
    ::= { affirmedNetworkContextIpLogicalIntfStatsOtherStatsEntry 9 }

affirmedNetworkContextIpLogicalIntfStatsOtherStatsNumRxDropOperDownPkts OBJECT-TYPE
    SYNTAX      ConfdString
    MAX-ACCESS  read-only
    STATUS      current
    DESCRIPTION "Number of Rx Drop Oper Down Pkts "
    ::= { affirmedNetworkContextIpLogicalIntfStatsOtherStatsEntry 10 }

affirmedNetworkContextIpLogicalIntfStatsOtherStatsNumRxGwErrorIndicationPkts OBJECT-TYPE
    SYNTAX      ConfdString
    MAX-ACCESS  read-only
    STATUS      current
    DESCRIPTION "Number of Rx GW Error Indication Pkts "
    ::= { affirmedNetworkContextIpLogicalIntfStatsOtherStatsEntry 11 }

affirmedNetworkContextIpLogicalIntfStatsOtherStatsNumRxErrIndRateLimitDropPkts OBJECT-TYPE
    SYNTAX      ConfdString
    MAX-ACCESS  read-only
    STATUS      current
    DESCRIPTION "Number of Rx Err Ind RateLimit Drop Pkts "
    ::= { affirmedNetworkContextIpLogicalIntfStatsOtherStatsEntry 12 }

affirmedNetworkContextIpLogicalIntfStatsOtherStatsNumRxMccUpstreamPkts OBJECT-TYPE
    SYNTAX      ConfdString
    MAX-ACCESS  read-only
    STATUS      current
    DESCRIPTION "Number of Rx MCC Upstream Pkts "
    ::= { affirmedNetworkContextIpLogicalIntfStatsOtherStatsEntry 13 }

affirmedNetworkContextIpLogicalIntfStatsOtherStatsNumRxBfdPkts OBJECT-TYPE
    SYNTAX      ConfdString
    MAX-ACCESS  read-only
    STATUS      current
    DESCRIPTION "Number of Rx BFD Pkts "
    ::= { affirmedNetworkContextIpLogicalIntfStatsOtherStatsEntry 14 }

affirmedNetworkContextIpLogicalIntfStatsOtherStatsNumTxNoRouteDropPkts OBJECT-TYPE
    SYNTAX      ConfdString
    MAX-ACCESS  read-only
    STATUS      current
    DESCRIPTION "Number of Tx No Route Drop Pkts "
    ::= { affirmedNetworkContextIpLogicalIntfStatsOtherStatsEntry 15 }

affirmedNetworkContextIpLogicalIntfStatsOtherStatsNumTxFragmentedPkts OBJECT-TYPE
    SYNTAX      ConfdString
    MAX-ACCESS  read-only
    STATUS      current
    DESCRIPTION "Number of Tx Fragmented Pkts "
    ::= { affirmedNetworkContextIpLogicalIntfStatsOtherStatsEntry 16 }

affirmedNetworkContextIpLogicalIntfStatsOtherStatsNumTxInvalidPkts OBJECT-TYPE
    SYNTAX      ConfdString
    MAX-ACCESS  read-only
    STATUS      current
    DESCRIPTION "Number of Tx Invalid Pkts "
    ::= { affirmedNetworkContextIpLogicalIntfStatsOtherStatsEntry 17 }

affirmedNetworkContextIpLogicalIntfStatsOtherStatsNumTxNoNextHopPkts OBJECT-TYPE
    SYNTAX      ConfdString
    MAX-ACCESS  read-only
    STATUS      current
    DESCRIPTION "Number of Tx No NextHop Pkts "
    ::= { affirmedNetworkContextIpLogicalIntfStatsOtherStatsEntry 18 }

affirmedNetworkContextIpLogicalIntfStatsOtherStatsNumTxEarlyIkePktDrops OBJECT-TYPE
    SYNTAX      ConfdString
    MAX-ACCESS  read-only
    STATUS      current
    DESCRIPTION "Number of Tx Early IKE Pkt Drops"
    ::= { affirmedNetworkContextIpLogicalIntfStatsOtherStatsEntry 19 }

affirmedNetworkContextIpLogicalIntfStatsOtherStatsNumRxGREPkts OBJECT-TYPE
    SYNTAX      ConfdString
    MAX-ACCESS  read-only
    STATUS      current
    DESCRIPTION "Number of Rx GRE Pkts "
    ::= { affirmedNetworkContextIpLogicalIntfStatsOtherStatsEntry 20 }

affirmedNetworkContextIpLogicalIntfStatsOtherStatsNumTunnelNotFoundPkts OBJECT-TYPE
    SYNTAX      ConfdString
    MAX-ACCESS  read-only
    STATUS      current
    DESCRIPTION "Number of Tunnel Not Found Pkts "
    ::= { affirmedNetworkContextIpLogicalIntfStatsOtherStatsEntry 21 }

affirmedNetworkContextIpLogicalIntfStatsOtherStatsNumInvalidTunnelPkts OBJECT-TYPE
    SYNTAX      ConfdString
    MAX-ACCESS  read-only
    STATUS      current
    DESCRIPTION "Number of Invalid Tunnel Pkts "
    ::= { affirmedNetworkContextIpLogicalIntfStatsOtherStatsEntry 22 }

affirmedNetworkContextIpLogicalIntfStatsOtherStatsNumInvalidTunnelInnerDstPkts OBJECT-TYPE
    SYNTAX      ConfdString
    MAX-ACCESS  read-only
    STATUS      current
    DESCRIPTION "Number of Invalid Tunnel Inner Dst Pkts "
    ::= { affirmedNetworkContextIpLogicalIntfStatsOtherStatsEntry 23 }

affirmedNetworkContextIpLogicalIntfStatsOtherStatsNumRxTeIdZeroVerDataPkts OBJECT-TYPE
    SYNTAX      ConfdString
    MAX-ACCESS  read-only
    STATUS      current
    DESCRIPTION "Number of Rx TEID Zero Ver Data Pkts "
    ::= { affirmedNetworkContextIpLogicalIntfStatsOtherStatsEntry 24 }

affirmedNetworkContextIpLogicalIntfStatsOtherStatsNumCsmProxySynDropPkts OBJECT-TYPE
    SYNTAX      ConfdString
    MAX-ACCESS  read-only
    STATUS      current
    DESCRIPTION "Number of CSM Proxy Syn Drop Pkts "
    ::= { affirmedNetworkContextIpLogicalIntfStatsOtherStatsEntry 25 }

affirmedNetworkContextIpLogicalIntfStatsSecurityStatsTable OBJECT-TYPE
    SYNTAX      SEQUENCE OF AffirmedNetworkContextIpLogicalIntfStatsSecurityStatsEntry
    MAX-ACCESS  not-accessible
    STATUS      current
    DESCRIPTION ""
    ::= { affirmedNetworkcontextMIB 30 }

affirmedNetworkContextIpLogicalIntfStatsSecurityStatsEntry OBJECT-TYPE
    SYNTAX      AffirmedNetworkContextIpLogicalIntfStatsSecurityStatsEntry
    MAX-ACCESS  not-accessible
    STATUS      current
    DESCRIPTION ""
    INDEX { affirmedNetworkContextName, affirmedNetworkContextIpLogicalIntfStatsSecurityStatsIfName }
        ::= { affirmedNetworkContextIpLogicalIntfStatsSecurityStatsTable 1 }

AffirmedNetworkContextIpLogicalIntfStatsSecurityStatsEntry ::=
    SEQUENCE {
        affirmedNetworkContextIpLogicalIntfStatsSecurityStatsIfName String,
        affirmedNetworkContextIpLogicalIntfStatsSecurityStatsIpAddress String,
        affirmedNetworkContextIpLogicalIntfStatsSecurityStatsPrefix String,
        affirmedNetworkContextIpLogicalIntfStatsSecurityStatsSecondaryIpAddress String,
        affirmedNetworkContextIpLogicalIntfStatsSecurityStatsSecondaryPrefixLength String,
        affirmedNetworkContextIpLogicalIntfStatsSecurityStatsOperStatus String,
        affirmedNetworkContextIpLogicalIntfStatsSecurityStatsNumRxSecurityForwardedPkts ConfdString,
        affirmedNetworkContextIpLogicalIntfStatsSecurityStatsNumTxSecurityForwardedPkts ConfdString,
        affirmedNetworkContextIpLogicalIntfStatsSecurityStatsNumRxDropSecurityErrorPkts ConfdString,
        affirmedNetworkContextIpLogicalIntfStatsSecurityStatsNumTxDropSecurityErrorPkts ConfdString
    }

affirmedNetworkContextIpLogicalIntfStatsSecurityStatsIfName OBJECT-TYPE
    SYNTAX      String
    MAX-ACCESS  not-accessible
    STATUS      current
    DESCRIPTION "IP interface name"
    ::= { affirmedNetworkContextIpLogicalIntfStatsSecurityStatsEntry 1 }

affirmedNetworkContextIpLogicalIntfStatsSecurityStatsIpAddress OBJECT-TYPE
    SYNTAX      String
    MAX-ACCESS  read-only
    STATUS      current
    DESCRIPTION "Address of the IP interface"
    ::= { affirmedNetworkContextIpLogicalIntfStatsSecurityStatsEntry 2 }

affirmedNetworkContextIpLogicalIntfStatsSecurityStatsPrefix OBJECT-TYPE
    SYNTAX      String
    MAX-ACCESS  read-only
    STATUS      current
    DESCRIPTION "Prefix length of the IP address"
    ::= { affirmedNetworkContextIpLogicalIntfStatsSecurityStatsEntry 3 }

affirmedNetworkContextIpLogicalIntfStatsSecurityStatsSecondaryIpAddress OBJECT-TYPE
    SYNTAX      String
    MAX-ACCESS  read-only
    STATUS      current
    DESCRIPTION "Secondary address of the IP interface"
    ::= { affirmedNetworkContextIpLogicalIntfStatsSecurityStatsEntry 4 }

affirmedNetworkContextIpLogicalIntfStatsSecurityStatsSecondaryPrefixLength OBJECT-TYPE
    SYNTAX      String
    MAX-ACCESS  read-only
    STATUS      current
    DESCRIPTION "Secondary prefix length of the IP address"
    ::= { affirmedNetworkContextIpLogicalIntfStatsSecurityStatsEntry 5 }

affirmedNetworkContextIpLogicalIntfStatsSecurityStatsOperStatus OBJECT-TYPE
    SYNTAX      String
    MAX-ACCESS  read-only
    STATUS      current
    DESCRIPTION "Interface operation status"
    ::= { affirmedNetworkContextIpLogicalIntfStatsSecurityStatsEntry 6 }

affirmedNetworkContextIpLogicalIntfStatsSecurityStatsNumRxSecurityForwardedPkts OBJECT-TYPE
    SYNTAX      ConfdString
    MAX-ACCESS  read-only
    STATUS      current
    DESCRIPTION "Number of  Rx Security Forwarded Pkts"
    ::= { affirmedNetworkContextIpLogicalIntfStatsSecurityStatsEntry 7 }

affirmedNetworkContextIpLogicalIntfStatsSecurityStatsNumTxSecurityForwardedPkts OBJECT-TYPE
    SYNTAX      ConfdString
    MAX-ACCESS  read-only
    STATUS      current
    DESCRIPTION "Number of  Tx Security Forwarded Pkts"
    ::= { affirmedNetworkContextIpLogicalIntfStatsSecurityStatsEntry 8 }

affirmedNetworkContextIpLogicalIntfStatsSecurityStatsNumRxDropSecurityErrorPkts OBJECT-TYPE
    SYNTAX      ConfdString
    MAX-ACCESS  read-only
    STATUS      current
    DESCRIPTION "Number of  Rx Drop Security  Error Pkts"
    ::= { affirmedNetworkContextIpLogicalIntfStatsSecurityStatsEntry 9 }

affirmedNetworkContextIpLogicalIntfStatsSecurityStatsNumTxDropSecurityErrorPkts OBJECT-TYPE
    SYNTAX      ConfdString
    MAX-ACCESS  read-only
    STATUS      current
    DESCRIPTION "Number of  Tx Drop Security  Error Pkts"
    ::= { affirmedNetworkContextIpLogicalIntfStatsSecurityStatsEntry 10 }

affirmedNetworkContextIpLogicalIntfStatsSummaryStatsTable OBJECT-TYPE
    SYNTAX      SEQUENCE OF AffirmedNetworkContextIpLogicalIntfStatsSummaryStatsEntry
    MAX-ACCESS  not-accessible
    STATUS      current
    DESCRIPTION ""
    ::= { affirmedNetworkcontextMIB 31 }

affirmedNetworkContextIpLogicalIntfStatsSummaryStatsEntry OBJECT-TYPE
    SYNTAX      AffirmedNetworkContextIpLogicalIntfStatsSummaryStatsEntry
    MAX-ACCESS  not-accessible
    STATUS      current
    DESCRIPTION ""
    INDEX { affirmedNetworkContextName, affirmedNetworkContextIpLogicalIntfStatsSummaryStatsIfName }
        ::= { affirmedNetworkContextIpLogicalIntfStatsSummaryStatsTable 1 }

AffirmedNetworkContextIpLogicalIntfStatsSummaryStatsEntry ::=
    SEQUENCE {
        affirmedNetworkContextIpLogicalIntfStatsSummaryStatsIfName String,
        affirmedNetworkContextIpLogicalIntfStatsSummaryStatsIpAddress String,
        affirmedNetworkContextIpLogicalIntfStatsSummaryStatsPrefix String,
        affirmedNetworkContextIpLogicalIntfStatsSummaryStatsSecondaryIpAddress String,
        affirmedNetworkContextIpLogicalIntfStatsSummaryStatsSecondaryPrefixLength String,
        affirmedNetworkContextIpLogicalIntfStatsSummaryStatsOperStatus String,
        affirmedNetworkContextIpLogicalIntfStatsSummaryStatsNumTxV4Pkts ConfdString,
        affirmedNetworkContextIpLogicalIntfStatsSummaryStatsNumTxV4Bytes ConfdString,
        affirmedNetworkContextIpLogicalIntfStatsSummaryStatsNumTxV4DropPkts ConfdString,
        affirmedNetworkContextIpLogicalIntfStatsSummaryStatsNumTxV4DropBytes ConfdString,
        affirmedNetworkContextIpLogicalIntfStatsSummaryStatsNumTxKernelV4IcmpPkts ConfdString,
        affirmedNetworkContextIpLogicalIntfStatsSummaryStatsNumTxErrorIndicationPkts ConfdString,
        affirmedNetworkContextIpLogicalIntfStatsSummaryStatsNumTxErrorIndicationFailurePkts ConfdString,
        affirmedNetworkContextIpLogicalIntfStatsSummaryStatsNumTxErrorIndicationFabricPkts ConfdString,
        affirmedNetworkContextIpLogicalIntfStatsSummaryStatsNumTxErrorIndicationRateLimitPkts ConfdString,
        affirmedNetworkContextIpLogicalIntfStatsSummaryStatsNumTxV4CsmProxyPkts ConfdString,
        affirmedNetworkContextIpLogicalIntfStatsSummaryStatsNumRxV4Pkts ConfdString,
        affirmedNetworkContextIpLogicalIntfStatsSummaryStatsNumRxV4Bytes ConfdString,
        affirmedNetworkContextIpLogicalIntfStatsSummaryStatsNumRxV4DropPkts ConfdString,
        affirmedNetworkContextIpLogicalIntfStatsSummaryStatsNumRxV4DropBytes ConfdString,
        affirmedNetworkContextIpLogicalIntfStatsSummaryStatsNumRxICMPV4Pkts ConfdString,
        affirmedNetworkContextIpLogicalIntfStatsSummaryStatsNumTxICMPV4Pkts ConfdString,
        affirmedNetworkContextIpLogicalIntfStatsSummaryStatsNumRxV4UnSuppAddrPkts ConfdString,
        affirmedNetworkContextIpLogicalIntfStatsSummaryStatsNumRxV4InvalidPkts ConfdString,
        affirmedNetworkContextIpLogicalIntfStatsSummaryStatsNumRxV4MulticastPkts ConfdString,
        affirmedNetworkContextIpLogicalIntfStatsSummaryStatsNumRxV4CsmProxyPkts ConfdString,
        affirmedNetworkContextIpLogicalIntfStatsSummaryStatsNumRxV4UeUpstreamPkts ConfdString,
        affirmedNetworkContextIpLogicalIntfStatsSummaryStatsNumRxV4UeDownstreamPkts ConfdString,
        affirmedNetworkContextIpLogicalIntfStatsSummaryStatsNumRxV4UeSubnetDownstreamPkts ConfdString,
        affirmedNetworkContextIpLogicalIntfStatsSummaryStatsNumRxV4LoadbalancerPkts ConfdString,
        affirmedNetworkContextIpLogicalIntfStatsSummaryStatsNumInvalidNatPortcounter ConfdString,
        affirmedNetworkContextIpLogicalIntfStatsSummaryStatsNumRxGtpInvalidPktscounter ConfdString,
        affirmedNetworkContextIpLogicalIntfStatsSummaryStatsNumTxV6Pkts ConfdString,
        affirmedNetworkContextIpLogicalIntfStatsSummaryStatsNumTxV6Bytes ConfdString,
        affirmedNetworkContextIpLogicalIntfStatsSummaryStatsNumTxV6DropPkts ConfdString,
        affirmedNetworkContextIpLogicalIntfStatsSummaryStatsNumTxV6DropBytes ConfdString,
        affirmedNetworkContextIpLogicalIntfStatsSummaryStatsNumTxKernelV6IcmpPkts ConfdString,
        affirmedNetworkContextIpLogicalIntfStatsSummaryStatsNumTxV6CsmProxyPkts ConfdString,
        affirmedNetworkContextIpLogicalIntfStatsSummaryStatsNumRxV6Pkts ConfdString,
        affirmedNetworkContextIpLogicalIntfStatsSummaryStatsNumRxV6Bytes ConfdString,
        affirmedNetworkContextIpLogicalIntfStatsSummaryStatsNumRxV6DropPkts ConfdString,
        affirmedNetworkContextIpLogicalIntfStatsSummaryStatsNumRxV6DropBytes ConfdString,
        affirmedNetworkContextIpLogicalIntfStatsSummaryStatsNumRxICMPV6Pkts ConfdString,
        affirmedNetworkContextIpLogicalIntfStatsSummaryStatsNumRxV6UnSuppAddrPkts ConfdString,
        affirmedNetworkContextIpLogicalIntfStatsSummaryStatsNumRxV6InvalidPkts ConfdString,
        affirmedNetworkContextIpLogicalIntfStatsSummaryStatsNumRxV6IcmpNAPkts ConfdString,
        affirmedNetworkContextIpLogicalIntfStatsSummaryStatsNumRxV6IcmpTooBigPkts ConfdString,
        affirmedNetworkContextIpLogicalIntfStatsSummaryStatsNumRxV6CsmProxyPkts ConfdString,
        affirmedNetworkContextIpLogicalIntfStatsSummaryStatsNumRxV6UeUpstreamPkts ConfdString,
        affirmedNetworkContextIpLogicalIntfStatsSummaryStatsNumRxV6UeDownstreamPkts ConfdString,
        affirmedNetworkContextIpLogicalIntfStatsSummaryStatsNumRxV6UeSubnetDownstreamPkts ConfdString,
        affirmedNetworkContextIpLogicalIntfStatsSummaryStatsNumRxV6LoadbalancerPkts ConfdString,
        affirmedNetworkContextIpLogicalIntfStatsSummaryStatsNumTxICMPV6Pkts ConfdString
    }

affirmedNetworkContextIpLogicalIntfStatsSummaryStatsIfName OBJECT-TYPE
    SYNTAX      String
    MAX-ACCESS  not-accessible
    STATUS      current
    DESCRIPTION "IP interface name"
    ::= { affirmedNetworkContextIpLogicalIntfStatsSummaryStatsEntry 1 }

affirmedNetworkContextIpLogicalIntfStatsSummaryStatsIpAddress OBJECT-TYPE
    SYNTAX      String
    MAX-ACCESS  read-only
    STATUS      current
    DESCRIPTION "Address of the IP interface"
    ::= { affirmedNetworkContextIpLogicalIntfStatsSummaryStatsEntry 2 }

affirmedNetworkContextIpLogicalIntfStatsSummaryStatsPrefix OBJECT-TYPE
    SYNTAX      String
    MAX-ACCESS  read-only
    STATUS      current
    DESCRIPTION "Prefix length of the IP address"
    ::= { affirmedNetworkContextIpLogicalIntfStatsSummaryStatsEntry 3 }

affirmedNetworkContextIpLogicalIntfStatsSummaryStatsSecondaryIpAddress OBJECT-TYPE
    SYNTAX      String
    MAX-ACCESS  read-only
    STATUS      current
    DESCRIPTION "Secondary address of the IP interface"
    ::= { affirmedNetworkContextIpLogicalIntfStatsSummaryStatsEntry 4 }

affirmedNetworkContextIpLogicalIntfStatsSummaryStatsSecondaryPrefixLength OBJECT-TYPE
    SYNTAX      String
    MAX-ACCESS  read-only
    STATUS      current
    DESCRIPTION "Secondary prefix length of the IP address"
    ::= { affirmedNetworkContextIpLogicalIntfStatsSummaryStatsEntry 5 }

affirmedNetworkContextIpLogicalIntfStatsSummaryStatsOperStatus OBJECT-TYPE
    SYNTAX      String
    MAX-ACCESS  read-only
    STATUS      current
    DESCRIPTION "Interface operation status"
    ::= { affirmedNetworkContextIpLogicalIntfStatsSummaryStatsEntry 6 }

affirmedNetworkContextIpLogicalIntfStatsSummaryStatsNumTxV4Pkts OBJECT-TYPE
    SYNTAX      ConfdString
    MAX-ACCESS  read-only
    STATUS      current
    DESCRIPTION "Number of transmitted IPv4 packets"
    ::= { affirmedNetworkContextIpLogicalIntfStatsSummaryStatsEntry 7 }

affirmedNetworkContextIpLogicalIntfStatsSummaryStatsNumTxV4Bytes OBJECT-TYPE
    SYNTAX      ConfdString
    MAX-ACCESS  read-only
    STATUS      current
    DESCRIPTION "Number of transmitted IPv4 packet bytes"
    ::= { affirmedNetworkContextIpLogicalIntfStatsSummaryStatsEntry 8 }

affirmedNetworkContextIpLogicalIntfStatsSummaryStatsNumTxV4DropPkts OBJECT-TYPE
    SYNTAX      ConfdString
    MAX-ACCESS  read-only
    STATUS      current
    DESCRIPTION "Number of transmitted dropped IPv4 packets"
    ::= { affirmedNetworkContextIpLogicalIntfStatsSummaryStatsEntry 9 }

affirmedNetworkContextIpLogicalIntfStatsSummaryStatsNumTxV4DropBytes OBJECT-TYPE
    SYNTAX      ConfdString
    MAX-ACCESS  read-only
    STATUS      current
    DESCRIPTION "Number of transmitted dropped IPv4 packet bytes"
    ::= { affirmedNetworkContextIpLogicalIntfStatsSummaryStatsEntry 10 }

affirmedNetworkContextIpLogicalIntfStatsSummaryStatsNumTxKernelV4IcmpPkts OBJECT-TYPE
    SYNTAX      ConfdString
    MAX-ACCESS  read-only
    STATUS      current
    DESCRIPTION "Number of transmitted kernel IPv4 ICMP packets"
    ::= { affirmedNetworkContextIpLogicalIntfStatsSummaryStatsEntry 11 }

affirmedNetworkContextIpLogicalIntfStatsSummaryStatsNumTxErrorIndicationPkts OBJECT-TYPE
    SYNTAX      ConfdString
    MAX-ACCESS  read-only
    STATUS      current
    DESCRIPTION "Number of transmitted IPv4 error indication packets"
    ::= { affirmedNetworkContextIpLogicalIntfStatsSummaryStatsEntry 12 }

affirmedNetworkContextIpLogicalIntfStatsSummaryStatsNumTxErrorIndicationFailurePkts OBJECT-TYPE
    SYNTAX      ConfdString
    MAX-ACCESS  read-only
    STATUS      current
    DESCRIPTION "Number of transmitted IPv4 error indication failure packets"
    ::= { affirmedNetworkContextIpLogicalIntfStatsSummaryStatsEntry 13 }

affirmedNetworkContextIpLogicalIntfStatsSummaryStatsNumTxErrorIndicationFabricPkts OBJECT-TYPE
    SYNTAX      ConfdString
    MAX-ACCESS  read-only
    STATUS      current
    DESCRIPTION "Number of transmitted IPv4 error indication fabric packets"
    ::= { affirmedNetworkContextIpLogicalIntfStatsSummaryStatsEntry 14 }

affirmedNetworkContextIpLogicalIntfStatsSummaryStatsNumTxErrorIndicationRateLimitPkts OBJECT-TYPE
    SYNTAX      ConfdString
    MAX-ACCESS  read-only
    STATUS      current
    DESCRIPTION "Number of transmitted IPv4 error indication rate limit packets"
    ::= { affirmedNetworkContextIpLogicalIntfStatsSummaryStatsEntry 15 }

affirmedNetworkContextIpLogicalIntfStatsSummaryStatsNumTxV4CsmProxyPkts OBJECT-TYPE
    SYNTAX      ConfdString
    MAX-ACCESS  read-only
    STATUS      current
    DESCRIPTION "Number of transmitted IPv4 CSM proxy packets"
    ::= { affirmedNetworkContextIpLogicalIntfStatsSummaryStatsEntry 16 }

affirmedNetworkContextIpLogicalIntfStatsSummaryStatsNumRxV4Pkts OBJECT-TYPE
    SYNTAX      ConfdString
    MAX-ACCESS  read-only
    STATUS      current
    DESCRIPTION "Number of received IPv4 packets"
    ::= { affirmedNetworkContextIpLogicalIntfStatsSummaryStatsEntry 17 }

affirmedNetworkContextIpLogicalIntfStatsSummaryStatsNumRxV4Bytes OBJECT-TYPE
    SYNTAX      ConfdString
    MAX-ACCESS  read-only
    STATUS      current
    DESCRIPTION "Number of received IPv4 packet bytes"
    ::= { affirmedNetworkContextIpLogicalIntfStatsSummaryStatsEntry 18 }

affirmedNetworkContextIpLogicalIntfStatsSummaryStatsNumRxV4DropPkts OBJECT-TYPE
    SYNTAX      ConfdString
    MAX-ACCESS  read-only
    STATUS      current
    DESCRIPTION "Number of received dropped IPv4 packets"
    ::= { affirmedNetworkContextIpLogicalIntfStatsSummaryStatsEntry 19 }

affirmedNetworkContextIpLogicalIntfStatsSummaryStatsNumRxV4DropBytes OBJECT-TYPE
    SYNTAX      ConfdString
    MAX-ACCESS  read-only
    STATUS      current
    DESCRIPTION "Number of received dropped IPv4 packet bytes"
    ::= { affirmedNetworkContextIpLogicalIntfStatsSummaryStatsEntry 20 }

affirmedNetworkContextIpLogicalIntfStatsSummaryStatsNumRxICMPV4Pkts OBJECT-TYPE
    SYNTAX      ConfdString
    MAX-ACCESS  read-only
    STATUS      current
    DESCRIPTION "Number of received ICMPv4 packets"
    ::= { affirmedNetworkContextIpLogicalIntfStatsSummaryStatsEntry 21 }

affirmedNetworkContextIpLogicalIntfStatsSummaryStatsNumTxICMPV4Pkts OBJECT-TYPE
    SYNTAX      ConfdString
    MAX-ACCESS  read-only
    STATUS      current
    DESCRIPTION "Number of transmitted ICMPv4 packets"
    ::= { affirmedNetworkContextIpLogicalIntfStatsSummaryStatsEntry 22 }

affirmedNetworkContextIpLogicalIntfStatsSummaryStatsNumRxV4UnSuppAddrPkts OBJECT-TYPE
    SYNTAX      ConfdString
    MAX-ACCESS  read-only
    STATUS      current
    DESCRIPTION "Number of received IPv4 unsupported address packets"
    ::= { affirmedNetworkContextIpLogicalIntfStatsSummaryStatsEntry 23 }

affirmedNetworkContextIpLogicalIntfStatsSummaryStatsNumRxV4InvalidPkts OBJECT-TYPE
    SYNTAX      ConfdString
    MAX-ACCESS  read-only
    STATUS      current
    DESCRIPTION "Number of received IPv4 invalid packets"
    ::= { affirmedNetworkContextIpLogicalIntfStatsSummaryStatsEntry 24 }

affirmedNetworkContextIpLogicalIntfStatsSummaryStatsNumRxV4MulticastPkts OBJECT-TYPE
    SYNTAX      ConfdString
    MAX-ACCESS  read-only
    STATUS      current
    DESCRIPTION "Number of received IPv4 multicast packets"
    ::= { affirmedNetworkContextIpLogicalIntfStatsSummaryStatsEntry 25 }

affirmedNetworkContextIpLogicalIntfStatsSummaryStatsNumRxV4CsmProxyPkts OBJECT-TYPE
    SYNTAX      ConfdString
    MAX-ACCESS  read-only
    STATUS      current
    DESCRIPTION "Number of received IPv4 CSM proxy packets"
    ::= { affirmedNetworkContextIpLogicalIntfStatsSummaryStatsEntry 26 }

affirmedNetworkContextIpLogicalIntfStatsSummaryStatsNumRxV4UeUpstreamPkts OBJECT-TYPE
    SYNTAX      ConfdString
    MAX-ACCESS  read-only
    STATUS      current
    DESCRIPTION "Number of received IPv4 UE upstreamproxy packets"
    ::= { affirmedNetworkContextIpLogicalIntfStatsSummaryStatsEntry 27 }

affirmedNetworkContextIpLogicalIntfStatsSummaryStatsNumRxV4UeDownstreamPkts OBJECT-TYPE
    SYNTAX      ConfdString
    MAX-ACCESS  read-only
    STATUS      current
    DESCRIPTION "Number of received IPv4 UE downstream packets"
    ::= { affirmedNetworkContextIpLogicalIntfStatsSummaryStatsEntry 28 }

affirmedNetworkContextIpLogicalIntfStatsSummaryStatsNumRxV4UeSubnetDownstreamPkts OBJECT-TYPE
    SYNTAX      ConfdString
    MAX-ACCESS  read-only
    STATUS      current
    DESCRIPTION "Number of received IPv4 UE subnet downstream packets"
    ::= { affirmedNetworkContextIpLogicalIntfStatsSummaryStatsEntry 29 }

affirmedNetworkContextIpLogicalIntfStatsSummaryStatsNumRxV4LoadbalancerPkts OBJECT-TYPE
    SYNTAX      ConfdString
    MAX-ACCESS  read-only
    STATUS      current
    DESCRIPTION "Number of received IPv4 load balancer  packets"
    ::= { affirmedNetworkContextIpLogicalIntfStatsSummaryStatsEntry 30 }

affirmedNetworkContextIpLogicalIntfStatsSummaryStatsNumInvalidNatPortcounter OBJECT-TYPE
    SYNTAX      ConfdString
    MAX-ACCESS  read-only
    STATUS      current
    DESCRIPTION "Number of received IPv4 packets with invalid nat port"
    ::= { affirmedNetworkContextIpLogicalIntfStatsSummaryStatsEntry 31 }

affirmedNetworkContextIpLogicalIntfStatsSummaryStatsNumRxGtpInvalidPktscounter OBJECT-TYPE
    SYNTAX      ConfdString
    MAX-ACCESS  read-only
    STATUS      current
    DESCRIPTION "Number of received invalid GTP packets"
    ::= { affirmedNetworkContextIpLogicalIntfStatsSummaryStatsEntry 32 }

affirmedNetworkContextIpLogicalIntfStatsSummaryStatsNumTxV6Pkts OBJECT-TYPE
    SYNTAX      ConfdString
    MAX-ACCESS  read-only
    STATUS      current
    DESCRIPTION "Number of transmitted IPv6 packets"
    ::= { affirmedNetworkContextIpLogicalIntfStatsSummaryStatsEntry 33 }

affirmedNetworkContextIpLogicalIntfStatsSummaryStatsNumTxV6Bytes OBJECT-TYPE
    SYNTAX      ConfdString
    MAX-ACCESS  read-only
    STATUS      current
    DESCRIPTION "Number of transmitted IPv6 packet bytes"
    ::= { affirmedNetworkContextIpLogicalIntfStatsSummaryStatsEntry 34 }

affirmedNetworkContextIpLogicalIntfStatsSummaryStatsNumTxV6DropPkts OBJECT-TYPE
    SYNTAX      ConfdString
    MAX-ACCESS  read-only
    STATUS      current
    DESCRIPTION "Number of transmitted dropped IPv6 packets"
    ::= { affirmedNetworkContextIpLogicalIntfStatsSummaryStatsEntry 35 }

affirmedNetworkContextIpLogicalIntfStatsSummaryStatsNumTxV6DropBytes OBJECT-TYPE
    SYNTAX      ConfdString
    MAX-ACCESS  read-only
    STATUS      current
    DESCRIPTION "Number of transmitted dropped IPv6 bytes"
    ::= { affirmedNetworkContextIpLogicalIntfStatsSummaryStatsEntry 36 }

affirmedNetworkContextIpLogicalIntfStatsSummaryStatsNumTxKernelV6IcmpPkts OBJECT-TYPE
    SYNTAX      ConfdString
    MAX-ACCESS  read-only
    STATUS      current
    DESCRIPTION "Number of transmitted kernal ICMPv6 packets "
    ::= { affirmedNetworkContextIpLogicalIntfStatsSummaryStatsEntry 37 }

affirmedNetworkContextIpLogicalIntfStatsSummaryStatsNumTxV6CsmProxyPkts OBJECT-TYPE
    SYNTAX      ConfdString
    MAX-ACCESS  read-only
    STATUS      current
    DESCRIPTION "Number of transmitted IPv6 CSM proxy packets "
    ::= { affirmedNetworkContextIpLogicalIntfStatsSummaryStatsEntry 38 }

affirmedNetworkContextIpLogicalIntfStatsSummaryStatsNumRxV6Pkts OBJECT-TYPE
    SYNTAX      ConfdString
    MAX-ACCESS  read-only
    STATUS      current
    DESCRIPTION "Number of received IPv6 packets"
    ::= { affirmedNetworkContextIpLogicalIntfStatsSummaryStatsEntry 39 }

affirmedNetworkContextIpLogicalIntfStatsSummaryStatsNumRxV6Bytes OBJECT-TYPE
    SYNTAX      ConfdString
    MAX-ACCESS  read-only
    STATUS      current
    DESCRIPTION "Number of received IPv6 bytes"
    ::= { affirmedNetworkContextIpLogicalIntfStatsSummaryStatsEntry 40 }

affirmedNetworkContextIpLogicalIntfStatsSummaryStatsNumRxV6DropPkts OBJECT-TYPE
    SYNTAX      ConfdString
    MAX-ACCESS  read-only
    STATUS      current
    DESCRIPTION "Number of received dropped IPv6 packets"
    ::= { affirmedNetworkContextIpLogicalIntfStatsSummaryStatsEntry 41 }

affirmedNetworkContextIpLogicalIntfStatsSummaryStatsNumRxV6DropBytes OBJECT-TYPE
    SYNTAX      ConfdString
    MAX-ACCESS  read-only
    STATUS      current
    DESCRIPTION "Number of received dropped IPv6 bytes"
    ::= { affirmedNetworkContextIpLogicalIntfStatsSummaryStatsEntry 42 }

affirmedNetworkContextIpLogicalIntfStatsSummaryStatsNumRxICMPV6Pkts OBJECT-TYPE
    SYNTAX      ConfdString
    MAX-ACCESS  read-only
    STATUS      current
    DESCRIPTION "Number of received ICMPv6 packets"
    ::= { affirmedNetworkContextIpLogicalIntfStatsSummaryStatsEntry 43 }

affirmedNetworkContextIpLogicalIntfStatsSummaryStatsNumRxV6UnSuppAddrPkts OBJECT-TYPE
    SYNTAX      ConfdString
    MAX-ACCESS  read-only
    STATUS      current
    DESCRIPTION "Number of received IPv6 unsupported address packets"
    ::= { affirmedNetworkContextIpLogicalIntfStatsSummaryStatsEntry 44 }

affirmedNetworkContextIpLogicalIntfStatsSummaryStatsNumRxV6InvalidPkts OBJECT-TYPE
    SYNTAX      ConfdString
    MAX-ACCESS  read-only
    STATUS      current
    DESCRIPTION "Number of received IPv6 invalid packets"
    ::= { affirmedNetworkContextIpLogicalIntfStatsSummaryStatsEntry 45 }

affirmedNetworkContextIpLogicalIntfStatsSummaryStatsNumRxV6IcmpNAPkts OBJECT-TYPE
    SYNTAX      ConfdString
    MAX-ACCESS  read-only
    STATUS      current
    DESCRIPTION "Number of received ICMPv6 NA packets"
    ::= { affirmedNetworkContextIpLogicalIntfStatsSummaryStatsEntry 46 }

affirmedNetworkContextIpLogicalIntfStatsSummaryStatsNumRxV6IcmpTooBigPkts OBJECT-TYPE
    SYNTAX      ConfdString
    MAX-ACCESS  read-only
    STATUS      current
    DESCRIPTION "Number of received ICMPv6 too big packets"
    ::= { affirmedNetworkContextIpLogicalIntfStatsSummaryStatsEntry 47 }

affirmedNetworkContextIpLogicalIntfStatsSummaryStatsNumRxV6CsmProxyPkts OBJECT-TYPE
    SYNTAX      ConfdString
    MAX-ACCESS  read-only
    STATUS      current
    DESCRIPTION "Number of received IPv6 CSM proxy packets"
    ::= { affirmedNetworkContextIpLogicalIntfStatsSummaryStatsEntry 48 }

affirmedNetworkContextIpLogicalIntfStatsSummaryStatsNumRxV6UeUpstreamPkts OBJECT-TYPE
    SYNTAX      ConfdString
    MAX-ACCESS  read-only
    STATUS      current
    DESCRIPTION "Number of received IPv6 UE upstream packets"
    ::= { affirmedNetworkContextIpLogicalIntfStatsSummaryStatsEntry 49 }

affirmedNetworkContextIpLogicalIntfStatsSummaryStatsNumRxV6UeDownstreamPkts OBJECT-TYPE
    SYNTAX      ConfdString
    MAX-ACCESS  read-only
    STATUS      current
    DESCRIPTION "Number of received IPv6 UE downstream packets"
    ::= { affirmedNetworkContextIpLogicalIntfStatsSummaryStatsEntry 50 }

affirmedNetworkContextIpLogicalIntfStatsSummaryStatsNumRxV6UeSubnetDownstreamPkts OBJECT-TYPE
    SYNTAX      ConfdString
    MAX-ACCESS  read-only
    STATUS      current
    DESCRIPTION "Number of received IPv6 UE subnet downstream packets"
    ::= { affirmedNetworkContextIpLogicalIntfStatsSummaryStatsEntry 51 }

affirmedNetworkContextIpLogicalIntfStatsSummaryStatsNumRxV6LoadbalancerPkts OBJECT-TYPE
    SYNTAX      ConfdString
    MAX-ACCESS  read-only
    STATUS      current
    DESCRIPTION "Number of received IPv6 load-banancer packets"
    ::= { affirmedNetworkContextIpLogicalIntfStatsSummaryStatsEntry 52 }

affirmedNetworkContextIpLogicalIntfStatsSummaryStatsNumTxICMPV6Pkts OBJECT-TYPE
    SYNTAX      ConfdString
    MAX-ACCESS  read-only
    STATUS      current
    DESCRIPTION "Number of transmitted ICMPv6 packets"
    ::= { affirmedNetworkContextIpLogicalIntfStatsSummaryStatsEntry 53 }

affirmedNetworkContextIpLogicalIntfStatsTcpStatsTable OBJECT-TYPE
    SYNTAX      SEQUENCE OF AffirmedNetworkContextIpLogicalIntfStatsTcpStatsEntry
    MAX-ACCESS  not-accessible
    STATUS      current
    DESCRIPTION ""
    ::= { affirmedNetworkcontextMIB 32 }

affirmedNetworkContextIpLogicalIntfStatsTcpStatsEntry OBJECT-TYPE
    SYNTAX      AffirmedNetworkContextIpLogicalIntfStatsTcpStatsEntry
    MAX-ACCESS  not-accessible
    STATUS      current
    DESCRIPTION ""
    INDEX { affirmedNetworkContextName, affirmedNetworkContextIpLogicalIntfStatsTcpStatsIfName }
        ::= { affirmedNetworkContextIpLogicalIntfStatsTcpStatsTable 1 }

AffirmedNetworkContextIpLogicalIntfStatsTcpStatsEntry ::=
    SEQUENCE {
        affirmedNetworkContextIpLogicalIntfStatsTcpStatsIfName String,
        affirmedNetworkContextIpLogicalIntfStatsTcpStatsIpAddress String,
        affirmedNetworkContextIpLogicalIntfStatsTcpStatsPrefix String,
        affirmedNetworkContextIpLogicalIntfStatsTcpStatsSecondaryIpAddress String,
        affirmedNetworkContextIpLogicalIntfStatsTcpStatsSecondaryPrefixLength String,
        affirmedNetworkContextIpLogicalIntfStatsTcpStatsOperStatus String,
        affirmedNetworkContextIpLogicalIntfStatsTcpStatsNumTcpMssAdjustRxPkts ConfdString,
        affirmedNetworkContextIpLogicalIntfStatsTcpStatsNumTcpMssAdjustTxPkts ConfdString,
        affirmedNetworkContextIpLogicalIntfStatsTcpStatsNumTcpMssAdjustErrors ConfdString,
        affirmedNetworkContextIpLogicalIntfStatsTcpStatsNumTcpMssAdjustProxyPkts ConfdString,
        affirmedNetworkContextIpLogicalIntfStatsTcpStatsNumTcpMssAdjustProxyErrors ConfdString
    }

affirmedNetworkContextIpLogicalIntfStatsTcpStatsIfName OBJECT-TYPE
    SYNTAX      String
    MAX-ACCESS  not-accessible
    STATUS      current
    DESCRIPTION "IP interface name"
    ::= { affirmedNetworkContextIpLogicalIntfStatsTcpStatsEntry 1 }

affirmedNetworkContextIpLogicalIntfStatsTcpStatsIpAddress OBJECT-TYPE
    SYNTAX      String
    MAX-ACCESS  read-only
    STATUS      current
    DESCRIPTION "Address of the IP interface"
    ::= { affirmedNetworkContextIpLogicalIntfStatsTcpStatsEntry 2 }

affirmedNetworkContextIpLogicalIntfStatsTcpStatsPrefix OBJECT-TYPE
    SYNTAX      String
    MAX-ACCESS  read-only
    STATUS      current
    DESCRIPTION "Prefix length of the IP address"
    ::= { affirmedNetworkContextIpLogicalIntfStatsTcpStatsEntry 3 }

affirmedNetworkContextIpLogicalIntfStatsTcpStatsSecondaryIpAddress OBJECT-TYPE
    SYNTAX      String
    MAX-ACCESS  read-only
    STATUS      current
    DESCRIPTION "Secondary address of the IP interface"
    ::= { affirmedNetworkContextIpLogicalIntfStatsTcpStatsEntry 4 }

affirmedNetworkContextIpLogicalIntfStatsTcpStatsSecondaryPrefixLength OBJECT-TYPE
    SYNTAX      String
    MAX-ACCESS  read-only
    STATUS      current
    DESCRIPTION "Secondary prefix length of the IP address"
    ::= { affirmedNetworkContextIpLogicalIntfStatsTcpStatsEntry 5 }

affirmedNetworkContextIpLogicalIntfStatsTcpStatsOperStatus OBJECT-TYPE
    SYNTAX      String
    MAX-ACCESS  read-only
    STATUS      current
    DESCRIPTION "Interface operation status"
    ::= { affirmedNetworkContextIpLogicalIntfStatsTcpStatsEntry 6 }

affirmedNetworkContextIpLogicalIntfStatsTcpStatsNumTcpMssAdjustRxPkts OBJECT-TYPE
    SYNTAX      ConfdString
    MAX-ACCESS  read-only
    STATUS      current
    DESCRIPTION "Number of  TCP MSS Adjust Rx Pkts"
    ::= { affirmedNetworkContextIpLogicalIntfStatsTcpStatsEntry 7 }

affirmedNetworkContextIpLogicalIntfStatsTcpStatsNumTcpMssAdjustTxPkts OBJECT-TYPE
    SYNTAX      ConfdString
    MAX-ACCESS  read-only
    STATUS      current
    DESCRIPTION "Number of  TCP MSS Adjust Tx Pkts"
    ::= { affirmedNetworkContextIpLogicalIntfStatsTcpStatsEntry 8 }

affirmedNetworkContextIpLogicalIntfStatsTcpStatsNumTcpMssAdjustErrors OBJECT-TYPE
    SYNTAX      ConfdString
    MAX-ACCESS  read-only
    STATUS      current
    DESCRIPTION "Number of  TCP MSS Adjust Errors"
    ::= { affirmedNetworkContextIpLogicalIntfStatsTcpStatsEntry 9 }

affirmedNetworkContextIpLogicalIntfStatsTcpStatsNumTcpMssAdjustProxyPkts OBJECT-TYPE
    SYNTAX      ConfdString
    MAX-ACCESS  read-only
    STATUS      current
    DESCRIPTION "Number of  TCP MSS Adjust Proxy Pkts"
    ::= { affirmedNetworkContextIpLogicalIntfStatsTcpStatsEntry 10 }

affirmedNetworkContextIpLogicalIntfStatsTcpStatsNumTcpMssAdjustProxyErrors OBJECT-TYPE
    SYNTAX      ConfdString
    MAX-ACCESS  read-only
    STATUS      current
    DESCRIPTION "Number of  TCP MSS Adjust Proxy Errors"
    ::= { affirmedNetworkContextIpLogicalIntfStatsTcpStatsEntry 11 }

affirmedNetworkContextIpLogicalIntfStatsWagStatsTable OBJECT-TYPE
    SYNTAX      SEQUENCE OF AffirmedNetworkContextIpLogicalIntfStatsWagStatsEntry
    MAX-ACCESS  not-accessible
    STATUS      current
    DESCRIPTION ""
    ::= { affirmedNetworkcontextMIB 33 }

affirmedNetworkContextIpLogicalIntfStatsWagStatsEntry OBJECT-TYPE
    SYNTAX      AffirmedNetworkContextIpLogicalIntfStatsWagStatsEntry
    MAX-ACCESS  not-accessible
    STATUS      current
    DESCRIPTION ""
    INDEX { affirmedNetworkContextName, affirmedNetworkContextIpLogicalIntfStatsWagStatsIfName }
        ::= { affirmedNetworkContextIpLogicalIntfStatsWagStatsTable 1 }

AffirmedNetworkContextIpLogicalIntfStatsWagStatsEntry ::=
    SEQUENCE {
        affirmedNetworkContextIpLogicalIntfStatsWagStatsIfName String,
        affirmedNetworkContextIpLogicalIntfStatsWagStatsIpAddress String,
        affirmedNetworkContextIpLogicalIntfStatsWagStatsPrefix String,
        affirmedNetworkContextIpLogicalIntfStatsWagStatsSecondaryIpAddress String,
        affirmedNetworkContextIpLogicalIntfStatsWagStatsSecondaryPrefixLength String,
        affirmedNetworkContextIpLogicalIntfStatsWagStatsOperStatus String,
        affirmedNetworkContextIpLogicalIntfStatsWagStatsNumRxWAGUpstreamPkts ConfdString,
        affirmedNetworkContextIpLogicalIntfStatsWagStatsNumRxWAGpktsToImsiMgr ConfdString,
        affirmedNetworkContextIpLogicalIntfStatsWagStatsNumRxWAGUpstreamInvalidPkts ConfdString,
        affirmedNetworkContextIpLogicalIntfStatsWagStatsNumRxWAGUpstreamUnknSubPkts ConfdString,
        affirmedNetworkContextIpLogicalIntfStatsWagStatsNumRxWAGUpstreamArpPkts ConfdString,
        affirmedNetworkContextIpLogicalIntfStatsWagStatsNumTxWAGUpstreamArpLocalRespOk ConfdString,
        affirmedNetworkContextIpLogicalIntfStatsWagStatsNumRxWAGUpstreamArpFailures ConfdString,
        affirmedNetworkContextIpLogicalIntfStatsWagStatsNumRxWAGUpstreamArpIgnores ConfdString,
        affirmedNetworkContextIpLogicalIntfStatsWagStatsNumRxWAGUpstreamArpLpmLkupFailures ConfdString
    }

affirmedNetworkContextIpLogicalIntfStatsWagStatsIfName OBJECT-TYPE
    SYNTAX      String
    MAX-ACCESS  not-accessible
    STATUS      current
    DESCRIPTION "IP interface name"
    ::= { affirmedNetworkContextIpLogicalIntfStatsWagStatsEntry 1 }

affirmedNetworkContextIpLogicalIntfStatsWagStatsIpAddress OBJECT-TYPE
    SYNTAX      String
    MAX-ACCESS  read-only
    STATUS      current
    DESCRIPTION "Address of the IP interface"
    ::= { affirmedNetworkContextIpLogicalIntfStatsWagStatsEntry 2 }

affirmedNetworkContextIpLogicalIntfStatsWagStatsPrefix OBJECT-TYPE
    SYNTAX      String
    MAX-ACCESS  read-only
    STATUS      current
    DESCRIPTION "Prefix length of the IP address"
    ::= { affirmedNetworkContextIpLogicalIntfStatsWagStatsEntry 3 }

affirmedNetworkContextIpLogicalIntfStatsWagStatsSecondaryIpAddress OBJECT-TYPE
    SYNTAX      String
    MAX-ACCESS  read-only
    STATUS      current
    DESCRIPTION "Secondary address of the IP interface"
    ::= { affirmedNetworkContextIpLogicalIntfStatsWagStatsEntry 4 }

affirmedNetworkContextIpLogicalIntfStatsWagStatsSecondaryPrefixLength OBJECT-TYPE
    SYNTAX      String
    MAX-ACCESS  read-only
    STATUS      current
    DESCRIPTION "Secondary prefix length of the IP address"
    ::= { affirmedNetworkContextIpLogicalIntfStatsWagStatsEntry 5 }

affirmedNetworkContextIpLogicalIntfStatsWagStatsOperStatus OBJECT-TYPE
    SYNTAX      String
    MAX-ACCESS  read-only
    STATUS      current
    DESCRIPTION "Interface operation status"
    ::= { affirmedNetworkContextIpLogicalIntfStatsWagStatsEntry 6 }

affirmedNetworkContextIpLogicalIntfStatsWagStatsNumRxWAGUpstreamPkts OBJECT-TYPE
    SYNTAX      ConfdString
    MAX-ACCESS  read-only
    STATUS      current
    DESCRIPTION "Number of  Rx WAG Upstream Pkts"
    ::= { affirmedNetworkContextIpLogicalIntfStatsWagStatsEntry 7 }

affirmedNetworkContextIpLogicalIntfStatsWagStatsNumRxWAGpktsToImsiMgr OBJECT-TYPE
    SYNTAX      ConfdString
    MAX-ACCESS  read-only
    STATUS      current
    DESCRIPTION "Number of  Rx WAG pkts To Imsi Mgr"
    ::= { affirmedNetworkContextIpLogicalIntfStatsWagStatsEntry 8 }

affirmedNetworkContextIpLogicalIntfStatsWagStatsNumRxWAGUpstreamInvalidPkts OBJECT-TYPE
    SYNTAX      ConfdString
    MAX-ACCESS  read-only
    STATUS      current
    DESCRIPTION "Number of  Rx WAG Upstream Invalid Pkts"
    ::= { affirmedNetworkContextIpLogicalIntfStatsWagStatsEntry 9 }

affirmedNetworkContextIpLogicalIntfStatsWagStatsNumRxWAGUpstreamUnknSubPkts OBJECT-TYPE
    SYNTAX      ConfdString
    MAX-ACCESS  read-only
    STATUS      current
    DESCRIPTION "Number of  Rx WAG Upstream Unknown Sub Pkts"
    ::= { affirmedNetworkContextIpLogicalIntfStatsWagStatsEntry 10 }

affirmedNetworkContextIpLogicalIntfStatsWagStatsNumRxWAGUpstreamArpPkts OBJECT-TYPE
    SYNTAX      ConfdString
    MAX-ACCESS  read-only
    STATUS      current
    DESCRIPTION "Number of  Rx WAG Upstream ARP Pkts"
    ::= { affirmedNetworkContextIpLogicalIntfStatsWagStatsEntry 11 }

affirmedNetworkContextIpLogicalIntfStatsWagStatsNumTxWAGUpstreamArpLocalRespOk OBJECT-TYPE
    SYNTAX      ConfdString
    MAX-ACCESS  read-only
    STATUS      current
    DESCRIPTION "Number of  Tx WAG Upstream ARP Local Resp Ok"
    ::= { affirmedNetworkContextIpLogicalIntfStatsWagStatsEntry 12 }

affirmedNetworkContextIpLogicalIntfStatsWagStatsNumRxWAGUpstreamArpFailures OBJECT-TYPE
    SYNTAX      ConfdString
    MAX-ACCESS  read-only
    STATUS      current
    DESCRIPTION "Number of  Rx WAG Upstream ARP Failures"
    ::= { affirmedNetworkContextIpLogicalIntfStatsWagStatsEntry 13 }

affirmedNetworkContextIpLogicalIntfStatsWagStatsNumRxWAGUpstreamArpIgnores OBJECT-TYPE
    SYNTAX      ConfdString
    MAX-ACCESS  read-only
    STATUS      current
    DESCRIPTION "Number of  Rx WAG Upstream ARP Ignores"
    ::= { affirmedNetworkContextIpLogicalIntfStatsWagStatsEntry 14 }

affirmedNetworkContextIpLogicalIntfStatsWagStatsNumRxWAGUpstreamArpLpmLkupFailures OBJECT-TYPE
    SYNTAX      ConfdString
    MAX-ACCESS  read-only
    STATUS      current
    DESCRIPTION "Number of  Rx WAG Upstream ARP LpmLkupFailures"
    ::= { affirmedNetworkContextIpLogicalIntfStatsWagStatsEntry 15 }

affirmedNetworkContextIpInterfaceCaptureStatusTable OBJECT-TYPE
    SYNTAX      SEQUENCE OF AffirmedNetworkContextIpInterfaceCaptureStatusEntry
    MAX-ACCESS  not-accessible
    STATUS      current
    DESCRIPTION ""
    ::= { affirmedNetworkcontextMIB 4 }

affirmedNetworkContextIpInterfaceCaptureStatusEntry OBJECT-TYPE
    SYNTAX      AffirmedNetworkContextIpInterfaceCaptureStatusEntry
    MAX-ACCESS  not-accessible
    STATUS      current
    DESCRIPTION ""
    INDEX { affirmedNetworkContextName, affirmedNetworkContextIpInterfaceCaptureStatusIfName }
        ::= { affirmedNetworkContextIpInterfaceCaptureStatusTable 1 }

AffirmedNetworkContextIpInterfaceCaptureStatusEntry ::=
    SEQUENCE {
        affirmedNetworkContextIpInterfaceCaptureStatusIfName String,
        affirmedNetworkContextIpInterfaceCaptureStatusNumCaptured Unsigned32,
        affirmedNetworkContextIpInterfaceCaptureStatusNumRemaining Unsigned32,
        affirmedNetworkContextIpInterfaceCaptureStatusSecondsRemaining Unsigned32,
        affirmedNetworkContextIpInterfaceCaptureStatusState String
    }

affirmedNetworkContextIpInterfaceCaptureStatusIfName OBJECT-TYPE
    SYNTAX      String
    MAX-ACCESS  not-accessible
    STATUS      current
    DESCRIPTION "IP interface name"
    ::= { affirmedNetworkContextIpInterfaceCaptureStatusEntry 1 }

affirmedNetworkContextIpInterfaceCaptureStatusNumCaptured OBJECT-TYPE
    SYNTAX      Unsigned32
    MAX-ACCESS  read-only
    STATUS      current
    DESCRIPTION "how many packets have been captured"
    ::= { affirmedNetworkContextIpInterfaceCaptureStatusEntry 2 }

affirmedNetworkContextIpInterfaceCaptureStatusNumRemaining OBJECT-TYPE
    SYNTAX      Unsigned32
    MAX-ACCESS  read-only
    STATUS      current
    DESCRIPTION "how many more packets to capture"
    ::= { affirmedNetworkContextIpInterfaceCaptureStatusEntry 3 }

affirmedNetworkContextIpInterfaceCaptureStatusSecondsRemaining OBJECT-TYPE
    SYNTAX      Unsigned32
    MAX-ACCESS  read-only
    STATUS      current
    DESCRIPTION "how many more seconds to capture"
    ::= { affirmedNetworkContextIpInterfaceCaptureStatusEntry 4 }

affirmedNetworkContextIpInterfaceCaptureStatusState OBJECT-TYPE
    SYNTAX      String
    MAX-ACCESS  read-only
    STATUS      current
    DESCRIPTION "packet capture state"
    ::= { affirmedNetworkContextIpInterfaceCaptureStatusEntry 5 }

affirmedNetworkContextIpInterfaceStatisticsTable OBJECT-TYPE
    SYNTAX      SEQUENCE OF AffirmedNetworkContextIpInterfaceStatisticsEntry
    MAX-ACCESS  not-accessible
    STATUS      current
    DESCRIPTION ""
    ::= { affirmedNetworkcontextMIB 5 }

affirmedNetworkContextIpInterfaceStatisticsEntry OBJECT-TYPE
    SYNTAX      AffirmedNetworkContextIpInterfaceStatisticsEntry
    MAX-ACCESS  not-accessible
    STATUS      current
    DESCRIPTION ""
    INDEX { affirmedNetworkContextName, affirmedNetworkContextIpInterfaceStatisticsName }
        ::= { affirmedNetworkContextIpInterfaceStatisticsTable 1 }

AffirmedNetworkContextIpInterfaceStatisticsEntry ::=
    SEQUENCE {
        affirmedNetworkContextIpInterfaceStatisticsName String,
        affirmedNetworkContextIpInterfaceStatisticsNumTxV4Pkts ConfdString,
        affirmedNetworkContextIpInterfaceStatisticsNumTxV4Bytes ConfdString,
        affirmedNetworkContextIpInterfaceStatisticsNumTxV4DropPkts ConfdString,
        affirmedNetworkContextIpInterfaceStatisticsNumTxV4DropBytes ConfdString,
        affirmedNetworkContextIpInterfaceStatisticsNumRxV4Pkts ConfdString,
        affirmedNetworkContextIpInterfaceStatisticsNumRxV4Bytes ConfdString,
        affirmedNetworkContextIpInterfaceStatisticsNumRxV4DropPkts ConfdString,
        affirmedNetworkContextIpInterfaceStatisticsNumRxV4DropBytes ConfdString,
        affirmedNetworkContextIpInterfaceStatisticsNumTxV6Pkts ConfdString,
        affirmedNetworkContextIpInterfaceStatisticsNumTxV6Bytes ConfdString,
        affirmedNetworkContextIpInterfaceStatisticsNumTxV6DropPkts ConfdString,
        affirmedNetworkContextIpInterfaceStatisticsNumTxV6DropBytes ConfdString,
        affirmedNetworkContextIpInterfaceStatisticsNumRxV6Pkts ConfdString,
        affirmedNetworkContextIpInterfaceStatisticsNumRxV6Bytes ConfdString,
        affirmedNetworkContextIpInterfaceStatisticsNumRxV6DropPkts ConfdString,
        affirmedNetworkContextIpInterfaceStatisticsNumRxV6DropBytes ConfdString,
        affirmedNetworkContextIpInterfaceStatisticsNumRxMplsPkts ConfdString,
        affirmedNetworkContextIpInterfaceStatisticsNumRxMplsBytes ConfdString,
        affirmedNetworkContextIpInterfaceStatisticsNumRxMplsUnknownLabelPkts ConfdString,
        affirmedNetworkContextIpInterfaceStatisticsNumRxMplsDropPkts ConfdString,
        affirmedNetworkContextIpInterfaceStatisticsNumTxMplsPkts ConfdString,
        affirmedNetworkContextIpInterfaceStatisticsNumRxICMPV4Pkts ConfdString,
        affirmedNetworkContextIpInterfaceStatisticsNumTxICMPV4Pkts ConfdString,
        affirmedNetworkContextIpInterfaceStatisticsNumRxICMPV6Pkts ConfdString,
        affirmedNetworkContextIpInterfaceStatisticsNumTxICMPV6Pkts ConfdString,
        affirmedNetworkContextIpInterfaceStatisticsNumTxMplsBytes ConfdString,
        affirmedNetworkContextIpInterfaceStatisticsNumTxNoRouteDropPkts ConfdString,
        affirmedNetworkContextIpInterfaceStatisticsNumTxFragmentedPkts ConfdString
    }

affirmedNetworkContextIpInterfaceStatisticsName OBJECT-TYPE
    SYNTAX      String
    MAX-ACCESS  not-accessible
    STATUS      current
    DESCRIPTION "IP interface name"
    ::= { affirmedNetworkContextIpInterfaceStatisticsEntry 1 }

affirmedNetworkContextIpInterfaceStatisticsNumTxV4Pkts OBJECT-TYPE
    SYNTAX      ConfdString
    MAX-ACCESS  read-only
    STATUS      current
    DESCRIPTION "Number of transmitted IPv4 packets"
    ::= { affirmedNetworkContextIpInterfaceStatisticsEntry 2 }

affirmedNetworkContextIpInterfaceStatisticsNumTxV4Bytes OBJECT-TYPE
    SYNTAX      ConfdString
    MAX-ACCESS  read-only
    STATUS      current
    DESCRIPTION "Number of transmitted IPv4 packet bytes"
    ::= { affirmedNetworkContextIpInterfaceStatisticsEntry 3 }

affirmedNetworkContextIpInterfaceStatisticsNumTxV4DropPkts OBJECT-TYPE
    SYNTAX      ConfdString
    MAX-ACCESS  read-only
    STATUS      current
    DESCRIPTION "Number of transmitted dropped IPv4 packets"
    ::= { affirmedNetworkContextIpInterfaceStatisticsEntry 4 }

affirmedNetworkContextIpInterfaceStatisticsNumTxV4DropBytes OBJECT-TYPE
    SYNTAX      ConfdString
    MAX-ACCESS  read-only
    STATUS      current
    DESCRIPTION "Number of transmitted dropped IPv4 packet bytes"
    ::= { affirmedNetworkContextIpInterfaceStatisticsEntry 5 }

affirmedNetworkContextIpInterfaceStatisticsNumRxV4Pkts OBJECT-TYPE
    SYNTAX      ConfdString
    MAX-ACCESS  read-only
    STATUS      current
    DESCRIPTION "Number of received IPv4 packets"
    ::= { affirmedNetworkContextIpInterfaceStatisticsEntry 6 }

affirmedNetworkContextIpInterfaceStatisticsNumRxV4Bytes OBJECT-TYPE
    SYNTAX      ConfdString
    MAX-ACCESS  read-only
    STATUS      current
    DESCRIPTION "Number of received IPv4 packet bytes"
    ::= { affirmedNetworkContextIpInterfaceStatisticsEntry 7 }

affirmedNetworkContextIpInterfaceStatisticsNumRxV4DropPkts OBJECT-TYPE
    SYNTAX      ConfdString
    MAX-ACCESS  read-only
    STATUS      current
    DESCRIPTION "Number of received dropped IPv4 packets"
    ::= { affirmedNetworkContextIpInterfaceStatisticsEntry 8 }

affirmedNetworkContextIpInterfaceStatisticsNumRxV4DropBytes OBJECT-TYPE
    SYNTAX      ConfdString
    MAX-ACCESS  read-only
    STATUS      current
    DESCRIPTION "Number of received dropped IPv4 packet bytes"
    ::= { affirmedNetworkContextIpInterfaceStatisticsEntry 9 }

affirmedNetworkContextIpInterfaceStatisticsNumTxV6Pkts OBJECT-TYPE
    SYNTAX      ConfdString
    MAX-ACCESS  read-only
    STATUS      current
    DESCRIPTION "Number of transmitted IPv6 packets"
    ::= { affirmedNetworkContextIpInterfaceStatisticsEntry 10 }

affirmedNetworkContextIpInterfaceStatisticsNumTxV6Bytes OBJECT-TYPE
    SYNTAX      ConfdString
    MAX-ACCESS  read-only
    STATUS      current
    DESCRIPTION "Number of transmitted IPv6 packet bytes"
    ::= { affirmedNetworkContextIpInterfaceStatisticsEntry 11 }

affirmedNetworkContextIpInterfaceStatisticsNumTxV6DropPkts OBJECT-TYPE
    SYNTAX      ConfdString
    MAX-ACCESS  read-only
    STATUS      current
    DESCRIPTION "Number of transmitted dropped IPv6 packets"
    ::= { affirmedNetworkContextIpInterfaceStatisticsEntry 12 }

affirmedNetworkContextIpInterfaceStatisticsNumTxV6DropBytes OBJECT-TYPE
    SYNTAX      ConfdString
    MAX-ACCESS  read-only
    STATUS      current
    DESCRIPTION "Number of transmitted dropped IPv6 bytes"
    ::= { affirmedNetworkContextIpInterfaceStatisticsEntry 13 }

affirmedNetworkContextIpInterfaceStatisticsNumRxV6Pkts OBJECT-TYPE
    SYNTAX      ConfdString
    MAX-ACCESS  read-only
    STATUS      current
    DESCRIPTION "Number of received IPv6 packets"
    ::= { affirmedNetworkContextIpInterfaceStatisticsEntry 14 }

affirmedNetworkContextIpInterfaceStatisticsNumRxV6Bytes OBJECT-TYPE
    SYNTAX      ConfdString
    MAX-ACCESS  read-only
    STATUS      current
    DESCRIPTION "Number of received IPv6 packet bytes"
    ::= { affirmedNetworkContextIpInterfaceStatisticsEntry 15 }

affirmedNetworkContextIpInterfaceStatisticsNumRxV6DropPkts OBJECT-TYPE
    SYNTAX      ConfdString
    MAX-ACCESS  read-only
    STATUS      current
    DESCRIPTION "Number of received dropped IPv6 packets"
    ::= { affirmedNetworkContextIpInterfaceStatisticsEntry 16 }

affirmedNetworkContextIpInterfaceStatisticsNumRxV6DropBytes OBJECT-TYPE
    SYNTAX      ConfdString
    MAX-ACCESS  read-only
    STATUS      current
    DESCRIPTION "Number of received dropped IPv6 packet bytes"
    ::= { affirmedNetworkContextIpInterfaceStatisticsEntry 17 }

affirmedNetworkContextIpInterfaceStatisticsNumRxMplsPkts OBJECT-TYPE
    SYNTAX      ConfdString
    MAX-ACCESS  read-only
    STATUS      current
    DESCRIPTION "Number of received MPLS packets"
    ::= { affirmedNetworkContextIpInterfaceStatisticsEntry 18 }

affirmedNetworkContextIpInterfaceStatisticsNumRxMplsBytes OBJECT-TYPE
    SYNTAX      ConfdString
    MAX-ACCESS  read-only
    STATUS      current
    DESCRIPTION "Number of received MPLS bytes"
    ::= { affirmedNetworkContextIpInterfaceStatisticsEntry 19 }

affirmedNetworkContextIpInterfaceStatisticsNumRxMplsUnknownLabelPkts OBJECT-TYPE
    SYNTAX      ConfdString
    MAX-ACCESS  read-only
    STATUS      current
    DESCRIPTION "Number of received MPLS packets with unknown labels"
    ::= { affirmedNetworkContextIpInterfaceStatisticsEntry 20 }

affirmedNetworkContextIpInterfaceStatisticsNumRxMplsDropPkts OBJECT-TYPE
    SYNTAX      ConfdString
    MAX-ACCESS  read-only
    STATUS      current
    DESCRIPTION "Number of dropped MPLS packets"
    ::= { affirmedNetworkContextIpInterfaceStatisticsEntry 21 }

affirmedNetworkContextIpInterfaceStatisticsNumTxMplsPkts OBJECT-TYPE
    SYNTAX      ConfdString
    MAX-ACCESS  read-only
    STATUS      current
    DESCRIPTION "Number of transmitted MPLS packets"
    ::= { affirmedNetworkContextIpInterfaceStatisticsEntry 22 }

affirmedNetworkContextIpInterfaceStatisticsNumRxICMPV4Pkts OBJECT-TYPE
    SYNTAX      ConfdString
    MAX-ACCESS  read-only
    STATUS      current
    DESCRIPTION "Number of received ICMPv4 packets"
    ::= { affirmedNetworkContextIpInterfaceStatisticsEntry 23 }

affirmedNetworkContextIpInterfaceStatisticsNumTxICMPV4Pkts OBJECT-TYPE
    SYNTAX      ConfdString
    MAX-ACCESS  read-only
    STATUS      current
    DESCRIPTION "Number of transmitted ICMPv4 packets"
    ::= { affirmedNetworkContextIpInterfaceStatisticsEntry 24 }

affirmedNetworkContextIpInterfaceStatisticsNumRxICMPV6Pkts OBJECT-TYPE
    SYNTAX      ConfdString
    MAX-ACCESS  read-only
    STATUS      current
    DESCRIPTION "Number of received ICMPv6 packets"
    ::= { affirmedNetworkContextIpInterfaceStatisticsEntry 25 }

affirmedNetworkContextIpInterfaceStatisticsNumTxICMPV6Pkts OBJECT-TYPE
    SYNTAX      ConfdString
    MAX-ACCESS  read-only
    STATUS      current
    DESCRIPTION "Number of transmitted ICMPv6 packets"
    ::= { affirmedNetworkContextIpInterfaceStatisticsEntry 26 }

affirmedNetworkContextIpInterfaceStatisticsNumTxMplsBytes OBJECT-TYPE
    SYNTAX      ConfdString
    MAX-ACCESS  read-only
    STATUS      current
    DESCRIPTION "Number of transmitted MPLS bytes"
    ::= { affirmedNetworkContextIpInterfaceStatisticsEntry 27 }

affirmedNetworkContextIpInterfaceStatisticsNumTxNoRouteDropPkts OBJECT-TYPE
    SYNTAX      ConfdString
    MAX-ACCESS  read-only
    STATUS      current
    DESCRIPTION "Number of Tx No Route Drop Pkts "
    ::= { affirmedNetworkContextIpInterfaceStatisticsEntry 28 }

affirmedNetworkContextIpInterfaceStatisticsNumTxFragmentedPkts OBJECT-TYPE
    SYNTAX      ConfdString
    MAX-ACCESS  read-only
    STATUS      current
    DESCRIPTION "Number of Tx Fragmented Pkts "
    ::= { affirmedNetworkContextIpInterfaceStatisticsEntry 29 }

affirmedNetworkContextIpRouteStatusNewTable OBJECT-TYPE
    SYNTAX      SEQUENCE OF AffirmedNetworkContextIpRouteStatusNewEntry
    MAX-ACCESS  not-accessible
    STATUS      current
    DESCRIPTION ""
    ::= { affirmedNetworkcontextMIB 41 }

affirmedNetworkContextIpRouteStatusNewEntry OBJECT-TYPE
    SYNTAX      AffirmedNetworkContextIpRouteStatusNewEntry
    MAX-ACCESS  not-accessible
    STATUS      current
    DESCRIPTION ""
    INDEX { affirmedNetworkContextName, affirmedNetworkContextIpRouteStatusNewDest, affirmedNetworkContextIpRouteStatusNewPrefix, affirmedNetworkContextIpRouteStatusNewNextHop, affirmedNetworkContextIpRouteStatusNewIpInterface }
        ::= { affirmedNetworkContextIpRouteStatusNewTable 1 }

AffirmedNetworkContextIpRouteStatusNewEntry ::=
    SEQUENCE {
        affirmedNetworkContextIpRouteStatusNewDest String,
        affirmedNetworkContextIpRouteStatusNewPrefix Unsigned32,
        affirmedNetworkContextIpRouteStatusNewNextHop String,
        affirmedNetworkContextIpRouteStatusNewIpInterface String,
        affirmedNetworkContextIpRouteStatusNewPreference Unsigned32,
        affirmedNetworkContextIpRouteStatusNewType INTEGER
    }

affirmedNetworkContextIpRouteStatusNewDest OBJECT-TYPE
    SYNTAX      String
    MAX-ACCESS  not-accessible
    STATUS      current
    DESCRIPTION ""
    ::= { affirmedNetworkContextIpRouteStatusNewEntry 1 }

affirmedNetworkContextIpRouteStatusNewPrefix OBJECT-TYPE
    SYNTAX      Unsigned32
    MAX-ACCESS  not-accessible
    STATUS      current
    DESCRIPTION "Prefix length of the IP address"
    ::= { affirmedNetworkContextIpRouteStatusNewEntry 2 }

affirmedNetworkContextIpRouteStatusNewNextHop OBJECT-TYPE
    SYNTAX      String
    MAX-ACCESS  not-accessible
    STATUS      current
    DESCRIPTION ""
    ::= { affirmedNetworkContextIpRouteStatusNewEntry 3 }

affirmedNetworkContextIpRouteStatusNewIpInterface OBJECT-TYPE
    SYNTAX      String
    MAX-ACCESS  not-accessible
    STATUS      current
    DESCRIPTION ""
    ::= { affirmedNetworkContextIpRouteStatusNewEntry 4 }

affirmedNetworkContextIpRouteStatusNewPreference OBJECT-TYPE
    SYNTAX      Unsigned32
    MAX-ACCESS  read-only
    STATUS      current
    DESCRIPTION ""
    ::= { affirmedNetworkContextIpRouteStatusNewEntry 5 }

affirmedNetworkContextIpRouteStatusNewType OBJECT-TYPE
    SYNTAX      INTEGER {static(0),ospf(1),other(2)}
    MAX-ACCESS  read-only
    STATUS      current
    DESCRIPTION ""
    ::= { affirmedNetworkContextIpRouteStatusNewEntry 6 }

affirmedNetworkContextIpRouteStatusTable OBJECT-TYPE
    SYNTAX      SEQUENCE OF AffirmedNetworkContextIpRouteStatusEntry
    MAX-ACCESS  not-accessible
    STATUS      deprecated
    DESCRIPTION ""
    ::= { affirmedNetworkcontextMIB 6 }

affirmedNetworkContextIpRouteStatusEntry OBJECT-TYPE
    SYNTAX      AffirmedNetworkContextIpRouteStatusEntry
    MAX-ACCESS  not-accessible
    STATUS      deprecated
    DESCRIPTION ""
    INDEX { affirmedNetworkContextName, affirmedNetworkContextIpRouteStatusDest, affirmedNetworkContextIpRouteStatusPrefix, affirmedNetworkContextIpRouteStatusNextHop }
        ::= { affirmedNetworkContextIpRouteStatusTable 1 }

AffirmedNetworkContextIpRouteStatusEntry ::=
    SEQUENCE {
        affirmedNetworkContextIpRouteStatusDest String,
        affirmedNetworkContextIpRouteStatusPrefix Unsigned32,
        affirmedNetworkContextIpRouteStatusNextHop String,
        affirmedNetworkContextIpRouteStatusIpInterface String,
        affirmedNetworkContextIpRouteStatusPreference Unsigned32,
        affirmedNetworkContextIpRouteStatusType INTEGER
    }

affirmedNetworkContextIpRouteStatusDest OBJECT-TYPE
    SYNTAX      String
    MAX-ACCESS  not-accessible
    STATUS      current
    DESCRIPTION ""
    ::= { affirmedNetworkContextIpRouteStatusEntry 1 }

affirmedNetworkContextIpRouteStatusPrefix OBJECT-TYPE
    SYNTAX      Unsigned32
    MAX-ACCESS  not-accessible
    STATUS      current
    DESCRIPTION "Prefix length of the IP address"
    ::= { affirmedNetworkContextIpRouteStatusEntry 2 }

affirmedNetworkContextIpRouteStatusNextHop OBJECT-TYPE
    SYNTAX      String
    MAX-ACCESS  not-accessible
    STATUS      current
    DESCRIPTION ""
    ::= { affirmedNetworkContextIpRouteStatusEntry 3 }

affirmedNetworkContextIpRouteStatusIpInterface OBJECT-TYPE
    SYNTAX      String
    MAX-ACCESS  read-only
    STATUS      current
    DESCRIPTION ""
    ::= { affirmedNetworkContextIpRouteStatusEntry 4 }

affirmedNetworkContextIpRouteStatusPreference OBJECT-TYPE
    SYNTAX      Unsigned32
    MAX-ACCESS  read-only
    STATUS      current
    DESCRIPTION ""
    ::= { affirmedNetworkContextIpRouteStatusEntry 5 }

affirmedNetworkContextIpRouteStatusType OBJECT-TYPE
    SYNTAX      INTEGER {static(0),ospf(1),other(2)}
    MAX-ACCESS  read-only
    STATUS      current
    DESCRIPTION ""
    ::= { affirmedNetworkContextIpRouteStatusEntry 6 }

affirmedNetworkContextIpRoutingTable OBJECT-TYPE
    SYNTAX      SEQUENCE OF AffirmedNetworkContextIpRoutingEntry
    MAX-ACCESS  not-accessible
    STATUS      deprecated
    DESCRIPTION ""
    ::= { affirmedNetworkcontextMIB 19 }

affirmedNetworkContextIpRoutingEntry OBJECT-TYPE
    SYNTAX      AffirmedNetworkContextIpRoutingEntry
    MAX-ACCESS  not-accessible
    STATUS      deprecated
    DESCRIPTION ""
    INDEX { affirmedNetworkContextName, affirmedNetworkContextIpRoutingTablePrefix, affirmedNetworkContextIpRoutingTableLength }
        ::= { affirmedNetworkContextIpRoutingTable 1 }

AffirmedNetworkContextIpRoutingEntry ::=
    SEQUENCE {
        affirmedNetworkContextIpRoutingTablePrefix String,
        affirmedNetworkContextIpRoutingTableLength Unsigned32,
        affirmedNetworkContextIpRoutingTableOutput String
    }

affirmedNetworkContextIpRoutingTablePrefix OBJECT-TYPE
    SYNTAX      String
    MAX-ACCESS  not-accessible
    STATUS      current
    DESCRIPTION ""
    ::= { affirmedNetworkContextIpRoutingEntry 1 }

affirmedNetworkContextIpRoutingTableLength OBJECT-TYPE
    SYNTAX      Unsigned32
    MAX-ACCESS  not-accessible
    STATUS      current
    DESCRIPTION "Prefix length of the IP address"
    ::= { affirmedNetworkContextIpRoutingEntry 2 }

affirmedNetworkContextIpRoutingTableOutput OBJECT-TYPE
    SYNTAX      String
    MAX-ACCESS  read-only
    STATUS      current
    DESCRIPTION ""
    ::= { affirmedNetworkContextIpRoutingEntry 3 }

affirmedNetworkContextIpMplsFtnTable OBJECT-TYPE
    SYNTAX      SEQUENCE OF AffirmedNetworkContextIpMplsFtnEntry
    MAX-ACCESS  not-accessible
    STATUS      deprecated
    DESCRIPTION ""
    ::= { affirmedNetworkcontextMIB 22 }

affirmedNetworkContextIpMplsFtnEntry OBJECT-TYPE
    SYNTAX      AffirmedNetworkContextIpMplsFtnEntry
    MAX-ACCESS  not-accessible
    STATUS      deprecated
    DESCRIPTION ""
    INDEX { affirmedNetworkContextName, affirmedNetworkContextIpMplsFtnTableEntryId }
        ::= { affirmedNetworkContextIpMplsFtnTable 1 }

AffirmedNetworkContextIpMplsFtnEntry ::=
    SEQUENCE {
        affirmedNetworkContextIpMplsFtnTableEntryId INTEGER,
        affirmedNetworkContextIpMplsFtnTableOutput String
    }

affirmedNetworkContextIpMplsFtnTableEntryId OBJECT-TYPE
    SYNTAX      INTEGER {entry(0)}
    MAX-ACCESS  not-accessible
    STATUS      current
    DESCRIPTION ""
    ::= { affirmedNetworkContextIpMplsFtnEntry 1 }

affirmedNetworkContextIpMplsFtnTableOutput OBJECT-TYPE
    SYNTAX      String
    MAX-ACCESS  read-only
    STATUS      current
    DESCRIPTION ""
    ::= { affirmedNetworkContextIpMplsFtnEntry 2 }

affirmedNetworkContextIpMplsIlmTable OBJECT-TYPE
    SYNTAX      SEQUENCE OF AffirmedNetworkContextIpMplsIlmEntry
    MAX-ACCESS  not-accessible
    STATUS      deprecated
    DESCRIPTION ""
    ::= { affirmedNetworkcontextMIB 23 }

affirmedNetworkContextIpMplsIlmEntry OBJECT-TYPE
    SYNTAX      AffirmedNetworkContextIpMplsIlmEntry
    MAX-ACCESS  not-accessible
    STATUS      deprecated
    DESCRIPTION ""
    INDEX { affirmedNetworkContextName, affirmedNetworkContextIpMplsIlmTableEntryId }
        ::= { affirmedNetworkContextIpMplsIlmTable 1 }

AffirmedNetworkContextIpMplsIlmEntry ::=
    SEQUENCE {
        affirmedNetworkContextIpMplsIlmTableEntryId INTEGER,
        affirmedNetworkContextIpMplsIlmTableOutput String
    }

affirmedNetworkContextIpMplsIlmTableEntryId OBJECT-TYPE
    SYNTAX      INTEGER {entry(0)}
    MAX-ACCESS  not-accessible
    STATUS      current
    DESCRIPTION ""
    ::= { affirmedNetworkContextIpMplsIlmEntry 1 }

affirmedNetworkContextIpMplsIlmTableOutput OBJECT-TYPE
    SYNTAX      String
    MAX-ACCESS  read-only
    STATUS      current
    DESCRIPTION ""
    ::= { affirmedNetworkContextIpMplsIlmEntry 2 }

affirmedNetworkContextIpV4RouteStatusNewTable OBJECT-TYPE
    SYNTAX      SEQUENCE OF AffirmedNetworkContextIpV4RouteStatusNewEntry
    MAX-ACCESS  not-accessible
    STATUS      current
    DESCRIPTION ""
    ::= { affirmedNetworkcontextMIB 42 }

affirmedNetworkContextIpV4RouteStatusNewEntry OBJECT-TYPE
    SYNTAX      AffirmedNetworkContextIpV4RouteStatusNewEntry
    MAX-ACCESS  not-accessible
    STATUS      current
    DESCRIPTION ""
    INDEX { affirmedNetworkContextName, affirmedNetworkContextIpV4RouteStatusNewDest, affirmedNetworkContextIpV4RouteStatusNewPrefix, affirmedNetworkContextIpV4RouteStatusNewNextHop, affirmedNetworkContextIpV4RouteStatusNewIpInterface }
        ::= { affirmedNetworkContextIpV4RouteStatusNewTable 1 }

AffirmedNetworkContextIpV4RouteStatusNewEntry ::=
    SEQUENCE {
        affirmedNetworkContextIpV4RouteStatusNewDest String,
        affirmedNetworkContextIpV4RouteStatusNewPrefix Unsigned32,
        affirmedNetworkContextIpV4RouteStatusNewNextHop String,
        affirmedNetworkContextIpV4RouteStatusNewIpInterface String,
        affirmedNetworkContextIpV4RouteStatusNewPreference Unsigned32,
        affirmedNetworkContextIpV4RouteStatusNewType INTEGER
    }

affirmedNetworkContextIpV4RouteStatusNewDest OBJECT-TYPE
    SYNTAX      String
    MAX-ACCESS  not-accessible
    STATUS      current
    DESCRIPTION ""
    ::= { affirmedNetworkContextIpV4RouteStatusNewEntry 1 }

affirmedNetworkContextIpV4RouteStatusNewPrefix OBJECT-TYPE
    SYNTAX      Unsigned32
    MAX-ACCESS  not-accessible
    STATUS      current
    DESCRIPTION "Prefix length of the IP address"
    ::= { affirmedNetworkContextIpV4RouteStatusNewEntry 2 }

affirmedNetworkContextIpV4RouteStatusNewNextHop OBJECT-TYPE
    SYNTAX      String
    MAX-ACCESS  not-accessible
    STATUS      current
    DESCRIPTION ""
    ::= { affirmedNetworkContextIpV4RouteStatusNewEntry 3 }

affirmedNetworkContextIpV4RouteStatusNewIpInterface OBJECT-TYPE
    SYNTAX      String
    MAX-ACCESS  not-accessible
    STATUS      current
    DESCRIPTION ""
    ::= { affirmedNetworkContextIpV4RouteStatusNewEntry 4 }

affirmedNetworkContextIpV4RouteStatusNewPreference OBJECT-TYPE
    SYNTAX      Unsigned32
    MAX-ACCESS  read-only
    STATUS      current
    DESCRIPTION ""
    ::= { affirmedNetworkContextIpV4RouteStatusNewEntry 5 }

affirmedNetworkContextIpV4RouteStatusNewType OBJECT-TYPE
    SYNTAX      INTEGER {static(0),ospf(1),other(2)}
    MAX-ACCESS  read-only
    STATUS      current
    DESCRIPTION ""
    ::= { affirmedNetworkContextIpV4RouteStatusNewEntry 6 }

affirmedNetworkContextIpV4RouteStatusTable OBJECT-TYPE
    SYNTAX      SEQUENCE OF AffirmedNetworkContextIpV4RouteStatusEntry
    MAX-ACCESS  not-accessible
    STATUS      deprecated
    DESCRIPTION ""
    ::= { affirmedNetworkcontextMIB 7 }

affirmedNetworkContextIpV4RouteStatusEntry OBJECT-TYPE
    SYNTAX      AffirmedNetworkContextIpV4RouteStatusEntry
    MAX-ACCESS  not-accessible
    STATUS      deprecated
    DESCRIPTION ""
    INDEX { affirmedNetworkContextName, affirmedNetworkContextIpV4RouteStatusDest, affirmedNetworkContextIpV4RouteStatusPrefix, affirmedNetworkContextIpV4RouteStatusNextHop }
        ::= { affirmedNetworkContextIpV4RouteStatusTable 1 }

AffirmedNetworkContextIpV4RouteStatusEntry ::=
    SEQUENCE {
        affirmedNetworkContextIpV4RouteStatusDest String,
        affirmedNetworkContextIpV4RouteStatusPrefix Unsigned32,
        affirmedNetworkContextIpV4RouteStatusNextHop String,
        affirmedNetworkContextIpV4RouteStatusIpInterface String,
        affirmedNetworkContextIpV4RouteStatusPreference Unsigned32,
        affirmedNetworkContextIpV4RouteStatusType INTEGER
    }

affirmedNetworkContextIpV4RouteStatusDest OBJECT-TYPE
    SYNTAX      String
    MAX-ACCESS  not-accessible
    STATUS      current
    DESCRIPTION ""
    ::= { affirmedNetworkContextIpV4RouteStatusEntry 1 }

affirmedNetworkContextIpV4RouteStatusPrefix OBJECT-TYPE
    SYNTAX      Unsigned32
    MAX-ACCESS  not-accessible
    STATUS      current
    DESCRIPTION "Prefix length of the IP address"
    ::= { affirmedNetworkContextIpV4RouteStatusEntry 2 }

affirmedNetworkContextIpV4RouteStatusNextHop OBJECT-TYPE
    SYNTAX      String
    MAX-ACCESS  not-accessible
    STATUS      current
    DESCRIPTION ""
    ::= { affirmedNetworkContextIpV4RouteStatusEntry 3 }

affirmedNetworkContextIpV4RouteStatusIpInterface OBJECT-TYPE
    SYNTAX      String
    MAX-ACCESS  read-only
    STATUS      current
    DESCRIPTION ""
    ::= { affirmedNetworkContextIpV4RouteStatusEntry 4 }

affirmedNetworkContextIpV4RouteStatusPreference OBJECT-TYPE
    SYNTAX      Unsigned32
    MAX-ACCESS  read-only
    STATUS      current
    DESCRIPTION ""
    ::= { affirmedNetworkContextIpV4RouteStatusEntry 5 }

affirmedNetworkContextIpV4RouteStatusType OBJECT-TYPE
    SYNTAX      INTEGER {static(0),ospf(1),other(2)}
    MAX-ACCESS  read-only
    STATUS      current
    DESCRIPTION ""
    ::= { affirmedNetworkContextIpV4RouteStatusEntry 6 }

affirmedNetworkContextIpV4RoutingTable OBJECT-TYPE
    SYNTAX      SEQUENCE OF AffirmedNetworkContextIpV4RoutingEntry
    MAX-ACCESS  not-accessible
    STATUS      deprecated
    DESCRIPTION ""
    ::= { affirmedNetworkcontextMIB 20 }

affirmedNetworkContextIpV4RoutingEntry OBJECT-TYPE
    SYNTAX      AffirmedNetworkContextIpV4RoutingEntry
    MAX-ACCESS  not-accessible
    STATUS      deprecated
    DESCRIPTION ""
    INDEX { affirmedNetworkContextName, affirmedNetworkContextIpV4RoutingTablePrefix, affirmedNetworkContextIpV4RoutingTableLength }
        ::= { affirmedNetworkContextIpV4RoutingTable 1 }

AffirmedNetworkContextIpV4RoutingEntry ::=
    SEQUENCE {
        affirmedNetworkContextIpV4RoutingTablePrefix String,
        affirmedNetworkContextIpV4RoutingTableLength Unsigned32,
        affirmedNetworkContextIpV4RoutingTableOutput String
    }

affirmedNetworkContextIpV4RoutingTablePrefix OBJECT-TYPE
    SYNTAX      String
    MAX-ACCESS  not-accessible
    STATUS      current
    DESCRIPTION ""
    ::= { affirmedNetworkContextIpV4RoutingEntry 1 }

affirmedNetworkContextIpV4RoutingTableLength OBJECT-TYPE
    SYNTAX      Unsigned32
    MAX-ACCESS  not-accessible
    STATUS      current
    DESCRIPTION "Prefix length of the IP address"
    ::= { affirmedNetworkContextIpV4RoutingEntry 2 }

affirmedNetworkContextIpV4RoutingTableOutput OBJECT-TYPE
    SYNTAX      String
    MAX-ACCESS  read-only
    STATUS      current
    DESCRIPTION ""
    ::= { affirmedNetworkContextIpV4RoutingEntry 3 }

affirmedNetworkContextIpV6RouteStatusNewTable OBJECT-TYPE
    SYNTAX      SEQUENCE OF AffirmedNetworkContextIpV6RouteStatusNewEntry
    MAX-ACCESS  not-accessible
    STATUS      current
    DESCRIPTION ""
    ::= { affirmedNetworkcontextMIB 43 }

affirmedNetworkContextIpV6RouteStatusNewEntry OBJECT-TYPE
    SYNTAX      AffirmedNetworkContextIpV6RouteStatusNewEntry
    MAX-ACCESS  not-accessible
    STATUS      current
    DESCRIPTION ""
    INDEX { affirmedNetworkContextName, affirmedNetworkContextIpV6RouteStatusNewDest, affirmedNetworkContextIpV6RouteStatusNewPrefix, affirmedNetworkContextIpV6RouteStatusNewNextHop, affirmedNetworkContextIpV6RouteStatusNewIpInterface }
        ::= { affirmedNetworkContextIpV6RouteStatusNewTable 1 }

AffirmedNetworkContextIpV6RouteStatusNewEntry ::=
    SEQUENCE {
        affirmedNetworkContextIpV6RouteStatusNewDest String,
        affirmedNetworkContextIpV6RouteStatusNewPrefix Unsigned32,
        affirmedNetworkContextIpV6RouteStatusNewNextHop String,
        affirmedNetworkContextIpV6RouteStatusNewIpInterface String,
        affirmedNetworkContextIpV6RouteStatusNewPreference Unsigned32,
        affirmedNetworkContextIpV6RouteStatusNewType INTEGER
    }

affirmedNetworkContextIpV6RouteStatusNewDest OBJECT-TYPE
    SYNTAX      String
    MAX-ACCESS  not-accessible
    STATUS      current
    DESCRIPTION ""
    ::= { affirmedNetworkContextIpV6RouteStatusNewEntry 1 }

affirmedNetworkContextIpV6RouteStatusNewPrefix OBJECT-TYPE
    SYNTAX      Unsigned32
    MAX-ACCESS  not-accessible
    STATUS      current
    DESCRIPTION "Prefix length of the IP address"
    ::= { affirmedNetworkContextIpV6RouteStatusNewEntry 2 }

affirmedNetworkContextIpV6RouteStatusNewNextHop OBJECT-TYPE
    SYNTAX      String
    MAX-ACCESS  not-accessible
    STATUS      current
    DESCRIPTION ""
    ::= { affirmedNetworkContextIpV6RouteStatusNewEntry 3 }

affirmedNetworkContextIpV6RouteStatusNewIpInterface OBJECT-TYPE
    SYNTAX      String
    MAX-ACCESS  not-accessible
    STATUS      current
    DESCRIPTION ""
    ::= { affirmedNetworkContextIpV6RouteStatusNewEntry 4 }

affirmedNetworkContextIpV6RouteStatusNewPreference OBJECT-TYPE
    SYNTAX      Unsigned32
    MAX-ACCESS  read-only
    STATUS      current
    DESCRIPTION ""
    ::= { affirmedNetworkContextIpV6RouteStatusNewEntry 5 }

affirmedNetworkContextIpV6RouteStatusNewType OBJECT-TYPE
    SYNTAX      INTEGER {static(0),ospf(1),other(2)}
    MAX-ACCESS  read-only
    STATUS      current
    DESCRIPTION ""
    ::= { affirmedNetworkContextIpV6RouteStatusNewEntry 6 }

affirmedNetworkContextIpV6RouteStatusTable OBJECT-TYPE
    SYNTAX      SEQUENCE OF AffirmedNetworkContextIpV6RouteStatusEntry
    MAX-ACCESS  not-accessible
    STATUS      deprecated
    DESCRIPTION ""
    ::= { affirmedNetworkcontextMIB 8 }

affirmedNetworkContextIpV6RouteStatusEntry OBJECT-TYPE
    SYNTAX      AffirmedNetworkContextIpV6RouteStatusEntry
    MAX-ACCESS  not-accessible
    STATUS      deprecated
    DESCRIPTION ""
    INDEX { affirmedNetworkContextName, affirmedNetworkContextIpV6RouteStatusDest, affirmedNetworkContextIpV6RouteStatusPrefix, affirmedNetworkContextIpV6RouteStatusNextHop }
        ::= { affirmedNetworkContextIpV6RouteStatusTable 1 }

AffirmedNetworkContextIpV6RouteStatusEntry ::=
    SEQUENCE {
        affirmedNetworkContextIpV6RouteStatusDest String,
        affirmedNetworkContextIpV6RouteStatusPrefix Unsigned32,
        affirmedNetworkContextIpV6RouteStatusNextHop String,
        affirmedNetworkContextIpV6RouteStatusIpInterface String,
        affirmedNetworkContextIpV6RouteStatusPreference Unsigned32,
        affirmedNetworkContextIpV6RouteStatusType INTEGER
    }

affirmedNetworkContextIpV6RouteStatusDest OBJECT-TYPE
    SYNTAX      String
    MAX-ACCESS  not-accessible
    STATUS      current
    DESCRIPTION ""
    ::= { affirmedNetworkContextIpV6RouteStatusEntry 1 }

affirmedNetworkContextIpV6RouteStatusPrefix OBJECT-TYPE
    SYNTAX      Unsigned32
    MAX-ACCESS  not-accessible
    STATUS      current
    DESCRIPTION "Prefix length of the IP address"
    ::= { affirmedNetworkContextIpV6RouteStatusEntry 2 }

affirmedNetworkContextIpV6RouteStatusNextHop OBJECT-TYPE
    SYNTAX      String
    MAX-ACCESS  not-accessible
    STATUS      current
    DESCRIPTION ""
    ::= { affirmedNetworkContextIpV6RouteStatusEntry 3 }

affirmedNetworkContextIpV6RouteStatusIpInterface OBJECT-TYPE
    SYNTAX      String
    MAX-ACCESS  read-only
    STATUS      current
    DESCRIPTION ""
    ::= { affirmedNetworkContextIpV6RouteStatusEntry 4 }

affirmedNetworkContextIpV6RouteStatusPreference OBJECT-TYPE
    SYNTAX      Unsigned32
    MAX-ACCESS  read-only
    STATUS      current
    DESCRIPTION ""
    ::= { affirmedNetworkContextIpV6RouteStatusEntry 5 }

affirmedNetworkContextIpV6RouteStatusType OBJECT-TYPE
    SYNTAX      INTEGER {static(0),ospf(1),other(2)}
    MAX-ACCESS  read-only
    STATUS      current
    DESCRIPTION ""
    ::= { affirmedNetworkContextIpV6RouteStatusEntry 6 }

affirmedNetworkContextIpV6RoutingTable OBJECT-TYPE
    SYNTAX      SEQUENCE OF AffirmedNetworkContextIpV6RoutingEntry
    MAX-ACCESS  not-accessible
    STATUS      deprecated
    DESCRIPTION ""
    ::= { affirmedNetworkcontextMIB 21 }

affirmedNetworkContextIpV6RoutingEntry OBJECT-TYPE
    SYNTAX      AffirmedNetworkContextIpV6RoutingEntry
    MAX-ACCESS  not-accessible
    STATUS      deprecated
    DESCRIPTION ""
    INDEX { affirmedNetworkContextName, affirmedNetworkContextIpV6RoutingTablePrefix, affirmedNetworkContextIpV6RoutingTableLength }
        ::= { affirmedNetworkContextIpV6RoutingTable 1 }

AffirmedNetworkContextIpV6RoutingEntry ::=
    SEQUENCE {
        affirmedNetworkContextIpV6RoutingTablePrefix String,
        affirmedNetworkContextIpV6RoutingTableLength Unsigned32,
        affirmedNetworkContextIpV6RoutingTableOutput String
    }

affirmedNetworkContextIpV6RoutingTablePrefix OBJECT-TYPE
    SYNTAX      String
    MAX-ACCESS  not-accessible
    STATUS      current
    DESCRIPTION ""
    ::= { affirmedNetworkContextIpV6RoutingEntry 1 }

affirmedNetworkContextIpV6RoutingTableLength OBJECT-TYPE
    SYNTAX      Unsigned32
    MAX-ACCESS  not-accessible
    STATUS      current
    DESCRIPTION "Prefix length of the IP address"
    ::= { affirmedNetworkContextIpV6RoutingEntry 2 }

affirmedNetworkContextIpV6RoutingTableOutput OBJECT-TYPE
    SYNTAX      String
    MAX-ACCESS  read-only
    STATUS      current
    DESCRIPTION ""
    ::= { affirmedNetworkContextIpV6RoutingEntry 3 }

affirmedNetworkContextIpForwardingTable OBJECT-TYPE
    SYNTAX      SEQUENCE OF AffirmedNetworkContextIpForwardingEntry
    MAX-ACCESS  not-accessible
    STATUS      current
    DESCRIPTION ""
    ::= { affirmedNetworkcontextMIB 35 }

affirmedNetworkContextIpForwardingEntry OBJECT-TYPE
    SYNTAX      AffirmedNetworkContextIpForwardingEntry
    MAX-ACCESS  not-accessible
    STATUS      current
    DESCRIPTION ""
    INDEX { affirmedNetworkContextName, affirmedNetworkContextIpForwardingTableSlot, affirmedNetworkContextIpForwardingTableDestination, affirmedNetworkContextIpForwardingTablePrefixLength, affirmedNetworkContextIpForwardingTableGateway, affirmedNetworkContextIpForwardingTableInterface }
        ::= { affirmedNetworkContextIpForwardingTable 1 }

AffirmedNetworkContextIpForwardingEntry ::=
    SEQUENCE {
        affirmedNetworkContextIpForwardingTableSlot Unsigned32,
        affirmedNetworkContextIpForwardingTableDestination String,
        affirmedNetworkContextIpForwardingTablePrefixLength Unsigned32,
        affirmedNetworkContextIpForwardingTableGateway String,
        affirmedNetworkContextIpForwardingTableInterface String,
        affirmedNetworkContextIpForwardingTableFlags Unsigned32,
        affirmedNetworkContextIpForwardingTableType String,
        affirmedNetworkContextIpForwardingTableMetric Unsigned32,
        affirmedNetworkContextIpForwardingTableState String,
        affirmedNetworkContextIpForwardingTableHostCsm String
    }

affirmedNetworkContextIpForwardingTableSlot OBJECT-TYPE
    SYNTAX      Unsigned32
    MAX-ACCESS  not-accessible
    STATUS      current
    DESCRIPTION ""
    ::= { affirmedNetworkContextIpForwardingEntry 1 }

affirmedNetworkContextIpForwardingTableDestination OBJECT-TYPE
    SYNTAX      String
    MAX-ACCESS  not-accessible
    STATUS      current
    DESCRIPTION ""
    ::= { affirmedNetworkContextIpForwardingEntry 2 }

affirmedNetworkContextIpForwardingTablePrefixLength OBJECT-TYPE
    SYNTAX      Unsigned32
    MAX-ACCESS  not-accessible
    STATUS      current
    DESCRIPTION ""
    ::= { affirmedNetworkContextIpForwardingEntry 3 }

affirmedNetworkContextIpForwardingTableGateway OBJECT-TYPE
    SYNTAX      String
    MAX-ACCESS  not-accessible
    STATUS      current
    DESCRIPTION ""
    ::= { affirmedNetworkContextIpForwardingEntry 4 }

affirmedNetworkContextIpForwardingTableInterface OBJECT-TYPE
    SYNTAX      String
    MAX-ACCESS  not-accessible
    STATUS      current
    DESCRIPTION ""
    ::= { affirmedNetworkContextIpForwardingEntry 5 }

affirmedNetworkContextIpForwardingTableFlags OBJECT-TYPE
    SYNTAX      Unsigned32
    MAX-ACCESS  read-only
    STATUS      current
    DESCRIPTION ""
    ::= { affirmedNetworkContextIpForwardingEntry 6 }

affirmedNetworkContextIpForwardingTableType OBJECT-TYPE
    SYNTAX      String
    MAX-ACCESS  read-only
    STATUS      current
    DESCRIPTION "Type of route"
    ::= { affirmedNetworkContextIpForwardingEntry 7 }

affirmedNetworkContextIpForwardingTableMetric OBJECT-TYPE
    SYNTAX      Unsigned32
    MAX-ACCESS  read-only
    STATUS      current
    DESCRIPTION "Display metric"
    ::= { affirmedNetworkContextIpForwardingEntry 8 }

affirmedNetworkContextIpForwardingTableState OBJECT-TYPE
    SYNTAX      String
    MAX-ACCESS  read-only
    STATUS      current
    DESCRIPTION "Display state of a route"
    ::= { affirmedNetworkContextIpForwardingEntry 9 }

affirmedNetworkContextIpForwardingTableHostCsm OBJECT-TYPE
    SYNTAX      String
    MAX-ACCESS  read-only
    STATUS      current
    DESCRIPTION "Display slot id"
    ::= { affirmedNetworkContextIpForwardingEntry 10 }

affirmedNetworkContextIpVpnRtmTable OBJECT-TYPE
    SYNTAX      SEQUENCE OF AffirmedNetworkContextIpVpnRtmEntry
    MAX-ACCESS  not-accessible
    STATUS      current
    DESCRIPTION ""
    ::= { affirmedNetworkcontextMIB 36 }

affirmedNetworkContextIpVpnRtmEntry OBJECT-TYPE
    SYNTAX      AffirmedNetworkContextIpVpnRtmEntry
    MAX-ACCESS  not-accessible
    STATUS      current
    DESCRIPTION ""
    INDEX { affirmedNetworkContextName, affirmedNetworkContextIpVpnRtmSlot, affirmedNetworkContextIpVpnRtmDestination, affirmedNetworkContextIpVpnRtmPrefixLength, affirmedNetworkContextIpVpnRtmLabelGateway, affirmedNetworkContextIpVpnRtmLabels }
        ::= { affirmedNetworkContextIpVpnRtmTable 1 }

AffirmedNetworkContextIpVpnRtmEntry ::=
    SEQUENCE {
        affirmedNetworkContextIpVpnRtmSlot Unsigned32,
        affirmedNetworkContextIpVpnRtmDestination String,
        affirmedNetworkContextIpVpnRtmPrefixLength Unsigned32,
        affirmedNetworkContextIpVpnRtmLabelGateway String,
        affirmedNetworkContextIpVpnRtmLabels String,
        affirmedNetworkContextIpVpnRtmState String,
        affirmedNetworkContextIpVpnRtmHostCsm Unsigned32
    }

affirmedNetworkContextIpVpnRtmSlot OBJECT-TYPE
    SYNTAX      Unsigned32
    MAX-ACCESS  not-accessible
    STATUS      current
    DESCRIPTION ""
    ::= { affirmedNetworkContextIpVpnRtmEntry 1 }

affirmedNetworkContextIpVpnRtmDestination OBJECT-TYPE
    SYNTAX      String
    MAX-ACCESS  not-accessible
    STATUS      current
    DESCRIPTION ""
    ::= { affirmedNetworkContextIpVpnRtmEntry 2 }

affirmedNetworkContextIpVpnRtmPrefixLength OBJECT-TYPE
    SYNTAX      Unsigned32
    MAX-ACCESS  not-accessible
    STATUS      current
    DESCRIPTION ""
    ::= { affirmedNetworkContextIpVpnRtmEntry 3 }

affirmedNetworkContextIpVpnRtmLabelGateway OBJECT-TYPE
    SYNTAX      String
    MAX-ACCESS  not-accessible
    STATUS      current
    DESCRIPTION ""
    ::= { affirmedNetworkContextIpVpnRtmEntry 4 }

affirmedNetworkContextIpVpnRtmLabels OBJECT-TYPE
    SYNTAX      String
    MAX-ACCESS  not-accessible
    STATUS      current
    DESCRIPTION ""
    ::= { affirmedNetworkContextIpVpnRtmEntry 5 }

affirmedNetworkContextIpVpnRtmState OBJECT-TYPE
    SYNTAX      String
    MAX-ACCESS  read-only
    STATUS      current
    DESCRIPTION ""
    ::= { affirmedNetworkContextIpVpnRtmEntry 6 }

affirmedNetworkContextIpVpnRtmHostCsm OBJECT-TYPE
    SYNTAX      Unsigned32
    MAX-ACCESS  read-only
    STATUS      current
    DESCRIPTION ""
    ::= { affirmedNetworkContextIpVpnRtmEntry 7 }

affirmedNetworkContextShowIpInterfaceIpInterfaceTableNewTable OBJECT-TYPE
    SYNTAX      SEQUENCE OF AffirmedNetworkContextShowIpInterfaceIpInterfaceTableNewEntry
    MAX-ACCESS  not-accessible
    STATUS      current
    DESCRIPTION ""
    ::= { affirmedNetworkcontextMIB 38 }

affirmedNetworkContextShowIpInterfaceIpInterfaceTableNewEntry OBJECT-TYPE
    SYNTAX      AffirmedNetworkContextShowIpInterfaceIpInterfaceTableNewEntry
    MAX-ACCESS  not-accessible
    STATUS      current
    DESCRIPTION ""
    INDEX { affirmedNetworkContextName, affirmedNetworkContextShowIpInterfaceIpInterfaceTableNewEntryId }
        ::= { affirmedNetworkContextShowIpInterfaceIpInterfaceTableNewTable 1 }

AffirmedNetworkContextShowIpInterfaceIpInterfaceTableNewEntry ::=
    SEQUENCE {
        affirmedNetworkContextShowIpInterfaceIpInterfaceTableNewEntryId INTEGER,
        affirmedNetworkContextShowIpInterfaceIpInterfaceTableNewOutput String
    }

affirmedNetworkContextShowIpInterfaceIpInterfaceTableNewEntryId OBJECT-TYPE
    SYNTAX      INTEGER {entry(0)}
    MAX-ACCESS  not-accessible
    STATUS      current
    DESCRIPTION ""
    ::= { affirmedNetworkContextShowIpInterfaceIpInterfaceTableNewEntry 1 }

affirmedNetworkContextShowIpInterfaceIpInterfaceTableNewOutput OBJECT-TYPE
    SYNTAX      String
    MAX-ACCESS  read-only
    STATUS      current
    DESCRIPTION ""
    ::= { affirmedNetworkContextShowIpInterfaceIpInterfaceTableNewEntry 2 }

affirmedNetworkContextShowIpInterfaceSummaryTable OBJECT-TYPE
    SYNTAX      SEQUENCE OF AffirmedNetworkContextShowIpInterfaceSummaryEntry
    MAX-ACCESS  not-accessible
    STATUS      deprecated
    DESCRIPTION ""
    ::= { affirmedNetworkcontextMIB 39 }

affirmedNetworkContextShowIpInterfaceSummaryEntry OBJECT-TYPE
    SYNTAX      AffirmedNetworkContextShowIpInterfaceSummaryEntry
    MAX-ACCESS  not-accessible
    STATUS      deprecated
    DESCRIPTION ""
    INDEX { affirmedNetworkContextName, affirmedNetworkContextShowIpInterfaceSummarySlot, affirmedNetworkContextShowIpInterfaceSummaryPortName, affirmedNetworkContextShowIpInterfaceSummaryVlanId }
        ::= { affirmedNetworkContextShowIpInterfaceSummaryTable 1 }

AffirmedNetworkContextShowIpInterfaceSummaryEntry ::=
    SEQUENCE {
        affirmedNetworkContextShowIpInterfaceSummarySlot Unsigned32,
        affirmedNetworkContextShowIpInterfaceSummaryPortName String,
        affirmedNetworkContextShowIpInterfaceSummaryVlanId Unsigned32,
        affirmedNetworkContextShowIpInterfaceSummaryName String,
        affirmedNetworkContextShowIpInterfaceSummaryIfIndex Unsigned32,
        affirmedNetworkContextShowIpInterfaceSummaryIfNum Unsigned32,
        affirmedNetworkContextShowIpInterfaceSummaryNetContextId Unsigned32,
        affirmedNetworkContextShowIpInterfaceSummaryIpAddress String,
        affirmedNetworkContextShowIpInterfaceSummaryAdminState String,
        affirmedNetworkContextShowIpInterfaceSummaryOperState String
    }

affirmedNetworkContextShowIpInterfaceSummarySlot OBJECT-TYPE
    SYNTAX      Unsigned32
    MAX-ACCESS  not-accessible
    STATUS      current
    DESCRIPTION ""
    ::= { affirmedNetworkContextShowIpInterfaceSummaryEntry 1 }

affirmedNetworkContextShowIpInterfaceSummaryPortName OBJECT-TYPE
    SYNTAX      String
    MAX-ACCESS  not-accessible
    STATUS      current
    DESCRIPTION ""
    ::= { affirmedNetworkContextShowIpInterfaceSummaryEntry 2 }

affirmedNetworkContextShowIpInterfaceSummaryVlanId OBJECT-TYPE
    SYNTAX      Unsigned32
    MAX-ACCESS  not-accessible
    STATUS      current
    DESCRIPTION ""
    ::= { affirmedNetworkContextShowIpInterfaceSummaryEntry 3 }

affirmedNetworkContextShowIpInterfaceSummaryName OBJECT-TYPE
    SYNTAX      String
    MAX-ACCESS  read-only
    STATUS      current
    DESCRIPTION ""
    ::= { affirmedNetworkContextShowIpInterfaceSummaryEntry 4 }

affirmedNetworkContextShowIpInterfaceSummaryIfIndex OBJECT-TYPE
    SYNTAX      Unsigned32
    MAX-ACCESS  read-only
    STATUS      current
    DESCRIPTION ""
    ::= { affirmedNetworkContextShowIpInterfaceSummaryEntry 5 }

affirmedNetworkContextShowIpInterfaceSummaryIfNum OBJECT-TYPE
    SYNTAX      Unsigned32
    MAX-ACCESS  read-only
    STATUS      current
    DESCRIPTION ""
    ::= { affirmedNetworkContextShowIpInterfaceSummaryEntry 6 }

affirmedNetworkContextShowIpInterfaceSummaryNetContextId OBJECT-TYPE
    SYNTAX      Unsigned32
    MAX-ACCESS  read-only
    STATUS      current
    DESCRIPTION ""
    ::= { affirmedNetworkContextShowIpInterfaceSummaryEntry 7 }

affirmedNetworkContextShowIpInterfaceSummaryIpAddress OBJECT-TYPE
    SYNTAX      String
    MAX-ACCESS  read-only
    STATUS      current
    DESCRIPTION ""
    ::= { affirmedNetworkContextShowIpInterfaceSummaryEntry 8 }

affirmedNetworkContextShowIpInterfaceSummaryAdminState OBJECT-TYPE
    SYNTAX      String
    MAX-ACCESS  read-only
    STATUS      current
    DESCRIPTION ""
    ::= { affirmedNetworkContextShowIpInterfaceSummaryEntry 9 }

affirmedNetworkContextShowIpInterfaceSummaryOperState OBJECT-TYPE
    SYNTAX      String
    MAX-ACCESS  read-only
    STATUS      current
    DESCRIPTION ""
    ::= { affirmedNetworkContextShowIpInterfaceSummaryEntry 10 }

affirmedNetworkContextShowIpInterfaceSummaryNewTable OBJECT-TYPE
    SYNTAX      SEQUENCE OF AffirmedNetworkContextShowIpInterfaceSummaryNewEntry
    MAX-ACCESS  not-accessible
    STATUS      current
    DESCRIPTION ""
    ::= { affirmedNetworkcontextMIB 40 }

affirmedNetworkContextShowIpInterfaceSummaryNewEntry OBJECT-TYPE
    SYNTAX      AffirmedNetworkContextShowIpInterfaceSummaryNewEntry
    MAX-ACCESS  not-accessible
    STATUS      current
    DESCRIPTION ""
    INDEX { affirmedNetworkContextName, affirmedNetworkContextShowIpInterfaceSummaryNewSlot, affirmedNetworkContextShowIpInterfaceSummaryNewName }
        ::= { affirmedNetworkContextShowIpInterfaceSummaryNewTable 1 }

AffirmedNetworkContextShowIpInterfaceSummaryNewEntry ::=
    SEQUENCE {
        affirmedNetworkContextShowIpInterfaceSummaryNewSlot Unsigned32,
        affirmedNetworkContextShowIpInterfaceSummaryNewName String,
        affirmedNetworkContextShowIpInterfaceSummaryNewPortName String,
        affirmedNetworkContextShowIpInterfaceSummaryNewVlanId Unsigned32,
        affirmedNetworkContextShowIpInterfaceSummaryNewIfIndex Unsigned32,
        affirmedNetworkContextShowIpInterfaceSummaryNewIfNum Unsigned32,
        affirmedNetworkContextShowIpInterfaceSummaryNewNetContextId Unsigned32,
        affirmedNetworkContextShowIpInterfaceSummaryNewIpAddress String,
        affirmedNetworkContextShowIpInterfaceSummaryNewAdminState String,
        affirmedNetworkContextShowIpInterfaceSummaryNewOperState String
    }

affirmedNetworkContextShowIpInterfaceSummaryNewSlot OBJECT-TYPE
    SYNTAX      Unsigned32
    MAX-ACCESS  not-accessible
    STATUS      current
    DESCRIPTION ""
    ::= { affirmedNetworkContextShowIpInterfaceSummaryNewEntry 1 }

affirmedNetworkContextShowIpInterfaceSummaryNewName OBJECT-TYPE
    SYNTAX      String
    MAX-ACCESS  not-accessible
    STATUS      current
    DESCRIPTION ""
    ::= { affirmedNetworkContextShowIpInterfaceSummaryNewEntry 2 }

affirmedNetworkContextShowIpInterfaceSummaryNewPortName OBJECT-TYPE
    SYNTAX      String
    MAX-ACCESS  read-only
    STATUS      current
    DESCRIPTION ""
    ::= { affirmedNetworkContextShowIpInterfaceSummaryNewEntry 3 }

affirmedNetworkContextShowIpInterfaceSummaryNewVlanId OBJECT-TYPE
    SYNTAX      Unsigned32
    MAX-ACCESS  read-only
    STATUS      current
    DESCRIPTION ""
    ::= { affirmedNetworkContextShowIpInterfaceSummaryNewEntry 4 }

affirmedNetworkContextShowIpInterfaceSummaryNewIfIndex OBJECT-TYPE
    SYNTAX      Unsigned32
    MAX-ACCESS  read-only
    STATUS      current
    DESCRIPTION ""
    ::= { affirmedNetworkContextShowIpInterfaceSummaryNewEntry 5 }

affirmedNetworkContextShowIpInterfaceSummaryNewIfNum OBJECT-TYPE
    SYNTAX      Unsigned32
    MAX-ACCESS  read-only
    STATUS      current
    DESCRIPTION ""
    ::= { affirmedNetworkContextShowIpInterfaceSummaryNewEntry 6 }

affirmedNetworkContextShowIpInterfaceSummaryNewNetContextId OBJECT-TYPE
    SYNTAX      Unsigned32
    MAX-ACCESS  read-only
    STATUS      current
    DESCRIPTION ""
    ::= { affirmedNetworkContextShowIpInterfaceSummaryNewEntry 7 }

affirmedNetworkContextShowIpInterfaceSummaryNewIpAddress OBJECT-TYPE
    SYNTAX      String
    MAX-ACCESS  read-only
    STATUS      current
    DESCRIPTION ""
    ::= { affirmedNetworkContextShowIpInterfaceSummaryNewEntry 8 }

affirmedNetworkContextShowIpInterfaceSummaryNewAdminState OBJECT-TYPE
    SYNTAX      String
    MAX-ACCESS  read-only
    STATUS      current
    DESCRIPTION ""
    ::= { affirmedNetworkContextShowIpInterfaceSummaryNewEntry 9 }

affirmedNetworkContextShowIpInterfaceSummaryNewOperState OBJECT-TYPE
    SYNTAX      String
    MAX-ACCESS  read-only
    STATUS      current
    DESCRIPTION ""
    ::= { affirmedNetworkContextShowIpInterfaceSummaryNewEntry 10 }

affirmedNetworkContextTunnelStatsTable OBJECT-TYPE
    SYNTAX      SEQUENCE OF AffirmedNetworkContextTunnelStatsEntry
    MAX-ACCESS  not-accessible
    STATUS      current
    DESCRIPTION ""
    ::= { affirmedNetworkcontextMIB 9 }

affirmedNetworkContextTunnelStatsEntry OBJECT-TYPE
    SYNTAX      AffirmedNetworkContextTunnelStatsEntry
    MAX-ACCESS  not-accessible
    STATUS      current
    DESCRIPTION ""
    INDEX { affirmedNetworkContextName, affirmedNetworkContextTunnelStatsTunName }
        ::= { affirmedNetworkContextTunnelStatsTable 1 }

AffirmedNetworkContextTunnelStatsEntry ::=
    SEQUENCE {
        affirmedNetworkContextTunnelStatsTunName String,
        affirmedNetworkContextTunnelStatsNumTxPkts ConfdString,
        affirmedNetworkContextTunnelStatsNumTxBytes ConfdString,
        affirmedNetworkContextTunnelStatsNumTxDropPkts ConfdString,
        affirmedNetworkContextTunnelStatsNumTxDropBytes ConfdString,
        affirmedNetworkContextTunnelStatsNumTxInvalidPkts ConfdString,
        affirmedNetworkContextTunnelStatsNumRxPkts ConfdString,
        affirmedNetworkContextTunnelStatsNumRxBytes ConfdString,
        affirmedNetworkContextTunnelStatsNumRxDropPkts ConfdString,
        affirmedNetworkContextTunnelStatsNumRxDropBytes ConfdString,
        affirmedNetworkContextTunnelStatsNumRxInvalidPkts ConfdString
    }

affirmedNetworkContextTunnelStatsTunName OBJECT-TYPE
    SYNTAX      String
    MAX-ACCESS  not-accessible
    STATUS      current
    DESCRIPTION "Tunnel name"
    ::= { affirmedNetworkContextTunnelStatsEntry 1 }

affirmedNetworkContextTunnelStatsNumTxPkts OBJECT-TYPE
    SYNTAX      ConfdString
    MAX-ACCESS  read-only
    STATUS      current
    DESCRIPTION "Number of transmitted packets"
    ::= { affirmedNetworkContextTunnelStatsEntry 2 }

affirmedNetworkContextTunnelStatsNumTxBytes OBJECT-TYPE
    SYNTAX      ConfdString
    MAX-ACCESS  read-only
    STATUS      current
    DESCRIPTION "Number of transmitted packet bytes"
    ::= { affirmedNetworkContextTunnelStatsEntry 3 }

affirmedNetworkContextTunnelStatsNumTxDropPkts OBJECT-TYPE
    SYNTAX      ConfdString
    MAX-ACCESS  read-only
    STATUS      current
    DESCRIPTION "Number of transmitted dropped packets"
    ::= { affirmedNetworkContextTunnelStatsEntry 4 }

affirmedNetworkContextTunnelStatsNumTxDropBytes OBJECT-TYPE
    SYNTAX      ConfdString
    MAX-ACCESS  read-only
    STATUS      current
    DESCRIPTION "Number of transmitted dropped packet bytes"
    ::= { affirmedNetworkContextTunnelStatsEntry 5 }

affirmedNetworkContextTunnelStatsNumTxInvalidPkts OBJECT-TYPE
    SYNTAX      ConfdString
    MAX-ACCESS  read-only
    STATUS      current
    DESCRIPTION "Number of transmitted invalid packets"
    ::= { affirmedNetworkContextTunnelStatsEntry 6 }

affirmedNetworkContextTunnelStatsNumRxPkts OBJECT-TYPE
    SYNTAX      ConfdString
    MAX-ACCESS  read-only
    STATUS      current
    DESCRIPTION "Number of received packets"
    ::= { affirmedNetworkContextTunnelStatsEntry 7 }

affirmedNetworkContextTunnelStatsNumRxBytes OBJECT-TYPE
    SYNTAX      ConfdString
    MAX-ACCESS  read-only
    STATUS      current
    DESCRIPTION "Number of received packet bytes"
    ::= { affirmedNetworkContextTunnelStatsEntry 8 }

affirmedNetworkContextTunnelStatsNumRxDropPkts OBJECT-TYPE
    SYNTAX      ConfdString
    MAX-ACCESS  read-only
    STATUS      current
    DESCRIPTION "Number of received dropped packets"
    ::= { affirmedNetworkContextTunnelStatsEntry 9 }

affirmedNetworkContextTunnelStatsNumRxDropBytes OBJECT-TYPE
    SYNTAX      ConfdString
    MAX-ACCESS  read-only
    STATUS      current
    DESCRIPTION "Number of received dropped packet bytes"
    ::= { affirmedNetworkContextTunnelStatsEntry 10 }

affirmedNetworkContextTunnelStatsNumRxInvalidPkts OBJECT-TYPE
    SYNTAX      ConfdString
    MAX-ACCESS  read-only
    STATUS      current
    DESCRIPTION ""
    ::= { affirmedNetworkContextTunnelStatsEntry 11 }

affirmedNetworkContextNetworkContextStatisticsTable OBJECT-TYPE
    SYNTAX      SEQUENCE OF AffirmedNetworkContextNetworkContextStatisticsEntry
    MAX-ACCESS  not-accessible
    STATUS      current
    DESCRIPTION ""
    ::= { affirmedNetworkcontextMIB 10 }

affirmedNetworkContextNetworkContextStatisticsEntry OBJECT-TYPE
    SYNTAX      AffirmedNetworkContextNetworkContextStatisticsEntry
    MAX-ACCESS  not-accessible
    STATUS      current
    DESCRIPTION ""
    INDEX { affirmedNetworkContextName, affirmedNetworkContextNetworkContextStatisticsName }
        ::= { affirmedNetworkContextNetworkContextStatisticsTable 1 }

AffirmedNetworkContextNetworkContextStatisticsEntry ::=
    SEQUENCE {
        affirmedNetworkContextNetworkContextStatisticsName String,
        affirmedNetworkContextNetworkContextStatisticsNumTxV4Pkts ConfdString,
        affirmedNetworkContextNetworkContextStatisticsNumTxV4Bytes ConfdString,
        affirmedNetworkContextNetworkContextStatisticsNumTxV4DropPkts ConfdString,
        affirmedNetworkContextNetworkContextStatisticsNumTxV4DropBytes ConfdString,
        affirmedNetworkContextNetworkContextStatisticsNumRxV4Pkts ConfdString,
        affirmedNetworkContextNetworkContextStatisticsNumRxV4Bytes ConfdString,
        affirmedNetworkContextNetworkContextStatisticsNumRxV4DropPkts ConfdString,
        affirmedNetworkContextNetworkContextStatisticsNumRxV4DropBytes ConfdString,
        affirmedNetworkContextNetworkContextStatisticsNumTxV6Pkts ConfdString,
        affirmedNetworkContextNetworkContextStatisticsNumTxV6Bytes ConfdString,
        affirmedNetworkContextNetworkContextStatisticsNumTxV6DropPkts ConfdString,
        affirmedNetworkContextNetworkContextStatisticsNumTxV6DropBytes ConfdString,
        affirmedNetworkContextNetworkContextStatisticsNumRxV6Pkts ConfdString,
        affirmedNetworkContextNetworkContextStatisticsNumRxV6Bytes ConfdString,
        affirmedNetworkContextNetworkContextStatisticsNumRxV6DropPkts ConfdString,
        affirmedNetworkContextNetworkContextStatisticsNumRxV6DropBytes ConfdString,
        affirmedNetworkContextNetworkContextStatisticsNumRxMplsPkts ConfdString,
        affirmedNetworkContextNetworkContextStatisticsNumRxMplsBytes ConfdString,
        affirmedNetworkContextNetworkContextStatisticsNumRxMplsUnknownLabelPkts ConfdString,
        affirmedNetworkContextNetworkContextStatisticsNumRxMplsDropPkts ConfdString,
        affirmedNetworkContextNetworkContextStatisticsNumTxMplsPkts ConfdString,
        affirmedNetworkContextNetworkContextStatisticsNumRxICMPV4Pkts ConfdString,
        affirmedNetworkContextNetworkContextStatisticsNumTxICMPV4Pkts ConfdString,
        affirmedNetworkContextNetworkContextStatisticsNumRxICMPV6Pkts ConfdString,
        affirmedNetworkContextNetworkContextStatisticsNumTxICMPV6Pkts ConfdString,
        affirmedNetworkContextNetworkContextStatisticsNumTxMplsBytes ConfdString,
        affirmedNetworkContextNetworkContextStatisticsNumTxNoRouteDropPkts ConfdString,
        affirmedNetworkContextNetworkContextStatisticsNumTxFragmentedPkts ConfdString
    }

affirmedNetworkContextNetworkContextStatisticsName OBJECT-TYPE
    SYNTAX      String
    MAX-ACCESS  not-accessible
    STATUS      current
    DESCRIPTION "network context name"
    ::= { affirmedNetworkContextNetworkContextStatisticsEntry 1 }

affirmedNetworkContextNetworkContextStatisticsNumTxV4Pkts OBJECT-TYPE
    SYNTAX      ConfdString
    MAX-ACCESS  read-only
    STATUS      current
    DESCRIPTION "Number of transmitted IPv4 packets"
    ::= { affirmedNetworkContextNetworkContextStatisticsEntry 2 }

affirmedNetworkContextNetworkContextStatisticsNumTxV4Bytes OBJECT-TYPE
    SYNTAX      ConfdString
    MAX-ACCESS  read-only
    STATUS      current
    DESCRIPTION "Number of transmitted IPv4 packet bytes"
    ::= { affirmedNetworkContextNetworkContextStatisticsEntry 3 }

affirmedNetworkContextNetworkContextStatisticsNumTxV4DropPkts OBJECT-TYPE
    SYNTAX      ConfdString
    MAX-ACCESS  read-only
    STATUS      current
    DESCRIPTION "Number of transmitted dropped IPv4 packets"
    ::= { affirmedNetworkContextNetworkContextStatisticsEntry 4 }

affirmedNetworkContextNetworkContextStatisticsNumTxV4DropBytes OBJECT-TYPE
    SYNTAX      ConfdString
    MAX-ACCESS  read-only
    STATUS      current
    DESCRIPTION "Number of transmitted dropped IPv4 packet bytes"
    ::= { affirmedNetworkContextNetworkContextStatisticsEntry 5 }

affirmedNetworkContextNetworkContextStatisticsNumRxV4Pkts OBJECT-TYPE
    SYNTAX      ConfdString
    MAX-ACCESS  read-only
    STATUS      current
    DESCRIPTION "Number of received IPv4 packets"
    ::= { affirmedNetworkContextNetworkContextStatisticsEntry 6 }

affirmedNetworkContextNetworkContextStatisticsNumRxV4Bytes OBJECT-TYPE
    SYNTAX      ConfdString
    MAX-ACCESS  read-only
    STATUS      current
    DESCRIPTION "Number of received IPv4 packet bytes"
    ::= { affirmedNetworkContextNetworkContextStatisticsEntry 7 }

affirmedNetworkContextNetworkContextStatisticsNumRxV4DropPkts OBJECT-TYPE
    SYNTAX      ConfdString
    MAX-ACCESS  read-only
    STATUS      current
    DESCRIPTION "Number of received dropped IPv4 packets"
    ::= { affirmedNetworkContextNetworkContextStatisticsEntry 8 }

affirmedNetworkContextNetworkContextStatisticsNumRxV4DropBytes OBJECT-TYPE
    SYNTAX      ConfdString
    MAX-ACCESS  read-only
    STATUS      current
    DESCRIPTION "Number of received dropped IPv4 packet bytes"
    ::= { affirmedNetworkContextNetworkContextStatisticsEntry 9 }

affirmedNetworkContextNetworkContextStatisticsNumTxV6Pkts OBJECT-TYPE
    SYNTAX      ConfdString
    MAX-ACCESS  read-only
    STATUS      current
    DESCRIPTION "Number of transmitted IPv6 packets"
    ::= { affirmedNetworkContextNetworkContextStatisticsEntry 10 }

affirmedNetworkContextNetworkContextStatisticsNumTxV6Bytes OBJECT-TYPE
    SYNTAX      ConfdString
    MAX-ACCESS  read-only
    STATUS      current
    DESCRIPTION "Number of transmitted IPv6 packet bytes"
    ::= { affirmedNetworkContextNetworkContextStatisticsEntry 11 }

affirmedNetworkContextNetworkContextStatisticsNumTxV6DropPkts OBJECT-TYPE
    SYNTAX      ConfdString
    MAX-ACCESS  read-only
    STATUS      current
    DESCRIPTION "Number of transmitted dropped IPv6 packets"
    ::= { affirmedNetworkContextNetworkContextStatisticsEntry 12 }

affirmedNetworkContextNetworkContextStatisticsNumTxV6DropBytes OBJECT-TYPE
    SYNTAX      ConfdString
    MAX-ACCESS  read-only
    STATUS      current
    DESCRIPTION "Number of transmitted dropped IPv6 bytes"
    ::= { affirmedNetworkContextNetworkContextStatisticsEntry 13 }

affirmedNetworkContextNetworkContextStatisticsNumRxV6Pkts OBJECT-TYPE
    SYNTAX      ConfdString
    MAX-ACCESS  read-only
    STATUS      current
    DESCRIPTION "Number of received IPv6 packets"
    ::= { affirmedNetworkContextNetworkContextStatisticsEntry 14 }

affirmedNetworkContextNetworkContextStatisticsNumRxV6Bytes OBJECT-TYPE
    SYNTAX      ConfdString
    MAX-ACCESS  read-only
    STATUS      current
    DESCRIPTION "Number of received IPv6 packet bytes"
    ::= { affirmedNetworkContextNetworkContextStatisticsEntry 15 }

affirmedNetworkContextNetworkContextStatisticsNumRxV6DropPkts OBJECT-TYPE
    SYNTAX      ConfdString
    MAX-ACCESS  read-only
    STATUS      current
    DESCRIPTION "Number of received dropped IPv6 packets"
    ::= { affirmedNetworkContextNetworkContextStatisticsEntry 16 }

affirmedNetworkContextNetworkContextStatisticsNumRxV6DropBytes OBJECT-TYPE
    SYNTAX      ConfdString
    MAX-ACCESS  read-only
    STATUS      current
    DESCRIPTION "Number of received dropped IPv6 packet bytes"
    ::= { affirmedNetworkContextNetworkContextStatisticsEntry 17 }

affirmedNetworkContextNetworkContextStatisticsNumRxMplsPkts OBJECT-TYPE
    SYNTAX      ConfdString
    MAX-ACCESS  read-only
    STATUS      current
    DESCRIPTION "Number of received MPLS packets"
    ::= { affirmedNetworkContextNetworkContextStatisticsEntry 18 }

affirmedNetworkContextNetworkContextStatisticsNumRxMplsBytes OBJECT-TYPE
    SYNTAX      ConfdString
    MAX-ACCESS  read-only
    STATUS      current
    DESCRIPTION "Number of received MPLS bytes"
    ::= { affirmedNetworkContextNetworkContextStatisticsEntry 19 }

affirmedNetworkContextNetworkContextStatisticsNumRxMplsUnknownLabelPkts OBJECT-TYPE
    SYNTAX      ConfdString
    MAX-ACCESS  read-only
    STATUS      current
    DESCRIPTION "Number of received MPLS packets with unknown labels"
    ::= { affirmedNetworkContextNetworkContextStatisticsEntry 20 }

affirmedNetworkContextNetworkContextStatisticsNumRxMplsDropPkts OBJECT-TYPE
    SYNTAX      ConfdString
    MAX-ACCESS  read-only
    STATUS      current
    DESCRIPTION "Number of dropped MPLS packets"
    ::= { affirmedNetworkContextNetworkContextStatisticsEntry 21 }

affirmedNetworkContextNetworkContextStatisticsNumTxMplsPkts OBJECT-TYPE
    SYNTAX      ConfdString
    MAX-ACCESS  read-only
    STATUS      current
    DESCRIPTION "Number of transmitted MPLS packets"
    ::= { affirmedNetworkContextNetworkContextStatisticsEntry 22 }

affirmedNetworkContextNetworkContextStatisticsNumRxICMPV4Pkts OBJECT-TYPE
    SYNTAX      ConfdString
    MAX-ACCESS  read-only
    STATUS      current
    DESCRIPTION "Number of received ICMPv4 packets"
    ::= { affirmedNetworkContextNetworkContextStatisticsEntry 23 }

affirmedNetworkContextNetworkContextStatisticsNumTxICMPV4Pkts OBJECT-TYPE
    SYNTAX      ConfdString
    MAX-ACCESS  read-only
    STATUS      current
    DESCRIPTION "Number of transmitted ICMPv4 packets"
    ::= { affirmedNetworkContextNetworkContextStatisticsEntry 24 }

affirmedNetworkContextNetworkContextStatisticsNumRxICMPV6Pkts OBJECT-TYPE
    SYNTAX      ConfdString
    MAX-ACCESS  read-only
    STATUS      current
    DESCRIPTION "Number of received ICMPv6 packets"
    ::= { affirmedNetworkContextNetworkContextStatisticsEntry 25 }

affirmedNetworkContextNetworkContextStatisticsNumTxICMPV6Pkts OBJECT-TYPE
    SYNTAX      ConfdString
    MAX-ACCESS  read-only
    STATUS      current
    DESCRIPTION "Number of transmitted ICMPv6 packets"
    ::= { affirmedNetworkContextNetworkContextStatisticsEntry 26 }

affirmedNetworkContextNetworkContextStatisticsNumTxMplsBytes OBJECT-TYPE
    SYNTAX      ConfdString
    MAX-ACCESS  read-only
    STATUS      current
    DESCRIPTION "Number of transmitted MPLS bytes"
    ::= { affirmedNetworkContextNetworkContextStatisticsEntry 27 }

affirmedNetworkContextNetworkContextStatisticsNumTxNoRouteDropPkts OBJECT-TYPE
    SYNTAX      ConfdString
    MAX-ACCESS  read-only
    STATUS      current
    DESCRIPTION "Number of Tx No Route Drop Pkts "
    ::= { affirmedNetworkContextNetworkContextStatisticsEntry 28 }

affirmedNetworkContextNetworkContextStatisticsNumTxFragmentedPkts OBJECT-TYPE
    SYNTAX      ConfdString
    MAX-ACCESS  read-only
    STATUS      current
    DESCRIPTION "Number of Tx Fragmented Pkts "
    ::= { affirmedNetworkContextNetworkContextStatisticsEntry 29 }

affirmedNetworkContextIpSubPoolStatusTable OBJECT-TYPE
    SYNTAX      SEQUENCE OF AffirmedNetworkContextIpSubPoolStatusEntry
    MAX-ACCESS  not-accessible
    STATUS      current
    DESCRIPTION ""
    ::= { affirmedNetworkcontextMIB 11 }

affirmedNetworkContextIpSubPoolStatusEntry OBJECT-TYPE
    SYNTAX      AffirmedNetworkContextIpSubPoolStatusEntry
    MAX-ACCESS  not-accessible
    STATUS      current
    DESCRIPTION ""
    INDEX { affirmedNetworkContextName, affirmedNetworkContextIpSubPoolStatusName }
        ::= { affirmedNetworkContextIpSubPoolStatusTable 1 }

AffirmedNetworkContextIpSubPoolStatusEntry ::=
    SEQUENCE {
        affirmedNetworkContextIpSubPoolStatusName String,
        affirmedNetworkContextIpSubPoolStatusUePool String,
        affirmedNetworkContextIpSubPoolStatusOperStatus INTEGER,
        affirmedNetworkContextIpSubPoolStatusIpSubPoolUtil String,
        affirmedNetworkContextIpSubPoolStatusIpSubPoolSize Unsigned32,
        affirmedNetworkContextIpSubPoolStatusCurrentAllocated Unsigned32,
        affirmedNetworkContextIpSubPoolStatusQuarantineQueueSize ConfdString,
        affirmedNetworkContextIpSubPoolStatusQuarantineOverrideCount ConfdString,
        affirmedNetworkContextIpSubPoolStatusSubPoolUnderModification INTEGER,
        affirmedNetworkContextIpSubPoolStatusSubpoolModificationSessionShrinkCount ConfdString,
        affirmedNetworkContextIpSubPoolStatusOperIpRangeStart String,
        affirmedNetworkContextIpSubPoolStatusOperIpRangeEnd String,
        affirmedNetworkContextIpSubPoolStatusOriginalIpRangeStart String,
        affirmedNetworkContextIpSubPoolStatusOriginalIpRangeEnd String,
        affirmedNetworkContextIpSubPoolStatusUserPlaneProfile String
    }

affirmedNetworkContextIpSubPoolStatusName OBJECT-TYPE
    SYNTAX      String
    MAX-ACCESS  not-accessible
    STATUS      current
    DESCRIPTION "IP subpool name"
    ::= { affirmedNetworkContextIpSubPoolStatusEntry 1 }

affirmedNetworkContextIpSubPoolStatusUePool OBJECT-TYPE
    SYNTAX      String
    MAX-ACCESS  read-only
    STATUS      current
    DESCRIPTION "UE Pool name"
    ::= { affirmedNetworkContextIpSubPoolStatusEntry 2 }

affirmedNetworkContextIpSubPoolStatusOperStatus OBJECT-TYPE
    SYNTAX      INTEGER {disabled(0),enabled(1),maintenance(2)}
    MAX-ACCESS  read-only
    STATUS      current
    DESCRIPTION "IP subpool operational status"
    ::= { affirmedNetworkContextIpSubPoolStatusEntry 3 }

affirmedNetworkContextIpSubPoolStatusIpSubPoolUtil OBJECT-TYPE
    SYNTAX      String
    MAX-ACCESS  read-only
    STATUS      current
    DESCRIPTION "IP subpool utilization percentage"
    ::= { affirmedNetworkContextIpSubPoolStatusEntry 4 }

affirmedNetworkContextIpSubPoolStatusIpSubPoolSize OBJECT-TYPE
    SYNTAX      Unsigned32
    MAX-ACCESS  read-only
    STATUS      current
    DESCRIPTION "Size of the IP range managed in this IP subpool"
    ::= { affirmedNetworkContextIpSubPoolStatusEntry 5 }

affirmedNetworkContextIpSubPoolStatusCurrentAllocated OBJECT-TYPE
    SYNTAX      Unsigned32
    MAX-ACCESS  read-only
    STATUS      current
    DESCRIPTION "Count of IPs in use in this IP subpool"
    ::= { affirmedNetworkContextIpSubPoolStatusEntry 6 }

affirmedNetworkContextIpSubPoolStatusQuarantineQueueSize OBJECT-TYPE
    SYNTAX      ConfdString
    MAX-ACCESS  read-only
    STATUS      current
    DESCRIPTION "Count of the IPs in quarantine in this IP subpool"
    ::= { affirmedNetworkContextIpSubPoolStatusEntry 7 }

affirmedNetworkContextIpSubPoolStatusQuarantineOverrideCount OBJECT-TYPE
    SYNTAX      ConfdString
    MAX-ACCESS  read-only
    STATUS      current
    DESCRIPTION "Count of the instances when quarantine queue override was employed for IP allocation"
    ::= { affirmedNetworkContextIpSubPoolStatusEntry 8 }

affirmedNetworkContextIpSubPoolStatusSubPoolUnderModification OBJECT-TYPE
    SYNTAX      INTEGER {false(0),true(1)}
    MAX-ACCESS  read-only
    STATUS      current
    DESCRIPTION "The state that indicates if the UE ip-sub-pool is currently undergoing modification"
    ::= { affirmedNetworkContextIpSubPoolStatusEntry 9 }

affirmedNetworkContextIpSubPoolStatusSubpoolModificationSessionShrinkCount OBJECT-TYPE
    SYNTAX      ConfdString
    MAX-ACCESS  read-only
    STATUS      current
    DESCRIPTION "The count indicating the number of sessions pending deletion in the deleted range of the IP sub-pool before the modification process can be completed."
    ::= { affirmedNetworkContextIpSubPoolStatusEntry 10 }

affirmedNetworkContextIpSubPoolStatusOperIpRangeStart OBJECT-TYPE
    SYNTAX      String
    MAX-ACCESS  read-only
    STATUS      current
    DESCRIPTION "Starting value of the operational IP address range for this sub pool"
    ::= { affirmedNetworkContextIpSubPoolStatusEntry 11 }

affirmedNetworkContextIpSubPoolStatusOperIpRangeEnd OBJECT-TYPE
    SYNTAX      String
    MAX-ACCESS  read-only
    STATUS      current
    DESCRIPTION "Ending value of the operational IP address range for this sub pool"
    ::= { affirmedNetworkContextIpSubPoolStatusEntry 12 }

affirmedNetworkContextIpSubPoolStatusOriginalIpRangeStart OBJECT-TYPE
    SYNTAX      String
    MAX-ACCESS  read-only
    STATUS      current
    DESCRIPTION "Starting value of the IP address range for this sub pool before the current range modification - valid only when a modification is in progress"
    ::= { affirmedNetworkContextIpSubPoolStatusEntry 13 }

affirmedNetworkContextIpSubPoolStatusOriginalIpRangeEnd OBJECT-TYPE
    SYNTAX      String
    MAX-ACCESS  read-only
    STATUS      current
    DESCRIPTION "Ending value of the IP address range for this sub pool before the current range modification  - valid only when a modification is in progress"
    ::= { affirmedNetworkContextIpSubPoolStatusEntry 14 }

affirmedNetworkContextIpSubPoolStatusUserPlaneProfile OBJECT-TYPE
    SYNTAX      String
    MAX-ACCESS  read-only
    STATUS      current
    DESCRIPTION "User Plane Profile name"
    ::= { affirmedNetworkContextIpSubPoolStatusEntry 15 }

affirmedNetworkContextUePoolStatusTable OBJECT-TYPE
    SYNTAX      SEQUENCE OF AffirmedNetworkContextUePoolStatusEntry
    MAX-ACCESS  not-accessible
    STATUS      current
    DESCRIPTION ""
    ::= { affirmedNetworkcontextMIB 12 }

affirmedNetworkContextUePoolStatusEntry OBJECT-TYPE
    SYNTAX      AffirmedNetworkContextUePoolStatusEntry
    MAX-ACCESS  not-accessible
    STATUS      current
    DESCRIPTION ""
    INDEX { affirmedNetworkContextName, affirmedNetworkContextUePoolStatusName }
        ::= { affirmedNetworkContextUePoolStatusTable 1 }

AffirmedNetworkContextUePoolStatusEntry ::=
    SEQUENCE {
        affirmedNetworkContextUePoolStatusName String,
        affirmedNetworkContextUePoolStatusOperStatus INTEGER,
        affirmedNetworkContextUePoolStatusUePoolAllocMode INTEGER,
        affirmedNetworkContextUePoolStatusNumIpSubPools Unsigned32,
        affirmedNetworkContextUePoolStatusNumIpv4SubPools Unsigned32,
        affirmedNetworkContextUePoolStatusNumIpv6SubPools Unsigned32,
        affirmedNetworkContextUePoolStatusQuarantineTimerValue Unsigned32,
        affirmedNetworkContextUePoolStatusIpv4SubPoolUtil String,
        affirmedNetworkContextUePoolStatusIpv4SubPoolsTotalCount ConfdString,
        affirmedNetworkContextUePoolStatusIpv4SubPoolsAllocCount ConfdString,
        affirmedNetworkContextUePoolStatusIpv4QuarantineQueueCount ConfdString,
        affirmedNetworkContextUePoolStatusIpv4QuarantineOverrideCount ConfdString,
        affirmedNetworkContextUePoolStatusIpv6SubPoolUtil String,
        affirmedNetworkContextUePoolStatusIpv6SubPoolsTotalCount ConfdString,
        affirmedNetworkContextUePoolStatusIpv6SubPoolsAllocCount ConfdString,
        affirmedNetworkContextUePoolStatusIpv6QuarantineQueueCount ConfdString,
        affirmedNetworkContextUePoolStatusIpv6QuarantineOverrideCount ConfdString
    }

affirmedNetworkContextUePoolStatusName OBJECT-TYPE
    SYNTAX      String
    MAX-ACCESS  not-accessible
    STATUS      current
    DESCRIPTION "UE Pool name"
    ::= { affirmedNetworkContextUePoolStatusEntry 1 }

affirmedNetworkContextUePoolStatusOperStatus OBJECT-TYPE
    SYNTAX      INTEGER {disabled(0),enabled(1),maintenance(2)}
    MAX-ACCESS  read-only
    STATUS      current
    DESCRIPTION "UE Pool operational status"
    ::= { affirmedNetworkContextUePoolStatusEntry 2 }

affirmedNetworkContextUePoolStatusUePoolAllocMode OBJECT-TYPE
    SYNTAX      INTEGER {local-allocation(1),remote-allocation(2)}
    MAX-ACCESS  read-only
    STATUS      current
    DESCRIPTION "UE Pool allocation mode"
    ::= { affirmedNetworkContextUePoolStatusEntry 3 }

affirmedNetworkContextUePoolStatusNumIpSubPools OBJECT-TYPE
    SYNTAX      Unsigned32
    MAX-ACCESS  read-only
    STATUS      current
    DESCRIPTION "Total number of IP subpools associated with this UE Pool"
    ::= { affirmedNetworkContextUePoolStatusEntry 4 }

affirmedNetworkContextUePoolStatusNumIpv4SubPools OBJECT-TYPE
    SYNTAX      Unsigned32
    MAX-ACCESS  read-only
    STATUS      current
    DESCRIPTION "Total number of Ipv4 subpools associated with this UE Pool"
    ::= { affirmedNetworkContextUePoolStatusEntry 5 }

affirmedNetworkContextUePoolStatusNumIpv6SubPools OBJECT-TYPE
    SYNTAX      Unsigned32
    MAX-ACCESS  read-only
    STATUS      current
    DESCRIPTION "Total number of Ipv6 subpools associated with this UE Pool"
    ::= { affirmedNetworkContextUePoolStatusEntry 6 }

affirmedNetworkContextUePoolStatusQuarantineTimerValue OBJECT-TYPE
    SYNTAX      Unsigned32
    MAX-ACCESS  read-only
    STATUS      current
    DESCRIPTION "Quarantine timer value"
    ::= { affirmedNetworkContextUePoolStatusEntry 7 }

affirmedNetworkContextUePoolStatusIpv4SubPoolUtil OBJECT-TYPE
    SYNTAX      String
    MAX-ACCESS  read-only
    STATUS      current
    DESCRIPTION "IPv4 subpool utilization percentage for this UE Pool"
    ::= { affirmedNetworkContextUePoolStatusEntry 8 }

affirmedNetworkContextUePoolStatusIpv4SubPoolsTotalCount OBJECT-TYPE
    SYNTAX      ConfdString
    MAX-ACCESS  read-only
    STATUS      current
    DESCRIPTION "Count of the IPs configured in all the IPv4 subpools belonging to this UE Pool"
    ::= { affirmedNetworkContextUePoolStatusEntry 9 }

affirmedNetworkContextUePoolStatusIpv4SubPoolsAllocCount OBJECT-TYPE
    SYNTAX      ConfdString
    MAX-ACCESS  read-only
    STATUS      current
    DESCRIPTION "Count of the IPs in use in all the IPv4 subpools belonging to this UE Pool"
    ::= { affirmedNetworkContextUePoolStatusEntry 10 }

affirmedNetworkContextUePoolStatusIpv4QuarantineQueueCount OBJECT-TYPE
    SYNTAX      ConfdString
    MAX-ACCESS  read-only
    STATUS      current
    DESCRIPTION "Count of IPs belong to IPv4 subpools that are in quarantine"
    ::= { affirmedNetworkContextUePoolStatusEntry 11 }

affirmedNetworkContextUePoolStatusIpv4QuarantineOverrideCount OBJECT-TYPE
    SYNTAX      ConfdString
    MAX-ACCESS  read-only
    STATUS      current
    DESCRIPTION "IPv4 subpool quarantine override count"
    ::= { affirmedNetworkContextUePoolStatusEntry 12 }

affirmedNetworkContextUePoolStatusIpv6SubPoolUtil OBJECT-TYPE
    SYNTAX      String
    MAX-ACCESS  read-only
    STATUS      current
    DESCRIPTION "IPv6 subpool utilization percentage for this UE Pool"
    ::= { affirmedNetworkContextUePoolStatusEntry 13 }

affirmedNetworkContextUePoolStatusIpv6SubPoolsTotalCount OBJECT-TYPE
    SYNTAX      ConfdString
    MAX-ACCESS  read-only
    STATUS      current
    DESCRIPTION "Count of the IPs configured in all the IPv6 subpools belonging to this UE Pool"
    ::= { affirmedNetworkContextUePoolStatusEntry 14 }

affirmedNetworkContextUePoolStatusIpv6SubPoolsAllocCount OBJECT-TYPE
    SYNTAX      ConfdString
    MAX-ACCESS  read-only
    STATUS      current
    DESCRIPTION "Count of the IPs in use in all the IPv6 subpools belonging to this UE Pool"
    ::= { affirmedNetworkContextUePoolStatusEntry 15 }

affirmedNetworkContextUePoolStatusIpv6QuarantineQueueCount OBJECT-TYPE
    SYNTAX      ConfdString
    MAX-ACCESS  read-only
    STATUS      current
    DESCRIPTION "Count of IPs belong to IPv6 subpools that are in quarantine"
    ::= { affirmedNetworkContextUePoolStatusEntry 16 }

affirmedNetworkContextUePoolStatusIpv6QuarantineOverrideCount OBJECT-TYPE
    SYNTAX      ConfdString
    MAX-ACCESS  read-only
    STATUS      current
    DESCRIPTION "IPv6 subpool quarantine override count"
    ::= { affirmedNetworkContextUePoolStatusEntry 17 }

affirmedNetworkContextApnStatusTable OBJECT-TYPE
    SYNTAX      SEQUENCE OF AffirmedNetworkContextApnStatusEntry
    MAX-ACCESS  not-accessible
    STATUS      current
    DESCRIPTION ""
    ::= { affirmedNetworkcontextMIB 13 }

affirmedNetworkContextApnStatusEntry OBJECT-TYPE
    SYNTAX      AffirmedNetworkContextApnStatusEntry
    MAX-ACCESS  not-accessible
    STATUS      current
    DESCRIPTION ""
    INDEX { affirmedNetworkContextName, affirmedNetworkContextApnStatusApnName }
        ::= { affirmedNetworkContextApnStatusTable 1 }

AffirmedNetworkContextApnStatusEntry ::=
    SEQUENCE {
        affirmedNetworkContextApnStatusApnName String,
        affirmedNetworkContextApnStatusNumUePools Unsigned32,
        affirmedNetworkContextApnStatusUePoolNames String,
        affirmedNetworkContextApnStatusNumLocalUePools Unsigned32,
        affirmedNetworkContextApnStatusNumRemoteUePools Unsigned32,
        affirmedNetworkContextApnStatusNumLocalAllocSuccess ConfdString,
        affirmedNetworkContextApnStatusNumLocalAllocFailure ConfdString,
        affirmedNetworkContextApnStatusNumRemoteReserveSuccess ConfdString,
        affirmedNetworkContextApnStatusNumRemoteReserveFailure ConfdString,
        affirmedNetworkContextApnStatusNumLocalAllocFromSubPoolSuccess ConfdString,
        affirmedNetworkContextApnStatusNumLocalAllocFromSubPoolFailure ConfdString,
        affirmedNetworkContextApnStatusNumRemoteAllocSuccess ConfdString,
        affirmedNetworkContextApnStatusNumRemoteAllocFailure ConfdString,
        affirmedNetworkContextApnStatusNumRemoteAllocFromSubPoolSuccess ConfdString,
        affirmedNetworkContextApnStatusNumRemoteAllocFromSubPoolFailure ConfdString,
        affirmedNetworkContextApnStatusNumLocalIPv4AllocSuccess ConfdString,
        affirmedNetworkContextApnStatusNumLocalIPv4AllocFailure ConfdString,
        affirmedNetworkContextApnStatusNumLocalIPv6AllocSuccess ConfdString,
        affirmedNetworkContextApnStatusNumLocalIPv6AllocFailure ConfdString,
        affirmedNetworkContextApnStatusNumRemoteIPv4ReserveSuccess ConfdString,
        affirmedNetworkContextApnStatusNumRemoteIPv4ReserveFailure ConfdString,
        affirmedNetworkContextApnStatusNumRemoteIPv6ReserveSuccess ConfdString,
        affirmedNetworkContextApnStatusNumRemoteIPv6ReserveFailure ConfdString,
        affirmedNetworkContextApnStatusNumRemoteIPv4AllocSuccess ConfdString,
        affirmedNetworkContextApnStatusNumRemoteIPv4AllocFailure ConfdString,
        affirmedNetworkContextApnStatusNumRemoteIPv6AllocSuccess ConfdString,
        affirmedNetworkContextApnStatusNumRemoteIPv6AllocFailure ConfdString,
        affirmedNetworkContextApnStatusNumRemoteDelegatedIPv6ReserveSuccess ConfdString,
        affirmedNetworkContextApnStatusNumRemoteDelegatedIPv6ReserveFailure ConfdString,
        affirmedNetworkContextApnStatusNumLocalDelegatedIPv6AllocSuccess ConfdString,
        affirmedNetworkContextApnStatusNumLocalDelegatedIPv6AllocFailure ConfdString
    }

affirmedNetworkContextApnStatusApnName OBJECT-TYPE
    SYNTAX      String
    MAX-ACCESS  not-accessible
    STATUS      current
    DESCRIPTION "APN name"
    ::= { affirmedNetworkContextApnStatusEntry 1 }

affirmedNetworkContextApnStatusNumUePools OBJECT-TYPE
    SYNTAX      Unsigned32
    MAX-ACCESS  read-only
    STATUS      current
    DESCRIPTION "Number of associated UE Pools"
    ::= { affirmedNetworkContextApnStatusEntry 2 }

affirmedNetworkContextApnStatusUePoolNames OBJECT-TYPE
    SYNTAX      String
    MAX-ACCESS  read-only
    STATUS      current
    DESCRIPTION "Associated UE Pool names"
    ::= { affirmedNetworkContextApnStatusEntry 3 }

affirmedNetworkContextApnStatusNumLocalUePools OBJECT-TYPE
    SYNTAX      Unsigned32
    MAX-ACCESS  read-only
    STATUS      current
    DESCRIPTION "Number of associated local UE Pools"
    ::= { affirmedNetworkContextApnStatusEntry 4 }

affirmedNetworkContextApnStatusNumRemoteUePools OBJECT-TYPE
    SYNTAX      Unsigned32
    MAX-ACCESS  read-only
    STATUS      current
    DESCRIPTION "Number of associated remote UE Pools"
    ::= { affirmedNetworkContextApnStatusEntry 5 }

affirmedNetworkContextApnStatusNumLocalAllocSuccess OBJECT-TYPE
    SYNTAX      ConfdString
    MAX-ACCESS  read-only
    STATUS      deprecated
    DESCRIPTION "Count of local IP allocation successess"
    ::= { affirmedNetworkContextApnStatusEntry 6 }

affirmedNetworkContextApnStatusNumLocalAllocFailure OBJECT-TYPE
    SYNTAX      ConfdString
    MAX-ACCESS  read-only
    STATUS      deprecated
    DESCRIPTION "Count of local IP allocation failures"
    ::= { affirmedNetworkContextApnStatusEntry 7 }

affirmedNetworkContextApnStatusNumRemoteReserveSuccess OBJECT-TYPE
    SYNTAX      ConfdString
    MAX-ACCESS  read-only
    STATUS      deprecated
    DESCRIPTION "Count of remote IP reservation successess"
    ::= { affirmedNetworkContextApnStatusEntry 8 }

affirmedNetworkContextApnStatusNumRemoteReserveFailure OBJECT-TYPE
    SYNTAX      ConfdString
    MAX-ACCESS  read-only
    STATUS      deprecated
    DESCRIPTION "Count of remote IP reservation failures"
    ::= { affirmedNetworkContextApnStatusEntry 9 }

affirmedNetworkContextApnStatusNumLocalAllocFromSubPoolSuccess OBJECT-TYPE
    SYNTAX      ConfdString
    MAX-ACCESS  read-only
    STATUS      current
    DESCRIPTION "Count of local IP allocation from subpool successess"
    ::= { affirmedNetworkContextApnStatusEntry 10 }

affirmedNetworkContextApnStatusNumLocalAllocFromSubPoolFailure OBJECT-TYPE
    SYNTAX      ConfdString
    MAX-ACCESS  read-only
    STATUS      current
    DESCRIPTION "Count of local IP allocation from subpool failures"
    ::= { affirmedNetworkContextApnStatusEntry 11 }

affirmedNetworkContextApnStatusNumRemoteAllocSuccess OBJECT-TYPE
    SYNTAX      ConfdString
    MAX-ACCESS  read-only
    STATUS      deprecated
    DESCRIPTION "Count of remote IP allocation successess"
    ::= { affirmedNetworkContextApnStatusEntry 12 }

affirmedNetworkContextApnStatusNumRemoteAllocFailure OBJECT-TYPE
    SYNTAX      ConfdString
    MAX-ACCESS  read-only
    STATUS      deprecated
    DESCRIPTION "Count of remote IP allocation failures"
    ::= { affirmedNetworkContextApnStatusEntry 13 }

affirmedNetworkContextApnStatusNumRemoteAllocFromSubPoolSuccess OBJECT-TYPE
    SYNTAX      ConfdString
    MAX-ACCESS  read-only
    STATUS      current
    DESCRIPTION "Count of remote IP allocation from subpool successess"
    ::= { affirmedNetworkContextApnStatusEntry 14 }

affirmedNetworkContextApnStatusNumRemoteAllocFromSubPoolFailure OBJECT-TYPE
    SYNTAX      ConfdString
    MAX-ACCESS  read-only
    STATUS      current
    DESCRIPTION "Count of remote IP allocation from subpool failures"
    ::= { affirmedNetworkContextApnStatusEntry 15 }

affirmedNetworkContextApnStatusNumLocalIPv4AllocSuccess OBJECT-TYPE
    SYNTAX      ConfdString
    MAX-ACCESS  read-only
    STATUS      current
    DESCRIPTION "Count of local IPv4 allocation successess"
    ::= { affirmedNetworkContextApnStatusEntry 16 }

affirmedNetworkContextApnStatusNumLocalIPv4AllocFailure OBJECT-TYPE
    SYNTAX      ConfdString
    MAX-ACCESS  read-only
    STATUS      current
    DESCRIPTION "Count of local IPv4 allocation failures"
    ::= { affirmedNetworkContextApnStatusEntry 17 }

affirmedNetworkContextApnStatusNumLocalIPv6AllocSuccess OBJECT-TYPE
    SYNTAX      ConfdString
    MAX-ACCESS  read-only
    STATUS      current
    DESCRIPTION "Count of local IPv6 allocation successess"
    ::= { affirmedNetworkContextApnStatusEntry 18 }

affirmedNetworkContextApnStatusNumLocalIPv6AllocFailure OBJECT-TYPE
    SYNTAX      ConfdString
    MAX-ACCESS  read-only
    STATUS      current
    DESCRIPTION "Count of local IPv6 allocation failures"
    ::= { affirmedNetworkContextApnStatusEntry 19 }

affirmedNetworkContextApnStatusNumRemoteIPv4ReserveSuccess OBJECT-TYPE
    SYNTAX      ConfdString
    MAX-ACCESS  read-only
    STATUS      current
    DESCRIPTION "Count of remote IPv4 reservation successess"
    ::= { affirmedNetworkContextApnStatusEntry 20 }

affirmedNetworkContextApnStatusNumRemoteIPv4ReserveFailure OBJECT-TYPE
    SYNTAX      ConfdString
    MAX-ACCESS  read-only
    STATUS      current
    DESCRIPTION "Count of remote IPv4 reservation failures"
    ::= { affirmedNetworkContextApnStatusEntry 21 }

affirmedNetworkContextApnStatusNumRemoteIPv6ReserveSuccess OBJECT-TYPE
    SYNTAX      ConfdString
    MAX-ACCESS  read-only
    STATUS      current
    DESCRIPTION "Count of remote IPv6 reservation successess"
    ::= { affirmedNetworkContextApnStatusEntry 22 }

affirmedNetworkContextApnStatusNumRemoteIPv6ReserveFailure OBJECT-TYPE
    SYNTAX      ConfdString
    MAX-ACCESS  read-only
    STATUS      current
    DESCRIPTION "Count of remote IPv6 reservation failures"
    ::= { affirmedNetworkContextApnStatusEntry 23 }

affirmedNetworkContextApnStatusNumRemoteIPv4AllocSuccess OBJECT-TYPE
    SYNTAX      ConfdString
    MAX-ACCESS  read-only
    STATUS      current
    DESCRIPTION "Count of remote IPv4 allocation successess"
    ::= { affirmedNetworkContextApnStatusEntry 24 }

affirmedNetworkContextApnStatusNumRemoteIPv4AllocFailure OBJECT-TYPE
    SYNTAX      ConfdString
    MAX-ACCESS  read-only
    STATUS      current
    DESCRIPTION "Count of remote IPv4 allocation failures"
    ::= { affirmedNetworkContextApnStatusEntry 25 }

affirmedNetworkContextApnStatusNumRemoteIPv6AllocSuccess OBJECT-TYPE
    SYNTAX      ConfdString
    MAX-ACCESS  read-only
    STATUS      current
    DESCRIPTION "Count of remote IPv6 allocation successess"
    ::= { affirmedNetworkContextApnStatusEntry 26 }

affirmedNetworkContextApnStatusNumRemoteIPv6AllocFailure OBJECT-TYPE
    SYNTAX      ConfdString
    MAX-ACCESS  read-only
    STATUS      current
    DESCRIPTION "Count of remote IPv6 allocation failures"
    ::= { affirmedNetworkContextApnStatusEntry 27 }

affirmedNetworkContextApnStatusNumRemoteDelegatedIPv6ReserveSuccess OBJECT-TYPE
    SYNTAX      ConfdString
    MAX-ACCESS  read-only
    STATUS      current
    DESCRIPTION "Count of remote delegated IPv6 reservation successess"
    ::= { affirmedNetworkContextApnStatusEntry 28 }

affirmedNetworkContextApnStatusNumRemoteDelegatedIPv6ReserveFailure OBJECT-TYPE
    SYNTAX      ConfdString
    MAX-ACCESS  read-only
    STATUS      current
    DESCRIPTION "Count of remote delegated IPv6 reservation failures"
    ::= { affirmedNetworkContextApnStatusEntry 29 }

affirmedNetworkContextApnStatusNumLocalDelegatedIPv6AllocSuccess OBJECT-TYPE
    SYNTAX      ConfdString
    MAX-ACCESS  read-only
    STATUS      current
    DESCRIPTION "Count of local delegated IPv6 allocation successess"
    ::= { affirmedNetworkContextApnStatusEntry 30 }

affirmedNetworkContextApnStatusNumLocalDelegatedIPv6AllocFailure OBJECT-TYPE
    SYNTAX      ConfdString
    MAX-ACCESS  read-only
    STATUS      current
    DESCRIPTION "Count of local delegated IPv6 allocation failures"
    ::= { affirmedNetworkContextApnStatusEntry 31 }

affirmedNetworkContextUeIpSubPoolStatisticsTable OBJECT-TYPE
    SYNTAX      SEQUENCE OF AffirmedNetworkContextUeIpSubPoolStatisticsEntry
    MAX-ACCESS  not-accessible
    STATUS      current
    DESCRIPTION ""
    ::= { affirmedNetworkcontextMIB 14 }

affirmedNetworkContextUeIpSubPoolStatisticsEntry OBJECT-TYPE
    SYNTAX      AffirmedNetworkContextUeIpSubPoolStatisticsEntry
    MAX-ACCESS  not-accessible
    STATUS      current
    DESCRIPTION ""
    INDEX { affirmedNetworkContextName, affirmedNetworkContextUeIpSubPoolStatisticsName }
        ::= { affirmedNetworkContextUeIpSubPoolStatisticsTable 1 }

AffirmedNetworkContextUeIpSubPoolStatisticsEntry ::=
    SEQUENCE {
        affirmedNetworkContextUeIpSubPoolStatisticsName String,
        affirmedNetworkContextUeIpSubPoolStatisticsCurrentAllocCount ConfdString,
        affirmedNetworkContextUeIpSubPoolStatisticsCurrentFreeCount ConfdString,
        affirmedNetworkContextUeIpSubPoolStatisticsNumQuarantineQueueCount ConfdString,
        affirmedNetworkContextUeIpSubPoolStatisticsIpSubPoolUtil ConfdString,
        affirmedNetworkContextUeIpSubPoolStatisticsNumAllocSuccess ConfdString,
        affirmedNetworkContextUeIpSubPoolStatisticsNumAllocFailure ConfdString,
        affirmedNetworkContextUeIpSubPoolStatisticsNumReserveSuccess ConfdString,
        affirmedNetworkContextUeIpSubPoolStatisticsNumReserveFailure ConfdString,
        affirmedNetworkContextUeIpSubPoolStatisticsNumReleaseSuccess ConfdString,
        affirmedNetworkContextUeIpSubPoolStatisticsNumReleaseFailure ConfdString,
        affirmedNetworkContextUeIpSubPoolStatisticsNumQuarantineSuccess ConfdString,
        affirmedNetworkContextUeIpSubPoolStatisticsNumQuarantineFailure ConfdString,
        affirmedNetworkContextUeIpSubPoolStatisticsNumQuarantineRelSuccess ConfdString,
        affirmedNetworkContextUeIpSubPoolStatisticsNumQuarantineRelFailure ConfdString,
        affirmedNetworkContextUeIpSubPoolStatisticsNumQuarantineOverrideCount ConfdString,
        affirmedNetworkContextUeIpSubPoolStatisticsNumQuarantineOverrideTokRelCount ConfdString,
        affirmedNetworkContextUeIpSubPoolStatisticsNumReleaseFailureIpOutOfRange ConfdString,
        affirmedNetworkContextUeIpSubPoolStatisticsNumReleaseFailureNoBindRec ConfdString,
        affirmedNetworkContextUeIpSubPoolStatisticsNumReleaseFailureInvalidBindRec ConfdString,
        affirmedNetworkContextUeIpSubPoolStatisticsNumReleaseFailureSessIdMismatch ConfdString
    }

affirmedNetworkContextUeIpSubPoolStatisticsName OBJECT-TYPE
    SYNTAX      String
    MAX-ACCESS  not-accessible
    STATUS      current
    DESCRIPTION "Ip SubPool Name"
    ::= { affirmedNetworkContextUeIpSubPoolStatisticsEntry 1 }

affirmedNetworkContextUeIpSubPoolStatisticsCurrentAllocCount OBJECT-TYPE
    SYNTAX      ConfdString
    MAX-ACCESS  read-only
    STATUS      current
    DESCRIPTION "Count of IPs in use on this sub pool"
    ::= { affirmedNetworkContextUeIpSubPoolStatisticsEntry 2 }

affirmedNetworkContextUeIpSubPoolStatisticsCurrentFreeCount OBJECT-TYPE
    SYNTAX      ConfdString
    MAX-ACCESS  read-only
    STATUS      current
    DESCRIPTION "Current IP free count"
    ::= { affirmedNetworkContextUeIpSubPoolStatisticsEntry 3 }

affirmedNetworkContextUeIpSubPoolStatisticsNumQuarantineQueueCount OBJECT-TYPE
    SYNTAX      ConfdString
    MAX-ACCESS  read-only
    STATUS      current
    DESCRIPTION "Current IPs in quarantine count"
    ::= { affirmedNetworkContextUeIpSubPoolStatisticsEntry 4 }

affirmedNetworkContextUeIpSubPoolStatisticsIpSubPoolUtil OBJECT-TYPE
    SYNTAX      ConfdString
    MAX-ACCESS  read-only
    STATUS      current
    DESCRIPTION "IP subpool utilization percentage"
    ::= { affirmedNetworkContextUeIpSubPoolStatisticsEntry 5 }

affirmedNetworkContextUeIpSubPoolStatisticsNumAllocSuccess OBJECT-TYPE
    SYNTAX      ConfdString
    MAX-ACCESS  read-only
    STATUS      current
    DESCRIPTION "Total successful IP allocation count"
    ::= { affirmedNetworkContextUeIpSubPoolStatisticsEntry 6 }

affirmedNetworkContextUeIpSubPoolStatisticsNumAllocFailure OBJECT-TYPE
    SYNTAX      ConfdString
    MAX-ACCESS  read-only
    STATUS      current
    DESCRIPTION "Total failed IP allocation count"
    ::= { affirmedNetworkContextUeIpSubPoolStatisticsEntry 7 }

affirmedNetworkContextUeIpSubPoolStatisticsNumReserveSuccess OBJECT-TYPE
    SYNTAX      ConfdString
    MAX-ACCESS  read-only
    STATUS      current
    DESCRIPTION "Total successful IP reservation count"
    ::= { affirmedNetworkContextUeIpSubPoolStatisticsEntry 8 }

affirmedNetworkContextUeIpSubPoolStatisticsNumReserveFailure OBJECT-TYPE
    SYNTAX      ConfdString
    MAX-ACCESS  read-only
    STATUS      current
    DESCRIPTION "Total failed IP reservation count"
    ::= { affirmedNetworkContextUeIpSubPoolStatisticsEntry 9 }

affirmedNetworkContextUeIpSubPoolStatisticsNumReleaseSuccess OBJECT-TYPE
    SYNTAX      ConfdString
    MAX-ACCESS  read-only
    STATUS      current
    DESCRIPTION "Total successful IP release count"
    ::= { affirmedNetworkContextUeIpSubPoolStatisticsEntry 10 }

affirmedNetworkContextUeIpSubPoolStatisticsNumReleaseFailure OBJECT-TYPE
    SYNTAX      ConfdString
    MAX-ACCESS  read-only
    STATUS      current
    DESCRIPTION "Total failed IP release count"
    ::= { affirmedNetworkContextUeIpSubPoolStatisticsEntry 11 }

affirmedNetworkContextUeIpSubPoolStatisticsNumQuarantineSuccess OBJECT-TYPE
    SYNTAX      ConfdString
    MAX-ACCESS  read-only
    STATUS      current
    DESCRIPTION "Total successful IP quarantine count"
    ::= { affirmedNetworkContextUeIpSubPoolStatisticsEntry 12 }

affirmedNetworkContextUeIpSubPoolStatisticsNumQuarantineFailure OBJECT-TYPE
    SYNTAX      ConfdString
    MAX-ACCESS  read-only
    STATUS      current
    DESCRIPTION "Total failed IP quarantine failure"
    ::= { affirmedNetworkContextUeIpSubPoolStatisticsEntry 13 }

affirmedNetworkContextUeIpSubPoolStatisticsNumQuarantineRelSuccess OBJECT-TYPE
    SYNTAX      ConfdString
    MAX-ACCESS  read-only
    STATUS      current
    DESCRIPTION "Total successful IP quarantine release count"
    ::= { affirmedNetworkContextUeIpSubPoolStatisticsEntry 14 }

affirmedNetworkContextUeIpSubPoolStatisticsNumQuarantineRelFailure OBJECT-TYPE
    SYNTAX      ConfdString
    MAX-ACCESS  read-only
    STATUS      current
    DESCRIPTION "Total failed IP quarantine release count"
    ::= { affirmedNetworkContextUeIpSubPoolStatisticsEntry 15 }

affirmedNetworkContextUeIpSubPoolStatisticsNumQuarantineOverrideCount OBJECT-TYPE
    SYNTAX      ConfdString
    MAX-ACCESS  read-only
    STATUS      current
    DESCRIPTION "Total quarantine override count"
    ::= { affirmedNetworkContextUeIpSubPoolStatisticsEntry 16 }

affirmedNetworkContextUeIpSubPoolStatisticsNumQuarantineOverrideTokRelCount OBJECT-TYPE
    SYNTAX      ConfdString
    MAX-ACCESS  read-only
    STATUS      current
    DESCRIPTION "Total quarantine override IP release count"
    ::= { affirmedNetworkContextUeIpSubPoolStatisticsEntry 17 }

affirmedNetworkContextUeIpSubPoolStatisticsNumReleaseFailureIpOutOfRange OBJECT-TYPE
    SYNTAX      ConfdString
    MAX-ACCESS  read-only
    STATUS      current
    DESCRIPTION "Total failed IP release count - IP out of range"
    ::= { affirmedNetworkContextUeIpSubPoolStatisticsEntry 18 }

affirmedNetworkContextUeIpSubPoolStatisticsNumReleaseFailureNoBindRec OBJECT-TYPE
    SYNTAX      ConfdString
    MAX-ACCESS  read-only
    STATUS      current
    DESCRIPTION "Total failed IP release count - no IP binding record"
    ::= { affirmedNetworkContextUeIpSubPoolStatisticsEntry 19 }

affirmedNetworkContextUeIpSubPoolStatisticsNumReleaseFailureInvalidBindRec OBJECT-TYPE
    SYNTAX      ConfdString
    MAX-ACCESS  read-only
    STATUS      current
    DESCRIPTION "Total failed IP release count - invalid IP binding record"
    ::= { affirmedNetworkContextUeIpSubPoolStatisticsEntry 20 }

affirmedNetworkContextUeIpSubPoolStatisticsNumReleaseFailureSessIdMismatch OBJECT-TYPE
    SYNTAX      ConfdString
    MAX-ACCESS  read-only
    STATUS      current
    DESCRIPTION "Total failed IP release count - PDN session ID mismatch"
    ::= { affirmedNetworkContextUeIpSubPoolStatisticsEntry 21 }

affirmedNetworkContextUeIpPdnSessionRecordTable OBJECT-TYPE
    SYNTAX      SEQUENCE OF AffirmedNetworkContextUeIpPdnSessionRecordEntry
    MAX-ACCESS  not-accessible
    STATUS      current
    DESCRIPTION ""
    ::= { affirmedNetworkcontextMIB 15 }

affirmedNetworkContextUeIpPdnSessionRecordEntry OBJECT-TYPE
    SYNTAX      AffirmedNetworkContextUeIpPdnSessionRecordEntry
    MAX-ACCESS  not-accessible
    STATUS      current
    DESCRIPTION ""
    INDEX { affirmedNetworkContextName, affirmedNetworkContextUeIpPdnSessionRecordUeIp }
        ::= { affirmedNetworkContextUeIpPdnSessionRecordTable 1 }

AffirmedNetworkContextUeIpPdnSessionRecordEntry ::=
    SEQUENCE {
        affirmedNetworkContextUeIpPdnSessionRecordUeIp String,
        affirmedNetworkContextUeIpPdnSessionRecordUePoolName String,
        affirmedNetworkContextUeIpPdnSessionRecordIpSubPoolName String,
        affirmedNetworkContextUeIpPdnSessionRecordUeIpBindState INTEGER,
        affirmedNetworkContextUeIpPdnSessionRecordPdnSessionIpAllocationType INTEGER,
        affirmedNetworkContextUeIpPdnSessionRecordPdnSessionId Unsigned32,
        affirmedNetworkContextUeIpPdnSessionRecordImsi ConfdString,
        affirmedNetworkContextUeIpPdnSessionRecordGwName String,
        affirmedNetworkContextUeIpPdnSessionRecordApnName String,
        affirmedNetworkContextUeIpPdnSessionRecordOtherUeIp String,
        affirmedNetworkContextUeIpPdnSessionRecordOtherUePoolName String,
        affirmedNetworkContextUeIpPdnSessionRecordOtherIpSubPoolName String,
        affirmedNetworkContextUeIpPdnSessionRecordOtherIpInShrinkRange INTEGER
    }

affirmedNetworkContextUeIpPdnSessionRecordUeIp OBJECT-TYPE
    SYNTAX      String
    MAX-ACCESS  not-accessible
    STATUS      current
    DESCRIPTION "IP belonging to a UE IP sub pool in this network context"
    ::= { affirmedNetworkContextUeIpPdnSessionRecordEntry 1 }

affirmedNetworkContextUeIpPdnSessionRecordUePoolName OBJECT-TYPE
    SYNTAX      String
    MAX-ACCESS  read-only
    STATUS      current
    DESCRIPTION "UE Pool associated with this UE IP"
    ::= { affirmedNetworkContextUeIpPdnSessionRecordEntry 2 }

affirmedNetworkContextUeIpPdnSessionRecordIpSubPoolName OBJECT-TYPE
    SYNTAX      String
    MAX-ACCESS  read-only
    STATUS      current
    DESCRIPTION "IP subpool associated with this UE IP"
    ::= { affirmedNetworkContextUeIpPdnSessionRecordEntry 3 }

affirmedNetworkContextUeIpPdnSessionRecordUeIpBindState OBJECT-TYPE
    SYNTAX      INTEGER {ip-state-available(0),ip-state-in-use(1),ip-state-in-quarantine(2),ip-state-not-configured(3),ip-state-not-available(4),ip-state-in-shrink-list(5)}
    MAX-ACCESS  read-only
    STATUS      current
    DESCRIPTION "IP state"
    ::= { affirmedNetworkContextUeIpPdnSessionRecordEntry 4 }

affirmedNetworkContextUeIpPdnSessionRecordPdnSessionIpAllocationType OBJECT-TYPE
    SYNTAX      INTEGER {ip-allocation-type-v4(0),ip-allocation-type-v6(1),ip-allocation-type-v4v6(2)}
    MAX-ACCESS  read-only
    STATUS      current
    DESCRIPTION "The type of UE IP address (V4, V6 or V4V6) assigned to this PDN session"
    ::= { affirmedNetworkContextUeIpPdnSessionRecordEntry 5 }

affirmedNetworkContextUeIpPdnSessionRecordPdnSessionId OBJECT-TYPE
    SYNTAX      Unsigned32
    MAX-ACCESS  read-only
    STATUS      current
    DESCRIPTION "PDN Session ID"
    ::= { affirmedNetworkContextUeIpPdnSessionRecordEntry 6 }

affirmedNetworkContextUeIpPdnSessionRecordImsi OBJECT-TYPE
    SYNTAX      ConfdString
    MAX-ACCESS  read-only
    STATUS      current
    DESCRIPTION "IMSI"
    ::= { affirmedNetworkContextUeIpPdnSessionRecordEntry 7 }

affirmedNetworkContextUeIpPdnSessionRecordGwName OBJECT-TYPE
    SYNTAX      String
    MAX-ACCESS  read-only
    STATUS      current
    DESCRIPTION "Gateway name"
    ::= { affirmedNetworkContextUeIpPdnSessionRecordEntry 8 }

affirmedNetworkContextUeIpPdnSessionRecordApnName OBJECT-TYPE
    SYNTAX      String
    MAX-ACCESS  read-only
    STATUS      current
    DESCRIPTION "APN name"
    ::= { affirmedNetworkContextUeIpPdnSessionRecordEntry 9 }

affirmedNetworkContextUeIpPdnSessionRecordOtherUeIp OBJECT-TYPE
    SYNTAX      String
    MAX-ACCESS  read-only
    STATUS      current
    DESCRIPTION "The other IP that ahs been assigned to this PDN session"
    ::= { affirmedNetworkContextUeIpPdnSessionRecordEntry 10 }

affirmedNetworkContextUeIpPdnSessionRecordOtherUePoolName OBJECT-TYPE
    SYNTAX      String
    MAX-ACCESS  read-only
    STATUS      current
    DESCRIPTION "UE Pool associated with the other IP address assigned to this PDN session"
    ::= { affirmedNetworkContextUeIpPdnSessionRecordEntry 11 }

affirmedNetworkContextUeIpPdnSessionRecordOtherIpSubPoolName OBJECT-TYPE
    SYNTAX      String
    MAX-ACCESS  read-only
    STATUS      current
    DESCRIPTION "IP subpool associated with the other IP address assigned to this PDN session"
    ::= { affirmedNetworkContextUeIpPdnSessionRecordEntry 12 }

affirmedNetworkContextUeIpPdnSessionRecordOtherIpInShrinkRange OBJECT-TYPE
    SYNTAX      INTEGER {false(0),true(1)}
    MAX-ACCESS  read-only
    STATUS      current
    DESCRIPTION "The other IP assigned is not in the operational range of the subpool"
    ::= { affirmedNetworkContextUeIpPdnSessionRecordEntry 13 }

affirmedNetworkContextUePoolStatisticsTable OBJECT-TYPE
    SYNTAX      SEQUENCE OF AffirmedNetworkContextUePoolStatisticsEntry
    MAX-ACCESS  not-accessible
    STATUS      current
    DESCRIPTION ""
    ::= { affirmedNetworkcontextMIB 16 }

affirmedNetworkContextUePoolStatisticsEntry OBJECT-TYPE
    SYNTAX      AffirmedNetworkContextUePoolStatisticsEntry
    MAX-ACCESS  not-accessible
    STATUS      current
    DESCRIPTION ""
    INDEX { affirmedNetworkContextName, affirmedNetworkContextUePoolStatisticsName }
        ::= { affirmedNetworkContextUePoolStatisticsTable 1 }

AffirmedNetworkContextUePoolStatisticsEntry ::=
    SEQUENCE {
        affirmedNetworkContextUePoolStatisticsName String,
        affirmedNetworkContextUePoolStatisticsNumIpv4SubPools Unsigned32,
        affirmedNetworkContextUePoolStatisticsNumIpv6SubPools Unsigned32,
        affirmedNetworkContextUePoolStatisticsCurrentIpv4SubPoolsAllocCount ConfdString,
        affirmedNetworkContextUePoolStatisticsCurrentIpv6SubPoolsAllocCount ConfdString,
        affirmedNetworkContextUePoolStatisticsCurrentIpv4SubPoolsFreeCount ConfdString,
        affirmedNetworkContextUePoolStatisticsCurrentIpv6SubPoolsFreeCount ConfdString,
        affirmedNetworkContextUePoolStatisticsCurrentIpv4QuarantineQueueCount ConfdString,
        affirmedNetworkContextUePoolStatisticsCurrentIpv6QuarantineQueueCount ConfdString,
        affirmedNetworkContextUePoolStatisticsIpv4SubPoolUtil ConfdString,
        affirmedNetworkContextUePoolStatisticsIpv6SubPoolUtil ConfdString,
        affirmedNetworkContextUePoolStatisticsTotalIpv4SubPoolsAllocSuccess ConfdString,
        affirmedNetworkContextUePoolStatisticsTotalIpv4SubPoolsAllocFail ConfdString,
        affirmedNetworkContextUePoolStatisticsTotalIpv6SubPoolsAllocSuccess ConfdString,
        affirmedNetworkContextUePoolStatisticsTotalIpv6SubPoolsAllocFail ConfdString,
        affirmedNetworkContextUePoolStatisticsTotalIpv4SubPoolsReserveSuccess ConfdString,
        affirmedNetworkContextUePoolStatisticsTotalIpv4SubPoolsReserveFail ConfdString,
        affirmedNetworkContextUePoolStatisticsTotalIpv6SubPoolsReserveSuccess ConfdString,
        affirmedNetworkContextUePoolStatisticsTotalIpv6SubPoolsReserveFail ConfdString,
        affirmedNetworkContextUePoolStatisticsTotalIpv4SubPoolsReleaseSuccess ConfdString,
        affirmedNetworkContextUePoolStatisticsTotalIpv4SubPoolsReleaseFail ConfdString,
        affirmedNetworkContextUePoolStatisticsTotalIpv6SubPoolsReleaseSuccess ConfdString,
        affirmedNetworkContextUePoolStatisticsTotalIpv6SubPoolsReleaseFail ConfdString,
        affirmedNetworkContextUePoolStatisticsTotalIpv4SubPoolsQuarantineSuccess ConfdString,
        affirmedNetworkContextUePoolStatisticsTotalIpv4SubPoolsQuarantineFail ConfdString,
        affirmedNetworkContextUePoolStatisticsTotalIpv6SubPoolsQuarantineSuccess ConfdString,
        affirmedNetworkContextUePoolStatisticsTotalIpv6SubPoolsQuarantineFail ConfdString,
        affirmedNetworkContextUePoolStatisticsTotalIpv4SubPoolsQuarantineRelSuccess ConfdString,
        affirmedNetworkContextUePoolStatisticsTotalIpv4SubPoolsQuarantineRelFail ConfdString,
        affirmedNetworkContextUePoolStatisticsTotalIpv6SubPoolsQuarantineRelSuccess ConfdString,
        affirmedNetworkContextUePoolStatisticsTotalIpv6SubPoolsQuarantineRelFail ConfdString,
        affirmedNetworkContextUePoolStatisticsTotalIpv4QuarantineOverrideCount ConfdString,
        affirmedNetworkContextUePoolStatisticsTotalIpv6QuarantineOverrideCount ConfdString,
        affirmedNetworkContextUePoolStatisticsTotalIpv4QuarantineOverrideIpRelCount ConfdString,
        affirmedNetworkContextUePoolStatisticsTotalIpv6QuarantineOverrideIpRelCount ConfdString
    }

affirmedNetworkContextUePoolStatisticsName OBJECT-TYPE
    SYNTAX      String
    MAX-ACCESS  not-accessible
    STATUS      current
    DESCRIPTION "Ue Pool Name"
    ::= { affirmedNetworkContextUePoolStatisticsEntry 1 }

affirmedNetworkContextUePoolStatisticsNumIpv4SubPools OBJECT-TYPE
    SYNTAX      Unsigned32
    MAX-ACCESS  read-only
    STATUS      current
    DESCRIPTION "Number of IPv4 subpools"
    ::= { affirmedNetworkContextUePoolStatisticsEntry 2 }

affirmedNetworkContextUePoolStatisticsNumIpv6SubPools OBJECT-TYPE
    SYNTAX      Unsigned32
    MAX-ACCESS  read-only
    STATUS      current
    DESCRIPTION "Number of IPv6 subpools"
    ::= { affirmedNetworkContextUePoolStatisticsEntry 3 }

affirmedNetworkContextUePoolStatisticsCurrentIpv4SubPoolsAllocCount OBJECT-TYPE
    SYNTAX      ConfdString
    MAX-ACCESS  read-only
    STATUS      current
    DESCRIPTION "Count of IPs currently in use from IPv4 subpools"
    ::= { affirmedNetworkContextUePoolStatisticsEntry 4 }

affirmedNetworkContextUePoolStatisticsCurrentIpv6SubPoolsAllocCount OBJECT-TYPE
    SYNTAX      ConfdString
    MAX-ACCESS  read-only
    STATUS      current
    DESCRIPTION "Count of IPs currently in use from IPv6 subpools"
    ::= { affirmedNetworkContextUePoolStatisticsEntry 5 }

affirmedNetworkContextUePoolStatisticsCurrentIpv4SubPoolsFreeCount OBJECT-TYPE
    SYNTAX      ConfdString
    MAX-ACCESS  read-only
    STATUS      current
    DESCRIPTION "Count of IPs currently free in IPv4 subpools"
    ::= { affirmedNetworkContextUePoolStatisticsEntry 6 }

affirmedNetworkContextUePoolStatisticsCurrentIpv6SubPoolsFreeCount OBJECT-TYPE
    SYNTAX      ConfdString
    MAX-ACCESS  read-only
    STATUS      current
    DESCRIPTION "Count of IPs currently free in IPv6 subpools"
    ::= { affirmedNetworkContextUePoolStatisticsEntry 7 }

affirmedNetworkContextUePoolStatisticsCurrentIpv4QuarantineQueueCount OBJECT-TYPE
    SYNTAX      ConfdString
    MAX-ACCESS  read-only
    STATUS      current
    DESCRIPTION "Count of IPv4 addresses currently in quarantine"
    ::= { affirmedNetworkContextUePoolStatisticsEntry 8 }

affirmedNetworkContextUePoolStatisticsCurrentIpv6QuarantineQueueCount OBJECT-TYPE
    SYNTAX      ConfdString
    MAX-ACCESS  read-only
    STATUS      current
    DESCRIPTION "Count of IPv6 addresses currently in quarantine"
    ::= { affirmedNetworkContextUePoolStatisticsEntry 9 }

affirmedNetworkContextUePoolStatisticsIpv4SubPoolUtil OBJECT-TYPE
    SYNTAX      ConfdString
    MAX-ACCESS  read-only
    STATUS      current
    DESCRIPTION "IPv4 subpool utilization percentage"
    ::= { affirmedNetworkContextUePoolStatisticsEntry 10 }

affirmedNetworkContextUePoolStatisticsIpv6SubPoolUtil OBJECT-TYPE
    SYNTAX      ConfdString
    MAX-ACCESS  read-only
    STATUS      current
    DESCRIPTION "IPv6 subpool utilization percentage"
    ::= { affirmedNetworkContextUePoolStatisticsEntry 11 }

affirmedNetworkContextUePoolStatisticsTotalIpv4SubPoolsAllocSuccess OBJECT-TYPE
    SYNTAX      ConfdString
    MAX-ACCESS  read-only
    STATUS      current
    DESCRIPTION "Total successful IPv4 allocation count (cumulative)"
    ::= { affirmedNetworkContextUePoolStatisticsEntry 12 }

affirmedNetworkContextUePoolStatisticsTotalIpv4SubPoolsAllocFail OBJECT-TYPE
    SYNTAX      ConfdString
    MAX-ACCESS  read-only
    STATUS      current
    DESCRIPTION "Total failed IPv4 allocation count (cumulative)"
    ::= { affirmedNetworkContextUePoolStatisticsEntry 13 }

affirmedNetworkContextUePoolStatisticsTotalIpv6SubPoolsAllocSuccess OBJECT-TYPE
    SYNTAX      ConfdString
    MAX-ACCESS  read-only
    STATUS      current
    DESCRIPTION "Total successful IPv6 allocation count (cumulative)"
    ::= { affirmedNetworkContextUePoolStatisticsEntry 14 }

affirmedNetworkContextUePoolStatisticsTotalIpv6SubPoolsAllocFail OBJECT-TYPE
    SYNTAX      ConfdString
    MAX-ACCESS  read-only
    STATUS      current
    DESCRIPTION "Total failed IPv6 allocation count (cumulative)"
    ::= { affirmedNetworkContextUePoolStatisticsEntry 15 }

affirmedNetworkContextUePoolStatisticsTotalIpv4SubPoolsReserveSuccess OBJECT-TYPE
    SYNTAX      ConfdString
    MAX-ACCESS  read-only
    STATUS      current
    DESCRIPTION "Total successful IPv4 reservation count (cumulative)"
    ::= { affirmedNetworkContextUePoolStatisticsEntry 16 }

affirmedNetworkContextUePoolStatisticsTotalIpv4SubPoolsReserveFail OBJECT-TYPE
    SYNTAX      ConfdString
    MAX-ACCESS  read-only
    STATUS      current
    DESCRIPTION "Total failed IPv4 reservation count (cumulative)"
    ::= { affirmedNetworkContextUePoolStatisticsEntry 17 }

affirmedNetworkContextUePoolStatisticsTotalIpv6SubPoolsReserveSuccess OBJECT-TYPE
    SYNTAX      ConfdString
    MAX-ACCESS  read-only
    STATUS      current
    DESCRIPTION "Total successful IPv6 reservation count (cumulative)"
    ::= { affirmedNetworkContextUePoolStatisticsEntry 18 }

affirmedNetworkContextUePoolStatisticsTotalIpv6SubPoolsReserveFail OBJECT-TYPE
    SYNTAX      ConfdString
    MAX-ACCESS  read-only
    STATUS      current
    DESCRIPTION "Total failed IPv6 reservation count (cumulative)"
    ::= { affirmedNetworkContextUePoolStatisticsEntry 19 }

affirmedNetworkContextUePoolStatisticsTotalIpv4SubPoolsReleaseSuccess OBJECT-TYPE
    SYNTAX      ConfdString
    MAX-ACCESS  read-only
    STATUS      current
    DESCRIPTION "Total successful IPv4 release count (cumulative)"
    ::= { affirmedNetworkContextUePoolStatisticsEntry 20 }

affirmedNetworkContextUePoolStatisticsTotalIpv4SubPoolsReleaseFail OBJECT-TYPE
    SYNTAX      ConfdString
    MAX-ACCESS  read-only
    STATUS      current
    DESCRIPTION "Total failed IPv4 release count (cumulative)"
    ::= { affirmedNetworkContextUePoolStatisticsEntry 21 }

affirmedNetworkContextUePoolStatisticsTotalIpv6SubPoolsReleaseSuccess OBJECT-TYPE
    SYNTAX      ConfdString
    MAX-ACCESS  read-only
    STATUS      current
    DESCRIPTION "Total successful IPv6 release count (cumulative)"
    ::= { affirmedNetworkContextUePoolStatisticsEntry 22 }

affirmedNetworkContextUePoolStatisticsTotalIpv6SubPoolsReleaseFail OBJECT-TYPE
    SYNTAX      ConfdString
    MAX-ACCESS  read-only
    STATUS      current
    DESCRIPTION "Total failed IPv6 release count (cumulative)"
    ::= { affirmedNetworkContextUePoolStatisticsEntry 23 }

affirmedNetworkContextUePoolStatisticsTotalIpv4SubPoolsQuarantineSuccess OBJECT-TYPE
    SYNTAX      ConfdString
    MAX-ACCESS  read-only
    STATUS      current
    DESCRIPTION "Total successful IPv4 quarantine count (cumulative)"
    ::= { affirmedNetworkContextUePoolStatisticsEntry 24 }

affirmedNetworkContextUePoolStatisticsTotalIpv4SubPoolsQuarantineFail OBJECT-TYPE
    SYNTAX      ConfdString
    MAX-ACCESS  read-only
    STATUS      current
    DESCRIPTION "Total failed IPv4 quarantine count (cumulative)"
    ::= { affirmedNetworkContextUePoolStatisticsEntry 25 }

affirmedNetworkContextUePoolStatisticsTotalIpv6SubPoolsQuarantineSuccess OBJECT-TYPE
    SYNTAX      ConfdString
    MAX-ACCESS  read-only
    STATUS      current
    DESCRIPTION "Total successful IPv6 quarantine count (cumulative)"
    ::= { affirmedNetworkContextUePoolStatisticsEntry 26 }

affirmedNetworkContextUePoolStatisticsTotalIpv6SubPoolsQuarantineFail OBJECT-TYPE
    SYNTAX      ConfdString
    MAX-ACCESS  read-only
    STATUS      current
    DESCRIPTION "Total failed IPv6 quarantine count (cumulative)"
    ::= { affirmedNetworkContextUePoolStatisticsEntry 27 }

affirmedNetworkContextUePoolStatisticsTotalIpv4SubPoolsQuarantineRelSuccess OBJECT-TYPE
    SYNTAX      ConfdString
    MAX-ACCESS  read-only
    STATUS      current
    DESCRIPTION "Total successful IPv4 quarantine release count (cumulative)"
    ::= { affirmedNetworkContextUePoolStatisticsEntry 28 }

affirmedNetworkContextUePoolStatisticsTotalIpv4SubPoolsQuarantineRelFail OBJECT-TYPE
    SYNTAX      ConfdString
    MAX-ACCESS  read-only
    STATUS      current
    DESCRIPTION "Total failed IPv4 quarantine release count (cumulative)"
    ::= { affirmedNetworkContextUePoolStatisticsEntry 29 }

affirmedNetworkContextUePoolStatisticsTotalIpv6SubPoolsQuarantineRelSuccess OBJECT-TYPE
    SYNTAX      ConfdString
    MAX-ACCESS  read-only
    STATUS      current
    DESCRIPTION "Total successful IPv6 quarantine release count (cumulative)"
    ::= { affirmedNetworkContextUePoolStatisticsEntry 30 }

affirmedNetworkContextUePoolStatisticsTotalIpv6SubPoolsQuarantineRelFail OBJECT-TYPE
    SYNTAX      ConfdString
    MAX-ACCESS  read-only
    STATUS      current
    DESCRIPTION "Total failed IPv6 quarantine release count (cumulative)"
    ::= { affirmedNetworkContextUePoolStatisticsEntry 31 }

affirmedNetworkContextUePoolStatisticsTotalIpv4QuarantineOverrideCount OBJECT-TYPE
    SYNTAX      ConfdString
    MAX-ACCESS  read-only
    STATUS      current
    DESCRIPTION "Total IPv4 quarantine override count (cumulative)"
    ::= { affirmedNetworkContextUePoolStatisticsEntry 32 }

affirmedNetworkContextUePoolStatisticsTotalIpv6QuarantineOverrideCount OBJECT-TYPE
    SYNTAX      ConfdString
    MAX-ACCESS  read-only
    STATUS      current
    DESCRIPTION "Total IPv6 quarantine override count (cumulative)"
    ::= { affirmedNetworkContextUePoolStatisticsEntry 33 }

affirmedNetworkContextUePoolStatisticsTotalIpv4QuarantineOverrideIpRelCount OBJECT-TYPE
    SYNTAX      ConfdString
    MAX-ACCESS  read-only
    STATUS      current
    DESCRIPTION "Total IPv4 quarantine override IP release count (cumulative)"
    ::= { affirmedNetworkContextUePoolStatisticsEntry 34 }

affirmedNetworkContextUePoolStatisticsTotalIpv6QuarantineOverrideIpRelCount OBJECT-TYPE
    SYNTAX      ConfdString
    MAX-ACCESS  read-only
    STATUS      current
    DESCRIPTION "Total IPv6 quarantine override IP release count (cumulative)"
    ::= { affirmedNetworkContextUePoolStatisticsEntry 35 }

affirmedNetworkContextUimStatisticsTable OBJECT-TYPE
    SYNTAX      SEQUENCE OF AffirmedNetworkContextUimStatisticsEntry
    MAX-ACCESS  not-accessible
    STATUS      current
    DESCRIPTION ""
    ::= { affirmedNetworkcontextMIB 17 }

affirmedNetworkContextUimStatisticsEntry OBJECT-TYPE
    SYNTAX      AffirmedNetworkContextUimStatisticsEntry
    MAX-ACCESS  not-accessible
    STATUS      current
    DESCRIPTION ""
    INDEX { affirmedNetworkContextName, affirmedNetworkContextUimStatisticsName }
        ::= { affirmedNetworkContextUimStatisticsTable 1 }

AffirmedNetworkContextUimStatisticsEntry ::=
    SEQUENCE {
        affirmedNetworkContextUimStatisticsName String,
        affirmedNetworkContextUimStatisticsNumUePools ConfdString,
        affirmedNetworkContextUimStatisticsNumLocalUePools ConfdString,
        affirmedNetworkContextUimStatisticsNumRemoteUePools ConfdString,
        affirmedNetworkContextUimStatisticsNumIpSubPools ConfdString,
        affirmedNetworkContextUimStatisticsNumIpv4SubPools ConfdString,
        affirmedNetworkContextUimStatisticsNumIpv6SubPools ConfdString,
        affirmedNetworkContextUimStatisticsNumApn ConfdString,
        affirmedNetworkContextUimStatisticsCurrentIpv4SubPoolsAllocCount ConfdString,
        affirmedNetworkContextUimStatisticsCurrentIpv6SubPoolsAllocCount ConfdString,
        affirmedNetworkContextUimStatisticsCurrentIpv4SubPoolsFreeCount ConfdString,
        affirmedNetworkContextUimStatisticsCurrentIpv6SubPoolsFreeCount ConfdString,
        affirmedNetworkContextUimStatisticsCurrentIpv4QuarantineQueueCount ConfdString,
        affirmedNetworkContextUimStatisticsCurrentIpv6QuarantineQueueCount ConfdString,
        affirmedNetworkContextUimStatisticsIpv4SubPoolUtil ConfdString,
        affirmedNetworkContextUimStatisticsIpv6SubPoolUtil ConfdString,
        affirmedNetworkContextUimStatisticsAllocIpv4LocalSuccess ConfdString,
        affirmedNetworkContextUimStatisticsAllocIpv4LocalFailure ConfdString,
        affirmedNetworkContextUimStatisticsAllocIpv6LocalSuccess ConfdString,
        affirmedNetworkContextUimStatisticsAllocIpv6LocalFailure ConfdString,
        affirmedNetworkContextUimStatisticsAllocIpv4v6LocalSuccess ConfdString,
        affirmedNetworkContextUimStatisticsAllocIpv4v6LocalFailure ConfdString,
        affirmedNetworkContextUimStatisticsReserveIpv4RemoteSuccess ConfdString,
        affirmedNetworkContextUimStatisticsReserveIpv4RemoteFailure ConfdString,
        affirmedNetworkContextUimStatisticsReserveIpv6RemoteSuccess ConfdString,
        affirmedNetworkContextUimStatisticsReserveIpv6RemoteFailure ConfdString,
        affirmedNetworkContextUimStatisticsReserveIpv4v6RemoteSuccess ConfdString,
        affirmedNetworkContextUimStatisticsReserveIpv4v6RemoteFailure ConfdString,
        affirmedNetworkContextUimStatisticsAllocIpv4RemoteSuccess ConfdString,
        affirmedNetworkContextUimStatisticsAllocIpv4RemoteFailure ConfdString,
        affirmedNetworkContextUimStatisticsAllocIpv6RemoteSuccess ConfdString,
        affirmedNetworkContextUimStatisticsAllocIpv6RemoteFailure ConfdString,
        affirmedNetworkContextUimStatisticsAllocIpv4v6RemoteSuccess ConfdString,
        affirmedNetworkContextUimStatisticsAllocIpv4v6RemoteFailure ConfdString,
        affirmedNetworkContextUimStatisticsReleaseIpv4Success ConfdString,
        affirmedNetworkContextUimStatisticsReleaseIpv4Failure ConfdString,
        affirmedNetworkContextUimStatisticsReleaseIpv6Success ConfdString,
        affirmedNetworkContextUimStatisticsReleaseIpv6Failure ConfdString,
        affirmedNetworkContextUimStatisticsReleaseIpv4v6Success ConfdString,
        affirmedNetworkContextUimStatisticsReleaseIpv4v6Failure ConfdString,
        affirmedNetworkContextUimStatisticsHybridReserveV4LocalAllocV6Success ConfdString,
        affirmedNetworkContextUimStatisticsHybridReserveV4LocalAllocV6Failure ConfdString,
        affirmedNetworkContextUimStatisticsHybridReserveV4RemoteAllocV6Success ConfdString,
        affirmedNetworkContextUimStatisticsHybridReserveV4RemoteAllocV6Failure ConfdString,
        affirmedNetworkContextUimStatisticsHybridReserveV6LocalAllocV4Success ConfdString,
        affirmedNetworkContextUimStatisticsHybridReserveV6LocalAllocV4Failure ConfdString,
        affirmedNetworkContextUimStatisticsHybridReserveV6RemoteAllocV4Success ConfdString,
        affirmedNetworkContextUimStatisticsHybridReserveV6RemoteAllocV4Failure ConfdString,
        affirmedNetworkContextUimStatisticsClearSessDupV4ReserveSameImsiSuccess ConfdString,
        affirmedNetworkContextUimStatisticsClearSessDupV4ReserveSameImsiFailure ConfdString,
        affirmedNetworkContextUimStatisticsClearSessDupV4ReserveDiffImsiSuccess ConfdString,
        affirmedNetworkContextUimStatisticsClearSessDupV4ReserveDiffImsiFailure ConfdString,
        affirmedNetworkContextUimStatisticsClearSessDupV6ReserveSameImsiSuccess ConfdString,
        affirmedNetworkContextUimStatisticsClearSessDupV6ReserveSameImsiFailure ConfdString,
        affirmedNetworkContextUimStatisticsClearSessDupV6ReserveDiffImsiSuccess ConfdString,
        affirmedNetworkContextUimStatisticsClearSessDupV6ReserveDiffImsiFailure ConfdString,
        affirmedNetworkContextUimStatisticsReserveDelegIpv6RemoteSuccess ConfdString,
        affirmedNetworkContextUimStatisticsReserveDelegIpv6RemoteFailure ConfdString,
        affirmedNetworkContextUimStatisticsReleaseDelegIpv6Success ConfdString,
        affirmedNetworkContextUimStatisticsReleaseDelegIpv6Failure ConfdString,
        affirmedNetworkContextUimStatisticsAllocDelegIpv6LocalSuccess ConfdString,
        affirmedNetworkContextUimStatisticsAllocDelegIpv6LocalFailure ConfdString,
        affirmedNetworkContextUimStatisticsUplaneReserveIpv4Success ConfdString,
        affirmedNetworkContextUimStatisticsUplaneReserveIpv4Failure ConfdString,
        affirmedNetworkContextUimStatisticsUplaneReserveIpv6Success ConfdString,
        affirmedNetworkContextUimStatisticsUplaneReserveIpv6Failure ConfdString,
        affirmedNetworkContextUimStatisticsUplaneReserveIpv4v6Success ConfdString,
        affirmedNetworkContextUimStatisticsUplaneReserveIpv4v6Failure ConfdString,
        affirmedNetworkContextUimStatisticsAllocV4TamFailure ConfdString,
        affirmedNetworkContextUimStatisticsAllocV6TamFailure ConfdString,
        affirmedNetworkContextUimStatisticsAllocV4V6TamFailure ConfdString,
        affirmedNetworkContextUimStatisticsReserveV4TamFailure ConfdString,
        affirmedNetworkContextUimStatisticsReserveV6TamFailure ConfdString,
        affirmedNetworkContextUimStatisticsReserveV4V6TamFailure ConfdString,
        affirmedNetworkContextUimStatisticsHybridV4V6TamFailure ConfdString,
        affirmedNetworkContextUimStatisticsAllocDelegV6TamFailure ConfdString,
        affirmedNetworkContextUimStatisticsReserveDelegV6TamFailure ConfdString
    }

affirmedNetworkContextUimStatisticsName OBJECT-TYPE
    SYNTAX      String
    MAX-ACCESS  not-accessible
    STATUS      current
    DESCRIPTION "Network Context name"
    ::= { affirmedNetworkContextUimStatisticsEntry 1 }

affirmedNetworkContextUimStatisticsNumUePools OBJECT-TYPE
    SYNTAX      ConfdString
    MAX-ACCESS  read-only
    STATUS      current
    DESCRIPTION "Number of UePool's configured on this network context"
    ::= { affirmedNetworkContextUimStatisticsEntry 2 }

affirmedNetworkContextUimStatisticsNumLocalUePools OBJECT-TYPE
    SYNTAX      ConfdString
    MAX-ACCESS  read-only
    STATUS      current
    DESCRIPTION "Number of local UePool's configured on this this network context"
    ::= { affirmedNetworkContextUimStatisticsEntry 3 }

affirmedNetworkContextUimStatisticsNumRemoteUePools OBJECT-TYPE
    SYNTAX      ConfdString
    MAX-ACCESS  read-only
    STATUS      current
    DESCRIPTION "Number of remote UePool's configured on this network context"
    ::= { affirmedNetworkContextUimStatisticsEntry 4 }

affirmedNetworkContextUimStatisticsNumIpSubPools OBJECT-TYPE
    SYNTAX      ConfdString
    MAX-ACCESS  read-only
    STATUS      current
    DESCRIPTION "Number of IpSubPool's configured on this network context"
    ::= { affirmedNetworkContextUimStatisticsEntry 5 }

affirmedNetworkContextUimStatisticsNumIpv4SubPools OBJECT-TYPE
    SYNTAX      ConfdString
    MAX-ACCESS  read-only
    STATUS      current
    DESCRIPTION "Number of IPv4 subpools configured on this network context"
    ::= { affirmedNetworkContextUimStatisticsEntry 6 }

affirmedNetworkContextUimStatisticsNumIpv6SubPools OBJECT-TYPE
    SYNTAX      ConfdString
    MAX-ACCESS  read-only
    STATUS      current
    DESCRIPTION "Number of IPv6 subpools configured on this network context"
    ::= { affirmedNetworkContextUimStatisticsEntry 7 }

affirmedNetworkContextUimStatisticsNumApn OBJECT-TYPE
    SYNTAX      ConfdString
    MAX-ACCESS  read-only
    STATUS      current
    DESCRIPTION "Number of APN's associated with this network context"
    ::= { affirmedNetworkContextUimStatisticsEntry 8 }

affirmedNetworkContextUimStatisticsCurrentIpv4SubPoolsAllocCount OBJECT-TYPE
    SYNTAX      ConfdString
    MAX-ACCESS  read-only
    STATUS      current
    DESCRIPTION "Count of IPs currently in use from IPv4 subpools"
    ::= { affirmedNetworkContextUimStatisticsEntry 9 }

affirmedNetworkContextUimStatisticsCurrentIpv6SubPoolsAllocCount OBJECT-TYPE
    SYNTAX      ConfdString
    MAX-ACCESS  read-only
    STATUS      current
    DESCRIPTION "Count of IPs currently in use from IPv6 subpools"
    ::= { affirmedNetworkContextUimStatisticsEntry 10 }

affirmedNetworkContextUimStatisticsCurrentIpv4SubPoolsFreeCount OBJECT-TYPE
    SYNTAX      ConfdString
    MAX-ACCESS  read-only
    STATUS      current
    DESCRIPTION "Count of IPs currently free in IPv4 subpools"
    ::= { affirmedNetworkContextUimStatisticsEntry 11 }

affirmedNetworkContextUimStatisticsCurrentIpv6SubPoolsFreeCount OBJECT-TYPE
    SYNTAX      ConfdString
    MAX-ACCESS  read-only
    STATUS      current
    DESCRIPTION "Count of IPs currently free in IPv6 subpools"
    ::= { affirmedNetworkContextUimStatisticsEntry 12 }

affirmedNetworkContextUimStatisticsCurrentIpv4QuarantineQueueCount OBJECT-TYPE
    SYNTAX      ConfdString
    MAX-ACCESS  read-only
    STATUS      current
    DESCRIPTION "Count of IPv4 addresses currently in quarantine"
    ::= { affirmedNetworkContextUimStatisticsEntry 13 }

affirmedNetworkContextUimStatisticsCurrentIpv6QuarantineQueueCount OBJECT-TYPE
    SYNTAX      ConfdString
    MAX-ACCESS  read-only
    STATUS      current
    DESCRIPTION "Count of IPv6 addresses currently in quarantine"
    ::= { affirmedNetworkContextUimStatisticsEntry 14 }

affirmedNetworkContextUimStatisticsIpv4SubPoolUtil OBJECT-TYPE
    SYNTAX      ConfdString
    MAX-ACCESS  read-only
    STATUS      current
    DESCRIPTION "IPv4 subpool utilization percentage"
    ::= { affirmedNetworkContextUimStatisticsEntry 15 }

affirmedNetworkContextUimStatisticsIpv6SubPoolUtil OBJECT-TYPE
    SYNTAX      ConfdString
    MAX-ACCESS  read-only
    STATUS      current
    DESCRIPTION "IPv6 subpool utilization percentage"
    ::= { affirmedNetworkContextUimStatisticsEntry 16 }

affirmedNetworkContextUimStatisticsAllocIpv4LocalSuccess OBJECT-TYPE
    SYNTAX      ConfdString
    MAX-ACCESS  read-only
    STATUS      current
    DESCRIPTION "Total successful local IPv4 allocation count"
    ::= { affirmedNetworkContextUimStatisticsEntry 17 }

affirmedNetworkContextUimStatisticsAllocIpv4LocalFailure OBJECT-TYPE
    SYNTAX      ConfdString
    MAX-ACCESS  read-only
    STATUS      current
    DESCRIPTION "Total failed local IPv4 allocation count"
    ::= { affirmedNetworkContextUimStatisticsEntry 18 }

affirmedNetworkContextUimStatisticsAllocIpv6LocalSuccess OBJECT-TYPE
    SYNTAX      ConfdString
    MAX-ACCESS  read-only
    STATUS      current
    DESCRIPTION "Total successful local IPv6 allocation count"
    ::= { affirmedNetworkContextUimStatisticsEntry 19 }

affirmedNetworkContextUimStatisticsAllocIpv6LocalFailure OBJECT-TYPE
    SYNTAX      ConfdString
    MAX-ACCESS  read-only
    STATUS      current
    DESCRIPTION "Total failed local IPv6 allocation count"
    ::= { affirmedNetworkContextUimStatisticsEntry 20 }

affirmedNetworkContextUimStatisticsAllocIpv4v6LocalSuccess OBJECT-TYPE
    SYNTAX      ConfdString
    MAX-ACCESS  read-only
    STATUS      current
    DESCRIPTION "Total successful local IPv4v6 allocation count"
    ::= { affirmedNetworkContextUimStatisticsEntry 21 }

affirmedNetworkContextUimStatisticsAllocIpv4v6LocalFailure OBJECT-TYPE
    SYNTAX      ConfdString
    MAX-ACCESS  read-only
    STATUS      current
    DESCRIPTION "Total failed local IPv4v6 allocation count"
    ::= { affirmedNetworkContextUimStatisticsEntry 22 }

affirmedNetworkContextUimStatisticsReserveIpv4RemoteSuccess OBJECT-TYPE
    SYNTAX      ConfdString
    MAX-ACCESS  read-only
    STATUS      current
    DESCRIPTION "Total successful remote IPv4 reservation count"
    ::= { affirmedNetworkContextUimStatisticsEntry 23 }

affirmedNetworkContextUimStatisticsReserveIpv4RemoteFailure OBJECT-TYPE
    SYNTAX      ConfdString
    MAX-ACCESS  read-only
    STATUS      current
    DESCRIPTION "Total failed remote IPv4 reservation count"
    ::= { affirmedNetworkContextUimStatisticsEntry 24 }

affirmedNetworkContextUimStatisticsReserveIpv6RemoteSuccess OBJECT-TYPE
    SYNTAX      ConfdString
    MAX-ACCESS  read-only
    STATUS      current
    DESCRIPTION "Total successful remote IPv6 reservation count"
    ::= { affirmedNetworkContextUimStatisticsEntry 25 }

affirmedNetworkContextUimStatisticsReserveIpv6RemoteFailure OBJECT-TYPE
    SYNTAX      ConfdString
    MAX-ACCESS  read-only
    STATUS      current
    DESCRIPTION "Total failed remote IPv6 reservation count"
    ::= { affirmedNetworkContextUimStatisticsEntry 26 }

affirmedNetworkContextUimStatisticsReserveIpv4v6RemoteSuccess OBJECT-TYPE
    SYNTAX      ConfdString
    MAX-ACCESS  read-only
    STATUS      current
    DESCRIPTION "Total successful remote IPv4v6 reservation count"
    ::= { affirmedNetworkContextUimStatisticsEntry 27 }

affirmedNetworkContextUimStatisticsReserveIpv4v6RemoteFailure OBJECT-TYPE
    SYNTAX      ConfdString
    MAX-ACCESS  read-only
    STATUS      current
    DESCRIPTION "Total failed remote IPv4v6 reservation count"
    ::= { affirmedNetworkContextUimStatisticsEntry 28 }

affirmedNetworkContextUimStatisticsAllocIpv4RemoteSuccess OBJECT-TYPE
    SYNTAX      ConfdString
    MAX-ACCESS  read-only
    STATUS      current
    DESCRIPTION "Total successful remote IPv4 allocation count"
    ::= { affirmedNetworkContextUimStatisticsEntry 29 }

affirmedNetworkContextUimStatisticsAllocIpv4RemoteFailure OBJECT-TYPE
    SYNTAX      ConfdString
    MAX-ACCESS  read-only
    STATUS      current
    DESCRIPTION "Total failed remote IPv4 allocation count"
    ::= { affirmedNetworkContextUimStatisticsEntry 30 }

affirmedNetworkContextUimStatisticsAllocIpv6RemoteSuccess OBJECT-TYPE
    SYNTAX      ConfdString
    MAX-ACCESS  read-only
    STATUS      current
    DESCRIPTION "Total successful remote IPv6 allocation count"
    ::= { affirmedNetworkContextUimStatisticsEntry 31 }

affirmedNetworkContextUimStatisticsAllocIpv6RemoteFailure OBJECT-TYPE
    SYNTAX      ConfdString
    MAX-ACCESS  read-only
    STATUS      current
    DESCRIPTION "Total failed remote IPv6 allocation count"
    ::= { affirmedNetworkContextUimStatisticsEntry 32 }

affirmedNetworkContextUimStatisticsAllocIpv4v6RemoteSuccess OBJECT-TYPE
    SYNTAX      ConfdString
    MAX-ACCESS  read-only
    STATUS      current
    DESCRIPTION "Total successful remote IPv4v6 allocation count"
    ::= { affirmedNetworkContextUimStatisticsEntry 33 }

affirmedNetworkContextUimStatisticsAllocIpv4v6RemoteFailure OBJECT-TYPE
    SYNTAX      ConfdString
    MAX-ACCESS  read-only
    STATUS      current
    DESCRIPTION "Total failed remote IPv4v6 allocation count"
    ::= { affirmedNetworkContextUimStatisticsEntry 34 }

affirmedNetworkContextUimStatisticsReleaseIpv4Success OBJECT-TYPE
    SYNTAX      ConfdString
    MAX-ACCESS  read-only
    STATUS      current
    DESCRIPTION "Total successful IPv4 release count"
    ::= { affirmedNetworkContextUimStatisticsEntry 35 }

affirmedNetworkContextUimStatisticsReleaseIpv4Failure OBJECT-TYPE
    SYNTAX      ConfdString
    MAX-ACCESS  read-only
    STATUS      current
    DESCRIPTION "Total failed IPv4 release count"
    ::= { affirmedNetworkContextUimStatisticsEntry 36 }

affirmedNetworkContextUimStatisticsReleaseIpv6Success OBJECT-TYPE
    SYNTAX      ConfdString
    MAX-ACCESS  read-only
    STATUS      current
    DESCRIPTION "Total successful IPv6 release count"
    ::= { affirmedNetworkContextUimStatisticsEntry 37 }

affirmedNetworkContextUimStatisticsReleaseIpv6Failure OBJECT-TYPE
    SYNTAX      ConfdString
    MAX-ACCESS  read-only
    STATUS      current
    DESCRIPTION "Total failed IPv6 release count"
    ::= { affirmedNetworkContextUimStatisticsEntry 38 }

affirmedNetworkContextUimStatisticsReleaseIpv4v6Success OBJECT-TYPE
    SYNTAX      ConfdString
    MAX-ACCESS  read-only
    STATUS      current
    DESCRIPTION "Total successful IPv4v6 release count"
    ::= { affirmedNetworkContextUimStatisticsEntry 39 }

affirmedNetworkContextUimStatisticsReleaseIpv4v6Failure OBJECT-TYPE
    SYNTAX      ConfdString
    MAX-ACCESS  read-only
    STATUS      current
    DESCRIPTION "Total failed IPv4v6 release count"
    ::= { affirmedNetworkContextUimStatisticsEntry 40 }

affirmedNetworkContextUimStatisticsHybridReserveV4LocalAllocV6Success OBJECT-TYPE
    SYNTAX      ConfdString
    MAX-ACCESS  read-only
    STATUS      current
    DESCRIPTION "Total successful hybrid IPv4v6 count for IPv4 - remote reservation, IPV6 - local subpool allocation"
    ::= { affirmedNetworkContextUimStatisticsEntry 41 }

affirmedNetworkContextUimStatisticsHybridReserveV4LocalAllocV6Failure OBJECT-TYPE
    SYNTAX      ConfdString
    MAX-ACCESS  read-only
    STATUS      current
    DESCRIPTION "Total failed hybrid IPv4v6 count for IPv4 - remote reservation, IPV6 - local subpool allocation"
    ::= { affirmedNetworkContextUimStatisticsEntry 42 }

affirmedNetworkContextUimStatisticsHybridReserveV4RemoteAllocV6Success OBJECT-TYPE
    SYNTAX      ConfdString
    MAX-ACCESS  read-only
    STATUS      current
    DESCRIPTION "Total successful hybrid IPv4v6 count for IPv4 - remote reservation, IPV6 - remote subpool allocation"
    ::= { affirmedNetworkContextUimStatisticsEntry 43 }

affirmedNetworkContextUimStatisticsHybridReserveV4RemoteAllocV6Failure OBJECT-TYPE
    SYNTAX      ConfdString
    MAX-ACCESS  read-only
    STATUS      current
    DESCRIPTION "Total failed hybrid IPv4v6 count for IPv4 - remote reservation, IPV6 - remote subpool allocation"
    ::= { affirmedNetworkContextUimStatisticsEntry 44 }

affirmedNetworkContextUimStatisticsHybridReserveV6LocalAllocV4Success OBJECT-TYPE
    SYNTAX      ConfdString
    MAX-ACCESS  read-only
    STATUS      current
    DESCRIPTION "Total successful hybrid IPv4v6 count for IPv6 - remote reservation, IPV4 - local subpool allocation"
    ::= { affirmedNetworkContextUimStatisticsEntry 45 }

affirmedNetworkContextUimStatisticsHybridReserveV6LocalAllocV4Failure OBJECT-TYPE
    SYNTAX      ConfdString
    MAX-ACCESS  read-only
    STATUS      current
    DESCRIPTION "Total failed hybrid IPv4v6 count for IPv6 - remote reservation, IPV4 - local subpool allocation"
    ::= { affirmedNetworkContextUimStatisticsEntry 46 }

affirmedNetworkContextUimStatisticsHybridReserveV6RemoteAllocV4Success OBJECT-TYPE
    SYNTAX      ConfdString
    MAX-ACCESS  read-only
    STATUS      current
    DESCRIPTION "Total successful hybrid IPv4v6 count for IPv6 - remote reservation, IPV4 - remote subpool allocation"
    ::= { affirmedNetworkContextUimStatisticsEntry 47 }

affirmedNetworkContextUimStatisticsHybridReserveV6RemoteAllocV4Failure OBJECT-TYPE
    SYNTAX      ConfdString
    MAX-ACCESS  read-only
    STATUS      current
    DESCRIPTION "Total failed hybrid IPv4v6 count for IPv6 - remote reservation, IPV4 - remote subpool allocation"
    ::= { affirmedNetworkContextUimStatisticsEntry 48 }

affirmedNetworkContextUimStatisticsClearSessDupV4ReserveSameImsiSuccess OBJECT-TYPE
    SYNTAX      ConfdString
    MAX-ACCESS  read-only
    STATUS      current
    DESCRIPTION "Total sessions (same IMSI) cleared successfully - by duplicate IPV4 reserve request"
    ::= { affirmedNetworkContextUimStatisticsEntry 49 }

affirmedNetworkContextUimStatisticsClearSessDupV4ReserveSameImsiFailure OBJECT-TYPE
    SYNTAX      ConfdString
    MAX-ACCESS  read-only
    STATUS      current
    DESCRIPTION "Total sessions (same IMSI) clear failures - by duplicate IPV4 reserve request"
    ::= { affirmedNetworkContextUimStatisticsEntry 50 }

affirmedNetworkContextUimStatisticsClearSessDupV4ReserveDiffImsiSuccess OBJECT-TYPE
    SYNTAX      ConfdString
    MAX-ACCESS  read-only
    STATUS      current
    DESCRIPTION "Total sessions (different IMSI) cleared successfully - by duplicate IPV4 reserve request"
    ::= { affirmedNetworkContextUimStatisticsEntry 51 }

affirmedNetworkContextUimStatisticsClearSessDupV4ReserveDiffImsiFailure OBJECT-TYPE
    SYNTAX      ConfdString
    MAX-ACCESS  read-only
    STATUS      current
    DESCRIPTION "Total sessions (different IMSI) clear failures - by duplicate IPV4 reserve request"
    ::= { affirmedNetworkContextUimStatisticsEntry 52 }

affirmedNetworkContextUimStatisticsClearSessDupV6ReserveSameImsiSuccess OBJECT-TYPE
    SYNTAX      ConfdString
    MAX-ACCESS  read-only
    STATUS      current
    DESCRIPTION "Total sessions (same IMSI) cleared successfully - by duplicate IPV6 reserve request"
    ::= { affirmedNetworkContextUimStatisticsEntry 53 }

affirmedNetworkContextUimStatisticsClearSessDupV6ReserveSameImsiFailure OBJECT-TYPE
    SYNTAX      ConfdString
    MAX-ACCESS  read-only
    STATUS      current
    DESCRIPTION "Total sessions (same IMSI) clear failures - by duplicate IPV6 reserve request"
    ::= { affirmedNetworkContextUimStatisticsEntry 54 }

affirmedNetworkContextUimStatisticsClearSessDupV6ReserveDiffImsiSuccess OBJECT-TYPE
    SYNTAX      ConfdString
    MAX-ACCESS  read-only
    STATUS      current
    DESCRIPTION "Total sessions (different IMSI) cleared successfully - by duplicate IPV6 reserve request"
    ::= { affirmedNetworkContextUimStatisticsEntry 55 }

affirmedNetworkContextUimStatisticsClearSessDupV6ReserveDiffImsiFailure OBJECT-TYPE
    SYNTAX      ConfdString
    MAX-ACCESS  read-only
    STATUS      current
    DESCRIPTION "Total sessions (different IMSI) clear failures - by duplicate IPV6 reserve request"
    ::= { affirmedNetworkContextUimStatisticsEntry 56 }

affirmedNetworkContextUimStatisticsReserveDelegIpv6RemoteSuccess OBJECT-TYPE
    SYNTAX      ConfdString
    MAX-ACCESS  read-only
    STATUS      current
    DESCRIPTION "Total successful remote delegated IPv6 reservation count"
    ::= { affirmedNetworkContextUimStatisticsEntry 57 }

affirmedNetworkContextUimStatisticsReserveDelegIpv6RemoteFailure OBJECT-TYPE
    SYNTAX      ConfdString
    MAX-ACCESS  read-only
    STATUS      current
    DESCRIPTION "Total failed remote delegated IPv6 reservation count"
    ::= { affirmedNetworkContextUimStatisticsEntry 58 }

affirmedNetworkContextUimStatisticsReleaseDelegIpv6Success OBJECT-TYPE
    SYNTAX      ConfdString
    MAX-ACCESS  read-only
    STATUS      current
    DESCRIPTION "Total successful delegated IPv6 release count"
    ::= { affirmedNetworkContextUimStatisticsEntry 59 }

affirmedNetworkContextUimStatisticsReleaseDelegIpv6Failure OBJECT-TYPE
    SYNTAX      ConfdString
    MAX-ACCESS  read-only
    STATUS      current
    DESCRIPTION "Total failed delegated IPv6 release count"
    ::= { affirmedNetworkContextUimStatisticsEntry 60 }

affirmedNetworkContextUimStatisticsAllocDelegIpv6LocalSuccess OBJECT-TYPE
    SYNTAX      ConfdString
    MAX-ACCESS  read-only
    STATUS      current
    DESCRIPTION "Total successful local delegated IPv6 allocation count"
    ::= { affirmedNetworkContextUimStatisticsEntry 61 }

affirmedNetworkContextUimStatisticsAllocDelegIpv6LocalFailure OBJECT-TYPE
    SYNTAX      ConfdString
    MAX-ACCESS  read-only
    STATUS      current
    DESCRIPTION "Total failed local delegated IPv6 allocation count"
    ::= { affirmedNetworkContextUimStatisticsEntry 62 }

affirmedNetworkContextUimStatisticsUplaneReserveIpv4Success OBJECT-TYPE
    SYNTAX      ConfdString
    MAX-ACCESS  read-only
    STATUS      current
    DESCRIPTION "Total successful user-plane IPv4 Reservations"
    ::= { affirmedNetworkContextUimStatisticsEntry 63 }

affirmedNetworkContextUimStatisticsUplaneReserveIpv4Failure OBJECT-TYPE
    SYNTAX      ConfdString
    MAX-ACCESS  read-only
    STATUS      current
    DESCRIPTION "Total failed user-plane IPv4 Reservations"
    ::= { affirmedNetworkContextUimStatisticsEntry 64 }

affirmedNetworkContextUimStatisticsUplaneReserveIpv6Success OBJECT-TYPE
    SYNTAX      ConfdString
    MAX-ACCESS  read-only
    STATUS      current
    DESCRIPTION "Total successful user-plane IPv6 Reservations"
    ::= { affirmedNetworkContextUimStatisticsEntry 65 }

affirmedNetworkContextUimStatisticsUplaneReserveIpv6Failure OBJECT-TYPE
    SYNTAX      ConfdString
    MAX-ACCESS  read-only
    STATUS      current
    DESCRIPTION "Total failed user-plane IPv6 Reservations"
    ::= { affirmedNetworkContextUimStatisticsEntry 66 }

affirmedNetworkContextUimStatisticsUplaneReserveIpv4v6Success OBJECT-TYPE
    SYNTAX      ConfdString
    MAX-ACCESS  read-only
    STATUS      current
    DESCRIPTION "Total successful user-plane IPv4v6 Reservations"
    ::= { affirmedNetworkContextUimStatisticsEntry 67 }

affirmedNetworkContextUimStatisticsUplaneReserveIpv4v6Failure OBJECT-TYPE
    SYNTAX      ConfdString
    MAX-ACCESS  read-only
    STATUS      current
    DESCRIPTION "Total failed user-plane IPv4v6 Reservations"
    ::= { affirmedNetworkContextUimStatisticsEntry 68 }

affirmedNetworkContextUimStatisticsAllocV4TamFailure OBJECT-TYPE
    SYNTAX      ConfdString
    MAX-ACCESS  read-only
    STATUS      current
    DESCRIPTION "Total IPv4 allocation failures with TAM node mismatch reason"
    ::= { affirmedNetworkContextUimStatisticsEntry 69 }

affirmedNetworkContextUimStatisticsAllocV6TamFailure OBJECT-TYPE
    SYNTAX      ConfdString
    MAX-ACCESS  read-only
    STATUS      current
    DESCRIPTION "Total IPv6 allocation failures with TAM node mismatch reason"
    ::= { affirmedNetworkContextUimStatisticsEntry 70 }

affirmedNetworkContextUimStatisticsAllocV4V6TamFailure OBJECT-TYPE
    SYNTAX      ConfdString
    MAX-ACCESS  read-only
    STATUS      current
    DESCRIPTION "Total IPv4v6 allocation failures with TAM node mismatch reason"
    ::= { affirmedNetworkContextUimStatisticsEntry 71 }

affirmedNetworkContextUimStatisticsReserveV4TamFailure OBJECT-TYPE
    SYNTAX      ConfdString
    MAX-ACCESS  read-only
    STATUS      current
    DESCRIPTION "Total IPv4 reservation failures with TAM node mismatch reason"
    ::= { affirmedNetworkContextUimStatisticsEntry 72 }

affirmedNetworkContextUimStatisticsReserveV6TamFailure OBJECT-TYPE
    SYNTAX      ConfdString
    MAX-ACCESS  read-only
    STATUS      current
    DESCRIPTION "Total IPv6 reservation failures with TAM node mismatch reason"
    ::= { affirmedNetworkContextUimStatisticsEntry 73 }

affirmedNetworkContextUimStatisticsReserveV4V6TamFailure OBJECT-TYPE
    SYNTAX      ConfdString
    MAX-ACCESS  read-only
    STATUS      current
    DESCRIPTION "Total IPv4v6 reservation failures with TAM node mismatch reason"
    ::= { affirmedNetworkContextUimStatisticsEntry 74 }

affirmedNetworkContextUimStatisticsHybridV4V6TamFailure OBJECT-TYPE
    SYNTAX      ConfdString
    MAX-ACCESS  read-only
    STATUS      current
    DESCRIPTION "Total IPv4v6 hybrid allocation failures with TAM node mismatch reason"
    ::= { affirmedNetworkContextUimStatisticsEntry 75 }

affirmedNetworkContextUimStatisticsAllocDelegV6TamFailure OBJECT-TYPE
    SYNTAX      ConfdString
    MAX-ACCESS  read-only
    STATUS      current
    DESCRIPTION "Total delegated IPv6 allocation failures with TAM node mismatch reason"
    ::= { affirmedNetworkContextUimStatisticsEntry 76 }

affirmedNetworkContextUimStatisticsReserveDelegV6TamFailure OBJECT-TYPE
    SYNTAX      ConfdString
    MAX-ACCESS  read-only
    STATUS      current
    DESCRIPTION "Total delegated IPv6 reservation failures with TAM node mismatch reason"
    ::= { affirmedNetworkContextUimStatisticsEntry 77 }

affirmedNetworkContextNatSubPoolStatisticsTable OBJECT-TYPE
    SYNTAX      SEQUENCE OF AffirmedNetworkContextNatSubPoolStatisticsEntry
    MAX-ACCESS  not-accessible
    STATUS      deprecated
    DESCRIPTION ""
    ::= { affirmedNetworkcontextMIB 18 }

affirmedNetworkContextNatSubPoolStatisticsEntry OBJECT-TYPE
    SYNTAX      AffirmedNetworkContextNatSubPoolStatisticsEntry
    MAX-ACCESS  not-accessible
    STATUS      deprecated
    DESCRIPTION ""
    INDEX { affirmedNetworkContextName, affirmedNetworkContextNatSubPoolStatisticsName }
        ::= { affirmedNetworkContextNatSubPoolStatisticsTable 1 }

AffirmedNetworkContextNatSubPoolStatisticsEntry ::=
    SEQUENCE {
        affirmedNetworkContextNatSubPoolStatisticsName String,
        affirmedNetworkContextNatSubPoolStatisticsNumAllocIpSuccess ConfdString,
        affirmedNetworkContextNatSubPoolStatisticsNumAllocIpFailure ConfdString,
        affirmedNetworkContextNatSubPoolStatisticsNumAllocPortChunkSuccess ConfdString,
        affirmedNetworkContextNatSubPoolStatisticsNumAllocPortChunkFailure ConfdString,
        affirmedNetworkContextNatSubPoolStatisticsNumDeAllocIpSuccess ConfdString,
        affirmedNetworkContextNatSubPoolStatisticsNumDeAllocIpFailure ConfdString,
        affirmedNetworkContextNatSubPoolStatisticsNumDeAllocPortChunkSuccess ConfdString,
        affirmedNetworkContextNatSubPoolStatisticsNumDeAllocPortChunkFailure ConfdString,
        affirmedNetworkContextNatSubPoolStatisticsNumNatRatioLimitReached ConfdString,
        affirmedNetworkContextNatSubPoolStatisticsNumSessionIpOutOfPortChunks ConfdString
    }

affirmedNetworkContextNatSubPoolStatisticsName OBJECT-TYPE
    SYNTAX      String
    MAX-ACCESS  not-accessible
    STATUS      current
    DESCRIPTION "NAT SubPool Name"
    ::= { affirmedNetworkContextNatSubPoolStatisticsEntry 1 }

affirmedNetworkContextNatSubPoolStatisticsNumAllocIpSuccess OBJECT-TYPE
    SYNTAX      ConfdString
    MAX-ACCESS  read-only
    STATUS      deprecated
    DESCRIPTION "Total IP Address Allocation Success"
    ::= { affirmedNetworkContextNatSubPoolStatisticsEntry 2 }

affirmedNetworkContextNatSubPoolStatisticsNumAllocIpFailure OBJECT-TYPE
    SYNTAX      ConfdString
    MAX-ACCESS  read-only
    STATUS      deprecated
    DESCRIPTION "Total IP Address Allocation Failure"
    ::= { affirmedNetworkContextNatSubPoolStatisticsEntry 3 }

affirmedNetworkContextNatSubPoolStatisticsNumAllocPortChunkSuccess OBJECT-TYPE
    SYNTAX      ConfdString
    MAX-ACCESS  read-only
    STATUS      deprecated
    DESCRIPTION "Total Port Chunk Allocation Success"
    ::= { affirmedNetworkContextNatSubPoolStatisticsEntry 4 }

affirmedNetworkContextNatSubPoolStatisticsNumAllocPortChunkFailure OBJECT-TYPE
    SYNTAX      ConfdString
    MAX-ACCESS  read-only
    STATUS      deprecated
    DESCRIPTION "Total Port Chunk Allocation Failure"
    ::= { affirmedNetworkContextNatSubPoolStatisticsEntry 5 }

affirmedNetworkContextNatSubPoolStatisticsNumDeAllocIpSuccess OBJECT-TYPE
    SYNTAX      ConfdString
    MAX-ACCESS  read-only
    STATUS      deprecated
    DESCRIPTION "Total IP Address Release Success"
    ::= { affirmedNetworkContextNatSubPoolStatisticsEntry 6 }

affirmedNetworkContextNatSubPoolStatisticsNumDeAllocIpFailure OBJECT-TYPE
    SYNTAX      ConfdString
    MAX-ACCESS  read-only
    STATUS      deprecated
    DESCRIPTION "Total IP Address Release Failure"
    ::= { affirmedNetworkContextNatSubPoolStatisticsEntry 7 }

affirmedNetworkContextNatSubPoolStatisticsNumDeAllocPortChunkSuccess OBJECT-TYPE
    SYNTAX      ConfdString
    MAX-ACCESS  read-only
    STATUS      deprecated
    DESCRIPTION "Total Port Chunk Release Success"
    ::= { affirmedNetworkContextNatSubPoolStatisticsEntry 8 }

affirmedNetworkContextNatSubPoolStatisticsNumDeAllocPortChunkFailure OBJECT-TYPE
    SYNTAX      ConfdString
    MAX-ACCESS  read-only
    STATUS      deprecated
    DESCRIPTION "Total Port Chunk Release Failure"
    ::= { affirmedNetworkContextNatSubPoolStatisticsEntry 9 }

affirmedNetworkContextNatSubPoolStatisticsNumNatRatioLimitReached OBJECT-TYPE
    SYNTAX      ConfdString
    MAX-ACCESS  read-only
    STATUS      deprecated
    DESCRIPTION "Nat Ratio Limit Reached Failure"
    ::= { affirmedNetworkContextNatSubPoolStatisticsEntry 10 }

affirmedNetworkContextNatSubPoolStatisticsNumSessionIpOutOfPortChunks OBJECT-TYPE
    SYNTAX      ConfdString
    MAX-ACCESS  read-only
    STATUS      deprecated
    DESCRIPTION "Total IP Out of Port Chunks Failure"
    ::= { affirmedNetworkContextNatSubPoolStatisticsEntry 11 }

affirmedNetworkContextNatPoolStatisticsTable OBJECT-TYPE
    SYNTAX      SEQUENCE OF AffirmedNetworkContextNatPoolStatisticsEntry
    MAX-ACCESS  not-accessible
    STATUS      deprecated
    DESCRIPTION ""
    ::= { affirmedNetworkcontextMIB 34 }

affirmedNetworkContextNatPoolStatisticsEntry OBJECT-TYPE
    SYNTAX      AffirmedNetworkContextNatPoolStatisticsEntry
    MAX-ACCESS  not-accessible
    STATUS      deprecated
    DESCRIPTION ""
    INDEX { affirmedNetworkContextName, affirmedNetworkContextNatPoolStatisticsName }
        ::= { affirmedNetworkContextNatPoolStatisticsTable 1 }

AffirmedNetworkContextNatPoolStatisticsEntry ::=
    SEQUENCE {
        affirmedNetworkContextNatPoolStatisticsName String,
        affirmedNetworkContextNatPoolStatisticsNumConnections ConfdString,
        affirmedNetworkContextNatPoolStatisticsNumConnsPurgedAdminDisabled ConfdString,
        affirmedNetworkContextNatPoolStatisticsNumAllocateNatPortSuccess ConfdString,
        affirmedNetworkContextNatPoolStatisticsNumAllocateNatPortFailure ConfdString,
        affirmedNetworkContextNatPoolStatisticsNumDeallocateNatPortSuccess ConfdString,
        affirmedNetworkContextNatPoolStatisticsNumAllocatePortChunkSuccess ConfdString,
        affirmedNetworkContextNatPoolStatisticsNumAllocateStatisticalPortChunkFailure ConfdString,
        affirmedNetworkContextNatPoolStatisticsNumAllocateGuaranteedNoFreePortsAvailable ConfdString,
        affirmedNetworkContextNatPoolStatisticsNumReleasePortChunkSuccess ConfdString,
        affirmedNetworkContextNatPoolStatisticsNumAllocatePortMaxChunkFailure ConfdString,
        affirmedNetworkContextNatPoolStatisticsNumAllocateGuaranteedPortChunkSuccess ConfdString,
        affirmedNetworkContextNatPoolStatisticsNumReleaseGuaranteedPortChunkSuccess ConfdString,
        affirmedNetworkContextNatPoolStatisticsNumGuaranteedChunkSizeMismatch ConfdString,
        affirmedNetworkContextNatPoolStatisticsNumGuaranteedChunkSubPoolNotFound ConfdString,
        affirmedNetworkContextNatPoolStatisticsNumGuaranteedChunkIpAddrNotFound ConfdString,
        affirmedNetworkContextNatPoolStatisticsNumGuaranteedChunkPortChunkNotFound ConfdString
    }

affirmedNetworkContextNatPoolStatisticsName OBJECT-TYPE
    SYNTAX      String
    MAX-ACCESS  not-accessible
    STATUS      current
    DESCRIPTION "NAT Pool Name"
    ::= { affirmedNetworkContextNatPoolStatisticsEntry 1 }

affirmedNetworkContextNatPoolStatisticsNumConnections OBJECT-TYPE
    SYNTAX      ConfdString
    MAX-ACCESS  read-only
    STATUS      deprecated
    DESCRIPTION "Number of connections"
    ::= { affirmedNetworkContextNatPoolStatisticsEntry 2 }

affirmedNetworkContextNatPoolStatisticsNumConnsPurgedAdminDisabled OBJECT-TYPE
    SYNTAX      ConfdString
    MAX-ACCESS  read-only
    STATUS      deprecated
    DESCRIPTION "Number of connections purged because admin state of NAT pool is modified to disabled"
    ::= { affirmedNetworkContextNatPoolStatisticsEntry 3 }

affirmedNetworkContextNatPoolStatisticsNumAllocateNatPortSuccess OBJECT-TYPE
    SYNTAX      ConfdString
    MAX-ACCESS  read-only
    STATUS      deprecated
    DESCRIPTION "Number of allocated nat port success count"
    ::= { affirmedNetworkContextNatPoolStatisticsEntry 4 }

affirmedNetworkContextNatPoolStatisticsNumAllocateNatPortFailure OBJECT-TYPE
    SYNTAX      ConfdString
    MAX-ACCESS  read-only
    STATUS      deprecated
    DESCRIPTION "Number of allocated nat port failure count"
    ::= { affirmedNetworkContextNatPoolStatisticsEntry 5 }

affirmedNetworkContextNatPoolStatisticsNumDeallocateNatPortSuccess OBJECT-TYPE
    SYNTAX      ConfdString
    MAX-ACCESS  read-only
    STATUS      deprecated
    DESCRIPTION "Number of deallocated nat port success count"
    ::= { affirmedNetworkContextNatPoolStatisticsEntry 6 }

affirmedNetworkContextNatPoolStatisticsNumAllocatePortChunkSuccess OBJECT-TYPE
    SYNTAX      ConfdString
    MAX-ACCESS  read-only
    STATUS      deprecated
    DESCRIPTION "Number of allocate port chunk success count"
    ::= { affirmedNetworkContextNatPoolStatisticsEntry 7 }

affirmedNetworkContextNatPoolStatisticsNumAllocateStatisticalPortChunkFailure OBJECT-TYPE
    SYNTAX      ConfdString
    MAX-ACCESS  read-only
    STATUS      current
    DESCRIPTION "Number of allocate statistical port chunk failure count"
    ::= { affirmedNetworkContextNatPoolStatisticsEntry 8 }

affirmedNetworkContextNatPoolStatisticsNumAllocateGuaranteedNoFreePortsAvailable OBJECT-TYPE
    SYNTAX      ConfdString
    MAX-ACCESS  read-only
    STATUS      deprecated
    DESCRIPTION "Number of allocate guaranted no free ports available count"
    ::= { affirmedNetworkContextNatPoolStatisticsEntry 9 }

affirmedNetworkContextNatPoolStatisticsNumReleasePortChunkSuccess OBJECT-TYPE
    SYNTAX      ConfdString
    MAX-ACCESS  read-only
    STATUS      current
    DESCRIPTION "Number of release port chunk success count"
    ::= { affirmedNetworkContextNatPoolStatisticsEntry 10 }

affirmedNetworkContextNatPoolStatisticsNumAllocatePortMaxChunkFailure OBJECT-TYPE
    SYNTAX      ConfdString
    MAX-ACCESS  read-only
    STATUS      deprecated
    DESCRIPTION "Number of allocate port max chunk failure count"
    ::= { affirmedNetworkContextNatPoolStatisticsEntry 11 }

affirmedNetworkContextNatPoolStatisticsNumAllocateGuaranteedPortChunkSuccess OBJECT-TYPE
    SYNTAX      ConfdString
    MAX-ACCESS  read-only
    STATUS      deprecated
    DESCRIPTION "Number of allocate guaranteed port chunk success count"
    ::= { affirmedNetworkContextNatPoolStatisticsEntry 12 }

affirmedNetworkContextNatPoolStatisticsNumReleaseGuaranteedPortChunkSuccess OBJECT-TYPE
    SYNTAX      ConfdString
    MAX-ACCESS  read-only
    STATUS      deprecated
    DESCRIPTION "Number of release guaranteed port chunk success count"
    ::= { affirmedNetworkContextNatPoolStatisticsEntry 13 }

affirmedNetworkContextNatPoolStatisticsNumGuaranteedChunkSizeMismatch OBJECT-TYPE
    SYNTAX      ConfdString
    MAX-ACCESS  read-only
    STATUS      deprecated
    DESCRIPTION "Number of guaranteed chunk size mismatch count"
    ::= { affirmedNetworkContextNatPoolStatisticsEntry 14 }

affirmedNetworkContextNatPoolStatisticsNumGuaranteedChunkSubPoolNotFound OBJECT-TYPE
    SYNTAX      ConfdString
    MAX-ACCESS  read-only
    STATUS      deprecated
    DESCRIPTION "Number of guaranteed chunk subpool not found count"
    ::= { affirmedNetworkContextNatPoolStatisticsEntry 15 }

affirmedNetworkContextNatPoolStatisticsNumGuaranteedChunkIpAddrNotFound OBJECT-TYPE
    SYNTAX      ConfdString
    MAX-ACCESS  read-only
    STATUS      deprecated
    DESCRIPTION "Number of guaranteed chunk ip address not found count"
    ::= { affirmedNetworkContextNatPoolStatisticsEntry 16 }

affirmedNetworkContextNatPoolStatisticsNumGuaranteedChunkPortChunkNotFound OBJECT-TYPE
    SYNTAX      ConfdString
    MAX-ACCESS  read-only
    STATUS      deprecated
    DESCRIPTION "Number of guaranteed chunk port chunk not found count"
    ::= { affirmedNetworkContextNatPoolStatisticsEntry 17 }

affirmedNetworkContextSummaryTable OBJECT-TYPE
    SYNTAX      SEQUENCE OF AffirmedNetworkContextSummaryEntry
    MAX-ACCESS  not-accessible
    STATUS      current
    DESCRIPTION ""
    ::= { affirmedNetworkcontextMIB 37 }

affirmedNetworkContextSummaryEntry OBJECT-TYPE
    SYNTAX      AffirmedNetworkContextSummaryEntry
    MAX-ACCESS  not-accessible
    STATUS      current
    DESCRIPTION ""
    INDEX { affirmedNetworkContextName, affirmedNetworkContextSummarySlot }
        ::= { affirmedNetworkContextSummaryTable 1 }

AffirmedNetworkContextSummaryEntry ::=
    SEQUENCE {
        affirmedNetworkContextSummarySlot Unsigned32,
        affirmedNetworkContextSummaryIndex Unsigned32,
        affirmedNetworkContextSummaryHostCsm Unsigned32
    }

affirmedNetworkContextSummarySlot OBJECT-TYPE
    SYNTAX      Unsigned32
    MAX-ACCESS  not-accessible
    STATUS      current
    DESCRIPTION "Slot Id"
    ::= { affirmedNetworkContextSummaryEntry 1 }

affirmedNetworkContextSummaryIndex OBJECT-TYPE
    SYNTAX      Unsigned32
    MAX-ACCESS  read-only
    STATUS      current
    DESCRIPTION "Network-context Id"
    ::= { affirmedNetworkContextSummaryEntry 2 }

affirmedNetworkContextSummaryHostCsm OBJECT-TYPE
    SYNTAX      Unsigned32
    MAX-ACCESS  read-only
    STATUS      current
    DESCRIPTION "Hosted CSM"
    ::= { affirmedNetworkContextSummaryEntry 3 }

END

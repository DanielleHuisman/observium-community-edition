AFFIRMED-PERFSTATMGMT-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedPerfstatmgmtMIB MODULE-IDENTITY
    ORGANIZATION "Affirmed Networks, Inc."
    CONTACT-INFO "Affirmed Networks, Inc. 35 Nagog Park, Acton, MA, USA"
    DESCRIPTION ""
    ::= { 1 3 6 1 4 1 37963 10 6 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedPerfstatmgmt OBJECT IDENTIFIER ::= { affirmedPerfstatmgmtMIB 1 }

affirmedPerfstatmgmtTableStatusTable OBJECT-TYPE
    SYNTAX      SEQUENCE OF AffirmedPerfstatmgmtTableStatusEntry
    MAX-ACCESS  not-accessible
    STATUS      current
    DESCRIPTION ""
    ::= { affirmedPerfstatmgmt 1 }

affirmedPerfstatmgmtTableStatusEntry OBJECT-TYPE
    SYNTAX      AffirmedPerfstatmgmtTableStatusEntry
    MAX-ACCESS  not-accessible
    STATUS      current
    DESCRIPTION ""
    INDEX { affirmedPerfstatmgmtTableStatusName }
        ::= { affirmedPerfstatmgmtTableStatusTable 1 }

AffirmedPerfstatmgmtTableStatusEntry ::=
    SEQUENCE {
        affirmedPerfstatmgmtTableStatusName String,
        affirmedPerfstatmgmtTableStatusCollectionStartTime String,
        affirmedPerfstatmgmtTableStatusNextCollectionTime String,
        affirmedPerfstatmgmtTableStatusCollectionAttempts Unsigned32,
        affirmedPerfstatmgmtTableStatusCollectionSuccess Unsigned32,
        affirmedPerfstatmgmtTableStatusCollectionPartial Unsigned32,
        affirmedPerfstatmgmtTableStatusCollectionFailure Unsigned32,
        affirmedPerfstatmgmtTableStatusCollectionOutstanding Unsigned32,
        affirmedPerfstatmgmtTableStatusAvgCollectionTime ConfdString,
        affirmedPerfstatmgmtTableStatusMaxCollectionTime ConfdString,
        affirmedPerfstatmgmtTableStatusMinCollectionTime ConfdString,
        affirmedPerfstatmgmtTableStatusAvgNumRowsPerCollection String,
        affirmedPerfstatmgmtTableStatusMaxNumRowsPerCollection Unsigned32,
        affirmedPerfstatmgmtTableStatusMinNumRowsPerCollection Unsigned32
    }

affirmedPerfstatmgmtTableStatusName OBJECT-TYPE
    SYNTAX      String
    MAX-ACCESS  not-accessible
    STATUS      current
    DESCRIPTION ""
    ::= { affirmedPerfstatmgmtTableStatusEntry 1 }

affirmedPerfstatmgmtTableStatusCollectionStartTime OBJECT-TYPE
    SYNTAX      String
    MAX-ACCESS  read-only
    STATUS      current
    DESCRIPTION ""
    ::= { affirmedPerfstatmgmtTableStatusEntry 2 }

affirmedPerfstatmgmtTableStatusNextCollectionTime OBJECT-TYPE
    SYNTAX      String
    MAX-ACCESS  read-only
    STATUS      current
    DESCRIPTION ""
    ::= { affirmedPerfstatmgmtTableStatusEntry 3 }

affirmedPerfstatmgmtTableStatusCollectionAttempts OBJECT-TYPE
    SYNTAX      Unsigned32
    MAX-ACCESS  read-only
    STATUS      current
    DESCRIPTION ""
    ::= { affirmedPerfstatmgmtTableStatusEntry 4 }

affirmedPerfstatmgmtTableStatusCollectionSuccess OBJECT-TYPE
    SYNTAX      Unsigned32
    MAX-ACCESS  read-only
    STATUS      current
    DESCRIPTION ""
    ::= { affirmedPerfstatmgmtTableStatusEntry 5 }

affirmedPerfstatmgmtTableStatusCollectionPartial OBJECT-TYPE
    SYNTAX      Unsigned32
    MAX-ACCESS  read-only
    STATUS      current
    DESCRIPTION ""
    ::= { affirmedPerfstatmgmtTableStatusEntry 6 }

affirmedPerfstatmgmtTableStatusCollectionFailure OBJECT-TYPE
    SYNTAX      Unsigned32
    MAX-ACCESS  read-only
    STATUS      current
    DESCRIPTION ""
    ::= { affirmedPerfstatmgmtTableStatusEntry 7 }

affirmedPerfstatmgmtTableStatusCollectionOutstanding OBJECT-TYPE
    SYNTAX      Unsigned32
    MAX-ACCESS  read-only
    STATUS      current
    DESCRIPTION ""
    ::= { affirmedPerfstatmgmtTableStatusEntry 8 }

affirmedPerfstatmgmtTableStatusAvgCollectionTime OBJECT-TYPE
    SYNTAX      ConfdString
    MAX-ACCESS  read-only
    STATUS      current
    DESCRIPTION ""
    ::= { affirmedPerfstatmgmtTableStatusEntry 9 }

affirmedPerfstatmgmtTableStatusMaxCollectionTime OBJECT-TYPE
    SYNTAX      ConfdString
    MAX-ACCESS  read-only
    STATUS      current
    DESCRIPTION ""
    ::= { affirmedPerfstatmgmtTableStatusEntry 10 }

affirmedPerfstatmgmtTableStatusMinCollectionTime OBJECT-TYPE
    SYNTAX      ConfdString
    MAX-ACCESS  read-only
    STATUS      current
    DESCRIPTION ""
    ::= { affirmedPerfstatmgmtTableStatusEntry 11 }

affirmedPerfstatmgmtTableStatusAvgNumRowsPerCollection OBJECT-TYPE
    SYNTAX      String
    MAX-ACCESS  read-only
    STATUS      current
    DESCRIPTION ""
    ::= { affirmedPerfstatmgmtTableStatusEntry 12 }

affirmedPerfstatmgmtTableStatusMaxNumRowsPerCollection OBJECT-TYPE
    SYNTAX      Unsigned32
    MAX-ACCESS  read-only
    STATUS      current
    DESCRIPTION ""
    ::= { affirmedPerfstatmgmtTableStatusEntry 13 }

affirmedPerfstatmgmtTableStatusMinNumRowsPerCollection OBJECT-TYPE
    SYNTAX      Unsigned32
    MAX-ACCESS  read-only
    STATUS      current
    DESCRIPTION ""
    ::= { affirmedPerfstatmgmtTableStatusEntry 14 }

END

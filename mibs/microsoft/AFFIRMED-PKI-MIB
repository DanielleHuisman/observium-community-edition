AFFIRMED-PKI-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedPkiMIB MODULE-IDENTITY
    ORGANIZATION "Affirmed Networks, Inc."
    CONTACT-INFO "Affirmed Networks, Inc. 35 Nagog Park, Acton, MA, USA"
    DESCRIPTION ""
    ::= { 1 3 6 1 4 1 37963 10 25 }

String ::= TEXTUAL-CONVENTION
    DISPLAY-HINT "1t"
    STATUS      current
    DESCRIPTION "xs:string"
    SYNTAX      OCTET STRING

affirmedPki OBJECT IDENTIFIER ::= { affirmedPkiMIB 1 }

affirmedPkiSsh OBJECT IDENTIFIER ::= { affirmedPki 2 }

affirmedPkiObjectsTable OBJECT-TYPE
    SYNTAX      SEQUENCE OF AffirmedPkiObjectsEntry
    MAX-ACCESS  not-accessible
    STATUS      current
    DESCRIPTION ""
    ::= { affirmedPki 1 }

affirmedPkiObjectsEntry OBJECT-TYPE
    SYNTAX      AffirmedPkiObjectsEntry
    MAX-ACCESS  not-accessible
    STATUS      current
    DESCRIPTION ""
    INDEX { affirmedPkiObjectsType, affirmedPkiObjectsName, affirmedPkiObjectsState }
        ::= { affirmedPkiObjectsTable 1 }

AffirmedPkiObjectsEntry ::=
    SEQUENCE {
        affirmedPkiObjectsType INTEGER,
        affirmedPkiObjectsName String,
        affirmedPkiObjectsState INTEGER,
        affirmedPkiObjectsModified String,
        affirmedPkiObjectsEncoding INTEGER,
        affirmedPkiObjectsFormat INTEGER,
        affirmedPkiObjectsDescription String
    }

affirmedPkiObjectsType OBJECT-TYPE
    SYNTAX      INTEGER {public(0),private(1),ca(2),tls-ca(3),tls-server(4),tfd(5),epdg(6),user(7),host(10),sendd(11),calea(12),imsi(13)}
    MAX-ACCESS  not-accessible
    STATUS      current
    DESCRIPTION ""
    ::= { affirmedPkiObjectsEntry 1 }

affirmedPkiObjectsName OBJECT-TYPE
    SYNTAX      String
    MAX-ACCESS  not-accessible
    STATUS      current
    DESCRIPTION ""
    ::= { affirmedPkiObjectsEntry 2 }

affirmedPkiObjectsState OBJECT-TYPE
    SYNTAX      INTEGER {ready(0),invalid(1),updating(2),pending(3),adding(4)}
    MAX-ACCESS  not-accessible
    STATUS      current
    DESCRIPTION ""
    ::= { affirmedPkiObjectsEntry 3 }

affirmedPkiObjectsModified OBJECT-TYPE
    SYNTAX      String
    MAX-ACCESS  read-only
    STATUS      current
    DESCRIPTION ""
    ::= { affirmedPkiObjectsEntry 4 }

affirmedPkiObjectsEncoding OBJECT-TYPE
    SYNTAX      INTEGER {unknown(0),pem(1),ber(2),ssh(3)}
    MAX-ACCESS  read-only
    STATUS      current
    DESCRIPTION ""
    ::= { affirmedPkiObjectsEntry 5 }

affirmedPkiObjectsFormat OBJECT-TYPE
    SYNTAX      INTEGER {unknown(0),x509(1),x509crl(2),x509stack(3),pubkey(4),prvkey(5),ssh-pub(6),ssh-cert(7),ssh-krl(8),ssh-pvt(9)}
    MAX-ACCESS  read-only
    STATUS      current
    DESCRIPTION ""
    ::= { affirmedPkiObjectsEntry 6 }

affirmedPkiObjectsDescription OBJECT-TYPE
    SYNTAX      String
    MAX-ACCESS  read-only
    STATUS      current
    DESCRIPTION ""
    ::= { affirmedPkiObjectsEntry 7 }

affirmedPkiSshSummaryTable OBJECT-TYPE
    SYNTAX      SEQUENCE OF AffirmedPkiSshSummaryEntry
    MAX-ACCESS  not-accessible
    STATUS      current
    DESCRIPTION ""
    ::= { affirmedPkiSsh 1 }

affirmedPkiSshSummaryEntry OBJECT-TYPE
    SYNTAX      AffirmedPkiSshSummaryEntry
    MAX-ACCESS  not-accessible
    STATUS      current
    DESCRIPTION ""
    INDEX { affirmedPkiSshSummaryGroup, affirmedPkiSshSummaryUser }
        ::= { affirmedPkiSshSummaryTable 1 }

AffirmedPkiSshSummaryEntry ::=
    SEQUENCE {
        affirmedPkiSshSummaryGroup String,
        affirmedPkiSshSummaryUser String,
        affirmedPkiSshSummaryDescription String
    }

affirmedPkiSshSummaryGroup OBJECT-TYPE
    SYNTAX      String
    MAX-ACCESS  not-accessible
    STATUS      current
    DESCRIPTION ""
    ::= { affirmedPkiSshSummaryEntry 1 }

affirmedPkiSshSummaryUser OBJECT-TYPE
    SYNTAX      String
    MAX-ACCESS  not-accessible
    STATUS      current
    DESCRIPTION ""
    ::= { affirmedPkiSshSummaryEntry 2 }

affirmedPkiSshSummaryDescription OBJECT-TYPE
    SYNTAX      String
    MAX-ACCESS  read-only
    STATUS      current
    DESCRIPTION ""
    ::= { affirmedPkiSshSummaryEntry 3 }

END

AFFIRMED-SECURITY-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

affirmedSecurityMIB MODULE-IDENTITY
    ORGANIZATION "Affirmed Networks, Inc."
    CONTACT-INFO "Affirmed Networks, Inc. 35 Nagog Park, Acton, MA, USA"
    DESCRIPTION ""
    ::= { 1 3 6 1 4 1 37963 10 12 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

affirmedSecurity OBJECT IDENTIFIER ::= { affirmedSecurityMIB 1 }

affirmedSecurityHistory OBJECT IDENTIFIER ::= { affirmedSecurity 2 }

affirmedSecurityStatistics OBJECT IDENTIFIER ::= { affirmedSecurity 1 }

affirmedSecurityStatisticsCpu-level OBJECT IDENTIFIER ::= { affirmedSecurityStatistics 5 }

affirmedSecurityStatisticsDebug OBJECT IDENTIFIER ::= { affirmedSecurityStatistics 7 }

affirmedSecurityStatisticsIkeMessage OBJECT IDENTIFIER ::= { affirmedSecurityStatistics 9 }

affirmedSecurityHistoryIkeFailuresMultiSpmTable OBJECT-TYPE
    SYNTAX      SEQUENCE OF AffirmedSecurityHistoryIkeFailuresMultiSpmEntry
    MAX-ACCESS  not-accessible
    STATUS      current
    DESCRIPTION ""
    ::= { affirmedSecurityHistory 5 }

affirmedSecurityHistoryIkeFailuresMultiSpmEntry OBJECT-TYPE
    SYNTAX      AffirmedSecurityHistoryIkeFailuresMultiSpmEntry
    MAX-ACCESS  not-accessible
    STATUS      current
    DESCRIPTION ""
    INDEX { affirmedSecurityHistoryIkeFailuresMultiSpmNetworkContext, affirmedSecurityHistoryIkeFailuresMultiSpmServiceName, affirmedSecurityHistoryIkeFailuresMultiSpmId }
        ::= { affirmedSecurityHistoryIkeFailuresMultiSpmTable 1 }

AffirmedSecurityHistoryIkeFailuresMultiSpmEntry ::=
    SEQUENCE {
        affirmedSecurityHistoryIkeFailuresMultiSpmNetworkContext String,
        affirmedSecurityHistoryIkeFailuresMultiSpmServiceName String,
        affirmedSecurityHistoryIkeFailuresMultiSpmId Unsigned32,
        affirmedSecurityHistoryIkeFailuresMultiSpmTimestamp String,
        affirmedSecurityHistoryIkeFailuresMultiSpmMode String,
        affirmedSecurityHistoryIkeFailuresMultiSpmIkeVersion String,
        affirmedSecurityHistoryIkeFailuresMultiSpmLocalAddress String,
        affirmedSecurityHistoryIkeFailuresMultiSpmLocalPort String,
        affirmedSecurityHistoryIkeFailuresMultiSpmLocalId String,
        affirmedSecurityHistoryIkeFailuresMultiSpmRemoteAddress String,
        affirmedSecurityHistoryIkeFailuresMultiSpmRemotePort String,
        affirmedSecurityHistoryIkeFailuresMultiSpmRemoteId String,
        affirmedSecurityHistoryIkeFailuresMultiSpmErrorMsg String,
        affirmedSecurityHistoryIkeFailuresMultiSpmErrorId String,
        affirmedSecurityHistoryIkeFailuresMultiSpmErrorReason String,
        affirmedSecurityHistoryIkeFailuresMultiSpmTunnelName String
    }

affirmedSecurityHistoryIkeFailuresMultiSpmNetworkContext OBJECT-TYPE
    SYNTAX      String
    MAX-ACCESS  not-accessible
    STATUS      current
    DESCRIPTION "Network Context Name"
    ::= { affirmedSecurityHistoryIkeFailuresMultiSpmEntry 1 }

affirmedSecurityHistoryIkeFailuresMultiSpmServiceName OBJECT-TYPE
    SYNTAX      String
    MAX-ACCESS  not-accessible
    STATUS      current
    DESCRIPTION "Task service name"
    ::= { affirmedSecurityHistoryIkeFailuresMultiSpmEntry 2 }

affirmedSecurityHistoryIkeFailuresMultiSpmId OBJECT-TYPE
    SYNTAX      Unsigned32
    MAX-ACCESS  not-accessible
    STATUS      current
    DESCRIPTION "Internal Entry Identifier"
    ::= { affirmedSecurityHistoryIkeFailuresMultiSpmEntry 3 }

affirmedSecurityHistoryIkeFailuresMultiSpmTimestamp OBJECT-TYPE
    SYNTAX      String
    MAX-ACCESS  read-only
    STATUS      current
    DESCRIPTION "Timestamp"
    ::= { affirmedSecurityHistoryIkeFailuresMultiSpmEntry 4 }

affirmedSecurityHistoryIkeFailuresMultiSpmMode OBJECT-TYPE
    SYNTAX      String
    MAX-ACCESS  read-only
    STATUS      current
    DESCRIPTION "Mode"
    ::= { affirmedSecurityHistoryIkeFailuresMultiSpmEntry 5 }

affirmedSecurityHistoryIkeFailuresMultiSpmIkeVersion OBJECT-TYPE
    SYNTAX      String
    MAX-ACCESS  read-only
    STATUS      current
    DESCRIPTION "IKE version"
    ::= { affirmedSecurityHistoryIkeFailuresMultiSpmEntry 6 }

affirmedSecurityHistoryIkeFailuresMultiSpmLocalAddress OBJECT-TYPE
    SYNTAX      String
    MAX-ACCESS  read-only
    STATUS      current
    DESCRIPTION "Address Of Local Endpoint"
    ::= { affirmedSecurityHistoryIkeFailuresMultiSpmEntry 7 }

affirmedSecurityHistoryIkeFailuresMultiSpmLocalPort OBJECT-TYPE
    SYNTAX      String
    MAX-ACCESS  read-only
    STATUS      current
    DESCRIPTION "Port Number Of Local Endpoint"
    ::= { affirmedSecurityHistoryIkeFailuresMultiSpmEntry 8 }

affirmedSecurityHistoryIkeFailuresMultiSpmLocalId OBJECT-TYPE
    SYNTAX      String
    MAX-ACCESS  read-only
    STATUS      current
    DESCRIPTION "Local Endpoint Identifier"
    ::= { affirmedSecurityHistoryIkeFailuresMultiSpmEntry 9 }

affirmedSecurityHistoryIkeFailuresMultiSpmRemoteAddress OBJECT-TYPE
    SYNTAX      String
    MAX-ACCESS  read-only
    STATUS      current
    DESCRIPTION "Address Of Remote Endpoint"
    ::= { affirmedSecurityHistoryIkeFailuresMultiSpmEntry 10 }

affirmedSecurityHistoryIkeFailuresMultiSpmRemotePort OBJECT-TYPE
    SYNTAX      String
    MAX-ACCESS  read-only
    STATUS      current
    DESCRIPTION "Port Number Of Remote Endpoint"
    ::= { affirmedSecurityHistoryIkeFailuresMultiSpmEntry 11 }

affirmedSecurityHistoryIkeFailuresMultiSpmRemoteId OBJECT-TYPE
    SYNTAX      String
    MAX-ACCESS  read-only
    STATUS      current
    DESCRIPTION "Remote Endpoint Identifier"
    ::= { affirmedSecurityHistoryIkeFailuresMultiSpmEntry 12 }

affirmedSecurityHistoryIkeFailuresMultiSpmErrorMsg OBJECT-TYPE
    SYNTAX      String
    MAX-ACCESS  read-only
    STATUS      current
    DESCRIPTION "Error Message String"
    ::= { affirmedSecurityHistoryIkeFailuresMultiSpmEntry 13 }

affirmedSecurityHistoryIkeFailuresMultiSpmErrorId OBJECT-TYPE
    SYNTAX      String
    MAX-ACCESS  read-only
    STATUS      current
    DESCRIPTION "Error Identifier"
    ::= { affirmedSecurityHistoryIkeFailuresMultiSpmEntry 14 }

affirmedSecurityHistoryIkeFailuresMultiSpmErrorReason OBJECT-TYPE
    SYNTAX      String
    MAX-ACCESS  read-only
    STATUS      current
    DESCRIPTION "Error Reason (if known)"
    ::= { affirmedSecurityHistoryIkeFailuresMultiSpmEntry 15 }

affirmedSecurityHistoryIkeFailuresMultiSpmTunnelName OBJECT-TYPE
    SYNTAX      String
    MAX-ACCESS  read-only
    STATUS      current
    DESCRIPTION "Security Tunnel Name"
    ::= { affirmedSecurityHistoryIkeFailuresMultiSpmEntry 16 }

affirmedSecurityHistoryIkeFailuresTable OBJECT-TYPE
    SYNTAX      SEQUENCE OF AffirmedSecurityHistoryIkeFailuresEntry
    MAX-ACCESS  not-accessible
    STATUS      deprecated
    DESCRIPTION ""
    ::= { affirmedSecurityHistory 1 }

affirmedSecurityHistoryIkeFailuresEntry OBJECT-TYPE
    SYNTAX      AffirmedSecurityHistoryIkeFailuresEntry
    MAX-ACCESS  not-accessible
    STATUS      deprecated
    DESCRIPTION ""
    INDEX { affirmedSecurityHistoryIkeFailuresNetworkContext, affirmedSecurityHistoryIkeFailuresId }
        ::= { affirmedSecurityHistoryIkeFailuresTable 1 }

AffirmedSecurityHistoryIkeFailuresEntry ::=
    SEQUENCE {
        affirmedSecurityHistoryIkeFailuresNetworkContext String,
        affirmedSecurityHistoryIkeFailuresId Unsigned32,
        affirmedSecurityHistoryIkeFailuresTimestamp String,
        affirmedSecurityHistoryIkeFailuresMode String,
        affirmedSecurityHistoryIkeFailuresIkeVersion String,
        affirmedSecurityHistoryIkeFailuresLocalAddress String,
        affirmedSecurityHistoryIkeFailuresLocalPort String,
        affirmedSecurityHistoryIkeFailuresLocalId String,
        affirmedSecurityHistoryIkeFailuresRemoteAddress String,
        affirmedSecurityHistoryIkeFailuresRemotePort String,
        affirmedSecurityHistoryIkeFailuresRemoteId String,
        affirmedSecurityHistoryIkeFailuresErrorMsg String,
        affirmedSecurityHistoryIkeFailuresErrorId String,
        affirmedSecurityHistoryIkeFailuresErrorReason String,
        affirmedSecurityHistoryIkeFailuresSecondaryErrorReason INTEGER
    }

affirmedSecurityHistoryIkeFailuresNetworkContext OBJECT-TYPE
    SYNTAX      String
    MAX-ACCESS  not-accessible
    STATUS      current
    DESCRIPTION "Network Context Name"
    ::= { affirmedSecurityHistoryIkeFailuresEntry 1 }

affirmedSecurityHistoryIkeFailuresId OBJECT-TYPE
    SYNTAX      Unsigned32
    MAX-ACCESS  not-accessible
    STATUS      current
    DESCRIPTION "Internal Entry Identifier"
    ::= { affirmedSecurityHistoryIkeFailuresEntry 2 }

affirmedSecurityHistoryIkeFailuresTimestamp OBJECT-TYPE
    SYNTAX      String
    MAX-ACCESS  read-only
    STATUS      current
    DESCRIPTION "Timestamp"
    ::= { affirmedSecurityHistoryIkeFailuresEntry 3 }

affirmedSecurityHistoryIkeFailuresMode OBJECT-TYPE
    SYNTAX      String
    MAX-ACCESS  read-only
    STATUS      current
    DESCRIPTION "Mode"
    ::= { affirmedSecurityHistoryIkeFailuresEntry 4 }

affirmedSecurityHistoryIkeFailuresIkeVersion OBJECT-TYPE
    SYNTAX      String
    MAX-ACCESS  read-only
    STATUS      current
    DESCRIPTION "IKE version"
    ::= { affirmedSecurityHistoryIkeFailuresEntry 5 }

affirmedSecurityHistoryIkeFailuresLocalAddress OBJECT-TYPE
    SYNTAX      String
    MAX-ACCESS  read-only
    STATUS      current
    DESCRIPTION "Address Of Local Endpoint"
    ::= { affirmedSecurityHistoryIkeFailuresEntry 6 }

affirmedSecurityHistoryIkeFailuresLocalPort OBJECT-TYPE
    SYNTAX      String
    MAX-ACCESS  read-only
    STATUS      current
    DESCRIPTION "Port Number Of Local Endpoint"
    ::= { affirmedSecurityHistoryIkeFailuresEntry 7 }

affirmedSecurityHistoryIkeFailuresLocalId OBJECT-TYPE
    SYNTAX      String
    MAX-ACCESS  read-only
    STATUS      current
    DESCRIPTION "Local Endpoint Identifier"
    ::= { affirmedSecurityHistoryIkeFailuresEntry 8 }

affirmedSecurityHistoryIkeFailuresRemoteAddress OBJECT-TYPE
    SYNTAX      String
    MAX-ACCESS  read-only
    STATUS      current
    DESCRIPTION "Address Of Remote Endpoint"
    ::= { affirmedSecurityHistoryIkeFailuresEntry 9 }

affirmedSecurityHistoryIkeFailuresRemotePort OBJECT-TYPE
    SYNTAX      String
    MAX-ACCESS  read-only
    STATUS      current
    DESCRIPTION "Port Number Of Remote Endpoint"
    ::= { affirmedSecurityHistoryIkeFailuresEntry 10 }

affirmedSecurityHistoryIkeFailuresRemoteId OBJECT-TYPE
    SYNTAX      String
    MAX-ACCESS  read-only
    STATUS      current
    DESCRIPTION "Remote Endpoint Identifier"
    ::= { affirmedSecurityHistoryIkeFailuresEntry 11 }

affirmedSecurityHistoryIkeFailuresErrorMsg OBJECT-TYPE
    SYNTAX      String
    MAX-ACCESS  read-only
    STATUS      current
    DESCRIPTION "Error Message String"
    ::= { affirmedSecurityHistoryIkeFailuresEntry 12 }

affirmedSecurityHistoryIkeFailuresErrorId OBJECT-TYPE
    SYNTAX      String
    MAX-ACCESS  read-only
    STATUS      current
    DESCRIPTION "Error Identifier"
    ::= { affirmedSecurityHistoryIkeFailuresEntry 13 }

affirmedSecurityHistoryIkeFailuresErrorReason OBJECT-TYPE
    SYNTAX      String
    MAX-ACCESS  read-only
    STATUS      current
    DESCRIPTION "Error Reason (if known)"
    ::= { affirmedSecurityHistoryIkeFailuresEntry 14 }

affirmedSecurityHistoryIkeFailuresSecondaryErrorReason OBJECT-TYPE
    SYNTAX      INTEGER {none(0),audit-failure(1),aaa-not-available(2),aaa-timeout(3),aaa-failure(4),pgw-no-response(5),gw-failure(6),ip-address-not-available(7),re-authentication(8),gw-initiated(9),unspecified(10),re-attach(11),gw-timeout(12),invalid-remote-identity(13),missing-local-identity(14),no-matching-epdg(15),internal-error(16),gw-not-found(17),identity-decryption-failed(18)}
    MAX-ACCESS  read-only
    STATUS      current
    DESCRIPTION "Secondary Error Reason (if known)"
    ::= { affirmedSecurityHistoryIkeFailuresEntry 15 }

affirmedSecurityHistoryIkeNegotiationsMultiSpmTable OBJECT-TYPE
    SYNTAX      SEQUENCE OF AffirmedSecurityHistoryIkeNegotiationsMultiSpmEntry
    MAX-ACCESS  not-accessible
    STATUS      current
    DESCRIPTION ""
    ::= { affirmedSecurityHistory 6 }

affirmedSecurityHistoryIkeNegotiationsMultiSpmEntry OBJECT-TYPE
    SYNTAX      AffirmedSecurityHistoryIkeNegotiationsMultiSpmEntry
    MAX-ACCESS  not-accessible
    STATUS      current
    DESCRIPTION ""
    INDEX { affirmedSecurityHistoryIkeNegotiationsMultiSpmNetworkContext, affirmedSecurityHistoryIkeNegotiationsMultiSpmServiceName, affirmedSecurityHistoryIkeNegotiationsMultiSpmId }
        ::= { affirmedSecurityHistoryIkeNegotiationsMultiSpmTable 1 }

AffirmedSecurityHistoryIkeNegotiationsMultiSpmEntry ::=
    SEQUENCE {
        affirmedSecurityHistoryIkeNegotiationsMultiSpmNetworkContext String,
        affirmedSecurityHistoryIkeNegotiationsMultiSpmServiceName String,
        affirmedSecurityHistoryIkeNegotiationsMultiSpmId Unsigned32,
        affirmedSecurityHistoryIkeNegotiationsMultiSpmTimestamp String,
        affirmedSecurityHistoryIkeNegotiationsMultiSpmMode String,
        affirmedSecurityHistoryIkeNegotiationsMultiSpmIkeVersion String,
        affirmedSecurityHistoryIkeNegotiationsMultiSpmLocalAuthMethod String,
        affirmedSecurityHistoryIkeNegotiationsMultiSpmRemoteAuthMethod String,
        affirmedSecurityHistoryIkeNegotiationsMultiSpmIkeAlgorithms String,
        affirmedSecurityHistoryIkeNegotiationsMultiSpmDhGroups String,
        affirmedSecurityHistoryIkeNegotiationsMultiSpmLocalAddress String,
        affirmedSecurityHistoryIkeNegotiationsMultiSpmLocalPort String,
        affirmedSecurityHistoryIkeNegotiationsMultiSpmLocalId String,
        affirmedSecurityHistoryIkeNegotiationsMultiSpmRemoteAddress String,
        affirmedSecurityHistoryIkeNegotiationsMultiSpmRemotePort String,
        affirmedSecurityHistoryIkeNegotiationsMultiSpmRemoteId String,
        affirmedSecurityHistoryIkeNegotiationsMultiSpmInitiatorSpi String,
        affirmedSecurityHistoryIkeNegotiationsMultiSpmResponderSpi String,
        affirmedSecurityHistoryIkeNegotiationsMultiSpmLocalLifetime String,
        affirmedSecurityHistoryIkeNegotiationsMultiSpmTunnelName String
    }

affirmedSecurityHistoryIkeNegotiationsMultiSpmNetworkContext OBJECT-TYPE
    SYNTAX      String
    MAX-ACCESS  not-accessible
    STATUS      current
    DESCRIPTION "Network Context Name"
    ::= { affirmedSecurityHistoryIkeNegotiationsMultiSpmEntry 1 }

affirmedSecurityHistoryIkeNegotiationsMultiSpmServiceName OBJECT-TYPE
    SYNTAX      String
    MAX-ACCESS  not-accessible
    STATUS      current
    DESCRIPTION "Task service name"
    ::= { affirmedSecurityHistoryIkeNegotiationsMultiSpmEntry 2 }

affirmedSecurityHistoryIkeNegotiationsMultiSpmId OBJECT-TYPE
    SYNTAX      Unsigned32
    MAX-ACCESS  not-accessible
    STATUS      current
    DESCRIPTION "Internal Entry Identifier"
    ::= { affirmedSecurityHistoryIkeNegotiationsMultiSpmEntry 3 }

affirmedSecurityHistoryIkeNegotiationsMultiSpmTimestamp OBJECT-TYPE
    SYNTAX      String
    MAX-ACCESS  read-only
    STATUS      current
    DESCRIPTION "Timestamp"
    ::= { affirmedSecurityHistoryIkeNegotiationsMultiSpmEntry 4 }

affirmedSecurityHistoryIkeNegotiationsMultiSpmMode OBJECT-TYPE
    SYNTAX      String
    MAX-ACCESS  read-only
    STATUS      current
    DESCRIPTION "Mode"
    ::= { affirmedSecurityHistoryIkeNegotiationsMultiSpmEntry 5 }

affirmedSecurityHistoryIkeNegotiationsMultiSpmIkeVersion OBJECT-TYPE
    SYNTAX      String
    MAX-ACCESS  read-only
    STATUS      current
    DESCRIPTION "IKE version"
    ::= { affirmedSecurityHistoryIkeNegotiationsMultiSpmEntry 6 }

affirmedSecurityHistoryIkeNegotiationsMultiSpmLocalAuthMethod OBJECT-TYPE
    SYNTAX      String
    MAX-ACCESS  read-only
    STATUS      current
    DESCRIPTION "Local Authentication Method"
    ::= { affirmedSecurityHistoryIkeNegotiationsMultiSpmEntry 7 }

affirmedSecurityHistoryIkeNegotiationsMultiSpmRemoteAuthMethod OBJECT-TYPE
    SYNTAX      String
    MAX-ACCESS  read-only
    STATUS      current
    DESCRIPTION "Remote Authentication Method"
    ::= { affirmedSecurityHistoryIkeNegotiationsMultiSpmEntry 8 }

affirmedSecurityHistoryIkeNegotiationsMultiSpmIkeAlgorithms OBJECT-TYPE
    SYNTAX      String
    MAX-ACCESS  read-only
    STATUS      current
    DESCRIPTION "IKE Algorithms Employed"
    ::= { affirmedSecurityHistoryIkeNegotiationsMultiSpmEntry 9 }

affirmedSecurityHistoryIkeNegotiationsMultiSpmDhGroups OBJECT-TYPE
    SYNTAX      String
    MAX-ACCESS  read-only
    STATUS      current
    DESCRIPTION "Diffie Hellman Groups"
    ::= { affirmedSecurityHistoryIkeNegotiationsMultiSpmEntry 10 }

affirmedSecurityHistoryIkeNegotiationsMultiSpmLocalAddress OBJECT-TYPE
    SYNTAX      String
    MAX-ACCESS  read-only
    STATUS      current
    DESCRIPTION "Address Of Local Endpoint"
    ::= { affirmedSecurityHistoryIkeNegotiationsMultiSpmEntry 11 }

affirmedSecurityHistoryIkeNegotiationsMultiSpmLocalPort OBJECT-TYPE
    SYNTAX      String
    MAX-ACCESS  read-only
    STATUS      current
    DESCRIPTION "Port Number Of Local Endpoint"
    ::= { affirmedSecurityHistoryIkeNegotiationsMultiSpmEntry 12 }

affirmedSecurityHistoryIkeNegotiationsMultiSpmLocalId OBJECT-TYPE
    SYNTAX      String
    MAX-ACCESS  read-only
    STATUS      current
    DESCRIPTION "Local Endpoint Identifier"
    ::= { affirmedSecurityHistoryIkeNegotiationsMultiSpmEntry 13 }

affirmedSecurityHistoryIkeNegotiationsMultiSpmRemoteAddress OBJECT-TYPE
    SYNTAX      String
    MAX-ACCESS  read-only
    STATUS      current
    DESCRIPTION "Address Of Remote Endpoint"
    ::= { affirmedSecurityHistoryIkeNegotiationsMultiSpmEntry 14 }

affirmedSecurityHistoryIkeNegotiationsMultiSpmRemotePort OBJECT-TYPE
    SYNTAX      String
    MAX-ACCESS  read-only
    STATUS      current
    DESCRIPTION "Port Number Of Remote Endpoint"
    ::= { affirmedSecurityHistoryIkeNegotiationsMultiSpmEntry 15 }

affirmedSecurityHistoryIkeNegotiationsMultiSpmRemoteId OBJECT-TYPE
    SYNTAX      String
    MAX-ACCESS  read-only
    STATUS      current
    DESCRIPTION "Remote Endpoint Identifier"
    ::= { affirmedSecurityHistoryIkeNegotiationsMultiSpmEntry 16 }

affirmedSecurityHistoryIkeNegotiationsMultiSpmInitiatorSpi OBJECT-TYPE
    SYNTAX      String
    MAX-ACCESS  read-only
    STATUS      current
    DESCRIPTION "Initiator SPI"
    ::= { affirmedSecurityHistoryIkeNegotiationsMultiSpmEntry 17 }

affirmedSecurityHistoryIkeNegotiationsMultiSpmResponderSpi OBJECT-TYPE
    SYNTAX      String
    MAX-ACCESS  read-only
    STATUS      current
    DESCRIPTION "Responder SPI"
    ::= { affirmedSecurityHistoryIkeNegotiationsMultiSpmEntry 18 }

affirmedSecurityHistoryIkeNegotiationsMultiSpmLocalLifetime OBJECT-TYPE
    SYNTAX      String
    MAX-ACCESS  read-only
    STATUS      current
    DESCRIPTION "Local Lifetime"
    ::= { affirmedSecurityHistoryIkeNegotiationsMultiSpmEntry 19 }

affirmedSecurityHistoryIkeNegotiationsMultiSpmTunnelName OBJECT-TYPE
    SYNTAX      String
    MAX-ACCESS  read-only
    STATUS      current
    DESCRIPTION "Security Tunnel Name"
    ::= { affirmedSecurityHistoryIkeNegotiationsMultiSpmEntry 20 }

affirmedSecurityHistoryIkeNegotiationsTable OBJECT-TYPE
    SYNTAX      SEQUENCE OF AffirmedSecurityHistoryIkeNegotiationsEntry
    MAX-ACCESS  not-accessible
    STATUS      deprecated
    DESCRIPTION ""
    ::= { affirmedSecurityHistory 2 }

affirmedSecurityHistoryIkeNegotiationsEntry OBJECT-TYPE
    SYNTAX      AffirmedSecurityHistoryIkeNegotiationsEntry
    MAX-ACCESS  not-accessible
    STATUS      deprecated
    DESCRIPTION ""
    INDEX { affirmedSecurityHistoryIkeNegotiationsNetworkContext, affirmedSecurityHistoryIkeNegotiationsId }
        ::= { affirmedSecurityHistoryIkeNegotiationsTable 1 }

AffirmedSecurityHistoryIkeNegotiationsEntry ::=
    SEQUENCE {
        affirmedSecurityHistoryIkeNegotiationsNetworkContext String,
        affirmedSecurityHistoryIkeNegotiationsId Unsigned32,
        affirmedSecurityHistoryIkeNegotiationsTimestamp String,
        affirmedSecurityHistoryIkeNegotiationsMode String,
        affirmedSecurityHistoryIkeNegotiationsIkeVersion String,
        affirmedSecurityHistoryIkeNegotiationsLocalAuthMethod String,
        affirmedSecurityHistoryIkeNegotiationsRemoteAuthMethod String,
        affirmedSecurityHistoryIkeNegotiationsIkeAlgorithms String,
        affirmedSecurityHistoryIkeNegotiationsDhGroups String,
        affirmedSecurityHistoryIkeNegotiationsLocalAddress String,
        affirmedSecurityHistoryIkeNegotiationsLocalPort String,
        affirmedSecurityHistoryIkeNegotiationsLocalId String,
        affirmedSecurityHistoryIkeNegotiationsRemoteAddress String,
        affirmedSecurityHistoryIkeNegotiationsRemotePort String,
        affirmedSecurityHistoryIkeNegotiationsRemoteId String,
        affirmedSecurityHistoryIkeNegotiationsInitiatorSpi String,
        affirmedSecurityHistoryIkeNegotiationsResponderSpi String,
        affirmedSecurityHistoryIkeNegotiationsLocalLifetime String
    }

affirmedSecurityHistoryIkeNegotiationsNetworkContext OBJECT-TYPE
    SYNTAX      String
    MAX-ACCESS  not-accessible
    STATUS      current
    DESCRIPTION "Network Context Name"
    ::= { affirmedSecurityHistoryIkeNegotiationsEntry 1 }

affirmedSecurityHistoryIkeNegotiationsId OBJECT-TYPE
    SYNTAX      Unsigned32
    MAX-ACCESS  not-accessible
    STATUS      current
    DESCRIPTION "Internal Entry Identifier"
    ::= { affirmedSecurityHistoryIkeNegotiationsEntry 2 }

affirmedSecurityHistoryIkeNegotiationsTimestamp OBJECT-TYPE
    SYNTAX      String
    MAX-ACCESS  read-only
    STATUS      current
    DESCRIPTION "Timestamp"
    ::= { affirmedSecurityHistoryIkeNegotiationsEntry 3 }

affirmedSecurityHistoryIkeNegotiationsMode OBJECT-TYPE
    SYNTAX      String
    MAX-ACCESS  read-only
    STATUS      current
    DESCRIPTION "Mode"
    ::= { affirmedSecurityHistoryIkeNegotiationsEntry 4 }

affirmedSecurityHistoryIkeNegotiationsIkeVersion OBJECT-TYPE
    SYNTAX      String
    MAX-ACCESS  read-only
    STATUS      current
    DESCRIPTION "IKE version"
    ::= { affirmedSecurityHistoryIkeNegotiationsEntry 5 }

affirmedSecurityHistoryIkeNegotiationsLocalAuthMethod OBJECT-TYPE
    SYNTAX      String
    MAX-ACCESS  read-only
    STATUS      current
    DESCRIPTION "Local Authentication Method"
    ::= { affirmedSecurityHistoryIkeNegotiationsEntry 6 }

affirmedSecurityHistoryIkeNegotiationsRemoteAuthMethod OBJECT-TYPE
    SYNTAX      String
    MAX-ACCESS  read-only
    STATUS      current
    DESCRIPTION "Remote Authentication Method"
    ::= { affirmedSecurityHistoryIkeNegotiationsEntry 7 }

affirmedSecurityHistoryIkeNegotiationsIkeAlgorithms OBJECT-TYPE
    SYNTAX      String
    MAX-ACCESS  read-only
    STATUS      current
    DESCRIPTION "IKE Algorithms Employed"
    ::= { affirmedSecurityHistoryIkeNegotiationsEntry 8 }

affirmedSecurityHistoryIkeNegotiationsDhGroups OBJECT-TYPE
    SYNTAX      String
    MAX-ACCESS  read-only
    STATUS      current
    DESCRIPTION "Diffie Hellman Groups"
    ::= { affirmedSecurityHistoryIkeNegotiationsEntry 9 }

affirmedSecurityHistoryIkeNegotiationsLocalAddress OBJECT-TYPE
    SYNTAX      String
    MAX-ACCESS  read-only
    STATUS      current
    DESCRIPTION "Address Of Local Endpoint"
    ::= { affirmedSecurityHistoryIkeNegotiationsEntry 10 }

affirmedSecurityHistoryIkeNegotiationsLocalPort OBJECT-TYPE
    SYNTAX      String
    MAX-ACCESS  read-only
    STATUS      current
    DESCRIPTION "Port Number Of Local Endpoint"
    ::= { affirmedSecurityHistoryIkeNegotiationsEntry 11 }

affirmedSecurityHistoryIkeNegotiationsLocalId OBJECT-TYPE
    SYNTAX      String
    MAX-ACCESS  read-only
    STATUS      current
    DESCRIPTION "Local Endpoint Identifier"
    ::= { affirmedSecurityHistoryIkeNegotiationsEntry 12 }

affirmedSecurityHistoryIkeNegotiationsRemoteAddress OBJECT-TYPE
    SYNTAX      String
    MAX-ACCESS  read-only
    STATUS      current
    DESCRIPTION "Address Of Remote Endpoint"
    ::= { affirmedSecurityHistoryIkeNegotiationsEntry 13 }

affirmedSecurityHistoryIkeNegotiationsRemotePort OBJECT-TYPE
    SYNTAX      String
    MAX-ACCESS  read-only
    STATUS      current
    DESCRIPTION "Port Number Of Remote Endpoint"
    ::= { affirmedSecurityHistoryIkeNegotiationsEntry 14 }

affirmedSecurityHistoryIkeNegotiationsRemoteId OBJECT-TYPE
    SYNTAX      String
    MAX-ACCESS  read-only
    STATUS      current
    DESCRIPTION "Remote Endpoint Identifier"
    ::= { affirmedSecurityHistoryIkeNegotiationsEntry 15 }

affirmedSecurityHistoryIkeNegotiationsInitiatorSpi OBJECT-TYPE
    SYNTAX      String
    MAX-ACCESS  read-only
    STATUS      current
    DESCRIPTION "Initiator SPI"
    ::= { affirmedSecurityHistoryIkeNegotiationsEntry 16 }

affirmedSecurityHistoryIkeNegotiationsResponderSpi OBJECT-TYPE
    SYNTAX      String
    MAX-ACCESS  read-only
    STATUS      current
    DESCRIPTION "Responder SPI"
    ::= { affirmedSecurityHistoryIkeNegotiationsEntry 17 }

affirmedSecurityHistoryIkeNegotiationsLocalLifetime OBJECT-TYPE
    SYNTAX      String
    MAX-ACCESS  read-only
    STATUS      current
    DESCRIPTION "Local Lifetime"
    ::= { affirmedSecurityHistoryIkeNegotiationsEntry 18 }

affirmedSecurityHistoryIpsecFailuresMultiSpmTable OBJECT-TYPE
    SYNTAX      SEQUENCE OF AffirmedSecurityHistoryIpsecFailuresMultiSpmEntry
    MAX-ACCESS  not-accessible
    STATUS      current
    DESCRIPTION ""
    ::= { affirmedSecurityHistory 7 }

affirmedSecurityHistoryIpsecFailuresMultiSpmEntry OBJECT-TYPE
    SYNTAX      AffirmedSecurityHistoryIpsecFailuresMultiSpmEntry
    MAX-ACCESS  not-accessible
    STATUS      current
    DESCRIPTION ""
    INDEX { affirmedSecurityHistoryIpsecFailuresMultiSpmNetworkContext, affirmedSecurityHistoryIpsecFailuresMultiSpmServiceName, affirmedSecurityHistoryIpsecFailuresMultiSpmId }
        ::= { affirmedSecurityHistoryIpsecFailuresMultiSpmTable 1 }

AffirmedSecurityHistoryIpsecFailuresMultiSpmEntry ::=
    SEQUENCE {
        affirmedSecurityHistoryIpsecFailuresMultiSpmNetworkContext String,
        affirmedSecurityHistoryIpsecFailuresMultiSpmServiceName String,
        affirmedSecurityHistoryIpsecFailuresMultiSpmId Unsigned32,
        affirmedSecurityHistoryIpsecFailuresMultiSpmTimestamp String,
        affirmedSecurityHistoryIpsecFailuresMultiSpmMode String,
        affirmedSecurityHistoryIpsecFailuresMultiSpmLocalAddress String,
        affirmedSecurityHistoryIpsecFailuresMultiSpmLocalPort String,
        affirmedSecurityHistoryIpsecFailuresMultiSpmLocalId String,
        affirmedSecurityHistoryIpsecFailuresMultiSpmRemoteAddress String,
        affirmedSecurityHistoryIpsecFailuresMultiSpmRemotePort String,
        affirmedSecurityHistoryIpsecFailuresMultiSpmRemoteId String,
        affirmedSecurityHistoryIpsecFailuresMultiSpmErrorMsg String,
        affirmedSecurityHistoryIpsecFailuresMultiSpmErrorId String,
        affirmedSecurityHistoryIpsecFailuresMultiSpmErrorReason String,
        affirmedSecurityHistoryIpsecFailuresMultiSpmTunnelName String
    }

affirmedSecurityHistoryIpsecFailuresMultiSpmNetworkContext OBJECT-TYPE
    SYNTAX      String
    MAX-ACCESS  not-accessible
    STATUS      current
    DESCRIPTION "Network Context Name"
    ::= { affirmedSecurityHistoryIpsecFailuresMultiSpmEntry 1 }

affirmedSecurityHistoryIpsecFailuresMultiSpmServiceName OBJECT-TYPE
    SYNTAX      String
    MAX-ACCESS  not-accessible
    STATUS      current
    DESCRIPTION "Task service name"
    ::= { affirmedSecurityHistoryIpsecFailuresMultiSpmEntry 2 }

affirmedSecurityHistoryIpsecFailuresMultiSpmId OBJECT-TYPE
    SYNTAX      Unsigned32
    MAX-ACCESS  not-accessible
    STATUS      current
    DESCRIPTION "Internal Entry Identifier"
    ::= { affirmedSecurityHistoryIpsecFailuresMultiSpmEntry 3 }

affirmedSecurityHistoryIpsecFailuresMultiSpmTimestamp OBJECT-TYPE
    SYNTAX      String
    MAX-ACCESS  read-only
    STATUS      current
    DESCRIPTION "Timestamp"
    ::= { affirmedSecurityHistoryIpsecFailuresMultiSpmEntry 4 }

affirmedSecurityHistoryIpsecFailuresMultiSpmMode OBJECT-TYPE
    SYNTAX      String
    MAX-ACCESS  read-only
    STATUS      current
    DESCRIPTION "Mode"
    ::= { affirmedSecurityHistoryIpsecFailuresMultiSpmEntry 5 }

affirmedSecurityHistoryIpsecFailuresMultiSpmLocalAddress OBJECT-TYPE
    SYNTAX      String
    MAX-ACCESS  read-only
    STATUS      current
    DESCRIPTION "Address Of Local Endpoint"
    ::= { affirmedSecurityHistoryIpsecFailuresMultiSpmEntry 6 }

affirmedSecurityHistoryIpsecFailuresMultiSpmLocalPort OBJECT-TYPE
    SYNTAX      String
    MAX-ACCESS  read-only
    STATUS      current
    DESCRIPTION "Port Number Of Local Endpoint"
    ::= { affirmedSecurityHistoryIpsecFailuresMultiSpmEntry 7 }

affirmedSecurityHistoryIpsecFailuresMultiSpmLocalId OBJECT-TYPE
    SYNTAX      String
    MAX-ACCESS  read-only
    STATUS      current
    DESCRIPTION "Local Endpoint Identifier"
    ::= { affirmedSecurityHistoryIpsecFailuresMultiSpmEntry 8 }

affirmedSecurityHistoryIpsecFailuresMultiSpmRemoteAddress OBJECT-TYPE
    SYNTAX      String
    MAX-ACCESS  read-only
    STATUS      current
    DESCRIPTION "Address Of Remote Endpoint"
    ::= { affirmedSecurityHistoryIpsecFailuresMultiSpmEntry 9 }

affirmedSecurityHistoryIpsecFailuresMultiSpmRemotePort OBJECT-TYPE
    SYNTAX      String
    MAX-ACCESS  read-only
    STATUS      current
    DESCRIPTION "Port Number Of Remote Endpoint"
    ::= { affirmedSecurityHistoryIpsecFailuresMultiSpmEntry 10 }

affirmedSecurityHistoryIpsecFailuresMultiSpmRemoteId OBJECT-TYPE
    SYNTAX      String
    MAX-ACCESS  read-only
    STATUS      current
    DESCRIPTION "Remote Endpoint Identifier"
    ::= { affirmedSecurityHistoryIpsecFailuresMultiSpmEntry 11 }

affirmedSecurityHistoryIpsecFailuresMultiSpmErrorMsg OBJECT-TYPE
    SYNTAX      String
    MAX-ACCESS  read-only
    STATUS      current
    DESCRIPTION "Error Message String"
    ::= { affirmedSecurityHistoryIpsecFailuresMultiSpmEntry 12 }

affirmedSecurityHistoryIpsecFailuresMultiSpmErrorId OBJECT-TYPE
    SYNTAX      String
    MAX-ACCESS  read-only
    STATUS      current
    DESCRIPTION "Error Identifier"
    ::= { affirmedSecurityHistoryIpsecFailuresMultiSpmEntry 13 }

affirmedSecurityHistoryIpsecFailuresMultiSpmErrorReason OBJECT-TYPE
    SYNTAX      String
    MAX-ACCESS  read-only
    STATUS      current
    DESCRIPTION "Error Reason (if known)"
    ::= { affirmedSecurityHistoryIpsecFailuresMultiSpmEntry 14 }

affirmedSecurityHistoryIpsecFailuresMultiSpmTunnelName OBJECT-TYPE
    SYNTAX      String
    MAX-ACCESS  read-only
    STATUS      current
    DESCRIPTION "Security Tunnel Name"
    ::= { affirmedSecurityHistoryIpsecFailuresMultiSpmEntry 15 }

affirmedSecurityHistoryIpsecFailuresTable OBJECT-TYPE
    SYNTAX      SEQUENCE OF AffirmedSecurityHistoryIpsecFailuresEntry
    MAX-ACCESS  not-accessible
    STATUS      deprecated
    DESCRIPTION ""
    ::= { affirmedSecurityHistory 3 }

affirmedSecurityHistoryIpsecFailuresEntry OBJECT-TYPE
    SYNTAX      AffirmedSecurityHistoryIpsecFailuresEntry
    MAX-ACCESS  not-accessible
    STATUS      deprecated
    DESCRIPTION ""
    INDEX { affirmedSecurityHistoryIpsecFailuresNetworkContext, affirmedSecurityHistoryIpsecFailuresId }
        ::= { affirmedSecurityHistoryIpsecFailuresTable 1 }

AffirmedSecurityHistoryIpsecFailuresEntry ::=
    SEQUENCE {
        affirmedSecurityHistoryIpsecFailuresNetworkContext String,
        affirmedSecurityHistoryIpsecFailuresId Unsigned32,
        affirmedSecurityHistoryIpsecFailuresTimestamp String,
        affirmedSecurityHistoryIpsecFailuresMode String,
        affirmedSecurityHistoryIpsecFailuresLocalAddress String,
        affirmedSecurityHistoryIpsecFailuresLocalPort String,
        affirmedSecurityHistoryIpsecFailuresLocalId String,
        affirmedSecurityHistoryIpsecFailuresRemoteAddress String,
        affirmedSecurityHistoryIpsecFailuresRemotePort String,
        affirmedSecurityHistoryIpsecFailuresRemoteId String,
        affirmedSecurityHistoryIpsecFailuresErrorMsg String,
        affirmedSecurityHistoryIpsecFailuresErrorId String,
        affirmedSecurityHistoryIpsecFailuresErrorReason String,
        affirmedSecurityHistoryIpsecFailuresSecondaryErrorReason INTEGER
    }

affirmedSecurityHistoryIpsecFailuresNetworkContext OBJECT-TYPE
    SYNTAX      String
    MAX-ACCESS  not-accessible
    STATUS      current
    DESCRIPTION "Network Context Name"
    ::= { affirmedSecurityHistoryIpsecFailuresEntry 1 }

affirmedSecurityHistoryIpsecFailuresId OBJECT-TYPE
    SYNTAX      Unsigned32
    MAX-ACCESS  not-accessible
    STATUS      current
    DESCRIPTION "Internal Entry Identifier"
    ::= { affirmedSecurityHistoryIpsecFailuresEntry 2 }

affirmedSecurityHistoryIpsecFailuresTimestamp OBJECT-TYPE
    SYNTAX      String
    MAX-ACCESS  read-only
    STATUS      current
    DESCRIPTION "Timestamp"
    ::= { affirmedSecurityHistoryIpsecFailuresEntry 3 }

affirmedSecurityHistoryIpsecFailuresMode OBJECT-TYPE
    SYNTAX      String
    MAX-ACCESS  read-only
    STATUS      current
    DESCRIPTION "Mode"
    ::= { affirmedSecurityHistoryIpsecFailuresEntry 4 }

affirmedSecurityHistoryIpsecFailuresLocalAddress OBJECT-TYPE
    SYNTAX      String
    MAX-ACCESS  read-only
    STATUS      current
    DESCRIPTION "Address Of Local Endpoint"
    ::= { affirmedSecurityHistoryIpsecFailuresEntry 5 }

affirmedSecurityHistoryIpsecFailuresLocalPort OBJECT-TYPE
    SYNTAX      String
    MAX-ACCESS  read-only
    STATUS      current
    DESCRIPTION "Port Number Of Local Endpoint"
    ::= { affirmedSecurityHistoryIpsecFailuresEntry 6 }

affirmedSecurityHistoryIpsecFailuresLocalId OBJECT-TYPE
    SYNTAX      String
    MAX-ACCESS  read-only
    STATUS      current
    DESCRIPTION "Local Endpoint Identifier"
    ::= { affirmedSecurityHistoryIpsecFailuresEntry 7 }

affirmedSecurityHistoryIpsecFailuresRemoteAddress OBJECT-TYPE
    SYNTAX      String
    MAX-ACCESS  read-only
    STATUS      current
    DESCRIPTION "Address Of Remote Endpoint"
    ::= { affirmedSecurityHistoryIpsecFailuresEntry 8 }

affirmedSecurityHistoryIpsecFailuresRemotePort OBJECT-TYPE
    SYNTAX      String
    MAX-ACCESS  read-only
    STATUS      current
    DESCRIPTION "Port Number Of Remote Endpoint"
    ::= { affirmedSecurityHistoryIpsecFailuresEntry 9 }

affirmedSecurityHistoryIpsecFailuresRemoteId OBJECT-TYPE
    SYNTAX      String
    MAX-ACCESS  read-only
    STATUS      current
    DESCRIPTION "Remote Endpoint Identifier"
    ::= { affirmedSecurityHistoryIpsecFailuresEntry 10 }

affirmedSecurityHistoryIpsecFailuresErrorMsg OBJECT-TYPE
    SYNTAX      String
    MAX-ACCESS  read-only
    STATUS      current
    DESCRIPTION "Error Message String"
    ::= { affirmedSecurityHistoryIpsecFailuresEntry 11 }

affirmedSecurityHistoryIpsecFailuresErrorId OBJECT-TYPE
    SYNTAX      String
    MAX-ACCESS  read-only
    STATUS      current
    DESCRIPTION "Error Identifier"
    ::= { affirmedSecurityHistoryIpsecFailuresEntry 12 }

affirmedSecurityHistoryIpsecFailuresErrorReason OBJECT-TYPE
    SYNTAX      String
    MAX-ACCESS  read-only
    STATUS      current
    DESCRIPTION "Error Reason (if known)"
    ::= { affirmedSecurityHistoryIpsecFailuresEntry 13 }

affirmedSecurityHistoryIpsecFailuresSecondaryErrorReason OBJECT-TYPE
    SYNTAX      INTEGER {none(0),audit-failure(1),aaa-not-available(2),aaa-timeout(3),aaa-failure(4),pgw-no-response(5),gw-failure(6),ip-address-not-available(7),re-authentication(8),gw-initiated(9),unspecified(10),re-attach(11),gw-timeout(12),invalid-remote-identity(13),missing-local-identity(14),no-matching-epdg(15),internal-error(16),gw-not-found(17),identity-decryption-failed(18)}
    MAX-ACCESS  read-only
    STATUS      current
    DESCRIPTION "Secondary Error Reason (if known)"
    ::= { affirmedSecurityHistoryIpsecFailuresEntry 14 }

affirmedSecurityHistoryIpsecNegotiationsMultiSpmTable OBJECT-TYPE
    SYNTAX      SEQUENCE OF AffirmedSecurityHistoryIpsecNegotiationsMultiSpmEntry
    MAX-ACCESS  not-accessible
    STATUS      current
    DESCRIPTION ""
    ::= { affirmedSecurityHistory 8 }

affirmedSecurityHistoryIpsecNegotiationsMultiSpmEntry OBJECT-TYPE
    SYNTAX      AffirmedSecurityHistoryIpsecNegotiationsMultiSpmEntry
    MAX-ACCESS  not-accessible
    STATUS      current
    DESCRIPTION ""
    INDEX { affirmedSecurityHistoryIpsecNegotiationsMultiSpmNetworkContext, affirmedSecurityHistoryIpsecNegotiationsMultiSpmServiceName, affirmedSecurityHistoryIpsecNegotiationsMultiSpmId }
        ::= { affirmedSecurityHistoryIpsecNegotiationsMultiSpmTable 1 }

AffirmedSecurityHistoryIpsecNegotiationsMultiSpmEntry ::=
    SEQUENCE {
        affirmedSecurityHistoryIpsecNegotiationsMultiSpmNetworkContext String,
        affirmedSecurityHistoryIpsecNegotiationsMultiSpmServiceName String,
        affirmedSecurityHistoryIpsecNegotiationsMultiSpmId Unsigned32,
        affirmedSecurityHistoryIpsecNegotiationsMultiSpmTimestamp String,
        affirmedSecurityHistoryIpsecNegotiationsMultiSpmMode String,
        affirmedSecurityHistoryIpsecNegotiationsMultiSpmDhGroup String,
        affirmedSecurityHistoryIpsecNegotiationsMultiSpmLocalAddress String,
        affirmedSecurityHistoryIpsecNegotiationsMultiSpmLocalPort String,
        affirmedSecurityHistoryIpsecNegotiationsMultiSpmLocalId String,
        affirmedSecurityHistoryIpsecNegotiationsMultiSpmRemoteAddress String,
        affirmedSecurityHistoryIpsecNegotiationsMultiSpmRemotePort String,
        affirmedSecurityHistoryIpsecNegotiationsMultiSpmRemoteId String,
        affirmedSecurityHistoryIpsecNegotiationsMultiSpmLocalTrafficSelector String,
        affirmedSecurityHistoryIpsecNegotiationsMultiSpmRemoteTrafficSelector String,
        affirmedSecurityHistoryIpsecNegotiationsMultiSpmTransformType String,
        affirmedSecurityHistoryIpsecNegotiationsMultiSpmInboundSpi String,
        affirmedSecurityHistoryIpsecNegotiationsMultiSpmOutboundSpi String,
        affirmedSecurityHistoryIpsecNegotiationsMultiSpmAlgorithm String,
        affirmedSecurityHistoryIpsecNegotiationsMultiSpmLocalLifetime String,
        affirmedSecurityHistoryIpsecNegotiationsMultiSpmTunnelName String
    }

affirmedSecurityHistoryIpsecNegotiationsMultiSpmNetworkContext OBJECT-TYPE
    SYNTAX      String
    MAX-ACCESS  not-accessible
    STATUS      current
    DESCRIPTION "Network Context Name"
    ::= { affirmedSecurityHistoryIpsecNegotiationsMultiSpmEntry 1 }

affirmedSecurityHistoryIpsecNegotiationsMultiSpmServiceName OBJECT-TYPE
    SYNTAX      String
    MAX-ACCESS  not-accessible
    STATUS      current
    DESCRIPTION "Task service name"
    ::= { affirmedSecurityHistoryIpsecNegotiationsMultiSpmEntry 2 }

affirmedSecurityHistoryIpsecNegotiationsMultiSpmId OBJECT-TYPE
    SYNTAX      Unsigned32
    MAX-ACCESS  not-accessible
    STATUS      current
    DESCRIPTION "Internal Entry Identifier"
    ::= { affirmedSecurityHistoryIpsecNegotiationsMultiSpmEntry 3 }

affirmedSecurityHistoryIpsecNegotiationsMultiSpmTimestamp OBJECT-TYPE
    SYNTAX      String
    MAX-ACCESS  read-only
    STATUS      current
    DESCRIPTION "Timestamp"
    ::= { affirmedSecurityHistoryIpsecNegotiationsMultiSpmEntry 4 }

affirmedSecurityHistoryIpsecNegotiationsMultiSpmMode OBJECT-TYPE
    SYNTAX      String
    MAX-ACCESS  read-only
    STATUS      current
    DESCRIPTION "Mode"
    ::= { affirmedSecurityHistoryIpsecNegotiationsMultiSpmEntry 5 }

affirmedSecurityHistoryIpsecNegotiationsMultiSpmDhGroup OBJECT-TYPE
    SYNTAX      String
    MAX-ACCESS  read-only
    STATUS      current
    DESCRIPTION "Diffie Hellman Group"
    ::= { affirmedSecurityHistoryIpsecNegotiationsMultiSpmEntry 6 }

affirmedSecurityHistoryIpsecNegotiationsMultiSpmLocalAddress OBJECT-TYPE
    SYNTAX      String
    MAX-ACCESS  read-only
    STATUS      current
    DESCRIPTION "Address Of Local Endpoint"
    ::= { affirmedSecurityHistoryIpsecNegotiationsMultiSpmEntry 7 }

affirmedSecurityHistoryIpsecNegotiationsMultiSpmLocalPort OBJECT-TYPE
    SYNTAX      String
    MAX-ACCESS  read-only
    STATUS      current
    DESCRIPTION "Port Number Of Local Endpoint"
    ::= { affirmedSecurityHistoryIpsecNegotiationsMultiSpmEntry 8 }

affirmedSecurityHistoryIpsecNegotiationsMultiSpmLocalId OBJECT-TYPE
    SYNTAX      String
    MAX-ACCESS  read-only
    STATUS      current
    DESCRIPTION "Local Endpoint Identifier"
    ::= { affirmedSecurityHistoryIpsecNegotiationsMultiSpmEntry 9 }

affirmedSecurityHistoryIpsecNegotiationsMultiSpmRemoteAddress OBJECT-TYPE
    SYNTAX      String
    MAX-ACCESS  read-only
    STATUS      current
    DESCRIPTION "Address Of Remote Endpoint"
    ::= { affirmedSecurityHistoryIpsecNegotiationsMultiSpmEntry 10 }

affirmedSecurityHistoryIpsecNegotiationsMultiSpmRemotePort OBJECT-TYPE
    SYNTAX      String
    MAX-ACCESS  read-only
    STATUS      current
    DESCRIPTION "Port Number Of Remote Endpoint"
    ::= { affirmedSecurityHistoryIpsecNegotiationsMultiSpmEntry 11 }

affirmedSecurityHistoryIpsecNegotiationsMultiSpmRemoteId OBJECT-TYPE
    SYNTAX      String
    MAX-ACCESS  read-only
    STATUS      current
    DESCRIPTION "Remote Endpoint Identifier"
    ::= { affirmedSecurityHistoryIpsecNegotiationsMultiSpmEntry 12 }

affirmedSecurityHistoryIpsecNegotiationsMultiSpmLocalTrafficSelector OBJECT-TYPE
    SYNTAX      String
    MAX-ACCESS  read-only
    STATUS      current
    DESCRIPTION "Local Traffic Selector"
    ::= { affirmedSecurityHistoryIpsecNegotiationsMultiSpmEntry 13 }

affirmedSecurityHistoryIpsecNegotiationsMultiSpmRemoteTrafficSelector OBJECT-TYPE
    SYNTAX      String
    MAX-ACCESS  read-only
    STATUS      current
    DESCRIPTION "Remote Traffic Selector"
    ::= { affirmedSecurityHistoryIpsecNegotiationsMultiSpmEntry 14 }

affirmedSecurityHistoryIpsecNegotiationsMultiSpmTransformType OBJECT-TYPE
    SYNTAX      String
    MAX-ACCESS  read-only
    STATUS      current
    DESCRIPTION "Transform Type"
    ::= { affirmedSecurityHistoryIpsecNegotiationsMultiSpmEntry 15 }

affirmedSecurityHistoryIpsecNegotiationsMultiSpmInboundSpi OBJECT-TYPE
    SYNTAX      String
    MAX-ACCESS  read-only
    STATUS      current
    DESCRIPTION "Inbound SPI"
    ::= { affirmedSecurityHistoryIpsecNegotiationsMultiSpmEntry 16 }

affirmedSecurityHistoryIpsecNegotiationsMultiSpmOutboundSpi OBJECT-TYPE
    SYNTAX      String
    MAX-ACCESS  read-only
    STATUS      current
    DESCRIPTION "Outbound SPI"
    ::= { affirmedSecurityHistoryIpsecNegotiationsMultiSpmEntry 17 }

affirmedSecurityHistoryIpsecNegotiationsMultiSpmAlgorithm OBJECT-TYPE
    SYNTAX      String
    MAX-ACCESS  read-only
    STATUS      current
    DESCRIPTION "Algorithm"
    ::= { affirmedSecurityHistoryIpsecNegotiationsMultiSpmEntry 18 }

affirmedSecurityHistoryIpsecNegotiationsMultiSpmLocalLifetime OBJECT-TYPE
    SYNTAX      String
    MAX-ACCESS  read-only
    STATUS      current
    DESCRIPTION "Local Lifetime"
    ::= { affirmedSecurityHistoryIpsecNegotiationsMultiSpmEntry 19 }

affirmedSecurityHistoryIpsecNegotiationsMultiSpmTunnelName OBJECT-TYPE
    SYNTAX      String
    MAX-ACCESS  read-only
    STATUS      current
    DESCRIPTION "Security Tunnel Name"
    ::= { affirmedSecurityHistoryIpsecNegotiationsMultiSpmEntry 20 }

affirmedSecurityHistoryIpsecNegotiationsTable OBJECT-TYPE
    SYNTAX      SEQUENCE OF AffirmedSecurityHistoryIpsecNegotiationsEntry
    MAX-ACCESS  not-accessible
    STATUS      deprecated
    DESCRIPTION ""
    ::= { affirmedSecurityHistory 4 }

affirmedSecurityHistoryIpsecNegotiationsEntry OBJECT-TYPE
    SYNTAX      AffirmedSecurityHistoryIpsecNegotiationsEntry
    MAX-ACCESS  not-accessible
    STATUS      deprecated
    DESCRIPTION ""
    INDEX { affirmedSecurityHistoryIpsecNegotiationsNetworkContext, affirmedSecurityHistoryIpsecNegotiationsId }
        ::= { affirmedSecurityHistoryIpsecNegotiationsTable 1 }

AffirmedSecurityHistoryIpsecNegotiationsEntry ::=
    SEQUENCE {
        affirmedSecurityHistoryIpsecNegotiationsNetworkContext String,
        affirmedSecurityHistoryIpsecNegotiationsId Unsigned32,
        affirmedSecurityHistoryIpsecNegotiationsTimestamp String,
        affirmedSecurityHistoryIpsecNegotiationsMode String,
        affirmedSecurityHistoryIpsecNegotiationsDhGroup String,
        affirmedSecurityHistoryIpsecNegotiationsLocalAddress String,
        affirmedSecurityHistoryIpsecNegotiationsLocalPort String,
        affirmedSecurityHistoryIpsecNegotiationsLocalId String,
        affirmedSecurityHistoryIpsecNegotiationsRemoteAddress String,
        affirmedSecurityHistoryIpsecNegotiationsRemotePort String,
        affirmedSecurityHistoryIpsecNegotiationsRemoteId String,
        affirmedSecurityHistoryIpsecNegotiationsLocalTrafficSelector String,
        affirmedSecurityHistoryIpsecNegotiationsRemoteTrafficSelector String,
        affirmedSecurityHistoryIpsecNegotiationsTransformType String,
        affirmedSecurityHistoryIpsecNegotiationsInboundSpi String,
        affirmedSecurityHistoryIpsecNegotiationsOutboundSpi String,
        affirmedSecurityHistoryIpsecNegotiationsAlgorithm String,
        affirmedSecurityHistoryIpsecNegotiationsLocalLifetime String
    }

affirmedSecurityHistoryIpsecNegotiationsNetworkContext OBJECT-TYPE
    SYNTAX      String
    MAX-ACCESS  not-accessible
    STATUS      current
    DESCRIPTION "Network Context Name"
    ::= { affirmedSecurityHistoryIpsecNegotiationsEntry 1 }

affirmedSecurityHistoryIpsecNegotiationsId OBJECT-TYPE
    SYNTAX      Unsigned32
    MAX-ACCESS  not-accessible
    STATUS      current
    DESCRIPTION "Internal Entry Identifier"
    ::= { affirmedSecurityHistoryIpsecNegotiationsEntry 2 }

affirmedSecurityHistoryIpsecNegotiationsTimestamp OBJECT-TYPE
    SYNTAX      String
    MAX-ACCESS  read-only
    STATUS      current
    DESCRIPTION "Timestamp"
    ::= { affirmedSecurityHistoryIpsecNegotiationsEntry 3 }

affirmedSecurityHistoryIpsecNegotiationsMode OBJECT-TYPE
    SYNTAX      String
    MAX-ACCESS  read-only
    STATUS      current
    DESCRIPTION "Mode"
    ::= { affirmedSecurityHistoryIpsecNegotiationsEntry 4 }

affirmedSecurityHistoryIpsecNegotiationsDhGroup OBJECT-TYPE
    SYNTAX      String
    MAX-ACCESS  read-only
    STATUS      current
    DESCRIPTION "Diffie Hellman Group"
    ::= { affirmedSecurityHistoryIpsecNegotiationsEntry 5 }

affirmedSecurityHistoryIpsecNegotiationsLocalAddress OBJECT-TYPE
    SYNTAX      String
    MAX-ACCESS  read-only
    STATUS      current
    DESCRIPTION "Address Of Local Endpoint"
    ::= { affirmedSecurityHistoryIpsecNegotiationsEntry 6 }

affirmedSecurityHistoryIpsecNegotiationsLocalPort OBJECT-TYPE
    SYNTAX      String
    MAX-ACCESS  read-only
    STATUS      current
    DESCRIPTION "Port Number Of Local Endpoint"
    ::= { affirmedSecurityHistoryIpsecNegotiationsEntry 7 }

affirmedSecurityHistoryIpsecNegotiationsLocalId OBJECT-TYPE
    SYNTAX      String
    MAX-ACCESS  read-only
    STATUS      current
    DESCRIPTION "Local Endpoint Identifier"
    ::= { affirmedSecurityHistoryIpsecNegotiationsEntry 8 }

affirmedSecurityHistoryIpsecNegotiationsRemoteAddress OBJECT-TYPE
    SYNTAX      String
    MAX-ACCESS  read-only
    STATUS      current
    DESCRIPTION "Address Of Remote Endpoint"
    ::= { affirmedSecurityHistoryIpsecNegotiationsEntry 9 }

affirmedSecurityHistoryIpsecNegotiationsRemotePort OBJECT-TYPE
    SYNTAX      String
    MAX-ACCESS  read-only
    STATUS      current
    DESCRIPTION "Port Number Of Remote Endpoint"
    ::= { affirmedSecurityHistoryIpsecNegotiationsEntry 10 }

affirmedSecurityHistoryIpsecNegotiationsRemoteId OBJECT-TYPE
    SYNTAX      String
    MAX-ACCESS  read-only
    STATUS      current
    DESCRIPTION "Remote Endpoint Identifier"
    ::= { affirmedSecurityHistoryIpsecNegotiationsEntry 11 }

affirmedSecurityHistoryIpsecNegotiationsLocalTrafficSelector OBJECT-TYPE
    SYNTAX      String
    MAX-ACCESS  read-only
    STATUS      current
    DESCRIPTION "Local Traffic Selector"
    ::= { affirmedSecurityHistoryIpsecNegotiationsEntry 12 }

affirmedSecurityHistoryIpsecNegotiationsRemoteTrafficSelector OBJECT-TYPE
    SYNTAX      String
    MAX-ACCESS  read-only
    STATUS      current
    DESCRIPTION "Remote Traffic Selector"
    ::= { affirmedSecurityHistoryIpsecNegotiationsEntry 13 }

affirmedSecurityHistoryIpsecNegotiationsTransformType OBJECT-TYPE
    SYNTAX      String
    MAX-ACCESS  read-only
    STATUS      current
    DESCRIPTION "Transform Type"
    ::= { affirmedSecurityHistoryIpsecNegotiationsEntry 14 }

affirmedSecurityHistoryIpsecNegotiationsInboundSpi OBJECT-TYPE
    SYNTAX      String
    MAX-ACCESS  read-only
    STATUS      current
    DESCRIPTION "Inbound SPI"
    ::= { affirmedSecurityHistoryIpsecNegotiationsEntry 15 }

affirmedSecurityHistoryIpsecNegotiationsOutboundSpi OBJECT-TYPE
    SYNTAX      String
    MAX-ACCESS  read-only
    STATUS      current
    DESCRIPTION "Outbound SPI"
    ::= { affirmedSecurityHistoryIpsecNegotiationsEntry 16 }

affirmedSecurityHistoryIpsecNegotiationsAlgorithm OBJECT-TYPE
    SYNTAX      String
    MAX-ACCESS  read-only
    STATUS      current
    DESCRIPTION "Algorithm"
    ::= { affirmedSecurityHistoryIpsecNegotiationsEntry 17 }

affirmedSecurityHistoryIpsecNegotiationsLocalLifetime OBJECT-TYPE
    SYNTAX      String
    MAX-ACCESS  read-only
    STATUS      current
    DESCRIPTION "Local Lifetime"
    ::= { affirmedSecurityHistoryIpsecNegotiationsEntry 18 }

affirmedSecurityStatisticsNetworkContextTable OBJECT-TYPE
    SYNTAX      SEQUENCE OF AffirmedSecurityStatisticsNetworkContextEntry
    MAX-ACCESS  not-accessible
    STATUS      current
    DESCRIPTION ""
    ::= { affirmedSecurityStatistics 1 }

affirmedSecurityStatisticsNetworkContextEntry OBJECT-TYPE
    SYNTAX      AffirmedSecurityStatisticsNetworkContextEntry
    MAX-ACCESS  not-accessible
    STATUS      current
    DESCRIPTION ""
    INDEX { affirmedSecurityStatisticsNetworkContextName }
        ::= { affirmedSecurityStatisticsNetworkContextTable 1 }

AffirmedSecurityStatisticsNetworkContextEntry ::=
    SEQUENCE {
        affirmedSecurityStatisticsNetworkContextName String,
        affirmedSecurityStatisticsNetworkContextCurrentIkeTunnels ConfdString,
        affirmedSecurityStatisticsNetworkContextTotalIkeTunnels ConfdString,
        affirmedSecurityStatisticsNetworkContextTotalIkeFailedTunnels ConfdString,
        affirmedSecurityStatisticsNetworkContextTotalIkeRekeyedTunnels ConfdString,
        affirmedSecurityStatisticsNetworkContextCurrentIpsecTunnels ConfdString,
        affirmedSecurityStatisticsNetworkContextTotalIpsecTunnels ConfdString,
        affirmedSecurityStatisticsNetworkContextTotalIpsecFailedTunnels ConfdString,
        affirmedSecurityStatisticsNetworkContextCurrentTransforms ConfdString,
        affirmedSecurityStatisticsNetworkContextTotalTransforms ConfdString,
        affirmedSecurityStatisticsNetworkContextRekeyedTransforms ConfdString,
        affirmedSecurityStatisticsNetworkContextCurrentRules ConfdString,
        affirmedSecurityStatisticsNetworkContextTotalRules ConfdString,
        affirmedSecurityStatisticsNetworkContextCurrentFlows ConfdString,
        affirmedSecurityStatisticsNetworkContextTotalFlows ConfdString
    }

affirmedSecurityStatisticsNetworkContextName OBJECT-TYPE
    SYNTAX      String
    MAX-ACCESS  not-accessible
    STATUS      current
    DESCRIPTION "name of network context"
    ::= { affirmedSecurityStatisticsNetworkContextEntry 1 }

affirmedSecurityStatisticsNetworkContextCurrentIkeTunnels OBJECT-TYPE
    SYNTAX      ConfdString
    MAX-ACCESS  read-only
    STATUS      current
    DESCRIPTION "number of current IKE tunnels"
    ::= { affirmedSecurityStatisticsNetworkContextEntry 2 }

affirmedSecurityStatisticsNetworkContextTotalIkeTunnels OBJECT-TYPE
    SYNTAX      ConfdString
    MAX-ACCESS  read-only
    STATUS      current
    DESCRIPTION "number of total IKE tunnels"
    ::= { affirmedSecurityStatisticsNetworkContextEntry 3 }

affirmedSecurityStatisticsNetworkContextTotalIkeFailedTunnels OBJECT-TYPE
    SYNTAX      ConfdString
    MAX-ACCESS  read-only
    STATUS      current
    DESCRIPTION "number of total failed IKE tunnels"
    ::= { affirmedSecurityStatisticsNetworkContextEntry 4 }

affirmedSecurityStatisticsNetworkContextTotalIkeRekeyedTunnels OBJECT-TYPE
    SYNTAX      ConfdString
    MAX-ACCESS  read-only
    STATUS      current
    DESCRIPTION "number of total rekeyed IKE tunnels"
    ::= { affirmedSecurityStatisticsNetworkContextEntry 5 }

affirmedSecurityStatisticsNetworkContextCurrentIpsecTunnels OBJECT-TYPE
    SYNTAX      ConfdString
    MAX-ACCESS  read-only
    STATUS      current
    DESCRIPTION "number of current IPSEC tunnels"
    ::= { affirmedSecurityStatisticsNetworkContextEntry 6 }

affirmedSecurityStatisticsNetworkContextTotalIpsecTunnels OBJECT-TYPE
    SYNTAX      ConfdString
    MAX-ACCESS  read-only
    STATUS      current
    DESCRIPTION "number of total IPSEC tunnels"
    ::= { affirmedSecurityStatisticsNetworkContextEntry 7 }

affirmedSecurityStatisticsNetworkContextTotalIpsecFailedTunnels OBJECT-TYPE
    SYNTAX      ConfdString
    MAX-ACCESS  read-only
    STATUS      current
    DESCRIPTION "number of total failed IPSEC tunnels"
    ::= { affirmedSecurityStatisticsNetworkContextEntry 8 }

affirmedSecurityStatisticsNetworkContextCurrentTransforms OBJECT-TYPE
    SYNTAX      ConfdString
    MAX-ACCESS  read-only
    STATUS      current
    DESCRIPTION "number of current transforms"
    ::= { affirmedSecurityStatisticsNetworkContextEntry 9 }

affirmedSecurityStatisticsNetworkContextTotalTransforms OBJECT-TYPE
    SYNTAX      ConfdString
    MAX-ACCESS  read-only
    STATUS      current
    DESCRIPTION "number of total transforms"
    ::= { affirmedSecurityStatisticsNetworkContextEntry 10 }

affirmedSecurityStatisticsNetworkContextRekeyedTransforms OBJECT-TYPE
    SYNTAX      ConfdString
    MAX-ACCESS  read-only
    STATUS      current
    DESCRIPTION "number of rekeyed transforms"
    ::= { affirmedSecurityStatisticsNetworkContextEntry 11 }

affirmedSecurityStatisticsNetworkContextCurrentRules OBJECT-TYPE
    SYNTAX      ConfdString
    MAX-ACCESS  read-only
    STATUS      current
    DESCRIPTION "number of current rules"
    ::= { affirmedSecurityStatisticsNetworkContextEntry 12 }

affirmedSecurityStatisticsNetworkContextTotalRules OBJECT-TYPE
    SYNTAX      ConfdString
    MAX-ACCESS  read-only
    STATUS      current
    DESCRIPTION "number of total rules"
    ::= { affirmedSecurityStatisticsNetworkContextEntry 13 }

affirmedSecurityStatisticsNetworkContextCurrentFlows OBJECT-TYPE
    SYNTAX      ConfdString
    MAX-ACCESS  read-only
    STATUS      current
    DESCRIPTION "number of current flows"
    ::= { affirmedSecurityStatisticsNetworkContextEntry 14 }

affirmedSecurityStatisticsNetworkContextTotalFlows OBJECT-TYPE
    SYNTAX      ConfdString
    MAX-ACCESS  read-only
    STATUS      current
    DESCRIPTION "number of total flows"
    ::= { affirmedSecurityStatisticsNetworkContextEntry 15 }

affirmedSecurityStatisticsRuleTable OBJECT-TYPE
    SYNTAX      SEQUENCE OF AffirmedSecurityStatisticsRuleEntry
    MAX-ACCESS  not-accessible
    STATUS      deprecated
    DESCRIPTION ""
    ::= { affirmedSecurityStatistics 2 }

affirmedSecurityStatisticsRuleEntry OBJECT-TYPE
    SYNTAX      AffirmedSecurityStatisticsRuleEntry
    MAX-ACCESS  not-accessible
    STATUS      deprecated
    DESCRIPTION ""
    INDEX { affirmedSecurityStatisticsRuleNetworkContext, affirmedSecurityStatisticsRuleName }
        ::= { affirmedSecurityStatisticsRuleTable 1 }

AffirmedSecurityStatisticsRuleEntry ::=
    SEQUENCE {
        affirmedSecurityStatisticsRuleNetworkContext String,
        affirmedSecurityStatisticsRuleName String,
        affirmedSecurityStatisticsRuleTimesUsed ConfdString,
        affirmedSecurityStatisticsRuleCurrentFlows ConfdString,
        affirmedSecurityStatisticsRuleTotalFlows ConfdString,
        affirmedSecurityStatisticsRuleToTransformIndex Unsigned32,
        affirmedSecurityStatisticsRuleFromTransformIndex Unsigned32
    }

affirmedSecurityStatisticsRuleNetworkContext OBJECT-TYPE
    SYNTAX      String
    MAX-ACCESS  not-accessible
    STATUS      current
    DESCRIPTION "network context for this rule"
    ::= { affirmedSecurityStatisticsRuleEntry 1 }

affirmedSecurityStatisticsRuleName OBJECT-TYPE
    SYNTAX      String
    MAX-ACCESS  not-accessible
    STATUS      current
    DESCRIPTION "name of this rule"
    ::= { affirmedSecurityStatisticsRuleEntry 2 }

affirmedSecurityStatisticsRuleTimesUsed OBJECT-TYPE
    SYNTAX      ConfdString
    MAX-ACCESS  read-only
    STATUS      current
    DESCRIPTION "number of times this rule has been used"
    ::= { affirmedSecurityStatisticsRuleEntry 3 }

affirmedSecurityStatisticsRuleCurrentFlows OBJECT-TYPE
    SYNTAX      ConfdString
    MAX-ACCESS  read-only
    STATUS      current
    DESCRIPTION "number of current flows using this rule"
    ::= { affirmedSecurityStatisticsRuleEntry 4 }

affirmedSecurityStatisticsRuleTotalFlows OBJECT-TYPE
    SYNTAX      ConfdString
    MAX-ACCESS  read-only
    STATUS      current
    DESCRIPTION "number of total flows using this rule"
    ::= { affirmedSecurityStatisticsRuleEntry 5 }

affirmedSecurityStatisticsRuleToTransformIndex OBJECT-TYPE
    SYNTAX      Unsigned32
    MAX-ACCESS  read-only
    STATUS      current
    DESCRIPTION "index of the to-transform associated with this high level rule"
    ::= { affirmedSecurityStatisticsRuleEntry 6 }

affirmedSecurityStatisticsRuleFromTransformIndex OBJECT-TYPE
    SYNTAX      Unsigned32
    MAX-ACCESS  read-only
    STATUS      current
    DESCRIPTION "index of the from-transform associated with this high level rule"
    ::= { affirmedSecurityStatisticsRuleEntry 7 }

affirmedSecurityStatisticsRuleStatsTable OBJECT-TYPE
    SYNTAX      SEQUENCE OF AffirmedSecurityStatisticsRuleStatsEntry
    MAX-ACCESS  not-accessible
    STATUS      current
    DESCRIPTION ""
    ::= { affirmedSecurityStatistics 8 }

affirmedSecurityStatisticsRuleStatsEntry OBJECT-TYPE
    SYNTAX      AffirmedSecurityStatisticsRuleStatsEntry
    MAX-ACCESS  not-accessible
    STATUS      current
    DESCRIPTION ""
    INDEX { affirmedSecurityStatisticsRuleStatsNetworkContext, affirmedSecurityStatisticsRuleStatsName }
        ::= { affirmedSecurityStatisticsRuleStatsTable 1 }

AffirmedSecurityStatisticsRuleStatsEntry ::=
    SEQUENCE {
        affirmedSecurityStatisticsRuleStatsNetworkContext String,
        affirmedSecurityStatisticsRuleStatsName String,
        affirmedSecurityStatisticsRuleStatsCurrentFlows ConfdString,
        affirmedSecurityStatisticsRuleStatsTotalFlows ConfdString,
        affirmedSecurityStatisticsRuleStatsSecmNumFrlDropIngressCnts ConfdString,
        affirmedSecurityStatisticsRuleStatsSecmNumPrlDropIngressCnts ConfdString,
        affirmedSecurityStatisticsRuleStatsSecmNumFrlDropEgressCnts ConfdString,
        affirmedSecurityStatisticsRuleStatsSecmNumPrlDropEgressCnts ConfdString,
        affirmedSecurityStatisticsRuleStatsSecmNumFrlAvailableTokens ConfdString,
        affirmedSecurityStatisticsRuleStatsSecmNumPrlAvailableTokens ConfdString
    }

affirmedSecurityStatisticsRuleStatsNetworkContext OBJECT-TYPE
    SYNTAX      String
    MAX-ACCESS  not-accessible
    STATUS      current
    DESCRIPTION "network context for this rule"
    ::= { affirmedSecurityStatisticsRuleStatsEntry 1 }

affirmedSecurityStatisticsRuleStatsName OBJECT-TYPE
    SYNTAX      String
    MAX-ACCESS  not-accessible
    STATUS      current
    DESCRIPTION "name of this rule"
    ::= { affirmedSecurityStatisticsRuleStatsEntry 2 }

affirmedSecurityStatisticsRuleStatsCurrentFlows OBJECT-TYPE
    SYNTAX      ConfdString
    MAX-ACCESS  read-only
    STATUS      current
    DESCRIPTION "number of current flows using this rule"
    ::= { affirmedSecurityStatisticsRuleStatsEntry 3 }

affirmedSecurityStatisticsRuleStatsTotalFlows OBJECT-TYPE
    SYNTAX      ConfdString
    MAX-ACCESS  read-only
    STATUS      current
    DESCRIPTION "number of total flows that used this rule"
    ::= { affirmedSecurityStatisticsRuleStatsEntry 4 }

affirmedSecurityStatisticsRuleStatsSecmNumFrlDropIngressCnts OBJECT-TYPE
    SYNTAX      ConfdString
    MAX-ACCESS  read-only
    STATUS      current
    DESCRIPTION "number of total ingress flows dropped due to flow-rate-limit configuration in this rule"
    ::= { affirmedSecurityStatisticsRuleStatsEntry 5 }

affirmedSecurityStatisticsRuleStatsSecmNumPrlDropIngressCnts OBJECT-TYPE
    SYNTAX      ConfdString
    MAX-ACCESS  read-only
    STATUS      current
    DESCRIPTION "number of total ingress packets dropped due to packet-rate-limit configuration in this rule"
    ::= { affirmedSecurityStatisticsRuleStatsEntry 6 }

affirmedSecurityStatisticsRuleStatsSecmNumFrlDropEgressCnts OBJECT-TYPE
    SYNTAX      ConfdString
    MAX-ACCESS  read-only
    STATUS      current
    DESCRIPTION "number of total egress flows dropped due to packet-rate-limit configuration in this rule"
    ::= { affirmedSecurityStatisticsRuleStatsEntry 7 }

affirmedSecurityStatisticsRuleStatsSecmNumPrlDropEgressCnts OBJECT-TYPE
    SYNTAX      ConfdString
    MAX-ACCESS  read-only
    STATUS      current
    DESCRIPTION "number of total egress packets dropped due to packet-rate-limit configuration in this rule"
    ::= { affirmedSecurityStatisticsRuleStatsEntry 8 }

affirmedSecurityStatisticsRuleStatsSecmNumFrlAvailableTokens OBJECT-TYPE
    SYNTAX      ConfdString
    MAX-ACCESS  read-only
    STATUS      deprecated
    DESCRIPTION "number of total available tokens in Active flow-rate-limit Bucket in this rule"
    ::= { affirmedSecurityStatisticsRuleStatsEntry 9 }

affirmedSecurityStatisticsRuleStatsSecmNumPrlAvailableTokens OBJECT-TYPE
    SYNTAX      ConfdString
    MAX-ACCESS  read-only
    STATUS      deprecated
    DESCRIPTION "number of total available tokens in Active packet-rate-limit Bucket in this rule"
    ::= { affirmedSecurityStatisticsRuleStatsEntry 10 }

affirmedSecurityStatisticsTunnelTable OBJECT-TYPE
    SYNTAX      SEQUENCE OF AffirmedSecurityStatisticsTunnelEntry
    MAX-ACCESS  not-accessible
    STATUS      current
    DESCRIPTION ""
    ::= { affirmedSecurityStatistics 6 }

affirmedSecurityStatisticsTunnelEntry OBJECT-TYPE
    SYNTAX      AffirmedSecurityStatisticsTunnelEntry
    MAX-ACCESS  not-accessible
    STATUS      current
    DESCRIPTION ""
    INDEX { affirmedSecurityStatisticsTunnelNetworkContext, affirmedSecurityStatisticsTunnelSecurityServiceId, affirmedSecurityStatisticsTunnelIndex }
        ::= { affirmedSecurityStatisticsTunnelTable 1 }

AffirmedSecurityStatisticsTunnelEntry ::=
    SEQUENCE {
        affirmedSecurityStatisticsTunnelNetworkContext String,
        affirmedSecurityStatisticsTunnelSecurityServiceId Unsigned32,
        affirmedSecurityStatisticsTunnelIndex Unsigned32,
        affirmedSecurityStatisticsTunnelCurrentFlows ConfdString,
        affirmedSecurityStatisticsTunnelRekeys ConfdString,
        affirmedSecurityStatisticsTunnelInPackets ConfdString,
        affirmedSecurityStatisticsTunnelInOctets ConfdString,
        affirmedSecurityStatisticsTunnelInDropPackets ConfdString,
        affirmedSecurityStatisticsTunnelOutPackets ConfdString,
        affirmedSecurityStatisticsTunnelOutOctets ConfdString,
        affirmedSecurityStatisticsTunnelOutDropPackets ConfdString,
        affirmedSecurityStatisticsTunnelHmacFailurePackets ConfdString,
        affirmedSecurityStatisticsTunnelRemoteIpAddress String
    }

affirmedSecurityStatisticsTunnelNetworkContext OBJECT-TYPE
    SYNTAX      String
    MAX-ACCESS  not-accessible
    STATUS      current
    DESCRIPTION "network context for this transform"
    ::= { affirmedSecurityStatisticsTunnelEntry 1 }

affirmedSecurityStatisticsTunnelSecurityServiceId OBJECT-TYPE
    SYNTAX      Unsigned32
    MAX-ACCESS  not-accessible
    STATUS      current
    DESCRIPTION "internal ID for the SPM"
    ::= { affirmedSecurityStatisticsTunnelEntry 2 }

affirmedSecurityStatisticsTunnelIndex OBJECT-TYPE
    SYNTAX      Unsigned32
    MAX-ACCESS  not-accessible
    STATUS      current
    DESCRIPTION "internal index of this transform"
    ::= { affirmedSecurityStatisticsTunnelEntry 3 }

affirmedSecurityStatisticsTunnelCurrentFlows OBJECT-TYPE
    SYNTAX      ConfdString
    MAX-ACCESS  read-only
    STATUS      current
    DESCRIPTION "number of current flows using this transform"
    ::= { affirmedSecurityStatisticsTunnelEntry 4 }

affirmedSecurityStatisticsTunnelRekeys OBJECT-TYPE
    SYNTAX      ConfdString
    MAX-ACCESS  read-only
    STATUS      current
    DESCRIPTION "number of rekeys for this transform"
    ::= { affirmedSecurityStatisticsTunnelEntry 5 }

affirmedSecurityStatisticsTunnelInPackets OBJECT-TYPE
    SYNTAX      ConfdString
    MAX-ACCESS  read-only
    STATUS      current
    DESCRIPTION "packets received by this transform"
    ::= { affirmedSecurityStatisticsTunnelEntry 6 }

affirmedSecurityStatisticsTunnelInOctets OBJECT-TYPE
    SYNTAX      ConfdString
    MAX-ACCESS  read-only
    STATUS      current
    DESCRIPTION "octets received by this transform"
    ::= { affirmedSecurityStatisticsTunnelEntry 7 }

affirmedSecurityStatisticsTunnelInDropPackets OBJECT-TYPE
    SYNTAX      ConfdString
    MAX-ACCESS  read-only
    STATUS      current
    DESCRIPTION "incoming packets dropped by this transform"
    ::= { affirmedSecurityStatisticsTunnelEntry 8 }

affirmedSecurityStatisticsTunnelOutPackets OBJECT-TYPE
    SYNTAX      ConfdString
    MAX-ACCESS  read-only
    STATUS      current
    DESCRIPTION "packets sent by this transform"
    ::= { affirmedSecurityStatisticsTunnelEntry 9 }

affirmedSecurityStatisticsTunnelOutOctets OBJECT-TYPE
    SYNTAX      ConfdString
    MAX-ACCESS  read-only
    STATUS      current
    DESCRIPTION "octets sent by this transform"
    ::= { affirmedSecurityStatisticsTunnelEntry 10 }

affirmedSecurityStatisticsTunnelOutDropPackets OBJECT-TYPE
    SYNTAX      ConfdString
    MAX-ACCESS  read-only
    STATUS      current
    DESCRIPTION "outgoing packets dropped by this transform"
    ::= { affirmedSecurityStatisticsTunnelEntry 11 }

affirmedSecurityStatisticsTunnelHmacFailurePackets OBJECT-TYPE
    SYNTAX      ConfdString
    MAX-ACCESS  read-only
    STATUS      current
    DESCRIPTION "packets dropped due to HMAC failure by this transform"
    ::= { affirmedSecurityStatisticsTunnelEntry 12 }

affirmedSecurityStatisticsTunnelRemoteIpAddress OBJECT-TYPE
    SYNTAX      String
    MAX-ACCESS  read-only
    STATUS      current
    DESCRIPTION "IP addressof remote endpoint"
    ::= { affirmedSecurityStatisticsTunnelEntry 13 }

affirmedSecurityStatisticsTransformTable OBJECT-TYPE
    SYNTAX      SEQUENCE OF AffirmedSecurityStatisticsTransformEntry
    MAX-ACCESS  not-accessible
    STATUS      deprecated
    DESCRIPTION ""
    ::= { affirmedSecurityStatistics 3 }

affirmedSecurityStatisticsTransformEntry OBJECT-TYPE
    SYNTAX      AffirmedSecurityStatisticsTransformEntry
    MAX-ACCESS  not-accessible
    STATUS      deprecated
    DESCRIPTION ""
    INDEX { affirmedSecurityStatisticsTransformNetworkContext, affirmedSecurityStatisticsTransformIndex }
        ::= { affirmedSecurityStatisticsTransformTable 1 }

AffirmedSecurityStatisticsTransformEntry ::=
    SEQUENCE {
        affirmedSecurityStatisticsTransformNetworkContext String,
        affirmedSecurityStatisticsTransformIndex Unsigned32,
        affirmedSecurityStatisticsTransformCurrentFlows ConfdString,
        affirmedSecurityStatisticsTransformRekeys ConfdString,
        affirmedSecurityStatisticsTransformInPackets ConfdString,
        affirmedSecurityStatisticsTransformInOctets ConfdString,
        affirmedSecurityStatisticsTransformInDropPackets ConfdString,
        affirmedSecurityStatisticsTransformOutPackets ConfdString,
        affirmedSecurityStatisticsTransformOutOctets ConfdString,
        affirmedSecurityStatisticsTransformOutDropPackets ConfdString,
        affirmedSecurityStatisticsTransformHmacFailurePackets ConfdString
    }

affirmedSecurityStatisticsTransformNetworkContext OBJECT-TYPE
    SYNTAX      String
    MAX-ACCESS  not-accessible
    STATUS      current
    DESCRIPTION "network context for this transform"
    ::= { affirmedSecurityStatisticsTransformEntry 1 }

affirmedSecurityStatisticsTransformIndex OBJECT-TYPE
    SYNTAX      Unsigned32
    MAX-ACCESS  not-accessible
    STATUS      current
    DESCRIPTION "internal index of this transform"
    ::= { affirmedSecurityStatisticsTransformEntry 2 }

affirmedSecurityStatisticsTransformCurrentFlows OBJECT-TYPE
    SYNTAX      ConfdString
    MAX-ACCESS  read-only
    STATUS      current
    DESCRIPTION "number of current flows using this transform"
    ::= { affirmedSecurityStatisticsTransformEntry 3 }

affirmedSecurityStatisticsTransformRekeys OBJECT-TYPE
    SYNTAX      ConfdString
    MAX-ACCESS  read-only
    STATUS      current
    DESCRIPTION "number of rekeys for this transform"
    ::= { affirmedSecurityStatisticsTransformEntry 4 }

affirmedSecurityStatisticsTransformInPackets OBJECT-TYPE
    SYNTAX      ConfdString
    MAX-ACCESS  read-only
    STATUS      current
    DESCRIPTION "packets received by this transform"
    ::= { affirmedSecurityStatisticsTransformEntry 5 }

affirmedSecurityStatisticsTransformInOctets OBJECT-TYPE
    SYNTAX      ConfdString
    MAX-ACCESS  read-only
    STATUS      current
    DESCRIPTION "octets received by this transform"
    ::= { affirmedSecurityStatisticsTransformEntry 6 }

affirmedSecurityStatisticsTransformInDropPackets OBJECT-TYPE
    SYNTAX      ConfdString
    MAX-ACCESS  read-only
    STATUS      current
    DESCRIPTION "incoming packets dropped by this transform"
    ::= { affirmedSecurityStatisticsTransformEntry 7 }

affirmedSecurityStatisticsTransformOutPackets OBJECT-TYPE
    SYNTAX      ConfdString
    MAX-ACCESS  read-only
    STATUS      current
    DESCRIPTION "packets sent by this transform"
    ::= { affirmedSecurityStatisticsTransformEntry 8 }

affirmedSecurityStatisticsTransformOutOctets OBJECT-TYPE
    SYNTAX      ConfdString
    MAX-ACCESS  read-only
    STATUS      current
    DESCRIPTION "octets sent by this transform"
    ::= { affirmedSecurityStatisticsTransformEntry 9 }

affirmedSecurityStatisticsTransformOutDropPackets OBJECT-TYPE
    SYNTAX      ConfdString
    MAX-ACCESS  read-only
    STATUS      current
    DESCRIPTION "outgoing packets dropped by this transform"
    ::= { affirmedSecurityStatisticsTransformEntry 10 }

affirmedSecurityStatisticsTransformHmacFailurePackets OBJECT-TYPE
    SYNTAX      ConfdString
    MAX-ACCESS  read-only
    STATUS      current
    DESCRIPTION "packets dropped due to HMAC failure by this transform"
    ::= { affirmedSecurityStatisticsTransformEntry 11 }

affirmedSecurityStatisticsSecureNdSummaryTable OBJECT-TYPE
    SYNTAX      SEQUENCE OF AffirmedSecurityStatisticsSecureNdSummaryEntry
    MAX-ACCESS  not-accessible
    STATUS      deprecated
    DESCRIPTION ""
    ::= { affirmedSecurityStatistics 12 }

affirmedSecurityStatisticsSecureNdSummaryEntry OBJECT-TYPE
    SYNTAX      AffirmedSecurityStatisticsSecureNdSummaryEntry
    MAX-ACCESS  not-accessible
    STATUS      deprecated
    DESCRIPTION ""
    INDEX { affirmedSecurityStatisticsSecureNdSummaryDummyIndex }
        ::= { affirmedSecurityStatisticsSecureNdSummaryTable 1 }

AffirmedSecurityStatisticsSecureNdSummaryEntry ::=
    SEQUENCE {
        affirmedSecurityStatisticsSecureNdSummaryDummyIndex Unsigned32,
        affirmedSecurityStatisticsSecureNdSummaryInstanceId ConfdString,
        affirmedSecurityStatisticsSecureNdSummaryRouterAddress String,
        affirmedSecurityStatisticsSecureNdSummarySubnetPrefix String,
        affirmedSecurityStatisticsSecureNdSummaryNumNeighborsDiscovered ConfdString
    }

affirmedSecurityStatisticsSecureNdSummaryDummyIndex OBJECT-TYPE
    SYNTAX      Unsigned32
    MAX-ACCESS  not-accessible
    STATUS      current
    DESCRIPTION ""
    ::= { affirmedSecurityStatisticsSecureNdSummaryEntry 1 }

affirmedSecurityStatisticsSecureNdSummaryInstanceId OBJECT-TYPE
    SYNTAX      ConfdString
    MAX-ACCESS  read-only
    STATUS      current
    DESCRIPTION "Sendd task instance id"
    ::= { affirmedSecurityStatisticsSecureNdSummaryEntry 2 }

affirmedSecurityStatisticsSecureNdSummaryRouterAddress OBJECT-TYPE
    SYNTAX      String
    MAX-ACCESS  read-only
    STATUS      current
    DESCRIPTION "Address of the discovered router"
    ::= { affirmedSecurityStatisticsSecureNdSummaryEntry 3 }

affirmedSecurityStatisticsSecureNdSummarySubnetPrefix OBJECT-TYPE
    SYNTAX      String
    MAX-ACCESS  read-only
    STATUS      current
    DESCRIPTION "Subnet prefix"
    ::= { affirmedSecurityStatisticsSecureNdSummaryEntry 4 }

affirmedSecurityStatisticsSecureNdSummaryNumNeighborsDiscovered OBJECT-TYPE
    SYNTAX      ConfdString
    MAX-ACCESS  read-only
    STATUS      current
    DESCRIPTION "Number of discovered neighbors"
    ::= { affirmedSecurityStatisticsSecureNdSummaryEntry 5 }

affirmedSecurityStatisticsSecureNdStatsTable OBJECT-TYPE
    SYNTAX      SEQUENCE OF AffirmedSecurityStatisticsSecureNdStatsEntry
    MAX-ACCESS  not-accessible
    STATUS      deprecated
    DESCRIPTION ""
    ::= { affirmedSecurityStatistics 13 }

affirmedSecurityStatisticsSecureNdStatsEntry OBJECT-TYPE
    SYNTAX      AffirmedSecurityStatisticsSecureNdStatsEntry
    MAX-ACCESS  not-accessible
    STATUS      deprecated
    DESCRIPTION ""
    INDEX { affirmedSecurityStatisticsSecureNdStatsNetworkCtx, affirmedSecurityStatisticsSecureNdStatsIfIdx }
        ::= { affirmedSecurityStatisticsSecureNdStatsTable 1 }

AffirmedSecurityStatisticsSecureNdStatsEntry ::=
    SEQUENCE {
        affirmedSecurityStatisticsSecureNdStatsNetworkCtx String,
        affirmedSecurityStatisticsSecureNdStatsIfIdx Unsigned32,
        affirmedSecurityStatisticsSecureNdStatsReceivedNS ConfdString,
        affirmedSecurityStatisticsSecureNdStatsReceivedNA ConfdString,
        affirmedSecurityStatisticsSecureNdStatsReceivedRS ConfdString,
        affirmedSecurityStatisticsSecureNdStatsReceivedRA ConfdString,
        affirmedSecurityStatisticsSecureNdStatsReceivedCPS ConfdString,
        affirmedSecurityStatisticsSecureNdStatsReceivedCPA ConfdString,
        affirmedSecurityStatisticsSecureNdStatsSentNS ConfdString,
        affirmedSecurityStatisticsSecureNdStatsSentNA ConfdString,
        affirmedSecurityStatisticsSecureNdStatsSentRS ConfdString,
        affirmedSecurityStatisticsSecureNdStatsSentRA ConfdString,
        affirmedSecurityStatisticsSecureNdStatsSentCPS ConfdString,
        affirmedSecurityStatisticsSecureNdStatsSentCPA ConfdString,
        affirmedSecurityStatisticsSecureNdStatsDroppedNS ConfdString,
        affirmedSecurityStatisticsSecureNdStatsDroppedNA ConfdString,
        affirmedSecurityStatisticsSecureNdStatsDroppedRS ConfdString,
        affirmedSecurityStatisticsSecureNdStatsDroppedRA ConfdString,
        affirmedSecurityStatisticsSecureNdStatsDroppedCPS ConfdString,
        affirmedSecurityStatisticsSecureNdStatsDroppedCPA ConfdString
    }

affirmedSecurityStatisticsSecureNdStatsNetworkCtx OBJECT-TYPE
    SYNTAX      String
    MAX-ACCESS  not-accessible
    STATUS      current
    DESCRIPTION "Network context related to SeND statistics"
    ::= { affirmedSecurityStatisticsSecureNdStatsEntry 1 }

affirmedSecurityStatisticsSecureNdStatsIfIdx OBJECT-TYPE
    SYNTAX      Unsigned32
    MAX-ACCESS  not-accessible
    STATUS      current
    DESCRIPTION "IP interface index"
    ::= { affirmedSecurityStatisticsSecureNdStatsEntry 2 }

affirmedSecurityStatisticsSecureNdStatsReceivedNS OBJECT-TYPE
    SYNTAX      ConfdString
    MAX-ACCESS  read-only
    STATUS      current
    DESCRIPTION "Number of SEND packets NS received"
    ::= { affirmedSecurityStatisticsSecureNdStatsEntry 3 }

affirmedSecurityStatisticsSecureNdStatsReceivedNA OBJECT-TYPE
    SYNTAX      ConfdString
    MAX-ACCESS  read-only
    STATUS      current
    DESCRIPTION "Number of SEND packets NA received"
    ::= { affirmedSecurityStatisticsSecureNdStatsEntry 4 }

affirmedSecurityStatisticsSecureNdStatsReceivedRS OBJECT-TYPE
    SYNTAX      ConfdString
    MAX-ACCESS  read-only
    STATUS      current
    DESCRIPTION "Number of SEND packets RS received"
    ::= { affirmedSecurityStatisticsSecureNdStatsEntry 5 }

affirmedSecurityStatisticsSecureNdStatsReceivedRA OBJECT-TYPE
    SYNTAX      ConfdString
    MAX-ACCESS  read-only
    STATUS      current
    DESCRIPTION "Number of SEND packets RA received"
    ::= { affirmedSecurityStatisticsSecureNdStatsEntry 6 }

affirmedSecurityStatisticsSecureNdStatsReceivedCPS OBJECT-TYPE
    SYNTAX      ConfdString
    MAX-ACCESS  read-only
    STATUS      current
    DESCRIPTION "Number of SEND packets CPS received"
    ::= { affirmedSecurityStatisticsSecureNdStatsEntry 7 }

affirmedSecurityStatisticsSecureNdStatsReceivedCPA OBJECT-TYPE
    SYNTAX      ConfdString
    MAX-ACCESS  read-only
    STATUS      current
    DESCRIPTION "Number of SEND packets CPA received"
    ::= { affirmedSecurityStatisticsSecureNdStatsEntry 8 }

affirmedSecurityStatisticsSecureNdStatsSentNS OBJECT-TYPE
    SYNTAX      ConfdString
    MAX-ACCESS  read-only
    STATUS      current
    DESCRIPTION "Number of of SEND packets NS sent"
    ::= { affirmedSecurityStatisticsSecureNdStatsEntry 9 }

affirmedSecurityStatisticsSecureNdStatsSentNA OBJECT-TYPE
    SYNTAX      ConfdString
    MAX-ACCESS  read-only
    STATUS      current
    DESCRIPTION "Number of of SEND packets NA sent"
    ::= { affirmedSecurityStatisticsSecureNdStatsEntry 10 }

affirmedSecurityStatisticsSecureNdStatsSentRS OBJECT-TYPE
    SYNTAX      ConfdString
    MAX-ACCESS  read-only
    STATUS      current
    DESCRIPTION "Number of of SEND packets RS sent"
    ::= { affirmedSecurityStatisticsSecureNdStatsEntry 11 }

affirmedSecurityStatisticsSecureNdStatsSentRA OBJECT-TYPE
    SYNTAX      ConfdString
    MAX-ACCESS  read-only
    STATUS      current
    DESCRIPTION "Number of of SEND packets RA sent"
    ::= { affirmedSecurityStatisticsSecureNdStatsEntry 12 }

affirmedSecurityStatisticsSecureNdStatsSentCPS OBJECT-TYPE
    SYNTAX      ConfdString
    MAX-ACCESS  read-only
    STATUS      current
    DESCRIPTION "Number of of SEND packets CPS sent"
    ::= { affirmedSecurityStatisticsSecureNdStatsEntry 13 }

affirmedSecurityStatisticsSecureNdStatsSentCPA OBJECT-TYPE
    SYNTAX      ConfdString
    MAX-ACCESS  read-only
    STATUS      current
    DESCRIPTION "Number of of SEND packets CPA sent"
    ::= { affirmedSecurityStatisticsSecureNdStatsEntry 14 }

affirmedSecurityStatisticsSecureNdStatsDroppedNS OBJECT-TYPE
    SYNTAX      ConfdString
    MAX-ACCESS  read-only
    STATUS      current
    DESCRIPTION "Number of of SEND packets NS dropped"
    ::= { affirmedSecurityStatisticsSecureNdStatsEntry 15 }

affirmedSecurityStatisticsSecureNdStatsDroppedNA OBJECT-TYPE
    SYNTAX      ConfdString
    MAX-ACCESS  read-only
    STATUS      current
    DESCRIPTION "Number of SEND packets NA dropped"
    ::= { affirmedSecurityStatisticsSecureNdStatsEntry 16 }

affirmedSecurityStatisticsSecureNdStatsDroppedRS OBJECT-TYPE
    SYNTAX      ConfdString
    MAX-ACCESS  read-only
    STATUS      current
    DESCRIPTION "Number of SEND packets RS dropped"
    ::= { affirmedSecurityStatisticsSecureNdStatsEntry 17 }

affirmedSecurityStatisticsSecureNdStatsDroppedRA OBJECT-TYPE
    SYNTAX      ConfdString
    MAX-ACCESS  read-only
    STATUS      current
    DESCRIPTION "Number of SEND packets RA dropped"
    ::= { affirmedSecurityStatisticsSecureNdStatsEntry 18 }

affirmedSecurityStatisticsSecureNdStatsDroppedCPS OBJECT-TYPE
    SYNTAX      ConfdString
    MAX-ACCESS  read-only
    STATUS      current
    DESCRIPTION "Number of SEND packets CPS dropped"
    ::= { affirmedSecurityStatisticsSecureNdStatsEntry 19 }

affirmedSecurityStatisticsSecureNdStatsDroppedCPA OBJECT-TYPE
    SYNTAX      ConfdString
    MAX-ACCESS  read-only
    STATUS      current
    DESCRIPTION "Number of SEND packets CPA dropped"
    ::= { affirmedSecurityStatisticsSecureNdStatsEntry 20 }

affirmedSecurityStatisticsSecureNdSummarynewTable OBJECT-TYPE
    SYNTAX      SEQUENCE OF AffirmedSecurityStatisticsSecureNdSummarynewEntry
    MAX-ACCESS  not-accessible
    STATUS      current
    DESCRIPTION ""
    ::= { affirmedSecurityStatistics 14 }

affirmedSecurityStatisticsSecureNdSummarynewEntry OBJECT-TYPE
    SYNTAX      AffirmedSecurityStatisticsSecureNdSummarynewEntry
    MAX-ACCESS  not-accessible
    STATUS      current
    DESCRIPTION ""
    INDEX { affirmedSecurityStatisticsSecureNdSummarynewNetworkCtx, affirmedSecurityStatisticsSecureNdSummarynewIfName }
        ::= { affirmedSecurityStatisticsSecureNdSummarynewTable 1 }

AffirmedSecurityStatisticsSecureNdSummarynewEntry ::=
    SEQUENCE {
        affirmedSecurityStatisticsSecureNdSummarynewNetworkCtx String,
        affirmedSecurityStatisticsSecureNdSummarynewIfName String,
        affirmedSecurityStatisticsSecureNdSummarynewRouterAddress String,
        affirmedSecurityStatisticsSecureNdSummarynewSubnetPrefix String,
        affirmedSecurityStatisticsSecureNdSummarynewRsaKeyPairName String,
        affirmedSecurityStatisticsSecureNdSummarynewTrustAnchorName String,
        affirmedSecurityStatisticsSecureNdSummarynewCgaAddr String
    }

affirmedSecurityStatisticsSecureNdSummarynewNetworkCtx OBJECT-TYPE
    SYNTAX      String
    MAX-ACCESS  not-accessible
    STATUS      current
    DESCRIPTION "Network context related to SeND statistics"
    ::= { affirmedSecurityStatisticsSecureNdSummarynewEntry 1 }

affirmedSecurityStatisticsSecureNdSummarynewIfName OBJECT-TYPE
    SYNTAX      String
    MAX-ACCESS  not-accessible
    STATUS      current
    DESCRIPTION "IP interface name"
    ::= { affirmedSecurityStatisticsSecureNdSummarynewEntry 2 }

affirmedSecurityStatisticsSecureNdSummarynewRouterAddress OBJECT-TYPE
    SYNTAX      String
    MAX-ACCESS  read-only
    STATUS      current
    DESCRIPTION "Address of the discovered router"
    ::= { affirmedSecurityStatisticsSecureNdSummarynewEntry 3 }

affirmedSecurityStatisticsSecureNdSummarynewSubnetPrefix OBJECT-TYPE
    SYNTAX      String
    MAX-ACCESS  read-only
    STATUS      current
    DESCRIPTION "Subnet prefix"
    ::= { affirmedSecurityStatisticsSecureNdSummarynewEntry 4 }

affirmedSecurityStatisticsSecureNdSummarynewRsaKeyPairName OBJECT-TYPE
    SYNTAX      String
    MAX-ACCESS  read-only
    STATUS      current
    DESCRIPTION "RSA key-pair name"
    ::= { affirmedSecurityStatisticsSecureNdSummarynewEntry 5 }

affirmedSecurityStatisticsSecureNdSummarynewTrustAnchorName OBJECT-TYPE
    SYNTAX      String
    MAX-ACCESS  read-only
    STATUS      current
    DESCRIPTION "Trust Anchor name"
    ::= { affirmedSecurityStatisticsSecureNdSummarynewEntry 6 }

affirmedSecurityStatisticsSecureNdSummarynewCgaAddr OBJECT-TYPE
    SYNTAX      String
    MAX-ACCESS  read-only
    STATUS      current
    DESCRIPTION "CGA address"
    ::= { affirmedSecurityStatisticsSecureNdSummarynewEntry 7 }

affirmedSecurityStatisticsSecureNdStatsnewTable OBJECT-TYPE
    SYNTAX      SEQUENCE OF AffirmedSecurityStatisticsSecureNdStatsnewEntry
    MAX-ACCESS  not-accessible
    STATUS      deprecated
    DESCRIPTION ""
    ::= { affirmedSecurityStatistics 15 }

affirmedSecurityStatisticsSecureNdStatsnewEntry OBJECT-TYPE
    SYNTAX      AffirmedSecurityStatisticsSecureNdStatsnewEntry
    MAX-ACCESS  not-accessible
    STATUS      deprecated
    DESCRIPTION ""
    INDEX { affirmedSecurityStatisticsSecureNdStatsnewNetworkCtx, affirmedSecurityStatisticsSecureNdStatsnewIfName }
        ::= { affirmedSecurityStatisticsSecureNdStatsnewTable 1 }

AffirmedSecurityStatisticsSecureNdStatsnewEntry ::=
    SEQUENCE {
        affirmedSecurityStatisticsSecureNdStatsnewNetworkCtx String,
        affirmedSecurityStatisticsSecureNdStatsnewIfName String,
        affirmedSecurityStatisticsSecureNdStatsnewReceivedNS ConfdString,
        affirmedSecurityStatisticsSecureNdStatsnewReceivedNA ConfdString,
        affirmedSecurityStatisticsSecureNdStatsnewReceivedRS ConfdString,
        affirmedSecurityStatisticsSecureNdStatsnewReceivedRA ConfdString,
        affirmedSecurityStatisticsSecureNdStatsnewReceivedCPS ConfdString,
        affirmedSecurityStatisticsSecureNdStatsnewReceivedCPA ConfdString,
        affirmedSecurityStatisticsSecureNdStatsnewSentNS ConfdString,
        affirmedSecurityStatisticsSecureNdStatsnewSentNA ConfdString,
        affirmedSecurityStatisticsSecureNdStatsnewSentRS ConfdString,
        affirmedSecurityStatisticsSecureNdStatsnewSentRA ConfdString,
        affirmedSecurityStatisticsSecureNdStatsnewSentCPS ConfdString,
        affirmedSecurityStatisticsSecureNdStatsnewSentCPA ConfdString,
        affirmedSecurityStatisticsSecureNdStatsnewDroppedNS ConfdString,
        affirmedSecurityStatisticsSecureNdStatsnewDroppedNA ConfdString,
        affirmedSecurityStatisticsSecureNdStatsnewDroppedRS ConfdString,
        affirmedSecurityStatisticsSecureNdStatsnewDroppedRA ConfdString,
        affirmedSecurityStatisticsSecureNdStatsnewDroppedCPS ConfdString,
        affirmedSecurityStatisticsSecureNdStatsnewDroppedCPA ConfdString
    }

affirmedSecurityStatisticsSecureNdStatsnewNetworkCtx OBJECT-TYPE
    SYNTAX      String
    MAX-ACCESS  not-accessible
    STATUS      current
    DESCRIPTION "Network context related to SeND statistics"
    ::= { affirmedSecurityStatisticsSecureNdStatsnewEntry 1 }

affirmedSecurityStatisticsSecureNdStatsnewIfName OBJECT-TYPE
    SYNTAX      String
    MAX-ACCESS  not-accessible
    STATUS      current
    DESCRIPTION "IP interface index"
    ::= { affirmedSecurityStatisticsSecureNdStatsnewEntry 2 }

affirmedSecurityStatisticsSecureNdStatsnewReceivedNS OBJECT-TYPE
    SYNTAX      ConfdString
    MAX-ACCESS  read-only
    STATUS      current
    DESCRIPTION "Number of SEND packets NS received"
    ::= { affirmedSecurityStatisticsSecureNdStatsnewEntry 3 }

affirmedSecurityStatisticsSecureNdStatsnewReceivedNA OBJECT-TYPE
    SYNTAX      ConfdString
    MAX-ACCESS  read-only
    STATUS      current
    DESCRIPTION "Number of SEND packets NA received"
    ::= { affirmedSecurityStatisticsSecureNdStatsnewEntry 4 }

affirmedSecurityStatisticsSecureNdStatsnewReceivedRS OBJECT-TYPE
    SYNTAX      ConfdString
    MAX-ACCESS  read-only
    STATUS      current
    DESCRIPTION "Number of SEND packets RS received"
    ::= { affirmedSecurityStatisticsSecureNdStatsnewEntry 5 }

affirmedSecurityStatisticsSecureNdStatsnewReceivedRA OBJECT-TYPE
    SYNTAX      ConfdString
    MAX-ACCESS  read-only
    STATUS      current
    DESCRIPTION "Number of SEND packets RA received"
    ::= { affirmedSecurityStatisticsSecureNdStatsnewEntry 6 }

affirmedSecurityStatisticsSecureNdStatsnewReceivedCPS OBJECT-TYPE
    SYNTAX      ConfdString
    MAX-ACCESS  read-only
    STATUS      current
    DESCRIPTION "Number of SEND packets CPS received"
    ::= { affirmedSecurityStatisticsSecureNdStatsnewEntry 7 }

affirmedSecurityStatisticsSecureNdStatsnewReceivedCPA OBJECT-TYPE
    SYNTAX      ConfdString
    MAX-ACCESS  read-only
    STATUS      current
    DESCRIPTION "Number of SEND packets CPA received"
    ::= { affirmedSecurityStatisticsSecureNdStatsnewEntry 8 }

affirmedSecurityStatisticsSecureNdStatsnewSentNS OBJECT-TYPE
    SYNTAX      ConfdString
    MAX-ACCESS  read-only
    STATUS      current
    DESCRIPTION "Number of of SEND packets NS sent"
    ::= { affirmedSecurityStatisticsSecureNdStatsnewEntry 9 }

affirmedSecurityStatisticsSecureNdStatsnewSentNA OBJECT-TYPE
    SYNTAX      ConfdString
    MAX-ACCESS  read-only
    STATUS      current
    DESCRIPTION "Number of of SEND packets NA sent"
    ::= { affirmedSecurityStatisticsSecureNdStatsnewEntry 10 }

affirmedSecurityStatisticsSecureNdStatsnewSentRS OBJECT-TYPE
    SYNTAX      ConfdString
    MAX-ACCESS  read-only
    STATUS      current
    DESCRIPTION "Number of of SEND packets RS sent"
    ::= { affirmedSecurityStatisticsSecureNdStatsnewEntry 11 }

affirmedSecurityStatisticsSecureNdStatsnewSentRA OBJECT-TYPE
    SYNTAX      ConfdString
    MAX-ACCESS  read-only
    STATUS      current
    DESCRIPTION "Number of of SEND packets RA sent"
    ::= { affirmedSecurityStatisticsSecureNdStatsnewEntry 12 }

affirmedSecurityStatisticsSecureNdStatsnewSentCPS OBJECT-TYPE
    SYNTAX      ConfdString
    MAX-ACCESS  read-only
    STATUS      current
    DESCRIPTION "Number of of SEND packets CPS sent"
    ::= { affirmedSecurityStatisticsSecureNdStatsnewEntry 13 }

affirmedSecurityStatisticsSecureNdStatsnewSentCPA OBJECT-TYPE
    SYNTAX      ConfdString
    MAX-ACCESS  read-only
    STATUS      current
    DESCRIPTION "Number of of SEND packets CPA sent"
    ::= { affirmedSecurityStatisticsSecureNdStatsnewEntry 14 }

affirmedSecurityStatisticsSecureNdStatsnewDroppedNS OBJECT-TYPE
    SYNTAX      ConfdString
    MAX-ACCESS  read-only
    STATUS      current
    DESCRIPTION "Number of of SEND packets NS dropped"
    ::= { affirmedSecurityStatisticsSecureNdStatsnewEntry 15 }

affirmedSecurityStatisticsSecureNdStatsnewDroppedNA OBJECT-TYPE
    SYNTAX      ConfdString
    MAX-ACCESS  read-only
    STATUS      current
    DESCRIPTION "Number of SEND packets NA dropped"
    ::= { affirmedSecurityStatisticsSecureNdStatsnewEntry 16 }

affirmedSecurityStatisticsSecureNdStatsnewDroppedRS OBJECT-TYPE
    SYNTAX      ConfdString
    MAX-ACCESS  read-only
    STATUS      current
    DESCRIPTION "Number of SEND packets RS dropped"
    ::= { affirmedSecurityStatisticsSecureNdStatsnewEntry 17 }

affirmedSecurityStatisticsSecureNdStatsnewDroppedRA OBJECT-TYPE
    SYNTAX      ConfdString
    MAX-ACCESS  read-only
    STATUS      current
    DESCRIPTION "Number of SEND packets RA dropped"
    ::= { affirmedSecurityStatisticsSecureNdStatsnewEntry 18 }

affirmedSecurityStatisticsSecureNdStatsnewDroppedCPS OBJECT-TYPE
    SYNTAX      ConfdString
    MAX-ACCESS  read-only
    STATUS      current
    DESCRIPTION "Number of SEND packets CPS dropped"
    ::= { affirmedSecurityStatisticsSecureNdStatsnewEntry 19 }

affirmedSecurityStatisticsSecureNdStatsnewDroppedCPA OBJECT-TYPE
    SYNTAX      ConfdString
    MAX-ACCESS  read-only
    STATUS      current
    DESCRIPTION "Number of SEND packets CPA dropped"
    ::= { affirmedSecurityStatisticsSecureNdStatsnewEntry 20 }

affirmedSecurityStatisticsSecureNdCGAstatsTable OBJECT-TYPE
    SYNTAX      SEQUENCE OF AffirmedSecurityStatisticsSecureNdCGAstatsEntry
    MAX-ACCESS  not-accessible
    STATUS      deprecated
    DESCRIPTION ""
    ::= { affirmedSecurityStatistics 16 }

affirmedSecurityStatisticsSecureNdCGAstatsEntry OBJECT-TYPE
    SYNTAX      AffirmedSecurityStatisticsSecureNdCGAstatsEntry
    MAX-ACCESS  not-accessible
    STATUS      deprecated
    DESCRIPTION ""
    INDEX { affirmedSecurityStatisticsSecureNdCGAstatsNetworkCtx, affirmedSecurityStatisticsSecureNdCGAstatsIfName }
        ::= { affirmedSecurityStatisticsSecureNdCGAstatsTable 1 }

AffirmedSecurityStatisticsSecureNdCGAstatsEntry ::=
    SEQUENCE {
        affirmedSecurityStatisticsSecureNdCGAstatsNetworkCtx String,
        affirmedSecurityStatisticsSecureNdCGAstatsIfName String,
        affirmedSecurityStatisticsSecureNdCGAstatsNumCGAadded ConfdString,
        affirmedSecurityStatisticsSecureNdCGAstatsNumCGAdeleted ConfdString,
        affirmedSecurityStatisticsSecureNdCGAstatsNumCGAmodified ConfdString,
        affirmedSecurityStatisticsSecureNdCGAstatsNumMCDadded ConfdString,
        affirmedSecurityStatisticsSecureNdCGAstatsNumMCDdeleted ConfdString,
        affirmedSecurityStatisticsSecureNdCGAstatsNumMCDmodified ConfdString
    }

affirmedSecurityStatisticsSecureNdCGAstatsNetworkCtx OBJECT-TYPE
    SYNTAX      String
    MAX-ACCESS  not-accessible
    STATUS      current
    DESCRIPTION "Network context related to SeND statistics"
    ::= { affirmedSecurityStatisticsSecureNdCGAstatsEntry 1 }

affirmedSecurityStatisticsSecureNdCGAstatsIfName OBJECT-TYPE
    SYNTAX      String
    MAX-ACCESS  not-accessible
    STATUS      current
    DESCRIPTION "IP interface name"
    ::= { affirmedSecurityStatisticsSecureNdCGAstatsEntry 2 }

affirmedSecurityStatisticsSecureNdCGAstatsNumCGAadded OBJECT-TYPE
    SYNTAX      ConfdString
    MAX-ACCESS  read-only
    STATUS      current
    DESCRIPTION "Number of CGA added"
    ::= { affirmedSecurityStatisticsSecureNdCGAstatsEntry 3 }

affirmedSecurityStatisticsSecureNdCGAstatsNumCGAdeleted OBJECT-TYPE
    SYNTAX      ConfdString
    MAX-ACCESS  read-only
    STATUS      current
    DESCRIPTION "Number of CGA deleted"
    ::= { affirmedSecurityStatisticsSecureNdCGAstatsEntry 4 }

affirmedSecurityStatisticsSecureNdCGAstatsNumCGAmodified OBJECT-TYPE
    SYNTAX      ConfdString
    MAX-ACCESS  read-only
    STATUS      current
    DESCRIPTION "Number of CGA modified"
    ::= { affirmedSecurityStatisticsSecureNdCGAstatsEntry 5 }

affirmedSecurityStatisticsSecureNdCGAstatsNumMCDadded OBJECT-TYPE
    SYNTAX      ConfdString
    MAX-ACCESS  read-only
    STATUS      current
    DESCRIPTION "Number of MCD added"
    ::= { affirmedSecurityStatisticsSecureNdCGAstatsEntry 6 }

affirmedSecurityStatisticsSecureNdCGAstatsNumMCDdeleted OBJECT-TYPE
    SYNTAX      ConfdString
    MAX-ACCESS  read-only
    STATUS      current
    DESCRIPTION "Number of MCD deleted"
    ::= { affirmedSecurityStatisticsSecureNdCGAstatsEntry 7 }

affirmedSecurityStatisticsSecureNdCGAstatsNumMCDmodified OBJECT-TYPE
    SYNTAX      ConfdString
    MAX-ACCESS  read-only
    STATUS      current
    DESCRIPTION "Number of MCD modified"
    ::= { affirmedSecurityStatisticsSecureNdCGAstatsEntry 8 }

affirmedSecurityStatisticsDataStatsTable OBJECT-TYPE
    SYNTAX      SEQUENCE OF AffirmedSecurityStatisticsDataStatsEntry
    MAX-ACCESS  not-accessible
    STATUS      deprecated
    DESCRIPTION ""
    ::= { affirmedSecurityStatistics 4 }

affirmedSecurityStatisticsDataStatsEntry OBJECT-TYPE
    SYNTAX      AffirmedSecurityStatisticsDataStatsEntry
    MAX-ACCESS  not-accessible
    STATUS      deprecated
    DESCRIPTION ""
    INDEX { affirmedSecurityStatisticsDataStatsDummyIndex }
        ::= { affirmedSecurityStatisticsDataStatsTable 1 }

AffirmedSecurityStatisticsDataStatsEntry ::=
    SEQUENCE {
        affirmedSecurityStatisticsDataStatsDummyIndex Unsigned32,
        affirmedSecurityStatisticsDataStatsNonErrorDelimiter String,
        affirmedSecurityStatisticsDataStatsRxV4Pkts ConfdString,
        affirmedSecurityStatisticsDataStatsRxV4Bytes ConfdString,
        affirmedSecurityStatisticsDataStatsRxPostSecurityV4Pkts ConfdString,
        affirmedSecurityStatisticsDataStatsRxPostSecurityV4Bytes ConfdString,
        affirmedSecurityStatisticsDataStatsRxV6Pkts ConfdString,
        affirmedSecurityStatisticsDataStatsRxV6Bytes ConfdString,
        affirmedSecurityStatisticsDataStatsRxPostSecurityV6Pkts ConfdString,
        affirmedSecurityStatisticsDataStatsRxPostSecurityV6Bytes ConfdString,
        affirmedSecurityStatisticsDataStatsRxEspPkts ConfdString,
        affirmedSecurityStatisticsDataStatsRxAhPkts ConfdString,
        affirmedSecurityStatisticsDataStatsRxRemoteSecmPkts ConfdString,
        affirmedSecurityStatisticsDataStatsRxSecmIngTransPkts ConfdString,
        affirmedSecurityStatisticsDataStatsRxSecmEgrTransPkts ConfdString,
        affirmedSecurityStatisticsDataStatsRxSpmPkts ConfdString,
        affirmedSecurityStatisticsDataStatsFwdRemoteSecmPkts ConfdString,
        affirmedSecurityStatisticsDataStatsRxRemoteSecmSpmPkts ConfdString,
        affirmedSecurityStatisticsDataStatsFwdRemoteSecmSpmPkts ConfdString,
        affirmedSecurityStatisticsDataStatsFwdSpmPkts ConfdString,
        affirmedSecurityStatisticsDataStatsRxBypassRulePkts ConfdString,
        affirmedSecurityStatisticsDataStatsTxBypassRulePkts ConfdString,
        affirmedSecurityStatisticsDataStatsFwdPkts ConfdString,
        affirmedSecurityStatisticsDataStatsTxV4Pkts ConfdString,
        affirmedSecurityStatisticsDataStatsTxV4Bytes ConfdString,
        affirmedSecurityStatisticsDataStatsTxV6Pkts ConfdString,
        affirmedSecurityStatisticsDataStatsTxV6Bytes ConfdString,
        affirmedSecurityStatisticsDataStatsTxEspPkts ConfdString,
        affirmedSecurityStatisticsDataStatsTxAhPkts ConfdString,
        affirmedSecurityStatisticsDataStatsIdleFlowsReported ConfdString,
        affirmedSecurityStatisticsDataStatsTransactionsAllocated ConfdString,
        affirmedSecurityStatisticsDataStatsTransactionsDeallocated ConfdString,
        affirmedSecurityStatisticsDataStatsHdwTotIn ConfdString,
        affirmedSecurityStatisticsDataStatsHdwTotOut ConfdString,
        affirmedSecurityStatisticsDataStatsHdwEncIn ConfdString,
        affirmedSecurityStatisticsDataStatsHdwEncOut ConfdString,
        affirmedSecurityStatisticsDataStatsHdwDecIn ConfdString,
        affirmedSecurityStatisticsDataStatsHdwDecOut ConfdString,
        affirmedSecurityStatisticsDataStatsQueuedPkts ConfdString,
        affirmedSecurityStatisticsDataStatsDequeuedPkts ConfdString,
        affirmedSecurityStatisticsDataStatsErrorDelimiter String,
        affirmedSecurityStatisticsDataStatsRxV4DropPkts ConfdString,
        affirmedSecurityStatisticsDataStatsRxV4DropBytes ConfdString,
        affirmedSecurityStatisticsDataStatsRxV6DropPkts ConfdString,
        affirmedSecurityStatisticsDataStatsRxV6DropBytes ConfdString,
        affirmedSecurityStatisticsDataStatsRxSpmPktsIgnored ConfdString,
        affirmedSecurityStatisticsDataStatsRxSpmNoFlowPkts ConfdString,
        affirmedSecurityStatisticsDataStatsSecmSpmEgrPktsFwdFail ConfdString,
        affirmedSecurityStatisticsDataStatsSecmIngPktsFwdFail ConfdString,
        affirmedSecurityStatisticsDataStatsSecmEgrPktsFwdFail ConfdString,
        affirmedSecurityStatisticsDataStatsFwdSpmNoFlowPkts ConfdString,
        affirmedSecurityStatisticsDataStatsTxV4DropPkts ConfdString,
        affirmedSecurityStatisticsDataStatsTxV4DropBytes ConfdString,
        affirmedSecurityStatisticsDataStatsTxV6DropPkts ConfdString,
        affirmedSecurityStatisticsDataStatsTxV6DropBytes ConfdString,
        affirmedSecurityStatisticsDataStatsDropPktsRule ConfdString,
        affirmedSecurityStatisticsDataStatsDropPktsRejectRule ConfdString,
        affirmedSecurityStatisticsDataStatsDropPktsNoRule ConfdString,
        affirmedSecurityStatisticsDataStatsDropPktsTriggerRule ConfdString,
        affirmedSecurityStatisticsDataStatsRemoteTransError ConfdString,
        affirmedSecurityStatisticsDataStatsInvalidHeaderError ConfdString,
        affirmedSecurityStatisticsDataStatsRxPendingFlowError ConfdString,
        affirmedSecurityStatisticsDataStatsTxPendingFlowError ConfdString,
        affirmedSecurityStatisticsDataStatsNoFlowError ConfdString,
        affirmedSecurityStatisticsDataStatsTransNotFoundError ConfdString,
        affirmedSecurityStatisticsDataStatsDropPktsTooBig ConfdString,
        affirmedSecurityStatisticsDataStatsBadHandle ConfdString,
        affirmedSecurityStatisticsDataStatsIngCtxtInUse ConfdString,
        affirmedSecurityStatisticsDataStatsFailedSanity ConfdString,
        affirmedSecurityStatisticsDataStatsFlushedPkts ConfdString,
        affirmedSecurityStatisticsDataStatsDropPktsIntfNotFound ConfdString,
        affirmedSecurityStatisticsDataStatsDropPktsSessionNotFound ConfdString,
        affirmedSecurityStatisticsDataStatsDropPktsTransactionNotFound ConfdString,
        affirmedSecurityStatisticsDataStatsTransactionsDeallocFailed ConfdString,
        affirmedSecurityStatisticsDataStatsInvalidNumaNode ConfdString,
        affirmedSecurityStatisticsDataStatsFlowAccessTimeFix ConfdString,
        affirmedSecurityStatisticsDataStatsPendingFlowAccessTimeFix ConfdString,
        affirmedSecurityStatisticsDataStatsHdwBadIcvIngressIom ConfdString,
        affirmedSecurityStatisticsDataStatsHdwBadIcvIngressSecm ConfdString,
        affirmedSecurityStatisticsDataStatsIngSpiMismatch ConfdString,
        affirmedSecurityStatisticsDataStatsEgrSpiMismatch ConfdString,
        affirmedSecurityStatisticsDataStatsTransAuthErrs ConfdString,
        affirmedSecurityStatisticsDataStatsPostSecTransAuthErrs ConfdString,
        affirmedSecurityStatisticsDataStatsPostSecPktErrs ConfdString,
        affirmedSecurityStatisticsDataStatsPostSecIntfPktErrs ConfdString,
        affirmedSecurityStatisticsDataStatsPostSecFpPktErrs ConfdString,
        affirmedSecurityStatisticsDataStatsNoFlowPassAtRemoteSecm ConfdString,
        affirmedSecurityStatisticsDataStatsCreateFlowWithoutSpmForward ConfdString,
        affirmedSecurityStatisticsDataStatsEspSpiMismatchError ConfdString,
        affirmedSecurityStatisticsDataStatsAhSpiMismatchError ConfdString,
        affirmedSecurityStatisticsDataStatsCipherNotFoundError ConfdString,
        affirmedSecurityStatisticsDataStatsAuthNotFoundError ConfdString,
        affirmedSecurityStatisticsDataStatsPktDataAccessError ConfdString,
        affirmedSecurityStatisticsDataStatsPktSizeCipherSizeError ConfdString,
        affirmedSecurityStatisticsDataStatsPktTooShortError ConfdString,
        affirmedSecurityStatisticsDataStatsPktLenMismatchError ConfdString,
        affirmedSecurityStatisticsDataStatsParsePktHeaderError ConfdString,
        affirmedSecurityStatisticsDataStatsCalcPktInfoError ConfdString,
        affirmedSecurityStatisticsDataStatsPrelimAntiReplayErrLo ConfdString,
        affirmedSecurityStatisticsDataStatsPrelimAntiReplayError ConfdString,
        affirmedSecurityStatisticsDataStatsEspSeqNumError ConfdString,
        affirmedSecurityStatisticsDataStatsEspSeqSecm ConfdString,
        affirmedSecurityStatisticsDataStatsEspSeqNumLow ConfdString,
        affirmedSecurityStatisticsDataStatsAhSeqNumError ConfdString,
        affirmedSecurityStatisticsDataStatsAppendSeqHighError ConfdString,
        affirmedSecurityStatisticsDataStatsDeleteSeqHighError ConfdString,
        affirmedSecurityStatisticsDataStatsIcvComputeError ConfdString,
        affirmedSecurityStatisticsDataStatsIcvCheckError ConfdString,
        affirmedSecurityStatisticsDataStatsIcvLenError ConfdString,
        affirmedSecurityStatisticsDataStatsEspIcvAuthError ConfdString,
        affirmedSecurityStatisticsDataStatsEspPadError ConfdString,
        affirmedSecurityStatisticsDataStatsAhIcvAuthError ConfdString,
        affirmedSecurityStatisticsDataStatsEspTransChainError ConfdString,
        affirmedSecurityStatisticsDataStatsEspProcessAadError ConfdString,
        affirmedSecurityStatisticsDataStatsTransFinishError ConfdString,
        affirmedSecurityStatisticsDataStatsAuthAddRangeError ConfdString,
        affirmedSecurityStatisticsDataStatsAuthFinishError ConfdString,
        affirmedSecurityStatisticsDataStatsCipherUpdateError ConfdString,
        affirmedSecurityStatisticsDataStatsAhSeqNumOverflowError ConfdString,
        affirmedSecurityStatisticsDataStatsEspSeqNumOverflowError ConfdString,
        affirmedSecurityStatisticsDataStatsNumIngCryptoAllocFail ConfdString,
        affirmedSecurityStatisticsDataStatsNumEgrCryptoAllocFail ConfdString,
        affirmedSecurityStatisticsDataStatsNumGetNextHopFail ConfdString,
        affirmedSecurityStatisticsDataStatsBypassV4IkeFragment ConfdString,
        affirmedSecurityStatisticsDataStatsBypassV4OSPF ConfdString,
        affirmedSecurityStatisticsDataStatsBypassV4Multicast ConfdString,
        affirmedSecurityStatisticsDataStatsBypassV6LinkLocalDest ConfdString,
        affirmedSecurityStatisticsDataStatsBypassV6LinkLocalSrc ConfdString,
        affirmedSecurityStatisticsDataStatsBypassTid0V6Icmp ConfdString,
        affirmedSecurityStatisticsDataStatsBypassTid0IngressIke ConfdString,
        affirmedSecurityStatisticsDataStatsBypassTid0IngressIkeNatt ConfdString,
        affirmedSecurityStatisticsDataStatsBypassTid0IngressV4DhcpClient ConfdString,
        affirmedSecurityStatisticsDataStatsBypassTid0EgressV4DnsClient ConfdString,
        affirmedSecurityStatisticsDataStatsBypassTid1IngressUdp ConfdString,
        affirmedSecurityStatisticsDataStatsIngressIke ConfdString,
        affirmedSecurityStatisticsDataStatsIngressIkeNatt ConfdString,
        affirmedSecurityStatisticsDataStatsEgressIke ConfdString,
        affirmedSecurityStatisticsDataStatsEgressIkeNatt ConfdString,
        affirmedSecurityStatisticsDataStatsPassRuleHits ConfdString,
        affirmedSecurityStatisticsDataStatsApplyRuleHits ConfdString,
        affirmedSecurityStatisticsDataStatsRxNattKaPkts ConfdString,
        affirmedSecurityStatisticsDataStatsUseableRuleHits ConfdString,
        affirmedSecurityStatisticsDataStatsDropPktsWrongRule ConfdString,
        affirmedSecurityStatisticsDataStatsDropPktsOnWrongTunnel ConfdString,
        affirmedSecurityStatisticsDataStatsNoFlowErrorIngress ConfdString,
        affirmedSecurityStatisticsDataStatsNoFlowErrorEgress ConfdString,
        affirmedSecurityStatisticsDataStatsPktsDiscarded ConfdString,
        affirmedSecurityStatisticsDataStatsNoFlowPassDrop ConfdString,
        affirmedSecurityStatisticsDataStatsNoFlowTid0IngressIPsec ConfdString,
        affirmedSecurityStatisticsDataStatsSpiEntryFailLookup ConfdString,
        affirmedSecurityStatisticsDataStatsDropPktsSecurityDisabled ConfdString,
        affirmedSecurityStatisticsDataStatsUnuseableRuleHits ConfdString,
        affirmedSecurityStatisticsDataStatsDropRuleHits ConfdString,
        affirmedSecurityStatisticsDataStatsRejectRuleHits ConfdString,
        affirmedSecurityStatisticsDataStatsInvalidRuleHits ConfdString,
        affirmedSecurityStatisticsDataStatsDormantApplyRuleHits ConfdString,
        affirmedSecurityStatisticsDataStatsUnknownRuleHits ConfdString,
        affirmedSecurityStatisticsDataStatsPostSecPktErrsInvalidHeader ConfdString,
        affirmedSecurityStatisticsDataStatsPostSecPktErrsInvalidFragHeader ConfdString,
        affirmedSecurityStatisticsDataStatsPostSecPktErrsNoFlowFound ConfdString,
        affirmedSecurityStatisticsDataStatsPostSecPktErrsBadFlowFound ConfdString,
        affirmedSecurityStatisticsDataStatsPostSecPktErrsUnexpectedPendFlow ConfdString,
        affirmedSecurityStatisticsDataStatsPostSecPktErrsUnexpectedApplyFlow ConfdString,
        affirmedSecurityStatisticsDataStatsPostSecPktErrsUnexpectedRejectFlow ConfdString,
        affirmedSecurityStatisticsDataStatsPostSecPktErrsUnexpectedTriggerFlow ConfdString,
        affirmedSecurityStatisticsDataStatsPostSecPktErrsUnexpectedDropFlow ConfdString,
        affirmedSecurityStatisticsDataStatsPostSecPktErrsUnexpectedNonExistentFlow ConfdString,
        affirmedSecurityStatisticsDataStatsDropPktsDropRule ConfdString,
        affirmedSecurityStatisticsDataStatsNullSpiEntry ConfdString,
        affirmedSecurityStatisticsDataStatsInvalidFSAPI ConfdString
    }

affirmedSecurityStatisticsDataStatsDummyIndex OBJECT-TYPE
    SYNTAX      Unsigned32
    MAX-ACCESS  not-accessible
    STATUS      current
    DESCRIPTION ""
    ::= { affirmedSecurityStatisticsDataStatsEntry 1 }

affirmedSecurityStatisticsDataStatsNonErrorDelimiter OBJECT-TYPE
    SYNTAX      String
    MAX-ACCESS  read-only
    STATUS      current
    DESCRIPTION "Separate non-error from error stats"
    ::= { affirmedSecurityStatisticsDataStatsEntry 2 }

affirmedSecurityStatisticsDataStatsRxV4Pkts OBJECT-TYPE
    SYNTAX      ConfdString
    MAX-ACCESS  read-only
    STATUS      current
    DESCRIPTION "Ingress IPv4 packets successfully processed "
    ::= { affirmedSecurityStatisticsDataStatsEntry 3 }

affirmedSecurityStatisticsDataStatsRxV4Bytes OBJECT-TYPE
    SYNTAX      ConfdString
    MAX-ACCESS  read-only
    STATUS      current
    DESCRIPTION "Ingress IPv4 bytes successfully processed "
    ::= { affirmedSecurityStatisticsDataStatsEntry 4 }

affirmedSecurityStatisticsDataStatsRxPostSecurityV4Pkts OBJECT-TYPE
    SYNTAX      ConfdString
    MAX-ACCESS  read-only
    STATUS      current
    DESCRIPTION "Dequeued ingress IPv4 packets successfully processed "
    ::= { affirmedSecurityStatisticsDataStatsEntry 5 }

affirmedSecurityStatisticsDataStatsRxPostSecurityV4Bytes OBJECT-TYPE
    SYNTAX      ConfdString
    MAX-ACCESS  read-only
    STATUS      current
    DESCRIPTION "Dequeued ingress IPv4 bytes successfully processed "
    ::= { affirmedSecurityStatisticsDataStatsEntry 6 }

affirmedSecurityStatisticsDataStatsRxV6Pkts OBJECT-TYPE
    SYNTAX      ConfdString
    MAX-ACCESS  read-only
    STATUS      current
    DESCRIPTION "Ingress IPv6 packets successfully processed "
    ::= { affirmedSecurityStatisticsDataStatsEntry 7 }

affirmedSecurityStatisticsDataStatsRxV6Bytes OBJECT-TYPE
    SYNTAX      ConfdString
    MAX-ACCESS  read-only
    STATUS      current
    DESCRIPTION "Ingress IPv6 bytes successfully processed "
    ::= { affirmedSecurityStatisticsDataStatsEntry 8 }

affirmedSecurityStatisticsDataStatsRxPostSecurityV6Pkts OBJECT-TYPE
    SYNTAX      ConfdString
    MAX-ACCESS  read-only
    STATUS      current
    DESCRIPTION "Dequeued ingress IPv6 packets successfully processed "
    ::= { affirmedSecurityStatisticsDataStatsEntry 9 }

affirmedSecurityStatisticsDataStatsRxPostSecurityV6Bytes OBJECT-TYPE
    SYNTAX      ConfdString
    MAX-ACCESS  read-only
    STATUS      current
    DESCRIPTION "Dequeued ingress IPv6 bytes successfully processed "
    ::= { affirmedSecurityStatisticsDataStatsEntry 10 }

affirmedSecurityStatisticsDataStatsRxEspPkts OBJECT-TYPE
    SYNTAX      ConfdString
    MAX-ACCESS  read-only
    STATUS      current
    DESCRIPTION "Authenticated and decrypted packets (ESP) received"
    ::= { affirmedSecurityStatisticsDataStatsEntry 11 }

affirmedSecurityStatisticsDataStatsRxAhPkts OBJECT-TYPE
    SYNTAX      ConfdString
    MAX-ACCESS  read-only
    STATUS      current
    DESCRIPTION "Authenticated (AH) packets received"
    ::= { affirmedSecurityStatisticsDataStatsEntry 12 }

affirmedSecurityStatisticsDataStatsRxRemoteSecmPkts OBJECT-TYPE
    SYNTAX      ConfdString
    MAX-ACCESS  read-only
    STATUS      current
    DESCRIPTION "Total packets from other SSM"
    ::= { affirmedSecurityStatisticsDataStatsEntry 13 }

affirmedSecurityStatisticsDataStatsRxSecmIngTransPkts OBJECT-TYPE
    SYNTAX      ConfdString
    MAX-ACCESS  read-only
    STATUS      current
    DESCRIPTION "Ingress packets from other SSM"
    ::= { affirmedSecurityStatisticsDataStatsEntry 14 }

affirmedSecurityStatisticsDataStatsRxSecmEgrTransPkts OBJECT-TYPE
    SYNTAX      ConfdString
    MAX-ACCESS  read-only
    STATUS      current
    DESCRIPTION "Egress packets from other SSM"
    ::= { affirmedSecurityStatisticsDataStatsEntry 15 }

affirmedSecurityStatisticsDataStatsRxSpmPkts OBJECT-TYPE
    SYNTAX      ConfdString
    MAX-ACCESS  read-only
    STATUS      current
    DESCRIPTION "Total packets from SPM"
    ::= { affirmedSecurityStatisticsDataStatsEntry 16 }

affirmedSecurityStatisticsDataStatsFwdRemoteSecmPkts OBJECT-TYPE
    SYNTAX      ConfdString
    MAX-ACCESS  read-only
    STATUS      current
    DESCRIPTION "Egress packets sent to other SSM"
    ::= { affirmedSecurityStatisticsDataStatsEntry 17 }

affirmedSecurityStatisticsDataStatsRxRemoteSecmSpmPkts OBJECT-TYPE
    SYNTAX      ConfdString
    MAX-ACCESS  read-only
    STATUS      current
    DESCRIPTION "Egress WF packets from other SSM"
    ::= { affirmedSecurityStatisticsDataStatsEntry 18 }

affirmedSecurityStatisticsDataStatsFwdRemoteSecmSpmPkts OBJECT-TYPE
    SYNTAX      ConfdString
    MAX-ACCESS  read-only
    STATUS      current
    DESCRIPTION "Egress WF packets sent to other SSM"
    ::= { affirmedSecurityStatisticsDataStatsEntry 19 }

affirmedSecurityStatisticsDataStatsFwdSpmPkts OBJECT-TYPE
    SYNTAX      ConfdString
    MAX-ACCESS  read-only
    STATUS      current
    DESCRIPTION "Packets forwarded to SPM"
    ::= { affirmedSecurityStatisticsDataStatsEntry 20 }

affirmedSecurityStatisticsDataStatsRxBypassRulePkts OBJECT-TYPE
    SYNTAX      ConfdString
    MAX-ACCESS  read-only
    STATUS      current
    DESCRIPTION "Packets received that bypass security"
    ::= { affirmedSecurityStatisticsDataStatsEntry 21 }

affirmedSecurityStatisticsDataStatsTxBypassRulePkts OBJECT-TYPE
    SYNTAX      ConfdString
    MAX-ACCESS  read-only
    STATUS      current
    DESCRIPTION "WF Packets from other SSM that bypass security"
    ::= { affirmedSecurityStatisticsDataStatsEntry 22 }

affirmedSecurityStatisticsDataStatsFwdPkts OBJECT-TYPE
    SYNTAX      ConfdString
    MAX-ACCESS  read-only
    STATUS      current
    DESCRIPTION "Egress IPv4 packets successfully processed "
    ::= { affirmedSecurityStatisticsDataStatsEntry 23 }

affirmedSecurityStatisticsDataStatsTxV4Pkts OBJECT-TYPE
    SYNTAX      ConfdString
    MAX-ACCESS  read-only
    STATUS      current
    DESCRIPTION "Egress IPv4 packets successfully processed "
    ::= { affirmedSecurityStatisticsDataStatsEntry 24 }

affirmedSecurityStatisticsDataStatsTxV4Bytes OBJECT-TYPE
    SYNTAX      ConfdString
    MAX-ACCESS  read-only
    STATUS      current
    DESCRIPTION "Egress IPv4 bytes successfully processed "
    ::= { affirmedSecurityStatisticsDataStatsEntry 25 }

affirmedSecurityStatisticsDataStatsTxV6Pkts OBJECT-TYPE
    SYNTAX      ConfdString
    MAX-ACCESS  read-only
    STATUS      current
    DESCRIPTION "Egress IPv6 packets successfully processed "
    ::= { affirmedSecurityStatisticsDataStatsEntry 26 }

affirmedSecurityStatisticsDataStatsTxV6Bytes OBJECT-TYPE
    SYNTAX      ConfdString
    MAX-ACCESS  read-only
    STATUS      current
    DESCRIPTION "Egress IPv6 bytes successfully processed "
    ::= { affirmedSecurityStatisticsDataStatsEntry 27 }

affirmedSecurityStatisticsDataStatsTxEspPkts OBJECT-TYPE
    SYNTAX      ConfdString
    MAX-ACCESS  read-only
    STATUS      current
    DESCRIPTION "Packets to be encrypted and authentication calculated"
    ::= { affirmedSecurityStatisticsDataStatsEntry 28 }

affirmedSecurityStatisticsDataStatsTxAhPkts OBJECT-TYPE
    SYNTAX      ConfdString
    MAX-ACCESS  read-only
    STATUS      current
    DESCRIPTION "Packets to have just authentication calculated"
    ::= { affirmedSecurityStatisticsDataStatsEntry 29 }

affirmedSecurityStatisticsDataStatsIdleFlowsReported OBJECT-TYPE
    SYNTAX      ConfdString
    MAX-ACCESS  read-only
    STATUS      current
    DESCRIPTION "Flows reported without traffic for 30 seconds"
    ::= { affirmedSecurityStatisticsDataStatsEntry 30 }

affirmedSecurityStatisticsDataStatsTransactionsAllocated OBJECT-TYPE
    SYNTAX      ConfdString
    MAX-ACCESS  read-only
    STATUS      current
    DESCRIPTION "Transactions Allocated"
    ::= { affirmedSecurityStatisticsDataStatsEntry 31 }

affirmedSecurityStatisticsDataStatsTransactionsDeallocated OBJECT-TYPE
    SYNTAX      ConfdString
    MAX-ACCESS  read-only
    STATUS      current
    DESCRIPTION "TransactionsDeallocated"
    ::= { affirmedSecurityStatisticsDataStatsEntry 32 }

affirmedSecurityStatisticsDataStatsHdwTotIn OBJECT-TYPE
    SYNTAX      ConfdString
    MAX-ACCESS  read-only
    STATUS      current
    DESCRIPTION "Packets sent to SAE"
    ::= { affirmedSecurityStatisticsDataStatsEntry 33 }

affirmedSecurityStatisticsDataStatsHdwTotOut OBJECT-TYPE
    SYNTAX      ConfdString
    MAX-ACCESS  read-only
    STATUS      current
    DESCRIPTION "Packets returned from SAE"
    ::= { affirmedSecurityStatisticsDataStatsEntry 34 }

affirmedSecurityStatisticsDataStatsHdwEncIn OBJECT-TYPE
    SYNTAX      ConfdString
    MAX-ACCESS  read-only
    STATUS      current
    DESCRIPTION "Packets sent to SAE for Encryption"
    ::= { affirmedSecurityStatisticsDataStatsEntry 35 }

affirmedSecurityStatisticsDataStatsHdwEncOut OBJECT-TYPE
    SYNTAX      ConfdString
    MAX-ACCESS  read-only
    STATUS      current
    DESCRIPTION "Encrypted packets returned from SAE"
    ::= { affirmedSecurityStatisticsDataStatsEntry 36 }

affirmedSecurityStatisticsDataStatsHdwDecIn OBJECT-TYPE
    SYNTAX      ConfdString
    MAX-ACCESS  read-only
    STATUS      current
    DESCRIPTION "Packets sent to SAE for Decryption"
    ::= { affirmedSecurityStatisticsDataStatsEntry 37 }

affirmedSecurityStatisticsDataStatsHdwDecOut OBJECT-TYPE
    SYNTAX      ConfdString
    MAX-ACCESS  read-only
    STATUS      current
    DESCRIPTION "Decrypted packets returned from SAE"
    ::= { affirmedSecurityStatisticsDataStatsEntry 38 }

affirmedSecurityStatisticsDataStatsQueuedPkts OBJECT-TYPE
    SYNTAX      ConfdString
    MAX-ACCESS  read-only
    STATUS      current
    DESCRIPTION "Packets queued waiting for SPM to validate flow"
    ::= { affirmedSecurityStatisticsDataStatsEntry 39 }

affirmedSecurityStatisticsDataStatsDequeuedPkts OBJECT-TYPE
    SYNTAX      ConfdString
    MAX-ACCESS  read-only
    STATUS      current
    DESCRIPTION "Packets dequeued when SPM validates flow"
    ::= { affirmedSecurityStatisticsDataStatsEntry 40 }

affirmedSecurityStatisticsDataStatsErrorDelimiter OBJECT-TYPE
    SYNTAX      String
    MAX-ACCESS  read-only
    STATUS      current
    DESCRIPTION "Separate non-error from error stats"
    ::= { affirmedSecurityStatisticsDataStatsEntry 41 }

affirmedSecurityStatisticsDataStatsRxV4DropPkts OBJECT-TYPE
    SYNTAX      ConfdString
    MAX-ACCESS  read-only
    STATUS      current
    DESCRIPTION "Ingress IPv4 packets dropped"
    ::= { affirmedSecurityStatisticsDataStatsEntry 42 }

affirmedSecurityStatisticsDataStatsRxV4DropBytes OBJECT-TYPE
    SYNTAX      ConfdString
    MAX-ACCESS  read-only
    STATUS      current
    DESCRIPTION "Ingress IPv4 bytes dropped"
    ::= { affirmedSecurityStatisticsDataStatsEntry 43 }

affirmedSecurityStatisticsDataStatsRxV6DropPkts OBJECT-TYPE
    SYNTAX      ConfdString
    MAX-ACCESS  read-only
    STATUS      current
    DESCRIPTION "Ingress IPv6 packets dropped"
    ::= { affirmedSecurityStatisticsDataStatsEntry 44 }

affirmedSecurityStatisticsDataStatsRxV6DropBytes OBJECT-TYPE
    SYNTAX      ConfdString
    MAX-ACCESS  read-only
    STATUS      current
    DESCRIPTION "Ingress IPv6 bytes dropped"
    ::= { affirmedSecurityStatisticsDataStatsEntry 45 }

affirmedSecurityStatisticsDataStatsRxSpmPktsIgnored OBJECT-TYPE
    SYNTAX      ConfdString
    MAX-ACCESS  read-only
    STATUS      current
    DESCRIPTION "Packets from SPM ignored"
    ::= { affirmedSecurityStatisticsDataStatsEntry 46 }

affirmedSecurityStatisticsDataStatsRxSpmNoFlowPkts OBJECT-TYPE
    SYNTAX      ConfdString
    MAX-ACCESS  read-only
    STATUS      current
    DESCRIPTION "Egress WF packets with no flow"
    ::= { affirmedSecurityStatisticsDataStatsEntry 47 }

affirmedSecurityStatisticsDataStatsSecmSpmEgrPktsFwdFail OBJECT-TYPE
    SYNTAX      ConfdString
    MAX-ACCESS  read-only
    STATUS      current
    DESCRIPTION "WF packets from other SPM failures"
    ::= { affirmedSecurityStatisticsDataStatsEntry 48 }

affirmedSecurityStatisticsDataStatsSecmIngPktsFwdFail OBJECT-TYPE
    SYNTAX      ConfdString
    MAX-ACCESS  read-only
    STATUS      current
    DESCRIPTION "Ingress packet from other SSM failures"
    ::= { affirmedSecurityStatisticsDataStatsEntry 49 }

affirmedSecurityStatisticsDataStatsSecmEgrPktsFwdFail OBJECT-TYPE
    SYNTAX      ConfdString
    MAX-ACCESS  read-only
    STATUS      current
    DESCRIPTION "Egress packet from other SSM failures"
    ::= { affirmedSecurityStatisticsDataStatsEntry 50 }

affirmedSecurityStatisticsDataStatsFwdSpmNoFlowPkts OBJECT-TYPE
    SYNTAX      ConfdString
    MAX-ACCESS  read-only
    STATUS      current
    DESCRIPTION "Packets forwarded to SPM with no flow creation"
    ::= { affirmedSecurityStatisticsDataStatsEntry 51 }

affirmedSecurityStatisticsDataStatsTxV4DropPkts OBJECT-TYPE
    SYNTAX      ConfdString
    MAX-ACCESS  read-only
    STATUS      current
    DESCRIPTION "Egress IPv4 packets dropped"
    ::= { affirmedSecurityStatisticsDataStatsEntry 52 }

affirmedSecurityStatisticsDataStatsTxV4DropBytes OBJECT-TYPE
    SYNTAX      ConfdString
    MAX-ACCESS  read-only
    STATUS      current
    DESCRIPTION "Egress IPv4 bytes dropped"
    ::= { affirmedSecurityStatisticsDataStatsEntry 53 }

affirmedSecurityStatisticsDataStatsTxV6DropPkts OBJECT-TYPE
    SYNTAX      ConfdString
    MAX-ACCESS  read-only
    STATUS      current
    DESCRIPTION "Egress IPv6 packets dropped"
    ::= { affirmedSecurityStatisticsDataStatsEntry 54 }

affirmedSecurityStatisticsDataStatsTxV6DropBytes OBJECT-TYPE
    SYNTAX      ConfdString
    MAX-ACCESS  read-only
    STATUS      current
    DESCRIPTION "Egress IPv6 bytes dropped"
    ::= { affirmedSecurityStatisticsDataStatsEntry 55 }

affirmedSecurityStatisticsDataStatsDropPktsRule OBJECT-TYPE
    SYNTAX      ConfdString
    MAX-ACCESS  read-only
    STATUS      current
    DESCRIPTION "Packets dropped via an explicit rule"
    ::= { affirmedSecurityStatisticsDataStatsEntry 56 }

affirmedSecurityStatisticsDataStatsDropPktsRejectRule OBJECT-TYPE
    SYNTAX      ConfdString
    MAX-ACCESS  read-only
    STATUS      current
    DESCRIPTION "Packets rejected via an explicit rule"
    ::= { affirmedSecurityStatisticsDataStatsEntry 57 }

affirmedSecurityStatisticsDataStatsDropPktsNoRule OBJECT-TYPE
    SYNTAX      ConfdString
    MAX-ACCESS  read-only
    STATUS      current
    DESCRIPTION "Packets dropped due to no or bad rule"
    ::= { affirmedSecurityStatisticsDataStatsEntry 58 }

affirmedSecurityStatisticsDataStatsDropPktsTriggerRule OBJECT-TYPE
    SYNTAX      ConfdString
    MAX-ACCESS  read-only
    STATUS      current
    DESCRIPTION "Packets rejected via a trigger explicit rule"
    ::= { affirmedSecurityStatisticsDataStatsEntry 59 }

affirmedSecurityStatisticsDataStatsRemoteTransError OBJECT-TYPE
    SYNTAX      ConfdString
    MAX-ACCESS  read-only
    STATUS      current
    DESCRIPTION "Packets sent to wrong SSM"
    ::= { affirmedSecurityStatisticsDataStatsEntry 60 }

affirmedSecurityStatisticsDataStatsInvalidHeaderError OBJECT-TYPE
    SYNTAX      ConfdString
    MAX-ACCESS  read-only
    STATUS      current
    DESCRIPTION "Packets with bad IP header or length less than IP length"
    ::= { affirmedSecurityStatisticsDataStatsEntry 61 }

affirmedSecurityStatisticsDataStatsRxPendingFlowError OBJECT-TYPE
    SYNTAX      ConfdString
    MAX-ACCESS  read-only
    STATUS      current
    DESCRIPTION "Ingress Packets dropped because SPM has not validated flow"
    ::= { affirmedSecurityStatisticsDataStatsEntry 62 }

affirmedSecurityStatisticsDataStatsTxPendingFlowError OBJECT-TYPE
    SYNTAX      ConfdString
    MAX-ACCESS  read-only
    STATUS      current
    DESCRIPTION "Egress Packets dropped because SPM has not validated flow"
    ::= { affirmedSecurityStatisticsDataStatsEntry 63 }

affirmedSecurityStatisticsDataStatsNoFlowError OBJECT-TYPE
    SYNTAX      ConfdString
    MAX-ACCESS  read-only
    STATUS      current
    DESCRIPTION "Packets from other SSM with no or bad flow"
    ::= { affirmedSecurityStatisticsDataStatsEntry 64 }

affirmedSecurityStatisticsDataStatsTransNotFoundError OBJECT-TYPE
    SYNTAX      ConfdString
    MAX-ACCESS  read-only
    STATUS      current
    DESCRIPTION "Packets dropped because transform not in hash"
    ::= { affirmedSecurityStatisticsDataStatsEntry 65 }

affirmedSecurityStatisticsDataStatsDropPktsTooBig OBJECT-TYPE
    SYNTAX      ConfdString
    MAX-ACCESS  read-only
    STATUS      current
    DESCRIPTION "Packets too big for hardware crypto"
    ::= { affirmedSecurityStatisticsDataStatsEntry 66 }

affirmedSecurityStatisticsDataStatsBadHandle OBJECT-TYPE
    SYNTAX      ConfdString
    MAX-ACCESS  read-only
    STATUS      current
    DESCRIPTION "(hw only) Internal error"
    ::= { affirmedSecurityStatisticsDataStatsEntry 67 }

affirmedSecurityStatisticsDataStatsIngCtxtInUse OBJECT-TYPE
    SYNTAX      ConfdString
    MAX-ACCESS  read-only
    STATUS      current
    DESCRIPTION "Ingress packet dropped by hdw crypto because rekeying not done"
    ::= { affirmedSecurityStatisticsDataStatsEntry 68 }

affirmedSecurityStatisticsDataStatsFailedSanity OBJECT-TYPE
    SYNTAX      ConfdString
    MAX-ACCESS  read-only
    STATUS      current
    DESCRIPTION "Ingress packets dropped by hdw crypto for memory corruption"
    ::= { affirmedSecurityStatisticsDataStatsEntry 69 }

affirmedSecurityStatisticsDataStatsFlushedPkts OBJECT-TYPE
    SYNTAX      ConfdString
    MAX-ACCESS  read-only
    STATUS      current
    DESCRIPTION "Packets flushed after waiting 30 sec for SPM to validate flow"
    ::= { affirmedSecurityStatisticsDataStatsEntry 70 }

affirmedSecurityStatisticsDataStatsDropPktsIntfNotFound OBJECT-TYPE
    SYNTAX      ConfdString
    MAX-ACCESS  read-only
    STATUS      current
    DESCRIPTION "Packets dropped when transmit logical interface not found"
    ::= { affirmedSecurityStatisticsDataStatsEntry 71 }

affirmedSecurityStatisticsDataStatsDropPktsSessionNotFound OBJECT-TYPE
    SYNTAX      ConfdString
    MAX-ACCESS  read-only
    STATUS      current
    DESCRIPTION "WF packets dropped when session not found"
    ::= { affirmedSecurityStatisticsDataStatsEntry 72 }

affirmedSecurityStatisticsDataStatsDropPktsTransactionNotFound OBJECT-TYPE
    SYNTAX      ConfdString
    MAX-ACCESS  read-only
    STATUS      current
    DESCRIPTION "UE addressed packets dropped when transaction not found"
    ::= { affirmedSecurityStatisticsDataStatsEntry 73 }

affirmedSecurityStatisticsDataStatsTransactionsDeallocFailed OBJECT-TYPE
    SYNTAX      ConfdString
    MAX-ACCESS  read-only
    STATUS      current
    DESCRIPTION "Transaction deallocoations failures"
    ::= { affirmedSecurityStatisticsDataStatsEntry 74 }

affirmedSecurityStatisticsDataStatsInvalidNumaNode OBJECT-TYPE
    SYNTAX      ConfdString
    MAX-ACCESS  read-only
    STATUS      current
    DESCRIPTION "Received a non-default numaNode"
    ::= { affirmedSecurityStatisticsDataStatsEntry 75 }

affirmedSecurityStatisticsDataStatsFlowAccessTimeFix OBJECT-TYPE
    SYNTAX      ConfdString
    MAX-ACCESS  read-only
    STATUS      current
    DESCRIPTION "Flows accessed after more than 60 seconds of idle time"
    ::= { affirmedSecurityStatisticsDataStatsEntry 76 }

affirmedSecurityStatisticsDataStatsPendingFlowAccessTimeFix OBJECT-TYPE
    SYNTAX      ConfdString
    MAX-ACCESS  read-only
    STATUS      current
    DESCRIPTION "Flows pending after more than 60 seconds of idle time"
    ::= { affirmedSecurityStatisticsDataStatsEntry 77 }

affirmedSecurityStatisticsDataStatsHdwBadIcvIngressIom OBJECT-TYPE
    SYNTAX      ConfdString
    MAX-ACCESS  read-only
    STATUS      current
    DESCRIPTION "Locally originated packets with bad authentication"
    ::= { affirmedSecurityStatisticsDataStatsEntry 78 }

affirmedSecurityStatisticsDataStatsHdwBadIcvIngressSecm OBJECT-TYPE
    SYNTAX      ConfdString
    MAX-ACCESS  read-only
    STATUS      current
    DESCRIPTION "Remotely originated packets with bad authentication"
    ::= { affirmedSecurityStatisticsDataStatsEntry 79 }

affirmedSecurityStatisticsDataStatsIngSpiMismatch OBJECT-TYPE
    SYNTAX      ConfdString
    MAX-ACCESS  read-only
    STATUS      current
    DESCRIPTION "(hw only) ingress packet's SPI matches neither transform's SPI"
    ::= { affirmedSecurityStatisticsDataStatsEntry 80 }

affirmedSecurityStatisticsDataStatsEgrSpiMismatch OBJECT-TYPE
    SYNTAX      ConfdString
    MAX-ACCESS  read-only
    STATUS      current
    DESCRIPTION "SPI set up in egress packet matches neither egress SPI"
    ::= { affirmedSecurityStatisticsDataStatsEntry 81 }

affirmedSecurityStatisticsDataStatsTransAuthErrs OBJECT-TYPE
    SYNTAX      ConfdString
    MAX-ACCESS  read-only
    STATUS      current
    DESCRIPTION "Ingress packet failed pre cipher checks"
    ::= { affirmedSecurityStatisticsDataStatsEntry 82 }

affirmedSecurityStatisticsDataStatsPostSecTransAuthErrs OBJECT-TYPE
    SYNTAX      ConfdString
    MAX-ACCESS  read-only
    STATUS      current
    DESCRIPTION "Ingress packet failed post cipher checks"
    ::= { affirmedSecurityStatisticsDataStatsEntry 83 }

affirmedSecurityStatisticsDataStatsPostSecPktErrs OBJECT-TYPE
    SYNTAX      ConfdString
    MAX-ACCESS  read-only
    STATUS      current
    DESCRIPTION "Decrypted packet failed non-cipher checks"
    ::= { affirmedSecurityStatisticsDataStatsEntry 84 }

affirmedSecurityStatisticsDataStatsPostSecIntfPktErrs OBJECT-TYPE
    SYNTAX      ConfdString
    MAX-ACCESS  read-only
    STATUS      current
    DESCRIPTION "Remotely originated decrypted packet transmit failures"
    ::= { affirmedSecurityStatisticsDataStatsEntry 85 }

affirmedSecurityStatisticsDataStatsPostSecFpPktErrs OBJECT-TYPE
    SYNTAX      ConfdString
    MAX-ACCESS  read-only
    STATUS      current
    DESCRIPTION "Locally originated decrypted packet transmit failures"
    ::= { affirmedSecurityStatisticsDataStatsEntry 86 }

affirmedSecurityStatisticsDataStatsNoFlowPassAtRemoteSecm OBJECT-TYPE
    SYNTAX      ConfdString
    MAX-ACCESS  read-only
    STATUS      current
    DESCRIPTION "Passes match no flow pass rule, but should not send to spm"
    ::= { affirmedSecurityStatisticsDataStatsEntry 87 }

affirmedSecurityStatisticsDataStatsCreateFlowWithoutSpmForward OBJECT-TYPE
    SYNTAX      ConfdString
    MAX-ACCESS  read-only
    STATUS      current
    DESCRIPTION "Flows created without sending packet to SPM"
    ::= { affirmedSecurityStatisticsDataStatsEntry 88 }

affirmedSecurityStatisticsDataStatsEspSpiMismatchError OBJECT-TYPE
    SYNTAX      ConfdString
    MAX-ACCESS  read-only
    STATUS      current
    DESCRIPTION "Newly received ESP packet matches neither SPI"
    ::= { affirmedSecurityStatisticsDataStatsEntry 89 }

affirmedSecurityStatisticsDataStatsAhSpiMismatchError OBJECT-TYPE
    SYNTAX      ConfdString
    MAX-ACCESS  read-only
    STATUS      current
    DESCRIPTION "Newly received AH packet matches neither SPI"
    ::= { affirmedSecurityStatisticsDataStatsEntry 90 }

affirmedSecurityStatisticsDataStatsCipherNotFoundError OBJECT-TYPE
    SYNTAX      ConfdString
    MAX-ACCESS  read-only
    STATUS      current
    DESCRIPTION "Transform setup fail because cipher algorithm not found"
    ::= { affirmedSecurityStatisticsDataStatsEntry 91 }

affirmedSecurityStatisticsDataStatsAuthNotFoundError OBJECT-TYPE
    SYNTAX      ConfdString
    MAX-ACCESS  read-only
    STATUS      current
    DESCRIPTION "Transform setup fail because authentication algorithm not found"
    ::= { affirmedSecurityStatisticsDataStatsEntry 92 }

affirmedSecurityStatisticsDataStatsPktDataAccessError OBJECT-TYPE
    SYNTAX      ConfdString
    MAX-ACCESS  read-only
    STATUS      current
    DESCRIPTION "Mismatches between packet and expected prefix lengths"
    ::= { affirmedSecurityStatisticsDataStatsEntry 93 }

affirmedSecurityStatisticsDataStatsPktSizeCipherSizeError OBJECT-TYPE
    SYNTAX      ConfdString
    MAX-ACCESS  read-only
    STATUS      current
    DESCRIPTION "Encrypted packet size not a multiple of cipher block size"
    ::= { affirmedSecurityStatisticsDataStatsEntry 94 }

affirmedSecurityStatisticsDataStatsPktTooShortError OBJECT-TYPE
    SYNTAX      ConfdString
    MAX-ACCESS  read-only
    STATUS      current
    DESCRIPTION "Encrypted packet size less than necessary prefix and trailer sizes"
    ::= { affirmedSecurityStatisticsDataStatsEntry 95 }

affirmedSecurityStatisticsDataStatsPktLenMismatchError OBJECT-TYPE
    SYNTAX      ConfdString
    MAX-ACCESS  read-only
    STATUS      current
    DESCRIPTION "Internal mismatch between calculated and actual lengths"
    ::= { affirmedSecurityStatisticsDataStatsEntry 96 }

affirmedSecurityStatisticsDataStatsParsePktHeaderError OBJECT-TYPE
    SYNTAX      ConfdString
    MAX-ACCESS  read-only
    STATUS      current
    DESCRIPTION "All errors parsing encrypted packet headers"
    ::= { affirmedSecurityStatisticsDataStatsEntry 97 }

affirmedSecurityStatisticsDataStatsCalcPktInfoError OBJECT-TYPE
    SYNTAX      ConfdString
    MAX-ACCESS  read-only
    STATUS      current
    DESCRIPTION "All errors in ingress packet lengths"
    ::= { affirmedSecurityStatisticsDataStatsEntry 98 }

affirmedSecurityStatisticsDataStatsPrelimAntiReplayErrLo OBJECT-TYPE
    SYNTAX      ConfdString
    MAX-ACCESS  read-only
    STATUS      current
    DESCRIPTION "Ingress packet sequence number too low, before decryption"
    ::= { affirmedSecurityStatisticsDataStatsEntry 99 }

affirmedSecurityStatisticsDataStatsPrelimAntiReplayError OBJECT-TYPE
    SYNTAX      ConfdString
    MAX-ACCESS  read-only
    STATUS      current
    DESCRIPTION "Ingress packet sequence number error, but not too low, before decryption"
    ::= { affirmedSecurityStatisticsDataStatsEntry 100 }

affirmedSecurityStatisticsDataStatsEspSeqNumError OBJECT-TYPE
    SYNTAX      ConfdString
    MAX-ACCESS  read-only
    STATUS      current
    DESCRIPTION "All ESP packet sequence number errors, after decryption"
    ::= { affirmedSecurityStatisticsDataStatsEntry 101 }

affirmedSecurityStatisticsDataStatsEspSeqSecm OBJECT-TYPE
    SYNTAX      ConfdString
    MAX-ACCESS  read-only
    STATUS      current
    DESCRIPTION "secm-secm ESP packet sequence number errors, after decryption"
    ::= { affirmedSecurityStatisticsDataStatsEntry 102 }

affirmedSecurityStatisticsDataStatsEspSeqNumLow OBJECT-TYPE
    SYNTAX      ConfdString
    MAX-ACCESS  read-only
    STATUS      current
    DESCRIPTION "ESP packet sequence number too low, after decryption"
    ::= { affirmedSecurityStatisticsDataStatsEntry 103 }

affirmedSecurityStatisticsDataStatsAhSeqNumError OBJECT-TYPE
    SYNTAX      ConfdString
    MAX-ACCESS  read-only
    STATUS      current
    DESCRIPTION "All AH packet sequence number errors, after authentication"
    ::= { affirmedSecurityStatisticsDataStatsEntry 104 }

affirmedSecurityStatisticsDataStatsAppendSeqHighError OBJECT-TYPE
    SYNTAX      ConfdString
    MAX-ACCESS  read-only
    STATUS      current
    DESCRIPTION "Errors appending high half of sequence number to encrypted packets"
    ::= { affirmedSecurityStatisticsDataStatsEntry 105 }

affirmedSecurityStatisticsDataStatsDeleteSeqHighError OBJECT-TYPE
    SYNTAX      ConfdString
    MAX-ACCESS  read-only
    STATUS      current
    DESCRIPTION "Errors in deleting high half sequence number after calculating ICV"
    ::= { affirmedSecurityStatisticsDataStatsEntry 106 }

affirmedSecurityStatisticsDataStatsIcvComputeError OBJECT-TYPE
    SYNTAX      ConfdString
    MAX-ACCESS  read-only
    STATUS      current
    DESCRIPTION "(hw only ) All authentication failures"
    ::= { affirmedSecurityStatisticsDataStatsEntry 107 }

affirmedSecurityStatisticsDataStatsIcvCheckError OBJECT-TYPE
    SYNTAX      ConfdString
    MAX-ACCESS  read-only
    STATUS      current
    DESCRIPTION "(sw only) post cipher authentication failures"
    ::= { affirmedSecurityStatisticsDataStatsEntry 108 }

affirmedSecurityStatisticsDataStatsIcvLenError OBJECT-TYPE
    SYNTAX      ConfdString
    MAX-ACCESS  read-only
    STATUS      current
    DESCRIPTION "(sw only) ingress packet ICV Length Errors"
    ::= { affirmedSecurityStatisticsDataStatsEntry 109 }

affirmedSecurityStatisticsDataStatsEspIcvAuthError OBJECT-TYPE
    SYNTAX      ConfdString
    MAX-ACCESS  read-only
    STATUS      current
    DESCRIPTION "(sw only) pre-cipher authentication failures"
    ::= { affirmedSecurityStatisticsDataStatsEntry 110 }

affirmedSecurityStatisticsDataStatsEspPadError OBJECT-TYPE
    SYNTAX      ConfdString
    MAX-ACCESS  read-only
    STATUS      current
    DESCRIPTION "error in pad field values"
    ::= { affirmedSecurityStatisticsDataStatsEntry 111 }

affirmedSecurityStatisticsDataStatsAhIcvAuthError OBJECT-TYPE
    SYNTAX      ConfdString
    MAX-ACCESS  read-only
    STATUS      current
    DESCRIPTION "(sw only) AH packet failed authentication"
    ::= { affirmedSecurityStatisticsDataStatsEntry 112 }

affirmedSecurityStatisticsDataStatsEspTransChainError OBJECT-TYPE
    SYNTAX      ConfdString
    MAX-ACCESS  read-only
    STATUS      current
    DESCRIPTION "(sw only) transform errors"
    ::= { affirmedSecurityStatisticsDataStatsEntry 113 }

affirmedSecurityStatisticsDataStatsEspProcessAadError OBJECT-TYPE
    SYNTAX      ConfdString
    MAX-ACCESS  read-only
    STATUS      current
    DESCRIPTION "(sw only) transform aad errors"
    ::= { affirmedSecurityStatisticsDataStatsEntry 114 }

affirmedSecurityStatisticsDataStatsTransFinishError OBJECT-TYPE
    SYNTAX      ConfdString
    MAX-ACCESS  read-only
    STATUS      current
    DESCRIPTION "post decryption errors"
    ::= { affirmedSecurityStatisticsDataStatsEntry 115 }

affirmedSecurityStatisticsDataStatsAuthAddRangeError OBJECT-TYPE
    SYNTAX      ConfdString
    MAX-ACCESS  read-only
    STATUS      current
    DESCRIPTION "(sw only) ingress segment errors"
    ::= { affirmedSecurityStatisticsDataStatsEntry 116 }

affirmedSecurityStatisticsDataStatsAuthFinishError OBJECT-TYPE
    SYNTAX      ConfdString
    MAX-ACCESS  read-only
    STATUS      current
    DESCRIPTION "(sw only) errors in finishing authentication"
    ::= { affirmedSecurityStatisticsDataStatsEntry 117 }

affirmedSecurityStatisticsDataStatsCipherUpdateError OBJECT-TYPE
    SYNTAX      ConfdString
    MAX-ACCESS  read-only
    STATUS      current
    DESCRIPTION "(sw only) setup: errors updating cipher"
    ::= { affirmedSecurityStatisticsDataStatsEntry 118 }

affirmedSecurityStatisticsDataStatsAhSeqNumOverflowError OBJECT-TYPE
    SYNTAX      ConfdString
    MAX-ACCESS  read-only
    STATUS      current
    DESCRIPTION "egress AH sequence number overflow"
    ::= { affirmedSecurityStatisticsDataStatsEntry 119 }

affirmedSecurityStatisticsDataStatsEspSeqNumOverflowError OBJECT-TYPE
    SYNTAX      ConfdString
    MAX-ACCESS  read-only
    STATUS      current
    DESCRIPTION "egress ESP sequence number overflow"
    ::= { affirmedSecurityStatisticsDataStatsEntry 120 }

affirmedSecurityStatisticsDataStatsNumIngCryptoAllocFail OBJECT-TYPE
    SYNTAX      ConfdString
    MAX-ACCESS  read-only
    STATUS      current
    DESCRIPTION "(sw only) - context allocation failure"
    ::= { affirmedSecurityStatisticsDataStatsEntry 121 }

affirmedSecurityStatisticsDataStatsNumEgrCryptoAllocFail OBJECT-TYPE
    SYNTAX      ConfdString
    MAX-ACCESS  read-only
    STATUS      current
    DESCRIPTION "(sw only) - context allocation failure"
    ::= { affirmedSecurityStatisticsDataStatsEntry 122 }

affirmedSecurityStatisticsDataStatsNumGetNextHopFail OBJECT-TYPE
    SYNTAX      ConfdString
    MAX-ACCESS  read-only
    STATUS      current
    DESCRIPTION "Egress packet cannot find next hop"
    ::= { affirmedSecurityStatisticsDataStatsEntry 123 }

affirmedSecurityStatisticsDataStatsBypassV4IkeFragment OBJECT-TYPE
    SYNTAX      ConfdString
    MAX-ACCESS  read-only
    STATUS      current
    DESCRIPTION "SPM has sent an IKE packet that was fragmented"
    ::= { affirmedSecurityStatisticsDataStatsEntry 124 }

affirmedSecurityStatisticsDataStatsBypassV4OSPF OBJECT-TYPE
    SYNTAX      ConfdString
    MAX-ACCESS  read-only
    STATUS      current
    DESCRIPTION "V4 OSPF pkts"
    ::= { affirmedSecurityStatisticsDataStatsEntry 125 }

affirmedSecurityStatisticsDataStatsBypassV4Multicast OBJECT-TYPE
    SYNTAX      ConfdString
    MAX-ACCESS  read-only
    STATUS      current
    DESCRIPTION "V4 Multicast pkts"
    ::= { affirmedSecurityStatisticsDataStatsEntry 126 }

affirmedSecurityStatisticsDataStatsBypassV6LinkLocalDest OBJECT-TYPE
    SYNTAX      ConfdString
    MAX-ACCESS  read-only
    STATUS      current
    DESCRIPTION "V6 link local dest pkts"
    ::= { affirmedSecurityStatisticsDataStatsEntry 127 }

affirmedSecurityStatisticsDataStatsBypassV6LinkLocalSrc OBJECT-TYPE
    SYNTAX      ConfdString
    MAX-ACCESS  read-only
    STATUS      current
    DESCRIPTION "V6 link local src pkts"
    ::= { affirmedSecurityStatisticsDataStatsEntry 128 }

affirmedSecurityStatisticsDataStatsBypassTid0V6Icmp OBJECT-TYPE
    SYNTAX      ConfdString
    MAX-ACCESS  read-only
    STATUS      current
    DESCRIPTION "V6 Non-ping icmp pkt"
    ::= { affirmedSecurityStatisticsDataStatsEntry 129 }

affirmedSecurityStatisticsDataStatsBypassTid0IngressIke OBJECT-TYPE
    SYNTAX      ConfdString
    MAX-ACCESS  read-only
    STATUS      current
    DESCRIPTION "Ingress IKE pkt"
    ::= { affirmedSecurityStatisticsDataStatsEntry 130 }

affirmedSecurityStatisticsDataStatsBypassTid0IngressIkeNatt OBJECT-TYPE
    SYNTAX      ConfdString
    MAX-ACCESS  read-only
    STATUS      current
    DESCRIPTION "Ingress IKE NATT pkt"
    ::= { affirmedSecurityStatisticsDataStatsEntry 131 }

affirmedSecurityStatisticsDataStatsBypassTid0IngressV4DhcpClient OBJECT-TYPE
    SYNTAX      ConfdString
    MAX-ACCESS  read-only
    STATUS      current
    DESCRIPTION "Ingress V4 DHCP Client"
    ::= { affirmedSecurityStatisticsDataStatsEntry 132 }

affirmedSecurityStatisticsDataStatsBypassTid0EgressV4DnsClient OBJECT-TYPE
    SYNTAX      ConfdString
    MAX-ACCESS  read-only
    STATUS      current
    DESCRIPTION "Ingress V4 DNS Client"
    ::= { affirmedSecurityStatisticsDataStatsEntry 133 }

affirmedSecurityStatisticsDataStatsBypassTid1IngressUdp OBJECT-TYPE
    SYNTAX      ConfdString
    MAX-ACCESS  read-only
    STATUS      current
    DESCRIPTION "BypassTid1IngressUdp"
    ::= { affirmedSecurityStatisticsDataStatsEntry 134 }

affirmedSecurityStatisticsDataStatsIngressIke OBJECT-TYPE
    SYNTAX      ConfdString
    MAX-ACCESS  read-only
    STATUS      current
    DESCRIPTION "IngressIke"
    ::= { affirmedSecurityStatisticsDataStatsEntry 135 }

affirmedSecurityStatisticsDataStatsIngressIkeNatt OBJECT-TYPE
    SYNTAX      ConfdString
    MAX-ACCESS  read-only
    STATUS      current
    DESCRIPTION "IngressIkeNatt"
    ::= { affirmedSecurityStatisticsDataStatsEntry 136 }

affirmedSecurityStatisticsDataStatsEgressIke OBJECT-TYPE
    SYNTAX      ConfdString
    MAX-ACCESS  read-only
    STATUS      current
    DESCRIPTION "EgressIke"
    ::= { affirmedSecurityStatisticsDataStatsEntry 137 }

affirmedSecurityStatisticsDataStatsEgressIkeNatt OBJECT-TYPE
    SYNTAX      ConfdString
    MAX-ACCESS  read-only
    STATUS      current
    DESCRIPTION "EgressIkeNatt"
    ::= { affirmedSecurityStatisticsDataStatsEntry 138 }

affirmedSecurityStatisticsDataStatsPassRuleHits OBJECT-TYPE
    SYNTAX      ConfdString
    MAX-ACCESS  read-only
    STATUS      current
    DESCRIPTION "PassRuleHits"
    ::= { affirmedSecurityStatisticsDataStatsEntry 139 }

affirmedSecurityStatisticsDataStatsApplyRuleHits OBJECT-TYPE
    SYNTAX      ConfdString
    MAX-ACCESS  read-only
    STATUS      current
    DESCRIPTION "ApplyRuleHits"
    ::= { affirmedSecurityStatisticsDataStatsEntry 140 }

affirmedSecurityStatisticsDataStatsRxNattKaPkts OBJECT-TYPE
    SYNTAX      ConfdString
    MAX-ACCESS  read-only
    STATUS      current
    DESCRIPTION "RxNattKaPkts"
    ::= { affirmedSecurityStatisticsDataStatsEntry 141 }

affirmedSecurityStatisticsDataStatsUseableRuleHits OBJECT-TYPE
    SYNTAX      ConfdString
    MAX-ACCESS  read-only
    STATUS      current
    DESCRIPTION "UseableRuleHits"
    ::= { affirmedSecurityStatisticsDataStatsEntry 142 }

affirmedSecurityStatisticsDataStatsDropPktsWrongRule OBJECT-TYPE
    SYNTAX      ConfdString
    MAX-ACCESS  read-only
    STATUS      current
    DESCRIPTION "DropPktsWrongRule"
    ::= { affirmedSecurityStatisticsDataStatsEntry 143 }

affirmedSecurityStatisticsDataStatsDropPktsOnWrongTunnel OBJECT-TYPE
    SYNTAX      ConfdString
    MAX-ACCESS  read-only
    STATUS      current
    DESCRIPTION "DropPktsOnWrongTunnel"
    ::= { affirmedSecurityStatisticsDataStatsEntry 144 }

affirmedSecurityStatisticsDataStatsNoFlowErrorIngress OBJECT-TYPE
    SYNTAX      ConfdString
    MAX-ACCESS  read-only
    STATUS      current
    DESCRIPTION "NoFlowErrorIngress"
    ::= { affirmedSecurityStatisticsDataStatsEntry 145 }

affirmedSecurityStatisticsDataStatsNoFlowErrorEgress OBJECT-TYPE
    SYNTAX      ConfdString
    MAX-ACCESS  read-only
    STATUS      current
    DESCRIPTION "NoFlowErrorEgress"
    ::= { affirmedSecurityStatisticsDataStatsEntry 146 }

affirmedSecurityStatisticsDataStatsPktsDiscarded OBJECT-TYPE
    SYNTAX      ConfdString
    MAX-ACCESS  read-only
    STATUS      current
    DESCRIPTION "PktsDiscarded"
    ::= { affirmedSecurityStatisticsDataStatsEntry 147 }

affirmedSecurityStatisticsDataStatsNoFlowPassDrop OBJECT-TYPE
    SYNTAX      ConfdString
    MAX-ACCESS  read-only
    STATUS      current
    DESCRIPTION "NoFlowPassDrop"
    ::= { affirmedSecurityStatisticsDataStatsEntry 148 }

affirmedSecurityStatisticsDataStatsNoFlowTid0IngressIPsec OBJECT-TYPE
    SYNTAX      ConfdString
    MAX-ACCESS  read-only
    STATUS      current
    DESCRIPTION "NoFlowTid0IngressIPsec"
    ::= { affirmedSecurityStatisticsDataStatsEntry 149 }

affirmedSecurityStatisticsDataStatsSpiEntryFailLookup OBJECT-TYPE
    SYNTAX      ConfdString
    MAX-ACCESS  read-only
    STATUS      current
    DESCRIPTION "SpiEntryFailLookup"
    ::= { affirmedSecurityStatisticsDataStatsEntry 150 }

affirmedSecurityStatisticsDataStatsDropPktsSecurityDisabled OBJECT-TYPE
    SYNTAX      ConfdString
    MAX-ACCESS  read-only
    STATUS      current
    DESCRIPTION "DropPktsSecurityDisabled"
    ::= { affirmedSecurityStatisticsDataStatsEntry 151 }

affirmedSecurityStatisticsDataStatsUnuseableRuleHits OBJECT-TYPE
    SYNTAX      ConfdString
    MAX-ACCESS  read-only
    STATUS      current
    DESCRIPTION "UnuseableRuleHits"
    ::= { affirmedSecurityStatisticsDataStatsEntry 152 }

affirmedSecurityStatisticsDataStatsDropRuleHits OBJECT-TYPE
    SYNTAX      ConfdString
    MAX-ACCESS  read-only
    STATUS      current
    DESCRIPTION "DropRuleHits"
    ::= { affirmedSecurityStatisticsDataStatsEntry 153 }

affirmedSecurityStatisticsDataStatsRejectRuleHits OBJECT-TYPE
    SYNTAX      ConfdString
    MAX-ACCESS  read-only
    STATUS      current
    DESCRIPTION "RejectRuleHits"
    ::= { affirmedSecurityStatisticsDataStatsEntry 154 }

affirmedSecurityStatisticsDataStatsInvalidRuleHits OBJECT-TYPE
    SYNTAX      ConfdString
    MAX-ACCESS  read-only
    STATUS      current
    DESCRIPTION "InvalidRuleHits"
    ::= { affirmedSecurityStatisticsDataStatsEntry 155 }

affirmedSecurityStatisticsDataStatsDormantApplyRuleHits OBJECT-TYPE
    SYNTAX      ConfdString
    MAX-ACCESS  read-only
    STATUS      current
    DESCRIPTION "DormantApplyRuleHits"
    ::= { affirmedSecurityStatisticsDataStatsEntry 156 }

affirmedSecurityStatisticsDataStatsUnknownRuleHits OBJECT-TYPE
    SYNTAX      ConfdString
    MAX-ACCESS  read-only
    STATUS      current
    DESCRIPTION "UnknownRuleHits"
    ::= { affirmedSecurityStatisticsDataStatsEntry 157 }

affirmedSecurityStatisticsDataStatsPostSecPktErrsInvalidHeader OBJECT-TYPE
    SYNTAX      ConfdString
    MAX-ACCESS  read-only
    STATUS      current
    DESCRIPTION "PostSecPktErrsInvalidHeader"
    ::= { affirmedSecurityStatisticsDataStatsEntry 158 }

affirmedSecurityStatisticsDataStatsPostSecPktErrsInvalidFragHeader OBJECT-TYPE
    SYNTAX      ConfdString
    MAX-ACCESS  read-only
    STATUS      current
    DESCRIPTION "PostSecPktErrsInvalidFragHeader"
    ::= { affirmedSecurityStatisticsDataStatsEntry 159 }

affirmedSecurityStatisticsDataStatsPostSecPktErrsNoFlowFound OBJECT-TYPE
    SYNTAX      ConfdString
    MAX-ACCESS  read-only
    STATUS      current
    DESCRIPTION "PostSecPktErrsNoFlowFound"
    ::= { affirmedSecurityStatisticsDataStatsEntry 160 }

affirmedSecurityStatisticsDataStatsPostSecPktErrsBadFlowFound OBJECT-TYPE
    SYNTAX      ConfdString
    MAX-ACCESS  read-only
    STATUS      current
    DESCRIPTION "PostSecPktErrsBadFlowFound"
    ::= { affirmedSecurityStatisticsDataStatsEntry 161 }

affirmedSecurityStatisticsDataStatsPostSecPktErrsUnexpectedPendFlow OBJECT-TYPE
    SYNTAX      ConfdString
    MAX-ACCESS  read-only
    STATUS      current
    DESCRIPTION "PostSecPktErrsUnexpectedPendFlow"
    ::= { affirmedSecurityStatisticsDataStatsEntry 162 }

affirmedSecurityStatisticsDataStatsPostSecPktErrsUnexpectedApplyFlow OBJECT-TYPE
    SYNTAX      ConfdString
    MAX-ACCESS  read-only
    STATUS      current
    DESCRIPTION "PostSecPktErrsUnexpectedApplyFlow"
    ::= { affirmedSecurityStatisticsDataStatsEntry 163 }

affirmedSecurityStatisticsDataStatsPostSecPktErrsUnexpectedRejectFlow OBJECT-TYPE
    SYNTAX      ConfdString
    MAX-ACCESS  read-only
    STATUS      current
    DESCRIPTION "PostSecPktErrsUnexpectedRejectFlow"
    ::= { affirmedSecurityStatisticsDataStatsEntry 164 }

affirmedSecurityStatisticsDataStatsPostSecPktErrsUnexpectedTriggerFlow OBJECT-TYPE
    SYNTAX      ConfdString
    MAX-ACCESS  read-only
    STATUS      current
    DESCRIPTION "PostSecPktErrsUnexpectedTriggerFlow"
    ::= { affirmedSecurityStatisticsDataStatsEntry 165 }

affirmedSecurityStatisticsDataStatsPostSecPktErrsUnexpectedDropFlow OBJECT-TYPE
    SYNTAX      ConfdString
    MAX-ACCESS  read-only
    STATUS      current
    DESCRIPTION "PostSecPktErrsUnexpectedDropFlow"
    ::= { affirmedSecurityStatisticsDataStatsEntry 166 }

affirmedSecurityStatisticsDataStatsPostSecPktErrsUnexpectedNonExistentFlow OBJECT-TYPE
    SYNTAX      ConfdString
    MAX-ACCESS  read-only
    STATUS      current
    DESCRIPTION "PostSecPktErrsUnexpectedNonExistentFlow"
    ::= { affirmedSecurityStatisticsDataStatsEntry 167 }

affirmedSecurityStatisticsDataStatsDropPktsDropRule OBJECT-TYPE
    SYNTAX      ConfdString
    MAX-ACCESS  read-only
    STATUS      current
    DESCRIPTION "DropPktsDropRule"
    ::= { affirmedSecurityStatisticsDataStatsEntry 168 }

affirmedSecurityStatisticsDataStatsNullSpiEntry OBJECT-TYPE
    SYNTAX      ConfdString
    MAX-ACCESS  read-only
    STATUS      current
    DESCRIPTION "NullSpiEntry"
    ::= { affirmedSecurityStatisticsDataStatsEntry 169 }

affirmedSecurityStatisticsDataStatsInvalidFSAPI OBJECT-TYPE
    SYNTAX      ConfdString
    MAX-ACCESS  read-only
    STATUS      current
    DESCRIPTION "InvalidFSAPI"
    ::= { affirmedSecurityStatisticsDataStatsEntry 170 }

affirmedSecurityStatisticsDataStatsNewTable OBJECT-TYPE
    SYNTAX      SEQUENCE OF AffirmedSecurityStatisticsDataStatsNewEntry
    MAX-ACCESS  not-accessible
    STATUS      current
    DESCRIPTION ""
    ::= { affirmedSecurityStatistics 10 }

affirmedSecurityStatisticsDataStatsNewEntry OBJECT-TYPE
    SYNTAX      AffirmedSecurityStatisticsDataStatsNewEntry
    MAX-ACCESS  not-accessible
    STATUS      current
    DESCRIPTION ""
    INDEX { affirmedSecurityStatisticsDataStatsNewDummyIndex }
        ::= { affirmedSecurityStatisticsDataStatsNewTable 1 }

AffirmedSecurityStatisticsDataStatsNewEntry ::=
    SEQUENCE {
        affirmedSecurityStatisticsDataStatsNewDummyIndex Unsigned32,
        affirmedSecurityStatisticsDataStatsNewRxV4Pkts ConfdString,
        affirmedSecurityStatisticsDataStatsNewRxV4Bytes ConfdString,
        affirmedSecurityStatisticsDataStatsNewRxV6Pkts ConfdString,
        affirmedSecurityStatisticsDataStatsNewRxV6Bytes ConfdString,
        affirmedSecurityStatisticsDataStatsNewTxV4Pkts ConfdString,
        affirmedSecurityStatisticsDataStatsNewTxV4Bytes ConfdString,
        affirmedSecurityStatisticsDataStatsNewTxV6Pkts ConfdString,
        affirmedSecurityStatisticsDataStatsNewTxV6Bytes ConfdString,
        affirmedSecurityStatisticsDataStatsNewRxPostSecurityV4Pkts ConfdString,
        affirmedSecurityStatisticsDataStatsNewRxPostSecurityV4Bytes ConfdString,
        affirmedSecurityStatisticsDataStatsNewRxPostSecurityV6Pkts ConfdString,
        affirmedSecurityStatisticsDataStatsNewRxPostSecurityV6Bytes ConfdString,
        affirmedSecurityStatisticsDataStatsNewRxEspPkts ConfdString,
        affirmedSecurityStatisticsDataStatsNewRxRemoteSecmPkts ConfdString,
        affirmedSecurityStatisticsDataStatsNewRxSecmIngTransPkts ConfdString,
        affirmedSecurityStatisticsDataStatsNewRxSecmEgrTransPkts ConfdString,
        affirmedSecurityStatisticsDataStatsNewRxSpmPktsIgnored ConfdString,
        affirmedSecurityStatisticsDataStatsNewFwdRemoteSecmPkts ConfdString,
        affirmedSecurityStatisticsDataStatsNewFwdSpmPkts ConfdString,
        affirmedSecurityStatisticsDataStatsNewSecmIngPktsFwdFail ConfdString,
        affirmedSecurityStatisticsDataStatsNewSecmEgrPktsFwdFail ConfdString,
        affirmedSecurityStatisticsDataStatsNewRxBypassRulePkts ConfdString,
        affirmedSecurityStatisticsDataStatsNewTxBypassRulePkts ConfdString,
        affirmedSecurityStatisticsDataStatsNewBypassV4IkeFragment ConfdString,
        affirmedSecurityStatisticsDataStatsNewBypassV4Multicast ConfdString,
        affirmedSecurityStatisticsDataStatsNewBypassV6NdNbrIcmp ConfdString,
        affirmedSecurityStatisticsDataStatsNewBypassV6Multicast ConfdString,
        affirmedSecurityStatisticsDataStatsNewBypassV6LinkLocalDest ConfdString,
        affirmedSecurityStatisticsDataStatsNewBypassV6LinkLocalSrc ConfdString,
        affirmedSecurityStatisticsDataStatsNewBypassTid0V6Icmp ConfdString,
        affirmedSecurityStatisticsDataStatsNewBypassTid0IngressIke ConfdString,
        affirmedSecurityStatisticsDataStatsNewBypassTid0IngressIkeNatt ConfdString,
        affirmedSecurityStatisticsDataStatsNewBypassTid0IngressV4DhcpClient ConfdString,
        affirmedSecurityStatisticsDataStatsNewBypassTid0EgressV4DnsClient ConfdString,
        affirmedSecurityStatisticsDataStatsNewBypassTid1IngressUdp ConfdString,
        affirmedSecurityStatisticsDataStatsNewTxEspPkts ConfdString,
        affirmedSecurityStatisticsDataStatsNewQueuedPkts ConfdString,
        affirmedSecurityStatisticsDataStatsNewDequeuedPkts ConfdString,
        affirmedSecurityStatisticsDataStatsNewTransactionsAllocated ConfdString,
        affirmedSecurityStatisticsDataStatsNewTransactionsDeallocated ConfdString,
        affirmedSecurityStatisticsDataStatsNewIngressIke ConfdString,
        affirmedSecurityStatisticsDataStatsNewIngressIkeNatt ConfdString,
        affirmedSecurityStatisticsDataStatsNewEgressIke ConfdString,
        affirmedSecurityStatisticsDataStatsNewEgressIkeNatt ConfdString,
        affirmedSecurityStatisticsDataStatsNewUseableRuleHits ConfdString,
        affirmedSecurityStatisticsDataStatsNewDropPktsRule ConfdString,
        affirmedSecurityStatisticsDataStatsNewDropPktsRejectRule ConfdString,
        affirmedSecurityStatisticsDataStatsNewPassRuleHits ConfdString,
        affirmedSecurityStatisticsDataStatsNewApplyRuleHits ConfdString,
        affirmedSecurityStatisticsDataStatsNewRxNattKaPkts ConfdString,
        affirmedSecurityStatisticsDataStatsNewRxEpdgPkts ConfdString,
        affirmedSecurityStatisticsDataStatsNewTxEpdgPkts ConfdString,
        affirmedSecurityStatisticsDataStatsNewRxIkeApplyPolicy ConfdString,
        affirmedSecurityStatisticsDataStatsNewRxIkeNattApplyPolicy ConfdString,
        affirmedSecurityStatisticsDataStatsNewRxV4DropPkts ConfdString,
        affirmedSecurityStatisticsDataStatsNewRxV4DropBytes ConfdString,
        affirmedSecurityStatisticsDataStatsNewRxV6DropPkts ConfdString,
        affirmedSecurityStatisticsDataStatsNewRxV6DropBytes ConfdString,
        affirmedSecurityStatisticsDataStatsNewTxV4DropPkts ConfdString,
        affirmedSecurityStatisticsDataStatsNewTxV4DropBytes ConfdString,
        affirmedSecurityStatisticsDataStatsNewTxV6DropPkts ConfdString,
        affirmedSecurityStatisticsDataStatsNewTxV6DropBytes ConfdString,
        affirmedSecurityStatisticsDataStatsNewRemoteTransError ConfdString,
        affirmedSecurityStatisticsDataStatsNewInvalidHeaderError ConfdString,
        affirmedSecurityStatisticsDataStatsNewRxPendingFlowError ConfdString,
        affirmedSecurityStatisticsDataStatsNewTxPendingFlowError ConfdString,
        affirmedSecurityStatisticsDataStatsNewNoFlowErrorIngress ConfdString,
        affirmedSecurityStatisticsDataStatsNewNoFlowErrorEgress ConfdString,
        affirmedSecurityStatisticsDataStatsNewTransNotFoundError ConfdString,
        affirmedSecurityStatisticsDataStatsNewIngCtxtInUse ConfdString,
        affirmedSecurityStatisticsDataStatsNewFailedSanity ConfdString,
        affirmedSecurityStatisticsDataStatsNewDropPktsIntfNotFound ConfdString,
        affirmedSecurityStatisticsDataStatsNewDropPktsSessionNotFound ConfdString,
        affirmedSecurityStatisticsDataStatsNewDropPktsSecurityDisabled ConfdString,
        affirmedSecurityStatisticsDataStatsNewTransactionsDeallocFailed ConfdString,
        affirmedSecurityStatisticsDataStatsNewInvalidNumaNode ConfdString,
        affirmedSecurityStatisticsDataStatsNewIngSpiMismatch ConfdString,
        affirmedSecurityStatisticsDataStatsNewEgrSpiMismatch ConfdString,
        affirmedSecurityStatisticsDataStatsNewTransAuthErrs ConfdString,
        affirmedSecurityStatisticsDataStatsNewPostSecTransAuthErrs ConfdString,
        affirmedSecurityStatisticsDataStatsNewPostSecPktErrs ConfdString,
        affirmedSecurityStatisticsDataStatsNewPostSecPktErrsInvalidHeader ConfdString,
        affirmedSecurityStatisticsDataStatsNewPostSecPktErrsInvalidFragHeader ConfdString,
        affirmedSecurityStatisticsDataStatsNewPostSecPktErrsNoFlowFound ConfdString,
        affirmedSecurityStatisticsDataStatsNewPostSecPktErrsBadFlowFound ConfdString,
        affirmedSecurityStatisticsDataStatsNewPostSecPktErrsUnexpectedPendFlow ConfdString,
        affirmedSecurityStatisticsDataStatsNewPostSecPktErrsUnexpectedApplyFlow ConfdString,
        affirmedSecurityStatisticsDataStatsNewPostSecPktErrsUnexpectedRejectFlow ConfdString,
        affirmedSecurityStatisticsDataStatsNewPostSecPktErrsUnexpectedTriggerFlow ConfdString,
        affirmedSecurityStatisticsDataStatsNewPostSecPktErrsUnexpectedDropFlow ConfdString,
        affirmedSecurityStatisticsDataStatsNewPostSecPktErrsUnexpectedNonExistentFlow ConfdString,
        affirmedSecurityStatisticsDataStatsNewPostSecIntfPktErrs ConfdString,
        affirmedSecurityStatisticsDataStatsNewPostSecFpPktErrs ConfdString,
        affirmedSecurityStatisticsDataStatsNewIngCtxtErrs ConfdString,
        affirmedSecurityStatisticsDataStatsNewEgrCtxtErrs ConfdString,
        affirmedSecurityStatisticsDataStatsNewUnuseableRuleHits ConfdString,
        affirmedSecurityStatisticsDataStatsNewInvalidRuleHits ConfdString,
        affirmedSecurityStatisticsDataStatsNewTriggerRuleHits ConfdString,
        affirmedSecurityStatisticsDataStatsNewDormantApplyRuleHits ConfdString,
        affirmedSecurityStatisticsDataStatsNewUnknownRuleHits ConfdString,
        affirmedSecurityStatisticsDataStatsNewNoFlowPassAtRemoteSecm ConfdString,
        affirmedSecurityStatisticsDataStatsNewPktsDiscarded ConfdString,
        affirmedSecurityStatisticsDataStatsNewNoFlowPassDrop ConfdString,
        affirmedSecurityStatisticsDataStatsNewNoFlowTid0IngressIPsec ConfdString,
        affirmedSecurityStatisticsDataStatsNewNoFlowTidV6IcmpErr ConfdString,
        affirmedSecurityStatisticsDataStatsNewNoFlowTidV4IcmpErr ConfdString,
        affirmedSecurityStatisticsDataStatsNewDropPktsTooBig ConfdString,
        affirmedSecurityStatisticsDataStatsNewDropPktsNoRule ConfdString,
        affirmedSecurityStatisticsDataStatsNewDropPktsTriggerRule ConfdString,
        affirmedSecurityStatisticsDataStatsNewDequeuePendingError ConfdString,
        affirmedSecurityStatisticsDataStatsNewNullSpiEntry ConfdString,
        affirmedSecurityStatisticsDataStatsNewInvalidFSAPI ConfdString,
        affirmedSecurityStatisticsDataStatsNewSpiEntryFailLookup ConfdString,
        affirmedSecurityStatisticsDataStatsNewSpiTransformEntryFailLookup ConfdString,
        affirmedSecurityStatisticsDataStatsNewTriggerRuleIngressPkts ConfdString,
        affirmedSecurityStatisticsDataStatsNewRejectRuleHits ConfdString,
        affirmedSecurityStatisticsDataStatsNewFlushedPkts ConfdString,
        affirmedSecurityStatisticsDataStatsNewQueuedPktNotApply ConfdString,
        affirmedSecurityStatisticsDataStatsNewEspSpiMismatchError ConfdString,
        affirmedSecurityStatisticsDataStatsNewCipherNotFoundError ConfdString,
        affirmedSecurityStatisticsDataStatsNewPktDataAccessError ConfdString,
        affirmedSecurityStatisticsDataStatsNewPktSizeCipherSizeError ConfdString,
        affirmedSecurityStatisticsDataStatsNewPktTooShortError ConfdString,
        affirmedSecurityStatisticsDataStatsNewPktLenMismatchError ConfdString,
        affirmedSecurityStatisticsDataStatsNewParsePktHeaderError ConfdString,
        affirmedSecurityStatisticsDataStatsNewCalcPktInfoError ConfdString,
        affirmedSecurityStatisticsDataStatsNewPrelimAntiReplayErrLo ConfdString,
        affirmedSecurityStatisticsDataStatsNewPrelimAntiReplayError ConfdString,
        affirmedSecurityStatisticsDataStatsNewEspSeqNumError ConfdString,
        affirmedSecurityStatisticsDataStatsNewEspSeqSecm ConfdString,
        affirmedSecurityStatisticsDataStatsNewEspSeqNumLow ConfdString,
        affirmedSecurityStatisticsDataStatsNewAppendSeqHighError ConfdString,
        affirmedSecurityStatisticsDataStatsNewDeleteSeqHighError ConfdString,
        affirmedSecurityStatisticsDataStatsNewIcvComputeError ConfdString,
        affirmedSecurityStatisticsDataStatsNewIcvCheckError ConfdString,
        affirmedSecurityStatisticsDataStatsNewIcvLenError ConfdString,
        affirmedSecurityStatisticsDataStatsNewEspIcvAuthError ConfdString,
        affirmedSecurityStatisticsDataStatsNewEspPadError ConfdString,
        affirmedSecurityStatisticsDataStatsNewEspTransChainError ConfdString,
        affirmedSecurityStatisticsDataStatsNewEspProcessAadError ConfdString,
        affirmedSecurityStatisticsDataStatsNewTransFinishError ConfdString,
        affirmedSecurityStatisticsDataStatsNewAuthAddRangeError ConfdString,
        affirmedSecurityStatisticsDataStatsNewAuthFinishError ConfdString,
        affirmedSecurityStatisticsDataStatsNewCipherUpdateError ConfdString,
        affirmedSecurityStatisticsDataStatsNewEspSeqNumOverflowError ConfdString,
        affirmedSecurityStatisticsDataStatsNewIngCryptoAllocFail ConfdString,
        affirmedSecurityStatisticsDataStatsNewEgrCryptoAllocFail ConfdString,
        affirmedSecurityStatisticsDataStatsNewIngCryptoResetFail ConfdString,
        affirmedSecurityStatisticsDataStatsNewEgrCryptoResetFail ConfdString,
        affirmedSecurityStatisticsDataStatsNewGetNextHopFail ConfdString,
        affirmedSecurityStatisticsDataStatsNewNoCryptoCapability ConfdString,
        affirmedSecurityStatisticsDataStatsNewSecmSessionIcmpFragNeededMsgSent ConfdString,
        affirmedSecurityStatisticsDataStatsNewSecmIcmpFragNeededMsgSent ConfdString,
        affirmedSecurityStatisticsDataStatsNewSecmSessionIcmpV6PacketTooBigMsgSent ConfdString,
        affirmedSecurityStatisticsDataStatsNewSecmIcmpV6PacketTooBigMsgSent ConfdString,
        affirmedSecurityStatisticsDataStatsNewSecmIPv6MaxFragAfterEncryptionTooBig ConfdString,
        affirmedSecurityStatisticsDataStatsNewSecmIPv6MaxFragTooBig ConfdString,
        affirmedSecurityStatisticsDataStatsNewSecmIPv6PktTooBigPreFragEnabled ConfdString,
        affirmedSecurityStatisticsDataStatsNewSecmIPv6FragSuccess ConfdString,
        affirmedSecurityStatisticsDataStatsNewSecmIPv4FragSuccess ConfdString,
        affirmedSecurityStatisticsDataStatsNewSecmIPv6FragFailed ConfdString,
        affirmedSecurityStatisticsDataStatsNewSecmIPv4FragFailed ConfdString,
        affirmedSecurityStatisticsDataStatsNewSecmFragStatusFailed ConfdString,
        affirmedSecurityStatisticsDataStatsNewSecmNumFrlDropIngressCnts ConfdString,
        affirmedSecurityStatisticsDataStatsNewSecmNumPrlDropIngressCnts ConfdString,
        affirmedSecurityStatisticsDataStatsNewSecmNumFrlDropEgressCnts ConfdString,
        affirmedSecurityStatisticsDataStatsNewSecmNumPrlDropEgressCnts ConfdString
    }

affirmedSecurityStatisticsDataStatsNewDummyIndex OBJECT-TYPE
    SYNTAX      Unsigned32
    MAX-ACCESS  not-accessible
    STATUS      current
    DESCRIPTION ""
    ::= { affirmedSecurityStatisticsDataStatsNewEntry 1 }

affirmedSecurityStatisticsDataStatsNewRxV4Pkts OBJECT-TYPE
    SYNTAX      ConfdString
    MAX-ACCESS  read-only
    STATUS      current
    DESCRIPTION "Ingress IPv4 packets successfully processed "
    ::= { affirmedSecurityStatisticsDataStatsNewEntry 2 }

affirmedSecurityStatisticsDataStatsNewRxV4Bytes OBJECT-TYPE
    SYNTAX      ConfdString
    MAX-ACCESS  read-only
    STATUS      current
    DESCRIPTION "Ingress IPv4 bytes successfully processed "
    ::= { affirmedSecurityStatisticsDataStatsNewEntry 3 }

affirmedSecurityStatisticsDataStatsNewRxV6Pkts OBJECT-TYPE
    SYNTAX      ConfdString
    MAX-ACCESS  read-only
    STATUS      current
    DESCRIPTION "Ingress IPv6 packets successfully processed "
    ::= { affirmedSecurityStatisticsDataStatsNewEntry 4 }

affirmedSecurityStatisticsDataStatsNewRxV6Bytes OBJECT-TYPE
    SYNTAX      ConfdString
    MAX-ACCESS  read-only
    STATUS      current
    DESCRIPTION "Ingress IPv6 bytes successfully processed "
    ::= { affirmedSecurityStatisticsDataStatsNewEntry 5 }

affirmedSecurityStatisticsDataStatsNewTxV4Pkts OBJECT-TYPE
    SYNTAX      ConfdString
    MAX-ACCESS  read-only
    STATUS      current
    DESCRIPTION "Egress IPv4 packets successfully processed "
    ::= { affirmedSecurityStatisticsDataStatsNewEntry 6 }

affirmedSecurityStatisticsDataStatsNewTxV4Bytes OBJECT-TYPE
    SYNTAX      ConfdString
    MAX-ACCESS  read-only
    STATUS      current
    DESCRIPTION "Egress IPv4 bytes successfully processed "
    ::= { affirmedSecurityStatisticsDataStatsNewEntry 7 }

affirmedSecurityStatisticsDataStatsNewTxV6Pkts OBJECT-TYPE
    SYNTAX      ConfdString
    MAX-ACCESS  read-only
    STATUS      current
    DESCRIPTION "Egress IPv6 packets successfully processed "
    ::= { affirmedSecurityStatisticsDataStatsNewEntry 8 }

affirmedSecurityStatisticsDataStatsNewTxV6Bytes OBJECT-TYPE
    SYNTAX      ConfdString
    MAX-ACCESS  read-only
    STATUS      current
    DESCRIPTION "Egress IPv6 bytes successfully processed "
    ::= { affirmedSecurityStatisticsDataStatsNewEntry 9 }

affirmedSecurityStatisticsDataStatsNewRxPostSecurityV4Pkts OBJECT-TYPE
    SYNTAX      ConfdString
    MAX-ACCESS  read-only
    STATUS      current
    DESCRIPTION "Dequeued ingress IPv4 packets successfully processed "
    ::= { affirmedSecurityStatisticsDataStatsNewEntry 10 }

affirmedSecurityStatisticsDataStatsNewRxPostSecurityV4Bytes OBJECT-TYPE
    SYNTAX      ConfdString
    MAX-ACCESS  read-only
    STATUS      current
    DESCRIPTION "Dequeued ingress IPv4 bytes successfully processed "
    ::= { affirmedSecurityStatisticsDataStatsNewEntry 11 }

affirmedSecurityStatisticsDataStatsNewRxPostSecurityV6Pkts OBJECT-TYPE
    SYNTAX      ConfdString
    MAX-ACCESS  read-only
    STATUS      current
    DESCRIPTION "Dequeued ingress IPv6 packets successfully processed "
    ::= { affirmedSecurityStatisticsDataStatsNewEntry 12 }

affirmedSecurityStatisticsDataStatsNewRxPostSecurityV6Bytes OBJECT-TYPE
    SYNTAX      ConfdString
    MAX-ACCESS  read-only
    STATUS      current
    DESCRIPTION "Dequeued ingress IPv6 bytes successfully processed "
    ::= { affirmedSecurityStatisticsDataStatsNewEntry 13 }

affirmedSecurityStatisticsDataStatsNewRxEspPkts OBJECT-TYPE
    SYNTAX      ConfdString
    MAX-ACCESS  read-only
    STATUS      current
    DESCRIPTION "Authenticated and decrypted packets (ESP) received"
    ::= { affirmedSecurityStatisticsDataStatsNewEntry 14 }

affirmedSecurityStatisticsDataStatsNewRxRemoteSecmPkts OBJECT-TYPE
    SYNTAX      ConfdString
    MAX-ACCESS  read-only
    STATUS      current
    DESCRIPTION "Total packets from other SSM"
    ::= { affirmedSecurityStatisticsDataStatsNewEntry 15 }

affirmedSecurityStatisticsDataStatsNewRxSecmIngTransPkts OBJECT-TYPE
    SYNTAX      ConfdString
    MAX-ACCESS  read-only
    STATUS      current
    DESCRIPTION "Ingress packets from other SSM"
    ::= { affirmedSecurityStatisticsDataStatsNewEntry 16 }

affirmedSecurityStatisticsDataStatsNewRxSecmEgrTransPkts OBJECT-TYPE
    SYNTAX      ConfdString
    MAX-ACCESS  read-only
    STATUS      current
    DESCRIPTION "Egress packets from other SSM"
    ::= { affirmedSecurityStatisticsDataStatsNewEntry 17 }

affirmedSecurityStatisticsDataStatsNewRxSpmPktsIgnored OBJECT-TYPE
    SYNTAX      ConfdString
    MAX-ACCESS  read-only
    STATUS      current
    DESCRIPTION "Packets from SPM ignored"
    ::= { affirmedSecurityStatisticsDataStatsNewEntry 18 }

affirmedSecurityStatisticsDataStatsNewFwdRemoteSecmPkts OBJECT-TYPE
    SYNTAX      ConfdString
    MAX-ACCESS  read-only
    STATUS      current
    DESCRIPTION "Egress packets sent to other SSM"
    ::= { affirmedSecurityStatisticsDataStatsNewEntry 19 }

affirmedSecurityStatisticsDataStatsNewFwdSpmPkts OBJECT-TYPE
    SYNTAX      ConfdString
    MAX-ACCESS  read-only
    STATUS      current
    DESCRIPTION "Packets forwarded to SPM"
    ::= { affirmedSecurityStatisticsDataStatsNewEntry 20 }

affirmedSecurityStatisticsDataStatsNewSecmIngPktsFwdFail OBJECT-TYPE
    SYNTAX      ConfdString
    MAX-ACCESS  read-only
    STATUS      current
    DESCRIPTION "Ingress packet from other SSM failures"
    ::= { affirmedSecurityStatisticsDataStatsNewEntry 21 }

affirmedSecurityStatisticsDataStatsNewSecmEgrPktsFwdFail OBJECT-TYPE
    SYNTAX      ConfdString
    MAX-ACCESS  read-only
    STATUS      current
    DESCRIPTION "Egress packet from other SSM failures"
    ::= { affirmedSecurityStatisticsDataStatsNewEntry 22 }

affirmedSecurityStatisticsDataStatsNewRxBypassRulePkts OBJECT-TYPE
    SYNTAX      ConfdString
    MAX-ACCESS  read-only
    STATUS      current
    DESCRIPTION "Packets received that bypass security"
    ::= { affirmedSecurityStatisticsDataStatsNewEntry 23 }

affirmedSecurityStatisticsDataStatsNewTxBypassRulePkts OBJECT-TYPE
    SYNTAX      ConfdString
    MAX-ACCESS  read-only
    STATUS      current
    DESCRIPTION "WF Packets from other SSM that bypass security"
    ::= { affirmedSecurityStatisticsDataStatsNewEntry 24 }

affirmedSecurityStatisticsDataStatsNewBypassV4IkeFragment OBJECT-TYPE
    SYNTAX      ConfdString
    MAX-ACCESS  read-only
    STATUS      current
    DESCRIPTION "SPM has sent an IKE packet that was fragmented"
    ::= { affirmedSecurityStatisticsDataStatsNewEntry 25 }

affirmedSecurityStatisticsDataStatsNewBypassV4Multicast OBJECT-TYPE
    SYNTAX      ConfdString
    MAX-ACCESS  read-only
    STATUS      current
    DESCRIPTION "V4 Multicast pkts"
    ::= { affirmedSecurityStatisticsDataStatsNewEntry 26 }

affirmedSecurityStatisticsDataStatsNewBypassV6NdNbrIcmp OBJECT-TYPE
    SYNTAX      ConfdString
    MAX-ACCESS  read-only
    STATUS      current
    DESCRIPTION "V6 Neighbor advertisement"
    ::= { affirmedSecurityStatisticsDataStatsNewEntry 27 }

affirmedSecurityStatisticsDataStatsNewBypassV6Multicast OBJECT-TYPE
    SYNTAX      ConfdString
    MAX-ACCESS  read-only
    STATUS      current
    DESCRIPTION "V6 Multicast pkts"
    ::= { affirmedSecurityStatisticsDataStatsNewEntry 28 }

affirmedSecurityStatisticsDataStatsNewBypassV6LinkLocalDest OBJECT-TYPE
    SYNTAX      ConfdString
    MAX-ACCESS  read-only
    STATUS      current
    DESCRIPTION "V6 link local dest pkts"
    ::= { affirmedSecurityStatisticsDataStatsNewEntry 29 }

affirmedSecurityStatisticsDataStatsNewBypassV6LinkLocalSrc OBJECT-TYPE
    SYNTAX      ConfdString
    MAX-ACCESS  read-only
    STATUS      current
    DESCRIPTION "V6 link local src pkts"
    ::= { affirmedSecurityStatisticsDataStatsNewEntry 30 }

affirmedSecurityStatisticsDataStatsNewBypassTid0V6Icmp OBJECT-TYPE
    SYNTAX      ConfdString
    MAX-ACCESS  read-only
    STATUS      current
    DESCRIPTION "V6 Non-ping icmp pkt"
    ::= { affirmedSecurityStatisticsDataStatsNewEntry 31 }

affirmedSecurityStatisticsDataStatsNewBypassTid0IngressIke OBJECT-TYPE
    SYNTAX      ConfdString
    MAX-ACCESS  read-only
    STATUS      current
    DESCRIPTION "Ingress IKE pkt"
    ::= { affirmedSecurityStatisticsDataStatsNewEntry 32 }

affirmedSecurityStatisticsDataStatsNewBypassTid0IngressIkeNatt OBJECT-TYPE
    SYNTAX      ConfdString
    MAX-ACCESS  read-only
    STATUS      current
    DESCRIPTION "Ingress IKE NATT pkt"
    ::= { affirmedSecurityStatisticsDataStatsNewEntry 33 }

affirmedSecurityStatisticsDataStatsNewBypassTid0IngressV4DhcpClient OBJECT-TYPE
    SYNTAX      ConfdString
    MAX-ACCESS  read-only
    STATUS      current
    DESCRIPTION "Ingress V4 DHCP Client"
    ::= { affirmedSecurityStatisticsDataStatsNewEntry 34 }

affirmedSecurityStatisticsDataStatsNewBypassTid0EgressV4DnsClient OBJECT-TYPE
    SYNTAX      ConfdString
    MAX-ACCESS  read-only
    STATUS      current
    DESCRIPTION "Ingress V4 DNS Client"
    ::= { affirmedSecurityStatisticsDataStatsNewEntry 35 }

affirmedSecurityStatisticsDataStatsNewBypassTid1IngressUdp OBJECT-TYPE
    SYNTAX      ConfdString
    MAX-ACCESS  read-only
    STATUS      current
    DESCRIPTION "BypassTid1IngressUdp"
    ::= { affirmedSecurityStatisticsDataStatsNewEntry 36 }

affirmedSecurityStatisticsDataStatsNewTxEspPkts OBJECT-TYPE
    SYNTAX      ConfdString
    MAX-ACCESS  read-only
    STATUS      current
    DESCRIPTION "Packets to be encrypted and authentication calculated"
    ::= { affirmedSecurityStatisticsDataStatsNewEntry 37 }

affirmedSecurityStatisticsDataStatsNewQueuedPkts OBJECT-TYPE
    SYNTAX      ConfdString
    MAX-ACCESS  read-only
    STATUS      current
    DESCRIPTION "Packets queued waiting for SPM to validate flow"
    ::= { affirmedSecurityStatisticsDataStatsNewEntry 38 }

affirmedSecurityStatisticsDataStatsNewDequeuedPkts OBJECT-TYPE
    SYNTAX      ConfdString
    MAX-ACCESS  read-only
    STATUS      current
    DESCRIPTION "Packets dequeued when SPM validates flow"
    ::= { affirmedSecurityStatisticsDataStatsNewEntry 39 }

affirmedSecurityStatisticsDataStatsNewTransactionsAllocated OBJECT-TYPE
    SYNTAX      ConfdString
    MAX-ACCESS  read-only
    STATUS      current
    DESCRIPTION "Transactions Allocated"
    ::= { affirmedSecurityStatisticsDataStatsNewEntry 40 }

affirmedSecurityStatisticsDataStatsNewTransactionsDeallocated OBJECT-TYPE
    SYNTAX      ConfdString
    MAX-ACCESS  read-only
    STATUS      current
    DESCRIPTION "TransactionsDeallocated"
    ::= { affirmedSecurityStatisticsDataStatsNewEntry 41 }

affirmedSecurityStatisticsDataStatsNewIngressIke OBJECT-TYPE
    SYNTAX      ConfdString
    MAX-ACCESS  read-only
    STATUS      current
    DESCRIPTION "IngressIke"
    ::= { affirmedSecurityStatisticsDataStatsNewEntry 42 }

affirmedSecurityStatisticsDataStatsNewIngressIkeNatt OBJECT-TYPE
    SYNTAX      ConfdString
    MAX-ACCESS  read-only
    STATUS      current
    DESCRIPTION "IngressIkeNatt"
    ::= { affirmedSecurityStatisticsDataStatsNewEntry 43 }

affirmedSecurityStatisticsDataStatsNewEgressIke OBJECT-TYPE
    SYNTAX      ConfdString
    MAX-ACCESS  read-only
    STATUS      current
    DESCRIPTION "EgressIke"
    ::= { affirmedSecurityStatisticsDataStatsNewEntry 44 }

affirmedSecurityStatisticsDataStatsNewEgressIkeNatt OBJECT-TYPE
    SYNTAX      ConfdString
    MAX-ACCESS  read-only
    STATUS      current
    DESCRIPTION "EgressIkeNatt"
    ::= { affirmedSecurityStatisticsDataStatsNewEntry 45 }

affirmedSecurityStatisticsDataStatsNewUseableRuleHits OBJECT-TYPE
    SYNTAX      ConfdString
    MAX-ACCESS  read-only
    STATUS      current
    DESCRIPTION "UseableRuleHits"
    ::= { affirmedSecurityStatisticsDataStatsNewEntry 46 }

affirmedSecurityStatisticsDataStatsNewDropPktsRule OBJECT-TYPE
    SYNTAX      ConfdString
    MAX-ACCESS  read-only
    STATUS      current
    DESCRIPTION "Packets dropped via an explicit rule"
    ::= { affirmedSecurityStatisticsDataStatsNewEntry 47 }

affirmedSecurityStatisticsDataStatsNewDropPktsRejectRule OBJECT-TYPE
    SYNTAX      ConfdString
    MAX-ACCESS  read-only
    STATUS      current
    DESCRIPTION "Packets rejected via an explicit rule"
    ::= { affirmedSecurityStatisticsDataStatsNewEntry 48 }

affirmedSecurityStatisticsDataStatsNewPassRuleHits OBJECT-TYPE
    SYNTAX      ConfdString
    MAX-ACCESS  read-only
    STATUS      current
    DESCRIPTION "PassRuleHits"
    ::= { affirmedSecurityStatisticsDataStatsNewEntry 49 }

affirmedSecurityStatisticsDataStatsNewApplyRuleHits OBJECT-TYPE
    SYNTAX      ConfdString
    MAX-ACCESS  read-only
    STATUS      current
    DESCRIPTION "ApplyRuleHits"
    ::= { affirmedSecurityStatisticsDataStatsNewEntry 50 }

affirmedSecurityStatisticsDataStatsNewRxNattKaPkts OBJECT-TYPE
    SYNTAX      ConfdString
    MAX-ACCESS  read-only
    STATUS      current
    DESCRIPTION "RxNattKaPkts"
    ::= { affirmedSecurityStatisticsDataStatsNewEntry 51 }

affirmedSecurityStatisticsDataStatsNewRxEpdgPkts OBJECT-TYPE
    SYNTAX      ConfdString
    MAX-ACCESS  read-only
    STATUS      current
    DESCRIPTION "Packets received for epdg sessions."
    ::= { affirmedSecurityStatisticsDataStatsNewEntry 52 }

affirmedSecurityStatisticsDataStatsNewTxEpdgPkts OBJECT-TYPE
    SYNTAX      ConfdString
    MAX-ACCESS  read-only
    STATUS      current
    DESCRIPTION "Packets transmitted for epdg sessions."
    ::= { affirmedSecurityStatisticsDataStatsNewEntry 53 }

affirmedSecurityStatisticsDataStatsNewRxIkeApplyPolicy OBJECT-TYPE
    SYNTAX      ConfdString
    MAX-ACCESS  read-only
    STATUS      current
    DESCRIPTION "IKE packets passed via configured policy."
    ::= { affirmedSecurityStatisticsDataStatsNewEntry 54 }

affirmedSecurityStatisticsDataStatsNewRxIkeNattApplyPolicy OBJECT-TYPE
    SYNTAX      ConfdString
    MAX-ACCESS  read-only
    STATUS      current
    DESCRIPTION "IKE NAT-T packets passed via configured policy."
    ::= { affirmedSecurityStatisticsDataStatsNewEntry 55 }

affirmedSecurityStatisticsDataStatsNewRxV4DropPkts OBJECT-TYPE
    SYNTAX      ConfdString
    MAX-ACCESS  read-only
    STATUS      current
    DESCRIPTION "Ingress IPv4 packets dropped"
    ::= { affirmedSecurityStatisticsDataStatsNewEntry 56 }

affirmedSecurityStatisticsDataStatsNewRxV4DropBytes OBJECT-TYPE
    SYNTAX      ConfdString
    MAX-ACCESS  read-only
    STATUS      current
    DESCRIPTION "Ingress IPv4 bytes dropped"
    ::= { affirmedSecurityStatisticsDataStatsNewEntry 57 }

affirmedSecurityStatisticsDataStatsNewRxV6DropPkts OBJECT-TYPE
    SYNTAX      ConfdString
    MAX-ACCESS  read-only
    STATUS      current
    DESCRIPTION "Ingress IPv6 packets dropped"
    ::= { affirmedSecurityStatisticsDataStatsNewEntry 58 }

affirmedSecurityStatisticsDataStatsNewRxV6DropBytes OBJECT-TYPE
    SYNTAX      ConfdString
    MAX-ACCESS  read-only
    STATUS      current
    DESCRIPTION "Ingress IPv6 bytes dropped"
    ::= { affirmedSecurityStatisticsDataStatsNewEntry 59 }

affirmedSecurityStatisticsDataStatsNewTxV4DropPkts OBJECT-TYPE
    SYNTAX      ConfdString
    MAX-ACCESS  read-only
    STATUS      current
    DESCRIPTION "Egress IPv4 packets dropped"
    ::= { affirmedSecurityStatisticsDataStatsNewEntry 60 }

affirmedSecurityStatisticsDataStatsNewTxV4DropBytes OBJECT-TYPE
    SYNTAX      ConfdString
    MAX-ACCESS  read-only
    STATUS      current
    DESCRIPTION "Egress IPv4 bytes dropped"
    ::= { affirmedSecurityStatisticsDataStatsNewEntry 61 }

affirmedSecurityStatisticsDataStatsNewTxV6DropPkts OBJECT-TYPE
    SYNTAX      ConfdString
    MAX-ACCESS  read-only
    STATUS      current
    DESCRIPTION "Egress IPv6 packets dropped"
    ::= { affirmedSecurityStatisticsDataStatsNewEntry 62 }

affirmedSecurityStatisticsDataStatsNewTxV6DropBytes OBJECT-TYPE
    SYNTAX      ConfdString
    MAX-ACCESS  read-only
    STATUS      current
    DESCRIPTION "Egress IPv6 bytes dropped"
    ::= { affirmedSecurityStatisticsDataStatsNewEntry 63 }

affirmedSecurityStatisticsDataStatsNewRemoteTransError OBJECT-TYPE
    SYNTAX      ConfdString
    MAX-ACCESS  read-only
    STATUS      current
    DESCRIPTION "Packets sent to wrong SSM"
    ::= { affirmedSecurityStatisticsDataStatsNewEntry 64 }

affirmedSecurityStatisticsDataStatsNewInvalidHeaderError OBJECT-TYPE
    SYNTAX      ConfdString
    MAX-ACCESS  read-only
    STATUS      current
    DESCRIPTION "Packets with bad IP header or length less than IP length"
    ::= { affirmedSecurityStatisticsDataStatsNewEntry 65 }

affirmedSecurityStatisticsDataStatsNewRxPendingFlowError OBJECT-TYPE
    SYNTAX      ConfdString
    MAX-ACCESS  read-only
    STATUS      current
    DESCRIPTION "Ingress Packets dropped because SPM has not validated flow"
    ::= { affirmedSecurityStatisticsDataStatsNewEntry 66 }

affirmedSecurityStatisticsDataStatsNewTxPendingFlowError OBJECT-TYPE
    SYNTAX      ConfdString
    MAX-ACCESS  read-only
    STATUS      current
    DESCRIPTION "Egress Packets dropped because SPM has not validated flow"
    ::= { affirmedSecurityStatisticsDataStatsNewEntry 67 }

affirmedSecurityStatisticsDataStatsNewNoFlowErrorIngress OBJECT-TYPE
    SYNTAX      ConfdString
    MAX-ACCESS  read-only
    STATUS      current
    DESCRIPTION "NoFlowErrorIngress"
    ::= { affirmedSecurityStatisticsDataStatsNewEntry 68 }

affirmedSecurityStatisticsDataStatsNewNoFlowErrorEgress OBJECT-TYPE
    SYNTAX      ConfdString
    MAX-ACCESS  read-only
    STATUS      current
    DESCRIPTION "NoFlowErrorEgress"
    ::= { affirmedSecurityStatisticsDataStatsNewEntry 69 }

affirmedSecurityStatisticsDataStatsNewTransNotFoundError OBJECT-TYPE
    SYNTAX      ConfdString
    MAX-ACCESS  read-only
    STATUS      current
    DESCRIPTION "Packets dropped because transform not in hash"
    ::= { affirmedSecurityStatisticsDataStatsNewEntry 70 }

affirmedSecurityStatisticsDataStatsNewIngCtxtInUse OBJECT-TYPE
    SYNTAX      ConfdString
    MAX-ACCESS  read-only
    STATUS      current
    DESCRIPTION "Ingress packet dropped by hdw crypto because rekeying not done"
    ::= { affirmedSecurityStatisticsDataStatsNewEntry 71 }

affirmedSecurityStatisticsDataStatsNewFailedSanity OBJECT-TYPE
    SYNTAX      ConfdString
    MAX-ACCESS  read-only
    STATUS      current
    DESCRIPTION "Ingress packets dropped by hdw crypto for memory corruption"
    ::= { affirmedSecurityStatisticsDataStatsNewEntry 72 }

affirmedSecurityStatisticsDataStatsNewDropPktsIntfNotFound OBJECT-TYPE
    SYNTAX      ConfdString
    MAX-ACCESS  read-only
    STATUS      current
    DESCRIPTION "Packets dropped when transmit logical interface not found"
    ::= { affirmedSecurityStatisticsDataStatsNewEntry 73 }

affirmedSecurityStatisticsDataStatsNewDropPktsSessionNotFound OBJECT-TYPE
    SYNTAX      ConfdString
    MAX-ACCESS  read-only
    STATUS      current
    DESCRIPTION "WF packets dropped when session not found"
    ::= { affirmedSecurityStatisticsDataStatsNewEntry 74 }

affirmedSecurityStatisticsDataStatsNewDropPktsSecurityDisabled OBJECT-TYPE
    SYNTAX      ConfdString
    MAX-ACCESS  read-only
    STATUS      current
    DESCRIPTION "DropPktsSecurityDisabled"
    ::= { affirmedSecurityStatisticsDataStatsNewEntry 75 }

affirmedSecurityStatisticsDataStatsNewTransactionsDeallocFailed OBJECT-TYPE
    SYNTAX      ConfdString
    MAX-ACCESS  read-only
    STATUS      current
    DESCRIPTION "Transaction deallocoations failures"
    ::= { affirmedSecurityStatisticsDataStatsNewEntry 76 }

affirmedSecurityStatisticsDataStatsNewInvalidNumaNode OBJECT-TYPE
    SYNTAX      ConfdString
    MAX-ACCESS  read-only
    STATUS      current
    DESCRIPTION "Received a non-default numaNode"
    ::= { affirmedSecurityStatisticsDataStatsNewEntry 77 }

affirmedSecurityStatisticsDataStatsNewIngSpiMismatch OBJECT-TYPE
    SYNTAX      ConfdString
    MAX-ACCESS  read-only
    STATUS      current
    DESCRIPTION "Ingress packet's SPI matches neither transform's SPI"
    ::= { affirmedSecurityStatisticsDataStatsNewEntry 78 }

affirmedSecurityStatisticsDataStatsNewEgrSpiMismatch OBJECT-TYPE
    SYNTAX      ConfdString
    MAX-ACCESS  read-only
    STATUS      current
    DESCRIPTION "SPI set up in egress packet matches neither egress SPI"
    ::= { affirmedSecurityStatisticsDataStatsNewEntry 79 }

affirmedSecurityStatisticsDataStatsNewTransAuthErrs OBJECT-TYPE
    SYNTAX      ConfdString
    MAX-ACCESS  read-only
    STATUS      current
    DESCRIPTION "Ingress packet failed pre cipher checks"
    ::= { affirmedSecurityStatisticsDataStatsNewEntry 80 }

affirmedSecurityStatisticsDataStatsNewPostSecTransAuthErrs OBJECT-TYPE
    SYNTAX      ConfdString
    MAX-ACCESS  read-only
    STATUS      current
    DESCRIPTION "Ingress packet failed post cipher checks"
    ::= { affirmedSecurityStatisticsDataStatsNewEntry 81 }

affirmedSecurityStatisticsDataStatsNewPostSecPktErrs OBJECT-TYPE
    SYNTAX      ConfdString
    MAX-ACCESS  read-only
    STATUS      current
    DESCRIPTION "Decrypted packet failed non-cipher checks"
    ::= { affirmedSecurityStatisticsDataStatsNewEntry 82 }

affirmedSecurityStatisticsDataStatsNewPostSecPktErrsInvalidHeader OBJECT-TYPE
    SYNTAX      ConfdString
    MAX-ACCESS  read-only
    STATUS      current
    DESCRIPTION "PostSecPktErrsInvalidHeader"
    ::= { affirmedSecurityStatisticsDataStatsNewEntry 83 }

affirmedSecurityStatisticsDataStatsNewPostSecPktErrsInvalidFragHeader OBJECT-TYPE
    SYNTAX      ConfdString
    MAX-ACCESS  read-only
    STATUS      current
    DESCRIPTION "PostSecPktErrsInvalidFragHeader"
    ::= { affirmedSecurityStatisticsDataStatsNewEntry 84 }

affirmedSecurityStatisticsDataStatsNewPostSecPktErrsNoFlowFound OBJECT-TYPE
    SYNTAX      ConfdString
    MAX-ACCESS  read-only
    STATUS      current
    DESCRIPTION "PostSecPktErrsNoFlowFound"
    ::= { affirmedSecurityStatisticsDataStatsNewEntry 85 }

affirmedSecurityStatisticsDataStatsNewPostSecPktErrsBadFlowFound OBJECT-TYPE
    SYNTAX      ConfdString
    MAX-ACCESS  read-only
    STATUS      current
    DESCRIPTION "PostSecPktErrsBadFlowFound"
    ::= { affirmedSecurityStatisticsDataStatsNewEntry 86 }

affirmedSecurityStatisticsDataStatsNewPostSecPktErrsUnexpectedPendFlow OBJECT-TYPE
    SYNTAX      ConfdString
    MAX-ACCESS  read-only
    STATUS      current
    DESCRIPTION "PostSecPktErrsUnexpectedPendFlow"
    ::= { affirmedSecurityStatisticsDataStatsNewEntry 87 }

affirmedSecurityStatisticsDataStatsNewPostSecPktErrsUnexpectedApplyFlow OBJECT-TYPE
    SYNTAX      ConfdString
    MAX-ACCESS  read-only
    STATUS      current
    DESCRIPTION "PostSecPktErrsUnexpectedApplyFlow"
    ::= { affirmedSecurityStatisticsDataStatsNewEntry 88 }

affirmedSecurityStatisticsDataStatsNewPostSecPktErrsUnexpectedRejectFlow OBJECT-TYPE
    SYNTAX      ConfdString
    MAX-ACCESS  read-only
    STATUS      current
    DESCRIPTION "PostSecPktErrsUnexpectedRejectFlow"
    ::= { affirmedSecurityStatisticsDataStatsNewEntry 89 }

affirmedSecurityStatisticsDataStatsNewPostSecPktErrsUnexpectedTriggerFlow OBJECT-TYPE
    SYNTAX      ConfdString
    MAX-ACCESS  read-only
    STATUS      current
    DESCRIPTION "PostSecPktErrsUnexpectedTriggerFlow"
    ::= { affirmedSecurityStatisticsDataStatsNewEntry 90 }

affirmedSecurityStatisticsDataStatsNewPostSecPktErrsUnexpectedDropFlow OBJECT-TYPE
    SYNTAX      ConfdString
    MAX-ACCESS  read-only
    STATUS      current
    DESCRIPTION "PostSecPktErrsUnexpectedDropFlow"
    ::= { affirmedSecurityStatisticsDataStatsNewEntry 91 }

affirmedSecurityStatisticsDataStatsNewPostSecPktErrsUnexpectedNonExistentFlow OBJECT-TYPE
    SYNTAX      ConfdString
    MAX-ACCESS  read-only
    STATUS      current
    DESCRIPTION "PostSecPktErrsUnexpectedNonExistentFlow"
    ::= { affirmedSecurityStatisticsDataStatsNewEntry 92 }

affirmedSecurityStatisticsDataStatsNewPostSecIntfPktErrs OBJECT-TYPE
    SYNTAX      ConfdString
    MAX-ACCESS  read-only
    STATUS      current
    DESCRIPTION "Remotely originated decrypted packet transmit failures"
    ::= { affirmedSecurityStatisticsDataStatsNewEntry 93 }

affirmedSecurityStatisticsDataStatsNewPostSecFpPktErrs OBJECT-TYPE
    SYNTAX      ConfdString
    MAX-ACCESS  read-only
    STATUS      current
    DESCRIPTION "Locally originated decrypted packet transmit failures"
    ::= { affirmedSecurityStatisticsDataStatsNewEntry 94 }

affirmedSecurityStatisticsDataStatsNewIngCtxtErrs OBJECT-TYPE
    SYNTAX      ConfdString
    MAX-ACCESS  read-only
    STATUS      current
    DESCRIPTION "Ingress packet dropped crypto context errors."
    ::= { affirmedSecurityStatisticsDataStatsNewEntry 95 }

affirmedSecurityStatisticsDataStatsNewEgrCtxtErrs OBJECT-TYPE
    SYNTAX      ConfdString
    MAX-ACCESS  read-only
    STATUS      current
    DESCRIPTION "Egress packet dropped crypto context errors."
    ::= { affirmedSecurityStatisticsDataStatsNewEntry 96 }

affirmedSecurityStatisticsDataStatsNewUnuseableRuleHits OBJECT-TYPE
    SYNTAX      ConfdString
    MAX-ACCESS  read-only
    STATUS      current
    DESCRIPTION "UnuseableRuleHits"
    ::= { affirmedSecurityStatisticsDataStatsNewEntry 97 }

affirmedSecurityStatisticsDataStatsNewInvalidRuleHits OBJECT-TYPE
    SYNTAX      ConfdString
    MAX-ACCESS  read-only
    STATUS      current
    DESCRIPTION "InvalidRuleHits"
    ::= { affirmedSecurityStatisticsDataStatsNewEntry 98 }

affirmedSecurityStatisticsDataStatsNewTriggerRuleHits OBJECT-TYPE
    SYNTAX      ConfdString
    MAX-ACCESS  read-only
    STATUS      current
    DESCRIPTION "Packets that matched a configured trigger rule"
    ::= { affirmedSecurityStatisticsDataStatsNewEntry 99 }

affirmedSecurityStatisticsDataStatsNewDormantApplyRuleHits OBJECT-TYPE
    SYNTAX      ConfdString
    MAX-ACCESS  read-only
    STATUS      current
    DESCRIPTION "DormantApplyRuleHits"
    ::= { affirmedSecurityStatisticsDataStatsNewEntry 100 }

affirmedSecurityStatisticsDataStatsNewUnknownRuleHits OBJECT-TYPE
    SYNTAX      ConfdString
    MAX-ACCESS  read-only
    STATUS      current
    DESCRIPTION "UnknownRuleHits"
    ::= { affirmedSecurityStatisticsDataStatsNewEntry 101 }

affirmedSecurityStatisticsDataStatsNewNoFlowPassAtRemoteSecm OBJECT-TYPE
    SYNTAX      ConfdString
    MAX-ACCESS  read-only
    STATUS      current
    DESCRIPTION "Passes match no flow pass rule, but should not send to spm"
    ::= { affirmedSecurityStatisticsDataStatsNewEntry 102 }

affirmedSecurityStatisticsDataStatsNewPktsDiscarded OBJECT-TYPE
    SYNTAX      ConfdString
    MAX-ACCESS  read-only
    STATUS      current
    DESCRIPTION "PktsDiscarded"
    ::= { affirmedSecurityStatisticsDataStatsNewEntry 103 }

affirmedSecurityStatisticsDataStatsNewNoFlowPassDrop OBJECT-TYPE
    SYNTAX      ConfdString
    MAX-ACCESS  read-only
    STATUS      current
    DESCRIPTION "NoFlowPassDrop"
    ::= { affirmedSecurityStatisticsDataStatsNewEntry 104 }

affirmedSecurityStatisticsDataStatsNewNoFlowTid0IngressIPsec OBJECT-TYPE
    SYNTAX      ConfdString
    MAX-ACCESS  read-only
    STATUS      current
    DESCRIPTION "NoFlowTid0IngressIPsec"
    ::= { affirmedSecurityStatisticsDataStatsNewEntry 105 }

affirmedSecurityStatisticsDataStatsNewNoFlowTidV6IcmpErr OBJECT-TYPE
    SYNTAX      ConfdString
    MAX-ACCESS  read-only
    STATUS      current
    DESCRIPTION "NoFlowTidV6IcmpErr"
    ::= { affirmedSecurityStatisticsDataStatsNewEntry 106 }

affirmedSecurityStatisticsDataStatsNewNoFlowTidV4IcmpErr OBJECT-TYPE
    SYNTAX      ConfdString
    MAX-ACCESS  read-only
    STATUS      current
    DESCRIPTION "NoFlowTidV4IcmpErr"
    ::= { affirmedSecurityStatisticsDataStatsNewEntry 107 }

affirmedSecurityStatisticsDataStatsNewDropPktsTooBig OBJECT-TYPE
    SYNTAX      ConfdString
    MAX-ACCESS  read-only
    STATUS      current
    DESCRIPTION "Packets too big for hardware crypto"
    ::= { affirmedSecurityStatisticsDataStatsNewEntry 108 }

affirmedSecurityStatisticsDataStatsNewDropPktsNoRule OBJECT-TYPE
    SYNTAX      ConfdString
    MAX-ACCESS  read-only
    STATUS      current
    DESCRIPTION "Packets dropped due to no or bad rule"
    ::= { affirmedSecurityStatisticsDataStatsNewEntry 109 }

affirmedSecurityStatisticsDataStatsNewDropPktsTriggerRule OBJECT-TYPE
    SYNTAX      ConfdString
    MAX-ACCESS  read-only
    STATUS      current
    DESCRIPTION "Packets rejected via a trigger explicit rule"
    ::= { affirmedSecurityStatisticsDataStatsNewEntry 110 }

affirmedSecurityStatisticsDataStatsNewDequeuePendingError OBJECT-TYPE
    SYNTAX      ConfdString
    MAX-ACCESS  read-only
    STATUS      current
    DESCRIPTION "Error dequeing a pending packet"
    ::= { affirmedSecurityStatisticsDataStatsNewEntry 111 }

affirmedSecurityStatisticsDataStatsNewNullSpiEntry OBJECT-TYPE
    SYNTAX      ConfdString
    MAX-ACCESS  read-only
    STATUS      current
    DESCRIPTION "NullSpiEntry"
    ::= { affirmedSecurityStatisticsDataStatsNewEntry 112 }

affirmedSecurityStatisticsDataStatsNewInvalidFSAPI OBJECT-TYPE
    SYNTAX      ConfdString
    MAX-ACCESS  read-only
    STATUS      current
    DESCRIPTION "InvalidFSAPI"
    ::= { affirmedSecurityStatisticsDataStatsNewEntry 113 }

affirmedSecurityStatisticsDataStatsNewSpiEntryFailLookup OBJECT-TYPE
    SYNTAX      ConfdString
    MAX-ACCESS  read-only
    STATUS      current
    DESCRIPTION "SpiEntryFailLookup"
    ::= { affirmedSecurityStatisticsDataStatsNewEntry 114 }

affirmedSecurityStatisticsDataStatsNewSpiTransformEntryFailLookup OBJECT-TYPE
    SYNTAX      ConfdString
    MAX-ACCESS  read-only
    STATUS      current
    DESCRIPTION "SpiTransformEntryFailLookup"
    ::= { affirmedSecurityStatisticsDataStatsNewEntry 115 }

affirmedSecurityStatisticsDataStatsNewTriggerRuleIngressPkts OBJECT-TYPE
    SYNTAX      ConfdString
    MAX-ACCESS  read-only
    STATUS      current
    DESCRIPTION "Ingress packets dropped due to match with trigger rule."
    ::= { affirmedSecurityStatisticsDataStatsNewEntry 116 }

affirmedSecurityStatisticsDataStatsNewRejectRuleHits OBJECT-TYPE
    SYNTAX      ConfdString
    MAX-ACCESS  read-only
    STATUS      current
    DESCRIPTION "RejectRuleHits"
    ::= { affirmedSecurityStatisticsDataStatsNewEntry 117 }

affirmedSecurityStatisticsDataStatsNewFlushedPkts OBJECT-TYPE
    SYNTAX      ConfdString
    MAX-ACCESS  read-only
    STATUS      current
    DESCRIPTION "Packets flushed after waiting 30 sec for SPM to validate flow"
    ::= { affirmedSecurityStatisticsDataStatsNewEntry 118 }

affirmedSecurityStatisticsDataStatsNewQueuedPktNotApply OBJECT-TYPE
    SYNTAX      ConfdString
    MAX-ACCESS  read-only
    STATUS      current
    DESCRIPTION "Queued packet dropped after not matching apply rule."
    ::= { affirmedSecurityStatisticsDataStatsNewEntry 119 }

affirmedSecurityStatisticsDataStatsNewEspSpiMismatchError OBJECT-TYPE
    SYNTAX      ConfdString
    MAX-ACCESS  read-only
    STATUS      current
    DESCRIPTION "Newly received ESP packet matches neither SPI"
    ::= { affirmedSecurityStatisticsDataStatsNewEntry 120 }

affirmedSecurityStatisticsDataStatsNewCipherNotFoundError OBJECT-TYPE
    SYNTAX      ConfdString
    MAX-ACCESS  read-only
    STATUS      current
    DESCRIPTION "Transform setup fail because cipher algorithm not found"
    ::= { affirmedSecurityStatisticsDataStatsNewEntry 121 }

affirmedSecurityStatisticsDataStatsNewPktDataAccessError OBJECT-TYPE
    SYNTAX      ConfdString
    MAX-ACCESS  read-only
    STATUS      current
    DESCRIPTION "Mismatches between packet and expected prefix lengths"
    ::= { affirmedSecurityStatisticsDataStatsNewEntry 122 }

affirmedSecurityStatisticsDataStatsNewPktSizeCipherSizeError OBJECT-TYPE
    SYNTAX      ConfdString
    MAX-ACCESS  read-only
    STATUS      current
    DESCRIPTION "Encrypted packet size not a multiple of cipher block size"
    ::= { affirmedSecurityStatisticsDataStatsNewEntry 123 }

affirmedSecurityStatisticsDataStatsNewPktTooShortError OBJECT-TYPE
    SYNTAX      ConfdString
    MAX-ACCESS  read-only
    STATUS      current
    DESCRIPTION "Encrypted packet size less than necessary prefix and trailer sizes"
    ::= { affirmedSecurityStatisticsDataStatsNewEntry 124 }

affirmedSecurityStatisticsDataStatsNewPktLenMismatchError OBJECT-TYPE
    SYNTAX      ConfdString
    MAX-ACCESS  read-only
    STATUS      current
    DESCRIPTION "Internal mismatch between calculated and actual lengths"
    ::= { affirmedSecurityStatisticsDataStatsNewEntry 125 }

affirmedSecurityStatisticsDataStatsNewParsePktHeaderError OBJECT-TYPE
    SYNTAX      ConfdString
    MAX-ACCESS  read-only
    STATUS      current
    DESCRIPTION "All errors parsing encrypted packet headers"
    ::= { affirmedSecurityStatisticsDataStatsNewEntry 126 }

affirmedSecurityStatisticsDataStatsNewCalcPktInfoError OBJECT-TYPE
    SYNTAX      ConfdString
    MAX-ACCESS  read-only
    STATUS      current
    DESCRIPTION "All errors in ingress packet lengths"
    ::= { affirmedSecurityStatisticsDataStatsNewEntry 127 }

affirmedSecurityStatisticsDataStatsNewPrelimAntiReplayErrLo OBJECT-TYPE
    SYNTAX      ConfdString
    MAX-ACCESS  read-only
    STATUS      current
    DESCRIPTION "Ingress packet sequence number too low, before decryption"
    ::= { affirmedSecurityStatisticsDataStatsNewEntry 128 }

affirmedSecurityStatisticsDataStatsNewPrelimAntiReplayError OBJECT-TYPE
    SYNTAX      ConfdString
    MAX-ACCESS  read-only
    STATUS      current
    DESCRIPTION "Ingress packet sequence number error, but not too low, before decryption"
    ::= { affirmedSecurityStatisticsDataStatsNewEntry 129 }

affirmedSecurityStatisticsDataStatsNewEspSeqNumError OBJECT-TYPE
    SYNTAX      ConfdString
    MAX-ACCESS  read-only
    STATUS      current
    DESCRIPTION "All ESP packet sequence number errors, after decryption"
    ::= { affirmedSecurityStatisticsDataStatsNewEntry 130 }

affirmedSecurityStatisticsDataStatsNewEspSeqSecm OBJECT-TYPE
    SYNTAX      ConfdString
    MAX-ACCESS  read-only
    STATUS      current
    DESCRIPTION "secm-secm ESP packet sequence number errors, after decryption"
    ::= { affirmedSecurityStatisticsDataStatsNewEntry 131 }

affirmedSecurityStatisticsDataStatsNewEspSeqNumLow OBJECT-TYPE
    SYNTAX      ConfdString
    MAX-ACCESS  read-only
    STATUS      current
    DESCRIPTION "ESP packet sequence number too low, after decryption"
    ::= { affirmedSecurityStatisticsDataStatsNewEntry 132 }

affirmedSecurityStatisticsDataStatsNewAppendSeqHighError OBJECT-TYPE
    SYNTAX      ConfdString
    MAX-ACCESS  read-only
    STATUS      current
    DESCRIPTION "Errors appending high half of sequence number to encrypted packets"
    ::= { affirmedSecurityStatisticsDataStatsNewEntry 133 }

affirmedSecurityStatisticsDataStatsNewDeleteSeqHighError OBJECT-TYPE
    SYNTAX      ConfdString
    MAX-ACCESS  read-only
    STATUS      current
    DESCRIPTION "Errors in deleting high half sequence number after calculating ICV"
    ::= { affirmedSecurityStatisticsDataStatsNewEntry 134 }

affirmedSecurityStatisticsDataStatsNewIcvComputeError OBJECT-TYPE
    SYNTAX      ConfdString
    MAX-ACCESS  read-only
    STATUS      current
    DESCRIPTION "(hw only ) All authentication failures"
    ::= { affirmedSecurityStatisticsDataStatsNewEntry 135 }

affirmedSecurityStatisticsDataStatsNewIcvCheckError OBJECT-TYPE
    SYNTAX      ConfdString
    MAX-ACCESS  read-only
    STATUS      current
    DESCRIPTION "(sw only) post cipher authentication failures"
    ::= { affirmedSecurityStatisticsDataStatsNewEntry 136 }

affirmedSecurityStatisticsDataStatsNewIcvLenError OBJECT-TYPE
    SYNTAX      ConfdString
    MAX-ACCESS  read-only
    STATUS      current
    DESCRIPTION "(sw only) ingress packet ICV Length Errors"
    ::= { affirmedSecurityStatisticsDataStatsNewEntry 137 }

affirmedSecurityStatisticsDataStatsNewEspIcvAuthError OBJECT-TYPE
    SYNTAX      ConfdString
    MAX-ACCESS  read-only
    STATUS      current
    DESCRIPTION "(sw only) pre-cipher authentication failures"
    ::= { affirmedSecurityStatisticsDataStatsNewEntry 138 }

affirmedSecurityStatisticsDataStatsNewEspPadError OBJECT-TYPE
    SYNTAX      ConfdString
    MAX-ACCESS  read-only
    STATUS      current
    DESCRIPTION "error in pad field values"
    ::= { affirmedSecurityStatisticsDataStatsNewEntry 139 }

affirmedSecurityStatisticsDataStatsNewEspTransChainError OBJECT-TYPE
    SYNTAX      ConfdString
    MAX-ACCESS  read-only
    STATUS      current
    DESCRIPTION "(sw only) transform errors"
    ::= { affirmedSecurityStatisticsDataStatsNewEntry 140 }

affirmedSecurityStatisticsDataStatsNewEspProcessAadError OBJECT-TYPE
    SYNTAX      ConfdString
    MAX-ACCESS  read-only
    STATUS      current
    DESCRIPTION "(sw only) transform aad errors"
    ::= { affirmedSecurityStatisticsDataStatsNewEntry 141 }

affirmedSecurityStatisticsDataStatsNewTransFinishError OBJECT-TYPE
    SYNTAX      ConfdString
    MAX-ACCESS  read-only
    STATUS      current
    DESCRIPTION "post decryption errors"
    ::= { affirmedSecurityStatisticsDataStatsNewEntry 142 }

affirmedSecurityStatisticsDataStatsNewAuthAddRangeError OBJECT-TYPE
    SYNTAX      ConfdString
    MAX-ACCESS  read-only
    STATUS      current
    DESCRIPTION "Ingress segment errors"
    ::= { affirmedSecurityStatisticsDataStatsNewEntry 143 }

affirmedSecurityStatisticsDataStatsNewAuthFinishError OBJECT-TYPE
    SYNTAX      ConfdString
    MAX-ACCESS  read-only
    STATUS      current
    DESCRIPTION "Errors in finishing authentication"
    ::= { affirmedSecurityStatisticsDataStatsNewEntry 144 }

affirmedSecurityStatisticsDataStatsNewCipherUpdateError OBJECT-TYPE
    SYNTAX      ConfdString
    MAX-ACCESS  read-only
    STATUS      current
    DESCRIPTION "Errors updating cipher"
    ::= { affirmedSecurityStatisticsDataStatsNewEntry 145 }

affirmedSecurityStatisticsDataStatsNewEspSeqNumOverflowError OBJECT-TYPE
    SYNTAX      ConfdString
    MAX-ACCESS  read-only
    STATUS      current
    DESCRIPTION "egress ESP sequence number overflow"
    ::= { affirmedSecurityStatisticsDataStatsNewEntry 146 }

affirmedSecurityStatisticsDataStatsNewIngCryptoAllocFail OBJECT-TYPE
    SYNTAX      ConfdString
    MAX-ACCESS  read-only
    STATUS      current
    DESCRIPTION "Ingress context allocation failure"
    ::= { affirmedSecurityStatisticsDataStatsNewEntry 147 }

affirmedSecurityStatisticsDataStatsNewEgrCryptoAllocFail OBJECT-TYPE
    SYNTAX      ConfdString
    MAX-ACCESS  read-only
    STATUS      current
    DESCRIPTION "Egress context allocation failure"
    ::= { affirmedSecurityStatisticsDataStatsNewEntry 148 }

affirmedSecurityStatisticsDataStatsNewIngCryptoResetFail OBJECT-TYPE
    SYNTAX      ConfdString
    MAX-ACCESS  read-only
    STATUS      current
    DESCRIPTION "Ingress context reset failure"
    ::= { affirmedSecurityStatisticsDataStatsNewEntry 149 }

affirmedSecurityStatisticsDataStatsNewEgrCryptoResetFail OBJECT-TYPE
    SYNTAX      ConfdString
    MAX-ACCESS  read-only
    STATUS      current
    DESCRIPTION "Egress context reset failure"
    ::= { affirmedSecurityStatisticsDataStatsNewEntry 150 }

affirmedSecurityStatisticsDataStatsNewGetNextHopFail OBJECT-TYPE
    SYNTAX      ConfdString
    MAX-ACCESS  read-only
    STATUS      current
    DESCRIPTION "Egress packet cannot find next hop"
    ::= { affirmedSecurityStatisticsDataStatsNewEntry 151 }

affirmedSecurityStatisticsDataStatsNewNoCryptoCapability OBJECT-TYPE
    SYNTAX      ConfdString
    MAX-ACCESS  read-only
    STATUS      current
    DESCRIPTION "NoCryptoCapability"
    ::= { affirmedSecurityStatisticsDataStatsNewEntry 152 }

affirmedSecurityStatisticsDataStatsNewSecmSessionIcmpFragNeededMsgSent OBJECT-TYPE
    SYNTAX      ConfdString
    MAX-ACCESS  read-only
    STATUS      current
    DESCRIPTION "SecmSessionIcmpFragNeededMsgSent"
    ::= { affirmedSecurityStatisticsDataStatsNewEntry 153 }

affirmedSecurityStatisticsDataStatsNewSecmIcmpFragNeededMsgSent OBJECT-TYPE
    SYNTAX      ConfdString
    MAX-ACCESS  read-only
    STATUS      current
    DESCRIPTION "SecmIcmpFragNeededMsgSent"
    ::= { affirmedSecurityStatisticsDataStatsNewEntry 154 }

affirmedSecurityStatisticsDataStatsNewSecmSessionIcmpV6PacketTooBigMsgSent OBJECT-TYPE
    SYNTAX      ConfdString
    MAX-ACCESS  read-only
    STATUS      current
    DESCRIPTION "SecmSessionIcmpV6PacketTooBigMsgSent"
    ::= { affirmedSecurityStatisticsDataStatsNewEntry 155 }

affirmedSecurityStatisticsDataStatsNewSecmIcmpV6PacketTooBigMsgSent OBJECT-TYPE
    SYNTAX      ConfdString
    MAX-ACCESS  read-only
    STATUS      current
    DESCRIPTION "SecmIcmpV6PacketTooBigMsgSent"
    ::= { affirmedSecurityStatisticsDataStatsNewEntry 156 }

affirmedSecurityStatisticsDataStatsNewSecmIPv6MaxFragAfterEncryptionTooBig OBJECT-TYPE
    SYNTAX      ConfdString
    MAX-ACCESS  read-only
    STATUS      current
    DESCRIPTION "SecmIPv6MaxFragAfterEncryptionTooBig"
    ::= { affirmedSecurityStatisticsDataStatsNewEntry 157 }

affirmedSecurityStatisticsDataStatsNewSecmIPv6MaxFragTooBig OBJECT-TYPE
    SYNTAX      ConfdString
    MAX-ACCESS  read-only
    STATUS      current
    DESCRIPTION "SecmIPv6MaxFragTooBig"
    ::= { affirmedSecurityStatisticsDataStatsNewEntry 158 }

affirmedSecurityStatisticsDataStatsNewSecmIPv6PktTooBigPreFragEnabled OBJECT-TYPE
    SYNTAX      ConfdString
    MAX-ACCESS  read-only
    STATUS      current
    DESCRIPTION "SecmIPv6PktTooBigPreFragEnabled"
    ::= { affirmedSecurityStatisticsDataStatsNewEntry 159 }

affirmedSecurityStatisticsDataStatsNewSecmIPv6FragSuccess OBJECT-TYPE
    SYNTAX      ConfdString
    MAX-ACCESS  read-only
    STATUS      current
    DESCRIPTION "SecmIPv6FragSuccess"
    ::= { affirmedSecurityStatisticsDataStatsNewEntry 160 }

affirmedSecurityStatisticsDataStatsNewSecmIPv4FragSuccess OBJECT-TYPE
    SYNTAX      ConfdString
    MAX-ACCESS  read-only
    STATUS      current
    DESCRIPTION "SecmIPv4FragSuccess"
    ::= { affirmedSecurityStatisticsDataStatsNewEntry 161 }

affirmedSecurityStatisticsDataStatsNewSecmIPv6FragFailed OBJECT-TYPE
    SYNTAX      ConfdString
    MAX-ACCESS  read-only
    STATUS      current
    DESCRIPTION "SecmIPv6FragFailed"
    ::= { affirmedSecurityStatisticsDataStatsNewEntry 162 }

affirmedSecurityStatisticsDataStatsNewSecmIPv4FragFailed OBJECT-TYPE
    SYNTAX      ConfdString
    MAX-ACCESS  read-only
    STATUS      current
    DESCRIPTION "SecmIPv4FragFailed"
    ::= { affirmedSecurityStatisticsDataStatsNewEntry 163 }

affirmedSecurityStatisticsDataStatsNewSecmFragStatusFailed OBJECT-TYPE
    SYNTAX      ConfdString
    MAX-ACCESS  read-only
    STATUS      current
    DESCRIPTION "SecmFragStatusFailed"
    ::= { affirmedSecurityStatisticsDataStatsNewEntry 164 }

affirmedSecurityStatisticsDataStatsNewSecmNumFrlDropIngressCnts OBJECT-TYPE
    SYNTAX      ConfdString
    MAX-ACCESS  read-only
    STATUS      current
    DESCRIPTION "Number of Ingress Flow drops due to flow rate limit"
    ::= { affirmedSecurityStatisticsDataStatsNewEntry 165 }

affirmedSecurityStatisticsDataStatsNewSecmNumPrlDropIngressCnts OBJECT-TYPE
    SYNTAX      ConfdString
    MAX-ACCESS  read-only
    STATUS      current
    DESCRIPTION "Number of Ingress Packets dropped due to packet rate limit"
    ::= { affirmedSecurityStatisticsDataStatsNewEntry 166 }

affirmedSecurityStatisticsDataStatsNewSecmNumFrlDropEgressCnts OBJECT-TYPE
    SYNTAX      ConfdString
    MAX-ACCESS  read-only
    STATUS      current
    DESCRIPTION "Number of Egress Flow drops due to flow rate limit"
    ::= { affirmedSecurityStatisticsDataStatsNewEntry 167 }

affirmedSecurityStatisticsDataStatsNewSecmNumPrlDropEgressCnts OBJECT-TYPE
    SYNTAX      ConfdString
    MAX-ACCESS  read-only
    STATUS      current
    DESCRIPTION "Number of Egress Packets dropped due to packet rate limit"
    ::= { affirmedSecurityStatisticsDataStatsNewEntry 168 }

affirmedSecurityStatisticsSecAgentStatsTable OBJECT-TYPE
    SYNTAX      SEQUENCE OF AffirmedSecurityStatisticsSecAgentStatsEntry
    MAX-ACCESS  not-accessible
    STATUS      current
    DESCRIPTION ""
    ::= { affirmedSecurityStatistics 11 }

affirmedSecurityStatisticsSecAgentStatsEntry OBJECT-TYPE
    SYNTAX      AffirmedSecurityStatisticsSecAgentStatsEntry
    MAX-ACCESS  not-accessible
    STATUS      current
    DESCRIPTION ""
    INDEX { affirmedSecurityStatisticsSecAgentStatsDummyIndex }
        ::= { affirmedSecurityStatisticsSecAgentStatsTable 1 }

AffirmedSecurityStatisticsSecAgentStatsEntry ::=
    SEQUENCE {
        affirmedSecurityStatisticsSecAgentStatsDummyIndex Unsigned32,
        affirmedSecurityStatisticsSecAgentStatsCryptoLibraryInitialized INTEGER,
        affirmedSecurityStatisticsSecAgentStatsNumNcSpmEntriesCreated ConfdString,
        affirmedSecurityStatisticsSecAgentStatsNumNcSpmEntriesModified ConfdString,
        affirmedSecurityStatisticsSecAgentStatsNumNcSpmEntriesDeleted ConfdString,
        affirmedSecurityStatisticsSecAgentStatsNumFullTransformsCreated ConfdString,
        affirmedSecurityStatisticsSecAgentStatsNumEpdgTransformsCreated ConfdString,
        affirmedSecurityStatisticsSecAgentStatsNumMiniTransformsCreated ConfdString,
        affirmedSecurityStatisticsSecAgentStatsNumTransformsRekeyed ConfdString,
        affirmedSecurityStatisticsSecAgentStatsNumTransformsModified ConfdString,
        affirmedSecurityStatisticsSecAgentStatsNumTransformsChngToFullFail ConfdString,
        affirmedSecurityStatisticsSecAgentStatsNumTransformsChngToEpdgFail ConfdString,
        affirmedSecurityStatisticsSecAgentStatsNumTransformsChngToMiniFail ConfdString,
        affirmedSecurityStatisticsSecAgentStatsNumFullTransformsDeleted ConfdString,
        affirmedSecurityStatisticsSecAgentStatsNumEpdgTransformsDeleted ConfdString,
        affirmedSecurityStatisticsSecAgentStatsNumMiniTransformsDeleted ConfdString,
        affirmedSecurityStatisticsSecAgentStatsNumTransformUpdates ConfdString,
        affirmedSecurityStatisticsSecAgentStatsNumTransformsFPDeletedStale ConfdString,
        affirmedSecurityStatisticsSecAgentStatsNumFlowsCreateAttempts ConfdString,
        affirmedSecurityStatisticsSecAgentStatsNumFlowsCreated ConfdString,
        affirmedSecurityStatisticsSecAgentStatsNumFlowsModifyAttempts ConfdString,
        affirmedSecurityStatisticsSecAgentStatsNumFlowsModified ConfdString,
        affirmedSecurityStatisticsSecAgentStatsNumFlowsDeleteAttempts ConfdString,
        affirmedSecurityStatisticsSecAgentStatsNumFlowsDeleted ConfdString,
        affirmedSecurityStatisticsSecAgentStatsNumFlowsFPDeleted ConfdString,
        affirmedSecurityStatisticsSecAgentStatsNumFlowsFPDeletedStale ConfdString,
        affirmedSecurityStatisticsSecAgentStatsNumFlowsFPCreateRace ConfdString,
        affirmedSecurityStatisticsSecAgentStatsNumTransactionsCreated ConfdString,
        affirmedSecurityStatisticsSecAgentStatsNumTransactionsDeleted ConfdString,
        affirmedSecurityStatisticsSecAgentStatsNumFlowCfmsReported ConfdString,
        affirmedSecurityStatisticsSecAgentStatsNumTransformCfmsReported ConfdString,
        affirmedSecurityStatisticsSecAgentStatsNumRsaRequests ConfdString,
        affirmedSecurityStatisticsSecAgentStatsNumRsaRequestsCalcResultOK ConfdString,
        affirmedSecurityStatisticsSecAgentStatsNumLocalTransforms ConfdString,
        affirmedSecurityStatisticsSecAgentStatsNumSpmFlowsAllocated ConfdString,
        affirmedSecurityStatisticsSecAgentStatsNumSpmFlowsDeallocated ConfdString,
        affirmedSecurityStatisticsSecAgentStatsNumPendingFlowsAllocated ConfdString,
        affirmedSecurityStatisticsSecAgentStatsNumPendingFlowsDeallocated ConfdString,
        affirmedSecurityStatisticsSecAgentStatsNumSpmPublishForPendingFlow ConfdString,
        affirmedSecurityStatisticsSecAgentStatsNumCreateFlowsWithoutSpmForward ConfdString,
        affirmedSecurityStatisticsSecAgentStatsNumIdleFlowsReported ConfdString,
        affirmedSecurityStatisticsSecAgentStatsNumFlowsCleanedup ConfdString,
        affirmedSecurityStatisticsSecAgentStatsNumFlowSetSpis ConfdString,
        affirmedSecurityStatisticsSecAgentStatsNumSpiEntryCreated ConfdString,
        affirmedSecurityStatisticsSecAgentStatsNumSessionEntryCreated ConfdString,
        affirmedSecurityStatisticsSecAgentStatsNumSessionEntryDeleted ConfdString,
        affirmedSecurityStatisticsSecAgentStatsNumSpiTransformEntryCreated ConfdString,
        affirmedSecurityStatisticsSecAgentStatsNumSpiTransformEntryDeleted ConfdString,
        affirmedSecurityStatisticsSecAgentStatsNumSkinnyFlowAllocated ConfdString,
        affirmedSecurityStatisticsSecAgentStatsNumSkinnyFlowDeallocated ConfdString,
        affirmedSecurityStatisticsSecAgentStatsNumSkinnyFlowCreateAttempts ConfdString,
        affirmedSecurityStatisticsSecAgentStatsNumSkinnyFlowCreated ConfdString,
        affirmedSecurityStatisticsSecAgentStatsNumSpdNcAddAttemptCount ConfdString,
        affirmedSecurityStatisticsSecAgentStatsNumSpdNcAddSuccessCount ConfdString,
        affirmedSecurityStatisticsSecAgentStatsNumSpdNcDelAttemptCount ConfdString,
        affirmedSecurityStatisticsSecAgentStatsNumSpdNcDelSuccessCount ConfdString,
        affirmedSecurityStatisticsSecAgentStatsNumSpdRuleAddAttemptCount ConfdString,
        affirmedSecurityStatisticsSecAgentStatsNumSpdRuleAddSuccessCount ConfdString,
        affirmedSecurityStatisticsSecAgentStatsNumSpdRuleModAttemptCount ConfdString,
        affirmedSecurityStatisticsSecAgentStatsNumSpdRuleModSuccessCount ConfdString,
        affirmedSecurityStatisticsSecAgentStatsNumSpdRuleDelAttemptCount ConfdString,
        affirmedSecurityStatisticsSecAgentStatsNumSpdRuleDelSuccessCount ConfdString,
        affirmedSecurityStatisticsSecAgentStatsNumFpFlowsAllocated ConfdString,
        affirmedSecurityStatisticsSecAgentStatsNumFpFlowsDeallocated ConfdString,
        affirmedSecurityStatisticsSecAgentStatsNumFpFlowCreateAttempts ConfdString,
        affirmedSecurityStatisticsSecAgentStatsNumFpFlowsCreated ConfdString,
        affirmedSecurityStatisticsSecAgentStatsNumFpFlowsModifyAttempts ConfdString,
        affirmedSecurityStatisticsSecAgentStatsNumFpFlowsModified ConfdString,
        affirmedSecurityStatisticsSecAgentStatsNumFpFlowsDeleteAttempts ConfdString,
        affirmedSecurityStatisticsSecAgentStatsNumFpFlowsDeleted ConfdString,
        affirmedSecurityStatisticsSecAgentStatsNumSpdAddRuleCtr ConfdString,
        affirmedSecurityStatisticsSecAgentStatsNumSpdDelRuleCtr ConfdString,
        affirmedSecurityStatisticsSecAgentStatsNumSkinnyFlowsIgnoreIom ConfdString,
        affirmedSecurityStatisticsSecAgentStatsNumFlowsDeleteFail ConfdString,
        affirmedSecurityStatisticsSecAgentStatsNumTransformsAddIgnore ConfdString,
        affirmedSecurityStatisticsSecAgentStatsNumTransformsModifyIgnore ConfdString,
        affirmedSecurityStatisticsSecAgentStatsNumTransformsDeleteIgnore ConfdString,
        affirmedSecurityStatisticsSecAgentStatsNumTransformsNotFound ConfdString,
        affirmedSecurityStatisticsSecAgentStatsNumRekeyModify ConfdString,
        affirmedSecurityStatisticsSecAgentStatsNumNoRekeyModify ConfdString,
        affirmedSecurityStatisticsSecAgentStatsNumNewOuterFlowFound ConfdString,
        affirmedSecurityStatisticsSecAgentStatsNumNewOuterFlowFoundInMaint ConfdString,
        affirmedSecurityStatisticsSecAgentStatsNumOuterFlowChange ConfdString,
        affirmedSecurityStatisticsSecAgentStatsNumIngressFlowsCreateDuplicate ConfdString,
        affirmedSecurityStatisticsSecAgentStatsNumSpmFlowsDuplicatedSpmFlows ConfdString,
        affirmedSecurityStatisticsSecAgentStatsNumFlowSpiChangeLate ConfdString,
        affirmedSecurityStatisticsSecAgentStatsNumFpFlowsFailHashTablesAdd ConfdString,
        affirmedSecurityStatisticsSecAgentStatsNumFpFlowsEgressMovedToHash ConfdString,
        affirmedSecurityStatisticsSecAgentStatsNumSpdNcAddFailCountDuplicate ConfdString,
        affirmedSecurityStatisticsSecAgentStatsNumSpiTransEntryTransformChange ConfdString,
        affirmedSecurityStatisticsSecAgentStatsNumSpiTransDeleteIndexMismatch ConfdString,
        affirmedSecurityStatisticsSecAgentStatsNumSessionEntryCreateFailDuplicate ConfdString,
        affirmedSecurityStatisticsSecAgentStatsNumCannotDecideIfAnchor ConfdString,
        affirmedSecurityStatisticsSecAgentStatsNumNcSpmEntriesError ConfdString,
        affirmedSecurityStatisticsSecAgentStatsNumTransformsCreateFailNoResources ConfdString,
        affirmedSecurityStatisticsSecAgentStatsNumTransformsCreateFailDuplicate ConfdString,
        affirmedSecurityStatisticsSecAgentStatsNumTransformsRekeyFail ConfdString,
        affirmedSecurityStatisticsSecAgentStatsNumFlowsCreateFail ConfdString,
        affirmedSecurityStatisticsSecAgentStatsNumFlowsCreateFailDuplicate ConfdString,
        affirmedSecurityStatisticsSecAgentStatsNumFlowsCreateFailNoResources ConfdString,
        affirmedSecurityStatisticsSecAgentStatsNumFlowsModifyFail ConfdString,
        affirmedSecurityStatisticsSecAgentStatsNumFlowsDoubleFree ConfdString,
        affirmedSecurityStatisticsSecAgentStatsNumFlowsNotFound ConfdString,
        affirmedSecurityStatisticsSecAgentStatsNumPktOnNewTunnel ConfdString,
        affirmedSecurityStatisticsSecAgentStatsNumEgressFlowsCreateDuplicate ConfdString,
        affirmedSecurityStatisticsSecAgentStatsNumFlowsFPCreateRaceError ConfdString,
        affirmedSecurityStatisticsSecAgentStatsNumTransactionsFailNoResources ConfdString,
        affirmedSecurityStatisticsSecAgentStatsNumRsaRequestsParamLenError ConfdString,
        affirmedSecurityStatisticsSecAgentStatsNumFlowDeleteDueToNewAdd ConfdString,
        affirmedSecurityStatisticsSecAgentStatsNumActiveFlowAddToHashFail ConfdString,
        affirmedSecurityStatisticsSecAgentStatsNumPendingFlowsFailNoResources ConfdString,
        affirmedSecurityStatisticsSecAgentStatsNumSpmFlowsFailNoResources ConfdString,
        affirmedSecurityStatisticsSecAgentStatsNumFlowAccessTimeFix ConfdString,
        affirmedSecurityStatisticsSecAgentStatsNumPendingFlowAccessTimeFix ConfdString,
        affirmedSecurityStatisticsSecAgentStatsNumRsaRequestsCalcResultError ConfdString,
        affirmedSecurityStatisticsSecAgentStatsNumIngFlowUpdateNoFlow ConfdString,
        affirmedSecurityStatisticsSecAgentStatsNumEgrFlowUpdateNoFlow ConfdString,
        affirmedSecurityStatisticsSecAgentStatsNumIngFlowUpdateError ConfdString,
        affirmedSecurityStatisticsSecAgentStatsNumEgrFlowUpdateError ConfdString,
        affirmedSecurityStatisticsSecAgentStatsNumFlowSetSpisError ConfdString,
        affirmedSecurityStatisticsSecAgentStatsNumTransformsInitError ConfdString,
        affirmedSecurityStatisticsSecAgentStatsNumSpiEntryCreateFailNoResource ConfdString,
        affirmedSecurityStatisticsSecAgentStatsNumSpiEntryCreateFailDuplicate ConfdString,
        affirmedSecurityStatisticsSecAgentStatsNumSpiEntryCreateFailOldSpiNotFound ConfdString,
        affirmedSecurityStatisticsSecAgentStatsNumSpiEntryFailureNoRemoteIp ConfdString,
        affirmedSecurityStatisticsSecAgentStatsNumSpiEntryNewAlreadyExists ConfdString,
        affirmedSecurityStatisticsSecAgentStatsNumSpiEntryFailureInvalidSpi ConfdString,
        affirmedSecurityStatisticsSecAgentStatsNumSessionEntryCreateFailNoResource ConfdString,
        affirmedSecurityStatisticsSecAgentStatsNumSessionEntryFailLookup ConfdString,
        affirmedSecurityStatisticsSecAgentStatsNumSessionEntryDeleteNotFound ConfdString,
        affirmedSecurityStatisticsSecAgentStatsNumErrorDuplicateIngressEgress ConfdString,
        affirmedSecurityStatisticsSecAgentStatsNumDrainQueueError ConfdString,
        affirmedSecurityStatisticsSecAgentStatsNumFlowMaintenanceListError ConfdString,
        affirmedSecurityStatisticsSecAgentStatsNumSpiTransformEntryCreateFailNoResource ConfdString,
        affirmedSecurityStatisticsSecAgentStatsNumSpiTransformEntryCreateFailDuplicate ConfdString,
        affirmedSecurityStatisticsSecAgentStatsNumDequeueDrainPendingCollision ConfdString,
        affirmedSecurityStatisticsSecAgentStatsNumSkinnyFlowCreateDuplicate ConfdString,
        affirmedSecurityStatisticsSecAgentStatsNumDequeueFlushPendingCollision ConfdString,
        affirmedSecurityStatisticsSecAgentStatsNumSkinnyFlowFailNoResources ConfdString,
        affirmedSecurityStatisticsSecAgentStatsNumErrorNewFlowBusy ConfdString,
        affirmedSecurityStatisticsSecAgentStatsNumSpdNcAddFailCountAlloc ConfdString,
        affirmedSecurityStatisticsSecAgentStatsNumSpdNcDelFailCountDuplicate ConfdString,
        affirmedSecurityStatisticsSecAgentStatsNumSpdNcDelFailCountDealloc ConfdString,
        affirmedSecurityStatisticsSecAgentStatsNumSpdNcStaleDeleteCount ConfdString,
        affirmedSecurityStatisticsSecAgentStatsNumSpdRuleAddFailCountNoNetCtxt ConfdString,
        affirmedSecurityStatisticsSecAgentStatsNumSpdRuleAddFailCountAllocation ConfdString,
        affirmedSecurityStatisticsSecAgentStatsNumSpdRuleModFailCountNoRule ConfdString,
        affirmedSecurityStatisticsSecAgentStatsNumSpdRuleDelFailCountNoNetCtxt ConfdString,
        affirmedSecurityStatisticsSecAgentStatsNumSpdRuleDelFailCountNoRule ConfdString,
        affirmedSecurityStatisticsSecAgentStatsNumSpdRuleLookupFailCountNoNetCtxt ConfdString,
        affirmedSecurityStatisticsSecAgentStatsNumFpFlowsIngressCreateDuplicate ConfdString,
        affirmedSecurityStatisticsSecAgentStatsNumFpFlowsEgressCreateDuplicate ConfdString,
        affirmedSecurityStatisticsSecAgentStatsNumFpFlowsModifyFail ConfdString,
        affirmedSecurityStatisticsSecAgentStatsNumFpFlowsDeleteFail ConfdString,
        affirmedSecurityStatisticsSecAgentStatsNumFpFlowsFailNoResources ConfdString,
        affirmedSecurityStatisticsSecAgentStatsNumFpFlowsFailNoTransform ConfdString,
        affirmedSecurityStatisticsSecAgentStatsNumFpFlowsFailNcidMismatch ConfdString,
        affirmedSecurityStatisticsSecAgentStatsNumFpFlowsFailNullFlowCreate ConfdString,
        affirmedSecurityStatisticsSecAgentStatsNumFpFlowsDuplicatedFpFlows ConfdString,
        affirmedSecurityStatisticsSecAgentStatsNumFpFlowsDuplicatedSpmFlows ConfdString,
        affirmedSecurityStatisticsSecAgentStatsNumSpmFlowsDuplicatedFpFlows ConfdString,
        affirmedSecurityStatisticsSecAgentStatsNumOrphanedSpmFlowsDeleted ConfdString,
        affirmedSecurityStatisticsSecAgentStatsNumSpmFlowAssociatedRace ConfdString,
        affirmedSecurityStatisticsSecAgentStatsNumFlowRemovedFromHashLate ConfdString,
        affirmedSecurityStatisticsSecAgentStatsNumSpdAddRuleCtrFail ConfdString,
        affirmedSecurityStatisticsSecAgentStatsNumSpdDelCtrNull ConfdString,
        affirmedSecurityStatisticsSecAgentStatsNumFpFlowsEgressMoveToHashFail ConfdString,
        affirmedSecurityStatisticsSecAgentStatsNumSpdRuleAddIgnoreCountNcMisMatch ConfdString
    }

affirmedSecurityStatisticsSecAgentStatsDummyIndex OBJECT-TYPE
    SYNTAX      Unsigned32
    MAX-ACCESS  not-accessible
    STATUS      current
    DESCRIPTION ""
    ::= { affirmedSecurityStatisticsSecAgentStatsEntry 1 }

affirmedSecurityStatisticsSecAgentStatsCryptoLibraryInitialized OBJECT-TYPE
    SYNTAX      INTEGER {false(0),true(1)}
    MAX-ACCESS  read-only
    STATUS      current
    DESCRIPTION "Crypto library initialized or not"
    ::= { affirmedSecurityStatisticsSecAgentStatsEntry 2 }

affirmedSecurityStatisticsSecAgentStatsNumNcSpmEntriesCreated OBJECT-TYPE
    SYNTAX      ConfdString
    MAX-ACCESS  read-only
    STATUS      current
    DESCRIPTION "Number of SPM created"
    ::= { affirmedSecurityStatisticsSecAgentStatsEntry 3 }

affirmedSecurityStatisticsSecAgentStatsNumNcSpmEntriesModified OBJECT-TYPE
    SYNTAX      ConfdString
    MAX-ACCESS  read-only
    STATUS      current
    DESCRIPTION "Number of SPM modified"
    ::= { affirmedSecurityStatisticsSecAgentStatsEntry 4 }

affirmedSecurityStatisticsSecAgentStatsNumNcSpmEntriesDeleted OBJECT-TYPE
    SYNTAX      ConfdString
    MAX-ACCESS  read-only
    STATUS      current
    DESCRIPTION "Number of SPM deleted"
    ::= { affirmedSecurityStatisticsSecAgentStatsEntry 5 }

affirmedSecurityStatisticsSecAgentStatsNumFullTransformsCreated OBJECT-TYPE
    SYNTAX      ConfdString
    MAX-ACCESS  read-only
    STATUS      current
    DESCRIPTION "Number of Full transforms created"
    ::= { affirmedSecurityStatisticsSecAgentStatsEntry 6 }

affirmedSecurityStatisticsSecAgentStatsNumEpdgTransformsCreated OBJECT-TYPE
    SYNTAX      ConfdString
    MAX-ACCESS  read-only
    STATUS      current
    DESCRIPTION "Number of epdg transforms created"
    ::= { affirmedSecurityStatisticsSecAgentStatsEntry 7 }

affirmedSecurityStatisticsSecAgentStatsNumMiniTransformsCreated OBJECT-TYPE
    SYNTAX      ConfdString
    MAX-ACCESS  read-only
    STATUS      current
    DESCRIPTION "Number of mini transforms created"
    ::= { affirmedSecurityStatisticsSecAgentStatsEntry 8 }

affirmedSecurityStatisticsSecAgentStatsNumTransformsRekeyed OBJECT-TYPE
    SYNTAX      ConfdString
    MAX-ACCESS  read-only
    STATUS      current
    DESCRIPTION "Number of transforms rekeyed"
    ::= { affirmedSecurityStatisticsSecAgentStatsEntry 9 }

affirmedSecurityStatisticsSecAgentStatsNumTransformsModified OBJECT-TYPE
    SYNTAX      ConfdString
    MAX-ACCESS  read-only
    STATUS      current
    DESCRIPTION "Number of transforms modified"
    ::= { affirmedSecurityStatisticsSecAgentStatsEntry 10 }

affirmedSecurityStatisticsSecAgentStatsNumTransformsChngToFullFail OBJECT-TYPE
    SYNTAX      ConfdString
    MAX-ACCESS  read-only
    STATUS      current
    DESCRIPTION "Number of transforms changed to full fail"
    ::= { affirmedSecurityStatisticsSecAgentStatsEntry 11 }

affirmedSecurityStatisticsSecAgentStatsNumTransformsChngToEpdgFail OBJECT-TYPE
    SYNTAX      ConfdString
    MAX-ACCESS  read-only
    STATUS      current
    DESCRIPTION "Number of transforms changed to epdg fail"
    ::= { affirmedSecurityStatisticsSecAgentStatsEntry 12 }

affirmedSecurityStatisticsSecAgentStatsNumTransformsChngToMiniFail OBJECT-TYPE
    SYNTAX      ConfdString
    MAX-ACCESS  read-only
    STATUS      current
    DESCRIPTION "Number of transforms changed to mini fail"
    ::= { affirmedSecurityStatisticsSecAgentStatsEntry 13 }

affirmedSecurityStatisticsSecAgentStatsNumFullTransformsDeleted OBJECT-TYPE
    SYNTAX      ConfdString
    MAX-ACCESS  read-only
    STATUS      current
    DESCRIPTION "Number of full transforms deleted"
    ::= { affirmedSecurityStatisticsSecAgentStatsEntry 14 }

affirmedSecurityStatisticsSecAgentStatsNumEpdgTransformsDeleted OBJECT-TYPE
    SYNTAX      ConfdString
    MAX-ACCESS  read-only
    STATUS      current
    DESCRIPTION "Number of epdg transforms deleted"
    ::= { affirmedSecurityStatisticsSecAgentStatsEntry 15 }

affirmedSecurityStatisticsSecAgentStatsNumMiniTransformsDeleted OBJECT-TYPE
    SYNTAX      ConfdString
    MAX-ACCESS  read-only
    STATUS      current
    DESCRIPTION "Number of mini transforms deleted"
    ::= { affirmedSecurityStatisticsSecAgentStatsEntry 16 }

affirmedSecurityStatisticsSecAgentStatsNumTransformUpdates OBJECT-TYPE
    SYNTAX      ConfdString
    MAX-ACCESS  read-only
    STATUS      current
    DESCRIPTION "Number of transform updates"
    ::= { affirmedSecurityStatisticsSecAgentStatsEntry 17 }

affirmedSecurityStatisticsSecAgentStatsNumTransformsFPDeletedStale OBJECT-TYPE
    SYNTAX      ConfdString
    MAX-ACCESS  read-only
    STATUS      current
    DESCRIPTION "Number of Fast Path stale transforms deleted"
    ::= { affirmedSecurityStatisticsSecAgentStatsEntry 18 }

affirmedSecurityStatisticsSecAgentStatsNumFlowsCreateAttempts OBJECT-TYPE
    SYNTAX      ConfdString
    MAX-ACCESS  read-only
    STATUS      current
    DESCRIPTION "Number of flow create attempts"
    ::= { affirmedSecurityStatisticsSecAgentStatsEntry 19 }

affirmedSecurityStatisticsSecAgentStatsNumFlowsCreated OBJECT-TYPE
    SYNTAX      ConfdString
    MAX-ACCESS  read-only
    STATUS      current
    DESCRIPTION "Number of flows created"
    ::= { affirmedSecurityStatisticsSecAgentStatsEntry 20 }

affirmedSecurityStatisticsSecAgentStatsNumFlowsModifyAttempts OBJECT-TYPE
    SYNTAX      ConfdString
    MAX-ACCESS  read-only
    STATUS      current
    DESCRIPTION "Number of flow modify attempts"
    ::= { affirmedSecurityStatisticsSecAgentStatsEntry 21 }

affirmedSecurityStatisticsSecAgentStatsNumFlowsModified OBJECT-TYPE
    SYNTAX      ConfdString
    MAX-ACCESS  read-only
    STATUS      current
    DESCRIPTION "Number of flows modified"
    ::= { affirmedSecurityStatisticsSecAgentStatsEntry 22 }

affirmedSecurityStatisticsSecAgentStatsNumFlowsDeleteAttempts OBJECT-TYPE
    SYNTAX      ConfdString
    MAX-ACCESS  read-only
    STATUS      current
    DESCRIPTION "Number of flow delete attempts"
    ::= { affirmedSecurityStatisticsSecAgentStatsEntry 23 }

affirmedSecurityStatisticsSecAgentStatsNumFlowsDeleted OBJECT-TYPE
    SYNTAX      ConfdString
    MAX-ACCESS  read-only
    STATUS      current
    DESCRIPTION "Number of flows deleted"
    ::= { affirmedSecurityStatisticsSecAgentStatsEntry 24 }

affirmedSecurityStatisticsSecAgentStatsNumFlowsFPDeleted OBJECT-TYPE
    SYNTAX      ConfdString
    MAX-ACCESS  read-only
    STATUS      current
    DESCRIPTION "Number of FP flows deleted"
    ::= { affirmedSecurityStatisticsSecAgentStatsEntry 25 }

affirmedSecurityStatisticsSecAgentStatsNumFlowsFPDeletedStale OBJECT-TYPE
    SYNTAX      ConfdString
    MAX-ACCESS  read-only
    STATUS      current
    DESCRIPTION "Number of FP stale flows deleted"
    ::= { affirmedSecurityStatisticsSecAgentStatsEntry 26 }

affirmedSecurityStatisticsSecAgentStatsNumFlowsFPCreateRace OBJECT-TYPE
    SYNTAX      ConfdString
    MAX-ACCESS  read-only
    STATUS      current
    DESCRIPTION "Number of FP flows create race"
    ::= { affirmedSecurityStatisticsSecAgentStatsEntry 27 }

affirmedSecurityStatisticsSecAgentStatsNumTransactionsCreated OBJECT-TYPE
    SYNTAX      ConfdString
    MAX-ACCESS  read-only
    STATUS      current
    DESCRIPTION "Number of transactions created"
    ::= { affirmedSecurityStatisticsSecAgentStatsEntry 28 }

affirmedSecurityStatisticsSecAgentStatsNumTransactionsDeleted OBJECT-TYPE
    SYNTAX      ConfdString
    MAX-ACCESS  read-only
    STATUS      current
    DESCRIPTION "Number of transactions deleted"
    ::= { affirmedSecurityStatisticsSecAgentStatsEntry 29 }

affirmedSecurityStatisticsSecAgentStatsNumFlowCfmsReported OBJECT-TYPE
    SYNTAX      ConfdString
    MAX-ACCESS  read-only
    STATUS      current
    DESCRIPTION "Number of flow Cfms reported"
    ::= { affirmedSecurityStatisticsSecAgentStatsEntry 30 }

affirmedSecurityStatisticsSecAgentStatsNumTransformCfmsReported OBJECT-TYPE
    SYNTAX      ConfdString
    MAX-ACCESS  read-only
    STATUS      current
    DESCRIPTION "Number of transform Cfms reported"
    ::= { affirmedSecurityStatisticsSecAgentStatsEntry 31 }

affirmedSecurityStatisticsSecAgentStatsNumRsaRequests OBJECT-TYPE
    SYNTAX      ConfdString
    MAX-ACCESS  read-only
    STATUS      current
    DESCRIPTION "Number of RSA requests"
    ::= { affirmedSecurityStatisticsSecAgentStatsEntry 32 }

affirmedSecurityStatisticsSecAgentStatsNumRsaRequestsCalcResultOK OBJECT-TYPE
    SYNTAX      ConfdString
    MAX-ACCESS  read-only
    STATUS      current
    DESCRIPTION "Number of RSA requests is OK"
    ::= { affirmedSecurityStatisticsSecAgentStatsEntry 33 }

affirmedSecurityStatisticsSecAgentStatsNumLocalTransforms OBJECT-TYPE
    SYNTAX      ConfdString
    MAX-ACCESS  read-only
    STATUS      current
    DESCRIPTION "Number of local transforms"
    ::= { affirmedSecurityStatisticsSecAgentStatsEntry 34 }

affirmedSecurityStatisticsSecAgentStatsNumSpmFlowsAllocated OBJECT-TYPE
    SYNTAX      ConfdString
    MAX-ACCESS  read-only
    STATUS      current
    DESCRIPTION "Number of spm flows allocated"
    ::= { affirmedSecurityStatisticsSecAgentStatsEntry 35 }

affirmedSecurityStatisticsSecAgentStatsNumSpmFlowsDeallocated OBJECT-TYPE
    SYNTAX      ConfdString
    MAX-ACCESS  read-only
    STATUS      current
    DESCRIPTION "Number of spm flows deallocated"
    ::= { affirmedSecurityStatisticsSecAgentStatsEntry 36 }

affirmedSecurityStatisticsSecAgentStatsNumPendingFlowsAllocated OBJECT-TYPE
    SYNTAX      ConfdString
    MAX-ACCESS  read-only
    STATUS      current
    DESCRIPTION "Number of pending flows allocated"
    ::= { affirmedSecurityStatisticsSecAgentStatsEntry 37 }

affirmedSecurityStatisticsSecAgentStatsNumPendingFlowsDeallocated OBJECT-TYPE
    SYNTAX      ConfdString
    MAX-ACCESS  read-only
    STATUS      current
    DESCRIPTION "Number of pending flows deallocated"
    ::= { affirmedSecurityStatisticsSecAgentStatsEntry 38 }

affirmedSecurityStatisticsSecAgentStatsNumSpmPublishForPendingFlow OBJECT-TYPE
    SYNTAX      ConfdString
    MAX-ACCESS  read-only
    STATUS      current
    DESCRIPTION "Number of Spm publish for pending flows"
    ::= { affirmedSecurityStatisticsSecAgentStatsEntry 39 }

affirmedSecurityStatisticsSecAgentStatsNumCreateFlowsWithoutSpmForward OBJECT-TYPE
    SYNTAX      ConfdString
    MAX-ACCESS  read-only
    STATUS      current
    DESCRIPTION "Number of flows created without spm forward"
    ::= { affirmedSecurityStatisticsSecAgentStatsEntry 40 }

affirmedSecurityStatisticsSecAgentStatsNumIdleFlowsReported OBJECT-TYPE
    SYNTAX      ConfdString
    MAX-ACCESS  read-only
    STATUS      current
    DESCRIPTION "Number of idle flows reported"
    ::= { affirmedSecurityStatisticsSecAgentStatsEntry 41 }

affirmedSecurityStatisticsSecAgentStatsNumFlowsCleanedup OBJECT-TYPE
    SYNTAX      ConfdString
    MAX-ACCESS  read-only
    STATUS      current
    DESCRIPTION "Number of flows cleanup"
    ::= { affirmedSecurityStatisticsSecAgentStatsEntry 42 }

affirmedSecurityStatisticsSecAgentStatsNumFlowSetSpis OBJECT-TYPE
    SYNTAX      ConfdString
    MAX-ACCESS  read-only
    STATUS      current
    DESCRIPTION "Number of flow set SPIs"
    ::= { affirmedSecurityStatisticsSecAgentStatsEntry 43 }

affirmedSecurityStatisticsSecAgentStatsNumSpiEntryCreated OBJECT-TYPE
    SYNTAX      ConfdString
    MAX-ACCESS  read-only
    STATUS      current
    DESCRIPTION "Number of spi entry created"
    ::= { affirmedSecurityStatisticsSecAgentStatsEntry 44 }

affirmedSecurityStatisticsSecAgentStatsNumSessionEntryCreated OBJECT-TYPE
    SYNTAX      ConfdString
    MAX-ACCESS  read-only
    STATUS      current
    DESCRIPTION "Number of session entry created"
    ::= { affirmedSecurityStatisticsSecAgentStatsEntry 45 }

affirmedSecurityStatisticsSecAgentStatsNumSessionEntryDeleted OBJECT-TYPE
    SYNTAX      ConfdString
    MAX-ACCESS  read-only
    STATUS      current
    DESCRIPTION "Number of session entry deleted"
    ::= { affirmedSecurityStatisticsSecAgentStatsEntry 46 }

affirmedSecurityStatisticsSecAgentStatsNumSpiTransformEntryCreated OBJECT-TYPE
    SYNTAX      ConfdString
    MAX-ACCESS  read-only
    STATUS      current
    DESCRIPTION "Number of spi transform entry created"
    ::= { affirmedSecurityStatisticsSecAgentStatsEntry 47 }

affirmedSecurityStatisticsSecAgentStatsNumSpiTransformEntryDeleted OBJECT-TYPE
    SYNTAX      ConfdString
    MAX-ACCESS  read-only
    STATUS      current
    DESCRIPTION "Number of spi transform entry deleted"
    ::= { affirmedSecurityStatisticsSecAgentStatsEntry 48 }

affirmedSecurityStatisticsSecAgentStatsNumSkinnyFlowAllocated OBJECT-TYPE
    SYNTAX      ConfdString
    MAX-ACCESS  read-only
    STATUS      current
    DESCRIPTION "Number of skinny flow allocated"
    ::= { affirmedSecurityStatisticsSecAgentStatsEntry 49 }

affirmedSecurityStatisticsSecAgentStatsNumSkinnyFlowDeallocated OBJECT-TYPE
    SYNTAX      ConfdString
    MAX-ACCESS  read-only
    STATUS      current
    DESCRIPTION "Number of skinny flow deallocated"
    ::= { affirmedSecurityStatisticsSecAgentStatsEntry 50 }

affirmedSecurityStatisticsSecAgentStatsNumSkinnyFlowCreateAttempts OBJECT-TYPE
    SYNTAX      ConfdString
    MAX-ACCESS  read-only
    STATUS      current
    DESCRIPTION "Number of skinny flow create attempts"
    ::= { affirmedSecurityStatisticsSecAgentStatsEntry 51 }

affirmedSecurityStatisticsSecAgentStatsNumSkinnyFlowCreated OBJECT-TYPE
    SYNTAX      ConfdString
    MAX-ACCESS  read-only
    STATUS      current
    DESCRIPTION "Number of skinny flow created"
    ::= { affirmedSecurityStatisticsSecAgentStatsEntry 52 }

affirmedSecurityStatisticsSecAgentStatsNumSpdNcAddAttemptCount OBJECT-TYPE
    SYNTAX      ConfdString
    MAX-ACCESS  read-only
    STATUS      current
    DESCRIPTION "Number of spd nc add attempt"
    ::= { affirmedSecurityStatisticsSecAgentStatsEntry 53 }

affirmedSecurityStatisticsSecAgentStatsNumSpdNcAddSuccessCount OBJECT-TYPE
    SYNTAX      ConfdString
    MAX-ACCESS  read-only
    STATUS      current
    DESCRIPTION "Number of spd nc add success"
    ::= { affirmedSecurityStatisticsSecAgentStatsEntry 54 }

affirmedSecurityStatisticsSecAgentStatsNumSpdNcDelAttemptCount OBJECT-TYPE
    SYNTAX      ConfdString
    MAX-ACCESS  read-only
    STATUS      current
    DESCRIPTION "Number of spd nc del attempt"
    ::= { affirmedSecurityStatisticsSecAgentStatsEntry 55 }

affirmedSecurityStatisticsSecAgentStatsNumSpdNcDelSuccessCount OBJECT-TYPE
    SYNTAX      ConfdString
    MAX-ACCESS  read-only
    STATUS      current
    DESCRIPTION "Number of spd nc del success"
    ::= { affirmedSecurityStatisticsSecAgentStatsEntry 56 }

affirmedSecurityStatisticsSecAgentStatsNumSpdRuleAddAttemptCount OBJECT-TYPE
    SYNTAX      ConfdString
    MAX-ACCESS  read-only
    STATUS      current
    DESCRIPTION "Number of spd rule add attempt"
    ::= { affirmedSecurityStatisticsSecAgentStatsEntry 57 }

affirmedSecurityStatisticsSecAgentStatsNumSpdRuleAddSuccessCount OBJECT-TYPE
    SYNTAX      ConfdString
    MAX-ACCESS  read-only
    STATUS      current
    DESCRIPTION "Number of spd rule add success"
    ::= { affirmedSecurityStatisticsSecAgentStatsEntry 58 }

affirmedSecurityStatisticsSecAgentStatsNumSpdRuleModAttemptCount OBJECT-TYPE
    SYNTAX      ConfdString
    MAX-ACCESS  read-only
    STATUS      current
    DESCRIPTION "Number of spd rule modify attempt"
    ::= { affirmedSecurityStatisticsSecAgentStatsEntry 59 }

affirmedSecurityStatisticsSecAgentStatsNumSpdRuleModSuccessCount OBJECT-TYPE
    SYNTAX      ConfdString
    MAX-ACCESS  read-only
    STATUS      current
    DESCRIPTION "Number of spd rule modify success"
    ::= { affirmedSecurityStatisticsSecAgentStatsEntry 60 }

affirmedSecurityStatisticsSecAgentStatsNumSpdRuleDelAttemptCount OBJECT-TYPE
    SYNTAX      ConfdString
    MAX-ACCESS  read-only
    STATUS      current
    DESCRIPTION "Number of spd rule delete attempt"
    ::= { affirmedSecurityStatisticsSecAgentStatsEntry 61 }

affirmedSecurityStatisticsSecAgentStatsNumSpdRuleDelSuccessCount OBJECT-TYPE
    SYNTAX      ConfdString
    MAX-ACCESS  read-only
    STATUS      current
    DESCRIPTION "Number of spd rule delete success"
    ::= { affirmedSecurityStatisticsSecAgentStatsEntry 62 }

affirmedSecurityStatisticsSecAgentStatsNumFpFlowsAllocated OBJECT-TYPE
    SYNTAX      ConfdString
    MAX-ACCESS  read-only
    STATUS      current
    DESCRIPTION "Number of fp flow allocated"
    ::= { affirmedSecurityStatisticsSecAgentStatsEntry 63 }

affirmedSecurityStatisticsSecAgentStatsNumFpFlowsDeallocated OBJECT-TYPE
    SYNTAX      ConfdString
    MAX-ACCESS  read-only
    STATUS      current
    DESCRIPTION "Number of fp flow deallocated"
    ::= { affirmedSecurityStatisticsSecAgentStatsEntry 64 }

affirmedSecurityStatisticsSecAgentStatsNumFpFlowCreateAttempts OBJECT-TYPE
    SYNTAX      ConfdString
    MAX-ACCESS  read-only
    STATUS      current
    DESCRIPTION "Number of fp flow create attempts"
    ::= { affirmedSecurityStatisticsSecAgentStatsEntry 65 }

affirmedSecurityStatisticsSecAgentStatsNumFpFlowsCreated OBJECT-TYPE
    SYNTAX      ConfdString
    MAX-ACCESS  read-only
    STATUS      current
    DESCRIPTION "Number of fp flows created"
    ::= { affirmedSecurityStatisticsSecAgentStatsEntry 66 }

affirmedSecurityStatisticsSecAgentStatsNumFpFlowsModifyAttempts OBJECT-TYPE
    SYNTAX      ConfdString
    MAX-ACCESS  read-only
    STATUS      current
    DESCRIPTION "Number of fp flow modify attempts"
    ::= { affirmedSecurityStatisticsSecAgentStatsEntry 67 }

affirmedSecurityStatisticsSecAgentStatsNumFpFlowsModified OBJECT-TYPE
    SYNTAX      ConfdString
    MAX-ACCESS  read-only
    STATUS      current
    DESCRIPTION "Number of fp flows modified"
    ::= { affirmedSecurityStatisticsSecAgentStatsEntry 68 }

affirmedSecurityStatisticsSecAgentStatsNumFpFlowsDeleteAttempts OBJECT-TYPE
    SYNTAX      ConfdString
    MAX-ACCESS  read-only
    STATUS      current
    DESCRIPTION "Number of fp flow delete attempts"
    ::= { affirmedSecurityStatisticsSecAgentStatsEntry 69 }

affirmedSecurityStatisticsSecAgentStatsNumFpFlowsDeleted OBJECT-TYPE
    SYNTAX      ConfdString
    MAX-ACCESS  read-only
    STATUS      current
    DESCRIPTION "Number of fp flows deleted"
    ::= { affirmedSecurityStatisticsSecAgentStatsEntry 70 }

affirmedSecurityStatisticsSecAgentStatsNumSpdAddRuleCtr OBJECT-TYPE
    SYNTAX      ConfdString
    MAX-ACCESS  read-only
    STATUS      current
    DESCRIPTION "Number of spd rule added"
    ::= { affirmedSecurityStatisticsSecAgentStatsEntry 71 }

affirmedSecurityStatisticsSecAgentStatsNumSpdDelRuleCtr OBJECT-TYPE
    SYNTAX      ConfdString
    MAX-ACCESS  read-only
    STATUS      current
    DESCRIPTION "Number of spd rule deleted"
    ::= { affirmedSecurityStatisticsSecAgentStatsEntry 72 }

affirmedSecurityStatisticsSecAgentStatsNumSkinnyFlowsIgnoreIom OBJECT-TYPE
    SYNTAX      ConfdString
    MAX-ACCESS  read-only
    STATUS      current
    DESCRIPTION "Number of skinny flow ignored iom"
    ::= { affirmedSecurityStatisticsSecAgentStatsEntry 73 }

affirmedSecurityStatisticsSecAgentStatsNumFlowsDeleteFail OBJECT-TYPE
    SYNTAX      ConfdString
    MAX-ACCESS  read-only
    STATUS      current
    DESCRIPTION "Number of flow delete fail"
    ::= { affirmedSecurityStatisticsSecAgentStatsEntry 74 }

affirmedSecurityStatisticsSecAgentStatsNumTransformsAddIgnore OBJECT-TYPE
    SYNTAX      ConfdString
    MAX-ACCESS  read-only
    STATUS      current
    DESCRIPTION "Number of transforms add ignore"
    ::= { affirmedSecurityStatisticsSecAgentStatsEntry 75 }

affirmedSecurityStatisticsSecAgentStatsNumTransformsModifyIgnore OBJECT-TYPE
    SYNTAX      ConfdString
    MAX-ACCESS  read-only
    STATUS      current
    DESCRIPTION "Number of transforms modify ignore"
    ::= { affirmedSecurityStatisticsSecAgentStatsEntry 76 }

affirmedSecurityStatisticsSecAgentStatsNumTransformsDeleteIgnore OBJECT-TYPE
    SYNTAX      ConfdString
    MAX-ACCESS  read-only
    STATUS      current
    DESCRIPTION "Number of transforms delete ignore"
    ::= { affirmedSecurityStatisticsSecAgentStatsEntry 77 }

affirmedSecurityStatisticsSecAgentStatsNumTransformsNotFound OBJECT-TYPE
    SYNTAX      ConfdString
    MAX-ACCESS  read-only
    STATUS      current
    DESCRIPTION "Number of transforms not found"
    ::= { affirmedSecurityStatisticsSecAgentStatsEntry 78 }

affirmedSecurityStatisticsSecAgentStatsNumRekeyModify OBJECT-TYPE
    SYNTAX      ConfdString
    MAX-ACCESS  read-only
    STATUS      current
    DESCRIPTION "Number of rekey modify"
    ::= { affirmedSecurityStatisticsSecAgentStatsEntry 79 }

affirmedSecurityStatisticsSecAgentStatsNumNoRekeyModify OBJECT-TYPE
    SYNTAX      ConfdString
    MAX-ACCESS  read-only
    STATUS      current
    DESCRIPTION "Number of no rekey modify"
    ::= { affirmedSecurityStatisticsSecAgentStatsEntry 80 }

affirmedSecurityStatisticsSecAgentStatsNumNewOuterFlowFound OBJECT-TYPE
    SYNTAX      ConfdString
    MAX-ACCESS  read-only
    STATUS      current
    DESCRIPTION "Number of new outer flow found"
    ::= { affirmedSecurityStatisticsSecAgentStatsEntry 81 }

affirmedSecurityStatisticsSecAgentStatsNumNewOuterFlowFoundInMaint OBJECT-TYPE
    SYNTAX      ConfdString
    MAX-ACCESS  read-only
    STATUS      current
    DESCRIPTION "Number of new outer flow maintenance"
    ::= { affirmedSecurityStatisticsSecAgentStatsEntry 82 }

affirmedSecurityStatisticsSecAgentStatsNumOuterFlowChange OBJECT-TYPE
    SYNTAX      ConfdString
    MAX-ACCESS  read-only
    STATUS      current
    DESCRIPTION "Number of outer flow change"
    ::= { affirmedSecurityStatisticsSecAgentStatsEntry 83 }

affirmedSecurityStatisticsSecAgentStatsNumIngressFlowsCreateDuplicate OBJECT-TYPE
    SYNTAX      ConfdString
    MAX-ACCESS  read-only
    STATUS      current
    DESCRIPTION "Number of ingress flow create duplicate"
    ::= { affirmedSecurityStatisticsSecAgentStatsEntry 84 }

affirmedSecurityStatisticsSecAgentStatsNumSpmFlowsDuplicatedSpmFlows OBJECT-TYPE
    SYNTAX      ConfdString
    MAX-ACCESS  read-only
    STATUS      current
    DESCRIPTION "Number of duplicated spm flows"
    ::= { affirmedSecurityStatisticsSecAgentStatsEntry 85 }

affirmedSecurityStatisticsSecAgentStatsNumFlowSpiChangeLate OBJECT-TYPE
    SYNTAX      ConfdString
    MAX-ACCESS  read-only
    STATUS      current
    DESCRIPTION "Number of flow spi change"
    ::= { affirmedSecurityStatisticsSecAgentStatsEntry 86 }

affirmedSecurityStatisticsSecAgentStatsNumFpFlowsFailHashTablesAdd OBJECT-TYPE
    SYNTAX      ConfdString
    MAX-ACCESS  read-only
    STATUS      current
    DESCRIPTION "Number of fp flow hash table add failed"
    ::= { affirmedSecurityStatisticsSecAgentStatsEntry 87 }

affirmedSecurityStatisticsSecAgentStatsNumFpFlowsEgressMovedToHash OBJECT-TYPE
    SYNTAX      ConfdString
    MAX-ACCESS  read-only
    STATUS      current
    DESCRIPTION "Number of fp flow egress moved to hash"
    ::= { affirmedSecurityStatisticsSecAgentStatsEntry 88 }

affirmedSecurityStatisticsSecAgentStatsNumSpdNcAddFailCountDuplicate OBJECT-TYPE
    SYNTAX      ConfdString
    MAX-ACCESS  read-only
    STATUS      current
    DESCRIPTION "Number of spd Nc add fail duplicated"
    ::= { affirmedSecurityStatisticsSecAgentStatsEntry 89 }

affirmedSecurityStatisticsSecAgentStatsNumSpiTransEntryTransformChange OBJECT-TYPE
    SYNTAX      ConfdString
    MAX-ACCESS  read-only
    STATUS      current
    DESCRIPTION "Number of spi entry transform change"
    ::= { affirmedSecurityStatisticsSecAgentStatsEntry 90 }

affirmedSecurityStatisticsSecAgentStatsNumSpiTransDeleteIndexMismatch OBJECT-TYPE
    SYNTAX      ConfdString
    MAX-ACCESS  read-only
    STATUS      current
    DESCRIPTION "Number of spi transform delete index mismatch"
    ::= { affirmedSecurityStatisticsSecAgentStatsEntry 91 }

affirmedSecurityStatisticsSecAgentStatsNumSessionEntryCreateFailDuplicate OBJECT-TYPE
    SYNTAX      ConfdString
    MAX-ACCESS  read-only
    STATUS      current
    DESCRIPTION "Number of session entry create fail duplicate"
    ::= { affirmedSecurityStatisticsSecAgentStatsEntry 92 }

affirmedSecurityStatisticsSecAgentStatsNumCannotDecideIfAnchor OBJECT-TYPE
    SYNTAX      ConfdString
    MAX-ACCESS  read-only
    STATUS      current
    DESCRIPTION "Number cannot decide if anchor"
    ::= { affirmedSecurityStatisticsSecAgentStatsEntry 93 }

affirmedSecurityStatisticsSecAgentStatsNumNcSpmEntriesError OBJECT-TYPE
    SYNTAX      ConfdString
    MAX-ACCESS  read-only
    STATUS      current
    DESCRIPTION "Number NC SPM entries error"
    ::= { affirmedSecurityStatisticsSecAgentStatsEntry 94 }

affirmedSecurityStatisticsSecAgentStatsNumTransformsCreateFailNoResources OBJECT-TYPE
    SYNTAX      ConfdString
    MAX-ACCESS  read-only
    STATUS      current
    DESCRIPTION "Number transform create fail due to no resources"
    ::= { affirmedSecurityStatisticsSecAgentStatsEntry 95 }

affirmedSecurityStatisticsSecAgentStatsNumTransformsCreateFailDuplicate OBJECT-TYPE
    SYNTAX      ConfdString
    MAX-ACCESS  read-only
    STATUS      current
    DESCRIPTION "Number transform create fail duplicate"
    ::= { affirmedSecurityStatisticsSecAgentStatsEntry 96 }

affirmedSecurityStatisticsSecAgentStatsNumTransformsRekeyFail OBJECT-TYPE
    SYNTAX      ConfdString
    MAX-ACCESS  read-only
    STATUS      current
    DESCRIPTION "Number transforms rekey fail"
    ::= { affirmedSecurityStatisticsSecAgentStatsEntry 97 }

affirmedSecurityStatisticsSecAgentStatsNumFlowsCreateFail OBJECT-TYPE
    SYNTAX      ConfdString
    MAX-ACCESS  read-only
    STATUS      current
    DESCRIPTION "Number of flows create failed"
    ::= { affirmedSecurityStatisticsSecAgentStatsEntry 98 }

affirmedSecurityStatisticsSecAgentStatsNumFlowsCreateFailDuplicate OBJECT-TYPE
    SYNTAX      ConfdString
    MAX-ACCESS  read-only
    STATUS      current
    DESCRIPTION "Number of flows create failed duplicate"
    ::= { affirmedSecurityStatisticsSecAgentStatsEntry 99 }

affirmedSecurityStatisticsSecAgentStatsNumFlowsCreateFailNoResources OBJECT-TYPE
    SYNTAX      ConfdString
    MAX-ACCESS  read-only
    STATUS      current
    DESCRIPTION "Number of flows create failed due to no resources"
    ::= { affirmedSecurityStatisticsSecAgentStatsEntry 100 }

affirmedSecurityStatisticsSecAgentStatsNumFlowsModifyFail OBJECT-TYPE
    SYNTAX      ConfdString
    MAX-ACCESS  read-only
    STATUS      current
    DESCRIPTION "Number of flows modify failed"
    ::= { affirmedSecurityStatisticsSecAgentStatsEntry 101 }

affirmedSecurityStatisticsSecAgentStatsNumFlowsDoubleFree OBJECT-TYPE
    SYNTAX      ConfdString
    MAX-ACCESS  read-only
    STATUS      current
    DESCRIPTION "Number of flows double freed"
    ::= { affirmedSecurityStatisticsSecAgentStatsEntry 102 }

affirmedSecurityStatisticsSecAgentStatsNumFlowsNotFound OBJECT-TYPE
    SYNTAX      ConfdString
    MAX-ACCESS  read-only
    STATUS      current
    DESCRIPTION "Number of flows not found"
    ::= { affirmedSecurityStatisticsSecAgentStatsEntry 103 }

affirmedSecurityStatisticsSecAgentStatsNumPktOnNewTunnel OBJECT-TYPE
    SYNTAX      ConfdString
    MAX-ACCESS  read-only
    STATUS      current
    DESCRIPTION "Number of packets on new tunnel"
    ::= { affirmedSecurityStatisticsSecAgentStatsEntry 104 }

affirmedSecurityStatisticsSecAgentStatsNumEgressFlowsCreateDuplicate OBJECT-TYPE
    SYNTAX      ConfdString
    MAX-ACCESS  read-only
    STATUS      current
    DESCRIPTION "Number of egress flows create duplicate"
    ::= { affirmedSecurityStatisticsSecAgentStatsEntry 105 }

affirmedSecurityStatisticsSecAgentStatsNumFlowsFPCreateRaceError OBJECT-TYPE
    SYNTAX      ConfdString
    MAX-ACCESS  read-only
    STATUS      current
    DESCRIPTION "Number of FP flows create race error"
    ::= { affirmedSecurityStatisticsSecAgentStatsEntry 106 }

affirmedSecurityStatisticsSecAgentStatsNumTransactionsFailNoResources OBJECT-TYPE
    SYNTAX      ConfdString
    MAX-ACCESS  read-only
    STATUS      current
    DESCRIPTION "Number of transactions failed due to no resources"
    ::= { affirmedSecurityStatisticsSecAgentStatsEntry 107 }

affirmedSecurityStatisticsSecAgentStatsNumRsaRequestsParamLenError OBJECT-TYPE
    SYNTAX      ConfdString
    MAX-ACCESS  read-only
    STATUS      current
    DESCRIPTION "Number of RSA requests parameter length error"
    ::= { affirmedSecurityStatisticsSecAgentStatsEntry 108 }

affirmedSecurityStatisticsSecAgentStatsNumFlowDeleteDueToNewAdd OBJECT-TYPE
    SYNTAX      ConfdString
    MAX-ACCESS  read-only
    STATUS      current
    DESCRIPTION "Number of flow delete due to new add"
    ::= { affirmedSecurityStatisticsSecAgentStatsEntry 109 }

affirmedSecurityStatisticsSecAgentStatsNumActiveFlowAddToHashFail OBJECT-TYPE
    SYNTAX      ConfdString
    MAX-ACCESS  read-only
    STATUS      current
    DESCRIPTION "Number of flow add to hash fail"
    ::= { affirmedSecurityStatisticsSecAgentStatsEntry 110 }

affirmedSecurityStatisticsSecAgentStatsNumPendingFlowsFailNoResources OBJECT-TYPE
    SYNTAX      ConfdString
    MAX-ACCESS  read-only
    STATUS      current
    DESCRIPTION "Number of pending flows fail due to no resources"
    ::= { affirmedSecurityStatisticsSecAgentStatsEntry 111 }

affirmedSecurityStatisticsSecAgentStatsNumSpmFlowsFailNoResources OBJECT-TYPE
    SYNTAX      ConfdString
    MAX-ACCESS  read-only
    STATUS      current
    DESCRIPTION "Number of SPM flows fail due to no resources"
    ::= { affirmedSecurityStatisticsSecAgentStatsEntry 112 }

affirmedSecurityStatisticsSecAgentStatsNumFlowAccessTimeFix OBJECT-TYPE
    SYNTAX      ConfdString
    MAX-ACCESS  read-only
    STATUS      current
    DESCRIPTION "Number of flow access time fix"
    ::= { affirmedSecurityStatisticsSecAgentStatsEntry 113 }

affirmedSecurityStatisticsSecAgentStatsNumPendingFlowAccessTimeFix OBJECT-TYPE
    SYNTAX      ConfdString
    MAX-ACCESS  read-only
    STATUS      current
    DESCRIPTION "Number of pending flow access time fix"
    ::= { affirmedSecurityStatisticsSecAgentStatsEntry 114 }

affirmedSecurityStatisticsSecAgentStatsNumRsaRequestsCalcResultError OBJECT-TYPE
    SYNTAX      ConfdString
    MAX-ACCESS  read-only
    STATUS      current
    DESCRIPTION "Number of RSA requests result error"
    ::= { affirmedSecurityStatisticsSecAgentStatsEntry 115 }

affirmedSecurityStatisticsSecAgentStatsNumIngFlowUpdateNoFlow OBJECT-TYPE
    SYNTAX      ConfdString
    MAX-ACCESS  read-only
    STATUS      current
    DESCRIPTION "Number of Ingress flow update no flow"
    ::= { affirmedSecurityStatisticsSecAgentStatsEntry 116 }

affirmedSecurityStatisticsSecAgentStatsNumEgrFlowUpdateNoFlow OBJECT-TYPE
    SYNTAX      ConfdString
    MAX-ACCESS  read-only
    STATUS      current
    DESCRIPTION "Number of Egress flow update no flow"
    ::= { affirmedSecurityStatisticsSecAgentStatsEntry 117 }

affirmedSecurityStatisticsSecAgentStatsNumIngFlowUpdateError OBJECT-TYPE
    SYNTAX      ConfdString
    MAX-ACCESS  read-only
    STATUS      current
    DESCRIPTION "Number of ingress flow update error"
    ::= { affirmedSecurityStatisticsSecAgentStatsEntry 118 }

affirmedSecurityStatisticsSecAgentStatsNumEgrFlowUpdateError OBJECT-TYPE
    SYNTAX      ConfdString
    MAX-ACCESS  read-only
    STATUS      current
    DESCRIPTION "Number of egress flow update error"
    ::= { affirmedSecurityStatisticsSecAgentStatsEntry 119 }

affirmedSecurityStatisticsSecAgentStatsNumFlowSetSpisError OBJECT-TYPE
    SYNTAX      ConfdString
    MAX-ACCESS  read-only
    STATUS      current
    DESCRIPTION "Number of flow set SPIs error"
    ::= { affirmedSecurityStatisticsSecAgentStatsEntry 120 }

affirmedSecurityStatisticsSecAgentStatsNumTransformsInitError OBJECT-TYPE
    SYNTAX      ConfdString
    MAX-ACCESS  read-only
    STATUS      current
    DESCRIPTION "Number of transforms init error"
    ::= { affirmedSecurityStatisticsSecAgentStatsEntry 121 }

affirmedSecurityStatisticsSecAgentStatsNumSpiEntryCreateFailNoResource OBJECT-TYPE
    SYNTAX      ConfdString
    MAX-ACCESS  read-only
    STATUS      current
    DESCRIPTION "Number of spi entry create fail due to no resources"
    ::= { affirmedSecurityStatisticsSecAgentStatsEntry 122 }

affirmedSecurityStatisticsSecAgentStatsNumSpiEntryCreateFailDuplicate OBJECT-TYPE
    SYNTAX      ConfdString
    MAX-ACCESS  read-only
    STATUS      current
    DESCRIPTION "Number of spi entry create fail duplicate"
    ::= { affirmedSecurityStatisticsSecAgentStatsEntry 123 }

affirmedSecurityStatisticsSecAgentStatsNumSpiEntryCreateFailOldSpiNotFound OBJECT-TYPE
    SYNTAX      ConfdString
    MAX-ACCESS  read-only
    STATUS      current
    DESCRIPTION "Number of spi entry create fail due to old spi not found"
    ::= { affirmedSecurityStatisticsSecAgentStatsEntry 124 }

affirmedSecurityStatisticsSecAgentStatsNumSpiEntryFailureNoRemoteIp OBJECT-TYPE
    SYNTAX      ConfdString
    MAX-ACCESS  read-only
    STATUS      current
    DESCRIPTION "Number of spi entry fail due to no remote ip"
    ::= { affirmedSecurityStatisticsSecAgentStatsEntry 125 }

affirmedSecurityStatisticsSecAgentStatsNumSpiEntryNewAlreadyExists OBJECT-TYPE
    SYNTAX      ConfdString
    MAX-ACCESS  read-only
    STATUS      current
    DESCRIPTION "Number of spi entry new already exists"
    ::= { affirmedSecurityStatisticsSecAgentStatsEntry 126 }

affirmedSecurityStatisticsSecAgentStatsNumSpiEntryFailureInvalidSpi OBJECT-TYPE
    SYNTAX      ConfdString
    MAX-ACCESS  read-only
    STATUS      current
    DESCRIPTION "Number of invalid sp? failure"
    ::= { affirmedSecurityStatisticsSecAgentStatsEntry 127 }

affirmedSecurityStatisticsSecAgentStatsNumSessionEntryCreateFailNoResource OBJECT-TYPE
    SYNTAX      ConfdString
    MAX-ACCESS  read-only
    STATUS      current
    DESCRIPTION "Number of session create failure due to no resource"
    ::= { affirmedSecurityStatisticsSecAgentStatsEntry 128 }

affirmedSecurityStatisticsSecAgentStatsNumSessionEntryFailLookup OBJECT-TYPE
    SYNTAX      ConfdString
    MAX-ACCESS  read-only
    STATUS      current
    DESCRIPTION "Number of session entry lookup failure"
    ::= { affirmedSecurityStatisticsSecAgentStatsEntry 129 }

affirmedSecurityStatisticsSecAgentStatsNumSessionEntryDeleteNotFound OBJECT-TYPE
    SYNTAX      ConfdString
    MAX-ACCESS  read-only
    STATUS      current
    DESCRIPTION "Number of session entry delete not found"
    ::= { affirmedSecurityStatisticsSecAgentStatsEntry 130 }

affirmedSecurityStatisticsSecAgentStatsNumErrorDuplicateIngressEgress OBJECT-TYPE
    SYNTAX      ConfdString
    MAX-ACCESS  read-only
    STATUS      current
    DESCRIPTION "Number of duplicate ingress egress"
    ::= { affirmedSecurityStatisticsSecAgentStatsEntry 131 }

affirmedSecurityStatisticsSecAgentStatsNumDrainQueueError OBJECT-TYPE
    SYNTAX      ConfdString
    MAX-ACCESS  read-only
    STATUS      current
    DESCRIPTION "Number of drain queue error"
    ::= { affirmedSecurityStatisticsSecAgentStatsEntry 132 }

affirmedSecurityStatisticsSecAgentStatsNumFlowMaintenanceListError OBJECT-TYPE
    SYNTAX      ConfdString
    MAX-ACCESS  read-only
    STATUS      current
    DESCRIPTION "Number of flow maintenance list error"
    ::= { affirmedSecurityStatisticsSecAgentStatsEntry 133 }

affirmedSecurityStatisticsSecAgentStatsNumSpiTransformEntryCreateFailNoResource OBJECT-TYPE
    SYNTAX      ConfdString
    MAX-ACCESS  read-only
    STATUS      current
    DESCRIPTION "Number of transform entry create failure due to no resources"
    ::= { affirmedSecurityStatisticsSecAgentStatsEntry 134 }

affirmedSecurityStatisticsSecAgentStatsNumSpiTransformEntryCreateFailDuplicate OBJECT-TYPE
    SYNTAX      ConfdString
    MAX-ACCESS  read-only
    STATUS      current
    DESCRIPTION "Number of transform entry create failure duplicate"
    ::= { affirmedSecurityStatisticsSecAgentStatsEntry 135 }

affirmedSecurityStatisticsSecAgentStatsNumDequeueDrainPendingCollision OBJECT-TYPE
    SYNTAX      ConfdString
    MAX-ACCESS  read-only
    STATUS      current
    DESCRIPTION "Number dequeue drain pending collision"
    ::= { affirmedSecurityStatisticsSecAgentStatsEntry 136 }

affirmedSecurityStatisticsSecAgentStatsNumSkinnyFlowCreateDuplicate OBJECT-TYPE
    SYNTAX      ConfdString
    MAX-ACCESS  read-only
    STATUS      current
    DESCRIPTION "Number of skinny flow create duplicate"
    ::= { affirmedSecurityStatisticsSecAgentStatsEntry 137 }

affirmedSecurityStatisticsSecAgentStatsNumDequeueFlushPendingCollision OBJECT-TYPE
    SYNTAX      ConfdString
    MAX-ACCESS  read-only
    STATUS      current
    DESCRIPTION "Number dequeue flush pending collision"
    ::= { affirmedSecurityStatisticsSecAgentStatsEntry 138 }

affirmedSecurityStatisticsSecAgentStatsNumSkinnyFlowFailNoResources OBJECT-TYPE
    SYNTAX      ConfdString
    MAX-ACCESS  read-only
    STATUS      current
    DESCRIPTION "Number of skinny flow fail due to no resources"
    ::= { affirmedSecurityStatisticsSecAgentStatsEntry 139 }

affirmedSecurityStatisticsSecAgentStatsNumErrorNewFlowBusy OBJECT-TYPE
    SYNTAX      ConfdString
    MAX-ACCESS  read-only
    STATUS      current
    DESCRIPTION "Number new flow busy error"
    ::= { affirmedSecurityStatisticsSecAgentStatsEntry 140 }

affirmedSecurityStatisticsSecAgentStatsNumSpdNcAddFailCountAlloc OBJECT-TYPE
    SYNTAX      ConfdString
    MAX-ACCESS  read-only
    STATUS      current
    DESCRIPTION "Number SPD NC add allocation failure"
    ::= { affirmedSecurityStatisticsSecAgentStatsEntry 141 }

affirmedSecurityStatisticsSecAgentStatsNumSpdNcDelFailCountDuplicate OBJECT-TYPE
    SYNTAX      ConfdString
    MAX-ACCESS  read-only
    STATUS      current
    DESCRIPTION "Number SPD NC del duplicate failure"
    ::= { affirmedSecurityStatisticsSecAgentStatsEntry 142 }

affirmedSecurityStatisticsSecAgentStatsNumSpdNcDelFailCountDealloc OBJECT-TYPE
    SYNTAX      ConfdString
    MAX-ACCESS  read-only
    STATUS      current
    DESCRIPTION "Number SPD NC delete deallocation failure"
    ::= { affirmedSecurityStatisticsSecAgentStatsEntry 143 }

affirmedSecurityStatisticsSecAgentStatsNumSpdNcStaleDeleteCount OBJECT-TYPE
    SYNTAX      ConfdString
    MAX-ACCESS  read-only
    STATUS      current
    DESCRIPTION "Number SPD NC stale delete"
    ::= { affirmedSecurityStatisticsSecAgentStatsEntry 144 }

affirmedSecurityStatisticsSecAgentStatsNumSpdRuleAddFailCountNoNetCtxt OBJECT-TYPE
    SYNTAX      ConfdString
    MAX-ACCESS  read-only
    STATUS      current
    DESCRIPTION "Number SPD rule add failure due to no network context"
    ::= { affirmedSecurityStatisticsSecAgentStatsEntry 145 }

affirmedSecurityStatisticsSecAgentStatsNumSpdRuleAddFailCountAllocation OBJECT-TYPE
    SYNTAX      ConfdString
    MAX-ACCESS  read-only
    STATUS      current
    DESCRIPTION "Number SPD rule add allocation failure"
    ::= { affirmedSecurityStatisticsSecAgentStatsEntry 146 }

affirmedSecurityStatisticsSecAgentStatsNumSpdRuleModFailCountNoRule OBJECT-TYPE
    SYNTAX      ConfdString
    MAX-ACCESS  read-only
    STATUS      current
    DESCRIPTION "Number SPD rule modify failure no rule"
    ::= { affirmedSecurityStatisticsSecAgentStatsEntry 147 }

affirmedSecurityStatisticsSecAgentStatsNumSpdRuleDelFailCountNoNetCtxt OBJECT-TYPE
    SYNTAX      ConfdString
    MAX-ACCESS  read-only
    STATUS      current
    DESCRIPTION "Number SPD rule delete failure due to no network context"
    ::= { affirmedSecurityStatisticsSecAgentStatsEntry 148 }

affirmedSecurityStatisticsSecAgentStatsNumSpdRuleDelFailCountNoRule OBJECT-TYPE
    SYNTAX      ConfdString
    MAX-ACCESS  read-only
    STATUS      current
    DESCRIPTION "Number SPD rule delete failure no rule"
    ::= { affirmedSecurityStatisticsSecAgentStatsEntry 149 }

affirmedSecurityStatisticsSecAgentStatsNumSpdRuleLookupFailCountNoNetCtxt OBJECT-TYPE
    SYNTAX      ConfdString
    MAX-ACCESS  read-only
    STATUS      current
    DESCRIPTION "Number SPD rule lookup failure due to no network context"
    ::= { affirmedSecurityStatisticsSecAgentStatsEntry 150 }

affirmedSecurityStatisticsSecAgentStatsNumFpFlowsIngressCreateDuplicate OBJECT-TYPE
    SYNTAX      ConfdString
    MAX-ACCESS  read-only
    STATUS      current
    DESCRIPTION "Number FP ingress flows create duplicate"
    ::= { affirmedSecurityStatisticsSecAgentStatsEntry 151 }

affirmedSecurityStatisticsSecAgentStatsNumFpFlowsEgressCreateDuplicate OBJECT-TYPE
    SYNTAX      ConfdString
    MAX-ACCESS  read-only
    STATUS      current
    DESCRIPTION "Number FP egress flows create duplicate"
    ::= { affirmedSecurityStatisticsSecAgentStatsEntry 152 }

affirmedSecurityStatisticsSecAgentStatsNumFpFlowsModifyFail OBJECT-TYPE
    SYNTAX      ConfdString
    MAX-ACCESS  read-only
    STATUS      current
    DESCRIPTION "Number FP flows modify fail"
    ::= { affirmedSecurityStatisticsSecAgentStatsEntry 153 }

affirmedSecurityStatisticsSecAgentStatsNumFpFlowsDeleteFail OBJECT-TYPE
    SYNTAX      ConfdString
    MAX-ACCESS  read-only
    STATUS      current
    DESCRIPTION "Number FP flows del fail"
    ::= { affirmedSecurityStatisticsSecAgentStatsEntry 154 }

affirmedSecurityStatisticsSecAgentStatsNumFpFlowsFailNoResources OBJECT-TYPE
    SYNTAX      ConfdString
    MAX-ACCESS  read-only
    STATUS      current
    DESCRIPTION "Number FP flows fail due to no resources"
    ::= { affirmedSecurityStatisticsSecAgentStatsEntry 155 }

affirmedSecurityStatisticsSecAgentStatsNumFpFlowsFailNoTransform OBJECT-TYPE
    SYNTAX      ConfdString
    MAX-ACCESS  read-only
    STATUS      current
    DESCRIPTION "Number FP flows fail due to no transform"
    ::= { affirmedSecurityStatisticsSecAgentStatsEntry 156 }

affirmedSecurityStatisticsSecAgentStatsNumFpFlowsFailNcidMismatch OBJECT-TYPE
    SYNTAX      ConfdString
    MAX-ACCESS  read-only
    STATUS      current
    DESCRIPTION "Number FP flows fail due to ncid mismatch"
    ::= { affirmedSecurityStatisticsSecAgentStatsEntry 157 }

affirmedSecurityStatisticsSecAgentStatsNumFpFlowsFailNullFlowCreate OBJECT-TYPE
    SYNTAX      ConfdString
    MAX-ACCESS  read-only
    STATUS      current
    DESCRIPTION "Number FP flows fail null flow create"
    ::= { affirmedSecurityStatisticsSecAgentStatsEntry 158 }

affirmedSecurityStatisticsSecAgentStatsNumFpFlowsDuplicatedFpFlows OBJECT-TYPE
    SYNTAX      ConfdString
    MAX-ACCESS  read-only
    STATUS      current
    DESCRIPTION "Number FP flows duplicated"
    ::= { affirmedSecurityStatisticsSecAgentStatsEntry 159 }

affirmedSecurityStatisticsSecAgentStatsNumFpFlowsDuplicatedSpmFlows OBJECT-TYPE
    SYNTAX      ConfdString
    MAX-ACCESS  read-only
    STATUS      current
    DESCRIPTION "Number FP flows duplicated spm flows"
    ::= { affirmedSecurityStatisticsSecAgentStatsEntry 160 }

affirmedSecurityStatisticsSecAgentStatsNumSpmFlowsDuplicatedFpFlows OBJECT-TYPE
    SYNTAX      ConfdString
    MAX-ACCESS  read-only
    STATUS      current
    DESCRIPTION "Number SPM flows duplicated FP flows"
    ::= { affirmedSecurityStatisticsSecAgentStatsEntry 161 }

affirmedSecurityStatisticsSecAgentStatsNumOrphanedSpmFlowsDeleted OBJECT-TYPE
    SYNTAX      ConfdString
    MAX-ACCESS  read-only
    STATUS      current
    DESCRIPTION "Number orphaned SPM flows deleted"
    ::= { affirmedSecurityStatisticsSecAgentStatsEntry 162 }

affirmedSecurityStatisticsSecAgentStatsNumSpmFlowAssociatedRace OBJECT-TYPE
    SYNTAX      ConfdString
    MAX-ACCESS  read-only
    STATUS      current
    DESCRIPTION "Number SPM flow assoicated race"
    ::= { affirmedSecurityStatisticsSecAgentStatsEntry 163 }

affirmedSecurityStatisticsSecAgentStatsNumFlowRemovedFromHashLate OBJECT-TYPE
    SYNTAX      ConfdString
    MAX-ACCESS  read-only
    STATUS      current
    DESCRIPTION "Number flow removed from hash"
    ::= { affirmedSecurityStatisticsSecAgentStatsEntry 164 }

affirmedSecurityStatisticsSecAgentStatsNumSpdAddRuleCtrFail OBJECT-TYPE
    SYNTAX      ConfdString
    MAX-ACCESS  read-only
    STATUS      current
    DESCRIPTION "Number SPD add rule failure"
    ::= { affirmedSecurityStatisticsSecAgentStatsEntry 165 }

affirmedSecurityStatisticsSecAgentStatsNumSpdDelCtrNull OBJECT-TYPE
    SYNTAX      ConfdString
    MAX-ACCESS  read-only
    STATUS      current
    DESCRIPTION "Number SPD del counter null"
    ::= { affirmedSecurityStatisticsSecAgentStatsEntry 166 }

affirmedSecurityStatisticsSecAgentStatsNumFpFlowsEgressMoveToHashFail OBJECT-TYPE
    SYNTAX      ConfdString
    MAX-ACCESS  read-only
    STATUS      current
    DESCRIPTION "Number of FP egress flows moved to hash failure"
    ::= { affirmedSecurityStatisticsSecAgentStatsEntry 167 }

affirmedSecurityStatisticsSecAgentStatsNumSpdRuleAddIgnoreCountNcMisMatch OBJECT-TYPE
    SYNTAX      ConfdString
    MAX-ACCESS  read-only
    STATUS      current
    DESCRIPTION "Number of Add Rule ignored because of NC mismatch"
    ::= { affirmedSecurityStatisticsSecAgentStatsEntry 168 }

affirmedSecurityStatisticsCpu-levelDataStatsTable OBJECT-TYPE
    SYNTAX      SEQUENCE OF AffirmedSecurityStatisticsCpu-levelDataStatsEntry
    MAX-ACCESS  not-accessible
    STATUS      deprecated
    DESCRIPTION ""
    ::= { affirmedSecurityStatisticsCpu-level 1 }

affirmedSecurityStatisticsCpu-levelDataStatsEntry OBJECT-TYPE
    SYNTAX      AffirmedSecurityStatisticsCpu-levelDataStatsEntry
    MAX-ACCESS  not-accessible
    STATUS      deprecated
    DESCRIPTION ""
    INDEX { affirmedSecurityStatisticsCpu-levelDataStatsSlot, affirmedSecurityStatisticsCpu-levelDataStatsCpuid }
        ::= { affirmedSecurityStatisticsCpu-levelDataStatsTable 1 }

AffirmedSecurityStatisticsCpu-levelDataStatsEntry ::=
    SEQUENCE {
        affirmedSecurityStatisticsCpu-levelDataStatsSlot Unsigned32,
        affirmedSecurityStatisticsCpu-levelDataStatsCpuid Unsigned32,
        affirmedSecurityStatisticsCpu-levelDataStatsNonErrorDelimiter String,
        affirmedSecurityStatisticsCpu-levelDataStatsRxV4Pkts ConfdString,
        affirmedSecurityStatisticsCpu-levelDataStatsRxV4Bytes ConfdString,
        affirmedSecurityStatisticsCpu-levelDataStatsRxPostSecurityV4Pkts ConfdString,
        affirmedSecurityStatisticsCpu-levelDataStatsRxPostSecurityV4Bytes ConfdString,
        affirmedSecurityStatisticsCpu-levelDataStatsRxV6Pkts ConfdString,
        affirmedSecurityStatisticsCpu-levelDataStatsRxV6Bytes ConfdString,
        affirmedSecurityStatisticsCpu-levelDataStatsRxPostSecurityV6Pkts ConfdString,
        affirmedSecurityStatisticsCpu-levelDataStatsRxPostSecurityV6Bytes ConfdString,
        affirmedSecurityStatisticsCpu-levelDataStatsRxEspPkts ConfdString,
        affirmedSecurityStatisticsCpu-levelDataStatsRxAhPkts ConfdString,
        affirmedSecurityStatisticsCpu-levelDataStatsRxRemoteSecmPkts ConfdString,
        affirmedSecurityStatisticsCpu-levelDataStatsRxSecmIngTransPkts ConfdString,
        affirmedSecurityStatisticsCpu-levelDataStatsRxSecmEgrTransPkts ConfdString,
        affirmedSecurityStatisticsCpu-levelDataStatsRxSpmPkts ConfdString,
        affirmedSecurityStatisticsCpu-levelDataStatsFwdRemoteSecmPkts ConfdString,
        affirmedSecurityStatisticsCpu-levelDataStatsRxRemoteSecmSpmPkts ConfdString,
        affirmedSecurityStatisticsCpu-levelDataStatsFwdRemoteSecmSpmPkts ConfdString,
        affirmedSecurityStatisticsCpu-levelDataStatsFwdSpmPkts ConfdString,
        affirmedSecurityStatisticsCpu-levelDataStatsRxBypassRulePkts ConfdString,
        affirmedSecurityStatisticsCpu-levelDataStatsTxBypassRulePkts ConfdString,
        affirmedSecurityStatisticsCpu-levelDataStatsFwdPkts ConfdString,
        affirmedSecurityStatisticsCpu-levelDataStatsTxV4Pkts ConfdString,
        affirmedSecurityStatisticsCpu-levelDataStatsTxV4Bytes ConfdString,
        affirmedSecurityStatisticsCpu-levelDataStatsTxV6Pkts ConfdString,
        affirmedSecurityStatisticsCpu-levelDataStatsTxV6Bytes ConfdString,
        affirmedSecurityStatisticsCpu-levelDataStatsTxEspPkts ConfdString,
        affirmedSecurityStatisticsCpu-levelDataStatsTxAhPkts ConfdString,
        affirmedSecurityStatisticsCpu-levelDataStatsIdleFlowsReported ConfdString,
        affirmedSecurityStatisticsCpu-levelDataStatsTransactionsAllocated ConfdString,
        affirmedSecurityStatisticsCpu-levelDataStatsTransactionsDeallocated ConfdString,
        affirmedSecurityStatisticsCpu-levelDataStatsHdwTotIn ConfdString,
        affirmedSecurityStatisticsCpu-levelDataStatsHdwTotOut ConfdString,
        affirmedSecurityStatisticsCpu-levelDataStatsHdwEncIn ConfdString,
        affirmedSecurityStatisticsCpu-levelDataStatsHdwEncOut ConfdString,
        affirmedSecurityStatisticsCpu-levelDataStatsHdwDecIn ConfdString,
        affirmedSecurityStatisticsCpu-levelDataStatsHdwDecOut ConfdString,
        affirmedSecurityStatisticsCpu-levelDataStatsQueuedPkts ConfdString,
        affirmedSecurityStatisticsCpu-levelDataStatsDequeuedPkts ConfdString,
        affirmedSecurityStatisticsCpu-levelDataStatsErrorDelimiter String,
        affirmedSecurityStatisticsCpu-levelDataStatsRxV4DropPkts ConfdString,
        affirmedSecurityStatisticsCpu-levelDataStatsRxV4DropBytes ConfdString,
        affirmedSecurityStatisticsCpu-levelDataStatsRxV6DropPkts ConfdString,
        affirmedSecurityStatisticsCpu-levelDataStatsRxV6DropBytes ConfdString,
        affirmedSecurityStatisticsCpu-levelDataStatsRxSpmPktsIgnored ConfdString,
        affirmedSecurityStatisticsCpu-levelDataStatsRxSpmNoFlowPkts ConfdString,
        affirmedSecurityStatisticsCpu-levelDataStatsSecmSpmEgrPktsFwdFail ConfdString,
        affirmedSecurityStatisticsCpu-levelDataStatsSecmIngPktsFwdFail ConfdString,
        affirmedSecurityStatisticsCpu-levelDataStatsSecmEgrPktsFwdFail ConfdString,
        affirmedSecurityStatisticsCpu-levelDataStatsFwdSpmNoFlowPkts ConfdString,
        affirmedSecurityStatisticsCpu-levelDataStatsTxV4DropPkts ConfdString,
        affirmedSecurityStatisticsCpu-levelDataStatsTxV4DropBytes ConfdString,
        affirmedSecurityStatisticsCpu-levelDataStatsTxV6DropPkts ConfdString,
        affirmedSecurityStatisticsCpu-levelDataStatsTxV6DropBytes ConfdString,
        affirmedSecurityStatisticsCpu-levelDataStatsDropPktsRule ConfdString,
        affirmedSecurityStatisticsCpu-levelDataStatsDropPktsRejectRule ConfdString,
        affirmedSecurityStatisticsCpu-levelDataStatsDropPktsNoRule ConfdString,
        affirmedSecurityStatisticsCpu-levelDataStatsDropPktsTriggerRule ConfdString,
        affirmedSecurityStatisticsCpu-levelDataStatsRemoteTransError ConfdString,
        affirmedSecurityStatisticsCpu-levelDataStatsInvalidHeaderError ConfdString,
        affirmedSecurityStatisticsCpu-levelDataStatsRxPendingFlowError ConfdString,
        affirmedSecurityStatisticsCpu-levelDataStatsTxPendingFlowError ConfdString,
        affirmedSecurityStatisticsCpu-levelDataStatsNoFlowError ConfdString,
        affirmedSecurityStatisticsCpu-levelDataStatsTransNotFoundError ConfdString,
        affirmedSecurityStatisticsCpu-levelDataStatsDropPktsTooBig ConfdString,
        affirmedSecurityStatisticsCpu-levelDataStatsBadHandle ConfdString,
        affirmedSecurityStatisticsCpu-levelDataStatsIngCtxtInUse ConfdString,
        affirmedSecurityStatisticsCpu-levelDataStatsFailedSanity ConfdString,
        affirmedSecurityStatisticsCpu-levelDataStatsFlushedPkts ConfdString,
        affirmedSecurityStatisticsCpu-levelDataStatsDropPktsIntfNotFound ConfdString,
        affirmedSecurityStatisticsCpu-levelDataStatsDropPktsSessionNotFound ConfdString,
        affirmedSecurityStatisticsCpu-levelDataStatsDropPktsTransactionNotFound ConfdString,
        affirmedSecurityStatisticsCpu-levelDataStatsTransactionsDeallocFailed ConfdString,
        affirmedSecurityStatisticsCpu-levelDataStatsInvalidNumaNode ConfdString,
        affirmedSecurityStatisticsCpu-levelDataStatsFlowAccessTimeFix ConfdString,
        affirmedSecurityStatisticsCpu-levelDataStatsPendingFlowAccessTimeFix ConfdString,
        affirmedSecurityStatisticsCpu-levelDataStatsHdwBadIcvIngressIom ConfdString,
        affirmedSecurityStatisticsCpu-levelDataStatsHdwBadIcvIngressSecm ConfdString,
        affirmedSecurityStatisticsCpu-levelDataStatsIngSpiMismatch ConfdString,
        affirmedSecurityStatisticsCpu-levelDataStatsEgrSpiMismatch ConfdString,
        affirmedSecurityStatisticsCpu-levelDataStatsTransAuthErrs ConfdString,
        affirmedSecurityStatisticsCpu-levelDataStatsPostSecTransAuthErrs ConfdString,
        affirmedSecurityStatisticsCpu-levelDataStatsPostSecPktErrs ConfdString,
        affirmedSecurityStatisticsCpu-levelDataStatsPostSecIntfPktErrs ConfdString,
        affirmedSecurityStatisticsCpu-levelDataStatsPostSecFpPktErrs ConfdString,
        affirmedSecurityStatisticsCpu-levelDataStatsNoFlowPassAtRemoteSecm ConfdString,
        affirmedSecurityStatisticsCpu-levelDataStatsCreateFlowWithoutSpmForward ConfdString,
        affirmedSecurityStatisticsCpu-levelDataStatsEspSpiMismatchError ConfdString,
        affirmedSecurityStatisticsCpu-levelDataStatsAhSpiMismatchError ConfdString,
        affirmedSecurityStatisticsCpu-levelDataStatsCipherNotFoundError ConfdString,
        affirmedSecurityStatisticsCpu-levelDataStatsAuthNotFoundError ConfdString,
        affirmedSecurityStatisticsCpu-levelDataStatsPktDataAccessError ConfdString,
        affirmedSecurityStatisticsCpu-levelDataStatsPktSizeCipherSizeError ConfdString,
        affirmedSecurityStatisticsCpu-levelDataStatsPktTooShortError ConfdString,
        affirmedSecurityStatisticsCpu-levelDataStatsPktLenMismatchError ConfdString,
        affirmedSecurityStatisticsCpu-levelDataStatsParsePktHeaderError ConfdString,
        affirmedSecurityStatisticsCpu-levelDataStatsCalcPktInfoError ConfdString,
        affirmedSecurityStatisticsCpu-levelDataStatsPrelimAntiReplayErrLo ConfdString,
        affirmedSecurityStatisticsCpu-levelDataStatsPrelimAntiReplayError ConfdString,
        affirmedSecurityStatisticsCpu-levelDataStatsEspSeqNumError ConfdString,
        affirmedSecurityStatisticsCpu-levelDataStatsEspSeqSecm ConfdString,
        affirmedSecurityStatisticsCpu-levelDataStatsEspSeqNumLow ConfdString,
        affirmedSecurityStatisticsCpu-levelDataStatsAhSeqNumError ConfdString,
        affirmedSecurityStatisticsCpu-levelDataStatsAppendSeqHighError ConfdString,
        affirmedSecurityStatisticsCpu-levelDataStatsDeleteSeqHighError ConfdString,
        affirmedSecurityStatisticsCpu-levelDataStatsIcvComputeError ConfdString,
        affirmedSecurityStatisticsCpu-levelDataStatsIcvCheckError ConfdString,
        affirmedSecurityStatisticsCpu-levelDataStatsIcvLenError ConfdString,
        affirmedSecurityStatisticsCpu-levelDataStatsEspIcvAuthError ConfdString,
        affirmedSecurityStatisticsCpu-levelDataStatsEspPadError ConfdString,
        affirmedSecurityStatisticsCpu-levelDataStatsAhIcvAuthError ConfdString,
        affirmedSecurityStatisticsCpu-levelDataStatsEspTransChainError ConfdString,
        affirmedSecurityStatisticsCpu-levelDataStatsEspProcessAadError ConfdString,
        affirmedSecurityStatisticsCpu-levelDataStatsTransFinishError ConfdString,
        affirmedSecurityStatisticsCpu-levelDataStatsAuthAddRangeError ConfdString,
        affirmedSecurityStatisticsCpu-levelDataStatsAuthFinishError ConfdString,
        affirmedSecurityStatisticsCpu-levelDataStatsCipherUpdateError ConfdString,
        affirmedSecurityStatisticsCpu-levelDataStatsAhSeqNumOverflowError ConfdString,
        affirmedSecurityStatisticsCpu-levelDataStatsEspSeqNumOverflowError ConfdString,
        affirmedSecurityStatisticsCpu-levelDataStatsNumIngCryptoAllocFail ConfdString,
        affirmedSecurityStatisticsCpu-levelDataStatsNumEgrCryptoAllocFail ConfdString,
        affirmedSecurityStatisticsCpu-levelDataStatsNumGetNextHopFail ConfdString,
        affirmedSecurityStatisticsCpu-levelDataStatsBypassV4IkeFragment ConfdString,
        affirmedSecurityStatisticsCpu-levelDataStatsBypassV4OSPF ConfdString,
        affirmedSecurityStatisticsCpu-levelDataStatsBypassV4Multicast ConfdString,
        affirmedSecurityStatisticsCpu-levelDataStatsBypassV6LinkLocalDest ConfdString,
        affirmedSecurityStatisticsCpu-levelDataStatsBypassV6LinkLocalSrc ConfdString,
        affirmedSecurityStatisticsCpu-levelDataStatsBypassTid0V6Icmp ConfdString,
        affirmedSecurityStatisticsCpu-levelDataStatsBypassTid0IngressIke ConfdString,
        affirmedSecurityStatisticsCpu-levelDataStatsBypassTid0IngressIkeNatt ConfdString,
        affirmedSecurityStatisticsCpu-levelDataStatsBypassTid0IngressV4DhcpClient ConfdString,
        affirmedSecurityStatisticsCpu-levelDataStatsBypassTid0EgressV4DnsClient ConfdString,
        affirmedSecurityStatisticsCpu-levelDataStatsBypassTid1IngressUdp ConfdString,
        affirmedSecurityStatisticsCpu-levelDataStatsIngressIke ConfdString,
        affirmedSecurityStatisticsCpu-levelDataStatsIngressIkeNatt ConfdString,
        affirmedSecurityStatisticsCpu-levelDataStatsEgressIke ConfdString,
        affirmedSecurityStatisticsCpu-levelDataStatsEgressIkeNatt ConfdString,
        affirmedSecurityStatisticsCpu-levelDataStatsPassRuleHits ConfdString,
        affirmedSecurityStatisticsCpu-levelDataStatsApplyRuleHits ConfdString,
        affirmedSecurityStatisticsCpu-levelDataStatsRxNattKaPkts ConfdString,
        affirmedSecurityStatisticsCpu-levelDataStatsUseableRuleHits ConfdString,
        affirmedSecurityStatisticsCpu-levelDataStatsDropPktsWrongRule ConfdString,
        affirmedSecurityStatisticsCpu-levelDataStatsDropPktsOnWrongTunnel ConfdString,
        affirmedSecurityStatisticsCpu-levelDataStatsNoFlowErrorIngress ConfdString,
        affirmedSecurityStatisticsCpu-levelDataStatsNoFlowErrorEgress ConfdString,
        affirmedSecurityStatisticsCpu-levelDataStatsPktsDiscarded ConfdString,
        affirmedSecurityStatisticsCpu-levelDataStatsNoFlowPassDrop ConfdString,
        affirmedSecurityStatisticsCpu-levelDataStatsNoFlowTid0IngressIPsec ConfdString,
        affirmedSecurityStatisticsCpu-levelDataStatsSpiEntryFailLookup ConfdString,
        affirmedSecurityStatisticsCpu-levelDataStatsDropPktsSecurityDisabled ConfdString,
        affirmedSecurityStatisticsCpu-levelDataStatsUnuseableRuleHits ConfdString,
        affirmedSecurityStatisticsCpu-levelDataStatsDropRuleHits ConfdString,
        affirmedSecurityStatisticsCpu-levelDataStatsRejectRuleHits ConfdString,
        affirmedSecurityStatisticsCpu-levelDataStatsInvalidRuleHits ConfdString,
        affirmedSecurityStatisticsCpu-levelDataStatsDormantApplyRuleHits ConfdString,
        affirmedSecurityStatisticsCpu-levelDataStatsUnknownRuleHits ConfdString,
        affirmedSecurityStatisticsCpu-levelDataStatsPostSecPktErrsInvalidHeader ConfdString,
        affirmedSecurityStatisticsCpu-levelDataStatsPostSecPktErrsInvalidFragHeader ConfdString,
        affirmedSecurityStatisticsCpu-levelDataStatsPostSecPktErrsNoFlowFound ConfdString,
        affirmedSecurityStatisticsCpu-levelDataStatsPostSecPktErrsBadFlowFound ConfdString,
        affirmedSecurityStatisticsCpu-levelDataStatsPostSecPktErrsUnexpectedPendFlow ConfdString,
        affirmedSecurityStatisticsCpu-levelDataStatsPostSecPktErrsUnexpectedApplyFlow ConfdString,
        affirmedSecurityStatisticsCpu-levelDataStatsPostSecPktErrsUnexpectedRejectFlow ConfdString,
        affirmedSecurityStatisticsCpu-levelDataStatsPostSecPktErrsUnexpectedTriggerFlow ConfdString,
        affirmedSecurityStatisticsCpu-levelDataStatsPostSecPktErrsUnexpectedDropFlow ConfdString,
        affirmedSecurityStatisticsCpu-levelDataStatsPostSecPktErrsUnexpectedNonExistentFlow ConfdString,
        affirmedSecurityStatisticsCpu-levelDataStatsDropPktsDropRule ConfdString,
        affirmedSecurityStatisticsCpu-levelDataStatsNullSpiEntry ConfdString,
        affirmedSecurityStatisticsCpu-levelDataStatsInvalidFSAPI ConfdString
    }

affirmedSecurityStatisticsCpu-levelDataStatsSlot OBJECT-TYPE
    SYNTAX      Unsigned32
    MAX-ACCESS  not-accessible
    STATUS      current
    DESCRIPTION "Slot number"
    ::= { affirmedSecurityStatisticsCpu-levelDataStatsEntry 1 }

affirmedSecurityStatisticsCpu-levelDataStatsCpuid OBJECT-TYPE
    SYNTAX      Unsigned32
    MAX-ACCESS  not-accessible
    STATUS      current
    DESCRIPTION "cpu number"
    ::= { affirmedSecurityStatisticsCpu-levelDataStatsEntry 2 }

affirmedSecurityStatisticsCpu-levelDataStatsNonErrorDelimiter OBJECT-TYPE
    SYNTAX      String
    MAX-ACCESS  read-only
    STATUS      current
    DESCRIPTION "Separate non-error from error stats"
    ::= { affirmedSecurityStatisticsCpu-levelDataStatsEntry 3 }

affirmedSecurityStatisticsCpu-levelDataStatsRxV4Pkts OBJECT-TYPE
    SYNTAX      ConfdString
    MAX-ACCESS  read-only
    STATUS      current
    DESCRIPTION "Ingress IPv4 packets successfully processed "
    ::= { affirmedSecurityStatisticsCpu-levelDataStatsEntry 4 }

affirmedSecurityStatisticsCpu-levelDataStatsRxV4Bytes OBJECT-TYPE
    SYNTAX      ConfdString
    MAX-ACCESS  read-only
    STATUS      current
    DESCRIPTION "Ingress IPv4 bytes successfully processed "
    ::= { affirmedSecurityStatisticsCpu-levelDataStatsEntry 5 }

affirmedSecurityStatisticsCpu-levelDataStatsRxPostSecurityV4Pkts OBJECT-TYPE
    SYNTAX      ConfdString
    MAX-ACCESS  read-only
    STATUS      current
    DESCRIPTION "Dequeued ingress IPv4 packets successfully processed "
    ::= { affirmedSecurityStatisticsCpu-levelDataStatsEntry 6 }

affirmedSecurityStatisticsCpu-levelDataStatsRxPostSecurityV4Bytes OBJECT-TYPE
    SYNTAX      ConfdString
    MAX-ACCESS  read-only
    STATUS      current
    DESCRIPTION "Dequeued ingress IPv4 bytes successfully processed "
    ::= { affirmedSecurityStatisticsCpu-levelDataStatsEntry 7 }

affirmedSecurityStatisticsCpu-levelDataStatsRxV6Pkts OBJECT-TYPE
    SYNTAX      ConfdString
    MAX-ACCESS  read-only
    STATUS      current
    DESCRIPTION "Ingress IPv6 packets successfully processed "
    ::= { affirmedSecurityStatisticsCpu-levelDataStatsEntry 8 }

affirmedSecurityStatisticsCpu-levelDataStatsRxV6Bytes OBJECT-TYPE
    SYNTAX      ConfdString
    MAX-ACCESS  read-only
    STATUS      current
    DESCRIPTION "Ingress IPv6 bytes successfully processed "
    ::= { affirmedSecurityStatisticsCpu-levelDataStatsEntry 9 }

affirmedSecurityStatisticsCpu-levelDataStatsRxPostSecurityV6Pkts OBJECT-TYPE
    SYNTAX      ConfdString
    MAX-ACCESS  read-only
    STATUS      current
    DESCRIPTION "Dequeued ingress IPv6 packets successfully processed "
    ::= { affirmedSecurityStatisticsCpu-levelDataStatsEntry 10 }

affirmedSecurityStatisticsCpu-levelDataStatsRxPostSecurityV6Bytes OBJECT-TYPE
    SYNTAX      ConfdString
    MAX-ACCESS  read-only
    STATUS      current
    DESCRIPTION "Dequeued ingress IPv6 bytes successfully processed "
    ::= { affirmedSecurityStatisticsCpu-levelDataStatsEntry 11 }

affirmedSecurityStatisticsCpu-levelDataStatsRxEspPkts OBJECT-TYPE
    SYNTAX      ConfdString
    MAX-ACCESS  read-only
    STATUS      current
    DESCRIPTION "Authenticated and decrypted packets (ESP) received"
    ::= { affirmedSecurityStatisticsCpu-levelDataStatsEntry 12 }

affirmedSecurityStatisticsCpu-levelDataStatsRxAhPkts OBJECT-TYPE
    SYNTAX      ConfdString
    MAX-ACCESS  read-only
    STATUS      current
    DESCRIPTION "Authenticated (AH) packets received"
    ::= { affirmedSecurityStatisticsCpu-levelDataStatsEntry 13 }

affirmedSecurityStatisticsCpu-levelDataStatsRxRemoteSecmPkts OBJECT-TYPE
    SYNTAX      ConfdString
    MAX-ACCESS  read-only
    STATUS      current
    DESCRIPTION "Total packets from other SSM"
    ::= { affirmedSecurityStatisticsCpu-levelDataStatsEntry 14 }

affirmedSecurityStatisticsCpu-levelDataStatsRxSecmIngTransPkts OBJECT-TYPE
    SYNTAX      ConfdString
    MAX-ACCESS  read-only
    STATUS      current
    DESCRIPTION "Ingress packets from other SSM"
    ::= { affirmedSecurityStatisticsCpu-levelDataStatsEntry 15 }

affirmedSecurityStatisticsCpu-levelDataStatsRxSecmEgrTransPkts OBJECT-TYPE
    SYNTAX      ConfdString
    MAX-ACCESS  read-only
    STATUS      current
    DESCRIPTION "Egress packets from other SSM"
    ::= { affirmedSecurityStatisticsCpu-levelDataStatsEntry 16 }

affirmedSecurityStatisticsCpu-levelDataStatsRxSpmPkts OBJECT-TYPE
    SYNTAX      ConfdString
    MAX-ACCESS  read-only
    STATUS      current
    DESCRIPTION "Total packets from SPM"
    ::= { affirmedSecurityStatisticsCpu-levelDataStatsEntry 17 }

affirmedSecurityStatisticsCpu-levelDataStatsFwdRemoteSecmPkts OBJECT-TYPE
    SYNTAX      ConfdString
    MAX-ACCESS  read-only
    STATUS      current
    DESCRIPTION "Egress packets sent to other SSM"
    ::= { affirmedSecurityStatisticsCpu-levelDataStatsEntry 18 }

affirmedSecurityStatisticsCpu-levelDataStatsRxRemoteSecmSpmPkts OBJECT-TYPE
    SYNTAX      ConfdString
    MAX-ACCESS  read-only
    STATUS      current
    DESCRIPTION "Egress WF packets from other SSM"
    ::= { affirmedSecurityStatisticsCpu-levelDataStatsEntry 19 }

affirmedSecurityStatisticsCpu-levelDataStatsFwdRemoteSecmSpmPkts OBJECT-TYPE
    SYNTAX      ConfdString
    MAX-ACCESS  read-only
    STATUS      current
    DESCRIPTION "Egress WF packets sent to other SSM"
    ::= { affirmedSecurityStatisticsCpu-levelDataStatsEntry 20 }

affirmedSecurityStatisticsCpu-levelDataStatsFwdSpmPkts OBJECT-TYPE
    SYNTAX      ConfdString
    MAX-ACCESS  read-only
    STATUS      current
    DESCRIPTION "Packets forwarded to SPM"
    ::= { affirmedSecurityStatisticsCpu-levelDataStatsEntry 21 }

affirmedSecurityStatisticsCpu-levelDataStatsRxBypassRulePkts OBJECT-TYPE
    SYNTAX      ConfdString
    MAX-ACCESS  read-only
    STATUS      current
    DESCRIPTION "Packets received that bypass security"
    ::= { affirmedSecurityStatisticsCpu-levelDataStatsEntry 22 }

affirmedSecurityStatisticsCpu-levelDataStatsTxBypassRulePkts OBJECT-TYPE
    SYNTAX      ConfdString
    MAX-ACCESS  read-only
    STATUS      current
    DESCRIPTION "WF Packets from other SSM that bypass security"
    ::= { affirmedSecurityStatisticsCpu-levelDataStatsEntry 23 }

affirmedSecurityStatisticsCpu-levelDataStatsFwdPkts OBJECT-TYPE
    SYNTAX      ConfdString
    MAX-ACCESS  read-only
    STATUS      current
    DESCRIPTION "Egress IPv4 packets successfully processed "
    ::= { affirmedSecurityStatisticsCpu-levelDataStatsEntry 24 }

affirmedSecurityStatisticsCpu-levelDataStatsTxV4Pkts OBJECT-TYPE
    SYNTAX      ConfdString
    MAX-ACCESS  read-only
    STATUS      current
    DESCRIPTION "Egress IPv4 packets successfully processed "
    ::= { affirmedSecurityStatisticsCpu-levelDataStatsEntry 25 }

affirmedSecurityStatisticsCpu-levelDataStatsTxV4Bytes OBJECT-TYPE
    SYNTAX      ConfdString
    MAX-ACCESS  read-only
    STATUS      current
    DESCRIPTION "Egress IPv4 bytes successfully processed "
    ::= { affirmedSecurityStatisticsCpu-levelDataStatsEntry 26 }

affirmedSecurityStatisticsCpu-levelDataStatsTxV6Pkts OBJECT-TYPE
    SYNTAX      ConfdString
    MAX-ACCESS  read-only
    STATUS      current
    DESCRIPTION "Egress IPv6 packets successfully processed "
    ::= { affirmedSecurityStatisticsCpu-levelDataStatsEntry 27 }

affirmedSecurityStatisticsCpu-levelDataStatsTxV6Bytes OBJECT-TYPE
    SYNTAX      ConfdString
    MAX-ACCESS  read-only
    STATUS      current
    DESCRIPTION "Egress IPv6 bytes successfully processed "
    ::= { affirmedSecurityStatisticsCpu-levelDataStatsEntry 28 }

affirmedSecurityStatisticsCpu-levelDataStatsTxEspPkts OBJECT-TYPE
    SYNTAX      ConfdString
    MAX-ACCESS  read-only
    STATUS      current
    DESCRIPTION "Packets to be encrypted and authentication calculated"
    ::= { affirmedSecurityStatisticsCpu-levelDataStatsEntry 29 }

affirmedSecurityStatisticsCpu-levelDataStatsTxAhPkts OBJECT-TYPE
    SYNTAX      ConfdString
    MAX-ACCESS  read-only
    STATUS      current
    DESCRIPTION "Packets to have just authentication calculated"
    ::= { affirmedSecurityStatisticsCpu-levelDataStatsEntry 30 }

affirmedSecurityStatisticsCpu-levelDataStatsIdleFlowsReported OBJECT-TYPE
    SYNTAX      ConfdString
    MAX-ACCESS  read-only
    STATUS      current
    DESCRIPTION "Flows reported without traffic for 30 seconds"
    ::= { affirmedSecurityStatisticsCpu-levelDataStatsEntry 31 }

affirmedSecurityStatisticsCpu-levelDataStatsTransactionsAllocated OBJECT-TYPE
    SYNTAX      ConfdString
    MAX-ACCESS  read-only
    STATUS      current
    DESCRIPTION "Transactions Allocated"
    ::= { affirmedSecurityStatisticsCpu-levelDataStatsEntry 32 }

affirmedSecurityStatisticsCpu-levelDataStatsTransactionsDeallocated OBJECT-TYPE
    SYNTAX      ConfdString
    MAX-ACCESS  read-only
    STATUS      current
    DESCRIPTION "TransactionsDeallocated"
    ::= { affirmedSecurityStatisticsCpu-levelDataStatsEntry 33 }

affirmedSecurityStatisticsCpu-levelDataStatsHdwTotIn OBJECT-TYPE
    SYNTAX      ConfdString
    MAX-ACCESS  read-only
    STATUS      current
    DESCRIPTION "Packets sent to SAE"
    ::= { affirmedSecurityStatisticsCpu-levelDataStatsEntry 34 }

affirmedSecurityStatisticsCpu-levelDataStatsHdwTotOut OBJECT-TYPE
    SYNTAX      ConfdString
    MAX-ACCESS  read-only
    STATUS      current
    DESCRIPTION "Packets returned from SAE"
    ::= { affirmedSecurityStatisticsCpu-levelDataStatsEntry 35 }

affirmedSecurityStatisticsCpu-levelDataStatsHdwEncIn OBJECT-TYPE
    SYNTAX      ConfdString
    MAX-ACCESS  read-only
    STATUS      current
    DESCRIPTION "Packets sent to SAE for Encryption"
    ::= { affirmedSecurityStatisticsCpu-levelDataStatsEntry 36 }

affirmedSecurityStatisticsCpu-levelDataStatsHdwEncOut OBJECT-TYPE
    SYNTAX      ConfdString
    MAX-ACCESS  read-only
    STATUS      current
    DESCRIPTION "Encrypted packets returned from SAE"
    ::= { affirmedSecurityStatisticsCpu-levelDataStatsEntry 37 }

affirmedSecurityStatisticsCpu-levelDataStatsHdwDecIn OBJECT-TYPE
    SYNTAX      ConfdString
    MAX-ACCESS  read-only
    STATUS      current
    DESCRIPTION "Packets sent to SAE for Decryption"
    ::= { affirmedSecurityStatisticsCpu-levelDataStatsEntry 38 }

affirmedSecurityStatisticsCpu-levelDataStatsHdwDecOut OBJECT-TYPE
    SYNTAX      ConfdString
    MAX-ACCESS  read-only
    STATUS      current
    DESCRIPTION "Decrypted packets returned from SAE"
    ::= { affirmedSecurityStatisticsCpu-levelDataStatsEntry 39 }

affirmedSecurityStatisticsCpu-levelDataStatsQueuedPkts OBJECT-TYPE
    SYNTAX      ConfdString
    MAX-ACCESS  read-only
    STATUS      current
    DESCRIPTION "Packets queued waiting for SPM to validate flow"
    ::= { affirmedSecurityStatisticsCpu-levelDataStatsEntry 40 }

affirmedSecurityStatisticsCpu-levelDataStatsDequeuedPkts OBJECT-TYPE
    SYNTAX      ConfdString
    MAX-ACCESS  read-only
    STATUS      current
    DESCRIPTION "Packets dequeued when SPM validates flow"
    ::= { affirmedSecurityStatisticsCpu-levelDataStatsEntry 41 }

affirmedSecurityStatisticsCpu-levelDataStatsErrorDelimiter OBJECT-TYPE
    SYNTAX      String
    MAX-ACCESS  read-only
    STATUS      current
    DESCRIPTION "Separate non-error from error stats"
    ::= { affirmedSecurityStatisticsCpu-levelDataStatsEntry 42 }

affirmedSecurityStatisticsCpu-levelDataStatsRxV4DropPkts OBJECT-TYPE
    SYNTAX      ConfdString
    MAX-ACCESS  read-only
    STATUS      current
    DESCRIPTION "Ingress IPv4 packets dropped"
    ::= { affirmedSecurityStatisticsCpu-levelDataStatsEntry 43 }

affirmedSecurityStatisticsCpu-levelDataStatsRxV4DropBytes OBJECT-TYPE
    SYNTAX      ConfdString
    MAX-ACCESS  read-only
    STATUS      current
    DESCRIPTION "Ingress IPv4 bytes dropped"
    ::= { affirmedSecurityStatisticsCpu-levelDataStatsEntry 44 }

affirmedSecurityStatisticsCpu-levelDataStatsRxV6DropPkts OBJECT-TYPE
    SYNTAX      ConfdString
    MAX-ACCESS  read-only
    STATUS      current
    DESCRIPTION "Ingress IPv6 packets dropped"
    ::= { affirmedSecurityStatisticsCpu-levelDataStatsEntry 45 }

affirmedSecurityStatisticsCpu-levelDataStatsRxV6DropBytes OBJECT-TYPE
    SYNTAX      ConfdString
    MAX-ACCESS  read-only
    STATUS      current
    DESCRIPTION "Ingress IPv6 bytes dropped"
    ::= { affirmedSecurityStatisticsCpu-levelDataStatsEntry 46 }

affirmedSecurityStatisticsCpu-levelDataStatsRxSpmPktsIgnored OBJECT-TYPE
    SYNTAX      ConfdString
    MAX-ACCESS  read-only
    STATUS      current
    DESCRIPTION "Packets from SPM ignored"
    ::= { affirmedSecurityStatisticsCpu-levelDataStatsEntry 47 }

affirmedSecurityStatisticsCpu-levelDataStatsRxSpmNoFlowPkts OBJECT-TYPE
    SYNTAX      ConfdString
    MAX-ACCESS  read-only
    STATUS      current
    DESCRIPTION "Egress WF packets with no flow"
    ::= { affirmedSecurityStatisticsCpu-levelDataStatsEntry 48 }

affirmedSecurityStatisticsCpu-levelDataStatsSecmSpmEgrPktsFwdFail OBJECT-TYPE
    SYNTAX      ConfdString
    MAX-ACCESS  read-only
    STATUS      current
    DESCRIPTION "WF packets from other SPM failures"
    ::= { affirmedSecurityStatisticsCpu-levelDataStatsEntry 49 }

affirmedSecurityStatisticsCpu-levelDataStatsSecmIngPktsFwdFail OBJECT-TYPE
    SYNTAX      ConfdString
    MAX-ACCESS  read-only
    STATUS      current
    DESCRIPTION "Ingress packet from other SSM failures"
    ::= { affirmedSecurityStatisticsCpu-levelDataStatsEntry 50 }

affirmedSecurityStatisticsCpu-levelDataStatsSecmEgrPktsFwdFail OBJECT-TYPE
    SYNTAX      ConfdString
    MAX-ACCESS  read-only
    STATUS      current
    DESCRIPTION "Egress packet from other SSM failures"
    ::= { affirmedSecurityStatisticsCpu-levelDataStatsEntry 51 }

affirmedSecurityStatisticsCpu-levelDataStatsFwdSpmNoFlowPkts OBJECT-TYPE
    SYNTAX      ConfdString
    MAX-ACCESS  read-only
    STATUS      current
    DESCRIPTION "Packets forwarded to SPM with no flow creation"
    ::= { affirmedSecurityStatisticsCpu-levelDataStatsEntry 52 }

affirmedSecurityStatisticsCpu-levelDataStatsTxV4DropPkts OBJECT-TYPE
    SYNTAX      ConfdString
    MAX-ACCESS  read-only
    STATUS      current
    DESCRIPTION "Egress IPv4 packets dropped"
    ::= { affirmedSecurityStatisticsCpu-levelDataStatsEntry 53 }

affirmedSecurityStatisticsCpu-levelDataStatsTxV4DropBytes OBJECT-TYPE
    SYNTAX      ConfdString
    MAX-ACCESS  read-only
    STATUS      current
    DESCRIPTION "Egress IPv4 bytes dropped"
    ::= { affirmedSecurityStatisticsCpu-levelDataStatsEntry 54 }

affirmedSecurityStatisticsCpu-levelDataStatsTxV6DropPkts OBJECT-TYPE
    SYNTAX      ConfdString
    MAX-ACCESS  read-only
    STATUS      current
    DESCRIPTION "Egress IPv6 packets dropped"
    ::= { affirmedSecurityStatisticsCpu-levelDataStatsEntry 55 }

affirmedSecurityStatisticsCpu-levelDataStatsTxV6DropBytes OBJECT-TYPE
    SYNTAX      ConfdString
    MAX-ACCESS  read-only
    STATUS      current
    DESCRIPTION "Egress IPv6 bytes dropped"
    ::= { affirmedSecurityStatisticsCpu-levelDataStatsEntry 56 }

affirmedSecurityStatisticsCpu-levelDataStatsDropPktsRule OBJECT-TYPE
    SYNTAX      ConfdString
    MAX-ACCESS  read-only
    STATUS      current
    DESCRIPTION "Packets dropped via an explicit rule"
    ::= { affirmedSecurityStatisticsCpu-levelDataStatsEntry 57 }

affirmedSecurityStatisticsCpu-levelDataStatsDropPktsRejectRule OBJECT-TYPE
    SYNTAX      ConfdString
    MAX-ACCESS  read-only
    STATUS      current
    DESCRIPTION "Packets rejected via an explicit rule"
    ::= { affirmedSecurityStatisticsCpu-levelDataStatsEntry 58 }

affirmedSecurityStatisticsCpu-levelDataStatsDropPktsNoRule OBJECT-TYPE
    SYNTAX      ConfdString
    MAX-ACCESS  read-only
    STATUS      current
    DESCRIPTION "Packets dropped due to no or bad rule"
    ::= { affirmedSecurityStatisticsCpu-levelDataStatsEntry 59 }

affirmedSecurityStatisticsCpu-levelDataStatsDropPktsTriggerRule OBJECT-TYPE
    SYNTAX      ConfdString
    MAX-ACCESS  read-only
    STATUS      current
    DESCRIPTION "Packets rejected via a trigger explicit rule"
    ::= { affirmedSecurityStatisticsCpu-levelDataStatsEntry 60 }

affirmedSecurityStatisticsCpu-levelDataStatsRemoteTransError OBJECT-TYPE
    SYNTAX      ConfdString
    MAX-ACCESS  read-only
    STATUS      current
    DESCRIPTION "Packets sent to wrong SSM"
    ::= { affirmedSecurityStatisticsCpu-levelDataStatsEntry 61 }

affirmedSecurityStatisticsCpu-levelDataStatsInvalidHeaderError OBJECT-TYPE
    SYNTAX      ConfdString
    MAX-ACCESS  read-only
    STATUS      current
    DESCRIPTION "Packets with bad IP header or length less than IP length"
    ::= { affirmedSecurityStatisticsCpu-levelDataStatsEntry 62 }

affirmedSecurityStatisticsCpu-levelDataStatsRxPendingFlowError OBJECT-TYPE
    SYNTAX      ConfdString
    MAX-ACCESS  read-only
    STATUS      current
    DESCRIPTION "Ingress Packets dropped because SPM has not validated flow"
    ::= { affirmedSecurityStatisticsCpu-levelDataStatsEntry 63 }

affirmedSecurityStatisticsCpu-levelDataStatsTxPendingFlowError OBJECT-TYPE
    SYNTAX      ConfdString
    MAX-ACCESS  read-only
    STATUS      current
    DESCRIPTION "Egress Packets dropped because SPM has not validated flow"
    ::= { affirmedSecurityStatisticsCpu-levelDataStatsEntry 64 }

affirmedSecurityStatisticsCpu-levelDataStatsNoFlowError OBJECT-TYPE
    SYNTAX      ConfdString
    MAX-ACCESS  read-only
    STATUS      current
    DESCRIPTION "Packets from other SSM with no or bad flow"
    ::= { affirmedSecurityStatisticsCpu-levelDataStatsEntry 65 }

affirmedSecurityStatisticsCpu-levelDataStatsTransNotFoundError OBJECT-TYPE
    SYNTAX      ConfdString
    MAX-ACCESS  read-only
    STATUS      current
    DESCRIPTION "Packets dropped because transform not in hash"
    ::= { affirmedSecurityStatisticsCpu-levelDataStatsEntry 66 }

affirmedSecurityStatisticsCpu-levelDataStatsDropPktsTooBig OBJECT-TYPE
    SYNTAX      ConfdString
    MAX-ACCESS  read-only
    STATUS      current
    DESCRIPTION "Packets too big for hardware crypto"
    ::= { affirmedSecurityStatisticsCpu-levelDataStatsEntry 67 }

affirmedSecurityStatisticsCpu-levelDataStatsBadHandle OBJECT-TYPE
    SYNTAX      ConfdString
    MAX-ACCESS  read-only
    STATUS      current
    DESCRIPTION "(hw only) Internal error"
    ::= { affirmedSecurityStatisticsCpu-levelDataStatsEntry 68 }

affirmedSecurityStatisticsCpu-levelDataStatsIngCtxtInUse OBJECT-TYPE
    SYNTAX      ConfdString
    MAX-ACCESS  read-only
    STATUS      current
    DESCRIPTION "Ingress packet dropped by hdw crypto because rekeying not done"
    ::= { affirmedSecurityStatisticsCpu-levelDataStatsEntry 69 }

affirmedSecurityStatisticsCpu-levelDataStatsFailedSanity OBJECT-TYPE
    SYNTAX      ConfdString
    MAX-ACCESS  read-only
    STATUS      current
    DESCRIPTION "Ingress packets dropped by hdw crypto for memory corruption"
    ::= { affirmedSecurityStatisticsCpu-levelDataStatsEntry 70 }

affirmedSecurityStatisticsCpu-levelDataStatsFlushedPkts OBJECT-TYPE
    SYNTAX      ConfdString
    MAX-ACCESS  read-only
    STATUS      current
    DESCRIPTION "Packets flushed after waiting 30 sec for SPM to validate flow"
    ::= { affirmedSecurityStatisticsCpu-levelDataStatsEntry 71 }

affirmedSecurityStatisticsCpu-levelDataStatsDropPktsIntfNotFound OBJECT-TYPE
    SYNTAX      ConfdString
    MAX-ACCESS  read-only
    STATUS      current
    DESCRIPTION "Packets dropped when transmit logical interface not found"
    ::= { affirmedSecurityStatisticsCpu-levelDataStatsEntry 72 }

affirmedSecurityStatisticsCpu-levelDataStatsDropPktsSessionNotFound OBJECT-TYPE
    SYNTAX      ConfdString
    MAX-ACCESS  read-only
    STATUS      current
    DESCRIPTION "WF packets dropped when session not found"
    ::= { affirmedSecurityStatisticsCpu-levelDataStatsEntry 73 }

affirmedSecurityStatisticsCpu-levelDataStatsDropPktsTransactionNotFound OBJECT-TYPE
    SYNTAX      ConfdString
    MAX-ACCESS  read-only
    STATUS      current
    DESCRIPTION "UE addressed packets dropped when transaction not found"
    ::= { affirmedSecurityStatisticsCpu-levelDataStatsEntry 74 }

affirmedSecurityStatisticsCpu-levelDataStatsTransactionsDeallocFailed OBJECT-TYPE
    SYNTAX      ConfdString
    MAX-ACCESS  read-only
    STATUS      current
    DESCRIPTION "Transaction deallocoations failures"
    ::= { affirmedSecurityStatisticsCpu-levelDataStatsEntry 75 }

affirmedSecurityStatisticsCpu-levelDataStatsInvalidNumaNode OBJECT-TYPE
    SYNTAX      ConfdString
    MAX-ACCESS  read-only
    STATUS      current
    DESCRIPTION "Received a non-default numaNode"
    ::= { affirmedSecurityStatisticsCpu-levelDataStatsEntry 76 }

affirmedSecurityStatisticsCpu-levelDataStatsFlowAccessTimeFix OBJECT-TYPE
    SYNTAX      ConfdString
    MAX-ACCESS  read-only
    STATUS      current
    DESCRIPTION "Flows accessed after more than 60 seconds of idle time"
    ::= { affirmedSecurityStatisticsCpu-levelDataStatsEntry 77 }

affirmedSecurityStatisticsCpu-levelDataStatsPendingFlowAccessTimeFix OBJECT-TYPE
    SYNTAX      ConfdString
    MAX-ACCESS  read-only
    STATUS      current
    DESCRIPTION "Flows pending after more than 60 seconds of idle time"
    ::= { affirmedSecurityStatisticsCpu-levelDataStatsEntry 78 }

affirmedSecurityStatisticsCpu-levelDataStatsHdwBadIcvIngressIom OBJECT-TYPE
    SYNTAX      ConfdString
    MAX-ACCESS  read-only
    STATUS      current
    DESCRIPTION "Locally originated packets with bad authentication"
    ::= { affirmedSecurityStatisticsCpu-levelDataStatsEntry 79 }

affirmedSecurityStatisticsCpu-levelDataStatsHdwBadIcvIngressSecm OBJECT-TYPE
    SYNTAX      ConfdString
    MAX-ACCESS  read-only
    STATUS      current
    DESCRIPTION "Remotely originated packets with bad authentication"
    ::= { affirmedSecurityStatisticsCpu-levelDataStatsEntry 80 }

affirmedSecurityStatisticsCpu-levelDataStatsIngSpiMismatch OBJECT-TYPE
    SYNTAX      ConfdString
    MAX-ACCESS  read-only
    STATUS      current
    DESCRIPTION "(hw only) ingress packet's SPI matches neither transform's SPI"
    ::= { affirmedSecurityStatisticsCpu-levelDataStatsEntry 81 }

affirmedSecurityStatisticsCpu-levelDataStatsEgrSpiMismatch OBJECT-TYPE
    SYNTAX      ConfdString
    MAX-ACCESS  read-only
    STATUS      current
    DESCRIPTION "SPI set up in egress packet matches neither egress SPI"
    ::= { affirmedSecurityStatisticsCpu-levelDataStatsEntry 82 }

affirmedSecurityStatisticsCpu-levelDataStatsTransAuthErrs OBJECT-TYPE
    SYNTAX      ConfdString
    MAX-ACCESS  read-only
    STATUS      current
    DESCRIPTION "Ingress packet failed pre cipher checks"
    ::= { affirmedSecurityStatisticsCpu-levelDataStatsEntry 83 }

affirmedSecurityStatisticsCpu-levelDataStatsPostSecTransAuthErrs OBJECT-TYPE
    SYNTAX      ConfdString
    MAX-ACCESS  read-only
    STATUS      current
    DESCRIPTION "Ingress packet failed post cipher checks"
    ::= { affirmedSecurityStatisticsCpu-levelDataStatsEntry 84 }

affirmedSecurityStatisticsCpu-levelDataStatsPostSecPktErrs OBJECT-TYPE
    SYNTAX      ConfdString
    MAX-ACCESS  read-only
    STATUS      current
    DESCRIPTION "Decrypted packet failed non-cipher checks"
    ::= { affirmedSecurityStatisticsCpu-levelDataStatsEntry 85 }

affirmedSecurityStatisticsCpu-levelDataStatsPostSecIntfPktErrs OBJECT-TYPE
    SYNTAX      ConfdString
    MAX-ACCESS  read-only
    STATUS      current
    DESCRIPTION "Remotely originated decrypted packet transmit failures"
    ::= { affirmedSecurityStatisticsCpu-levelDataStatsEntry 86 }

affirmedSecurityStatisticsCpu-levelDataStatsPostSecFpPktErrs OBJECT-TYPE
    SYNTAX      ConfdString
    MAX-ACCESS  read-only
    STATUS      current
    DESCRIPTION "Locally originated decrypted packet transmit failures"
    ::= { affirmedSecurityStatisticsCpu-levelDataStatsEntry 87 }

affirmedSecurityStatisticsCpu-levelDataStatsNoFlowPassAtRemoteSecm OBJECT-TYPE
    SYNTAX      ConfdString
    MAX-ACCESS  read-only
    STATUS      current
    DESCRIPTION "Passes match no flow pass rule, but should not send to spm"
    ::= { affirmedSecurityStatisticsCpu-levelDataStatsEntry 88 }

affirmedSecurityStatisticsCpu-levelDataStatsCreateFlowWithoutSpmForward OBJECT-TYPE
    SYNTAX      ConfdString
    MAX-ACCESS  read-only
    STATUS      current
    DESCRIPTION "Flows created without sending packet to SPM"
    ::= { affirmedSecurityStatisticsCpu-levelDataStatsEntry 89 }

affirmedSecurityStatisticsCpu-levelDataStatsEspSpiMismatchError OBJECT-TYPE
    SYNTAX      ConfdString
    MAX-ACCESS  read-only
    STATUS      current
    DESCRIPTION "Newly received ESP packet matches neither SPI"
    ::= { affirmedSecurityStatisticsCpu-levelDataStatsEntry 90 }

affirmedSecurityStatisticsCpu-levelDataStatsAhSpiMismatchError OBJECT-TYPE
    SYNTAX      ConfdString
    MAX-ACCESS  read-only
    STATUS      current
    DESCRIPTION "Newly received AH packet matches neither SPI"
    ::= { affirmedSecurityStatisticsCpu-levelDataStatsEntry 91 }

affirmedSecurityStatisticsCpu-levelDataStatsCipherNotFoundError OBJECT-TYPE
    SYNTAX      ConfdString
    MAX-ACCESS  read-only
    STATUS      current
    DESCRIPTION "Transform setup fail because cipher algorithm not found"
    ::= { affirmedSecurityStatisticsCpu-levelDataStatsEntry 92 }

affirmedSecurityStatisticsCpu-levelDataStatsAuthNotFoundError OBJECT-TYPE
    SYNTAX      ConfdString
    MAX-ACCESS  read-only
    STATUS      current
    DESCRIPTION "Transform setup fail because authentication algorithm not found"
    ::= { affirmedSecurityStatisticsCpu-levelDataStatsEntry 93 }

affirmedSecurityStatisticsCpu-levelDataStatsPktDataAccessError OBJECT-TYPE
    SYNTAX      ConfdString
    MAX-ACCESS  read-only
    STATUS      current
    DESCRIPTION "Mismatches between packet and expected prefix lengths"
    ::= { affirmedSecurityStatisticsCpu-levelDataStatsEntry 94 }

affirmedSecurityStatisticsCpu-levelDataStatsPktSizeCipherSizeError OBJECT-TYPE
    SYNTAX      ConfdString
    MAX-ACCESS  read-only
    STATUS      current
    DESCRIPTION "Encrypted packet size not a multiple of cipher block size"
    ::= { affirmedSecurityStatisticsCpu-levelDataStatsEntry 95 }

affirmedSecurityStatisticsCpu-levelDataStatsPktTooShortError OBJECT-TYPE
    SYNTAX      ConfdString
    MAX-ACCESS  read-only
    STATUS      current
    DESCRIPTION "Encrypted packet size less than necessary prefix and trailer sizes"
    ::= { affirmedSecurityStatisticsCpu-levelDataStatsEntry 96 }

affirmedSecurityStatisticsCpu-levelDataStatsPktLenMismatchError OBJECT-TYPE
    SYNTAX      ConfdString
    MAX-ACCESS  read-only
    STATUS      current
    DESCRIPTION "Internal mismatch between calculated and actual lengths"
    ::= { affirmedSecurityStatisticsCpu-levelDataStatsEntry 97 }

affirmedSecurityStatisticsCpu-levelDataStatsParsePktHeaderError OBJECT-TYPE
    SYNTAX      ConfdString
    MAX-ACCESS  read-only
    STATUS      current
    DESCRIPTION "All errors parsing encrypted packet headers"
    ::= { affirmedSecurityStatisticsCpu-levelDataStatsEntry 98 }

affirmedSecurityStatisticsCpu-levelDataStatsCalcPktInfoError OBJECT-TYPE
    SYNTAX      ConfdString
    MAX-ACCESS  read-only
    STATUS      current
    DESCRIPTION "All errors in ingress packet lengths"
    ::= { affirmedSecurityStatisticsCpu-levelDataStatsEntry 99 }

affirmedSecurityStatisticsCpu-levelDataStatsPrelimAntiReplayErrLo OBJECT-TYPE
    SYNTAX      ConfdString
    MAX-ACCESS  read-only
    STATUS      current
    DESCRIPTION "Ingress packet sequence number too low, before decryption"
    ::= { affirmedSecurityStatisticsCpu-levelDataStatsEntry 100 }

affirmedSecurityStatisticsCpu-levelDataStatsPrelimAntiReplayError OBJECT-TYPE
    SYNTAX      ConfdString
    MAX-ACCESS  read-only
    STATUS      current
    DESCRIPTION "Ingress packet sequence number error, but not too low, before decryption"
    ::= { affirmedSecurityStatisticsCpu-levelDataStatsEntry 101 }

affirmedSecurityStatisticsCpu-levelDataStatsEspSeqNumError OBJECT-TYPE
    SYNTAX      ConfdString
    MAX-ACCESS  read-only
    STATUS      current
    DESCRIPTION "All ESP packet sequence number errors, after decryption"
    ::= { affirmedSecurityStatisticsCpu-levelDataStatsEntry 102 }

affirmedSecurityStatisticsCpu-levelDataStatsEspSeqSecm OBJECT-TYPE
    SYNTAX      ConfdString
    MAX-ACCESS  read-only
    STATUS      current
    DESCRIPTION "secm-secm ESP packet sequence number errors, after decryption"
    ::= { affirmedSecurityStatisticsCpu-levelDataStatsEntry 103 }

affirmedSecurityStatisticsCpu-levelDataStatsEspSeqNumLow OBJECT-TYPE
    SYNTAX      ConfdString
    MAX-ACCESS  read-only
    STATUS      current
    DESCRIPTION "ESP packet sequence number too low, after decryption"
    ::= { affirmedSecurityStatisticsCpu-levelDataStatsEntry 104 }

affirmedSecurityStatisticsCpu-levelDataStatsAhSeqNumError OBJECT-TYPE
    SYNTAX      ConfdString
    MAX-ACCESS  read-only
    STATUS      current
    DESCRIPTION "All AH packet sequence number errors, after authentication"
    ::= { affirmedSecurityStatisticsCpu-levelDataStatsEntry 105 }

affirmedSecurityStatisticsCpu-levelDataStatsAppendSeqHighError OBJECT-TYPE
    SYNTAX      ConfdString
    MAX-ACCESS  read-only
    STATUS      current
    DESCRIPTION "Errors appending high half of sequence number to encrypted packets"
    ::= { affirmedSecurityStatisticsCpu-levelDataStatsEntry 106 }

affirmedSecurityStatisticsCpu-levelDataStatsDeleteSeqHighError OBJECT-TYPE
    SYNTAX      ConfdString
    MAX-ACCESS  read-only
    STATUS      current
    DESCRIPTION "Errors in deleting high half sequence number after calculating ICV"
    ::= { affirmedSecurityStatisticsCpu-levelDataStatsEntry 107 }

affirmedSecurityStatisticsCpu-levelDataStatsIcvComputeError OBJECT-TYPE
    SYNTAX      ConfdString
    MAX-ACCESS  read-only
    STATUS      current
    DESCRIPTION "(hw only ) All authentication failures"
    ::= { affirmedSecurityStatisticsCpu-levelDataStatsEntry 108 }

affirmedSecurityStatisticsCpu-levelDataStatsIcvCheckError OBJECT-TYPE
    SYNTAX      ConfdString
    MAX-ACCESS  read-only
    STATUS      current
    DESCRIPTION "(sw only) post cipher authentication failures"
    ::= { affirmedSecurityStatisticsCpu-levelDataStatsEntry 109 }

affirmedSecurityStatisticsCpu-levelDataStatsIcvLenError OBJECT-TYPE
    SYNTAX      ConfdString
    MAX-ACCESS  read-only
    STATUS      current
    DESCRIPTION "(sw only) ingress packet ICV Length Errors"
    ::= { affirmedSecurityStatisticsCpu-levelDataStatsEntry 110 }

affirmedSecurityStatisticsCpu-levelDataStatsEspIcvAuthError OBJECT-TYPE
    SYNTAX      ConfdString
    MAX-ACCESS  read-only
    STATUS      current
    DESCRIPTION "(sw only) pre-cipher authentication failures"
    ::= { affirmedSecurityStatisticsCpu-levelDataStatsEntry 111 }

affirmedSecurityStatisticsCpu-levelDataStatsEspPadError OBJECT-TYPE
    SYNTAX      ConfdString
    MAX-ACCESS  read-only
    STATUS      current
    DESCRIPTION "error in pad field values"
    ::= { affirmedSecurityStatisticsCpu-levelDataStatsEntry 112 }

affirmedSecurityStatisticsCpu-levelDataStatsAhIcvAuthError OBJECT-TYPE
    SYNTAX      ConfdString
    MAX-ACCESS  read-only
    STATUS      current
    DESCRIPTION "(sw only) AH packet failed authentication"
    ::= { affirmedSecurityStatisticsCpu-levelDataStatsEntry 113 }

affirmedSecurityStatisticsCpu-levelDataStatsEspTransChainError OBJECT-TYPE
    SYNTAX      ConfdString
    MAX-ACCESS  read-only
    STATUS      current
    DESCRIPTION "(sw only) transform errors"
    ::= { affirmedSecurityStatisticsCpu-levelDataStatsEntry 114 }

affirmedSecurityStatisticsCpu-levelDataStatsEspProcessAadError OBJECT-TYPE
    SYNTAX      ConfdString
    MAX-ACCESS  read-only
    STATUS      current
    DESCRIPTION "(sw only) transform aad errors"
    ::= { affirmedSecurityStatisticsCpu-levelDataStatsEntry 115 }

affirmedSecurityStatisticsCpu-levelDataStatsTransFinishError OBJECT-TYPE
    SYNTAX      ConfdString
    MAX-ACCESS  read-only
    STATUS      current
    DESCRIPTION "post decryption errors"
    ::= { affirmedSecurityStatisticsCpu-levelDataStatsEntry 116 }

affirmedSecurityStatisticsCpu-levelDataStatsAuthAddRangeError OBJECT-TYPE
    SYNTAX      ConfdString
    MAX-ACCESS  read-only
    STATUS      current
    DESCRIPTION "(sw only) ingress segment errors"
    ::= { affirmedSecurityStatisticsCpu-levelDataStatsEntry 117 }

affirmedSecurityStatisticsCpu-levelDataStatsAuthFinishError OBJECT-TYPE
    SYNTAX      ConfdString
    MAX-ACCESS  read-only
    STATUS      current
    DESCRIPTION "(sw only) errors in finishing authentication"
    ::= { affirmedSecurityStatisticsCpu-levelDataStatsEntry 118 }

affirmedSecurityStatisticsCpu-levelDataStatsCipherUpdateError OBJECT-TYPE
    SYNTAX      ConfdString
    MAX-ACCESS  read-only
    STATUS      current
    DESCRIPTION "(sw only) setup: errors updating cipher"
    ::= { affirmedSecurityStatisticsCpu-levelDataStatsEntry 119 }

affirmedSecurityStatisticsCpu-levelDataStatsAhSeqNumOverflowError OBJECT-TYPE
    SYNTAX      ConfdString
    MAX-ACCESS  read-only
    STATUS      current
    DESCRIPTION "egress AH sequence number overflow"
    ::= { affirmedSecurityStatisticsCpu-levelDataStatsEntry 120 }

affirmedSecurityStatisticsCpu-levelDataStatsEspSeqNumOverflowError OBJECT-TYPE
    SYNTAX      ConfdString
    MAX-ACCESS  read-only
    STATUS      current
    DESCRIPTION "egress ESP sequence number overflow"
    ::= { affirmedSecurityStatisticsCpu-levelDataStatsEntry 121 }

affirmedSecurityStatisticsCpu-levelDataStatsNumIngCryptoAllocFail OBJECT-TYPE
    SYNTAX      ConfdString
    MAX-ACCESS  read-only
    STATUS      current
    DESCRIPTION "(sw only) - context allocation failure"
    ::= { affirmedSecurityStatisticsCpu-levelDataStatsEntry 122 }

affirmedSecurityStatisticsCpu-levelDataStatsNumEgrCryptoAllocFail OBJECT-TYPE
    SYNTAX      ConfdString
    MAX-ACCESS  read-only
    STATUS      current
    DESCRIPTION "(sw only) - context allocation failure"
    ::= { affirmedSecurityStatisticsCpu-levelDataStatsEntry 123 }

affirmedSecurityStatisticsCpu-levelDataStatsNumGetNextHopFail OBJECT-TYPE
    SYNTAX      ConfdString
    MAX-ACCESS  read-only
    STATUS      current
    DESCRIPTION "Egress packet cannot find next hop"
    ::= { affirmedSecurityStatisticsCpu-levelDataStatsEntry 124 }

affirmedSecurityStatisticsCpu-levelDataStatsBypassV4IkeFragment OBJECT-TYPE
    SYNTAX      ConfdString
    MAX-ACCESS  read-only
    STATUS      current
    DESCRIPTION "SPM has sent an IKE packet that was fragmented"
    ::= { affirmedSecurityStatisticsCpu-levelDataStatsEntry 125 }

affirmedSecurityStatisticsCpu-levelDataStatsBypassV4OSPF OBJECT-TYPE
    SYNTAX      ConfdString
    MAX-ACCESS  read-only
    STATUS      current
    DESCRIPTION "V4 OSPF pkts"
    ::= { affirmedSecurityStatisticsCpu-levelDataStatsEntry 126 }

affirmedSecurityStatisticsCpu-levelDataStatsBypassV4Multicast OBJECT-TYPE
    SYNTAX      ConfdString
    MAX-ACCESS  read-only
    STATUS      current
    DESCRIPTION "V4 Multicast pkts"
    ::= { affirmedSecurityStatisticsCpu-levelDataStatsEntry 127 }

affirmedSecurityStatisticsCpu-levelDataStatsBypassV6LinkLocalDest OBJECT-TYPE
    SYNTAX      ConfdString
    MAX-ACCESS  read-only
    STATUS      current
    DESCRIPTION "V6 link local dest pkts"
    ::= { affirmedSecurityStatisticsCpu-levelDataStatsEntry 128 }

affirmedSecurityStatisticsCpu-levelDataStatsBypassV6LinkLocalSrc OBJECT-TYPE
    SYNTAX      ConfdString
    MAX-ACCESS  read-only
    STATUS      current
    DESCRIPTION "V6 link local src pkts"
    ::= { affirmedSecurityStatisticsCpu-levelDataStatsEntry 129 }

affirmedSecurityStatisticsCpu-levelDataStatsBypassTid0V6Icmp OBJECT-TYPE
    SYNTAX      ConfdString
    MAX-ACCESS  read-only
    STATUS      current
    DESCRIPTION "V6 Non-ping icmp pkt"
    ::= { affirmedSecurityStatisticsCpu-levelDataStatsEntry 130 }

affirmedSecurityStatisticsCpu-levelDataStatsBypassTid0IngressIke OBJECT-TYPE
    SYNTAX      ConfdString
    MAX-ACCESS  read-only
    STATUS      current
    DESCRIPTION "Ingress IKE pkt"
    ::= { affirmedSecurityStatisticsCpu-levelDataStatsEntry 131 }

affirmedSecurityStatisticsCpu-levelDataStatsBypassTid0IngressIkeNatt OBJECT-TYPE
    SYNTAX      ConfdString
    MAX-ACCESS  read-only
    STATUS      current
    DESCRIPTION "Ingress IKE NATT pkt"
    ::= { affirmedSecurityStatisticsCpu-levelDataStatsEntry 132 }

affirmedSecurityStatisticsCpu-levelDataStatsBypassTid0IngressV4DhcpClient OBJECT-TYPE
    SYNTAX      ConfdString
    MAX-ACCESS  read-only
    STATUS      current
    DESCRIPTION "Ingress V4 DHCP Client"
    ::= { affirmedSecurityStatisticsCpu-levelDataStatsEntry 133 }

affirmedSecurityStatisticsCpu-levelDataStatsBypassTid0EgressV4DnsClient OBJECT-TYPE
    SYNTAX      ConfdString
    MAX-ACCESS  read-only
    STATUS      current
    DESCRIPTION "Ingress V4 DNS Client"
    ::= { affirmedSecurityStatisticsCpu-levelDataStatsEntry 134 }

affirmedSecurityStatisticsCpu-levelDataStatsBypassTid1IngressUdp OBJECT-TYPE
    SYNTAX      ConfdString
    MAX-ACCESS  read-only
    STATUS      current
    DESCRIPTION "BypassTid1IngressUdp"
    ::= { affirmedSecurityStatisticsCpu-levelDataStatsEntry 135 }

affirmedSecurityStatisticsCpu-levelDataStatsIngressIke OBJECT-TYPE
    SYNTAX      ConfdString
    MAX-ACCESS  read-only
    STATUS      current
    DESCRIPTION "IngressIke"
    ::= { affirmedSecurityStatisticsCpu-levelDataStatsEntry 136 }

affirmedSecurityStatisticsCpu-levelDataStatsIngressIkeNatt OBJECT-TYPE
    SYNTAX      ConfdString
    MAX-ACCESS  read-only
    STATUS      current
    DESCRIPTION "IngressIkeNatt"
    ::= { affirmedSecurityStatisticsCpu-levelDataStatsEntry 137 }

affirmedSecurityStatisticsCpu-levelDataStatsEgressIke OBJECT-TYPE
    SYNTAX      ConfdString
    MAX-ACCESS  read-only
    STATUS      current
    DESCRIPTION "EgressIke"
    ::= { affirmedSecurityStatisticsCpu-levelDataStatsEntry 138 }

affirmedSecurityStatisticsCpu-levelDataStatsEgressIkeNatt OBJECT-TYPE
    SYNTAX      ConfdString
    MAX-ACCESS  read-only
    STATUS      current
    DESCRIPTION "EgressIkeNatt"
    ::= { affirmedSecurityStatisticsCpu-levelDataStatsEntry 139 }

affirmedSecurityStatisticsCpu-levelDataStatsPassRuleHits OBJECT-TYPE
    SYNTAX      ConfdString
    MAX-ACCESS  read-only
    STATUS      current
    DESCRIPTION "PassRuleHits"
    ::= { affirmedSecurityStatisticsCpu-levelDataStatsEntry 140 }

affirmedSecurityStatisticsCpu-levelDataStatsApplyRuleHits OBJECT-TYPE
    SYNTAX      ConfdString
    MAX-ACCESS  read-only
    STATUS      current
    DESCRIPTION "ApplyRuleHits"
    ::= { affirmedSecurityStatisticsCpu-levelDataStatsEntry 141 }

affirmedSecurityStatisticsCpu-levelDataStatsRxNattKaPkts OBJECT-TYPE
    SYNTAX      ConfdString
    MAX-ACCESS  read-only
    STATUS      current
    DESCRIPTION "RxNattKaPkts"
    ::= { affirmedSecurityStatisticsCpu-levelDataStatsEntry 142 }

affirmedSecurityStatisticsCpu-levelDataStatsUseableRuleHits OBJECT-TYPE
    SYNTAX      ConfdString
    MAX-ACCESS  read-only
    STATUS      current
    DESCRIPTION "UseableRuleHits"
    ::= { affirmedSecurityStatisticsCpu-levelDataStatsEntry 143 }

affirmedSecurityStatisticsCpu-levelDataStatsDropPktsWrongRule OBJECT-TYPE
    SYNTAX      ConfdString
    MAX-ACCESS  read-only
    STATUS      current
    DESCRIPTION "DropPktsWrongRule"
    ::= { affirmedSecurityStatisticsCpu-levelDataStatsEntry 144 }

affirmedSecurityStatisticsCpu-levelDataStatsDropPktsOnWrongTunnel OBJECT-TYPE
    SYNTAX      ConfdString
    MAX-ACCESS  read-only
    STATUS      current
    DESCRIPTION "DropPktsOnWrongTunnel"
    ::= { affirmedSecurityStatisticsCpu-levelDataStatsEntry 145 }

affirmedSecurityStatisticsCpu-levelDataStatsNoFlowErrorIngress OBJECT-TYPE
    SYNTAX      ConfdString
    MAX-ACCESS  read-only
    STATUS      current
    DESCRIPTION "NoFlowErrorIngress"
    ::= { affirmedSecurityStatisticsCpu-levelDataStatsEntry 146 }

affirmedSecurityStatisticsCpu-levelDataStatsNoFlowErrorEgress OBJECT-TYPE
    SYNTAX      ConfdString
    MAX-ACCESS  read-only
    STATUS      current
    DESCRIPTION "NoFlowErrorEgress"
    ::= { affirmedSecurityStatisticsCpu-levelDataStatsEntry 147 }

affirmedSecurityStatisticsCpu-levelDataStatsPktsDiscarded OBJECT-TYPE
    SYNTAX      ConfdString
    MAX-ACCESS  read-only
    STATUS      current
    DESCRIPTION "PktsDiscarded"
    ::= { affirmedSecurityStatisticsCpu-levelDataStatsEntry 148 }

affirmedSecurityStatisticsCpu-levelDataStatsNoFlowPassDrop OBJECT-TYPE
    SYNTAX      ConfdString
    MAX-ACCESS  read-only
    STATUS      current
    DESCRIPTION "NoFlowPassDrop"
    ::= { affirmedSecurityStatisticsCpu-levelDataStatsEntry 149 }

affirmedSecurityStatisticsCpu-levelDataStatsNoFlowTid0IngressIPsec OBJECT-TYPE
    SYNTAX      ConfdString
    MAX-ACCESS  read-only
    STATUS      current
    DESCRIPTION "NoFlowTid0IngressIPsec"
    ::= { affirmedSecurityStatisticsCpu-levelDataStatsEntry 150 }

affirmedSecurityStatisticsCpu-levelDataStatsSpiEntryFailLookup OBJECT-TYPE
    SYNTAX      ConfdString
    MAX-ACCESS  read-only
    STATUS      current
    DESCRIPTION "SpiEntryFailLookup"
    ::= { affirmedSecurityStatisticsCpu-levelDataStatsEntry 151 }

affirmedSecurityStatisticsCpu-levelDataStatsDropPktsSecurityDisabled OBJECT-TYPE
    SYNTAX      ConfdString
    MAX-ACCESS  read-only
    STATUS      current
    DESCRIPTION "DropPktsSecurityDisabled"
    ::= { affirmedSecurityStatisticsCpu-levelDataStatsEntry 152 }

affirmedSecurityStatisticsCpu-levelDataStatsUnuseableRuleHits OBJECT-TYPE
    SYNTAX      ConfdString
    MAX-ACCESS  read-only
    STATUS      current
    DESCRIPTION "UnuseableRuleHits"
    ::= { affirmedSecurityStatisticsCpu-levelDataStatsEntry 153 }

affirmedSecurityStatisticsCpu-levelDataStatsDropRuleHits OBJECT-TYPE
    SYNTAX      ConfdString
    MAX-ACCESS  read-only
    STATUS      current
    DESCRIPTION "DropRuleHits"
    ::= { affirmedSecurityStatisticsCpu-levelDataStatsEntry 154 }

affirmedSecurityStatisticsCpu-levelDataStatsRejectRuleHits OBJECT-TYPE
    SYNTAX      ConfdString
    MAX-ACCESS  read-only
    STATUS      current
    DESCRIPTION "RejectRuleHits"
    ::= { affirmedSecurityStatisticsCpu-levelDataStatsEntry 155 }

affirmedSecurityStatisticsCpu-levelDataStatsInvalidRuleHits OBJECT-TYPE
    SYNTAX      ConfdString
    MAX-ACCESS  read-only
    STATUS      current
    DESCRIPTION "InvalidRuleHits"
    ::= { affirmedSecurityStatisticsCpu-levelDataStatsEntry 156 }

affirmedSecurityStatisticsCpu-levelDataStatsDormantApplyRuleHits OBJECT-TYPE
    SYNTAX      ConfdString
    MAX-ACCESS  read-only
    STATUS      current
    DESCRIPTION "DormantApplyRuleHits"
    ::= { affirmedSecurityStatisticsCpu-levelDataStatsEntry 157 }

affirmedSecurityStatisticsCpu-levelDataStatsUnknownRuleHits OBJECT-TYPE
    SYNTAX      ConfdString
    MAX-ACCESS  read-only
    STATUS      current
    DESCRIPTION "UnknownRuleHits"
    ::= { affirmedSecurityStatisticsCpu-levelDataStatsEntry 158 }

affirmedSecurityStatisticsCpu-levelDataStatsPostSecPktErrsInvalidHeader OBJECT-TYPE
    SYNTAX      ConfdString
    MAX-ACCESS  read-only
    STATUS      current
    DESCRIPTION "PostSecPktErrsInvalidHeader"
    ::= { affirmedSecurityStatisticsCpu-levelDataStatsEntry 159 }

affirmedSecurityStatisticsCpu-levelDataStatsPostSecPktErrsInvalidFragHeader OBJECT-TYPE
    SYNTAX      ConfdString
    MAX-ACCESS  read-only
    STATUS      current
    DESCRIPTION "PostSecPktErrsInvalidFragHeader"
    ::= { affirmedSecurityStatisticsCpu-levelDataStatsEntry 160 }

affirmedSecurityStatisticsCpu-levelDataStatsPostSecPktErrsNoFlowFound OBJECT-TYPE
    SYNTAX      ConfdString
    MAX-ACCESS  read-only
    STATUS      current
    DESCRIPTION "PostSecPktErrsNoFlowFound"
    ::= { affirmedSecurityStatisticsCpu-levelDataStatsEntry 161 }

affirmedSecurityStatisticsCpu-levelDataStatsPostSecPktErrsBadFlowFound OBJECT-TYPE
    SYNTAX      ConfdString
    MAX-ACCESS  read-only
    STATUS      current
    DESCRIPTION "PostSecPktErrsBadFlowFound"
    ::= { affirmedSecurityStatisticsCpu-levelDataStatsEntry 162 }

affirmedSecurityStatisticsCpu-levelDataStatsPostSecPktErrsUnexpectedPendFlow OBJECT-TYPE
    SYNTAX      ConfdString
    MAX-ACCESS  read-only
    STATUS      current
    DESCRIPTION "PostSecPktErrsUnexpectedPendFlow"
    ::= { affirmedSecurityStatisticsCpu-levelDataStatsEntry 163 }

affirmedSecurityStatisticsCpu-levelDataStatsPostSecPktErrsUnexpectedApplyFlow OBJECT-TYPE
    SYNTAX      ConfdString
    MAX-ACCESS  read-only
    STATUS      current
    DESCRIPTION "PostSecPktErrsUnexpectedApplyFlow"
    ::= { affirmedSecurityStatisticsCpu-levelDataStatsEntry 164 }

affirmedSecurityStatisticsCpu-levelDataStatsPostSecPktErrsUnexpectedRejectFlow OBJECT-TYPE
    SYNTAX      ConfdString
    MAX-ACCESS  read-only
    STATUS      current
    DESCRIPTION "PostSecPktErrsUnexpectedRejectFlow"
    ::= { affirmedSecurityStatisticsCpu-levelDataStatsEntry 165 }

affirmedSecurityStatisticsCpu-levelDataStatsPostSecPktErrsUnexpectedTriggerFlow OBJECT-TYPE
    SYNTAX      ConfdString
    MAX-ACCESS  read-only
    STATUS      current
    DESCRIPTION "PostSecPktErrsUnexpectedTriggerFlow"
    ::= { affirmedSecurityStatisticsCpu-levelDataStatsEntry 166 }

affirmedSecurityStatisticsCpu-levelDataStatsPostSecPktErrsUnexpectedDropFlow OBJECT-TYPE
    SYNTAX      ConfdString
    MAX-ACCESS  read-only
    STATUS      current
    DESCRIPTION "PostSecPktErrsUnexpectedDropFlow"
    ::= { affirmedSecurityStatisticsCpu-levelDataStatsEntry 167 }

affirmedSecurityStatisticsCpu-levelDataStatsPostSecPktErrsUnexpectedNonExistentFlow OBJECT-TYPE
    SYNTAX      ConfdString
    MAX-ACCESS  read-only
    STATUS      current
    DESCRIPTION "PostSecPktErrsUnexpectedNonExistentFlow"
    ::= { affirmedSecurityStatisticsCpu-levelDataStatsEntry 168 }

affirmedSecurityStatisticsCpu-levelDataStatsDropPktsDropRule OBJECT-TYPE
    SYNTAX      ConfdString
    MAX-ACCESS  read-only
    STATUS      current
    DESCRIPTION "DropPktsDropRule"
    ::= { affirmedSecurityStatisticsCpu-levelDataStatsEntry 169 }

affirmedSecurityStatisticsCpu-levelDataStatsNullSpiEntry OBJECT-TYPE
    SYNTAX      ConfdString
    MAX-ACCESS  read-only
    STATUS      current
    DESCRIPTION "NullSpiEntry"
    ::= { affirmedSecurityStatisticsCpu-levelDataStatsEntry 170 }

affirmedSecurityStatisticsCpu-levelDataStatsInvalidFSAPI OBJECT-TYPE
    SYNTAX      ConfdString
    MAX-ACCESS  read-only
    STATUS      current
    DESCRIPTION "InvalidFSAPI"
    ::= { affirmedSecurityStatisticsCpu-levelDataStatsEntry 171 }

affirmedSecurityStatisticsCpu-levelDataStatsNewTable OBJECT-TYPE
    SYNTAX      SEQUENCE OF AffirmedSecurityStatisticsCpu-levelDataStatsNewEntry
    MAX-ACCESS  not-accessible
    STATUS      current
    DESCRIPTION ""
    ::= { affirmedSecurityStatisticsCpu-level 2 }

affirmedSecurityStatisticsCpu-levelDataStatsNewEntry OBJECT-TYPE
    SYNTAX      AffirmedSecurityStatisticsCpu-levelDataStatsNewEntry
    MAX-ACCESS  not-accessible
    STATUS      current
    DESCRIPTION ""
    INDEX { affirmedSecurityStatisticsCpu-levelDataStatsNewSlot, affirmedSecurityStatisticsCpu-levelDataStatsNewCpuid }
        ::= { affirmedSecurityStatisticsCpu-levelDataStatsNewTable 1 }

AffirmedSecurityStatisticsCpu-levelDataStatsNewEntry ::=
    SEQUENCE {
        affirmedSecurityStatisticsCpu-levelDataStatsNewSlot Unsigned32,
        affirmedSecurityStatisticsCpu-levelDataStatsNewCpuid Unsigned32,
        affirmedSecurityStatisticsCpu-levelDataStatsNewRxV4Pkts ConfdString,
        affirmedSecurityStatisticsCpu-levelDataStatsNewRxV4Bytes ConfdString,
        affirmedSecurityStatisticsCpu-levelDataStatsNewRxV6Pkts ConfdString,
        affirmedSecurityStatisticsCpu-levelDataStatsNewRxV6Bytes ConfdString,
        affirmedSecurityStatisticsCpu-levelDataStatsNewTxV4Pkts ConfdString,
        affirmedSecurityStatisticsCpu-levelDataStatsNewTxV4Bytes ConfdString,
        affirmedSecurityStatisticsCpu-levelDataStatsNewTxV6Pkts ConfdString,
        affirmedSecurityStatisticsCpu-levelDataStatsNewTxV6Bytes ConfdString,
        affirmedSecurityStatisticsCpu-levelDataStatsNewRxPostSecurityV4Pkts ConfdString,
        affirmedSecurityStatisticsCpu-levelDataStatsNewRxPostSecurityV4Bytes ConfdString,
        affirmedSecurityStatisticsCpu-levelDataStatsNewRxPostSecurityV6Pkts ConfdString,
        affirmedSecurityStatisticsCpu-levelDataStatsNewRxPostSecurityV6Bytes ConfdString,
        affirmedSecurityStatisticsCpu-levelDataStatsNewRxEspPkts ConfdString,
        affirmedSecurityStatisticsCpu-levelDataStatsNewRxRemoteSecmPkts ConfdString,
        affirmedSecurityStatisticsCpu-levelDataStatsNewRxSecmIngTransPkts ConfdString,
        affirmedSecurityStatisticsCpu-levelDataStatsNewRxSecmEgrTransPkts ConfdString,
        affirmedSecurityStatisticsCpu-levelDataStatsNewRxSpmPktsIgnored ConfdString,
        affirmedSecurityStatisticsCpu-levelDataStatsNewFwdRemoteSecmPkts ConfdString,
        affirmedSecurityStatisticsCpu-levelDataStatsNewFwdSpmPkts ConfdString,
        affirmedSecurityStatisticsCpu-levelDataStatsNewSecmIngPktsFwdFail ConfdString,
        affirmedSecurityStatisticsCpu-levelDataStatsNewSecmEgrPktsFwdFail ConfdString,
        affirmedSecurityStatisticsCpu-levelDataStatsNewRxBypassRulePkts ConfdString,
        affirmedSecurityStatisticsCpu-levelDataStatsNewTxBypassRulePkts ConfdString,
        affirmedSecurityStatisticsCpu-levelDataStatsNewBypassV4IkeFragment ConfdString,
        affirmedSecurityStatisticsCpu-levelDataStatsNewBypassV4Multicast ConfdString,
        affirmedSecurityStatisticsCpu-levelDataStatsNewBypassV6NdNbrIcmp ConfdString,
        affirmedSecurityStatisticsCpu-levelDataStatsNewBypassV6Multicast ConfdString,
        affirmedSecurityStatisticsCpu-levelDataStatsNewBypassV6LinkLocalDest ConfdString,
        affirmedSecurityStatisticsCpu-levelDataStatsNewBypassV6LinkLocalSrc ConfdString,
        affirmedSecurityStatisticsCpu-levelDataStatsNewBypassTid0V6Icmp ConfdString,
        affirmedSecurityStatisticsCpu-levelDataStatsNewBypassTid0IngressIke ConfdString,
        affirmedSecurityStatisticsCpu-levelDataStatsNewBypassTid0IngressIkeNatt ConfdString,
        affirmedSecurityStatisticsCpu-levelDataStatsNewBypassTid0IngressV4DhcpClient ConfdString,
        affirmedSecurityStatisticsCpu-levelDataStatsNewBypassTid0EgressV4DnsClient ConfdString,
        affirmedSecurityStatisticsCpu-levelDataStatsNewBypassTid1IngressUdp ConfdString,
        affirmedSecurityStatisticsCpu-levelDataStatsNewTxEspPkts ConfdString,
        affirmedSecurityStatisticsCpu-levelDataStatsNewQueuedPkts ConfdString,
        affirmedSecurityStatisticsCpu-levelDataStatsNewDequeuedPkts ConfdString,
        affirmedSecurityStatisticsCpu-levelDataStatsNewTransactionsAllocated ConfdString,
        affirmedSecurityStatisticsCpu-levelDataStatsNewTransactionsDeallocated ConfdString,
        affirmedSecurityStatisticsCpu-levelDataStatsNewIngressIke ConfdString,
        affirmedSecurityStatisticsCpu-levelDataStatsNewIngressIkeNatt ConfdString,
        affirmedSecurityStatisticsCpu-levelDataStatsNewEgressIke ConfdString,
        affirmedSecurityStatisticsCpu-levelDataStatsNewEgressIkeNatt ConfdString,
        affirmedSecurityStatisticsCpu-levelDataStatsNewUseableRuleHits ConfdString,
        affirmedSecurityStatisticsCpu-levelDataStatsNewDropPktsRule ConfdString,
        affirmedSecurityStatisticsCpu-levelDataStatsNewDropPktsRejectRule ConfdString,
        affirmedSecurityStatisticsCpu-levelDataStatsNewPassRuleHits ConfdString,
        affirmedSecurityStatisticsCpu-levelDataStatsNewApplyRuleHits ConfdString,
        affirmedSecurityStatisticsCpu-levelDataStatsNewRxNattKaPkts ConfdString,
        affirmedSecurityStatisticsCpu-levelDataStatsNewRxEpdgPkts ConfdString,
        affirmedSecurityStatisticsCpu-levelDataStatsNewTxEpdgPkts ConfdString,
        affirmedSecurityStatisticsCpu-levelDataStatsNewRxIkeApplyPolicy ConfdString,
        affirmedSecurityStatisticsCpu-levelDataStatsNewRxIkeNattApplyPolicy ConfdString,
        affirmedSecurityStatisticsCpu-levelDataStatsNewRxV4DropPkts ConfdString,
        affirmedSecurityStatisticsCpu-levelDataStatsNewRxV4DropBytes ConfdString,
        affirmedSecurityStatisticsCpu-levelDataStatsNewRxV6DropPkts ConfdString,
        affirmedSecurityStatisticsCpu-levelDataStatsNewRxV6DropBytes ConfdString,
        affirmedSecurityStatisticsCpu-levelDataStatsNewTxV4DropPkts ConfdString,
        affirmedSecurityStatisticsCpu-levelDataStatsNewTxV4DropBytes ConfdString,
        affirmedSecurityStatisticsCpu-levelDataStatsNewTxV6DropPkts ConfdString,
        affirmedSecurityStatisticsCpu-levelDataStatsNewTxV6DropBytes ConfdString,
        affirmedSecurityStatisticsCpu-levelDataStatsNewRemoteTransError ConfdString,
        affirmedSecurityStatisticsCpu-levelDataStatsNewInvalidHeaderError ConfdString,
        affirmedSecurityStatisticsCpu-levelDataStatsNewRxPendingFlowError ConfdString,
        affirmedSecurityStatisticsCpu-levelDataStatsNewTxPendingFlowError ConfdString,
        affirmedSecurityStatisticsCpu-levelDataStatsNewNoFlowErrorIngress ConfdString,
        affirmedSecurityStatisticsCpu-levelDataStatsNewNoFlowErrorEgress ConfdString,
        affirmedSecurityStatisticsCpu-levelDataStatsNewTransNotFoundError ConfdString,
        affirmedSecurityStatisticsCpu-levelDataStatsNewIngCtxtInUse ConfdString,
        affirmedSecurityStatisticsCpu-levelDataStatsNewFailedSanity ConfdString,
        affirmedSecurityStatisticsCpu-levelDataStatsNewDropPktsIntfNotFound ConfdString,
        affirmedSecurityStatisticsCpu-levelDataStatsNewDropPktsSessionNotFound ConfdString,
        affirmedSecurityStatisticsCpu-levelDataStatsNewDropPktsSecurityDisabled ConfdString,
        affirmedSecurityStatisticsCpu-levelDataStatsNewTransactionsDeallocFailed ConfdString,
        affirmedSecurityStatisticsCpu-levelDataStatsNewInvalidNumaNode ConfdString,
        affirmedSecurityStatisticsCpu-levelDataStatsNewIngSpiMismatch ConfdString,
        affirmedSecurityStatisticsCpu-levelDataStatsNewEgrSpiMismatch ConfdString,
        affirmedSecurityStatisticsCpu-levelDataStatsNewTransAuthErrs ConfdString,
        affirmedSecurityStatisticsCpu-levelDataStatsNewPostSecTransAuthErrs ConfdString,
        affirmedSecurityStatisticsCpu-levelDataStatsNewPostSecPktErrs ConfdString,
        affirmedSecurityStatisticsCpu-levelDataStatsNewPostSecPktErrsInvalidHeader ConfdString,
        affirmedSecurityStatisticsCpu-levelDataStatsNewPostSecPktErrsInvalidFragHeader ConfdString,
        affirmedSecurityStatisticsCpu-levelDataStatsNewPostSecPktErrsNoFlowFound ConfdString,
        affirmedSecurityStatisticsCpu-levelDataStatsNewPostSecPktErrsBadFlowFound ConfdString,
        affirmedSecurityStatisticsCpu-levelDataStatsNewPostSecPktErrsUnexpectedPendFlow ConfdString,
        affirmedSecurityStatisticsCpu-levelDataStatsNewPostSecPktErrsUnexpectedApplyFlow ConfdString,
        affirmedSecurityStatisticsCpu-levelDataStatsNewPostSecPktErrsUnexpectedRejectFlow ConfdString,
        affirmedSecurityStatisticsCpu-levelDataStatsNewPostSecPktErrsUnexpectedTriggerFlow ConfdString,
        affirmedSecurityStatisticsCpu-levelDataStatsNewPostSecPktErrsUnexpectedDropFlow ConfdString,
        affirmedSecurityStatisticsCpu-levelDataStatsNewPostSecPktErrsUnexpectedNonExistentFlow ConfdString,
        affirmedSecurityStatisticsCpu-levelDataStatsNewPostSecIntfPktErrs ConfdString,
        affirmedSecurityStatisticsCpu-levelDataStatsNewPostSecFpPktErrs ConfdString,
        affirmedSecurityStatisticsCpu-levelDataStatsNewIngCtxtErrs ConfdString,
        affirmedSecurityStatisticsCpu-levelDataStatsNewEgrCtxtErrs ConfdString,
        affirmedSecurityStatisticsCpu-levelDataStatsNewUnuseableRuleHits ConfdString,
        affirmedSecurityStatisticsCpu-levelDataStatsNewInvalidRuleHits ConfdString,
        affirmedSecurityStatisticsCpu-levelDataStatsNewTriggerRuleHits ConfdString,
        affirmedSecurityStatisticsCpu-levelDataStatsNewDormantApplyRuleHits ConfdString,
        affirmedSecurityStatisticsCpu-levelDataStatsNewUnknownRuleHits ConfdString,
        affirmedSecurityStatisticsCpu-levelDataStatsNewNoFlowPassAtRemoteSecm ConfdString,
        affirmedSecurityStatisticsCpu-levelDataStatsNewPktsDiscarded ConfdString,
        affirmedSecurityStatisticsCpu-levelDataStatsNewNoFlowPassDrop ConfdString,
        affirmedSecurityStatisticsCpu-levelDataStatsNewNoFlowTid0IngressIPsec ConfdString,
        affirmedSecurityStatisticsCpu-levelDataStatsNewNoFlowTidV6IcmpErr ConfdString,
        affirmedSecurityStatisticsCpu-levelDataStatsNewNoFlowTidV4IcmpErr ConfdString,
        affirmedSecurityStatisticsCpu-levelDataStatsNewDropPktsTooBig ConfdString,
        affirmedSecurityStatisticsCpu-levelDataStatsNewDropPktsNoRule ConfdString,
        affirmedSecurityStatisticsCpu-levelDataStatsNewDropPktsTriggerRule ConfdString,
        affirmedSecurityStatisticsCpu-levelDataStatsNewDequeuePendingError ConfdString,
        affirmedSecurityStatisticsCpu-levelDataStatsNewNullSpiEntry ConfdString,
        affirmedSecurityStatisticsCpu-levelDataStatsNewInvalidFSAPI ConfdString,
        affirmedSecurityStatisticsCpu-levelDataStatsNewSpiEntryFailLookup ConfdString,
        affirmedSecurityStatisticsCpu-levelDataStatsNewSpiTransformEntryFailLookup ConfdString,
        affirmedSecurityStatisticsCpu-levelDataStatsNewTriggerRuleIngressPkts ConfdString,
        affirmedSecurityStatisticsCpu-levelDataStatsNewRejectRuleHits ConfdString,
        affirmedSecurityStatisticsCpu-levelDataStatsNewFlushedPkts ConfdString,
        affirmedSecurityStatisticsCpu-levelDataStatsNewQueuedPktNotApply ConfdString,
        affirmedSecurityStatisticsCpu-levelDataStatsNewEspSpiMismatchError ConfdString,
        affirmedSecurityStatisticsCpu-levelDataStatsNewCipherNotFoundError ConfdString,
        affirmedSecurityStatisticsCpu-levelDataStatsNewPktDataAccessError ConfdString,
        affirmedSecurityStatisticsCpu-levelDataStatsNewPktSizeCipherSizeError ConfdString,
        affirmedSecurityStatisticsCpu-levelDataStatsNewPktTooShortError ConfdString,
        affirmedSecurityStatisticsCpu-levelDataStatsNewPktLenMismatchError ConfdString,
        affirmedSecurityStatisticsCpu-levelDataStatsNewParsePktHeaderError ConfdString,
        affirmedSecurityStatisticsCpu-levelDataStatsNewCalcPktInfoError ConfdString,
        affirmedSecurityStatisticsCpu-levelDataStatsNewPrelimAntiReplayErrLo ConfdString,
        affirmedSecurityStatisticsCpu-levelDataStatsNewPrelimAntiReplayError ConfdString,
        affirmedSecurityStatisticsCpu-levelDataStatsNewEspSeqNumError ConfdString,
        affirmedSecurityStatisticsCpu-levelDataStatsNewEspSeqSecm ConfdString,
        affirmedSecurityStatisticsCpu-levelDataStatsNewEspSeqNumLow ConfdString,
        affirmedSecurityStatisticsCpu-levelDataStatsNewAppendSeqHighError ConfdString,
        affirmedSecurityStatisticsCpu-levelDataStatsNewDeleteSeqHighError ConfdString,
        affirmedSecurityStatisticsCpu-levelDataStatsNewIcvComputeError ConfdString,
        affirmedSecurityStatisticsCpu-levelDataStatsNewIcvCheckError ConfdString,
        affirmedSecurityStatisticsCpu-levelDataStatsNewIcvLenError ConfdString,
        affirmedSecurityStatisticsCpu-levelDataStatsNewEspIcvAuthError ConfdString,
        affirmedSecurityStatisticsCpu-levelDataStatsNewEspPadError ConfdString,
        affirmedSecurityStatisticsCpu-levelDataStatsNewEspTransChainError ConfdString,
        affirmedSecurityStatisticsCpu-levelDataStatsNewEspProcessAadError ConfdString,
        affirmedSecurityStatisticsCpu-levelDataStatsNewTransFinishError ConfdString,
        affirmedSecurityStatisticsCpu-levelDataStatsNewAuthAddRangeError ConfdString,
        affirmedSecurityStatisticsCpu-levelDataStatsNewAuthFinishError ConfdString,
        affirmedSecurityStatisticsCpu-levelDataStatsNewCipherUpdateError ConfdString,
        affirmedSecurityStatisticsCpu-levelDataStatsNewEspSeqNumOverflowError ConfdString,
        affirmedSecurityStatisticsCpu-levelDataStatsNewIngCryptoAllocFail ConfdString,
        affirmedSecurityStatisticsCpu-levelDataStatsNewEgrCryptoAllocFail ConfdString,
        affirmedSecurityStatisticsCpu-levelDataStatsNewIngCryptoResetFail ConfdString,
        affirmedSecurityStatisticsCpu-levelDataStatsNewEgrCryptoResetFail ConfdString,
        affirmedSecurityStatisticsCpu-levelDataStatsNewGetNextHopFail ConfdString,
        affirmedSecurityStatisticsCpu-levelDataStatsNewNoCryptoCapability ConfdString,
        affirmedSecurityStatisticsCpu-levelDataStatsNewSecmSessionIcmpFragNeededMsgSent ConfdString,
        affirmedSecurityStatisticsCpu-levelDataStatsNewSecmIcmpFragNeededMsgSent ConfdString,
        affirmedSecurityStatisticsCpu-levelDataStatsNewSecmSessionIcmpV6PacketTooBigMsgSent ConfdString,
        affirmedSecurityStatisticsCpu-levelDataStatsNewSecmIcmpV6PacketTooBigMsgSent ConfdString,
        affirmedSecurityStatisticsCpu-levelDataStatsNewSecmIPv6MaxFragAfterEncryptionTooBig ConfdString,
        affirmedSecurityStatisticsCpu-levelDataStatsNewSecmIPv6MaxFragTooBig ConfdString,
        affirmedSecurityStatisticsCpu-levelDataStatsNewSecmIPv6PktTooBigPreFragEnabled ConfdString,
        affirmedSecurityStatisticsCpu-levelDataStatsNewSecmIPv6FragSuccess ConfdString,
        affirmedSecurityStatisticsCpu-levelDataStatsNewSecmIPv4FragSuccess ConfdString,
        affirmedSecurityStatisticsCpu-levelDataStatsNewSecmIPv6FragFailed ConfdString,
        affirmedSecurityStatisticsCpu-levelDataStatsNewSecmIPv4FragFailed ConfdString,
        affirmedSecurityStatisticsCpu-levelDataStatsNewSecmFragStatusFailed ConfdString,
        affirmedSecurityStatisticsCpu-levelDataStatsNewSecmNumFrlDropIngressCnts ConfdString,
        affirmedSecurityStatisticsCpu-levelDataStatsNewSecmNumPrlDropIngressCnts ConfdString,
        affirmedSecurityStatisticsCpu-levelDataStatsNewSecmNumFrlDropEgressCnts ConfdString,
        affirmedSecurityStatisticsCpu-levelDataStatsNewSecmNumPrlDropEgressCnts ConfdString
    }

affirmedSecurityStatisticsCpu-levelDataStatsNewSlot OBJECT-TYPE
    SYNTAX      Unsigned32
    MAX-ACCESS  not-accessible
    STATUS      current
    DESCRIPTION "Slot number"
    ::= { affirmedSecurityStatisticsCpu-levelDataStatsNewEntry 1 }

affirmedSecurityStatisticsCpu-levelDataStatsNewCpuid OBJECT-TYPE
    SYNTAX      Unsigned32
    MAX-ACCESS  not-accessible
    STATUS      current
    DESCRIPTION "cpu number"
    ::= { affirmedSecurityStatisticsCpu-levelDataStatsNewEntry 2 }

affirmedSecurityStatisticsCpu-levelDataStatsNewRxV4Pkts OBJECT-TYPE
    SYNTAX      ConfdString
    MAX-ACCESS  read-only
    STATUS      current
    DESCRIPTION "Ingress IPv4 packets successfully processed "
    ::= { affirmedSecurityStatisticsCpu-levelDataStatsNewEntry 3 }

affirmedSecurityStatisticsCpu-levelDataStatsNewRxV4Bytes OBJECT-TYPE
    SYNTAX      ConfdString
    MAX-ACCESS  read-only
    STATUS      current
    DESCRIPTION "Ingress IPv4 bytes successfully processed "
    ::= { affirmedSecurityStatisticsCpu-levelDataStatsNewEntry 4 }

affirmedSecurityStatisticsCpu-levelDataStatsNewRxV6Pkts OBJECT-TYPE
    SYNTAX      ConfdString
    MAX-ACCESS  read-only
    STATUS      current
    DESCRIPTION "Ingress IPv6 packets successfully processed "
    ::= { affirmedSecurityStatisticsCpu-levelDataStatsNewEntry 5 }

affirmedSecurityStatisticsCpu-levelDataStatsNewRxV6Bytes OBJECT-TYPE
    SYNTAX      ConfdString
    MAX-ACCESS  read-only
    STATUS      current
    DESCRIPTION "Ingress IPv6 bytes successfully processed "
    ::= { affirmedSecurityStatisticsCpu-levelDataStatsNewEntry 6 }

affirmedSecurityStatisticsCpu-levelDataStatsNewTxV4Pkts OBJECT-TYPE
    SYNTAX      ConfdString
    MAX-ACCESS  read-only
    STATUS      current
    DESCRIPTION "Egress IPv4 packets successfully processed "
    ::= { affirmedSecurityStatisticsCpu-levelDataStatsNewEntry 7 }

affirmedSecurityStatisticsCpu-levelDataStatsNewTxV4Bytes OBJECT-TYPE
    SYNTAX      ConfdString
    MAX-ACCESS  read-only
    STATUS      current
    DESCRIPTION "Egress IPv4 bytes successfully processed "
    ::= { affirmedSecurityStatisticsCpu-levelDataStatsNewEntry 8 }

affirmedSecurityStatisticsCpu-levelDataStatsNewTxV6Pkts OBJECT-TYPE
    SYNTAX      ConfdString
    MAX-ACCESS  read-only
    STATUS      current
    DESCRIPTION "Egress IPv6 packets successfully processed "
    ::= { affirmedSecurityStatisticsCpu-levelDataStatsNewEntry 9 }

affirmedSecurityStatisticsCpu-levelDataStatsNewTxV6Bytes OBJECT-TYPE
    SYNTAX      ConfdString
    MAX-ACCESS  read-only
    STATUS      current
    DESCRIPTION "Egress IPv6 bytes successfully processed "
    ::= { affirmedSecurityStatisticsCpu-levelDataStatsNewEntry 10 }

affirmedSecurityStatisticsCpu-levelDataStatsNewRxPostSecurityV4Pkts OBJECT-TYPE
    SYNTAX      ConfdString
    MAX-ACCESS  read-only
    STATUS      current
    DESCRIPTION "Dequeued ingress IPv4 packets successfully processed "
    ::= { affirmedSecurityStatisticsCpu-levelDataStatsNewEntry 11 }

affirmedSecurityStatisticsCpu-levelDataStatsNewRxPostSecurityV4Bytes OBJECT-TYPE
    SYNTAX      ConfdString
    MAX-ACCESS  read-only
    STATUS      current
    DESCRIPTION "Dequeued ingress IPv4 bytes successfully processed "
    ::= { affirmedSecurityStatisticsCpu-levelDataStatsNewEntry 12 }

affirmedSecurityStatisticsCpu-levelDataStatsNewRxPostSecurityV6Pkts OBJECT-TYPE
    SYNTAX      ConfdString
    MAX-ACCESS  read-only
    STATUS      current
    DESCRIPTION "Dequeued ingress IPv6 packets successfully processed "
    ::= { affirmedSecurityStatisticsCpu-levelDataStatsNewEntry 13 }

affirmedSecurityStatisticsCpu-levelDataStatsNewRxPostSecurityV6Bytes OBJECT-TYPE
    SYNTAX      ConfdString
    MAX-ACCESS  read-only
    STATUS      current
    DESCRIPTION "Dequeued ingress IPv6 bytes successfully processed "
    ::= { affirmedSecurityStatisticsCpu-levelDataStatsNewEntry 14 }

affirmedSecurityStatisticsCpu-levelDataStatsNewRxEspPkts OBJECT-TYPE
    SYNTAX      ConfdString
    MAX-ACCESS  read-only
    STATUS      current
    DESCRIPTION "Authenticated and decrypted packets (ESP) received"
    ::= { affirmedSecurityStatisticsCpu-levelDataStatsNewEntry 15 }

affirmedSecurityStatisticsCpu-levelDataStatsNewRxRemoteSecmPkts OBJECT-TYPE
    SYNTAX      ConfdString
    MAX-ACCESS  read-only
    STATUS      current
    DESCRIPTION "Total packets from other SSM"
    ::= { affirmedSecurityStatisticsCpu-levelDataStatsNewEntry 16 }

affirmedSecurityStatisticsCpu-levelDataStatsNewRxSecmIngTransPkts OBJECT-TYPE
    SYNTAX      ConfdString
    MAX-ACCESS  read-only
    STATUS      current
    DESCRIPTION "Ingress packets from other SSM"
    ::= { affirmedSecurityStatisticsCpu-levelDataStatsNewEntry 17 }

affirmedSecurityStatisticsCpu-levelDataStatsNewRxSecmEgrTransPkts OBJECT-TYPE
    SYNTAX      ConfdString
    MAX-ACCESS  read-only
    STATUS      current
    DESCRIPTION "Egress packets from other SSM"
    ::= { affirmedSecurityStatisticsCpu-levelDataStatsNewEntry 18 }

affirmedSecurityStatisticsCpu-levelDataStatsNewRxSpmPktsIgnored OBJECT-TYPE
    SYNTAX      ConfdString
    MAX-ACCESS  read-only
    STATUS      current
    DESCRIPTION "Packets from SPM ignored"
    ::= { affirmedSecurityStatisticsCpu-levelDataStatsNewEntry 19 }

affirmedSecurityStatisticsCpu-levelDataStatsNewFwdRemoteSecmPkts OBJECT-TYPE
    SYNTAX      ConfdString
    MAX-ACCESS  read-only
    STATUS      current
    DESCRIPTION "Egress packets sent to other SSM"
    ::= { affirmedSecurityStatisticsCpu-levelDataStatsNewEntry 20 }

affirmedSecurityStatisticsCpu-levelDataStatsNewFwdSpmPkts OBJECT-TYPE
    SYNTAX      ConfdString
    MAX-ACCESS  read-only
    STATUS      current
    DESCRIPTION "Packets forwarded to SPM"
    ::= { affirmedSecurityStatisticsCpu-levelDataStatsNewEntry 21 }

affirmedSecurityStatisticsCpu-levelDataStatsNewSecmIngPktsFwdFail OBJECT-TYPE
    SYNTAX      ConfdString
    MAX-ACCESS  read-only
    STATUS      current
    DESCRIPTION "Ingress packet from other SSM failures"
    ::= { affirmedSecurityStatisticsCpu-levelDataStatsNewEntry 22 }

affirmedSecurityStatisticsCpu-levelDataStatsNewSecmEgrPktsFwdFail OBJECT-TYPE
    SYNTAX      ConfdString
    MAX-ACCESS  read-only
    STATUS      current
    DESCRIPTION "Egress packet from other SSM failures"
    ::= { affirmedSecurityStatisticsCpu-levelDataStatsNewEntry 23 }

affirmedSecurityStatisticsCpu-levelDataStatsNewRxBypassRulePkts OBJECT-TYPE
    SYNTAX      ConfdString
    MAX-ACCESS  read-only
    STATUS      current
    DESCRIPTION "Packets received that bypass security"
    ::= { affirmedSecurityStatisticsCpu-levelDataStatsNewEntry 24 }

affirmedSecurityStatisticsCpu-levelDataStatsNewTxBypassRulePkts OBJECT-TYPE
    SYNTAX      ConfdString
    MAX-ACCESS  read-only
    STATUS      current
    DESCRIPTION "WF Packets from other SSM that bypass security"
    ::= { affirmedSecurityStatisticsCpu-levelDataStatsNewEntry 25 }

affirmedSecurityStatisticsCpu-levelDataStatsNewBypassV4IkeFragment OBJECT-TYPE
    SYNTAX      ConfdString
    MAX-ACCESS  read-only
    STATUS      current
    DESCRIPTION "SPM has sent an IKE packet that was fragmented"
    ::= { affirmedSecurityStatisticsCpu-levelDataStatsNewEntry 26 }

affirmedSecurityStatisticsCpu-levelDataStatsNewBypassV4Multicast OBJECT-TYPE
    SYNTAX      ConfdString
    MAX-ACCESS  read-only
    STATUS      current
    DESCRIPTION "V4 Multicast pkts"
    ::= { affirmedSecurityStatisticsCpu-levelDataStatsNewEntry 27 }

affirmedSecurityStatisticsCpu-levelDataStatsNewBypassV6NdNbrIcmp OBJECT-TYPE
    SYNTAX      ConfdString
    MAX-ACCESS  read-only
    STATUS      current
    DESCRIPTION "V6 Neighbor advertisement"
    ::= { affirmedSecurityStatisticsCpu-levelDataStatsNewEntry 28 }

affirmedSecurityStatisticsCpu-levelDataStatsNewBypassV6Multicast OBJECT-TYPE
    SYNTAX      ConfdString
    MAX-ACCESS  read-only
    STATUS      current
    DESCRIPTION "V6 Multicast pkts"
    ::= { affirmedSecurityStatisticsCpu-levelDataStatsNewEntry 29 }

affirmedSecurityStatisticsCpu-levelDataStatsNewBypassV6LinkLocalDest OBJECT-TYPE
    SYNTAX      ConfdString
    MAX-ACCESS  read-only
    STATUS      current
    DESCRIPTION "V6 link local dest pkts"
    ::= { affirmedSecurityStatisticsCpu-levelDataStatsNewEntry 30 }

affirmedSecurityStatisticsCpu-levelDataStatsNewBypassV6LinkLocalSrc OBJECT-TYPE
    SYNTAX      ConfdString
    MAX-ACCESS  read-only
    STATUS      current
    DESCRIPTION "V6 link local src pkts"
    ::= { affirmedSecurityStatisticsCpu-levelDataStatsNewEntry 31 }

affirmedSecurityStatisticsCpu-levelDataStatsNewBypassTid0V6Icmp OBJECT-TYPE
    SYNTAX      ConfdString
    MAX-ACCESS  read-only
    STATUS      current
    DESCRIPTION "V6 Non-ping icmp pkt"
    ::= { affirmedSecurityStatisticsCpu-levelDataStatsNewEntry 32 }

affirmedSecurityStatisticsCpu-levelDataStatsNewBypassTid0IngressIke OBJECT-TYPE
    SYNTAX      ConfdString
    MAX-ACCESS  read-only
    STATUS      current
    DESCRIPTION "Ingress IKE pkt"
    ::= { affirmedSecurityStatisticsCpu-levelDataStatsNewEntry 33 }

affirmedSecurityStatisticsCpu-levelDataStatsNewBypassTid0IngressIkeNatt OBJECT-TYPE
    SYNTAX      ConfdString
    MAX-ACCESS  read-only
    STATUS      current
    DESCRIPTION "Ingress IKE NATT pkt"
    ::= { affirmedSecurityStatisticsCpu-levelDataStatsNewEntry 34 }

affirmedSecurityStatisticsCpu-levelDataStatsNewBypassTid0IngressV4DhcpClient OBJECT-TYPE
    SYNTAX      ConfdString
    MAX-ACCESS  read-only
    STATUS      current
    DESCRIPTION "Ingress V4 DHCP Client"
    ::= { affirmedSecurityStatisticsCpu-levelDataStatsNewEntry 35 }

affirmedSecurityStatisticsCpu-levelDataStatsNewBypassTid0EgressV4DnsClient OBJECT-TYPE
    SYNTAX      ConfdString
    MAX-ACCESS  read-only
    STATUS      current
    DESCRIPTION "Ingress V4 DNS Client"
    ::= { affirmedSecurityStatisticsCpu-levelDataStatsNewEntry 36 }

affirmedSecurityStatisticsCpu-levelDataStatsNewBypassTid1IngressUdp OBJECT-TYPE
    SYNTAX      ConfdString
    MAX-ACCESS  read-only
    STATUS      current
    DESCRIPTION "BypassTid1IngressUdp"
    ::= { affirmedSecurityStatisticsCpu-levelDataStatsNewEntry 37 }

affirmedSecurityStatisticsCpu-levelDataStatsNewTxEspPkts OBJECT-TYPE
    SYNTAX      ConfdString
    MAX-ACCESS  read-only
    STATUS      current
    DESCRIPTION "Packets to be encrypted and authentication calculated"
    ::= { affirmedSecurityStatisticsCpu-levelDataStatsNewEntry 38 }

affirmedSecurityStatisticsCpu-levelDataStatsNewQueuedPkts OBJECT-TYPE
    SYNTAX      ConfdString
    MAX-ACCESS  read-only
    STATUS      current
    DESCRIPTION "Packets queued waiting for SPM to validate flow"
    ::= { affirmedSecurityStatisticsCpu-levelDataStatsNewEntry 39 }

affirmedSecurityStatisticsCpu-levelDataStatsNewDequeuedPkts OBJECT-TYPE
    SYNTAX      ConfdString
    MAX-ACCESS  read-only
    STATUS      current
    DESCRIPTION "Packets dequeued when SPM validates flow"
    ::= { affirmedSecurityStatisticsCpu-levelDataStatsNewEntry 40 }

affirmedSecurityStatisticsCpu-levelDataStatsNewTransactionsAllocated OBJECT-TYPE
    SYNTAX      ConfdString
    MAX-ACCESS  read-only
    STATUS      current
    DESCRIPTION "Transactions Allocated"
    ::= { affirmedSecurityStatisticsCpu-levelDataStatsNewEntry 41 }

affirmedSecurityStatisticsCpu-levelDataStatsNewTransactionsDeallocated OBJECT-TYPE
    SYNTAX      ConfdString
    MAX-ACCESS  read-only
    STATUS      current
    DESCRIPTION "TransactionsDeallocated"
    ::= { affirmedSecurityStatisticsCpu-levelDataStatsNewEntry 42 }

affirmedSecurityStatisticsCpu-levelDataStatsNewIngressIke OBJECT-TYPE
    SYNTAX      ConfdString
    MAX-ACCESS  read-only
    STATUS      current
    DESCRIPTION "IngressIke"
    ::= { affirmedSecurityStatisticsCpu-levelDataStatsNewEntry 43 }

affirmedSecurityStatisticsCpu-levelDataStatsNewIngressIkeNatt OBJECT-TYPE
    SYNTAX      ConfdString
    MAX-ACCESS  read-only
    STATUS      current
    DESCRIPTION "IngressIkeNatt"
    ::= { affirmedSecurityStatisticsCpu-levelDataStatsNewEntry 44 }

affirmedSecurityStatisticsCpu-levelDataStatsNewEgressIke OBJECT-TYPE
    SYNTAX      ConfdString
    MAX-ACCESS  read-only
    STATUS      current
    DESCRIPTION "EgressIke"
    ::= { affirmedSecurityStatisticsCpu-levelDataStatsNewEntry 45 }

affirmedSecurityStatisticsCpu-levelDataStatsNewEgressIkeNatt OBJECT-TYPE
    SYNTAX      ConfdString
    MAX-ACCESS  read-only
    STATUS      current
    DESCRIPTION "EgressIkeNatt"
    ::= { affirmedSecurityStatisticsCpu-levelDataStatsNewEntry 46 }

affirmedSecurityStatisticsCpu-levelDataStatsNewUseableRuleHits OBJECT-TYPE
    SYNTAX      ConfdString
    MAX-ACCESS  read-only
    STATUS      current
    DESCRIPTION "UseableRuleHits"
    ::= { affirmedSecurityStatisticsCpu-levelDataStatsNewEntry 47 }

affirmedSecurityStatisticsCpu-levelDataStatsNewDropPktsRule OBJECT-TYPE
    SYNTAX      ConfdString
    MAX-ACCESS  read-only
    STATUS      current
    DESCRIPTION "Packets dropped via an explicit rule"
    ::= { affirmedSecurityStatisticsCpu-levelDataStatsNewEntry 48 }

affirmedSecurityStatisticsCpu-levelDataStatsNewDropPktsRejectRule OBJECT-TYPE
    SYNTAX      ConfdString
    MAX-ACCESS  read-only
    STATUS      current
    DESCRIPTION "Packets rejected via an explicit rule"
    ::= { affirmedSecurityStatisticsCpu-levelDataStatsNewEntry 49 }

affirmedSecurityStatisticsCpu-levelDataStatsNewPassRuleHits OBJECT-TYPE
    SYNTAX      ConfdString
    MAX-ACCESS  read-only
    STATUS      current
    DESCRIPTION "PassRuleHits"
    ::= { affirmedSecurityStatisticsCpu-levelDataStatsNewEntry 50 }

affirmedSecurityStatisticsCpu-levelDataStatsNewApplyRuleHits OBJECT-TYPE
    SYNTAX      ConfdString
    MAX-ACCESS  read-only
    STATUS      current
    DESCRIPTION "ApplyRuleHits"
    ::= { affirmedSecurityStatisticsCpu-levelDataStatsNewEntry 51 }

affirmedSecurityStatisticsCpu-levelDataStatsNewRxNattKaPkts OBJECT-TYPE
    SYNTAX      ConfdString
    MAX-ACCESS  read-only
    STATUS      current
    DESCRIPTION "RxNattKaPkts"
    ::= { affirmedSecurityStatisticsCpu-levelDataStatsNewEntry 52 }

affirmedSecurityStatisticsCpu-levelDataStatsNewRxEpdgPkts OBJECT-TYPE
    SYNTAX      ConfdString
    MAX-ACCESS  read-only
    STATUS      current
    DESCRIPTION "Packets received for epdg sessions."
    ::= { affirmedSecurityStatisticsCpu-levelDataStatsNewEntry 53 }

affirmedSecurityStatisticsCpu-levelDataStatsNewTxEpdgPkts OBJECT-TYPE
    SYNTAX      ConfdString
    MAX-ACCESS  read-only
    STATUS      current
    DESCRIPTION "Packets transmitted for epdg sessions."
    ::= { affirmedSecurityStatisticsCpu-levelDataStatsNewEntry 54 }

affirmedSecurityStatisticsCpu-levelDataStatsNewRxIkeApplyPolicy OBJECT-TYPE
    SYNTAX      ConfdString
    MAX-ACCESS  read-only
    STATUS      current
    DESCRIPTION "IKE packets passed via configured policy."
    ::= { affirmedSecurityStatisticsCpu-levelDataStatsNewEntry 55 }

affirmedSecurityStatisticsCpu-levelDataStatsNewRxIkeNattApplyPolicy OBJECT-TYPE
    SYNTAX      ConfdString
    MAX-ACCESS  read-only
    STATUS      current
    DESCRIPTION "IKE NAT-T packets passed via configured policy."
    ::= { affirmedSecurityStatisticsCpu-levelDataStatsNewEntry 56 }

affirmedSecurityStatisticsCpu-levelDataStatsNewRxV4DropPkts OBJECT-TYPE
    SYNTAX      ConfdString
    MAX-ACCESS  read-only
    STATUS      current
    DESCRIPTION "Ingress IPv4 packets dropped"
    ::= { affirmedSecurityStatisticsCpu-levelDataStatsNewEntry 57 }

affirmedSecurityStatisticsCpu-levelDataStatsNewRxV4DropBytes OBJECT-TYPE
    SYNTAX      ConfdString
    MAX-ACCESS  read-only
    STATUS      current
    DESCRIPTION "Ingress IPv4 bytes dropped"
    ::= { affirmedSecurityStatisticsCpu-levelDataStatsNewEntry 58 }

affirmedSecurityStatisticsCpu-levelDataStatsNewRxV6DropPkts OBJECT-TYPE
    SYNTAX      ConfdString
    MAX-ACCESS  read-only
    STATUS      current
    DESCRIPTION "Ingress IPv6 packets dropped"
    ::= { affirmedSecurityStatisticsCpu-levelDataStatsNewEntry 59 }

affirmedSecurityStatisticsCpu-levelDataStatsNewRxV6DropBytes OBJECT-TYPE
    SYNTAX      ConfdString
    MAX-ACCESS  read-only
    STATUS      current
    DESCRIPTION "Ingress IPv6 bytes dropped"
    ::= { affirmedSecurityStatisticsCpu-levelDataStatsNewEntry 60 }

affirmedSecurityStatisticsCpu-levelDataStatsNewTxV4DropPkts OBJECT-TYPE
    SYNTAX      ConfdString
    MAX-ACCESS  read-only
    STATUS      current
    DESCRIPTION "Egress IPv4 packets dropped"
    ::= { affirmedSecurityStatisticsCpu-levelDataStatsNewEntry 61 }

affirmedSecurityStatisticsCpu-levelDataStatsNewTxV4DropBytes OBJECT-TYPE
    SYNTAX      ConfdString
    MAX-ACCESS  read-only
    STATUS      current
    DESCRIPTION "Egress IPv4 bytes dropped"
    ::= { affirmedSecurityStatisticsCpu-levelDataStatsNewEntry 62 }

affirmedSecurityStatisticsCpu-levelDataStatsNewTxV6DropPkts OBJECT-TYPE
    SYNTAX      ConfdString
    MAX-ACCESS  read-only
    STATUS      current
    DESCRIPTION "Egress IPv6 packets dropped"
    ::= { affirmedSecurityStatisticsCpu-levelDataStatsNewEntry 63 }

affirmedSecurityStatisticsCpu-levelDataStatsNewTxV6DropBytes OBJECT-TYPE
    SYNTAX      ConfdString
    MAX-ACCESS  read-only
    STATUS      current
    DESCRIPTION "Egress IPv6 bytes dropped"
    ::= { affirmedSecurityStatisticsCpu-levelDataStatsNewEntry 64 }

affirmedSecurityStatisticsCpu-levelDataStatsNewRemoteTransError OBJECT-TYPE
    SYNTAX      ConfdString
    MAX-ACCESS  read-only
    STATUS      current
    DESCRIPTION "Packets sent to wrong SSM"
    ::= { affirmedSecurityStatisticsCpu-levelDataStatsNewEntry 65 }

affirmedSecurityStatisticsCpu-levelDataStatsNewInvalidHeaderError OBJECT-TYPE
    SYNTAX      ConfdString
    MAX-ACCESS  read-only
    STATUS      current
    DESCRIPTION "Packets with bad IP header or length less than IP length"
    ::= { affirmedSecurityStatisticsCpu-levelDataStatsNewEntry 66 }

affirmedSecurityStatisticsCpu-levelDataStatsNewRxPendingFlowError OBJECT-TYPE
    SYNTAX      ConfdString
    MAX-ACCESS  read-only
    STATUS      current
    DESCRIPTION "Ingress Packets dropped because SPM has not validated flow"
    ::= { affirmedSecurityStatisticsCpu-levelDataStatsNewEntry 67 }

affirmedSecurityStatisticsCpu-levelDataStatsNewTxPendingFlowError OBJECT-TYPE
    SYNTAX      ConfdString
    MAX-ACCESS  read-only
    STATUS      current
    DESCRIPTION "Egress Packets dropped because SPM has not validated flow"
    ::= { affirmedSecurityStatisticsCpu-levelDataStatsNewEntry 68 }

affirmedSecurityStatisticsCpu-levelDataStatsNewNoFlowErrorIngress OBJECT-TYPE
    SYNTAX      ConfdString
    MAX-ACCESS  read-only
    STATUS      current
    DESCRIPTION "NoFlowErrorIngress"
    ::= { affirmedSecurityStatisticsCpu-levelDataStatsNewEntry 69 }

affirmedSecurityStatisticsCpu-levelDataStatsNewNoFlowErrorEgress OBJECT-TYPE
    SYNTAX      ConfdString
    MAX-ACCESS  read-only
    STATUS      current
    DESCRIPTION "NoFlowErrorEgress"
    ::= { affirmedSecurityStatisticsCpu-levelDataStatsNewEntry 70 }

affirmedSecurityStatisticsCpu-levelDataStatsNewTransNotFoundError OBJECT-TYPE
    SYNTAX      ConfdString
    MAX-ACCESS  read-only
    STATUS      current
    DESCRIPTION "Packets dropped because transform not in hash"
    ::= { affirmedSecurityStatisticsCpu-levelDataStatsNewEntry 71 }

affirmedSecurityStatisticsCpu-levelDataStatsNewIngCtxtInUse OBJECT-TYPE
    SYNTAX      ConfdString
    MAX-ACCESS  read-only
    STATUS      current
    DESCRIPTION "Ingress packet dropped by hdw crypto because rekeying not done"
    ::= { affirmedSecurityStatisticsCpu-levelDataStatsNewEntry 72 }

affirmedSecurityStatisticsCpu-levelDataStatsNewFailedSanity OBJECT-TYPE
    SYNTAX      ConfdString
    MAX-ACCESS  read-only
    STATUS      current
    DESCRIPTION "Ingress packets dropped by hdw crypto for memory corruption"
    ::= { affirmedSecurityStatisticsCpu-levelDataStatsNewEntry 73 }

affirmedSecurityStatisticsCpu-levelDataStatsNewDropPktsIntfNotFound OBJECT-TYPE
    SYNTAX      ConfdString
    MAX-ACCESS  read-only
    STATUS      current
    DESCRIPTION "Packets dropped when transmit logical interface not found"
    ::= { affirmedSecurityStatisticsCpu-levelDataStatsNewEntry 74 }

affirmedSecurityStatisticsCpu-levelDataStatsNewDropPktsSessionNotFound OBJECT-TYPE
    SYNTAX      ConfdString
    MAX-ACCESS  read-only
    STATUS      current
    DESCRIPTION "WF packets dropped when session not found"
    ::= { affirmedSecurityStatisticsCpu-levelDataStatsNewEntry 75 }

affirmedSecurityStatisticsCpu-levelDataStatsNewDropPktsSecurityDisabled OBJECT-TYPE
    SYNTAX      ConfdString
    MAX-ACCESS  read-only
    STATUS      current
    DESCRIPTION "DropPktsSecurityDisabled"
    ::= { affirmedSecurityStatisticsCpu-levelDataStatsNewEntry 76 }

affirmedSecurityStatisticsCpu-levelDataStatsNewTransactionsDeallocFailed OBJECT-TYPE
    SYNTAX      ConfdString
    MAX-ACCESS  read-only
    STATUS      current
    DESCRIPTION "Transaction deallocoations failures"
    ::= { affirmedSecurityStatisticsCpu-levelDataStatsNewEntry 77 }

affirmedSecurityStatisticsCpu-levelDataStatsNewInvalidNumaNode OBJECT-TYPE
    SYNTAX      ConfdString
    MAX-ACCESS  read-only
    STATUS      current
    DESCRIPTION "Received a non-default numaNode"
    ::= { affirmedSecurityStatisticsCpu-levelDataStatsNewEntry 78 }

affirmedSecurityStatisticsCpu-levelDataStatsNewIngSpiMismatch OBJECT-TYPE
    SYNTAX      ConfdString
    MAX-ACCESS  read-only
    STATUS      current
    DESCRIPTION "Ingress packet's SPI matches neither transform's SPI"
    ::= { affirmedSecurityStatisticsCpu-levelDataStatsNewEntry 79 }

affirmedSecurityStatisticsCpu-levelDataStatsNewEgrSpiMismatch OBJECT-TYPE
    SYNTAX      ConfdString
    MAX-ACCESS  read-only
    STATUS      current
    DESCRIPTION "SPI set up in egress packet matches neither egress SPI"
    ::= { affirmedSecurityStatisticsCpu-levelDataStatsNewEntry 80 }

affirmedSecurityStatisticsCpu-levelDataStatsNewTransAuthErrs OBJECT-TYPE
    SYNTAX      ConfdString
    MAX-ACCESS  read-only
    STATUS      current
    DESCRIPTION "Ingress packet failed pre cipher checks"
    ::= { affirmedSecurityStatisticsCpu-levelDataStatsNewEntry 81 }

affirmedSecurityStatisticsCpu-levelDataStatsNewPostSecTransAuthErrs OBJECT-TYPE
    SYNTAX      ConfdString
    MAX-ACCESS  read-only
    STATUS      current
    DESCRIPTION "Ingress packet failed post cipher checks"
    ::= { affirmedSecurityStatisticsCpu-levelDataStatsNewEntry 82 }

affirmedSecurityStatisticsCpu-levelDataStatsNewPostSecPktErrs OBJECT-TYPE
    SYNTAX      ConfdString
    MAX-ACCESS  read-only
    STATUS      current
    DESCRIPTION "Decrypted packet failed non-cipher checks"
    ::= { affirmedSecurityStatisticsCpu-levelDataStatsNewEntry 83 }

affirmedSecurityStatisticsCpu-levelDataStatsNewPostSecPktErrsInvalidHeader OBJECT-TYPE
    SYNTAX      ConfdString
    MAX-ACCESS  read-only
    STATUS      current
    DESCRIPTION "PostSecPktErrsInvalidHeader"
    ::= { affirmedSecurityStatisticsCpu-levelDataStatsNewEntry 84 }

affirmedSecurityStatisticsCpu-levelDataStatsNewPostSecPktErrsInvalidFragHeader OBJECT-TYPE
    SYNTAX      ConfdString
    MAX-ACCESS  read-only
    STATUS      current
    DESCRIPTION "PostSecPktErrsInvalidFragHeader"
    ::= { affirmedSecurityStatisticsCpu-levelDataStatsNewEntry 85 }

affirmedSecurityStatisticsCpu-levelDataStatsNewPostSecPktErrsNoFlowFound OBJECT-TYPE
    SYNTAX      ConfdString
    MAX-ACCESS  read-only
    STATUS      current
    DESCRIPTION "PostSecPktErrsNoFlowFound"
    ::= { affirmedSecurityStatisticsCpu-levelDataStatsNewEntry 86 }

affirmedSecurityStatisticsCpu-levelDataStatsNewPostSecPktErrsBadFlowFound OBJECT-TYPE
    SYNTAX      ConfdString
    MAX-ACCESS  read-only
    STATUS      current
    DESCRIPTION "PostSecPktErrsBadFlowFound"
    ::= { affirmedSecurityStatisticsCpu-levelDataStatsNewEntry 87 }

affirmedSecurityStatisticsCpu-levelDataStatsNewPostSecPktErrsUnexpectedPendFlow OBJECT-TYPE
    SYNTAX      ConfdString
    MAX-ACCESS  read-only
    STATUS      current
    DESCRIPTION "PostSecPktErrsUnexpectedPendFlow"
    ::= { affirmedSecurityStatisticsCpu-levelDataStatsNewEntry 88 }

affirmedSecurityStatisticsCpu-levelDataStatsNewPostSecPktErrsUnexpectedApplyFlow OBJECT-TYPE
    SYNTAX      ConfdString
    MAX-ACCESS  read-only
    STATUS      current
    DESCRIPTION "PostSecPktErrsUnexpectedApplyFlow"
    ::= { affirmedSecurityStatisticsCpu-levelDataStatsNewEntry 89 }

affirmedSecurityStatisticsCpu-levelDataStatsNewPostSecPktErrsUnexpectedRejectFlow OBJECT-TYPE
    SYNTAX      ConfdString
    MAX-ACCESS  read-only
    STATUS      current
    DESCRIPTION "PostSecPktErrsUnexpectedRejectFlow"
    ::= { affirmedSecurityStatisticsCpu-levelDataStatsNewEntry 90 }

affirmedSecurityStatisticsCpu-levelDataStatsNewPostSecPktErrsUnexpectedTriggerFlow OBJECT-TYPE
    SYNTAX      ConfdString
    MAX-ACCESS  read-only
    STATUS      current
    DESCRIPTION "PostSecPktErrsUnexpectedTriggerFlow"
    ::= { affirmedSecurityStatisticsCpu-levelDataStatsNewEntry 91 }

affirmedSecurityStatisticsCpu-levelDataStatsNewPostSecPktErrsUnexpectedDropFlow OBJECT-TYPE
    SYNTAX      ConfdString
    MAX-ACCESS  read-only
    STATUS      current
    DESCRIPTION "PostSecPktErrsUnexpectedDropFlow"
    ::= { affirmedSecurityStatisticsCpu-levelDataStatsNewEntry 92 }

affirmedSecurityStatisticsCpu-levelDataStatsNewPostSecPktErrsUnexpectedNonExistentFlow OBJECT-TYPE
    SYNTAX      ConfdString
    MAX-ACCESS  read-only
    STATUS      current
    DESCRIPTION "PostSecPktErrsUnexpectedNonExistentFlow"
    ::= { affirmedSecurityStatisticsCpu-levelDataStatsNewEntry 93 }

affirmedSecurityStatisticsCpu-levelDataStatsNewPostSecIntfPktErrs OBJECT-TYPE
    SYNTAX      ConfdString
    MAX-ACCESS  read-only
    STATUS      current
    DESCRIPTION "Remotely originated decrypted packet transmit failures"
    ::= { affirmedSecurityStatisticsCpu-levelDataStatsNewEntry 94 }

affirmedSecurityStatisticsCpu-levelDataStatsNewPostSecFpPktErrs OBJECT-TYPE
    SYNTAX      ConfdString
    MAX-ACCESS  read-only
    STATUS      current
    DESCRIPTION "Locally originated decrypted packet transmit failures"
    ::= { affirmedSecurityStatisticsCpu-levelDataStatsNewEntry 95 }

affirmedSecurityStatisticsCpu-levelDataStatsNewIngCtxtErrs OBJECT-TYPE
    SYNTAX      ConfdString
    MAX-ACCESS  read-only
    STATUS      current
    DESCRIPTION "Ingress packet dropped crypto context errors."
    ::= { affirmedSecurityStatisticsCpu-levelDataStatsNewEntry 96 }

affirmedSecurityStatisticsCpu-levelDataStatsNewEgrCtxtErrs OBJECT-TYPE
    SYNTAX      ConfdString
    MAX-ACCESS  read-only
    STATUS      current
    DESCRIPTION "Egress packet dropped crypto context errors."
    ::= { affirmedSecurityStatisticsCpu-levelDataStatsNewEntry 97 }

affirmedSecurityStatisticsCpu-levelDataStatsNewUnuseableRuleHits OBJECT-TYPE
    SYNTAX      ConfdString
    MAX-ACCESS  read-only
    STATUS      current
    DESCRIPTION "UnuseableRuleHits"
    ::= { affirmedSecurityStatisticsCpu-levelDataStatsNewEntry 98 }

affirmedSecurityStatisticsCpu-levelDataStatsNewInvalidRuleHits OBJECT-TYPE
    SYNTAX      ConfdString
    MAX-ACCESS  read-only
    STATUS      current
    DESCRIPTION "InvalidRuleHits"
    ::= { affirmedSecurityStatisticsCpu-levelDataStatsNewEntry 99 }

affirmedSecurityStatisticsCpu-levelDataStatsNewTriggerRuleHits OBJECT-TYPE
    SYNTAX      ConfdString
    MAX-ACCESS  read-only
    STATUS      current
    DESCRIPTION "Packets that matched a configured trigger rule"
    ::= { affirmedSecurityStatisticsCpu-levelDataStatsNewEntry 100 }

affirmedSecurityStatisticsCpu-levelDataStatsNewDormantApplyRuleHits OBJECT-TYPE
    SYNTAX      ConfdString
    MAX-ACCESS  read-only
    STATUS      current
    DESCRIPTION "DormantApplyRuleHits"
    ::= { affirmedSecurityStatisticsCpu-levelDataStatsNewEntry 101 }

affirmedSecurityStatisticsCpu-levelDataStatsNewUnknownRuleHits OBJECT-TYPE
    SYNTAX      ConfdString
    MAX-ACCESS  read-only
    STATUS      current
    DESCRIPTION "UnknownRuleHits"
    ::= { affirmedSecurityStatisticsCpu-levelDataStatsNewEntry 102 }

affirmedSecurityStatisticsCpu-levelDataStatsNewNoFlowPassAtRemoteSecm OBJECT-TYPE
    SYNTAX      ConfdString
    MAX-ACCESS  read-only
    STATUS      current
    DESCRIPTION "Passes match no flow pass rule, but should not send to spm"
    ::= { affirmedSecurityStatisticsCpu-levelDataStatsNewEntry 103 }

affirmedSecurityStatisticsCpu-levelDataStatsNewPktsDiscarded OBJECT-TYPE
    SYNTAX      ConfdString
    MAX-ACCESS  read-only
    STATUS      current
    DESCRIPTION "PktsDiscarded"
    ::= { affirmedSecurityStatisticsCpu-levelDataStatsNewEntry 104 }

affirmedSecurityStatisticsCpu-levelDataStatsNewNoFlowPassDrop OBJECT-TYPE
    SYNTAX      ConfdString
    MAX-ACCESS  read-only
    STATUS      current
    DESCRIPTION "NoFlowPassDrop"
    ::= { affirmedSecurityStatisticsCpu-levelDataStatsNewEntry 105 }

affirmedSecurityStatisticsCpu-levelDataStatsNewNoFlowTid0IngressIPsec OBJECT-TYPE
    SYNTAX      ConfdString
    MAX-ACCESS  read-only
    STATUS      current
    DESCRIPTION "NoFlowTid0IngressIPsec"
    ::= { affirmedSecurityStatisticsCpu-levelDataStatsNewEntry 106 }

affirmedSecurityStatisticsCpu-levelDataStatsNewNoFlowTidV6IcmpErr OBJECT-TYPE
    SYNTAX      ConfdString
    MAX-ACCESS  read-only
    STATUS      current
    DESCRIPTION "NoFlowTidV6IcmpErr"
    ::= { affirmedSecurityStatisticsCpu-levelDataStatsNewEntry 107 }

affirmedSecurityStatisticsCpu-levelDataStatsNewNoFlowTidV4IcmpErr OBJECT-TYPE
    SYNTAX      ConfdString
    MAX-ACCESS  read-only
    STATUS      current
    DESCRIPTION "NoFlowTidV4IcmpErr"
    ::= { affirmedSecurityStatisticsCpu-levelDataStatsNewEntry 108 }

affirmedSecurityStatisticsCpu-levelDataStatsNewDropPktsTooBig OBJECT-TYPE
    SYNTAX      ConfdString
    MAX-ACCESS  read-only
    STATUS      current
    DESCRIPTION "Packets too big for hardware crypto"
    ::= { affirmedSecurityStatisticsCpu-levelDataStatsNewEntry 109 }

affirmedSecurityStatisticsCpu-levelDataStatsNewDropPktsNoRule OBJECT-TYPE
    SYNTAX      ConfdString
    MAX-ACCESS  read-only
    STATUS      current
    DESCRIPTION "Packets dropped due to no or bad rule"
    ::= { affirmedSecurityStatisticsCpu-levelDataStatsNewEntry 110 }

affirmedSecurityStatisticsCpu-levelDataStatsNewDropPktsTriggerRule OBJECT-TYPE
    SYNTAX      ConfdString
    MAX-ACCESS  read-only
    STATUS      current
    DESCRIPTION "Packets rejected via a trigger explicit rule"
    ::= { affirmedSecurityStatisticsCpu-levelDataStatsNewEntry 111 }

affirmedSecurityStatisticsCpu-levelDataStatsNewDequeuePendingError OBJECT-TYPE
    SYNTAX      ConfdString
    MAX-ACCESS  read-only
    STATUS      current
    DESCRIPTION "Error dequeing a pending packet"
    ::= { affirmedSecurityStatisticsCpu-levelDataStatsNewEntry 112 }

affirmedSecurityStatisticsCpu-levelDataStatsNewNullSpiEntry OBJECT-TYPE
    SYNTAX      ConfdString
    MAX-ACCESS  read-only
    STATUS      current
    DESCRIPTION "NullSpiEntry"
    ::= { affirmedSecurityStatisticsCpu-levelDataStatsNewEntry 113 }

affirmedSecurityStatisticsCpu-levelDataStatsNewInvalidFSAPI OBJECT-TYPE
    SYNTAX      ConfdString
    MAX-ACCESS  read-only
    STATUS      current
    DESCRIPTION "InvalidFSAPI"
    ::= { affirmedSecurityStatisticsCpu-levelDataStatsNewEntry 114 }

affirmedSecurityStatisticsCpu-levelDataStatsNewSpiEntryFailLookup OBJECT-TYPE
    SYNTAX      ConfdString
    MAX-ACCESS  read-only
    STATUS      current
    DESCRIPTION "SpiEntryFailLookup"
    ::= { affirmedSecurityStatisticsCpu-levelDataStatsNewEntry 115 }

affirmedSecurityStatisticsCpu-levelDataStatsNewSpiTransformEntryFailLookup OBJECT-TYPE
    SYNTAX      ConfdString
    MAX-ACCESS  read-only
    STATUS      current
    DESCRIPTION "SpiTransformEntryFailLookup"
    ::= { affirmedSecurityStatisticsCpu-levelDataStatsNewEntry 116 }

affirmedSecurityStatisticsCpu-levelDataStatsNewTriggerRuleIngressPkts OBJECT-TYPE
    SYNTAX      ConfdString
    MAX-ACCESS  read-only
    STATUS      current
    DESCRIPTION "Ingress packets dropped due to match with trigger rule."
    ::= { affirmedSecurityStatisticsCpu-levelDataStatsNewEntry 117 }

affirmedSecurityStatisticsCpu-levelDataStatsNewRejectRuleHits OBJECT-TYPE
    SYNTAX      ConfdString
    MAX-ACCESS  read-only
    STATUS      current
    DESCRIPTION "RejectRuleHits"
    ::= { affirmedSecurityStatisticsCpu-levelDataStatsNewEntry 118 }

affirmedSecurityStatisticsCpu-levelDataStatsNewFlushedPkts OBJECT-TYPE
    SYNTAX      ConfdString
    MAX-ACCESS  read-only
    STATUS      current
    DESCRIPTION "Packets flushed after waiting 30 sec for SPM to validate flow"
    ::= { affirmedSecurityStatisticsCpu-levelDataStatsNewEntry 119 }

affirmedSecurityStatisticsCpu-levelDataStatsNewQueuedPktNotApply OBJECT-TYPE
    SYNTAX      ConfdString
    MAX-ACCESS  read-only
    STATUS      current
    DESCRIPTION "Queued packet dropped after not matching apply rule."
    ::= { affirmedSecurityStatisticsCpu-levelDataStatsNewEntry 120 }

affirmedSecurityStatisticsCpu-levelDataStatsNewEspSpiMismatchError OBJECT-TYPE
    SYNTAX      ConfdString
    MAX-ACCESS  read-only
    STATUS      current
    DESCRIPTION "Newly received ESP packet matches neither SPI"
    ::= { affirmedSecurityStatisticsCpu-levelDataStatsNewEntry 121 }

affirmedSecurityStatisticsCpu-levelDataStatsNewCipherNotFoundError OBJECT-TYPE
    SYNTAX      ConfdString
    MAX-ACCESS  read-only
    STATUS      current
    DESCRIPTION "Transform setup fail because cipher algorithm not found"
    ::= { affirmedSecurityStatisticsCpu-levelDataStatsNewEntry 122 }

affirmedSecurityStatisticsCpu-levelDataStatsNewPktDataAccessError OBJECT-TYPE
    SYNTAX      ConfdString
    MAX-ACCESS  read-only
    STATUS      current
    DESCRIPTION "Mismatches between packet and expected prefix lengths"
    ::= { affirmedSecurityStatisticsCpu-levelDataStatsNewEntry 123 }

affirmedSecurityStatisticsCpu-levelDataStatsNewPktSizeCipherSizeError OBJECT-TYPE
    SYNTAX      ConfdString
    MAX-ACCESS  read-only
    STATUS      current
    DESCRIPTION "Encrypted packet size not a multiple of cipher block size"
    ::= { affirmedSecurityStatisticsCpu-levelDataStatsNewEntry 124 }

affirmedSecurityStatisticsCpu-levelDataStatsNewPktTooShortError OBJECT-TYPE
    SYNTAX      ConfdString
    MAX-ACCESS  read-only
    STATUS      current
    DESCRIPTION "Encrypted packet size less than necessary prefix and trailer sizes"
    ::= { affirmedSecurityStatisticsCpu-levelDataStatsNewEntry 125 }

affirmedSecurityStatisticsCpu-levelDataStatsNewPktLenMismatchError OBJECT-TYPE
    SYNTAX      ConfdString
    MAX-ACCESS  read-only
    STATUS      current
    DESCRIPTION "Internal mismatch between calculated and actual lengths"
    ::= { affirmedSecurityStatisticsCpu-levelDataStatsNewEntry 126 }

affirmedSecurityStatisticsCpu-levelDataStatsNewParsePktHeaderError OBJECT-TYPE
    SYNTAX      ConfdString
    MAX-ACCESS  read-only
    STATUS      current
    DESCRIPTION "All errors parsing encrypted packet headers"
    ::= { affirmedSecurityStatisticsCpu-levelDataStatsNewEntry 127 }

affirmedSecurityStatisticsCpu-levelDataStatsNewCalcPktInfoError OBJECT-TYPE
    SYNTAX      ConfdString
    MAX-ACCESS  read-only
    STATUS      current
    DESCRIPTION "All errors in ingress packet lengths"
    ::= { affirmedSecurityStatisticsCpu-levelDataStatsNewEntry 128 }

affirmedSecurityStatisticsCpu-levelDataStatsNewPrelimAntiReplayErrLo OBJECT-TYPE
    SYNTAX      ConfdString
    MAX-ACCESS  read-only
    STATUS      current
    DESCRIPTION "Ingress packet sequence number too low, before decryption"
    ::= { affirmedSecurityStatisticsCpu-levelDataStatsNewEntry 129 }

affirmedSecurityStatisticsCpu-levelDataStatsNewPrelimAntiReplayError OBJECT-TYPE
    SYNTAX      ConfdString
    MAX-ACCESS  read-only
    STATUS      current
    DESCRIPTION "Ingress packet sequence number error, but not too low, before decryption"
    ::= { affirmedSecurityStatisticsCpu-levelDataStatsNewEntry 130 }

affirmedSecurityStatisticsCpu-levelDataStatsNewEspSeqNumError OBJECT-TYPE
    SYNTAX      ConfdString
    MAX-ACCESS  read-only
    STATUS      current
    DESCRIPTION "All ESP packet sequence number errors, after decryption"
    ::= { affirmedSecurityStatisticsCpu-levelDataStatsNewEntry 131 }

affirmedSecurityStatisticsCpu-levelDataStatsNewEspSeqSecm OBJECT-TYPE
    SYNTAX      ConfdString
    MAX-ACCESS  read-only
    STATUS      current
    DESCRIPTION "secm-secm ESP packet sequence number errors, after decryption"
    ::= { affirmedSecurityStatisticsCpu-levelDataStatsNewEntry 132 }

affirmedSecurityStatisticsCpu-levelDataStatsNewEspSeqNumLow OBJECT-TYPE
    SYNTAX      ConfdString
    MAX-ACCESS  read-only
    STATUS      current
    DESCRIPTION "ESP packet sequence number too low, after decryption"
    ::= { affirmedSecurityStatisticsCpu-levelDataStatsNewEntry 133 }

affirmedSecurityStatisticsCpu-levelDataStatsNewAppendSeqHighError OBJECT-TYPE
    SYNTAX      ConfdString
    MAX-ACCESS  read-only
    STATUS      current
    DESCRIPTION "Errors appending high half of sequence number to encrypted packets"
    ::= { affirmedSecurityStatisticsCpu-levelDataStatsNewEntry 134 }

affirmedSecurityStatisticsCpu-levelDataStatsNewDeleteSeqHighError OBJECT-TYPE
    SYNTAX      ConfdString
    MAX-ACCESS  read-only
    STATUS      current
    DESCRIPTION "Errors in deleting high half sequence number after calculating ICV"
    ::= { affirmedSecurityStatisticsCpu-levelDataStatsNewEntry 135 }

affirmedSecurityStatisticsCpu-levelDataStatsNewIcvComputeError OBJECT-TYPE
    SYNTAX      ConfdString
    MAX-ACCESS  read-only
    STATUS      current
    DESCRIPTION "(hw only ) All authentication failures"
    ::= { affirmedSecurityStatisticsCpu-levelDataStatsNewEntry 136 }

affirmedSecurityStatisticsCpu-levelDataStatsNewIcvCheckError OBJECT-TYPE
    SYNTAX      ConfdString
    MAX-ACCESS  read-only
    STATUS      current
    DESCRIPTION "(sw only) post cipher authentication failures"
    ::= { affirmedSecurityStatisticsCpu-levelDataStatsNewEntry 137 }

affirmedSecurityStatisticsCpu-levelDataStatsNewIcvLenError OBJECT-TYPE
    SYNTAX      ConfdString
    MAX-ACCESS  read-only
    STATUS      current
    DESCRIPTION "(sw only) ingress packet ICV Length Errors"
    ::= { affirmedSecurityStatisticsCpu-levelDataStatsNewEntry 138 }

affirmedSecurityStatisticsCpu-levelDataStatsNewEspIcvAuthError OBJECT-TYPE
    SYNTAX      ConfdString
    MAX-ACCESS  read-only
    STATUS      current
    DESCRIPTION "(sw only) pre-cipher authentication failures"
    ::= { affirmedSecurityStatisticsCpu-levelDataStatsNewEntry 139 }

affirmedSecurityStatisticsCpu-levelDataStatsNewEspPadError OBJECT-TYPE
    SYNTAX      ConfdString
    MAX-ACCESS  read-only
    STATUS      current
    DESCRIPTION "error in pad field values"
    ::= { affirmedSecurityStatisticsCpu-levelDataStatsNewEntry 140 }

affirmedSecurityStatisticsCpu-levelDataStatsNewEspTransChainError OBJECT-TYPE
    SYNTAX      ConfdString
    MAX-ACCESS  read-only
    STATUS      current
    DESCRIPTION "(sw only) transform errors"
    ::= { affirmedSecurityStatisticsCpu-levelDataStatsNewEntry 141 }

affirmedSecurityStatisticsCpu-levelDataStatsNewEspProcessAadError OBJECT-TYPE
    SYNTAX      ConfdString
    MAX-ACCESS  read-only
    STATUS      current
    DESCRIPTION "(sw only) transform aad errors"
    ::= { affirmedSecurityStatisticsCpu-levelDataStatsNewEntry 142 }

affirmedSecurityStatisticsCpu-levelDataStatsNewTransFinishError OBJECT-TYPE
    SYNTAX      ConfdString
    MAX-ACCESS  read-only
    STATUS      current
    DESCRIPTION "post decryption errors"
    ::= { affirmedSecurityStatisticsCpu-levelDataStatsNewEntry 143 }

affirmedSecurityStatisticsCpu-levelDataStatsNewAuthAddRangeError OBJECT-TYPE
    SYNTAX      ConfdString
    MAX-ACCESS  read-only
    STATUS      current
    DESCRIPTION "Ingress segment errors"
    ::= { affirmedSecurityStatisticsCpu-levelDataStatsNewEntry 144 }

affirmedSecurityStatisticsCpu-levelDataStatsNewAuthFinishError OBJECT-TYPE
    SYNTAX      ConfdString
    MAX-ACCESS  read-only
    STATUS      current
    DESCRIPTION "Errors in finishing authentication"
    ::= { affirmedSecurityStatisticsCpu-levelDataStatsNewEntry 145 }

affirmedSecurityStatisticsCpu-levelDataStatsNewCipherUpdateError OBJECT-TYPE
    SYNTAX      ConfdString
    MAX-ACCESS  read-only
    STATUS      current
    DESCRIPTION "Errors updating cipher"
    ::= { affirmedSecurityStatisticsCpu-levelDataStatsNewEntry 146 }

affirmedSecurityStatisticsCpu-levelDataStatsNewEspSeqNumOverflowError OBJECT-TYPE
    SYNTAX      ConfdString
    MAX-ACCESS  read-only
    STATUS      current
    DESCRIPTION "egress ESP sequence number overflow"
    ::= { affirmedSecurityStatisticsCpu-levelDataStatsNewEntry 147 }

affirmedSecurityStatisticsCpu-levelDataStatsNewIngCryptoAllocFail OBJECT-TYPE
    SYNTAX      ConfdString
    MAX-ACCESS  read-only
    STATUS      current
    DESCRIPTION "Ingress context allocation failure"
    ::= { affirmedSecurityStatisticsCpu-levelDataStatsNewEntry 148 }

affirmedSecurityStatisticsCpu-levelDataStatsNewEgrCryptoAllocFail OBJECT-TYPE
    SYNTAX      ConfdString
    MAX-ACCESS  read-only
    STATUS      current
    DESCRIPTION "Egress context allocation failure"
    ::= { affirmedSecurityStatisticsCpu-levelDataStatsNewEntry 149 }

affirmedSecurityStatisticsCpu-levelDataStatsNewIngCryptoResetFail OBJECT-TYPE
    SYNTAX      ConfdString
    MAX-ACCESS  read-only
    STATUS      current
    DESCRIPTION "Ingress context reset failure"
    ::= { affirmedSecurityStatisticsCpu-levelDataStatsNewEntry 150 }

affirmedSecurityStatisticsCpu-levelDataStatsNewEgrCryptoResetFail OBJECT-TYPE
    SYNTAX      ConfdString
    MAX-ACCESS  read-only
    STATUS      current
    DESCRIPTION "Egress context reset failure"
    ::= { affirmedSecurityStatisticsCpu-levelDataStatsNewEntry 151 }

affirmedSecurityStatisticsCpu-levelDataStatsNewGetNextHopFail OBJECT-TYPE
    SYNTAX      ConfdString
    MAX-ACCESS  read-only
    STATUS      current
    DESCRIPTION "Egress packet cannot find next hop"
    ::= { affirmedSecurityStatisticsCpu-levelDataStatsNewEntry 152 }

affirmedSecurityStatisticsCpu-levelDataStatsNewNoCryptoCapability OBJECT-TYPE
    SYNTAX      ConfdString
    MAX-ACCESS  read-only
    STATUS      current
    DESCRIPTION "NoCryptoCapability"
    ::= { affirmedSecurityStatisticsCpu-levelDataStatsNewEntry 153 }

affirmedSecurityStatisticsCpu-levelDataStatsNewSecmSessionIcmpFragNeededMsgSent OBJECT-TYPE
    SYNTAX      ConfdString
    MAX-ACCESS  read-only
    STATUS      current
    DESCRIPTION "SecmSessionIcmpFragNeededMsgSent"
    ::= { affirmedSecurityStatisticsCpu-levelDataStatsNewEntry 154 }

affirmedSecurityStatisticsCpu-levelDataStatsNewSecmIcmpFragNeededMsgSent OBJECT-TYPE
    SYNTAX      ConfdString
    MAX-ACCESS  read-only
    STATUS      current
    DESCRIPTION "SecmIcmpFragNeededMsgSent"
    ::= { affirmedSecurityStatisticsCpu-levelDataStatsNewEntry 155 }

affirmedSecurityStatisticsCpu-levelDataStatsNewSecmSessionIcmpV6PacketTooBigMsgSent OBJECT-TYPE
    SYNTAX      ConfdString
    MAX-ACCESS  read-only
    STATUS      current
    DESCRIPTION "SecmSessionIcmpV6PacketTooBigMsgSent"
    ::= { affirmedSecurityStatisticsCpu-levelDataStatsNewEntry 156 }

affirmedSecurityStatisticsCpu-levelDataStatsNewSecmIcmpV6PacketTooBigMsgSent OBJECT-TYPE
    SYNTAX      ConfdString
    MAX-ACCESS  read-only
    STATUS      current
    DESCRIPTION "SecmIcmpV6PacketTooBigMsgSent"
    ::= { affirmedSecurityStatisticsCpu-levelDataStatsNewEntry 157 }

affirmedSecurityStatisticsCpu-levelDataStatsNewSecmIPv6MaxFragAfterEncryptionTooBig OBJECT-TYPE
    SYNTAX      ConfdString
    MAX-ACCESS  read-only
    STATUS      current
    DESCRIPTION "SecmIPv6MaxFragAfterEncryptionTooBig"
    ::= { affirmedSecurityStatisticsCpu-levelDataStatsNewEntry 158 }

affirmedSecurityStatisticsCpu-levelDataStatsNewSecmIPv6MaxFragTooBig OBJECT-TYPE
    SYNTAX      ConfdString
    MAX-ACCESS  read-only
    STATUS      current
    DESCRIPTION "SecmIPv6MaxFragTooBig"
    ::= { affirmedSecurityStatisticsCpu-levelDataStatsNewEntry 159 }

affirmedSecurityStatisticsCpu-levelDataStatsNewSecmIPv6PktTooBigPreFragEnabled OBJECT-TYPE
    SYNTAX      ConfdString
    MAX-ACCESS  read-only
    STATUS      current
    DESCRIPTION "SecmIPv6PktTooBigPreFragEnabled"
    ::= { affirmedSecurityStatisticsCpu-levelDataStatsNewEntry 160 }

affirmedSecurityStatisticsCpu-levelDataStatsNewSecmIPv6FragSuccess OBJECT-TYPE
    SYNTAX      ConfdString
    MAX-ACCESS  read-only
    STATUS      current
    DESCRIPTION "SecmIPv6FragSuccess"
    ::= { affirmedSecurityStatisticsCpu-levelDataStatsNewEntry 161 }

affirmedSecurityStatisticsCpu-levelDataStatsNewSecmIPv4FragSuccess OBJECT-TYPE
    SYNTAX      ConfdString
    MAX-ACCESS  read-only
    STATUS      current
    DESCRIPTION "SecmIPv4FragSuccess"
    ::= { affirmedSecurityStatisticsCpu-levelDataStatsNewEntry 162 }

affirmedSecurityStatisticsCpu-levelDataStatsNewSecmIPv6FragFailed OBJECT-TYPE
    SYNTAX      ConfdString
    MAX-ACCESS  read-only
    STATUS      current
    DESCRIPTION "SecmIPv6FragFailed"
    ::= { affirmedSecurityStatisticsCpu-levelDataStatsNewEntry 163 }

affirmedSecurityStatisticsCpu-levelDataStatsNewSecmIPv4FragFailed OBJECT-TYPE
    SYNTAX      ConfdString
    MAX-ACCESS  read-only
    STATUS      current
    DESCRIPTION "SecmIPv4FragFailed"
    ::= { affirmedSecurityStatisticsCpu-levelDataStatsNewEntry 164 }

affirmedSecurityStatisticsCpu-levelDataStatsNewSecmFragStatusFailed OBJECT-TYPE
    SYNTAX      ConfdString
    MAX-ACCESS  read-only
    STATUS      current
    DESCRIPTION "SecmFragStatusFailed"
    ::= { affirmedSecurityStatisticsCpu-levelDataStatsNewEntry 165 }

affirmedSecurityStatisticsCpu-levelDataStatsNewSecmNumFrlDropIngressCnts OBJECT-TYPE
    SYNTAX      ConfdString
    MAX-ACCESS  read-only
    STATUS      current
    DESCRIPTION "Number of Ingress Flow drops due to flow rate limit"
    ::= { affirmedSecurityStatisticsCpu-levelDataStatsNewEntry 166 }

affirmedSecurityStatisticsCpu-levelDataStatsNewSecmNumPrlDropIngressCnts OBJECT-TYPE
    SYNTAX      ConfdString
    MAX-ACCESS  read-only
    STATUS      current
    DESCRIPTION "Number of Ingress Packets dropped due to packet rate limit"
    ::= { affirmedSecurityStatisticsCpu-levelDataStatsNewEntry 167 }

affirmedSecurityStatisticsCpu-levelDataStatsNewSecmNumFrlDropEgressCnts OBJECT-TYPE
    SYNTAX      ConfdString
    MAX-ACCESS  read-only
    STATUS      current
    DESCRIPTION "Number of Egress Flow drops due to flow rate limit"
    ::= { affirmedSecurityStatisticsCpu-levelDataStatsNewEntry 168 }

affirmedSecurityStatisticsCpu-levelDataStatsNewSecmNumPrlDropEgressCnts OBJECT-TYPE
    SYNTAX      ConfdString
    MAX-ACCESS  read-only
    STATUS      current
    DESCRIPTION "Number of Egress Packets dropped due to packet rate limit"
    ::= { affirmedSecurityStatisticsCpu-levelDataStatsNewEntry 169 }

affirmedSecurityStatisticsDebugEpdgTable OBJECT-TYPE
    SYNTAX      SEQUENCE OF AffirmedSecurityStatisticsDebugEpdgEntry
    MAX-ACCESS  not-accessible
    STATUS      current
    DESCRIPTION ""
    ::= { affirmedSecurityStatisticsDebug 1 }

affirmedSecurityStatisticsDebugEpdgEntry OBJECT-TYPE
    SYNTAX      AffirmedSecurityStatisticsDebugEpdgEntry
    MAX-ACCESS  not-accessible
    STATUS      current
    DESCRIPTION ""
    INDEX { affirmedSecurityStatisticsDebugEpdgNetworkContext }
        ::= { affirmedSecurityStatisticsDebugEpdgTable 1 }

AffirmedSecurityStatisticsDebugEpdgEntry ::=
    SEQUENCE {
        affirmedSecurityStatisticsDebugEpdgNetworkContext String,
        affirmedSecurityStatisticsDebugEpdgRxEapExchangeSuccess ConfdString,
        affirmedSecurityStatisticsDebugEpdgRxEapDataMissing ConfdString,
        affirmedSecurityStatisticsDebugEpdgRxEapNoListener ConfdString,
        affirmedSecurityStatisticsDebugEpdgRxSessSetupStaleContext ConfdString,
        affirmedSecurityStatisticsDebugEpdgRxSessSetupSuccess ConfdString,
        affirmedSecurityStatisticsDebugEpdgRxSessSetupFail ConfdString,
        affirmedSecurityStatisticsDebugEpdgRxReleaseReq ConfdString,
        affirmedSecurityStatisticsDebugEpdgRxBadOpaqueData ConfdString,
        affirmedSecurityStatisticsDebugEpdgRxMissingOpaqueData ConfdString,
        affirmedSecurityStatisticsDebugEpdgRxOpaqueDestreamErrors ConfdString,
        affirmedSecurityStatisticsDebugEpdgTxEapExchangeFailNoTask ConfdString,
        affirmedSecurityStatisticsDebugEpdgTxEapExchangeSuccess ConfdString,
        affirmedSecurityStatisticsDebugEpdgTxSessSetupSuccess ConfdString,
        affirmedSecurityStatisticsDebugEpdgTxSessSetupAbort ConfdString,
        affirmedSecurityStatisticsDebugEpdgTxDelete ConfdString,
        affirmedSecurityStatisticsDebugEpdgTxUiInitSessDelete ConfdString,
        affirmedSecurityStatisticsDebugEpdgIkeDeleteIgnoredRekey ConfdString,
        affirmedSecurityStatisticsDebugEpdgTxUpdateSpi ConfdString,
        affirmedSecurityStatisticsDebugEpdgTxSendSuccess ConfdString,
        affirmedSecurityStatisticsDebugEpdgTxImsiMgrMsgSendSuccess ConfdString,
        affirmedSecurityStatisticsDebugEpdgTxImsiMgrMsgSendFailNameNotReady ConfdString,
        affirmedSecurityStatisticsDebugEpdgRadiusTimeouts ConfdString,
        affirmedSecurityStatisticsDebugEpdgEapGtcIdRequests ConfdString,
        affirmedSecurityStatisticsDebugEpdgTxUpdateIkeSa ConfdString,
        affirmedSecurityStatisticsDebugEpdgRxReleaseReasonAuditFailure ConfdString,
        affirmedSecurityStatisticsDebugEpdgRxReleaseReasonAaaNotAvailable ConfdString,
        affirmedSecurityStatisticsDebugEpdgRxReleaseReasonAaaTimeout ConfdString,
        affirmedSecurityStatisticsDebugEpdgRxReleaseReasonAaaFailure ConfdString,
        affirmedSecurityStatisticsDebugEpdgRxReleaseReasonPgwNoResponse ConfdString,
        affirmedSecurityStatisticsDebugEpdgRxReleaseReasonGwFailure ConfdString,
        affirmedSecurityStatisticsDebugEpdgRxReleaseReasonIpAddressNotAvailable ConfdString,
        affirmedSecurityStatisticsDebugEpdgRxReleaseReasonReauthentication ConfdString,
        affirmedSecurityStatisticsDebugEpdgRxReleaseReasonGwInitiated ConfdString,
        affirmedSecurityStatisticsDebugEpdgRxReleaseReasonReattach ConfdString,
        affirmedSecurityStatisticsDebugEpdgRxReleaseReasonGwTimeout ConfdString,
        affirmedSecurityStatisticsDebugEpdgRxTotal ConfdString,
        affirmedSecurityStatisticsDebugEpdgRxReleaseReqIgnored ConfdString,
        affirmedSecurityStatisticsDebugEpdgRxReleaseReqRetried ConfdString,
        affirmedSecurityStatisticsDebugEpdgTxMobikeUpdate ConfdString,
        affirmedSecurityStatisticsDebugEpdgNumSpmInstances ConfdString,
        affirmedSecurityStatisticsDebugEpdgRxReleaseReasonInvalidRemoteIdentity ConfdString,
        affirmedSecurityStatisticsDebugEpdgRxReleaseReasonMissingLocalIdentity ConfdString,
        affirmedSecurityStatisticsDebugEpdgRxReleaseReasonNoMatchingEpdg ConfdString,
        affirmedSecurityStatisticsDebugEpdgRxReleaseReasonInternalError ConfdString,
        affirmedSecurityStatisticsDebugEpdgRxInactiveIgnored ConfdString,
        affirmedSecurityStatisticsDebugEpdgTxDeleteFailNoTask ConfdString,
        affirmedSecurityStatisticsDebugEpdgUpdateGwSvcIdSuccess ConfdString,
        affirmedSecurityStatisticsDebugEpdgRxReleaseReasonGwNotFound ConfdString,
        affirmedSecurityStatisticsDebugEpdgTxSessSetupFailNoTask ConfdString,
        affirmedSecurityStatisticsDebugEpdgTxSessSetupAbortFailNoTask ConfdString,
        affirmedSecurityStatisticsDebugEpdgTxIkeRtt ConfdString,
        affirmedSecurityStatisticsDebugEpdgTxIkeRttFailNoTask ConfdString,
        affirmedSecurityStatisticsDebugEpdgTxRemoteIpPortUpdate ConfdString
    }

affirmedSecurityStatisticsDebugEpdgNetworkContext OBJECT-TYPE
    SYNTAX      String
    MAX-ACCESS  not-accessible
    STATUS      current
    DESCRIPTION "security enabled network context"
    ::= { affirmedSecurityStatisticsDebugEpdgEntry 1 }

affirmedSecurityStatisticsDebugEpdgRxEapExchangeSuccess OBJECT-TYPE
    SYNTAX      ConfdString
    MAX-ACCESS  read-only
    STATUS      current
    DESCRIPTION ""
    ::= { affirmedSecurityStatisticsDebugEpdgEntry 2 }

affirmedSecurityStatisticsDebugEpdgRxEapDataMissing OBJECT-TYPE
    SYNTAX      ConfdString
    MAX-ACCESS  read-only
    STATUS      current
    DESCRIPTION ""
    ::= { affirmedSecurityStatisticsDebugEpdgEntry 3 }

affirmedSecurityStatisticsDebugEpdgRxEapNoListener OBJECT-TYPE
    SYNTAX      ConfdString
    MAX-ACCESS  read-only
    STATUS      current
    DESCRIPTION ""
    ::= { affirmedSecurityStatisticsDebugEpdgEntry 4 }

affirmedSecurityStatisticsDebugEpdgRxSessSetupStaleContext OBJECT-TYPE
    SYNTAX      ConfdString
    MAX-ACCESS  read-only
    STATUS      current
    DESCRIPTION ""
    ::= { affirmedSecurityStatisticsDebugEpdgEntry 5 }

affirmedSecurityStatisticsDebugEpdgRxSessSetupSuccess OBJECT-TYPE
    SYNTAX      ConfdString
    MAX-ACCESS  read-only
    STATUS      current
    DESCRIPTION ""
    ::= { affirmedSecurityStatisticsDebugEpdgEntry 6 }

affirmedSecurityStatisticsDebugEpdgRxSessSetupFail OBJECT-TYPE
    SYNTAX      ConfdString
    MAX-ACCESS  read-only
    STATUS      current
    DESCRIPTION ""
    ::= { affirmedSecurityStatisticsDebugEpdgEntry 7 }

affirmedSecurityStatisticsDebugEpdgRxReleaseReq OBJECT-TYPE
    SYNTAX      ConfdString
    MAX-ACCESS  read-only
    STATUS      current
    DESCRIPTION ""
    ::= { affirmedSecurityStatisticsDebugEpdgEntry 8 }

affirmedSecurityStatisticsDebugEpdgRxBadOpaqueData OBJECT-TYPE
    SYNTAX      ConfdString
    MAX-ACCESS  read-only
    STATUS      current
    DESCRIPTION ""
    ::= { affirmedSecurityStatisticsDebugEpdgEntry 9 }

affirmedSecurityStatisticsDebugEpdgRxMissingOpaqueData OBJECT-TYPE
    SYNTAX      ConfdString
    MAX-ACCESS  read-only
    STATUS      current
    DESCRIPTION ""
    ::= { affirmedSecurityStatisticsDebugEpdgEntry 10 }

affirmedSecurityStatisticsDebugEpdgRxOpaqueDestreamErrors OBJECT-TYPE
    SYNTAX      ConfdString
    MAX-ACCESS  read-only
    STATUS      current
    DESCRIPTION ""
    ::= { affirmedSecurityStatisticsDebugEpdgEntry 11 }

affirmedSecurityStatisticsDebugEpdgTxEapExchangeFailNoTask OBJECT-TYPE
    SYNTAX      ConfdString
    MAX-ACCESS  read-only
    STATUS      current
    DESCRIPTION ""
    ::= { affirmedSecurityStatisticsDebugEpdgEntry 12 }

affirmedSecurityStatisticsDebugEpdgTxEapExchangeSuccess OBJECT-TYPE
    SYNTAX      ConfdString
    MAX-ACCESS  read-only
    STATUS      current
    DESCRIPTION ""
    ::= { affirmedSecurityStatisticsDebugEpdgEntry 13 }

affirmedSecurityStatisticsDebugEpdgTxSessSetupSuccess OBJECT-TYPE
    SYNTAX      ConfdString
    MAX-ACCESS  read-only
    STATUS      current
    DESCRIPTION ""
    ::= { affirmedSecurityStatisticsDebugEpdgEntry 14 }

affirmedSecurityStatisticsDebugEpdgTxSessSetupAbort OBJECT-TYPE
    SYNTAX      ConfdString
    MAX-ACCESS  read-only
    STATUS      current
    DESCRIPTION ""
    ::= { affirmedSecurityStatisticsDebugEpdgEntry 15 }

affirmedSecurityStatisticsDebugEpdgTxDelete OBJECT-TYPE
    SYNTAX      ConfdString
    MAX-ACCESS  read-only
    STATUS      current
    DESCRIPTION ""
    ::= { affirmedSecurityStatisticsDebugEpdgEntry 16 }

affirmedSecurityStatisticsDebugEpdgTxUiInitSessDelete OBJECT-TYPE
    SYNTAX      ConfdString
    MAX-ACCESS  read-only
    STATUS      current
    DESCRIPTION ""
    ::= { affirmedSecurityStatisticsDebugEpdgEntry 17 }

affirmedSecurityStatisticsDebugEpdgIkeDeleteIgnoredRekey OBJECT-TYPE
    SYNTAX      ConfdString
    MAX-ACCESS  read-only
    STATUS      current
    DESCRIPTION ""
    ::= { affirmedSecurityStatisticsDebugEpdgEntry 18 }

affirmedSecurityStatisticsDebugEpdgTxUpdateSpi OBJECT-TYPE
    SYNTAX      ConfdString
    MAX-ACCESS  read-only
    STATUS      current
    DESCRIPTION ""
    ::= { affirmedSecurityStatisticsDebugEpdgEntry 19 }

affirmedSecurityStatisticsDebugEpdgTxSendSuccess OBJECT-TYPE
    SYNTAX      ConfdString
    MAX-ACCESS  read-only
    STATUS      current
    DESCRIPTION ""
    ::= { affirmedSecurityStatisticsDebugEpdgEntry 20 }

affirmedSecurityStatisticsDebugEpdgTxImsiMgrMsgSendSuccess OBJECT-TYPE
    SYNTAX      ConfdString
    MAX-ACCESS  read-only
    STATUS      current
    DESCRIPTION ""
    ::= { affirmedSecurityStatisticsDebugEpdgEntry 21 }

affirmedSecurityStatisticsDebugEpdgTxImsiMgrMsgSendFailNameNotReady OBJECT-TYPE
    SYNTAX      ConfdString
    MAX-ACCESS  read-only
    STATUS      current
    DESCRIPTION ""
    ::= { affirmedSecurityStatisticsDebugEpdgEntry 22 }

affirmedSecurityStatisticsDebugEpdgRadiusTimeouts OBJECT-TYPE
    SYNTAX      ConfdString
    MAX-ACCESS  read-only
    STATUS      current
    DESCRIPTION ""
    ::= { affirmedSecurityStatisticsDebugEpdgEntry 23 }

affirmedSecurityStatisticsDebugEpdgEapGtcIdRequests OBJECT-TYPE
    SYNTAX      ConfdString
    MAX-ACCESS  read-only
    STATUS      current
    DESCRIPTION ""
    ::= { affirmedSecurityStatisticsDebugEpdgEntry 24 }

affirmedSecurityStatisticsDebugEpdgTxUpdateIkeSa OBJECT-TYPE
    SYNTAX      ConfdString
    MAX-ACCESS  read-only
    STATUS      current
    DESCRIPTION ""
    ::= { affirmedSecurityStatisticsDebugEpdgEntry 25 }

affirmedSecurityStatisticsDebugEpdgRxReleaseReasonAuditFailure OBJECT-TYPE
    SYNTAX      ConfdString
    MAX-ACCESS  read-only
    STATUS      current
    DESCRIPTION ""
    ::= { affirmedSecurityStatisticsDebugEpdgEntry 26 }

affirmedSecurityStatisticsDebugEpdgRxReleaseReasonAaaNotAvailable OBJECT-TYPE
    SYNTAX      ConfdString
    MAX-ACCESS  read-only
    STATUS      current
    DESCRIPTION ""
    ::= { affirmedSecurityStatisticsDebugEpdgEntry 27 }

affirmedSecurityStatisticsDebugEpdgRxReleaseReasonAaaTimeout OBJECT-TYPE
    SYNTAX      ConfdString
    MAX-ACCESS  read-only
    STATUS      current
    DESCRIPTION ""
    ::= { affirmedSecurityStatisticsDebugEpdgEntry 28 }

affirmedSecurityStatisticsDebugEpdgRxReleaseReasonAaaFailure OBJECT-TYPE
    SYNTAX      ConfdString
    MAX-ACCESS  read-only
    STATUS      current
    DESCRIPTION ""
    ::= { affirmedSecurityStatisticsDebugEpdgEntry 29 }

affirmedSecurityStatisticsDebugEpdgRxReleaseReasonPgwNoResponse OBJECT-TYPE
    SYNTAX      ConfdString
    MAX-ACCESS  read-only
    STATUS      current
    DESCRIPTION ""
    ::= { affirmedSecurityStatisticsDebugEpdgEntry 30 }

affirmedSecurityStatisticsDebugEpdgRxReleaseReasonGwFailure OBJECT-TYPE
    SYNTAX      ConfdString
    MAX-ACCESS  read-only
    STATUS      current
    DESCRIPTION ""
    ::= { affirmedSecurityStatisticsDebugEpdgEntry 31 }

affirmedSecurityStatisticsDebugEpdgRxReleaseReasonIpAddressNotAvailable OBJECT-TYPE
    SYNTAX      ConfdString
    MAX-ACCESS  read-only
    STATUS      current
    DESCRIPTION ""
    ::= { affirmedSecurityStatisticsDebugEpdgEntry 32 }

affirmedSecurityStatisticsDebugEpdgRxReleaseReasonReauthentication OBJECT-TYPE
    SYNTAX      ConfdString
    MAX-ACCESS  read-only
    STATUS      current
    DESCRIPTION ""
    ::= { affirmedSecurityStatisticsDebugEpdgEntry 33 }

affirmedSecurityStatisticsDebugEpdgRxReleaseReasonGwInitiated OBJECT-TYPE
    SYNTAX      ConfdString
    MAX-ACCESS  read-only
    STATUS      current
    DESCRIPTION ""
    ::= { affirmedSecurityStatisticsDebugEpdgEntry 34 }

affirmedSecurityStatisticsDebugEpdgRxReleaseReasonReattach OBJECT-TYPE
    SYNTAX      ConfdString
    MAX-ACCESS  read-only
    STATUS      current
    DESCRIPTION ""
    ::= { affirmedSecurityStatisticsDebugEpdgEntry 35 }

affirmedSecurityStatisticsDebugEpdgRxReleaseReasonGwTimeout OBJECT-TYPE
    SYNTAX      ConfdString
    MAX-ACCESS  read-only
    STATUS      current
    DESCRIPTION ""
    ::= { affirmedSecurityStatisticsDebugEpdgEntry 36 }

affirmedSecurityStatisticsDebugEpdgRxTotal OBJECT-TYPE
    SYNTAX      ConfdString
    MAX-ACCESS  read-only
    STATUS      current
    DESCRIPTION ""
    ::= { affirmedSecurityStatisticsDebugEpdgEntry 37 }

affirmedSecurityStatisticsDebugEpdgRxReleaseReqIgnored OBJECT-TYPE
    SYNTAX      ConfdString
    MAX-ACCESS  read-only
    STATUS      current
    DESCRIPTION ""
    ::= { affirmedSecurityStatisticsDebugEpdgEntry 38 }

affirmedSecurityStatisticsDebugEpdgRxReleaseReqRetried OBJECT-TYPE
    SYNTAX      ConfdString
    MAX-ACCESS  read-only
    STATUS      current
    DESCRIPTION ""
    ::= { affirmedSecurityStatisticsDebugEpdgEntry 39 }

affirmedSecurityStatisticsDebugEpdgTxMobikeUpdate OBJECT-TYPE
    SYNTAX      ConfdString
    MAX-ACCESS  read-only
    STATUS      deprecated
    DESCRIPTION ""
    ::= { affirmedSecurityStatisticsDebugEpdgEntry 40 }

affirmedSecurityStatisticsDebugEpdgNumSpmInstances OBJECT-TYPE
    SYNTAX      ConfdString
    MAX-ACCESS  read-only
    STATUS      current
    DESCRIPTION ""
    ::= { affirmedSecurityStatisticsDebugEpdgEntry 41 }

affirmedSecurityStatisticsDebugEpdgRxReleaseReasonInvalidRemoteIdentity OBJECT-TYPE
    SYNTAX      ConfdString
    MAX-ACCESS  read-only
    STATUS      current
    DESCRIPTION ""
    ::= { affirmedSecurityStatisticsDebugEpdgEntry 42 }

affirmedSecurityStatisticsDebugEpdgRxReleaseReasonMissingLocalIdentity OBJECT-TYPE
    SYNTAX      ConfdString
    MAX-ACCESS  read-only
    STATUS      current
    DESCRIPTION ""
    ::= { affirmedSecurityStatisticsDebugEpdgEntry 43 }

affirmedSecurityStatisticsDebugEpdgRxReleaseReasonNoMatchingEpdg OBJECT-TYPE
    SYNTAX      ConfdString
    MAX-ACCESS  read-only
    STATUS      current
    DESCRIPTION ""
    ::= { affirmedSecurityStatisticsDebugEpdgEntry 44 }

affirmedSecurityStatisticsDebugEpdgRxReleaseReasonInternalError OBJECT-TYPE
    SYNTAX      ConfdString
    MAX-ACCESS  read-only
    STATUS      current
    DESCRIPTION ""
    ::= { affirmedSecurityStatisticsDebugEpdgEntry 45 }

affirmedSecurityStatisticsDebugEpdgRxInactiveIgnored OBJECT-TYPE
    SYNTAX      ConfdString
    MAX-ACCESS  read-only
    STATUS      current
    DESCRIPTION ""
    ::= { affirmedSecurityStatisticsDebugEpdgEntry 46 }

affirmedSecurityStatisticsDebugEpdgTxDeleteFailNoTask OBJECT-TYPE
    SYNTAX      ConfdString
    MAX-ACCESS  read-only
    STATUS      current
    DESCRIPTION ""
    ::= { affirmedSecurityStatisticsDebugEpdgEntry 47 }

affirmedSecurityStatisticsDebugEpdgUpdateGwSvcIdSuccess OBJECT-TYPE
    SYNTAX      ConfdString
    MAX-ACCESS  read-only
    STATUS      current
    DESCRIPTION ""
    ::= { affirmedSecurityStatisticsDebugEpdgEntry 48 }

affirmedSecurityStatisticsDebugEpdgRxReleaseReasonGwNotFound OBJECT-TYPE
    SYNTAX      ConfdString
    MAX-ACCESS  read-only
    STATUS      current
    DESCRIPTION ""
    ::= { affirmedSecurityStatisticsDebugEpdgEntry 49 }

affirmedSecurityStatisticsDebugEpdgTxSessSetupFailNoTask OBJECT-TYPE
    SYNTAX      ConfdString
    MAX-ACCESS  read-only
    STATUS      current
    DESCRIPTION ""
    ::= { affirmedSecurityStatisticsDebugEpdgEntry 50 }

affirmedSecurityStatisticsDebugEpdgTxSessSetupAbortFailNoTask OBJECT-TYPE
    SYNTAX      ConfdString
    MAX-ACCESS  read-only
    STATUS      current
    DESCRIPTION ""
    ::= { affirmedSecurityStatisticsDebugEpdgEntry 51 }

affirmedSecurityStatisticsDebugEpdgTxIkeRtt OBJECT-TYPE
    SYNTAX      ConfdString
    MAX-ACCESS  read-only
    STATUS      current
    DESCRIPTION ""
    ::= { affirmedSecurityStatisticsDebugEpdgEntry 52 }

affirmedSecurityStatisticsDebugEpdgTxIkeRttFailNoTask OBJECT-TYPE
    SYNTAX      ConfdString
    MAX-ACCESS  read-only
    STATUS      current
    DESCRIPTION ""
    ::= { affirmedSecurityStatisticsDebugEpdgEntry 53 }

affirmedSecurityStatisticsDebugEpdgTxRemoteIpPortUpdate OBJECT-TYPE
    SYNTAX      ConfdString
    MAX-ACCESS  read-only
    STATUS      current
    DESCRIPTION ""
    ::= { affirmedSecurityStatisticsDebugEpdgEntry 54 }

affirmedSecurityStatisticsIkeMessageNetworkContextTable OBJECT-TYPE
    SYNTAX      SEQUENCE OF AffirmedSecurityStatisticsIkeMessageNetworkContextEntry
    MAX-ACCESS  not-accessible
    STATUS      current
    DESCRIPTION ""
    ::= { affirmedSecurityStatisticsIkeMessage 1 }

affirmedSecurityStatisticsIkeMessageNetworkContextEntry OBJECT-TYPE
    SYNTAX      AffirmedSecurityStatisticsIkeMessageNetworkContextEntry
    MAX-ACCESS  not-accessible
    STATUS      current
    DESCRIPTION ""
    INDEX { affirmedSecurityStatisticsIkeMessageNetworkContextName }
        ::= { affirmedSecurityStatisticsIkeMessageNetworkContextTable 1 }

AffirmedSecurityStatisticsIkeMessageNetworkContextEntry ::=
    SEQUENCE {
        affirmedSecurityStatisticsIkeMessageNetworkContextName String,
        affirmedSecurityStatisticsIkeMessageNetworkContextTotalIkeSas ConfdString,
        affirmedSecurityStatisticsIkeMessageNetworkContextTotalIkeSasInitiated ConfdString,
        affirmedSecurityStatisticsIkeMessageNetworkContextTotalIkeSasResponded ConfdString,
        affirmedSecurityStatisticsIkeMessageNetworkContextTotalAttempts ConfdString,
        affirmedSecurityStatisticsIkeMessageNetworkContextTotalAttemptsInitiated ConfdString,
        affirmedSecurityStatisticsIkeMessageNetworkContextTotalAttemptsResponded ConfdString,
        affirmedSecurityStatisticsIkeMessageNetworkContextTotalPacketsIn ConfdString,
        affirmedSecurityStatisticsIkeMessageNetworkContextTotalPacketsOut ConfdString,
        affirmedSecurityStatisticsIkeMessageNetworkContextTotalOctetsIn ConfdString,
        affirmedSecurityStatisticsIkeMessageNetworkContextTotalOctetsOut ConfdString,
        affirmedSecurityStatisticsIkeMessageNetworkContextTotalRetransmits ConfdString,
        affirmedSecurityStatisticsIkeMessageNetworkContextTotalDiscardedPackets ConfdString,
        affirmedSecurityStatisticsIkeMessageNetworkContextTotalInitFailures ConfdString,
        affirmedSecurityStatisticsIkeMessageNetworkContextTotalInitNoResponse ConfdString,
        affirmedSecurityStatisticsIkeMessageNetworkContextTotalRespFailures ConfdString,
        affirmedSecurityStatisticsIkeMessageNetworkContextCurrentIkeSas ConfdString,
        affirmedSecurityStatisticsIkeMessageNetworkContextCurrentIkeSasInitiated ConfdString,
        affirmedSecurityStatisticsIkeMessageNetworkContextCurrentIkeSasResponded ConfdString,
        affirmedSecurityStatisticsIkeMessageNetworkContextZeroLengthPkts ConfdString,
        affirmedSecurityStatisticsIkeMessageNetworkContextPktsToExistingSas ConfdString,
        affirmedSecurityStatisticsIkeMessageNetworkContextIkev2WindowCheckPass ConfdString,
        affirmedSecurityStatisticsIkeMessageNetworkContextPacketsDecrypted ConfdString,
        affirmedSecurityStatisticsIkeMessageNetworkContextReceiveWindowRegistered ConfdString,
        affirmedSecurityStatisticsIkeMessageNetworkContextResponderInfoPktIn ConfdString,
        affirmedSecurityStatisticsIkeMessageNetworkContextIkev2ReplyPktsAllocated ConfdString,
        affirmedSecurityStatisticsIkeMessageNetworkContextIkeSaUpdated ConfdString,
        affirmedSecurityStatisticsIkeMessageNetworkContextResponderSideInfoIn ConfdString,
        affirmedSecurityStatisticsIkeMessageNetworkContextInitiatorSideInfoIn ConfdString,
        affirmedSecurityStatisticsIkeMessageNetworkContextIkev2RecvDrop ConfdString,
        affirmedSecurityStatisticsIkeMessageNetworkContextIkev2SendDrop ConfdString,
        affirmedSecurityStatisticsIkeMessageNetworkContextIkeInitReqIn ConfdString,
        affirmedSecurityStatisticsIkeMessageNetworkContextIkeInitRspIn ConfdString,
        affirmedSecurityStatisticsIkeMessageNetworkContextIkeAuthFromInitiator ConfdString,
        affirmedSecurityStatisticsIkeMessageNetworkContextIkeAuthFromResponder ConfdString,
        affirmedSecurityStatisticsIkeMessageNetworkContextIkev2SaSelectOk ConfdString,
        affirmedSecurityStatisticsIkeMessageNetworkContextIkev2SaSelectFail ConfdString,
        affirmedSecurityStatisticsIkeMessageNetworkContextCreateChildSaResponse ConfdString,
        affirmedSecurityStatisticsIkeMessageNetworkContextCreateChildSaRequest ConfdString,
        affirmedSecurityStatisticsIkeMessageNetworkContextCreateChildSaRekeyResponse ConfdString,
        affirmedSecurityStatisticsIkeMessageNetworkContextCreateChildSaRekeyRequest ConfdString,
        affirmedSecurityStatisticsIkeMessageNetworkContextIkeInitReplySend ConfdString,
        affirmedSecurityStatisticsIkeMessageNetworkContextDhSetupFail ConfdString,
        affirmedSecurityStatisticsIkeMessageNetworkContextDhSuccess ConfdString,
        affirmedSecurityStatisticsIkeMessageNetworkContextAddNonceErr ConfdString,
        affirmedSecurityStatisticsIkeMessageNetworkContextAddNonceOk ConfdString,
        affirmedSecurityStatisticsIkeMessageNetworkContextRespOutDhStart ConfdString,
        affirmedSecurityStatisticsIkeMessageNetworkContextRespOutDhOk ConfdString,
        affirmedSecurityStatisticsIkeMessageNetworkContextUdpReadSuccesses ConfdString,
        affirmedSecurityStatisticsIkeMessageNetworkContextUdpReadErrors ConfdString,
        affirmedSecurityStatisticsIkeMessageNetworkContextUdpReadNodata ConfdString,
        affirmedSecurityStatisticsIkeMessageNetworkContextUdpReadHeaderDecodeErrors ConfdString,
        affirmedSecurityStatisticsIkeMessageNetworkContextUdpReadUnsupportedErrors ConfdString,
        affirmedSecurityStatisticsIkeMessageNetworkContextUdpReadInternalErrors ConfdString,
        affirmedSecurityStatisticsIkeMessageNetworkContextUdpReadBadIkeVersion ConfdString,
        affirmedSecurityStatisticsIkeMessageNetworkContextIkev2RecvServerStopped ConfdString,
        affirmedSecurityStatisticsIkeMessageNetworkContextIkev2RecvSpiNotZero ConfdString,
        affirmedSecurityStatisticsIkeMessageNetworkContextIkev2RecvCreateError ConfdString,
        affirmedSecurityStatisticsIkeMessageNetworkContextIkev2RecvInvalidSpi ConfdString,
        affirmedSecurityStatisticsIkeMessageNetworkContextIkev2RecvUnknown ConfdString,
        affirmedSecurityStatisticsIkeMessageNetworkContextIkev2RecvErrorGetSa ConfdString,
        affirmedSecurityStatisticsIkeMessageNetworkContextIkev2RecvFallbackErr ConfdString,
        affirmedSecurityStatisticsIkeMessageNetworkContextIkev2RecvOutOfMem ConfdString,
        affirmedSecurityStatisticsIkeMessageNetworkContextIkev2RecvVerifyErr ConfdString,
        affirmedSecurityStatisticsIkeMessageNetworkContextIkev2RecvSaDeleted ConfdString,
        affirmedSecurityStatisticsIkeMessageNetworkContextIkev2RecvNotNat ConfdString,
        affirmedSecurityStatisticsIkeMessageNetworkContextIkev2NoIdrInitAuth ConfdString,
        affirmedSecurityStatisticsIkeMessageNetworkContextIkev2InitInvalidAuth ConfdString,
        affirmedSecurityStatisticsIkeMessageNetworkContextIkev2NoSaTsiTsr ConfdString,
        affirmedSecurityStatisticsIkeMessageNetworkContextIkev2NoSaPayload ConfdString,
        affirmedSecurityStatisticsIkeMessageNetworkContextIkev2MissingPayload ConfdString,
        affirmedSecurityStatisticsIkeMessageNetworkContextIkev2InvalidEapAuth ConfdString,
        affirmedSecurityStatisticsIkeMessageNetworkContextIkev2InvalidAuthType ConfdString,
        affirmedSecurityStatisticsIkeMessageNetworkContextIkev2NoManPayload ConfdString,
        affirmedSecurityStatisticsIkeMessageNetworkContextIkev2LenZero ConfdString,
        affirmedSecurityStatisticsIkeMessageNetworkContextIkev2Invalid2ndAuth ConfdString,
        affirmedSecurityStatisticsIkeMessageNetworkContextIkev22ndAuthNoIdi ConfdString,
        affirmedSecurityStatisticsIkeMessageNetworkContextIkev2Invalid2ndAuthMethod ConfdString,
        affirmedSecurityStatisticsIkeMessageNetworkContextIkev2RespInvalidAuth ConfdString,
        affirmedSecurityStatisticsIkeMessageNetworkContextIkev2NoAuthAfterEap ConfdString,
        affirmedSecurityStatisticsIkeMessageNetworkContextIkev2LenErrOut ConfdString,
        affirmedSecurityStatisticsIkeMessageNetworkContextIkev2MissingSarIn ConfdString,
        affirmedSecurityStatisticsIkeMessageNetworkContextIkev2KePayloadMismatch ConfdString,
        affirmedSecurityStatisticsIkeMessageNetworkContextIkev2TsMismatch ConfdString,
        affirmedSecurityStatisticsIkeMessageNetworkContextIkev2NoIdrOutAuth ConfdString,
        affirmedSecurityStatisticsIkeMessageNetworkContextIkev2NoSarRespIn ConfdString,
        affirmedSecurityStatisticsIkeMessageNetworkContextIkev2DuplicateSa ConfdString,
        affirmedSecurityStatisticsIkeMessageNetworkContextIkev2PayloadLenSmall ConfdString,
        affirmedSecurityStatisticsIkeMessageNetworkContextIkev2PayloadLenErr ConfdString,
        affirmedSecurityStatisticsIkeMessageNetworkContextIkev2PayloadNot2 ConfdString,
        affirmedSecurityStatisticsIkeMessageNetworkContextIkev2ProposalZero ConfdString,
        affirmedSecurityStatisticsIkeMessageNetworkContextIkev2PayloadLessProposal ConfdString,
        affirmedSecurityStatisticsIkeMessageNetworkContextIkev2MultiProposal ConfdString,
        affirmedSecurityStatisticsIkeMessageNetworkContextIkev2InvalidIncrement ConfdString,
        affirmedSecurityStatisticsIkeMessageNetworkContextIkev2ProposalLessSpi ConfdString,
        affirmedSecurityStatisticsIkeMessageNetworkContextIkev2EspNotIpsec ConfdString,
        affirmedSecurityStatisticsIkeMessageNetworkContextIkev2DecodeInvalidProtocol ConfdString,
        affirmedSecurityStatisticsIkeMessageNetworkContextIkev2LenLess8 ConfdString,
        affirmedSecurityStatisticsIkeMessageNetworkContextIkev2TransLess8 ConfdString,
        affirmedSecurityStatisticsIkeMessageNetworkContextIkev2TransLenErr ConfdString,
        affirmedSecurityStatisticsIkeMessageNetworkContextIkev2PayloadNot3 ConfdString,
        affirmedSecurityStatisticsIkeMessageNetworkContextIkev2PayloadLessTrans ConfdString,
        affirmedSecurityStatisticsIkeMessageNetworkContextIkev2TransNot4 ConfdString,
        affirmedSecurityStatisticsIkeMessageNetworkContextIkev2ExtraData ConfdString,
        affirmedSecurityStatisticsIkeMessageNetworkContextIkev2PayloadLess4 ConfdString,
        affirmedSecurityStatisticsIkeMessageNetworkContextIkev2DuplicateKePayload ConfdString,
        affirmedSecurityStatisticsIkeMessageNetworkContextIkev2PayloadNotGroup ConfdString,
        affirmedSecurityStatisticsIkeMessageNetworkContextIkev2LenLess4 ConfdString,
        affirmedSecurityStatisticsIkeMessageNetworkContextIkev2DuplicateId ConfdString,
        affirmedSecurityStatisticsIkeMessageNetworkContextIkev2InvalidId ConfdString,
        affirmedSecurityStatisticsIkeMessageNetworkContextIkev2InvalidSyntax ConfdString,
        affirmedSecurityStatisticsIkeMessageNetworkContextIkev2WrongExchange ConfdString,
        affirmedSecurityStatisticsIkeMessageNetworkContextIkev2IdrWrong ConfdString,
        affirmedSecurityStatisticsIkeMessageNetworkContextIkev2PayloadLess1 ConfdString,
        affirmedSecurityStatisticsIkeMessageNetworkContextIkev2CertLess1 ConfdString,
        affirmedSecurityStatisticsIkeMessageNetworkContextIkev2NoIkeD ConfdString,
        affirmedSecurityStatisticsIkeMessageNetworkContextIkev2AuthLess1 ConfdString,
        affirmedSecurityStatisticsIkeMessageNetworkContextIkev2DuplicateAuth ConfdString,
        affirmedSecurityStatisticsIkeMessageNetworkContextIkev2InvalidNonce ConfdString,
        affirmedSecurityStatisticsIkeMessageNetworkContextIkev2DecodeDuplicateNonce ConfdString,
        affirmedSecurityStatisticsIkeMessageNetworkContextIkev2NotifyLess4 ConfdString,
        affirmedSecurityStatisticsIkeMessageNetworkContextIkev2NotifySpiSize ConfdString,
        affirmedSecurityStatisticsIkeMessageNetworkContextIkev2DeleteLess4 ConfdString,
        affirmedSecurityStatisticsIkeMessageNetworkContextIkev2DeleteSpiErr ConfdString,
        affirmedSecurityStatisticsIkeMessageNetworkContextIkev2TsLess4 ConfdString,
        affirmedSecurityStatisticsIkeMessageNetworkContextIkev2DuplicateTs ConfdString,
        affirmedSecurityStatisticsIkeMessageNetworkContextIkev2DecodeTsLess8 ConfdString,
        affirmedSecurityStatisticsIkeMessageNetworkContextIkev2DecodeTsLenErr ConfdString,
        affirmedSecurityStatisticsIkeMessageNetworkContextIkev2Ip4RangeErr ConfdString,
        affirmedSecurityStatisticsIkeMessageNetworkContextIkev2Ip6RangeErr ConfdString,
        affirmedSecurityStatisticsIkeMessageNetworkContextIkev2TsUnsupported ConfdString,
        affirmedSecurityStatisticsIkeMessageNetworkContextIkev2TsLenNotZero ConfdString,
        affirmedSecurityStatisticsIkeMessageNetworkContextIkev2InvalidTsi ConfdString,
        affirmedSecurityStatisticsIkeMessageNetworkContextIkev2NoInvalidTsr ConfdString,
        affirmedSecurityStatisticsIkeMessageNetworkContextIkev2DecodeConfLess4 ConfdString,
        affirmedSecurityStatisticsIkeMessageNetworkContextIkev2DuplicateConf ConfdString,
        affirmedSecurityStatisticsIkeMessageNetworkContextIkev2Decode2ConfLess4 ConfdString,
        affirmedSecurityStatisticsIkeMessageNetworkContextIkev2ConfBadLen ConfdString,
        affirmedSecurityStatisticsIkeMessageNetworkContextIkev2RekeyNoSar ConfdString,
        affirmedSecurityStatisticsIkeMessageNetworkContextIkev2RekeySpiLen ConfdString,
        affirmedSecurityStatisticsIkeMessageNetworkContextIkev2KeGroupErr ConfdString,
        affirmedSecurityStatisticsIkeMessageNetworkContextIkev2Cookie2Err ConfdString,
        affirmedSecurityStatisticsIkeMessageNetworkContextIkev2NoCookie2 ConfdString,
        affirmedSecurityStatisticsIkeMessageNetworkContextIkev2InvalidHeader ConfdString,
        affirmedSecurityStatisticsIkeMessageNetworkContextIkev2SaDecodeErr ConfdString,
        affirmedSecurityStatisticsIkeMessageNetworkContextIkev2InvalidMacAlg ConfdString,
        affirmedSecurityStatisticsIkeMessageNetworkContextIkev2InvalidIkeSaPrf ConfdString,
        affirmedSecurityStatisticsIkeMessageNetworkContextIkev2InvalidSaEncrypt ConfdString,
        affirmedSecurityStatisticsIkeMessageNetworkContextIkev2SaDecodeFail ConfdString,
        affirmedSecurityStatisticsIkeMessageNetworkContextIkev2SaDecodeFail2 ConfdString,
        affirmedSecurityStatisticsIkeMessageNetworkContextIkev2SaTraiErr ConfdString,
        affirmedSecurityStatisticsIkeMessageNetworkContextIkev2PktLenLess4 ConfdString,
        affirmedSecurityStatisticsIkeMessageNetworkContextIkev2PktMalformedNatT ConfdString,
        affirmedSecurityStatisticsIkeMessageNetworkContextIkev2MalformedShort ConfdString,
        affirmedSecurityStatisticsIkeMessageNetworkContextIkev2CipherTransErr ConfdString,
        affirmedSecurityStatisticsIkeMessageNetworkContextIkev2IvErr ConfdString,
        affirmedSecurityStatisticsIkeMessageNetworkContextIkev2CipherTransFail ConfdString,
        affirmedSecurityStatisticsIkeMessageNetworkContextIkev2InvalidPad ConfdString,
        affirmedSecurityStatisticsIkeMessageNetworkContextIkev2Malformed ConfdString,
        affirmedSecurityStatisticsIkeMessageNetworkContextIkev2PktBadPayloadSyntax ConfdString,
        affirmedSecurityStatisticsIkeMessageNetworkContextIkev2PktShortPayload ConfdString,
        affirmedSecurityStatisticsIkeMessageNetworkContextIkev2NoSaKe ConfdString,
        affirmedSecurityStatisticsIkeMessageNetworkContextIkev2InvalidDhKe ConfdString,
        affirmedSecurityStatisticsIkeMessageNetworkContextIkev2NoSaNonce ConfdString,
        affirmedSecurityStatisticsIkeMessageNetworkContextIkev2CheckDuplicateNonce ConfdString,
        affirmedSecurityStatisticsIkeMessageNetworkContextIkev2VerifyInvalidProtocol ConfdString,
        affirmedSecurityStatisticsIkeMessageNetworkContextIkev2TooManyProposals ConfdString,
        affirmedSecurityStatisticsIkeMessageNetworkContextIkev2InvalidProposalNum ConfdString,
        affirmedSecurityStatisticsIkeMessageNetworkContextIkev2InvalidProtocolId ConfdString,
        affirmedSecurityStatisticsIkeMessageNetworkContextIkev2InvalidTransType ConfdString,
        affirmedSecurityStatisticsIkeMessageNetworkContextIkev2DuplicateTrans ConfdString,
        affirmedSecurityStatisticsIkeMessageNetworkContextIkev2NoTransType ConfdString,
        affirmedSecurityStatisticsIkeMessageNetworkContextIkev2NoProposalMatch ConfdString,
        affirmedSecurityStatisticsIkeMessageNetworkContextIkev2TrafficSelErr ConfdString,
        affirmedSecurityStatisticsIkeMessageNetworkContextIkev2NoNonce ConfdString,
        affirmedSecurityStatisticsIkeMessageNetworkContextIkev2AuthFinalFail ConfdString,
        affirmedSecurityStatisticsIkeMessageNetworkContextIkev2PktTooShort ConfdString,
        affirmedSecurityStatisticsIkeMessageNetworkContextIkev2MalformedPayload ConfdString,
        affirmedSecurityStatisticsIkeMessageNetworkContextIkev2ServerRestart ConfdString,
        affirmedSecurityStatisticsIkeMessageNetworkContextIkev2UpdateSaSuccess ConfdString,
        affirmedSecurityStatisticsIkeMessageNetworkContextIkev2UpdateSaFail ConfdString,
        affirmedSecurityStatisticsIkeMessageNetworkContextIkev2ErrResponseRcvd ConfdString,
        affirmedSecurityStatisticsIkeMessageNetworkContextIkev2ErrResponseSent ConfdString,
        affirmedSecurityStatisticsIkeMessageNetworkContextIkev2ReceivePayloadSa ConfdString,
        affirmedSecurityStatisticsIkeMessageNetworkContextIkev2ReceivePayloadKe ConfdString,
        affirmedSecurityStatisticsIkeMessageNetworkContextIkev2ReceivePayloadIdi ConfdString,
        affirmedSecurityStatisticsIkeMessageNetworkContextIkev2ReceivePayloadIdr ConfdString,
        affirmedSecurityStatisticsIkeMessageNetworkContextIkev2ReceivePayloadCert ConfdString,
        affirmedSecurityStatisticsIkeMessageNetworkContextIkev2ReceivePayloadCertReq ConfdString,
        affirmedSecurityStatisticsIkeMessageNetworkContextIkev2ReceivePayloadAuth ConfdString,
        affirmedSecurityStatisticsIkeMessageNetworkContextIkev2ReceivePayloadNonce ConfdString,
        affirmedSecurityStatisticsIkeMessageNetworkContextIkev2ReceivePayloadNotify ConfdString,
        affirmedSecurityStatisticsIkeMessageNetworkContextIkev2ReceivePayloadDelete ConfdString,
        affirmedSecurityStatisticsIkeMessageNetworkContextIkev2ReceivePayloadVid ConfdString,
        affirmedSecurityStatisticsIkeMessageNetworkContextIkev2ReceivePayloadTsi ConfdString,
        affirmedSecurityStatisticsIkeMessageNetworkContextIkev2ReceivePayloadTsr ConfdString,
        affirmedSecurityStatisticsIkeMessageNetworkContextIkev2ReceivePayloadConf ConfdString,
        affirmedSecurityStatisticsIkeMessageNetworkContextIkev2ReceivePayloadEap ConfdString,
        affirmedSecurityStatisticsIkeMessageNetworkContextIkev2EncodeSa ConfdString,
        affirmedSecurityStatisticsIkeMessageNetworkContextIkev2EncodeKe ConfdString,
        affirmedSecurityStatisticsIkeMessageNetworkContextIkev2EncodeId ConfdString,
        affirmedSecurityStatisticsIkeMessageNetworkContextIkev2EncodeCert ConfdString,
        affirmedSecurityStatisticsIkeMessageNetworkContextIkev2EncodeCertReq ConfdString,
        affirmedSecurityStatisticsIkeMessageNetworkContextIkev2EncodeAuth ConfdString,
        affirmedSecurityStatisticsIkeMessageNetworkContextIkev2EncodeNonce ConfdString,
        affirmedSecurityStatisticsIkeMessageNetworkContextIkev2EncodeNotify ConfdString,
        affirmedSecurityStatisticsIkeMessageNetworkContextIkev2EncodeDelete ConfdString,
        affirmedSecurityStatisticsIkeMessageNetworkContextIkev2EncodeVid ConfdString,
        affirmedSecurityStatisticsIkeMessageNetworkContextIkev2EncodeTs ConfdString,
        affirmedSecurityStatisticsIkeMessageNetworkContextIkev2EncodeConf ConfdString,
        affirmedSecurityStatisticsIkeMessageNetworkContextIkev2EncodeEap ConfdString,
        affirmedSecurityStatisticsIkeMessageNetworkContextRxNotifyUnsupported ConfdString,
        affirmedSecurityStatisticsIkeMessageNetworkContextRxNotifyInvalidIkeSpi ConfdString,
        affirmedSecurityStatisticsIkeMessageNetworkContextRxNotifyInvalidMajorVer ConfdString,
        affirmedSecurityStatisticsIkeMessageNetworkContextRxNotifyInvalidSyntax ConfdString,
        affirmedSecurityStatisticsIkeMessageNetworkContextRxNotifyInvalidMsgId ConfdString,
        affirmedSecurityStatisticsIkeMessageNetworkContextRxNotifyInvalidSpi ConfdString,
        affirmedSecurityStatisticsIkeMessageNetworkContextRxNotifyNoProposalChosen ConfdString,
        affirmedSecurityStatisticsIkeMessageNetworkContextRxNotifyInvalidIkePayload ConfdString,
        affirmedSecurityStatisticsIkeMessageNetworkContextRxNotifyAuthFailed ConfdString,
        affirmedSecurityStatisticsIkeMessageNetworkContextRxNotifySinglePairReq ConfdString,
        affirmedSecurityStatisticsIkeMessageNetworkContextRxNotifyNoAdditionalSas ConfdString,
        affirmedSecurityStatisticsIkeMessageNetworkContextRxNotifyInternalAddressFail ConfdString,
        affirmedSecurityStatisticsIkeMessageNetworkContextRxNotifyFailCpRequired ConfdString,
        affirmedSecurityStatisticsIkeMessageNetworkContextRxNotifyTsUnacceptable ConfdString,
        affirmedSecurityStatisticsIkeMessageNetworkContextRxNotifyInvalidSelectors ConfdString,
        affirmedSecurityStatisticsIkeMessageNetworkContextRxNotifyUnacceptableAddr ConfdString,
        affirmedSecurityStatisticsIkeMessageNetworkContextRxNotifyUnexpectedNat ConfdString,
        affirmedSecurityStatisticsIkeMessageNetworkContextRxNotifyTempFailure ConfdString,
        affirmedSecurityStatisticsIkeMessageNetworkContextRxNotifyChildSaNotFound ConfdString,
        affirmedSecurityStatisticsIkeMessageNetworkContextRxNotifyInitialContact ConfdString,
        affirmedSecurityStatisticsIkeMessageNetworkContextRxNotifySetWindowSize ConfdString,
        affirmedSecurityStatisticsIkeMessageNetworkContextRxNotifyAdditionalTsPossible ConfdString,
        affirmedSecurityStatisticsIkeMessageNetworkContextRxNotifyIpcompSupported ConfdString,
        affirmedSecurityStatisticsIkeMessageNetworkContextRxNotifyNatDetectSrcIp ConfdString,
        affirmedSecurityStatisticsIkeMessageNetworkContextRxNotifyNatDetectDstIp ConfdString,
        affirmedSecurityStatisticsIkeMessageNetworkContextRxNotifyCookie ConfdString,
        affirmedSecurityStatisticsIkeMessageNetworkContextRxNotifyUseTransportMode ConfdString,
        affirmedSecurityStatisticsIkeMessageNetworkContextRxNotifyHttpCertSupported ConfdString,
        affirmedSecurityStatisticsIkeMessageNetworkContextRxNotifyRekeySa ConfdString,
        affirmedSecurityStatisticsIkeMessageNetworkContextRxNotifyTfcPadNotSupported ConfdString,
        affirmedSecurityStatisticsIkeMessageNetworkContextRxNotifyNonFirstFragmentsAlso ConfdString,
        affirmedSecurityStatisticsIkeMessageNetworkContextRxNotifyMobikeSupported ConfdString,
        affirmedSecurityStatisticsIkeMessageNetworkContextRxNotifyAdditionalV4Addr ConfdString,
        affirmedSecurityStatisticsIkeMessageNetworkContextRxNotifyAdditionalV6Addr ConfdString,
        affirmedSecurityStatisticsIkeMessageNetworkContextRxNotifyNoAdditionalAddr ConfdString,
        affirmedSecurityStatisticsIkeMessageNetworkContextRxNotifyUpdateSaAddr ConfdString,
        affirmedSecurityStatisticsIkeMessageNetworkContextRxNotifyCookie2 ConfdString,
        affirmedSecurityStatisticsIkeMessageNetworkContextRxNotifyNoNatsAllowed ConfdString,
        affirmedSecurityStatisticsIkeMessageNetworkContextRxNotifyMultiAuthSupported ConfdString,
        affirmedSecurityStatisticsIkeMessageNetworkContextRxNotifyAuthFollows ConfdString,
        affirmedSecurityStatisticsIkeMessageNetworkContextRxNotifyEapOnlyAuth ConfdString,
        affirmedSecurityStatisticsIkeMessageNetworkContextRxNotifyUnknown ConfdString,
        affirmedSecurityStatisticsIkeMessageNetworkContextTxNotifyUnsupported ConfdString,
        affirmedSecurityStatisticsIkeMessageNetworkContextTxNotifyInvalidIkeSpi ConfdString,
        affirmedSecurityStatisticsIkeMessageNetworkContextTxNotifyInvalidMajorVer ConfdString,
        affirmedSecurityStatisticsIkeMessageNetworkContextTxNotifyInvalidSyntax ConfdString,
        affirmedSecurityStatisticsIkeMessageNetworkContextTxNotifyInvalidMsgId ConfdString,
        affirmedSecurityStatisticsIkeMessageNetworkContextTxNotifyInvalidSpi ConfdString,
        affirmedSecurityStatisticsIkeMessageNetworkContextTxNotifyNoProposalChosen ConfdString,
        affirmedSecurityStatisticsIkeMessageNetworkContextTxNotifyInvalidIkePayload ConfdString,
        affirmedSecurityStatisticsIkeMessageNetworkContextTxNotifyAuthFailed ConfdString,
        affirmedSecurityStatisticsIkeMessageNetworkContextTxNotifySinglePairReq ConfdString,
        affirmedSecurityStatisticsIkeMessageNetworkContextTxNotifyNoAdditionalSas ConfdString,
        affirmedSecurityStatisticsIkeMessageNetworkContextTxNotifyInternalAddressFail ConfdString,
        affirmedSecurityStatisticsIkeMessageNetworkContextTxNotifyFailCpRequired ConfdString,
        affirmedSecurityStatisticsIkeMessageNetworkContextTxNotifyTsUnacceptable ConfdString,
        affirmedSecurityStatisticsIkeMessageNetworkContextTxNotifyInvalidSelectors ConfdString,
        affirmedSecurityStatisticsIkeMessageNetworkContextTxNotifyUnacceptableAddr ConfdString,
        affirmedSecurityStatisticsIkeMessageNetworkContextTxNotifyUnexpectedNat ConfdString,
        affirmedSecurityStatisticsIkeMessageNetworkContextTxNotifyTempFailure ConfdString,
        affirmedSecurityStatisticsIkeMessageNetworkContextTxNotifyChildSaNotFound ConfdString,
        affirmedSecurityStatisticsIkeMessageNetworkContextTxNotifyInitialContact ConfdString,
        affirmedSecurityStatisticsIkeMessageNetworkContextTxNotifySetWindowSize ConfdString,
        affirmedSecurityStatisticsIkeMessageNetworkContextTxNotifyAdditionalTsPossible ConfdString,
        affirmedSecurityStatisticsIkeMessageNetworkContextTxNotifyIpcompSupported ConfdString,
        affirmedSecurityStatisticsIkeMessageNetworkContextTxNotifyNatDetectSrcIp ConfdString,
        affirmedSecurityStatisticsIkeMessageNetworkContextTxNotifyNatDetectDstIp ConfdString,
        affirmedSecurityStatisticsIkeMessageNetworkContextTxNotifyCookie ConfdString,
        affirmedSecurityStatisticsIkeMessageNetworkContextTxNotifyUseTransportMode ConfdString,
        affirmedSecurityStatisticsIkeMessageNetworkContextTxNotifyHttpCertSupported ConfdString,
        affirmedSecurityStatisticsIkeMessageNetworkContextTxNotifyRekeySa ConfdString,
        affirmedSecurityStatisticsIkeMessageNetworkContextTxNotifyTfcPadNotSupported ConfdString,
        affirmedSecurityStatisticsIkeMessageNetworkContextTxNotifyNonFirstFragmentsAlso ConfdString,
        affirmedSecurityStatisticsIkeMessageNetworkContextTxNotifyMobikeSupported ConfdString,
        affirmedSecurityStatisticsIkeMessageNetworkContextTxNotifyAdditionalV4Addr ConfdString,
        affirmedSecurityStatisticsIkeMessageNetworkContextTxNotifyAdditionalV6Addr ConfdString,
        affirmedSecurityStatisticsIkeMessageNetworkContextTxNotifyNoAdditionalAddr ConfdString,
        affirmedSecurityStatisticsIkeMessageNetworkContextTxNotifyUpdateSaAddr ConfdString,
        affirmedSecurityStatisticsIkeMessageNetworkContextTxNotifyCookie2 ConfdString,
        affirmedSecurityStatisticsIkeMessageNetworkContextTxNotifyNoNatsAllowed ConfdString,
        affirmedSecurityStatisticsIkeMessageNetworkContextTxNotifyMultiAuthSupported ConfdString,
        affirmedSecurityStatisticsIkeMessageNetworkContextTxNotifyAuthFollows ConfdString,
        affirmedSecurityStatisticsIkeMessageNetworkContextTxNotifyEapOnlyAuth ConfdString,
        affirmedSecurityStatisticsIkeMessageNetworkContextTxNotifyUnknown ConfdString,
        affirmedSecurityStatisticsIkeMessageNetworkContextRxNotifyDeviceIdImei ConfdString,
        affirmedSecurityStatisticsIkeMessageNetworkContextRxNotifyImeiDecodeSuccess ConfdString,
        affirmedSecurityStatisticsIkeMessageNetworkContextRxNotifyImeiTypeImei ConfdString,
        affirmedSecurityStatisticsIkeMessageNetworkContextRxNotifyImeiTypeImeisv ConfdString,
        affirmedSecurityStatisticsIkeMessageNetworkContextRxNotifyImeiTypeInvalid ConfdString,
        affirmedSecurityStatisticsIkeMessageNetworkContextRxNotifyImeiDecodeFailTypeMismatch ConfdString,
        affirmedSecurityStatisticsIkeMessageNetworkContextRxNotifyImeiDecodeFailBadLength ConfdString,
        affirmedSecurityStatisticsIkeMessageNetworkContextTxNotifyDeviceIdImei ConfdString,
        affirmedSecurityStatisticsIkeMessageNetworkContextTxNotifyCongestionError ConfdString,
        affirmedSecurityStatisticsIkeMessageNetworkContextTxNotifyPrivateError ConfdString,
        affirmedSecurityStatisticsIkeMessageNetworkContextDeadPeerDetections ConfdString,
        affirmedSecurityStatisticsIkeMessageNetworkContextTxNotifyError ConfdString,
        affirmedSecurityStatisticsIkeMessageNetworkContextIkev2ReceiveAnonymousIdi ConfdString,
        affirmedSecurityStatisticsIkeMessageNetworkContextIkev2ReceiveEapResponseIdentity ConfdString,
        affirmedSecurityStatisticsIkeMessageNetworkContextIkev2AuthMethodNoCaCerts ConfdString,
        affirmedSecurityStatisticsIkeMessageNetworkContextIkev2AuthMethodPskWithEapI ConfdString,
        affirmedSecurityStatisticsIkeMessageNetworkContextIkev2AuthMethodPskWithEapR ConfdString,
        affirmedSecurityStatisticsIkeMessageNetworkContextIkev2AuthMethodNoEapMethods ConfdString,
        affirmedSecurityStatisticsIkeMessageNetworkContextIkev2AuthMethodEapNotAuth ConfdString,
        affirmedSecurityStatisticsIkeMessageNetworkContextRxFragments ConfdString,
        affirmedSecurityStatisticsIkeMessageNetworkContextRxFragmentPackets ConfdString,
        affirmedSecurityStatisticsIkeMessageNetworkContextRxFragmentDrop ConfdString,
        affirmedSecurityStatisticsIkeMessageNetworkContextRxFragmentPacketFail ConfdString,
        affirmedSecurityStatisticsIkeMessageNetworkContextRxFragmentDecryptFail ConfdString,
        affirmedSecurityStatisticsIkeMessageNetworkContextRxFragmentBadPayload ConfdString,
        affirmedSecurityStatisticsIkeMessageNetworkContextRxFragmentNotNegotiated ConfdString,
        affirmedSecurityStatisticsIkeMessageNetworkContextTxFragments ConfdString,
        affirmedSecurityStatisticsIkeMessageNetworkContextTxFragmentPackets ConfdString,
        affirmedSecurityStatisticsIkeMessageNetworkContextTxFragmentPacketFail ConfdString,
        affirmedSecurityStatisticsIkeMessageNetworkContextRxNotifyFragSupported ConfdString,
        affirmedSecurityStatisticsIkeMessageNetworkContextRxDpdRequest ConfdString,
        affirmedSecurityStatisticsIkeMessageNetworkContextRxDpdResponse ConfdString,
        affirmedSecurityStatisticsIkeMessageNetworkContextTxNotifyFragSupported ConfdString,
        affirmedSecurityStatisticsIkeMessageNetworkContextTxDpdRequest ConfdString,
        affirmedSecurityStatisticsIkeMessageNetworkContextTxDpdRetransmit ConfdString,
        affirmedSecurityStatisticsIkeMessageNetworkContextTxDpdResponse ConfdString
    }

affirmedSecurityStatisticsIkeMessageNetworkContextName OBJECT-TYPE
    SYNTAX      String
    MAX-ACCESS  not-accessible
    STATUS      current
    DESCRIPTION "security enabled network context name"
    ::= { affirmedSecurityStatisticsIkeMessageNetworkContextEntry 1 }

affirmedSecurityStatisticsIkeMessageNetworkContextTotalIkeSas OBJECT-TYPE
    SYNTAX      ConfdString
    MAX-ACCESS  read-only
    STATUS      current
    DESCRIPTION "Total number of successful IKE SAs"
    ::= { affirmedSecurityStatisticsIkeMessageNetworkContextEntry 2 }

affirmedSecurityStatisticsIkeMessageNetworkContextTotalIkeSasInitiated OBJECT-TYPE
    SYNTAX      ConfdString
    MAX-ACCESS  read-only
    STATUS      current
    DESCRIPTION "Total number of IKE SAs initiated"
    ::= { affirmedSecurityStatisticsIkeMessageNetworkContextEntry 3 }

affirmedSecurityStatisticsIkeMessageNetworkContextTotalIkeSasResponded OBJECT-TYPE
    SYNTAX      ConfdString
    MAX-ACCESS  read-only
    STATUS      current
    DESCRIPTION "Total number of IKE SAs responded."
    ::= { affirmedSecurityStatisticsIkeMessageNetworkContextEntry 4 }

affirmedSecurityStatisticsIkeMessageNetworkContextTotalAttempts OBJECT-TYPE
    SYNTAX      ConfdString
    MAX-ACCESS  read-only
    STATUS      current
    DESCRIPTION "Total number attempted"
    ::= { affirmedSecurityStatisticsIkeMessageNetworkContextEntry 5 }

affirmedSecurityStatisticsIkeMessageNetworkContextTotalAttemptsInitiated OBJECT-TYPE
    SYNTAX      ConfdString
    MAX-ACCESS  read-only
    STATUS      current
    DESCRIPTION "Total number attempted initiated"
    ::= { affirmedSecurityStatisticsIkeMessageNetworkContextEntry 6 }

affirmedSecurityStatisticsIkeMessageNetworkContextTotalAttemptsResponded OBJECT-TYPE
    SYNTAX      ConfdString
    MAX-ACCESS  read-only
    STATUS      current
    DESCRIPTION "Total number attempted responded"
    ::= { affirmedSecurityStatisticsIkeMessageNetworkContextEntry 7 }

affirmedSecurityStatisticsIkeMessageNetworkContextTotalPacketsIn OBJECT-TYPE
    SYNTAX      ConfdString
    MAX-ACCESS  read-only
    STATUS      current
    DESCRIPTION "Total number of packets in"
    ::= { affirmedSecurityStatisticsIkeMessageNetworkContextEntry 8 }

affirmedSecurityStatisticsIkeMessageNetworkContextTotalPacketsOut OBJECT-TYPE
    SYNTAX      ConfdString
    MAX-ACCESS  read-only
    STATUS      current
    DESCRIPTION "Total number of packets out"
    ::= { affirmedSecurityStatisticsIkeMessageNetworkContextEntry 9 }

affirmedSecurityStatisticsIkeMessageNetworkContextTotalOctetsIn OBJECT-TYPE
    SYNTAX      ConfdString
    MAX-ACCESS  read-only
    STATUS      current
    DESCRIPTION "Total number of octets in"
    ::= { affirmedSecurityStatisticsIkeMessageNetworkContextEntry 10 }

affirmedSecurityStatisticsIkeMessageNetworkContextTotalOctetsOut OBJECT-TYPE
    SYNTAX      ConfdString
    MAX-ACCESS  read-only
    STATUS      current
    DESCRIPTION "Total number of octets out"
    ::= { affirmedSecurityStatisticsIkeMessageNetworkContextEntry 11 }

affirmedSecurityStatisticsIkeMessageNetworkContextTotalRetransmits OBJECT-TYPE
    SYNTAX      ConfdString
    MAX-ACCESS  read-only
    STATUS      current
    DESCRIPTION "Total number of retransmitted packets"
    ::= { affirmedSecurityStatisticsIkeMessageNetworkContextEntry 12 }

affirmedSecurityStatisticsIkeMessageNetworkContextTotalDiscardedPackets OBJECT-TYPE
    SYNTAX      ConfdString
    MAX-ACCESS  read-only
    STATUS      current
    DESCRIPTION "Total number of packets discarded"
    ::= { affirmedSecurityStatisticsIkeMessageNetworkContextEntry 13 }

affirmedSecurityStatisticsIkeMessageNetworkContextTotalInitFailures OBJECT-TYPE
    SYNTAX      ConfdString
    MAX-ACCESS  read-only
    STATUS      current
    DESCRIPTION "The total number of negotiations we initiated that failed because of an error"
    ::= { affirmedSecurityStatisticsIkeMessageNetworkContextEntry 14 }

affirmedSecurityStatisticsIkeMessageNetworkContextTotalInitNoResponse OBJECT-TYPE
    SYNTAX      ConfdString
    MAX-ACCESS  read-only
    STATUS      current
    DESCRIPTION "The total number of negotiations we initiated that failed because of an initial timeout"
    ::= { affirmedSecurityStatisticsIkeMessageNetworkContextEntry 15 }

affirmedSecurityStatisticsIkeMessageNetworkContextTotalRespFailures OBJECT-TYPE
    SYNTAX      ConfdString
    MAX-ACCESS  read-only
    STATUS      current
    DESCRIPTION "The total number of negotiations we responded to that failed because of an error"
    ::= { affirmedSecurityStatisticsIkeMessageNetworkContextEntry 16 }

affirmedSecurityStatisticsIkeMessageNetworkContextCurrentIkeSas OBJECT-TYPE
    SYNTAX      ConfdString
    MAX-ACCESS  read-only
    STATUS      current
    DESCRIPTION "The number of IKE SAs"
    ::= { affirmedSecurityStatisticsIkeMessageNetworkContextEntry 17 }

affirmedSecurityStatisticsIkeMessageNetworkContextCurrentIkeSasInitiated OBJECT-TYPE
    SYNTAX      ConfdString
    MAX-ACCESS  read-only
    STATUS      current
    DESCRIPTION "The number of IKE SAs initiated"
    ::= { affirmedSecurityStatisticsIkeMessageNetworkContextEntry 18 }

affirmedSecurityStatisticsIkeMessageNetworkContextCurrentIkeSasResponded OBJECT-TYPE
    SYNTAX      ConfdString
    MAX-ACCESS  read-only
    STATUS      current
    DESCRIPTION "The number of IKE SAs responded"
    ::= { affirmedSecurityStatisticsIkeMessageNetworkContextEntry 19 }

affirmedSecurityStatisticsIkeMessageNetworkContextZeroLengthPkts OBJECT-TYPE
    SYNTAX      ConfdString
    MAX-ACCESS  read-only
    STATUS      current
    DESCRIPTION "The number of IKE packets dropped due to read failures"
    ::= { affirmedSecurityStatisticsIkeMessageNetworkContextEntry 20 }

affirmedSecurityStatisticsIkeMessageNetworkContextPktsToExistingSas OBJECT-TYPE
    SYNTAX      ConfdString
    MAX-ACCESS  read-only
    STATUS      current
    DESCRIPTION "The number of IKE packets received to existing SAs"
    ::= { affirmedSecurityStatisticsIkeMessageNetworkContextEntry 21 }

affirmedSecurityStatisticsIkeMessageNetworkContextIkev2WindowCheckPass OBJECT-TYPE
    SYNTAX      ConfdString
    MAX-ACCESS  read-only
    STATUS      current
    DESCRIPTION "The number of IKE packets that passed the message window check"
    ::= { affirmedSecurityStatisticsIkeMessageNetworkContextEntry 22 }

affirmedSecurityStatisticsIkeMessageNetworkContextPacketsDecrypted OBJECT-TYPE
    SYNTAX      ConfdString
    MAX-ACCESS  read-only
    STATUS      current
    DESCRIPTION "The number of IKE packets decrypted"
    ::= { affirmedSecurityStatisticsIkeMessageNetworkContextEntry 23 }

affirmedSecurityStatisticsIkeMessageNetworkContextReceiveWindowRegistered OBJECT-TYPE
    SYNTAX      ConfdString
    MAX-ACCESS  read-only
    STATUS      current
    DESCRIPTION "The number of IKE requests confirmed as authentic requests"
    ::= { affirmedSecurityStatisticsIkeMessageNetworkContextEntry 24 }

affirmedSecurityStatisticsIkeMessageNetworkContextResponderInfoPktIn OBJECT-TYPE
    SYNTAX      ConfdString
    MAX-ACCESS  read-only
    STATUS      current
    DESCRIPTION "The number of incoming informational packets on the responder side"
    ::= { affirmedSecurityStatisticsIkeMessageNetworkContextEntry 25 }

affirmedSecurityStatisticsIkeMessageNetworkContextIkev2ReplyPktsAllocated OBJECT-TYPE
    SYNTAX      ConfdString
    MAX-ACCESS  read-only
    STATUS      current
    DESCRIPTION "The number of packets allocated for IKE replies"
    ::= { affirmedSecurityStatisticsIkeMessageNetworkContextEntry 26 }

affirmedSecurityStatisticsIkeMessageNetworkContextIkeSaUpdated OBJECT-TYPE
    SYNTAX      ConfdString
    MAX-ACCESS  read-only
    STATUS      current
    DESCRIPTION "The number of IKE SA updates"
    ::= { affirmedSecurityStatisticsIkeMessageNetworkContextEntry 27 }

affirmedSecurityStatisticsIkeMessageNetworkContextResponderSideInfoIn OBJECT-TYPE
    SYNTAX      ConfdString
    MAX-ACCESS  read-only
    STATUS      current
    DESCRIPTION "The number of incoming information requests"
    ::= { affirmedSecurityStatisticsIkeMessageNetworkContextEntry 28 }

affirmedSecurityStatisticsIkeMessageNetworkContextInitiatorSideInfoIn OBJECT-TYPE
    SYNTAX      ConfdString
    MAX-ACCESS  read-only
    STATUS      current
    DESCRIPTION "The number of incoming information responses"
    ::= { affirmedSecurityStatisticsIkeMessageNetworkContextEntry 29 }

affirmedSecurityStatisticsIkeMessageNetworkContextIkev2RecvDrop OBJECT-TYPE
    SYNTAX      ConfdString
    MAX-ACCESS  read-only
    STATUS      current
    DESCRIPTION "The number of IKE packets dropped without processing"
    ::= { affirmedSecurityStatisticsIkeMessageNetworkContextEntry 30 }

affirmedSecurityStatisticsIkeMessageNetworkContextIkev2SendDrop OBJECT-TYPE
    SYNTAX      ConfdString
    MAX-ACCESS  read-only
    STATUS      current
    DESCRIPTION "The number of IKE packets dropped due to send failures"
    ::= { affirmedSecurityStatisticsIkeMessageNetworkContextEntry 31 }

affirmedSecurityStatisticsIkeMessageNetworkContextIkeInitReqIn OBJECT-TYPE
    SYNTAX      ConfdString
    MAX-ACCESS  read-only
    STATUS      current
    DESCRIPTION "The number of incoming IKE INIT requests"
    ::= { affirmedSecurityStatisticsIkeMessageNetworkContextEntry 32 }

affirmedSecurityStatisticsIkeMessageNetworkContextIkeInitRspIn OBJECT-TYPE
    SYNTAX      ConfdString
    MAX-ACCESS  read-only
    STATUS      current
    DESCRIPTION "The number of incoming IKE INIT responses"
    ::= { affirmedSecurityStatisticsIkeMessageNetworkContextEntry 33 }

affirmedSecurityStatisticsIkeMessageNetworkContextIkeAuthFromInitiator OBJECT-TYPE
    SYNTAX      ConfdString
    MAX-ACCESS  read-only
    STATUS      current
    DESCRIPTION "The number of incoming IKE AUTH requests"
    ::= { affirmedSecurityStatisticsIkeMessageNetworkContextEntry 34 }

affirmedSecurityStatisticsIkeMessageNetworkContextIkeAuthFromResponder OBJECT-TYPE
    SYNTAX      ConfdString
    MAX-ACCESS  read-only
    STATUS      current
    DESCRIPTION "The number of incoming IKE AUTH responses"
    ::= { affirmedSecurityStatisticsIkeMessageNetworkContextEntry 35 }

affirmedSecurityStatisticsIkeMessageNetworkContextIkev2SaSelectOk OBJECT-TYPE
    SYNTAX      ConfdString
    MAX-ACCESS  read-only
    STATUS      current
    DESCRIPTION "The number of times SA was selected successfully for sending a reply"
    ::= { affirmedSecurityStatisticsIkeMessageNetworkContextEntry 36 }

affirmedSecurityStatisticsIkeMessageNetworkContextIkev2SaSelectFail OBJECT-TYPE
    SYNTAX      ConfdString
    MAX-ACCESS  read-only
    STATUS      current
    DESCRIPTION "The number of times replies failed due to SA selection failure"
    ::= { affirmedSecurityStatisticsIkeMessageNetworkContextEntry 37 }

affirmedSecurityStatisticsIkeMessageNetworkContextCreateChildSaResponse OBJECT-TYPE
    SYNTAX      ConfdString
    MAX-ACCESS  read-only
    STATUS      current
    DESCRIPTION "The number of create child SA responses received"
    ::= { affirmedSecurityStatisticsIkeMessageNetworkContextEntry 38 }

affirmedSecurityStatisticsIkeMessageNetworkContextCreateChildSaRequest OBJECT-TYPE
    SYNTAX      ConfdString
    MAX-ACCESS  read-only
    STATUS      current
    DESCRIPTION "The number of create child SA requests received"
    ::= { affirmedSecurityStatisticsIkeMessageNetworkContextEntry 39 }

affirmedSecurityStatisticsIkeMessageNetworkContextCreateChildSaRekeyResponse OBJECT-TYPE
    SYNTAX      ConfdString
    MAX-ACCESS  read-only
    STATUS      current
    DESCRIPTION "The number of create child SA rekey responses received"
    ::= { affirmedSecurityStatisticsIkeMessageNetworkContextEntry 40 }

affirmedSecurityStatisticsIkeMessageNetworkContextCreateChildSaRekeyRequest OBJECT-TYPE
    SYNTAX      ConfdString
    MAX-ACCESS  read-only
    STATUS      current
    DESCRIPTION "The number of create child SA rekey requests received"
    ::= { affirmedSecurityStatisticsIkeMessageNetworkContextEntry 41 }

affirmedSecurityStatisticsIkeMessageNetworkContextIkeInitReplySend OBJECT-TYPE
    SYNTAX      ConfdString
    MAX-ACCESS  read-only
    STATUS      current
    DESCRIPTION "The number of IKE_INIT replies sent"
    ::= { affirmedSecurityStatisticsIkeMessageNetworkContextEntry 42 }

affirmedSecurityStatisticsIkeMessageNetworkContextDhSetupFail OBJECT-TYPE
    SYNTAX      ConfdString
    MAX-ACCESS  read-only
    STATUS      current
    DESCRIPTION "The number of diffie-hellman setup failures"
    ::= { affirmedSecurityStatisticsIkeMessageNetworkContextEntry 43 }

affirmedSecurityStatisticsIkeMessageNetworkContextDhSuccess OBJECT-TYPE
    SYNTAX      ConfdString
    MAX-ACCESS  read-only
    STATUS      current
    DESCRIPTION "The number of diffie-hellman setup successes"
    ::= { affirmedSecurityStatisticsIkeMessageNetworkContextEntry 44 }

affirmedSecurityStatisticsIkeMessageNetworkContextAddNonceErr OBJECT-TYPE
    SYNTAX      ConfdString
    MAX-ACCESS  read-only
    STATUS      current
    DESCRIPTION "The number add nonce payload failures"
    ::= { affirmedSecurityStatisticsIkeMessageNetworkContextEntry 45 }

affirmedSecurityStatisticsIkeMessageNetworkContextAddNonceOk OBJECT-TYPE
    SYNTAX      ConfdString
    MAX-ACCESS  read-only
    STATUS      current
    DESCRIPTION "The number add nonce payload successes"
    ::= { affirmedSecurityStatisticsIkeMessageNetworkContextEntry 46 }

affirmedSecurityStatisticsIkeMessageNetworkContextRespOutDhStart OBJECT-TYPE
    SYNTAX      ConfdString
    MAX-ACCESS  read-only
    STATUS      current
    DESCRIPTION "The number of diffie-hellman processing starts"
    ::= { affirmedSecurityStatisticsIkeMessageNetworkContextEntry 47 }

affirmedSecurityStatisticsIkeMessageNetworkContextRespOutDhOk OBJECT-TYPE
    SYNTAX      ConfdString
    MAX-ACCESS  read-only
    STATUS      current
    DESCRIPTION "The number off diffie-hellman processing successes"
    ::= { affirmedSecurityStatisticsIkeMessageNetworkContextEntry 48 }

affirmedSecurityStatisticsIkeMessageNetworkContextUdpReadSuccesses OBJECT-TYPE
    SYNTAX      ConfdString
    MAX-ACCESS  read-only
    STATUS      current
    DESCRIPTION "The number of UDP read successes"
    ::= { affirmedSecurityStatisticsIkeMessageNetworkContextEntry 49 }

affirmedSecurityStatisticsIkeMessageNetworkContextUdpReadErrors OBJECT-TYPE
    SYNTAX      ConfdString
    MAX-ACCESS  read-only
    STATUS      current
    DESCRIPTION "The number of UDP read failures"
    ::= { affirmedSecurityStatisticsIkeMessageNetworkContextEntry 50 }

affirmedSecurityStatisticsIkeMessageNetworkContextUdpReadNodata OBJECT-TYPE
    SYNTAX      ConfdString
    MAX-ACCESS  read-only
    STATUS      current
    DESCRIPTION "The number of UDP read failures with no data"
    ::= { affirmedSecurityStatisticsIkeMessageNetworkContextEntry 51 }

affirmedSecurityStatisticsIkeMessageNetworkContextUdpReadHeaderDecodeErrors OBJECT-TYPE
    SYNTAX      ConfdString
    MAX-ACCESS  read-only
    STATUS      current
    DESCRIPTION "The number of UDP header decode errors"
    ::= { affirmedSecurityStatisticsIkeMessageNetworkContextEntry 52 }

affirmedSecurityStatisticsIkeMessageNetworkContextUdpReadUnsupportedErrors OBJECT-TYPE
    SYNTAX      ConfdString
    MAX-ACCESS  read-only
    STATUS      current
    DESCRIPTION "The number of UDP read unsupported errors"
    ::= { affirmedSecurityStatisticsIkeMessageNetworkContextEntry 53 }

affirmedSecurityStatisticsIkeMessageNetworkContextUdpReadInternalErrors OBJECT-TYPE
    SYNTAX      ConfdString
    MAX-ACCESS  read-only
    STATUS      current
    DESCRIPTION "The number of UDP read failures with internal error"
    ::= { affirmedSecurityStatisticsIkeMessageNetworkContextEntry 54 }

affirmedSecurityStatisticsIkeMessageNetworkContextUdpReadBadIkeVersion OBJECT-TYPE
    SYNTAX      ConfdString
    MAX-ACCESS  read-only
    STATUS      current
    DESCRIPTION "The number of bad IKE versions errors"
    ::= { affirmedSecurityStatisticsIkeMessageNetworkContextEntry 55 }

affirmedSecurityStatisticsIkeMessageNetworkContextIkev2RecvServerStopped OBJECT-TYPE
    SYNTAX      ConfdString
    MAX-ACCESS  read-only
    STATUS      current
    DESCRIPTION "The number of IKE packets dropped due to server in stopped state"
    ::= { affirmedSecurityStatisticsIkeMessageNetworkContextEntry 56 }

affirmedSecurityStatisticsIkeMessageNetworkContextIkev2RecvSpiNotZero OBJECT-TYPE
    SYNTAX      ConfdString
    MAX-ACCESS  read-only
    STATUS      current
    DESCRIPTION "The number of received SPI no zero errors"
    ::= { affirmedSecurityStatisticsIkeMessageNetworkContextEntry 57 }

affirmedSecurityStatisticsIkeMessageNetworkContextIkev2RecvCreateError OBJECT-TYPE
    SYNTAX      ConfdString
    MAX-ACCESS  read-only
    STATUS      current
    DESCRIPTION "The number of received errors in create sa"
    ::= { affirmedSecurityStatisticsIkeMessageNetworkContextEntry 58 }

affirmedSecurityStatisticsIkeMessageNetworkContextIkev2RecvInvalidSpi OBJECT-TYPE
    SYNTAX      ConfdString
    MAX-ACCESS  read-only
    STATUS      current
    DESCRIPTION "The number of invalid spis received"
    ::= { affirmedSecurityStatisticsIkeMessageNetworkContextEntry 59 }

affirmedSecurityStatisticsIkeMessageNetworkContextIkev2RecvUnknown OBJECT-TYPE
    SYNTAX      ConfdString
    MAX-ACCESS  read-only
    STATUS      current
    DESCRIPTION "The number of unknown responder packets dropped"
    ::= { affirmedSecurityStatisticsIkeMessageNetworkContextEntry 60 }

affirmedSecurityStatisticsIkeMessageNetworkContextIkev2RecvErrorGetSa OBJECT-TYPE
    SYNTAX      ConfdString
    MAX-ACCESS  read-only
    STATUS      current
    DESCRIPTION "The number of received errors in get sa"
    ::= { affirmedSecurityStatisticsIkeMessageNetworkContextEntry 61 }

affirmedSecurityStatisticsIkeMessageNetworkContextIkev2RecvFallbackErr OBJECT-TYPE
    SYNTAX      ConfdString
    MAX-ACCESS  read-only
    STATUS      current
    DESCRIPTION "The number failures falling back to ikev1"
    ::= { affirmedSecurityStatisticsIkeMessageNetworkContextEntry 62 }

affirmedSecurityStatisticsIkeMessageNetworkContextIkev2RecvOutOfMem OBJECT-TYPE
    SYNTAX      ConfdString
    MAX-ACCESS  read-only
    STATUS      current
    DESCRIPTION "The number out of memory failures"
    ::= { affirmedSecurityStatisticsIkeMessageNetworkContextEntry 63 }

affirmedSecurityStatisticsIkeMessageNetworkContextIkev2RecvVerifyErr OBJECT-TYPE
    SYNTAX      ConfdString
    MAX-ACCESS  read-only
    STATUS      current
    DESCRIPTION "The number out of IKE packets that failed verification"
    ::= { affirmedSecurityStatisticsIkeMessageNetworkContextEntry 64 }

affirmedSecurityStatisticsIkeMessageNetworkContextIkev2RecvSaDeleted OBJECT-TYPE
    SYNTAX      ConfdString
    MAX-ACCESS  read-only
    STATUS      current
    DESCRIPTION "The number out of IKE packets dropped because SA is being deleted"
    ::= { affirmedSecurityStatisticsIkeMessageNetworkContextEntry 65 }

affirmedSecurityStatisticsIkeMessageNetworkContextIkev2RecvNotNat OBJECT-TYPE
    SYNTAX      ConfdString
    MAX-ACCESS  read-only
    STATUS      current
    DESCRIPTION "The number out non-nat packets received when NAT was expected"
    ::= { affirmedSecurityStatisticsIkeMessageNetworkContextEntry 66 }

affirmedSecurityStatisticsIkeMessageNetworkContextIkev2NoIdrInitAuth OBJECT-TYPE
    SYNTAX      ConfdString
    MAX-ACCESS  read-only
    STATUS      current
    DESCRIPTION "The number IKE_AUTH received with missing IDr or AUTH payload"
    ::= { affirmedSecurityStatisticsIkeMessageNetworkContextEntry 67 }

affirmedSecurityStatisticsIkeMessageNetworkContextIkev2InitInvalidAuth OBJECT-TYPE
    SYNTAX      ConfdString
    MAX-ACCESS  read-only
    STATUS      current
    DESCRIPTION "The number IKE_AUTH received with invalid AUTH method"
    ::= { affirmedSecurityStatisticsIkeMessageNetworkContextEntry 68 }

affirmedSecurityStatisticsIkeMessageNetworkContextIkev2NoSaTsiTsr OBJECT-TYPE
    SYNTAX      ConfdString
    MAX-ACCESS  read-only
    STATUS      current
    DESCRIPTION "The number IKE_AUTH received with missing SA, TSi or TSr payload"
    ::= { affirmedSecurityStatisticsIkeMessageNetworkContextEntry 69 }

affirmedSecurityStatisticsIkeMessageNetworkContextIkev2NoSaPayload OBJECT-TYPE
    SYNTAX      ConfdString
    MAX-ACCESS  read-only
    STATUS      current
    DESCRIPTION "The number of IKE_AUTHs received with missing SA payload"
    ::= { affirmedSecurityStatisticsIkeMessageNetworkContextEntry 70 }

affirmedSecurityStatisticsIkeMessageNetworkContextIkev2MissingPayload OBJECT-TYPE
    SYNTAX      ConfdString
    MAX-ACCESS  read-only
    STATUS      current
    DESCRIPTION "The number of IKE_AUTHs received with missing mandatory payloads"
    ::= { affirmedSecurityStatisticsIkeMessageNetworkContextEntry 71 }

affirmedSecurityStatisticsIkeMessageNetworkContextIkev2InvalidEapAuth OBJECT-TYPE
    SYNTAX      ConfdString
    MAX-ACCESS  read-only
    STATUS      current
    DESCRIPTION "The number of invalid EAP auth methods received"
    ::= { affirmedSecurityStatisticsIkeMessageNetworkContextEntry 72 }

affirmedSecurityStatisticsIkeMessageNetworkContextIkev2InvalidAuthType OBJECT-TYPE
    SYNTAX      ConfdString
    MAX-ACCESS  read-only
    STATUS      current
    DESCRIPTION "The number of invalid auth methods proposed"
    ::= { affirmedSecurityStatisticsIkeMessageNetworkContextEntry 73 }

affirmedSecurityStatisticsIkeMessageNetworkContextIkev2NoManPayload OBJECT-TYPE
    SYNTAX      ConfdString
    MAX-ACCESS  read-only
    STATUS      current
    DESCRIPTION "The number of mandatory AUTH payloads missing after EAP done"
    ::= { affirmedSecurityStatisticsIkeMessageNetworkContextEntry 74 }

affirmedSecurityStatisticsIkeMessageNetworkContextIkev2LenZero OBJECT-TYPE
    SYNTAX      ConfdString
    MAX-ACCESS  read-only
    STATUS      current
    DESCRIPTION "The number of invalid syntax errors"
    ::= { affirmedSecurityStatisticsIkeMessageNetworkContextEntry 75 }

affirmedSecurityStatisticsIkeMessageNetworkContextIkev2Invalid2ndAuth OBJECT-TYPE
    SYNTAX      ConfdString
    MAX-ACCESS  read-only
    STATUS      current
    DESCRIPTION "The number of invalid second auth methods from initiator"
    ::= { affirmedSecurityStatisticsIkeMessageNetworkContextEntry 76 }

affirmedSecurityStatisticsIkeMessageNetworkContextIkev22ndAuthNoIdi OBJECT-TYPE
    SYNTAX      ConfdString
    MAX-ACCESS  read-only
    STATUS      current
    DESCRIPTION "The number of second auth missing idi payload"
    ::= { affirmedSecurityStatisticsIkeMessageNetworkContextEntry 77 }

affirmedSecurityStatisticsIkeMessageNetworkContextIkev2Invalid2ndAuthMethod OBJECT-TYPE
    SYNTAX      ConfdString
    MAX-ACCESS  read-only
    STATUS      current
    DESCRIPTION "The number of invalid second auth methods from responder"
    ::= { affirmedSecurityStatisticsIkeMessageNetworkContextEntry 78 }

affirmedSecurityStatisticsIkeMessageNetworkContextIkev2RespInvalidAuth OBJECT-TYPE
    SYNTAX      ConfdString
    MAX-ACCESS  read-only
    STATUS      current
    DESCRIPTION "The number of invalid second auth method for second authentication"
    ::= { affirmedSecurityStatisticsIkeMessageNetworkContextEntry 79 }

affirmedSecurityStatisticsIkeMessageNetworkContextIkev2NoAuthAfterEap OBJECT-TYPE
    SYNTAX      ConfdString
    MAX-ACCESS  read-only
    STATUS      current
    DESCRIPTION "The number of mandatory auth payload missing after EAP done"
    ::= { affirmedSecurityStatisticsIkeMessageNetworkContextEntry 80 }

affirmedSecurityStatisticsIkeMessageNetworkContextIkev2LenErrOut OBJECT-TYPE
    SYNTAX      ConfdString
    MAX-ACCESS  read-only
    STATUS      current
    DESCRIPTION "The number of encode errors due to zero length"
    ::= { affirmedSecurityStatisticsIkeMessageNetworkContextEntry 81 }

affirmedSecurityStatisticsIkeMessageNetworkContextIkev2MissingSarIn OBJECT-TYPE
    SYNTAX      ConfdString
    MAX-ACCESS  read-only
    STATUS      current
    DESCRIPTION "The number of mandatory payload missing"
    ::= { affirmedSecurityStatisticsIkeMessageNetworkContextEntry 82 }

affirmedSecurityStatisticsIkeMessageNetworkContextIkev2KePayloadMismatch OBJECT-TYPE
    SYNTAX      ConfdString
    MAX-ACCESS  read-only
    STATUS      current
    DESCRIPTION "The number of key exchange payload not matching selected group"
    ::= { affirmedSecurityStatisticsIkeMessageNetworkContextEntry 83 }

affirmedSecurityStatisticsIkeMessageNetworkContextIkev2TsMismatch OBJECT-TYPE
    SYNTAX      ConfdString
    MAX-ACCESS  read-only
    STATUS      current
    DESCRIPTION "The number of traffic selector mismatch"
    ::= { affirmedSecurityStatisticsIkeMessageNetworkContextEntry 84 }

affirmedSecurityStatisticsIkeMessageNetworkContextIkev2NoIdrOutAuth OBJECT-TYPE
    SYNTAX      ConfdString
    MAX-ACCESS  read-only
    STATUS      current
    DESCRIPTION "The number of no idr out auth"
    ::= { affirmedSecurityStatisticsIkeMessageNetworkContextEntry 85 }

affirmedSecurityStatisticsIkeMessageNetworkContextIkev2NoSarRespIn OBJECT-TYPE
    SYNTAX      ConfdString
    MAX-ACCESS  read-only
    STATUS      current
    DESCRIPTION "The number mandatory payload missing in create child"
    ::= { affirmedSecurityStatisticsIkeMessageNetworkContextEntry 86 }

affirmedSecurityStatisticsIkeMessageNetworkContextIkev2DuplicateSa OBJECT-TYPE
    SYNTAX      ConfdString
    MAX-ACCESS  read-only
    STATUS      current
    DESCRIPTION "The number duplicate SA payloads"
    ::= { affirmedSecurityStatisticsIkeMessageNetworkContextEntry 87 }

affirmedSecurityStatisticsIkeMessageNetworkContextIkev2PayloadLenSmall OBJECT-TYPE
    SYNTAX      ConfdString
    MAX-ACCESS  read-only
    STATUS      current
    DESCRIPTION "The number of decode errors due to length too small"
    ::= { affirmedSecurityStatisticsIkeMessageNetworkContextEntry 88 }

affirmedSecurityStatisticsIkeMessageNetworkContextIkev2PayloadLenErr OBJECT-TYPE
    SYNTAX      ConfdString
    MAX-ACCESS  read-only
    STATUS      current
    DESCRIPTION "The number of decode errors due to wrong length"
    ::= { affirmedSecurityStatisticsIkeMessageNetworkContextEntry 89 }

affirmedSecurityStatisticsIkeMessageNetworkContextIkev2PayloadNot2 OBJECT-TYPE
    SYNTAX      ConfdString
    MAX-ACCESS  read-only
    STATUS      current
    DESCRIPTION "The number of decode errors due to next payload not 0 or 2"
    ::= { affirmedSecurityStatisticsIkeMessageNetworkContextEntry 90 }

affirmedSecurityStatisticsIkeMessageNetworkContextIkev2ProposalZero OBJECT-TYPE
    SYNTAX      ConfdString
    MAX-ACCESS  read-only
    STATUS      current
    DESCRIPTION "The number of decode errors due proposal number 0"
    ::= { affirmedSecurityStatisticsIkeMessageNetworkContextEntry 91 }

affirmedSecurityStatisticsIkeMessageNetworkContextIkev2PayloadLessProposal OBJECT-TYPE
    SYNTAX      ConfdString
    MAX-ACCESS  read-only
    STATUS      current
    DESCRIPTION "The number of decode errors due invalid proposal length"
    ::= { affirmedSecurityStatisticsIkeMessageNetworkContextEntry 92 }

affirmedSecurityStatisticsIkeMessageNetworkContextIkev2MultiProposal OBJECT-TYPE
    SYNTAX      ConfdString
    MAX-ACCESS  read-only
    STATUS      current
    DESCRIPTION "The number of decode errors due multiple proposals in response"
    ::= { affirmedSecurityStatisticsIkeMessageNetworkContextEntry 93 }

affirmedSecurityStatisticsIkeMessageNetworkContextIkev2InvalidIncrement OBJECT-TYPE
    SYNTAX      ConfdString
    MAX-ACCESS  read-only
    STATUS      current
    DESCRIPTION "The number of decode errors due invalid increment"
    ::= { affirmedSecurityStatisticsIkeMessageNetworkContextEntry 94 }

affirmedSecurityStatisticsIkeMessageNetworkContextIkev2ProposalLessSpi OBJECT-TYPE
    SYNTAX      ConfdString
    MAX-ACCESS  read-only
    STATUS      current
    DESCRIPTION "The number of decode errors due to invalid SPI length"
    ::= { affirmedSecurityStatisticsIkeMessageNetworkContextEntry 95 }

affirmedSecurityStatisticsIkeMessageNetworkContextIkev2EspNotIpsec OBJECT-TYPE
    SYNTAX      ConfdString
    MAX-ACCESS  read-only
    STATUS      current
    DESCRIPTION "The number of decode errors due ah or esp"
    ::= { affirmedSecurityStatisticsIkeMessageNetworkContextEntry 96 }

affirmedSecurityStatisticsIkeMessageNetworkContextIkev2DecodeInvalidProtocol OBJECT-TYPE
    SYNTAX      ConfdString
    MAX-ACCESS  read-only
    STATUS      current
    DESCRIPTION "The number of decode errors due invalid protocol"
    ::= { affirmedSecurityStatisticsIkeMessageNetworkContextEntry 97 }

affirmedSecurityStatisticsIkeMessageNetworkContextIkev2LenLess8 OBJECT-TYPE
    SYNTAX      ConfdString
    MAX-ACCESS  read-only
    STATUS      current
    DESCRIPTION "The number of decode errors due length less than 8"
    ::= { affirmedSecurityStatisticsIkeMessageNetworkContextEntry 98 }

affirmedSecurityStatisticsIkeMessageNetworkContextIkev2TransLess8 OBJECT-TYPE
    SYNTAX      ConfdString
    MAX-ACCESS  read-only
    STATUS      current
    DESCRIPTION "The number of decode errors due transform length less than 8"
    ::= { affirmedSecurityStatisticsIkeMessageNetworkContextEntry 99 }

affirmedSecurityStatisticsIkeMessageNetworkContextIkev2TransLenErr OBJECT-TYPE
    SYNTAX      ConfdString
    MAX-ACCESS  read-only
    STATUS      current
    DESCRIPTION "The number of decode errors due to invalid transform length"
    ::= { affirmedSecurityStatisticsIkeMessageNetworkContextEntry 100 }

affirmedSecurityStatisticsIkeMessageNetworkContextIkev2PayloadNot3 OBJECT-TYPE
    SYNTAX      ConfdString
    MAX-ACCESS  read-only
    STATUS      current
    DESCRIPTION "The number of decode errors due to next payload not 0 o 3"
    ::= { affirmedSecurityStatisticsIkeMessageNetworkContextEntry 101 }

affirmedSecurityStatisticsIkeMessageNetworkContextIkev2PayloadLessTrans OBJECT-TYPE
    SYNTAX      ConfdString
    MAX-ACCESS  read-only
    STATUS      current
    DESCRIPTION "The number of decode errors due to invalid length"
    ::= { affirmedSecurityStatisticsIkeMessageNetworkContextEntry 102 }

affirmedSecurityStatisticsIkeMessageNetworkContextIkev2TransNot4 OBJECT-TYPE
    SYNTAX      ConfdString
    MAX-ACCESS  read-only
    STATUS      current
    DESCRIPTION "The number of decode errors due invalid transform attribute length"
    ::= { affirmedSecurityStatisticsIkeMessageNetworkContextEntry 103 }

affirmedSecurityStatisticsIkeMessageNetworkContextIkev2ExtraData OBJECT-TYPE
    SYNTAX      ConfdString
    MAX-ACCESS  read-only
    STATUS      current
    DESCRIPTION "The number of decode errors due extra data present"
    ::= { affirmedSecurityStatisticsIkeMessageNetworkContextEntry 104 }

affirmedSecurityStatisticsIkeMessageNetworkContextIkev2PayloadLess4 OBJECT-TYPE
    SYNTAX      ConfdString
    MAX-ACCESS  read-only
    STATUS      current
    DESCRIPTION "The number of decode ke failures due to invalid length"
    ::= { affirmedSecurityStatisticsIkeMessageNetworkContextEntry 105 }

affirmedSecurityStatisticsIkeMessageNetworkContextIkev2DuplicateKePayload OBJECT-TYPE
    SYNTAX      ConfdString
    MAX-ACCESS  read-only
    STATUS      current
    DESCRIPTION "The number of decode ke failures due to duplicate payload"
    ::= { affirmedSecurityStatisticsIkeMessageNetworkContextEntry 106 }

affirmedSecurityStatisticsIkeMessageNetworkContextIkev2PayloadNotGroup OBJECT-TYPE
    SYNTAX      ConfdString
    MAX-ACCESS  read-only
    STATUS      current
    DESCRIPTION "The number of decode ke failures due to invalid group length"
    ::= { affirmedSecurityStatisticsIkeMessageNetworkContextEntry 107 }

affirmedSecurityStatisticsIkeMessageNetworkContextIkev2LenLess4 OBJECT-TYPE
    SYNTAX      ConfdString
    MAX-ACCESS  read-only
    STATUS      current
    DESCRIPTION "The number of decode id failure due to invalid length"
    ::= { affirmedSecurityStatisticsIkeMessageNetworkContextEntry 108 }

affirmedSecurityStatisticsIkeMessageNetworkContextIkev2DuplicateId OBJECT-TYPE
    SYNTAX      ConfdString
    MAX-ACCESS  read-only
    STATUS      current
    DESCRIPTION "The number of decode id failures due to invalid group length"
    ::= { affirmedSecurityStatisticsIkeMessageNetworkContextEntry 109 }

affirmedSecurityStatisticsIkeMessageNetworkContextIkev2InvalidId OBJECT-TYPE
    SYNTAX      ConfdString
    MAX-ACCESS  read-only
    STATUS      current
    DESCRIPTION "The number of decode id failure due to invalid id"
    ::= { affirmedSecurityStatisticsIkeMessageNetworkContextEntry 110 }

affirmedSecurityStatisticsIkeMessageNetworkContextIkev2InvalidSyntax OBJECT-TYPE
    SYNTAX      ConfdString
    MAX-ACCESS  read-only
    STATUS      current
    DESCRIPTION "The number of decode id failure due to invalid syntax"
    ::= { affirmedSecurityStatisticsIkeMessageNetworkContextEntry 111 }

affirmedSecurityStatisticsIkeMessageNetworkContextIkev2WrongExchange OBJECT-TYPE
    SYNTAX      ConfdString
    MAX-ACCESS  read-only
    STATUS      current
    DESCRIPTION "The number of decode id failure due to wrong exchange"
    ::= { affirmedSecurityStatisticsIkeMessageNetworkContextEntry 112 }

affirmedSecurityStatisticsIkeMessageNetworkContextIkev2IdrWrong OBJECT-TYPE
    SYNTAX      ConfdString
    MAX-ACCESS  read-only
    STATUS      current
    DESCRIPTION "The number of decode idr failure due to wrong exchange"
    ::= { affirmedSecurityStatisticsIkeMessageNetworkContextEntry 113 }

affirmedSecurityStatisticsIkeMessageNetworkContextIkev2PayloadLess1 OBJECT-TYPE
    SYNTAX      ConfdString
    MAX-ACCESS  read-only
    STATUS      current
    DESCRIPTION "The number of decode certificate failure"
    ::= { affirmedSecurityStatisticsIkeMessageNetworkContextEntry 114 }

affirmedSecurityStatisticsIkeMessageNetworkContextIkev2CertLess1 OBJECT-TYPE
    SYNTAX      ConfdString
    MAX-ACCESS  read-only
    STATUS      current
    DESCRIPTION "The number of decode certificate request failure"
    ::= { affirmedSecurityStatisticsIkeMessageNetworkContextEntry 115 }

affirmedSecurityStatisticsIkeMessageNetworkContextIkev2NoIkeD OBJECT-TYPE
    SYNTAX      ConfdString
    MAX-ACCESS  read-only
    STATUS      current
    DESCRIPTION "The number of decode auth failure due to no ed"
    ::= { affirmedSecurityStatisticsIkeMessageNetworkContextEntry 116 }

affirmedSecurityStatisticsIkeMessageNetworkContextIkev2AuthLess1 OBJECT-TYPE
    SYNTAX      ConfdString
    MAX-ACCESS  read-only
    STATUS      current
    DESCRIPTION "The number of decode auth failure due to invalid length"
    ::= { affirmedSecurityStatisticsIkeMessageNetworkContextEntry 117 }

affirmedSecurityStatisticsIkeMessageNetworkContextIkev2DuplicateAuth OBJECT-TYPE
    SYNTAX      ConfdString
    MAX-ACCESS  read-only
    STATUS      current
    DESCRIPTION "The number of decode auth failure due duplicate auth payload"
    ::= { affirmedSecurityStatisticsIkeMessageNetworkContextEntry 118 }

affirmedSecurityStatisticsIkeMessageNetworkContextIkev2InvalidNonce OBJECT-TYPE
    SYNTAX      ConfdString
    MAX-ACCESS  read-only
    STATUS      current
    DESCRIPTION "The number of decode nonce failure due to invalid length"
    ::= { affirmedSecurityStatisticsIkeMessageNetworkContextEntry 119 }

affirmedSecurityStatisticsIkeMessageNetworkContextIkev2DecodeDuplicateNonce OBJECT-TYPE
    SYNTAX      ConfdString
    MAX-ACCESS  read-only
    STATUS      current
    DESCRIPTION "The number of decode nonce failure due to duplicate nonce payload"
    ::= { affirmedSecurityStatisticsIkeMessageNetworkContextEntry 120 }

affirmedSecurityStatisticsIkeMessageNetworkContextIkev2NotifyLess4 OBJECT-TYPE
    SYNTAX      ConfdString
    MAX-ACCESS  read-only
    STATUS      current
    DESCRIPTION "The number of decode notify errors due to invalid length"
    ::= { affirmedSecurityStatisticsIkeMessageNetworkContextEntry 121 }

affirmedSecurityStatisticsIkeMessageNetworkContextIkev2NotifySpiSize OBJECT-TYPE
    SYNTAX      ConfdString
    MAX-ACCESS  read-only
    STATUS      current
    DESCRIPTION "The number of decode notify errors due to invalid SPI size"
    ::= { affirmedSecurityStatisticsIkeMessageNetworkContextEntry 122 }

affirmedSecurityStatisticsIkeMessageNetworkContextIkev2DeleteLess4 OBJECT-TYPE
    SYNTAX      ConfdString
    MAX-ACCESS  read-only
    STATUS      current
    DESCRIPTION "The number of decode delete errors due to invalid length"
    ::= { affirmedSecurityStatisticsIkeMessageNetworkContextEntry 123 }

affirmedSecurityStatisticsIkeMessageNetworkContextIkev2DeleteSpiErr OBJECT-TYPE
    SYNTAX      ConfdString
    MAX-ACCESS  read-only
    STATUS      current
    DESCRIPTION "The number of decode delete errors due to invalid number of spis"
    ::= { affirmedSecurityStatisticsIkeMessageNetworkContextEntry 124 }

affirmedSecurityStatisticsIkeMessageNetworkContextIkev2TsLess4 OBJECT-TYPE
    SYNTAX      ConfdString
    MAX-ACCESS  read-only
    STATUS      current
    DESCRIPTION "The number of decode ts errors due to invalid length"
    ::= { affirmedSecurityStatisticsIkeMessageNetworkContextEntry 125 }

affirmedSecurityStatisticsIkeMessageNetworkContextIkev2DuplicateTs OBJECT-TYPE
    SYNTAX      ConfdString
    MAX-ACCESS  read-only
    STATUS      current
    DESCRIPTION "The number of decode ts failure due to duplicate ts payload"
    ::= { affirmedSecurityStatisticsIkeMessageNetworkContextEntry 126 }

affirmedSecurityStatisticsIkeMessageNetworkContextIkev2DecodeTsLess8 OBJECT-TYPE
    SYNTAX      ConfdString
    MAX-ACCESS  read-only
    STATUS      current
    DESCRIPTION "The number of decode ts failure due to ts length less than 8"
    ::= { affirmedSecurityStatisticsIkeMessageNetworkContextEntry 127 }

affirmedSecurityStatisticsIkeMessageNetworkContextIkev2DecodeTsLenErr OBJECT-TYPE
    SYNTAX      ConfdString
    MAX-ACCESS  read-only
    STATUS      current
    DESCRIPTION "The number of decode ts failures due to invalid ts length"
    ::= { affirmedSecurityStatisticsIkeMessageNetworkContextEntry 128 }

affirmedSecurityStatisticsIkeMessageNetworkContextIkev2Ip4RangeErr OBJECT-TYPE
    SYNTAX      ConfdString
    MAX-ACCESS  read-only
    STATUS      current
    DESCRIPTION "The number of decode ts failures due to ipv4 range error"
    ::= { affirmedSecurityStatisticsIkeMessageNetworkContextEntry 129 }

affirmedSecurityStatisticsIkeMessageNetworkContextIkev2Ip6RangeErr OBJECT-TYPE
    SYNTAX      ConfdString
    MAX-ACCESS  read-only
    STATUS      current
    DESCRIPTION "The number of decode ts failures due to ipv6 range error"
    ::= { affirmedSecurityStatisticsIkeMessageNetworkContextEntry 130 }

affirmedSecurityStatisticsIkeMessageNetworkContextIkev2TsUnsupported OBJECT-TYPE
    SYNTAX      ConfdString
    MAX-ACCESS  read-only
    STATUS      current
    DESCRIPTION "The number of decode ts failures due unsupported ts"
    ::= { affirmedSecurityStatisticsIkeMessageNetworkContextEntry 131 }

affirmedSecurityStatisticsIkeMessageNetworkContextIkev2TsLenNotZero OBJECT-TYPE
    SYNTAX      ConfdString
    MAX-ACCESS  read-only
    STATUS      current
    DESCRIPTION "The number of decode ts failures due to extra payload"
    ::= { affirmedSecurityStatisticsIkeMessageNetworkContextEntry 132 }

affirmedSecurityStatisticsIkeMessageNetworkContextIkev2InvalidTsi OBJECT-TYPE
    SYNTAX      ConfdString
    MAX-ACCESS  read-only
    STATUS      current
    DESCRIPTION "The number of decode tsi failures due to invalid tsi"
    ::= { affirmedSecurityStatisticsIkeMessageNetworkContextEntry 133 }

affirmedSecurityStatisticsIkeMessageNetworkContextIkev2NoInvalidTsr OBJECT-TYPE
    SYNTAX      ConfdString
    MAX-ACCESS  read-only
    STATUS      current
    DESCRIPTION "The number of decode tsr failures due to invalid tsr"
    ::= { affirmedSecurityStatisticsIkeMessageNetworkContextEntry 134 }

affirmedSecurityStatisticsIkeMessageNetworkContextIkev2DecodeConfLess4 OBJECT-TYPE
    SYNTAX      ConfdString
    MAX-ACCESS  read-only
    STATUS      current
    DESCRIPTION "The number of decode configuration failures due to invalid length"
    ::= { affirmedSecurityStatisticsIkeMessageNetworkContextEntry 135 }

affirmedSecurityStatisticsIkeMessageNetworkContextIkev2DuplicateConf OBJECT-TYPE
    SYNTAX      ConfdString
    MAX-ACCESS  read-only
    STATUS      current
    DESCRIPTION "The number of decode configuration failures due to duplicate payload"
    ::= { affirmedSecurityStatisticsIkeMessageNetworkContextEntry 136 }

affirmedSecurityStatisticsIkeMessageNetworkContextIkev2Decode2ConfLess4 OBJECT-TYPE
    SYNTAX      ConfdString
    MAX-ACCESS  read-only
    STATUS      current
    DESCRIPTION "The number of decode configuration failures due to length less than 4"
    ::= { affirmedSecurityStatisticsIkeMessageNetworkContextEntry 137 }

affirmedSecurityStatisticsIkeMessageNetworkContextIkev2ConfBadLen OBJECT-TYPE
    SYNTAX      ConfdString
    MAX-ACCESS  read-only
    STATUS      current
    DESCRIPTION "The number of decode configuration failures due to bad length"
    ::= { affirmedSecurityStatisticsIkeMessageNetworkContextEntry 138 }

affirmedSecurityStatisticsIkeMessageNetworkContextIkev2RekeyNoSar OBJECT-TYPE
    SYNTAX      ConfdString
    MAX-ACCESS  read-only
    STATUS      current
    DESCRIPTION "The number of rekeys with no sar"
    ::= { affirmedSecurityStatisticsIkeMessageNetworkContextEntry 139 }

affirmedSecurityStatisticsIkeMessageNetworkContextIkev2RekeySpiLen OBJECT-TYPE
    SYNTAX      ConfdString
    MAX-ACCESS  read-only
    STATUS      current
    DESCRIPTION "The number of rekeys with invalid SPI length"
    ::= { affirmedSecurityStatisticsIkeMessageNetworkContextEntry 140 }

affirmedSecurityStatisticsIkeMessageNetworkContextIkev2KeGroupErr OBJECT-TYPE
    SYNTAX      ConfdString
    MAX-ACCESS  read-only
    STATUS      current
    DESCRIPTION "The number of rekeys with group mismatch"
    ::= { affirmedSecurityStatisticsIkeMessageNetworkContextEntry 141 }

affirmedSecurityStatisticsIkeMessageNetworkContextIkev2Cookie2Err OBJECT-TYPE
    SYNTAX      ConfdString
    MAX-ACCESS  read-only
    STATUS      current
    DESCRIPTION "The number of cookie 2 errors"
    ::= { affirmedSecurityStatisticsIkeMessageNetworkContextEntry 142 }

affirmedSecurityStatisticsIkeMessageNetworkContextIkev2NoCookie2 OBJECT-TYPE
    SYNTAX      ConfdString
    MAX-ACCESS  read-only
    STATUS      current
    DESCRIPTION "The number of cookie 2 missing errors"
    ::= { affirmedSecurityStatisticsIkeMessageNetworkContextEntry 143 }

affirmedSecurityStatisticsIkeMessageNetworkContextIkev2InvalidHeader OBJECT-TYPE
    SYNTAX      ConfdString
    MAX-ACCESS  read-only
    STATUS      current
    DESCRIPTION "The number of IKE SA export errors due to invalid header format"
    ::= { affirmedSecurityStatisticsIkeMessageNetworkContextEntry 144 }

affirmedSecurityStatisticsIkeMessageNetworkContextIkev2SaDecodeErr OBJECT-TYPE
    SYNTAX      ConfdString
    MAX-ACCESS  read-only
    STATUS      current
    DESCRIPTION "The number of IKE SA export errors due to decode errors"
    ::= { affirmedSecurityStatisticsIkeMessageNetworkContextEntry 145 }

affirmedSecurityStatisticsIkeMessageNetworkContextIkev2InvalidMacAlg OBJECT-TYPE
    SYNTAX      ConfdString
    MAX-ACCESS  read-only
    STATUS      current
    DESCRIPTION "The number of IKE SA export errors due to invalid mac algorithm"
    ::= { affirmedSecurityStatisticsIkeMessageNetworkContextEntry 146 }

affirmedSecurityStatisticsIkeMessageNetworkContextIkev2InvalidIkeSaPrf OBJECT-TYPE
    SYNTAX      ConfdString
    MAX-ACCESS  read-only
    STATUS      current
    DESCRIPTION "The number of IKE SA export errors due invalid prf algorithm"
    ::= { affirmedSecurityStatisticsIkeMessageNetworkContextEntry 147 }

affirmedSecurityStatisticsIkeMessageNetworkContextIkev2InvalidSaEncrypt OBJECT-TYPE
    SYNTAX      ConfdString
    MAX-ACCESS  read-only
    STATUS      current
    DESCRIPTION "The number of IKE SA export errors due invalid encrypt algorithm"
    ::= { affirmedSecurityStatisticsIkeMessageNetworkContextEntry 148 }

affirmedSecurityStatisticsIkeMessageNetworkContextIkev2SaDecodeFail OBJECT-TYPE
    SYNTAX      ConfdString
    MAX-ACCESS  read-only
    STATUS      current
    DESCRIPTION "The number of IKE SA export decode failures"
    ::= { affirmedSecurityStatisticsIkeMessageNetworkContextEntry 149 }

affirmedSecurityStatisticsIkeMessageNetworkContextIkev2SaDecodeFail2 OBJECT-TYPE
    SYNTAX      ConfdString
    MAX-ACCESS  read-only
    STATUS      current
    DESCRIPTION "The number of IKE SA export decode failures"
    ::= { affirmedSecurityStatisticsIkeMessageNetworkContextEntry 150 }

affirmedSecurityStatisticsIkeMessageNetworkContextIkev2SaTraiErr OBJECT-TYPE
    SYNTAX      ConfdString
    MAX-ACCESS  read-only
    STATUS      current
    DESCRIPTION "The number of IKE SA import failures due to invalid length"
    ::= { affirmedSecurityStatisticsIkeMessageNetworkContextEntry 151 }

affirmedSecurityStatisticsIkeMessageNetworkContextIkev2PktLenLess4 OBJECT-TYPE
    SYNTAX      ConfdString
    MAX-ACCESS  read-only
    STATUS      current
    DESCRIPTION "The number of IKE SA import failures due to packet length less than 4"
    ::= { affirmedSecurityStatisticsIkeMessageNetworkContextEntry 152 }

affirmedSecurityStatisticsIkeMessageNetworkContextIkev2PktMalformedNatT OBJECT-TYPE
    SYNTAX      ConfdString
    MAX-ACCESS  read-only
    STATUS      current
    DESCRIPTION "The number of IKE SA import failures due to malformed-natt"
    ::= { affirmedSecurityStatisticsIkeMessageNetworkContextEntry 153 }

affirmedSecurityStatisticsIkeMessageNetworkContextIkev2MalformedShort OBJECT-TYPE
    SYNTAX      ConfdString
    MAX-ACCESS  read-only
    STATUS      current
    DESCRIPTION "The number of IKE SA import failures due to packet too short"
    ::= { affirmedSecurityStatisticsIkeMessageNetworkContextEntry 154 }

affirmedSecurityStatisticsIkeMessageNetworkContextIkev2CipherTransErr OBJECT-TYPE
    SYNTAX      ConfdString
    MAX-ACCESS  read-only
    STATUS      current
    DESCRIPTION "The number of packet decryption failures"
    ::= { affirmedSecurityStatisticsIkeMessageNetworkContextEntry 155 }

affirmedSecurityStatisticsIkeMessageNetworkContextIkev2IvErr OBJECT-TYPE
    SYNTAX      ConfdString
    MAX-ACCESS  read-only
    STATUS      current
    DESCRIPTION "The number of invalid iv lengths"
    ::= { affirmedSecurityStatisticsIkeMessageNetworkContextEntry 156 }

affirmedSecurityStatisticsIkeMessageNetworkContextIkev2CipherTransFail OBJECT-TYPE
    SYNTAX      ConfdString
    MAX-ACCESS  read-only
    STATUS      current
    DESCRIPTION "The number of packet decryption failures"
    ::= { affirmedSecurityStatisticsIkeMessageNetworkContextEntry 157 }

affirmedSecurityStatisticsIkeMessageNetworkContextIkev2InvalidPad OBJECT-TYPE
    SYNTAX      ConfdString
    MAX-ACCESS  read-only
    STATUS      current
    DESCRIPTION "The number of packets with invalid pad"
    ::= { affirmedSecurityStatisticsIkeMessageNetworkContextEntry 158 }

affirmedSecurityStatisticsIkeMessageNetworkContextIkev2Malformed OBJECT-TYPE
    SYNTAX      ConfdString
    MAX-ACCESS  read-only
    STATUS      current
    DESCRIPTION "The number of malformed packets"
    ::= { affirmedSecurityStatisticsIkeMessageNetworkContextEntry 159 }

affirmedSecurityStatisticsIkeMessageNetworkContextIkev2PktBadPayloadSyntax OBJECT-TYPE
    SYNTAX      ConfdString
    MAX-ACCESS  read-only
    STATUS      current
    DESCRIPTION "The number of bad payload syntax"
    ::= { affirmedSecurityStatisticsIkeMessageNetworkContextEntry 160 }

affirmedSecurityStatisticsIkeMessageNetworkContextIkev2PktShortPayload OBJECT-TYPE
    SYNTAX      ConfdString
    MAX-ACCESS  read-only
    STATUS      current
    DESCRIPTION "The number of packets with payload too short"
    ::= { affirmedSecurityStatisticsIkeMessageNetworkContextEntry 161 }

affirmedSecurityStatisticsIkeMessageNetworkContextIkev2NoSaKe OBJECT-TYPE
    SYNTAX      ConfdString
    MAX-ACCESS  read-only
    STATUS      current
    DESCRIPTION "The number of packets with no SA, KE or NONCE payloads"
    ::= { affirmedSecurityStatisticsIkeMessageNetworkContextEntry 162 }

affirmedSecurityStatisticsIkeMessageNetworkContextIkev2InvalidDhKe OBJECT-TYPE
    SYNTAX      ConfdString
    MAX-ACCESS  read-only
    STATUS      current
    DESCRIPTION "The number of packets with invalid diffie-hellman group"
    ::= { affirmedSecurityStatisticsIkeMessageNetworkContextEntry 163 }

affirmedSecurityStatisticsIkeMessageNetworkContextIkev2NoSaNonce OBJECT-TYPE
    SYNTAX      ConfdString
    MAX-ACCESS  read-only
    STATUS      current
    DESCRIPTION "The number of packets with no SA, KE or NONCE payloads"
    ::= { affirmedSecurityStatisticsIkeMessageNetworkContextEntry 164 }

affirmedSecurityStatisticsIkeMessageNetworkContextIkev2CheckDuplicateNonce OBJECT-TYPE
    SYNTAX      ConfdString
    MAX-ACCESS  read-only
    STATUS      current
    DESCRIPTION "The number of packets with duplicate nonce payloads"
    ::= { affirmedSecurityStatisticsIkeMessageNetworkContextEntry 165 }

affirmedSecurityStatisticsIkeMessageNetworkContextIkev2VerifyInvalidProtocol OBJECT-TYPE
    SYNTAX      ConfdString
    MAX-ACCESS  read-only
    STATUS      current
    DESCRIPTION "The number of packets with invalid protocol id"
    ::= { affirmedSecurityStatisticsIkeMessageNetworkContextEntry 166 }

affirmedSecurityStatisticsIkeMessageNetworkContextIkev2TooManyProposals OBJECT-TYPE
    SYNTAX      ConfdString
    MAX-ACCESS  read-only
    STATUS      current
    DESCRIPTION "The number of packets with multiple proposal selections"
    ::= { affirmedSecurityStatisticsIkeMessageNetworkContextEntry 167 }

affirmedSecurityStatisticsIkeMessageNetworkContextIkev2InvalidProposalNum OBJECT-TYPE
    SYNTAX      ConfdString
    MAX-ACCESS  read-only
    STATUS      current
    DESCRIPTION "The number of packets with invalid proposal number"
    ::= { affirmedSecurityStatisticsIkeMessageNetworkContextEntry 168 }

affirmedSecurityStatisticsIkeMessageNetworkContextIkev2InvalidProtocolId OBJECT-TYPE
    SYNTAX      ConfdString
    MAX-ACCESS  read-only
    STATUS      current
    DESCRIPTION "The number of packets with invalid protocol id"
    ::= { affirmedSecurityStatisticsIkeMessageNetworkContextEntry 169 }

affirmedSecurityStatisticsIkeMessageNetworkContextIkev2InvalidTransType OBJECT-TYPE
    SYNTAX      ConfdString
    MAX-ACCESS  read-only
    STATUS      current
    DESCRIPTION "The number of packets with invalid transform type"
    ::= { affirmedSecurityStatisticsIkeMessageNetworkContextEntry 170 }

affirmedSecurityStatisticsIkeMessageNetworkContextIkev2DuplicateTrans OBJECT-TYPE
    SYNTAX      ConfdString
    MAX-ACCESS  read-only
    STATUS      current
    DESCRIPTION "The number of packets with duplicate transform types"
    ::= { affirmedSecurityStatisticsIkeMessageNetworkContextEntry 171 }

affirmedSecurityStatisticsIkeMessageNetworkContextIkev2NoTransType OBJECT-TYPE
    SYNTAX      ConfdString
    MAX-ACCESS  read-only
    STATUS      current
    DESCRIPTION "The number of packets with missing transform type"
    ::= { affirmedSecurityStatisticsIkeMessageNetworkContextEntry 172 }

affirmedSecurityStatisticsIkeMessageNetworkContextIkev2NoProposalMatch OBJECT-TYPE
    SYNTAX      ConfdString
    MAX-ACCESS  read-only
    STATUS      current
    DESCRIPTION "The number of packets with no proposal match"
    ::= { affirmedSecurityStatisticsIkeMessageNetworkContextEntry 173 }

affirmedSecurityStatisticsIkeMessageNetworkContextIkev2TrafficSelErr OBJECT-TYPE
    SYNTAX      ConfdString
    MAX-ACCESS  read-only
    STATUS      current
    DESCRIPTION "The number of packets with traffic selectors not matching"
    ::= { affirmedSecurityStatisticsIkeMessageNetworkContextEntry 174 }

affirmedSecurityStatisticsIkeMessageNetworkContextIkev2NoNonce OBJECT-TYPE
    SYNTAX      ConfdString
    MAX-ACCESS  read-only
    STATUS      current
    DESCRIPTION "No memory for allocating nonce data"
    ::= { affirmedSecurityStatisticsIkeMessageNetworkContextEntry 175 }

affirmedSecurityStatisticsIkeMessageNetworkContextIkev2AuthFinalFail OBJECT-TYPE
    SYNTAX      ConfdString
    MAX-ACCESS  read-only
    STATUS      current
    DESCRIPTION "The number of final auth cipher failures"
    ::= { affirmedSecurityStatisticsIkeMessageNetworkContextEntry 176 }

affirmedSecurityStatisticsIkeMessageNetworkContextIkev2PktTooShort OBJECT-TYPE
    SYNTAX      ConfdString
    MAX-ACCESS  read-only
    STATUS      current
    DESCRIPTION "The number of decode failures due to packet too short"
    ::= { affirmedSecurityStatisticsIkeMessageNetworkContextEntry 177 }

affirmedSecurityStatisticsIkeMessageNetworkContextIkev2MalformedPayload OBJECT-TYPE
    SYNTAX      ConfdString
    MAX-ACCESS  read-only
    STATUS      current
    DESCRIPTION "The number of malformed packets received"
    ::= { affirmedSecurityStatisticsIkeMessageNetworkContextEntry 178 }

affirmedSecurityStatisticsIkeMessageNetworkContextIkev2ServerRestart OBJECT-TYPE
    SYNTAX      ConfdString
    MAX-ACCESS  read-only
    STATUS      current
    DESCRIPTION "The number of times IKE server was restarted"
    ::= { affirmedSecurityStatisticsIkeMessageNetworkContextEntry 179 }

affirmedSecurityStatisticsIkeMessageNetworkContextIkev2UpdateSaSuccess OBJECT-TYPE
    SYNTAX      ConfdString
    MAX-ACCESS  read-only
    STATUS      current
    DESCRIPTION "The number of mobike SA update successes"
    ::= { affirmedSecurityStatisticsIkeMessageNetworkContextEntry 180 }

affirmedSecurityStatisticsIkeMessageNetworkContextIkev2UpdateSaFail OBJECT-TYPE
    SYNTAX      ConfdString
    MAX-ACCESS  read-only
    STATUS      current
    DESCRIPTION "The number of mobike SA update failures"
    ::= { affirmedSecurityStatisticsIkeMessageNetworkContextEntry 181 }

affirmedSecurityStatisticsIkeMessageNetworkContextIkev2ErrResponseRcvd OBJECT-TYPE
    SYNTAX      ConfdString
    MAX-ACCESS  read-only
    STATUS      current
    DESCRIPTION "The number of error responses received"
    ::= { affirmedSecurityStatisticsIkeMessageNetworkContextEntry 182 }

affirmedSecurityStatisticsIkeMessageNetworkContextIkev2ErrResponseSent OBJECT-TYPE
    SYNTAX      ConfdString
    MAX-ACCESS  read-only
    STATUS      current
    DESCRIPTION "The number of error responses sent"
    ::= { affirmedSecurityStatisticsIkeMessageNetworkContextEntry 183 }

affirmedSecurityStatisticsIkeMessageNetworkContextIkev2ReceivePayloadSa OBJECT-TYPE
    SYNTAX      ConfdString
    MAX-ACCESS  read-only
    STATUS      current
    DESCRIPTION "The number of SA payloads received"
    ::= { affirmedSecurityStatisticsIkeMessageNetworkContextEntry 184 }

affirmedSecurityStatisticsIkeMessageNetworkContextIkev2ReceivePayloadKe OBJECT-TYPE
    SYNTAX      ConfdString
    MAX-ACCESS  read-only
    STATUS      current
    DESCRIPTION "The number of key exchange payloads received"
    ::= { affirmedSecurityStatisticsIkeMessageNetworkContextEntry 185 }

affirmedSecurityStatisticsIkeMessageNetworkContextIkev2ReceivePayloadIdi OBJECT-TYPE
    SYNTAX      ConfdString
    MAX-ACCESS  read-only
    STATUS      current
    DESCRIPTION "The number of initiator id payloads received"
    ::= { affirmedSecurityStatisticsIkeMessageNetworkContextEntry 186 }

affirmedSecurityStatisticsIkeMessageNetworkContextIkev2ReceivePayloadIdr OBJECT-TYPE
    SYNTAX      ConfdString
    MAX-ACCESS  read-only
    STATUS      current
    DESCRIPTION "The number of responder id payloads received"
    ::= { affirmedSecurityStatisticsIkeMessageNetworkContextEntry 187 }

affirmedSecurityStatisticsIkeMessageNetworkContextIkev2ReceivePayloadCert OBJECT-TYPE
    SYNTAX      ConfdString
    MAX-ACCESS  read-only
    STATUS      current
    DESCRIPTION "The number of certificate payloads received"
    ::= { affirmedSecurityStatisticsIkeMessageNetworkContextEntry 188 }

affirmedSecurityStatisticsIkeMessageNetworkContextIkev2ReceivePayloadCertReq OBJECT-TYPE
    SYNTAX      ConfdString
    MAX-ACCESS  read-only
    STATUS      current
    DESCRIPTION "The number of certificate request payloads received"
    ::= { affirmedSecurityStatisticsIkeMessageNetworkContextEntry 189 }

affirmedSecurityStatisticsIkeMessageNetworkContextIkev2ReceivePayloadAuth OBJECT-TYPE
    SYNTAX      ConfdString
    MAX-ACCESS  read-only
    STATUS      current
    DESCRIPTION "The number of auth payloads received"
    ::= { affirmedSecurityStatisticsIkeMessageNetworkContextEntry 190 }

affirmedSecurityStatisticsIkeMessageNetworkContextIkev2ReceivePayloadNonce OBJECT-TYPE
    SYNTAX      ConfdString
    MAX-ACCESS  read-only
    STATUS      current
    DESCRIPTION "The number of nonce payloads received"
    ::= { affirmedSecurityStatisticsIkeMessageNetworkContextEntry 191 }

affirmedSecurityStatisticsIkeMessageNetworkContextIkev2ReceivePayloadNotify OBJECT-TYPE
    SYNTAX      ConfdString
    MAX-ACCESS  read-only
    STATUS      current
    DESCRIPTION "The number of notify payloads received"
    ::= { affirmedSecurityStatisticsIkeMessageNetworkContextEntry 192 }

affirmedSecurityStatisticsIkeMessageNetworkContextIkev2ReceivePayloadDelete OBJECT-TYPE
    SYNTAX      ConfdString
    MAX-ACCESS  read-only
    STATUS      current
    DESCRIPTION "The number of delete payloads received"
    ::= { affirmedSecurityStatisticsIkeMessageNetworkContextEntry 193 }

affirmedSecurityStatisticsIkeMessageNetworkContextIkev2ReceivePayloadVid OBJECT-TYPE
    SYNTAX      ConfdString
    MAX-ACCESS  read-only
    STATUS      current
    DESCRIPTION "The number of vendor id payloads received"
    ::= { affirmedSecurityStatisticsIkeMessageNetworkContextEntry 194 }

affirmedSecurityStatisticsIkeMessageNetworkContextIkev2ReceivePayloadTsi OBJECT-TYPE
    SYNTAX      ConfdString
    MAX-ACCESS  read-only
    STATUS      current
    DESCRIPTION "The number of initiator traffic selector payloads received"
    ::= { affirmedSecurityStatisticsIkeMessageNetworkContextEntry 195 }

affirmedSecurityStatisticsIkeMessageNetworkContextIkev2ReceivePayloadTsr OBJECT-TYPE
    SYNTAX      ConfdString
    MAX-ACCESS  read-only
    STATUS      current
    DESCRIPTION "The number of responder traffic selector payloads received"
    ::= { affirmedSecurityStatisticsIkeMessageNetworkContextEntry 196 }

affirmedSecurityStatisticsIkeMessageNetworkContextIkev2ReceivePayloadConf OBJECT-TYPE
    SYNTAX      ConfdString
    MAX-ACCESS  read-only
    STATUS      current
    DESCRIPTION "The number of configuration payloads received"
    ::= { affirmedSecurityStatisticsIkeMessageNetworkContextEntry 197 }

affirmedSecurityStatisticsIkeMessageNetworkContextIkev2ReceivePayloadEap OBJECT-TYPE
    SYNTAX      ConfdString
    MAX-ACCESS  read-only
    STATUS      current
    DESCRIPTION "The number of EAP payloads received"
    ::= { affirmedSecurityStatisticsIkeMessageNetworkContextEntry 198 }

affirmedSecurityStatisticsIkeMessageNetworkContextIkev2EncodeSa OBJECT-TYPE
    SYNTAX      ConfdString
    MAX-ACCESS  read-only
    STATUS      current
    DESCRIPTION "The number of SA payloads sent"
    ::= { affirmedSecurityStatisticsIkeMessageNetworkContextEntry 199 }

affirmedSecurityStatisticsIkeMessageNetworkContextIkev2EncodeKe OBJECT-TYPE
    SYNTAX      ConfdString
    MAX-ACCESS  read-only
    STATUS      current
    DESCRIPTION "The number of key exchange payloads received"
    ::= { affirmedSecurityStatisticsIkeMessageNetworkContextEntry 200 }

affirmedSecurityStatisticsIkeMessageNetworkContextIkev2EncodeId OBJECT-TYPE
    SYNTAX      ConfdString
    MAX-ACCESS  read-only
    STATUS      current
    DESCRIPTION "The number of initiator id payloads sent"
    ::= { affirmedSecurityStatisticsIkeMessageNetworkContextEntry 201 }

affirmedSecurityStatisticsIkeMessageNetworkContextIkev2EncodeCert OBJECT-TYPE
    SYNTAX      ConfdString
    MAX-ACCESS  read-only
    STATUS      current
    DESCRIPTION "The number of certificate payloads sent"
    ::= { affirmedSecurityStatisticsIkeMessageNetworkContextEntry 202 }

affirmedSecurityStatisticsIkeMessageNetworkContextIkev2EncodeCertReq OBJECT-TYPE
    SYNTAX      ConfdString
    MAX-ACCESS  read-only
    STATUS      current
    DESCRIPTION "The number of certificate request payloads sent"
    ::= { affirmedSecurityStatisticsIkeMessageNetworkContextEntry 203 }

affirmedSecurityStatisticsIkeMessageNetworkContextIkev2EncodeAuth OBJECT-TYPE
    SYNTAX      ConfdString
    MAX-ACCESS  read-only
    STATUS      current
    DESCRIPTION "The number of auth payloads sent"
    ::= { affirmedSecurityStatisticsIkeMessageNetworkContextEntry 204 }

affirmedSecurityStatisticsIkeMessageNetworkContextIkev2EncodeNonce OBJECT-TYPE
    SYNTAX      ConfdString
    MAX-ACCESS  read-only
    STATUS      current
    DESCRIPTION "The number of nonce payloads sent"
    ::= { affirmedSecurityStatisticsIkeMessageNetworkContextEntry 205 }

affirmedSecurityStatisticsIkeMessageNetworkContextIkev2EncodeNotify OBJECT-TYPE
    SYNTAX      ConfdString
    MAX-ACCESS  read-only
    STATUS      current
    DESCRIPTION "The number of notify payloads sent"
    ::= { affirmedSecurityStatisticsIkeMessageNetworkContextEntry 206 }

affirmedSecurityStatisticsIkeMessageNetworkContextIkev2EncodeDelete OBJECT-TYPE
    SYNTAX      ConfdString
    MAX-ACCESS  read-only
    STATUS      current
    DESCRIPTION "The number of delete payloads sent"
    ::= { affirmedSecurityStatisticsIkeMessageNetworkContextEntry 207 }

affirmedSecurityStatisticsIkeMessageNetworkContextIkev2EncodeVid OBJECT-TYPE
    SYNTAX      ConfdString
    MAX-ACCESS  read-only
    STATUS      current
    DESCRIPTION "The number of vendor id payloads sent"
    ::= { affirmedSecurityStatisticsIkeMessageNetworkContextEntry 208 }

affirmedSecurityStatisticsIkeMessageNetworkContextIkev2EncodeTs OBJECT-TYPE
    SYNTAX      ConfdString
    MAX-ACCESS  read-only
    STATUS      current
    DESCRIPTION "The number of traffic selector payloads sent"
    ::= { affirmedSecurityStatisticsIkeMessageNetworkContextEntry 209 }

affirmedSecurityStatisticsIkeMessageNetworkContextIkev2EncodeConf OBJECT-TYPE
    SYNTAX      ConfdString
    MAX-ACCESS  read-only
    STATUS      current
    DESCRIPTION "The number of configuration payloads sent"
    ::= { affirmedSecurityStatisticsIkeMessageNetworkContextEntry 210 }

affirmedSecurityStatisticsIkeMessageNetworkContextIkev2EncodeEap OBJECT-TYPE
    SYNTAX      ConfdString
    MAX-ACCESS  read-only
    STATUS      current
    DESCRIPTION "The number of EAP payloads sent"
    ::= { affirmedSecurityStatisticsIkeMessageNetworkContextEntry 211 }

affirmedSecurityStatisticsIkeMessageNetworkContextRxNotifyUnsupported OBJECT-TYPE
    SYNTAX      ConfdString
    MAX-ACCESS  read-only
    STATUS      current
    DESCRIPTION "The number of notify unsupported received"
    ::= { affirmedSecurityStatisticsIkeMessageNetworkContextEntry 212 }

affirmedSecurityStatisticsIkeMessageNetworkContextRxNotifyInvalidIkeSpi OBJECT-TYPE
    SYNTAX      ConfdString
    MAX-ACCESS  read-only
    STATUS      current
    DESCRIPTION "The number of notify invalid IKE SPI received"
    ::= { affirmedSecurityStatisticsIkeMessageNetworkContextEntry 213 }

affirmedSecurityStatisticsIkeMessageNetworkContextRxNotifyInvalidMajorVer OBJECT-TYPE
    SYNTAX      ConfdString
    MAX-ACCESS  read-only
    STATUS      current
    DESCRIPTION "The number of notify invalid major version received"
    ::= { affirmedSecurityStatisticsIkeMessageNetworkContextEntry 214 }

affirmedSecurityStatisticsIkeMessageNetworkContextRxNotifyInvalidSyntax OBJECT-TYPE
    SYNTAX      ConfdString
    MAX-ACCESS  read-only
    STATUS      current
    DESCRIPTION "The number of notify invalid syntax received"
    ::= { affirmedSecurityStatisticsIkeMessageNetworkContextEntry 215 }

affirmedSecurityStatisticsIkeMessageNetworkContextRxNotifyInvalidMsgId OBJECT-TYPE
    SYNTAX      ConfdString
    MAX-ACCESS  read-only
    STATUS      current
    DESCRIPTION "The number of notify invalid message id received"
    ::= { affirmedSecurityStatisticsIkeMessageNetworkContextEntry 216 }

affirmedSecurityStatisticsIkeMessageNetworkContextRxNotifyInvalidSpi OBJECT-TYPE
    SYNTAX      ConfdString
    MAX-ACCESS  read-only
    STATUS      current
    DESCRIPTION "The number of notify invalid SPI received"
    ::= { affirmedSecurityStatisticsIkeMessageNetworkContextEntry 217 }

affirmedSecurityStatisticsIkeMessageNetworkContextRxNotifyNoProposalChosen OBJECT-TYPE
    SYNTAX      ConfdString
    MAX-ACCESS  read-only
    STATUS      current
    DESCRIPTION "The number of notify no proposal chosen received"
    ::= { affirmedSecurityStatisticsIkeMessageNetworkContextEntry 218 }

affirmedSecurityStatisticsIkeMessageNetworkContextRxNotifyInvalidIkePayload OBJECT-TYPE
    SYNTAX      ConfdString
    MAX-ACCESS  read-only
    STATUS      current
    DESCRIPTION "The number of notify invalid IKE payload received"
    ::= { affirmedSecurityStatisticsIkeMessageNetworkContextEntry 219 }

affirmedSecurityStatisticsIkeMessageNetworkContextRxNotifyAuthFailed OBJECT-TYPE
    SYNTAX      ConfdString
    MAX-ACCESS  read-only
    STATUS      current
    DESCRIPTION "The number of notify auth failed received"
    ::= { affirmedSecurityStatisticsIkeMessageNetworkContextEntry 220 }

affirmedSecurityStatisticsIkeMessageNetworkContextRxNotifySinglePairReq OBJECT-TYPE
    SYNTAX      ConfdString
    MAX-ACCESS  read-only
    STATUS      current
    DESCRIPTION "The number of notify single pair required received"
    ::= { affirmedSecurityStatisticsIkeMessageNetworkContextEntry 221 }

affirmedSecurityStatisticsIkeMessageNetworkContextRxNotifyNoAdditionalSas OBJECT-TYPE
    SYNTAX      ConfdString
    MAX-ACCESS  read-only
    STATUS      current
    DESCRIPTION "The number of notify no additional sas received"
    ::= { affirmedSecurityStatisticsIkeMessageNetworkContextEntry 222 }

affirmedSecurityStatisticsIkeMessageNetworkContextRxNotifyInternalAddressFail OBJECT-TYPE
    SYNTAX      ConfdString
    MAX-ACCESS  read-only
    STATUS      current
    DESCRIPTION "The number of notify internal address failure received"
    ::= { affirmedSecurityStatisticsIkeMessageNetworkContextEntry 223 }

affirmedSecurityStatisticsIkeMessageNetworkContextRxNotifyFailCpRequired OBJECT-TYPE
    SYNTAX      ConfdString
    MAX-ACCESS  read-only
    STATUS      current
    DESCRIPTION "The number of notify critical payload required received"
    ::= { affirmedSecurityStatisticsIkeMessageNetworkContextEntry 224 }

affirmedSecurityStatisticsIkeMessageNetworkContextRxNotifyTsUnacceptable OBJECT-TYPE
    SYNTAX      ConfdString
    MAX-ACCESS  read-only
    STATUS      current
    DESCRIPTION "The number of notify traffic selector unacceptable received"
    ::= { affirmedSecurityStatisticsIkeMessageNetworkContextEntry 225 }

affirmedSecurityStatisticsIkeMessageNetworkContextRxNotifyInvalidSelectors OBJECT-TYPE
    SYNTAX      ConfdString
    MAX-ACCESS  read-only
    STATUS      current
    DESCRIPTION "The number of notify invalid traffic selector received"
    ::= { affirmedSecurityStatisticsIkeMessageNetworkContextEntry 226 }

affirmedSecurityStatisticsIkeMessageNetworkContextRxNotifyUnacceptableAddr OBJECT-TYPE
    SYNTAX      ConfdString
    MAX-ACCESS  read-only
    STATUS      current
    DESCRIPTION "The number of notify unacceptable address received"
    ::= { affirmedSecurityStatisticsIkeMessageNetworkContextEntry 227 }

affirmedSecurityStatisticsIkeMessageNetworkContextRxNotifyUnexpectedNat OBJECT-TYPE
    SYNTAX      ConfdString
    MAX-ACCESS  read-only
    STATUS      current
    DESCRIPTION "The number of notify unexpected NAT received"
    ::= { affirmedSecurityStatisticsIkeMessageNetworkContextEntry 228 }

affirmedSecurityStatisticsIkeMessageNetworkContextRxNotifyTempFailure OBJECT-TYPE
    SYNTAX      ConfdString
    MAX-ACCESS  read-only
    STATUS      current
    DESCRIPTION "The number of notify temporary failure received"
    ::= { affirmedSecurityStatisticsIkeMessageNetworkContextEntry 229 }

affirmedSecurityStatisticsIkeMessageNetworkContextRxNotifyChildSaNotFound OBJECT-TYPE
    SYNTAX      ConfdString
    MAX-ACCESS  read-only
    STATUS      current
    DESCRIPTION "The number of notify child SA not found received"
    ::= { affirmedSecurityStatisticsIkeMessageNetworkContextEntry 230 }

affirmedSecurityStatisticsIkeMessageNetworkContextRxNotifyInitialContact OBJECT-TYPE
    SYNTAX      ConfdString
    MAX-ACCESS  read-only
    STATUS      current
    DESCRIPTION "The number of notify initial contact received"
    ::= { affirmedSecurityStatisticsIkeMessageNetworkContextEntry 231 }

affirmedSecurityStatisticsIkeMessageNetworkContextRxNotifySetWindowSize OBJECT-TYPE
    SYNTAX      ConfdString
    MAX-ACCESS  read-only
    STATUS      current
    DESCRIPTION "The number of notify set window size received"
    ::= { affirmedSecurityStatisticsIkeMessageNetworkContextEntry 232 }

affirmedSecurityStatisticsIkeMessageNetworkContextRxNotifyAdditionalTsPossible OBJECT-TYPE
    SYNTAX      ConfdString
    MAX-ACCESS  read-only
    STATUS      current
    DESCRIPTION "The number of notify additional traffic selector possible received"
    ::= { affirmedSecurityStatisticsIkeMessageNetworkContextEntry 233 }

affirmedSecurityStatisticsIkeMessageNetworkContextRxNotifyIpcompSupported OBJECT-TYPE
    SYNTAX      ConfdString
    MAX-ACCESS  read-only
    STATUS      current
    DESCRIPTION "The number of notify compression supported received"
    ::= { affirmedSecurityStatisticsIkeMessageNetworkContextEntry 234 }

affirmedSecurityStatisticsIkeMessageNetworkContextRxNotifyNatDetectSrcIp OBJECT-TYPE
    SYNTAX      ConfdString
    MAX-ACCESS  read-only
    STATUS      current
    DESCRIPTION "The number of notify NAT detect source ip received"
    ::= { affirmedSecurityStatisticsIkeMessageNetworkContextEntry 235 }

affirmedSecurityStatisticsIkeMessageNetworkContextRxNotifyNatDetectDstIp OBJECT-TYPE
    SYNTAX      ConfdString
    MAX-ACCESS  read-only
    STATUS      current
    DESCRIPTION "The number of notify NAT detect destination ip received"
    ::= { affirmedSecurityStatisticsIkeMessageNetworkContextEntry 236 }

affirmedSecurityStatisticsIkeMessageNetworkContextRxNotifyCookie OBJECT-TYPE
    SYNTAX      ConfdString
    MAX-ACCESS  read-only
    STATUS      current
    DESCRIPTION "The number of notify cookie received"
    ::= { affirmedSecurityStatisticsIkeMessageNetworkContextEntry 237 }

affirmedSecurityStatisticsIkeMessageNetworkContextRxNotifyUseTransportMode OBJECT-TYPE
    SYNTAX      ConfdString
    MAX-ACCESS  read-only
    STATUS      current
    DESCRIPTION "The number of notify use transport mode received"
    ::= { affirmedSecurityStatisticsIkeMessageNetworkContextEntry 238 }

affirmedSecurityStatisticsIkeMessageNetworkContextRxNotifyHttpCertSupported OBJECT-TYPE
    SYNTAX      ConfdString
    MAX-ACCESS  read-only
    STATUS      current
    DESCRIPTION "The number of notify http certificate supported received"
    ::= { affirmedSecurityStatisticsIkeMessageNetworkContextEntry 239 }

affirmedSecurityStatisticsIkeMessageNetworkContextRxNotifyRekeySa OBJECT-TYPE
    SYNTAX      ConfdString
    MAX-ACCESS  read-only
    STATUS      current
    DESCRIPTION "The number of notify rekey SA received"
    ::= { affirmedSecurityStatisticsIkeMessageNetworkContextEntry 240 }

affirmedSecurityStatisticsIkeMessageNetworkContextRxNotifyTfcPadNotSupported OBJECT-TYPE
    SYNTAX      ConfdString
    MAX-ACCESS  read-only
    STATUS      current
    DESCRIPTION "The number of notify tfc pad not supported received"
    ::= { affirmedSecurityStatisticsIkeMessageNetworkContextEntry 241 }

affirmedSecurityStatisticsIkeMessageNetworkContextRxNotifyNonFirstFragmentsAlso OBJECT-TYPE
    SYNTAX      ConfdString
    MAX-ACCESS  read-only
    STATUS      current
    DESCRIPTION "The number of notify non first fragments also received"
    ::= { affirmedSecurityStatisticsIkeMessageNetworkContextEntry 242 }

affirmedSecurityStatisticsIkeMessageNetworkContextRxNotifyMobikeSupported OBJECT-TYPE
    SYNTAX      ConfdString
    MAX-ACCESS  read-only
    STATUS      current
    DESCRIPTION "The number of notify mobike supported received"
    ::= { affirmedSecurityStatisticsIkeMessageNetworkContextEntry 243 }

affirmedSecurityStatisticsIkeMessageNetworkContextRxNotifyAdditionalV4Addr OBJECT-TYPE
    SYNTAX      ConfdString
    MAX-ACCESS  read-only
    STATUS      current
    DESCRIPTION "The number of notify additional v4 address received"
    ::= { affirmedSecurityStatisticsIkeMessageNetworkContextEntry 244 }

affirmedSecurityStatisticsIkeMessageNetworkContextRxNotifyAdditionalV6Addr OBJECT-TYPE
    SYNTAX      ConfdString
    MAX-ACCESS  read-only
    STATUS      current
    DESCRIPTION "The number of notify additional v6 address received"
    ::= { affirmedSecurityStatisticsIkeMessageNetworkContextEntry 245 }

affirmedSecurityStatisticsIkeMessageNetworkContextRxNotifyNoAdditionalAddr OBJECT-TYPE
    SYNTAX      ConfdString
    MAX-ACCESS  read-only
    STATUS      current
    DESCRIPTION "The number of notify no additional address received"
    ::= { affirmedSecurityStatisticsIkeMessageNetworkContextEntry 246 }

affirmedSecurityStatisticsIkeMessageNetworkContextRxNotifyUpdateSaAddr OBJECT-TYPE
    SYNTAX      ConfdString
    MAX-ACCESS  read-only
    STATUS      current
    DESCRIPTION "The number of notify update SA address received"
    ::= { affirmedSecurityStatisticsIkeMessageNetworkContextEntry 247 }

affirmedSecurityStatisticsIkeMessageNetworkContextRxNotifyCookie2 OBJECT-TYPE
    SYNTAX      ConfdString
    MAX-ACCESS  read-only
    STATUS      current
    DESCRIPTION "The number of notify cookie 2 received"
    ::= { affirmedSecurityStatisticsIkeMessageNetworkContextEntry 248 }

affirmedSecurityStatisticsIkeMessageNetworkContextRxNotifyNoNatsAllowed OBJECT-TYPE
    SYNTAX      ConfdString
    MAX-ACCESS  read-only
    STATUS      current
    DESCRIPTION "The number of notify no nats allowed received"
    ::= { affirmedSecurityStatisticsIkeMessageNetworkContextEntry 249 }

affirmedSecurityStatisticsIkeMessageNetworkContextRxNotifyMultiAuthSupported OBJECT-TYPE
    SYNTAX      ConfdString
    MAX-ACCESS  read-only
    STATUS      current
    DESCRIPTION "The number of notify multi auth supported received"
    ::= { affirmedSecurityStatisticsIkeMessageNetworkContextEntry 250 }

affirmedSecurityStatisticsIkeMessageNetworkContextRxNotifyAuthFollows OBJECT-TYPE
    SYNTAX      ConfdString
    MAX-ACCESS  read-only
    STATUS      current
    DESCRIPTION "The number of notify auth follows received"
    ::= { affirmedSecurityStatisticsIkeMessageNetworkContextEntry 251 }

affirmedSecurityStatisticsIkeMessageNetworkContextRxNotifyEapOnlyAuth OBJECT-TYPE
    SYNTAX      ConfdString
    MAX-ACCESS  read-only
    STATUS      current
    DESCRIPTION "The number of notify EAP only auth received"
    ::= { affirmedSecurityStatisticsIkeMessageNetworkContextEntry 252 }

affirmedSecurityStatisticsIkeMessageNetworkContextRxNotifyUnknown OBJECT-TYPE
    SYNTAX      ConfdString
    MAX-ACCESS  read-only
    STATUS      current
    DESCRIPTION "The number of notify unknown received"
    ::= { affirmedSecurityStatisticsIkeMessageNetworkContextEntry 253 }

affirmedSecurityStatisticsIkeMessageNetworkContextTxNotifyUnsupported OBJECT-TYPE
    SYNTAX      ConfdString
    MAX-ACCESS  read-only
    STATUS      current
    DESCRIPTION "The number of notify unsupported sent"
    ::= { affirmedSecurityStatisticsIkeMessageNetworkContextEntry 254 }

affirmedSecurityStatisticsIkeMessageNetworkContextTxNotifyInvalidIkeSpi OBJECT-TYPE
    SYNTAX      ConfdString
    MAX-ACCESS  read-only
    STATUS      current
    DESCRIPTION "The number of notify invalid IKE SPI sent"
    ::= { affirmedSecurityStatisticsIkeMessageNetworkContextEntry 255 }

affirmedSecurityStatisticsIkeMessageNetworkContextTxNotifyInvalidMajorVer OBJECT-TYPE
    SYNTAX      ConfdString
    MAX-ACCESS  read-only
    STATUS      current
    DESCRIPTION "The number of notify invalid major version sent"
    ::= { affirmedSecurityStatisticsIkeMessageNetworkContextEntry 256 }

affirmedSecurityStatisticsIkeMessageNetworkContextTxNotifyInvalidSyntax OBJECT-TYPE
    SYNTAX      ConfdString
    MAX-ACCESS  read-only
    STATUS      current
    DESCRIPTION "The number of notify invalid syntax sent"
    ::= { affirmedSecurityStatisticsIkeMessageNetworkContextEntry 257 }

affirmedSecurityStatisticsIkeMessageNetworkContextTxNotifyInvalidMsgId OBJECT-TYPE
    SYNTAX      ConfdString
    MAX-ACCESS  read-only
    STATUS      current
    DESCRIPTION "The number of notify invalid message id sent"
    ::= { affirmedSecurityStatisticsIkeMessageNetworkContextEntry 258 }

affirmedSecurityStatisticsIkeMessageNetworkContextTxNotifyInvalidSpi OBJECT-TYPE
    SYNTAX      ConfdString
    MAX-ACCESS  read-only
    STATUS      current
    DESCRIPTION "The number of notify invalid SPI sent"
    ::= { affirmedSecurityStatisticsIkeMessageNetworkContextEntry 259 }

affirmedSecurityStatisticsIkeMessageNetworkContextTxNotifyNoProposalChosen OBJECT-TYPE
    SYNTAX      ConfdString
    MAX-ACCESS  read-only
    STATUS      current
    DESCRIPTION "The number of notify no proposal chosen sent"
    ::= { affirmedSecurityStatisticsIkeMessageNetworkContextEntry 260 }

affirmedSecurityStatisticsIkeMessageNetworkContextTxNotifyInvalidIkePayload OBJECT-TYPE
    SYNTAX      ConfdString
    MAX-ACCESS  read-only
    STATUS      current
    DESCRIPTION "The number of notify invalid IKE payload sent"
    ::= { affirmedSecurityStatisticsIkeMessageNetworkContextEntry 261 }

affirmedSecurityStatisticsIkeMessageNetworkContextTxNotifyAuthFailed OBJECT-TYPE
    SYNTAX      ConfdString
    MAX-ACCESS  read-only
    STATUS      current
    DESCRIPTION "The number of notify auth failed sent"
    ::= { affirmedSecurityStatisticsIkeMessageNetworkContextEntry 262 }

affirmedSecurityStatisticsIkeMessageNetworkContextTxNotifySinglePairReq OBJECT-TYPE
    SYNTAX      ConfdString
    MAX-ACCESS  read-only
    STATUS      current
    DESCRIPTION "The number of notify single pair required sent"
    ::= { affirmedSecurityStatisticsIkeMessageNetworkContextEntry 263 }

affirmedSecurityStatisticsIkeMessageNetworkContextTxNotifyNoAdditionalSas OBJECT-TYPE
    SYNTAX      ConfdString
    MAX-ACCESS  read-only
    STATUS      current
    DESCRIPTION "The number of notify no additional sas sent"
    ::= { affirmedSecurityStatisticsIkeMessageNetworkContextEntry 264 }

affirmedSecurityStatisticsIkeMessageNetworkContextTxNotifyInternalAddressFail OBJECT-TYPE
    SYNTAX      ConfdString
    MAX-ACCESS  read-only
    STATUS      current
    DESCRIPTION "The number of notify internal address failure sent"
    ::= { affirmedSecurityStatisticsIkeMessageNetworkContextEntry 265 }

affirmedSecurityStatisticsIkeMessageNetworkContextTxNotifyFailCpRequired OBJECT-TYPE
    SYNTAX      ConfdString
    MAX-ACCESS  read-only
    STATUS      current
    DESCRIPTION "The number of notify critical payload required sent"
    ::= { affirmedSecurityStatisticsIkeMessageNetworkContextEntry 266 }

affirmedSecurityStatisticsIkeMessageNetworkContextTxNotifyTsUnacceptable OBJECT-TYPE
    SYNTAX      ConfdString
    MAX-ACCESS  read-only
    STATUS      current
    DESCRIPTION "The number of notify traffic selector unacceptable sent"
    ::= { affirmedSecurityStatisticsIkeMessageNetworkContextEntry 267 }

affirmedSecurityStatisticsIkeMessageNetworkContextTxNotifyInvalidSelectors OBJECT-TYPE
    SYNTAX      ConfdString
    MAX-ACCESS  read-only
    STATUS      current
    DESCRIPTION "The number of notify invalid traffic selector sent"
    ::= { affirmedSecurityStatisticsIkeMessageNetworkContextEntry 268 }

affirmedSecurityStatisticsIkeMessageNetworkContextTxNotifyUnacceptableAddr OBJECT-TYPE
    SYNTAX      ConfdString
    MAX-ACCESS  read-only
    STATUS      current
    DESCRIPTION "The number of notify unacceptable address sent"
    ::= { affirmedSecurityStatisticsIkeMessageNetworkContextEntry 269 }

affirmedSecurityStatisticsIkeMessageNetworkContextTxNotifyUnexpectedNat OBJECT-TYPE
    SYNTAX      ConfdString
    MAX-ACCESS  read-only
    STATUS      current
    DESCRIPTION "The number of notify unexpected NAT sent"
    ::= { affirmedSecurityStatisticsIkeMessageNetworkContextEntry 270 }

affirmedSecurityStatisticsIkeMessageNetworkContextTxNotifyTempFailure OBJECT-TYPE
    SYNTAX      ConfdString
    MAX-ACCESS  read-only
    STATUS      current
    DESCRIPTION "The number of notify temporary failure sent"
    ::= { affirmedSecurityStatisticsIkeMessageNetworkContextEntry 271 }

affirmedSecurityStatisticsIkeMessageNetworkContextTxNotifyChildSaNotFound OBJECT-TYPE
    SYNTAX      ConfdString
    MAX-ACCESS  read-only
    STATUS      current
    DESCRIPTION "The number of notify child SA not found sent"
    ::= { affirmedSecurityStatisticsIkeMessageNetworkContextEntry 272 }

affirmedSecurityStatisticsIkeMessageNetworkContextTxNotifyInitialContact OBJECT-TYPE
    SYNTAX      ConfdString
    MAX-ACCESS  read-only
    STATUS      current
    DESCRIPTION "The number of notify initial contact sent"
    ::= { affirmedSecurityStatisticsIkeMessageNetworkContextEntry 273 }

affirmedSecurityStatisticsIkeMessageNetworkContextTxNotifySetWindowSize OBJECT-TYPE
    SYNTAX      ConfdString
    MAX-ACCESS  read-only
    STATUS      current
    DESCRIPTION "The number of notify set window size sent"
    ::= { affirmedSecurityStatisticsIkeMessageNetworkContextEntry 274 }

affirmedSecurityStatisticsIkeMessageNetworkContextTxNotifyAdditionalTsPossible OBJECT-TYPE
    SYNTAX      ConfdString
    MAX-ACCESS  read-only
    STATUS      current
    DESCRIPTION "The number of notify additional traffic selector possible sent"
    ::= { affirmedSecurityStatisticsIkeMessageNetworkContextEntry 275 }

affirmedSecurityStatisticsIkeMessageNetworkContextTxNotifyIpcompSupported OBJECT-TYPE
    SYNTAX      ConfdString
    MAX-ACCESS  read-only
    STATUS      current
    DESCRIPTION "The number of notify compression supported sent"
    ::= { affirmedSecurityStatisticsIkeMessageNetworkContextEntry 276 }

affirmedSecurityStatisticsIkeMessageNetworkContextTxNotifyNatDetectSrcIp OBJECT-TYPE
    SYNTAX      ConfdString
    MAX-ACCESS  read-only
    STATUS      current
    DESCRIPTION "The number of notify NAT detect source ip sent"
    ::= { affirmedSecurityStatisticsIkeMessageNetworkContextEntry 277 }

affirmedSecurityStatisticsIkeMessageNetworkContextTxNotifyNatDetectDstIp OBJECT-TYPE
    SYNTAX      ConfdString
    MAX-ACCESS  read-only
    STATUS      current
    DESCRIPTION "The number of notify NAT detect destination ip sent"
    ::= { affirmedSecurityStatisticsIkeMessageNetworkContextEntry 278 }

affirmedSecurityStatisticsIkeMessageNetworkContextTxNotifyCookie OBJECT-TYPE
    SYNTAX      ConfdString
    MAX-ACCESS  read-only
    STATUS      current
    DESCRIPTION "The number of notify cookie sent"
    ::= { affirmedSecurityStatisticsIkeMessageNetworkContextEntry 279 }

affirmedSecurityStatisticsIkeMessageNetworkContextTxNotifyUseTransportMode OBJECT-TYPE
    SYNTAX      ConfdString
    MAX-ACCESS  read-only
    STATUS      current
    DESCRIPTION "The number of notify use transport mode sent"
    ::= { affirmedSecurityStatisticsIkeMessageNetworkContextEntry 280 }

affirmedSecurityStatisticsIkeMessageNetworkContextTxNotifyHttpCertSupported OBJECT-TYPE
    SYNTAX      ConfdString
    MAX-ACCESS  read-only
    STATUS      current
    DESCRIPTION "The number of notify http certificate supported sent"
    ::= { affirmedSecurityStatisticsIkeMessageNetworkContextEntry 281 }

affirmedSecurityStatisticsIkeMessageNetworkContextTxNotifyRekeySa OBJECT-TYPE
    SYNTAX      ConfdString
    MAX-ACCESS  read-only
    STATUS      current
    DESCRIPTION "The number of notify rekey SA sent"
    ::= { affirmedSecurityStatisticsIkeMessageNetworkContextEntry 282 }

affirmedSecurityStatisticsIkeMessageNetworkContextTxNotifyTfcPadNotSupported OBJECT-TYPE
    SYNTAX      ConfdString
    MAX-ACCESS  read-only
    STATUS      current
    DESCRIPTION "The number of notify tfc pad not supported sent"
    ::= { affirmedSecurityStatisticsIkeMessageNetworkContextEntry 283 }

affirmedSecurityStatisticsIkeMessageNetworkContextTxNotifyNonFirstFragmentsAlso OBJECT-TYPE
    SYNTAX      ConfdString
    MAX-ACCESS  read-only
    STATUS      current
    DESCRIPTION "The number of notify non first fragments also sent"
    ::= { affirmedSecurityStatisticsIkeMessageNetworkContextEntry 284 }

affirmedSecurityStatisticsIkeMessageNetworkContextTxNotifyMobikeSupported OBJECT-TYPE
    SYNTAX      ConfdString
    MAX-ACCESS  read-only
    STATUS      current
    DESCRIPTION "The number of notify mobike supported sent"
    ::= { affirmedSecurityStatisticsIkeMessageNetworkContextEntry 285 }

affirmedSecurityStatisticsIkeMessageNetworkContextTxNotifyAdditionalV4Addr OBJECT-TYPE
    SYNTAX      ConfdString
    MAX-ACCESS  read-only
    STATUS      current
    DESCRIPTION "The number of notify additional v4 address sent"
    ::= { affirmedSecurityStatisticsIkeMessageNetworkContextEntry 286 }

affirmedSecurityStatisticsIkeMessageNetworkContextTxNotifyAdditionalV6Addr OBJECT-TYPE
    SYNTAX      ConfdString
    MAX-ACCESS  read-only
    STATUS      current
    DESCRIPTION "The number of notify additional v6 address sent"
    ::= { affirmedSecurityStatisticsIkeMessageNetworkContextEntry 287 }

affirmedSecurityStatisticsIkeMessageNetworkContextTxNotifyNoAdditionalAddr OBJECT-TYPE
    SYNTAX      ConfdString
    MAX-ACCESS  read-only
    STATUS      current
    DESCRIPTION "The number of notify no additional address sent"
    ::= { affirmedSecurityStatisticsIkeMessageNetworkContextEntry 288 }

affirmedSecurityStatisticsIkeMessageNetworkContextTxNotifyUpdateSaAddr OBJECT-TYPE
    SYNTAX      ConfdString
    MAX-ACCESS  read-only
    STATUS      current
    DESCRIPTION "The number of notify update SA address sent"
    ::= { affirmedSecurityStatisticsIkeMessageNetworkContextEntry 289 }

affirmedSecurityStatisticsIkeMessageNetworkContextTxNotifyCookie2 OBJECT-TYPE
    SYNTAX      ConfdString
    MAX-ACCESS  read-only
    STATUS      current
    DESCRIPTION "The number of notify cookie 2 sent"
    ::= { affirmedSecurityStatisticsIkeMessageNetworkContextEntry 290 }

affirmedSecurityStatisticsIkeMessageNetworkContextTxNotifyNoNatsAllowed OBJECT-TYPE
    SYNTAX      ConfdString
    MAX-ACCESS  read-only
    STATUS      current
    DESCRIPTION "The number of notify no nats allowed sent"
    ::= { affirmedSecurityStatisticsIkeMessageNetworkContextEntry 291 }

affirmedSecurityStatisticsIkeMessageNetworkContextTxNotifyMultiAuthSupported OBJECT-TYPE
    SYNTAX      ConfdString
    MAX-ACCESS  read-only
    STATUS      current
    DESCRIPTION "The number of notify multi auth supported sent"
    ::= { affirmedSecurityStatisticsIkeMessageNetworkContextEntry 292 }

affirmedSecurityStatisticsIkeMessageNetworkContextTxNotifyAuthFollows OBJECT-TYPE
    SYNTAX      ConfdString
    MAX-ACCESS  read-only
    STATUS      current
    DESCRIPTION "The number of notify auth follows sent"
    ::= { affirmedSecurityStatisticsIkeMessageNetworkContextEntry 293 }

affirmedSecurityStatisticsIkeMessageNetworkContextTxNotifyEapOnlyAuth OBJECT-TYPE
    SYNTAX      ConfdString
    MAX-ACCESS  read-only
    STATUS      current
    DESCRIPTION "The number of notify EAP only auth sent"
    ::= { affirmedSecurityStatisticsIkeMessageNetworkContextEntry 294 }

affirmedSecurityStatisticsIkeMessageNetworkContextTxNotifyUnknown OBJECT-TYPE
    SYNTAX      ConfdString
    MAX-ACCESS  read-only
    STATUS      current
    DESCRIPTION "The number of notify unknown error sent"
    ::= { affirmedSecurityStatisticsIkeMessageNetworkContextEntry 295 }

affirmedSecurityStatisticsIkeMessageNetworkContextRxNotifyDeviceIdImei OBJECT-TYPE
    SYNTAX      ConfdString
    MAX-ACCESS  read-only
    STATUS      current
    DESCRIPTION "The number of notify device identity received"
    ::= { affirmedSecurityStatisticsIkeMessageNetworkContextEntry 296 }

affirmedSecurityStatisticsIkeMessageNetworkContextRxNotifyImeiDecodeSuccess OBJECT-TYPE
    SYNTAX      ConfdString
    MAX-ACCESS  read-only
    STATUS      current
    DESCRIPTION "The number of notify device identity decoded successfully"
    ::= { affirmedSecurityStatisticsIkeMessageNetworkContextEntry 297 }

affirmedSecurityStatisticsIkeMessageNetworkContextRxNotifyImeiTypeImei OBJECT-TYPE
    SYNTAX      ConfdString
    MAX-ACCESS  read-only
    STATUS      current
    DESCRIPTION "The number of notify imei type imei received"
    ::= { affirmedSecurityStatisticsIkeMessageNetworkContextEntry 298 }

affirmedSecurityStatisticsIkeMessageNetworkContextRxNotifyImeiTypeImeisv OBJECT-TYPE
    SYNTAX      ConfdString
    MAX-ACCESS  read-only
    STATUS      current
    DESCRIPTION "The number of notify imei type isv received"
    ::= { affirmedSecurityStatisticsIkeMessageNetworkContextEntry 299 }

affirmedSecurityStatisticsIkeMessageNetworkContextRxNotifyImeiTypeInvalid OBJECT-TYPE
    SYNTAX      ConfdString
    MAX-ACCESS  read-only
    STATUS      current
    DESCRIPTION "The number of notify imei type invalid received"
    ::= { affirmedSecurityStatisticsIkeMessageNetworkContextEntry 300 }

affirmedSecurityStatisticsIkeMessageNetworkContextRxNotifyImeiDecodeFailTypeMismatch OBJECT-TYPE
    SYNTAX      ConfdString
    MAX-ACCESS  read-only
    STATUS      current
    DESCRIPTION "The number of notify imei decode failed due to type mismatch"
    ::= { affirmedSecurityStatisticsIkeMessageNetworkContextEntry 301 }

affirmedSecurityStatisticsIkeMessageNetworkContextRxNotifyImeiDecodeFailBadLength OBJECT-TYPE
    SYNTAX      ConfdString
    MAX-ACCESS  read-only
    STATUS      current
    DESCRIPTION "The number of notify imei decode failed due to bad length"
    ::= { affirmedSecurityStatisticsIkeMessageNetworkContextEntry 302 }

affirmedSecurityStatisticsIkeMessageNetworkContextTxNotifyDeviceIdImei OBJECT-TYPE
    SYNTAX      ConfdString
    MAX-ACCESS  read-only
    STATUS      current
    DESCRIPTION "The number of notify device identity sent"
    ::= { affirmedSecurityStatisticsIkeMessageNetworkContextEntry 303 }

affirmedSecurityStatisticsIkeMessageNetworkContextTxNotifyCongestionError OBJECT-TYPE
    SYNTAX      ConfdString
    MAX-ACCESS  read-only
    STATUS      current
    DESCRIPTION "The number of notify congestion error sent"
    ::= { affirmedSecurityStatisticsIkeMessageNetworkContextEntry 304 }

affirmedSecurityStatisticsIkeMessageNetworkContextTxNotifyPrivateError OBJECT-TYPE
    SYNTAX      ConfdString
    MAX-ACCESS  read-only
    STATUS      current
    DESCRIPTION "The number of notify private error sent"
    ::= { affirmedSecurityStatisticsIkeMessageNetworkContextEntry 305 }

affirmedSecurityStatisticsIkeMessageNetworkContextDeadPeerDetections OBJECT-TYPE
    SYNTAX      ConfdString
    MAX-ACCESS  read-only
    STATUS      current
    DESCRIPTION "Number of remote peers declared dead by dead peer detection."
    ::= { affirmedSecurityStatisticsIkeMessageNetworkContextEntry 306 }

affirmedSecurityStatisticsIkeMessageNetworkContextTxNotifyError OBJECT-TYPE
    SYNTAX      ConfdString
    MAX-ACCESS  read-only
    STATUS      deprecated
    DESCRIPTION ""
    ::= { affirmedSecurityStatisticsIkeMessageNetworkContextEntry 307 }

affirmedSecurityStatisticsIkeMessageNetworkContextIkev2ReceiveAnonymousIdi OBJECT-TYPE
    SYNTAX      ConfdString
    MAX-ACCESS  read-only
    STATUS      current
    DESCRIPTION "The number of anonymous IDi received"
    ::= { affirmedSecurityStatisticsIkeMessageNetworkContextEntry 308 }

affirmedSecurityStatisticsIkeMessageNetworkContextIkev2ReceiveEapResponseIdentity OBJECT-TYPE
    SYNTAX      ConfdString
    MAX-ACCESS  read-only
    STATUS      current
    DESCRIPTION "The number of EAP Response/Identity received"
    ::= { affirmedSecurityStatisticsIkeMessageNetworkContextEntry 309 }

affirmedSecurityStatisticsIkeMessageNetworkContextIkev2AuthMethodNoCaCerts OBJECT-TYPE
    SYNTAX      ConfdString
    MAX-ACCESS  read-only
    STATUS      current
    DESCRIPTION "Authentication method mismatch: No CA certificates"
    ::= { affirmedSecurityStatisticsIkeMessageNetworkContextEntry 310 }

affirmedSecurityStatisticsIkeMessageNetworkContextIkev2AuthMethodPskWithEapI OBJECT-TYPE
    SYNTAX      ConfdString
    MAX-ACCESS  read-only
    STATUS      current
    DESCRIPTION "Authentication method mismatch: Responder using pre-shared key with EAP"
    ::= { affirmedSecurityStatisticsIkeMessageNetworkContextEntry 311 }

affirmedSecurityStatisticsIkeMessageNetworkContextIkev2AuthMethodPskWithEapR OBJECT-TYPE
    SYNTAX      ConfdString
    MAX-ACCESS  read-only
    STATUS      current
    DESCRIPTION "Authentication method mismatch: Using pre-shared key with EAP as responder"
    ::= { affirmedSecurityStatisticsIkeMessageNetworkContextEntry 312 }

affirmedSecurityStatisticsIkeMessageNetworkContextIkev2AuthMethodNoEapMethods OBJECT-TYPE
    SYNTAX      ConfdString
    MAX-ACCESS  read-only
    STATUS      current
    DESCRIPTION "Authentication method mismatch: No EAP methods"
    ::= { affirmedSecurityStatisticsIkeMessageNetworkContextEntry 313 }

affirmedSecurityStatisticsIkeMessageNetworkContextIkev2AuthMethodEapNotAuth OBJECT-TYPE
    SYNTAX      ConfdString
    MAX-ACCESS  read-only
    STATUS      current
    DESCRIPTION "Authentication method mismatch: Using EAP without authentication"
    ::= { affirmedSecurityStatisticsIkeMessageNetworkContextEntry 314 }

affirmedSecurityStatisticsIkeMessageNetworkContextRxFragments OBJECT-TYPE
    SYNTAX      ConfdString
    MAX-ACCESS  read-only
    STATUS      current
    DESCRIPTION "Fragments received"
    ::= { affirmedSecurityStatisticsIkeMessageNetworkContextEntry 315 }

affirmedSecurityStatisticsIkeMessageNetworkContextRxFragmentPackets OBJECT-TYPE
    SYNTAX      ConfdString
    MAX-ACCESS  read-only
    STATUS      current
    DESCRIPTION "Fragmented packets received"
    ::= { affirmedSecurityStatisticsIkeMessageNetworkContextEntry 316 }

affirmedSecurityStatisticsIkeMessageNetworkContextRxFragmentDrop OBJECT-TYPE
    SYNTAX      ConfdString
    MAX-ACCESS  read-only
    STATUS      current
    DESCRIPTION "Recieved fragments dropped"
    ::= { affirmedSecurityStatisticsIkeMessageNetworkContextEntry 317 }

affirmedSecurityStatisticsIkeMessageNetworkContextRxFragmentPacketFail OBJECT-TYPE
    SYNTAX      ConfdString
    MAX-ACCESS  read-only
    STATUS      current
    DESCRIPTION "Fragmented packets which failed reassembly"
    ::= { affirmedSecurityStatisticsIkeMessageNetworkContextEntry 318 }

affirmedSecurityStatisticsIkeMessageNetworkContextRxFragmentDecryptFail OBJECT-TYPE
    SYNTAX      ConfdString
    MAX-ACCESS  read-only
    STATUS      current
    DESCRIPTION "Fragments which failed decryption"
    ::= { affirmedSecurityStatisticsIkeMessageNetworkContextEntry 319 }

affirmedSecurityStatisticsIkeMessageNetworkContextRxFragmentBadPayload OBJECT-TYPE
    SYNTAX      ConfdString
    MAX-ACCESS  read-only
    STATUS      current
    DESCRIPTION "Fragments with invalid Encrypted Fragment payload"
    ::= { affirmedSecurityStatisticsIkeMessageNetworkContextEntry 320 }

affirmedSecurityStatisticsIkeMessageNetworkContextRxFragmentNotNegotiated OBJECT-TYPE
    SYNTAX      ConfdString
    MAX-ACCESS  read-only
    STATUS      current
    DESCRIPTION "Received fragments on an SA where IKE Fragmentation was not negotiated"
    ::= { affirmedSecurityStatisticsIkeMessageNetworkContextEntry 321 }

affirmedSecurityStatisticsIkeMessageNetworkContextTxFragments OBJECT-TYPE
    SYNTAX      ConfdString
    MAX-ACCESS  read-only
    STATUS      current
    DESCRIPTION "Fragments sent"
    ::= { affirmedSecurityStatisticsIkeMessageNetworkContextEntry 322 }

affirmedSecurityStatisticsIkeMessageNetworkContextTxFragmentPackets OBJECT-TYPE
    SYNTAX      ConfdString
    MAX-ACCESS  read-only
    STATUS      current
    DESCRIPTION "Fragmented packets sent"
    ::= { affirmedSecurityStatisticsIkeMessageNetworkContextEntry 323 }

affirmedSecurityStatisticsIkeMessageNetworkContextTxFragmentPacketFail OBJECT-TYPE
    SYNTAX      ConfdString
    MAX-ACCESS  read-only
    STATUS      current
    DESCRIPTION "Fragmented packets which could not be encoded"
    ::= { affirmedSecurityStatisticsIkeMessageNetworkContextEntry 324 }

affirmedSecurityStatisticsIkeMessageNetworkContextRxNotifyFragSupported OBJECT-TYPE
    SYNTAX      ConfdString
    MAX-ACCESS  read-only
    STATUS      current
    DESCRIPTION "The number of notify fragmentation supported received"
    ::= { affirmedSecurityStatisticsIkeMessageNetworkContextEntry 325 }

affirmedSecurityStatisticsIkeMessageNetworkContextRxDpdRequest OBJECT-TYPE
    SYNTAX      ConfdString
    MAX-ACCESS  read-only
    STATUS      current
    DESCRIPTION "DPD requests received"
    ::= { affirmedSecurityStatisticsIkeMessageNetworkContextEntry 326 }

affirmedSecurityStatisticsIkeMessageNetworkContextRxDpdResponse OBJECT-TYPE
    SYNTAX      ConfdString
    MAX-ACCESS  read-only
    STATUS      current
    DESCRIPTION "DPD responses received"
    ::= { affirmedSecurityStatisticsIkeMessageNetworkContextEntry 327 }

affirmedSecurityStatisticsIkeMessageNetworkContextTxNotifyFragSupported OBJECT-TYPE
    SYNTAX      ConfdString
    MAX-ACCESS  read-only
    STATUS      current
    DESCRIPTION "The number of notify fragmentation supported sent"
    ::= { affirmedSecurityStatisticsIkeMessageNetworkContextEntry 328 }

affirmedSecurityStatisticsIkeMessageNetworkContextTxDpdRequest OBJECT-TYPE
    SYNTAX      ConfdString
    MAX-ACCESS  read-only
    STATUS      current
    DESCRIPTION "DPD requests sent"
    ::= { affirmedSecurityStatisticsIkeMessageNetworkContextEntry 329 }

affirmedSecurityStatisticsIkeMessageNetworkContextTxDpdRetransmit OBJECT-TYPE
    SYNTAX      ConfdString
    MAX-ACCESS  read-only
    STATUS      current
    DESCRIPTION "DPD request retransmissions"
    ::= { affirmedSecurityStatisticsIkeMessageNetworkContextEntry 330 }

affirmedSecurityStatisticsIkeMessageNetworkContextTxDpdResponse OBJECT-TYPE
    SYNTAX      ConfdString
    MAX-ACCESS  read-only
    STATUS      current
    DESCRIPTION "DPD responses sent"
    ::= { affirmedSecurityStatisticsIkeMessageNetworkContextEntry 331 }

affirmedSecurityServiceStatusTable OBJECT-TYPE
    SYNTAX      SEQUENCE OF AffirmedSecurityServiceStatusEntry
    MAX-ACCESS  not-accessible
    STATUS      current
    DESCRIPTION ""
    ::= { affirmedSecurity 3 }

affirmedSecurityServiceStatusEntry OBJECT-TYPE
    SYNTAX      AffirmedSecurityServiceStatusEntry
    MAX-ACCESS  not-accessible
    STATUS      current
    DESCRIPTION ""
    INDEX { affirmedSecurityServiceStatusNetworkContext }
        ::= { affirmedSecurityServiceStatusTable 1 }

AffirmedSecurityServiceStatusEntry ::=
    SEQUENCE {
        affirmedSecurityServiceStatusNetworkContext String,
        affirmedSecurityServiceStatusActiveOperStatus INTEGER,
        affirmedSecurityServiceStatusNumActiveInstances Unsigned32,
        affirmedSecurityServiceStatusCurrentIkeTunnels Unsigned32,
        affirmedSecurityServiceStatusCurrentIpsecTunnels Unsigned32
    }

affirmedSecurityServiceStatusNetworkContext OBJECT-TYPE
    SYNTAX      String
    MAX-ACCESS  not-accessible
    STATUS      current
    DESCRIPTION "Security Enabled Network Context Name"
    ::= { affirmedSecurityServiceStatusEntry 1 }

affirmedSecurityServiceStatusActiveOperStatus OBJECT-TYPE
    SYNTAX      INTEGER {up(101),down(102),partially-up(103),maint(104),dryup(105),congested(106),unknown(107)}
    MAX-ACCESS  read-only
    STATUS      current
    DESCRIPTION "Active Operational Status"
    ::= { affirmedSecurityServiceStatusEntry 2 }

affirmedSecurityServiceStatusNumActiveInstances OBJECT-TYPE
    SYNTAX      Unsigned32
    MAX-ACCESS  read-only
    STATUS      current
    DESCRIPTION "Number of HA active instances"
    ::= { affirmedSecurityServiceStatusEntry 3 }

affirmedSecurityServiceStatusCurrentIkeTunnels OBJECT-TYPE
    SYNTAX      Unsigned32
    MAX-ACCESS  read-only
    STATUS      current
    DESCRIPTION "curent ike tunnels on this instance"
    ::= { affirmedSecurityServiceStatusEntry 4 }

affirmedSecurityServiceStatusCurrentIpsecTunnels OBJECT-TYPE
    SYNTAX      Unsigned32
    MAX-ACCESS  read-only
    STATUS      current
    DESCRIPTION "curent ipsec tunnels on this instance"
    ::= { affirmedSecurityServiceStatusEntry 5 }

affirmedSecurityInstanceStatusTable OBJECT-TYPE
    SYNTAX      SEQUENCE OF AffirmedSecurityInstanceStatusEntry
    MAX-ACCESS  not-accessible
    STATUS      current
    DESCRIPTION ""
    ::= { affirmedSecurity 4 }

affirmedSecurityInstanceStatusEntry OBJECT-TYPE
    SYNTAX      AffirmedSecurityInstanceStatusEntry
    MAX-ACCESS  not-accessible
    STATUS      current
    DESCRIPTION ""
    INDEX { affirmedSecurityInstanceStatusNetworkContext, affirmedSecurityInstanceStatusServiceName }
        ::= { affirmedSecurityInstanceStatusTable 1 }

AffirmedSecurityInstanceStatusEntry ::=
    SEQUENCE {
        affirmedSecurityInstanceStatusNetworkContext String,
        affirmedSecurityInstanceStatusServiceName String,
        affirmedSecurityInstanceStatusOperStatus INTEGER,
        affirmedSecurityInstanceStatusOperReason String,
        affirmedSecurityInstanceStatusNode Unsigned32,
        affirmedSecurityInstanceStatusCurrentIkeTunnels Unsigned32,
        affirmedSecurityInstanceStatusCurrentIpsecTunnels Unsigned32
    }

affirmedSecurityInstanceStatusNetworkContext OBJECT-TYPE
    SYNTAX      String
    MAX-ACCESS  not-accessible
    STATUS      current
    DESCRIPTION "Security Enabled Network Context Name"
    ::= { affirmedSecurityInstanceStatusEntry 1 }

affirmedSecurityInstanceStatusServiceName OBJECT-TYPE
    SYNTAX      String
    MAX-ACCESS  not-accessible
    STATUS      current
    DESCRIPTION "Task service name"
    ::= { affirmedSecurityInstanceStatusEntry 2 }

affirmedSecurityInstanceStatusOperStatus OBJECT-TYPE
    SYNTAX      INTEGER {up(101),down(102),partially-up(103),maint(104),dryup(105),congested(106),unknown(107)}
    MAX-ACCESS  read-only
    STATUS      current
    DESCRIPTION "Service Instance Operational Status"
    ::= { affirmedSecurityInstanceStatusEntry 3 }

affirmedSecurityInstanceStatusOperReason OBJECT-TYPE
    SYNTAX      String
    MAX-ACCESS  read-only
    STATUS      current
    DESCRIPTION "Operational Reason if state is Operationally Down"
    ::= { affirmedSecurityInstanceStatusEntry 4 }

affirmedSecurityInstanceStatusNode OBJECT-TYPE
    SYNTAX      Unsigned32
    MAX-ACCESS  read-only
    STATUS      current
    DESCRIPTION "node on which the instance is running"
    ::= { affirmedSecurityInstanceStatusEntry 5 }

affirmedSecurityInstanceStatusCurrentIkeTunnels OBJECT-TYPE
    SYNTAX      Unsigned32
    MAX-ACCESS  read-only
    STATUS      current
    DESCRIPTION "curent ike tunnels on this instance"
    ::= { affirmedSecurityInstanceStatusEntry 6 }

affirmedSecurityInstanceStatusCurrentIpsecTunnels OBJECT-TYPE
    SYNTAX      Unsigned32
    MAX-ACCESS  read-only
    STATUS      current
    DESCRIPTION "curent ipsec tunnels on this instance"
    ::= { affirmedSecurityInstanceStatusEntry 7 }

affirmedSecurityIkeStatsTable OBJECT-TYPE
    SYNTAX      SEQUENCE OF AffirmedSecurityIkeStatsEntry
    MAX-ACCESS  not-accessible
    STATUS      current
    DESCRIPTION ""
    ::= { affirmedSecurity 5 }

affirmedSecurityIkeStatsEntry OBJECT-TYPE
    SYNTAX      AffirmedSecurityIkeStatsEntry
    MAX-ACCESS  not-accessible
    STATUS      current
    DESCRIPTION ""
    INDEX { affirmedSecurityIkeStatsServiceName }
        ::= { affirmedSecurityIkeStatsTable 1 }

AffirmedSecurityIkeStatsEntry ::=
    SEQUENCE {
        affirmedSecurityIkeStatsServiceName String,
        affirmedSecurityIkeStatsTotalIkeSas ConfdString,
        affirmedSecurityIkeStatsTotalIkeSasInitiated ConfdString,
        affirmedSecurityIkeStatsTotalIkeSasResponded ConfdString,
        affirmedSecurityIkeStatsTotalInitFailures ConfdString,
        affirmedSecurityIkeStatsTotalInitNoResponse ConfdString,
        affirmedSecurityIkeStatsTotalRespFailures ConfdString,
        affirmedSecurityIkeStatsDeadPeerDetections ConfdString,
        affirmedSecurityIkeStatsIkeInitReqIn ConfdString,
        affirmedSecurityIkeStatsIkeInitRspIn ConfdString,
        affirmedSecurityIkeStatsIkeAuthFromInitiator ConfdString,
        affirmedSecurityIkeStatsIkeAuthFromResponder ConfdString,
        affirmedSecurityIkeStatsIkev2RecvDrop ConfdString,
        affirmedSecurityIkeStatsIkev2UpdateSaSuccess ConfdString,
        affirmedSecurityIkeStatsIkev2UpdateSaFail ConfdString,
        affirmedSecurityIkeStatsIkev2ReceiveAnonymousIdi ConfdString,
        affirmedSecurityIkeStatsIkev2ReceiveEapResponseIdentity ConfdString,
        affirmedSecurityIkeStatsIkev2UpdateRemoteIpPortSuccess ConfdString,
        affirmedSecurityIkeStatsIkev2UpdateRemoteIpPortFail ConfdString
    }

affirmedSecurityIkeStatsServiceName OBJECT-TYPE
    SYNTAX      String
    MAX-ACCESS  not-accessible
    STATUS      current
    DESCRIPTION "Task service name"
    ::= { affirmedSecurityIkeStatsEntry 1 }

affirmedSecurityIkeStatsTotalIkeSas OBJECT-TYPE
    SYNTAX      ConfdString
    MAX-ACCESS  read-only
    STATUS      current
    DESCRIPTION "total-ike-sas"
    ::= { affirmedSecurityIkeStatsEntry 2 }

affirmedSecurityIkeStatsTotalIkeSasInitiated OBJECT-TYPE
    SYNTAX      ConfdString
    MAX-ACCESS  read-only
    STATUS      current
    DESCRIPTION "total-ike-sas-initiated"
    ::= { affirmedSecurityIkeStatsEntry 3 }

affirmedSecurityIkeStatsTotalIkeSasResponded OBJECT-TYPE
    SYNTAX      ConfdString
    MAX-ACCESS  read-only
    STATUS      current
    DESCRIPTION "total-ike-sas-responded"
    ::= { affirmedSecurityIkeStatsEntry 4 }

affirmedSecurityIkeStatsTotalInitFailures OBJECT-TYPE
    SYNTAX      ConfdString
    MAX-ACCESS  read-only
    STATUS      current
    DESCRIPTION "total-init-failures"
    ::= { affirmedSecurityIkeStatsEntry 5 }

affirmedSecurityIkeStatsTotalInitNoResponse OBJECT-TYPE
    SYNTAX      ConfdString
    MAX-ACCESS  read-only
    STATUS      current
    DESCRIPTION "total-init-no-response"
    ::= { affirmedSecurityIkeStatsEntry 6 }

affirmedSecurityIkeStatsTotalRespFailures OBJECT-TYPE
    SYNTAX      ConfdString
    MAX-ACCESS  read-only
    STATUS      current
    DESCRIPTION "total-resp-failures"
    ::= { affirmedSecurityIkeStatsEntry 7 }

affirmedSecurityIkeStatsDeadPeerDetections OBJECT-TYPE
    SYNTAX      ConfdString
    MAX-ACCESS  read-only
    STATUS      current
    DESCRIPTION "dead-peer-detections"
    ::= { affirmedSecurityIkeStatsEntry 8 }

affirmedSecurityIkeStatsIkeInitReqIn OBJECT-TYPE
    SYNTAX      ConfdString
    MAX-ACCESS  read-only
    STATUS      current
    DESCRIPTION "ike-init-req-in"
    ::= { affirmedSecurityIkeStatsEntry 9 }

affirmedSecurityIkeStatsIkeInitRspIn OBJECT-TYPE
    SYNTAX      ConfdString
    MAX-ACCESS  read-only
    STATUS      current
    DESCRIPTION "ike-init-rsp-in"
    ::= { affirmedSecurityIkeStatsEntry 10 }

affirmedSecurityIkeStatsIkeAuthFromInitiator OBJECT-TYPE
    SYNTAX      ConfdString
    MAX-ACCESS  read-only
    STATUS      current
    DESCRIPTION "ike-auth-from-initiator"
    ::= { affirmedSecurityIkeStatsEntry 11 }

affirmedSecurityIkeStatsIkeAuthFromResponder OBJECT-TYPE
    SYNTAX      ConfdString
    MAX-ACCESS  read-only
    STATUS      current
    DESCRIPTION "ike-auth-from-responder"
    ::= { affirmedSecurityIkeStatsEntry 12 }

affirmedSecurityIkeStatsIkev2RecvDrop OBJECT-TYPE
    SYNTAX      ConfdString
    MAX-ACCESS  read-only
    STATUS      current
    DESCRIPTION "ikev2-recv-drop"
    ::= { affirmedSecurityIkeStatsEntry 13 }

affirmedSecurityIkeStatsIkev2UpdateSaSuccess OBJECT-TYPE
    SYNTAX      ConfdString
    MAX-ACCESS  read-only
    STATUS      current
    DESCRIPTION "ikev2-update-sa-success"
    ::= { affirmedSecurityIkeStatsEntry 14 }

affirmedSecurityIkeStatsIkev2UpdateSaFail OBJECT-TYPE
    SYNTAX      ConfdString
    MAX-ACCESS  read-only
    STATUS      current
    DESCRIPTION "ikev2-update-sa-fail"
    ::= { affirmedSecurityIkeStatsEntry 15 }

affirmedSecurityIkeStatsIkev2ReceiveAnonymousIdi OBJECT-TYPE
    SYNTAX      ConfdString
    MAX-ACCESS  read-only
    STATUS      current
    DESCRIPTION "The number of anonymous IDi received"
    ::= { affirmedSecurityIkeStatsEntry 16 }

affirmedSecurityIkeStatsIkev2ReceiveEapResponseIdentity OBJECT-TYPE
    SYNTAX      ConfdString
    MAX-ACCESS  read-only
    STATUS      current
    DESCRIPTION "The number of EAP Response/Identity received"
    ::= { affirmedSecurityIkeStatsEntry 17 }

affirmedSecurityIkeStatsIkev2UpdateRemoteIpPortSuccess OBJECT-TYPE
    SYNTAX      ConfdString
    MAX-ACCESS  read-only
    STATUS      current
    DESCRIPTION "ikev2 non-MOBIKE remote IP and Port update success"
    ::= { affirmedSecurityIkeStatsEntry 18 }

affirmedSecurityIkeStatsIkev2UpdateRemoteIpPortFail OBJECT-TYPE
    SYNTAX      ConfdString
    MAX-ACCESS  read-only
    STATUS      current
    DESCRIPTION "ikev2 non-MOBIKE remote IP and Port update failure"
    ::= { affirmedSecurityIkeStatsEntry 19 }

affirmedSecurityRedundancyStatsTable OBJECT-TYPE
    SYNTAX      SEQUENCE OF AffirmedSecurityRedundancyStatsEntry
    MAX-ACCESS  not-accessible
    STATUS      current
    DESCRIPTION ""
    ::= { affirmedSecurity 6 }

affirmedSecurityRedundancyStatsEntry OBJECT-TYPE
    SYNTAX      AffirmedSecurityRedundancyStatsEntry
    MAX-ACCESS  not-accessible
    STATUS      current
    DESCRIPTION ""
    INDEX { affirmedSecurityRedundancyStatsServiceName }
        ::= { affirmedSecurityRedundancyStatsTable 1 }

AffirmedSecurityRedundancyStatsEntry ::=
    SEQUENCE {
        affirmedSecurityRedundancyStatsServiceName String,
        affirmedSecurityRedundancyStatsIkeSaImportSuccess ConfdString,
        affirmedSecurityRedundancyStatsIkeSaImportFailure ConfdString,
        affirmedSecurityRedundancyStatsIPsecSaImportSuccess ConfdString,
        affirmedSecurityRedundancyStatsIPsecSaImportFailure ConfdString,
        affirmedSecurityRedundancyStatsFlowAuditDeletes ConfdString,
        affirmedSecurityRedundancyStatsTransformAuditDeletes ConfdString,
        affirmedSecurityRedundancyStatsIpsecSaUpdateOnIkeRekey ConfdString,
        affirmedSecurityRedundancyStatsIpsecSaUpdateOnIkeRekeyFail ConfdString
    }

affirmedSecurityRedundancyStatsServiceName OBJECT-TYPE
    SYNTAX      String
    MAX-ACCESS  not-accessible
    STATUS      current
    DESCRIPTION "Task service name"
    ::= { affirmedSecurityRedundancyStatsEntry 1 }

affirmedSecurityRedundancyStatsIkeSaImportSuccess OBJECT-TYPE
    SYNTAX      ConfdString
    MAX-ACCESS  read-only
    STATUS      current
    DESCRIPTION "IkeSaImportSuccess"
    ::= { affirmedSecurityRedundancyStatsEntry 2 }

affirmedSecurityRedundancyStatsIkeSaImportFailure OBJECT-TYPE
    SYNTAX      ConfdString
    MAX-ACCESS  read-only
    STATUS      current
    DESCRIPTION "IkeSaImportFailure"
    ::= { affirmedSecurityRedundancyStatsEntry 3 }

affirmedSecurityRedundancyStatsIPsecSaImportSuccess OBJECT-TYPE
    SYNTAX      ConfdString
    MAX-ACCESS  read-only
    STATUS      current
    DESCRIPTION "IPsecSaImportSuccess"
    ::= { affirmedSecurityRedundancyStatsEntry 4 }

affirmedSecurityRedundancyStatsIPsecSaImportFailure OBJECT-TYPE
    SYNTAX      ConfdString
    MAX-ACCESS  read-only
    STATUS      current
    DESCRIPTION "IPsecSaImportFailure"
    ::= { affirmedSecurityRedundancyStatsEntry 5 }

affirmedSecurityRedundancyStatsFlowAuditDeletes OBJECT-TYPE
    SYNTAX      ConfdString
    MAX-ACCESS  read-only
    STATUS      current
    DESCRIPTION "FlowAuditDeletes"
    ::= { affirmedSecurityRedundancyStatsEntry 6 }

affirmedSecurityRedundancyStatsTransformAuditDeletes OBJECT-TYPE
    SYNTAX      ConfdString
    MAX-ACCESS  read-only
    STATUS      current
    DESCRIPTION "TransformAuditDeletes"
    ::= { affirmedSecurityRedundancyStatsEntry 7 }

affirmedSecurityRedundancyStatsIpsecSaUpdateOnIkeRekey OBJECT-TYPE
    SYNTAX      ConfdString
    MAX-ACCESS  read-only
    STATUS      current
    DESCRIPTION "IpsecSaUpdateOnIkeRekey"
    ::= { affirmedSecurityRedundancyStatsEntry 8 }

affirmedSecurityRedundancyStatsIpsecSaUpdateOnIkeRekeyFail OBJECT-TYPE
    SYNTAX      ConfdString
    MAX-ACCESS  read-only
    STATUS      current
    DESCRIPTION "IpsecSaUpdateOnIkeRekeyFail"
    ::= { affirmedSecurityRedundancyStatsEntry 9 }

affirmedSecurityModexpStatsTable OBJECT-TYPE
    SYNTAX      SEQUENCE OF AffirmedSecurityModexpStatsEntry
    MAX-ACCESS  not-accessible
    STATUS      current
    DESCRIPTION ""
    ::= { affirmedSecurity 7 }

affirmedSecurityModexpStatsEntry OBJECT-TYPE
    SYNTAX      AffirmedSecurityModexpStatsEntry
    MAX-ACCESS  not-accessible
    STATUS      current
    DESCRIPTION ""
    INDEX { affirmedSecurityModexpStatsServiceName }
        ::= { affirmedSecurityModexpStatsTable 1 }

AffirmedSecurityModexpStatsEntry ::=
    SEQUENCE {
        affirmedSecurityModexpStatsServiceName String,
        affirmedSecurityModexpStatsSshDummyModexp ConfdString,
        affirmedSecurityModexpStatsModexpReqTimeout ConfdString,
        affirmedSecurityModexpStatsModexpCompletion ConfdString,
        affirmedSecurityModexpStatsModexpPerform ConfdString,
        affirmedSecurityModexpStatsModexpFinishSwAssist ConfdString,
        affirmedSecurityModexpStatsModexpAbort ConfdString,
        affirmedSecurityModexpStatsModexpThreadCb ConfdString
    }

affirmedSecurityModexpStatsServiceName OBJECT-TYPE
    SYNTAX      String
    MAX-ACCESS  not-accessible
    STATUS      current
    DESCRIPTION "Task service name"
    ::= { affirmedSecurityModexpStatsEntry 1 }

affirmedSecurityModexpStatsSshDummyModexp OBJECT-TYPE
    SYNTAX      ConfdString
    MAX-ACCESS  read-only
    STATUS      current
    DESCRIPTION "ssh_dummy_modexp"
    ::= { affirmedSecurityModexpStatsEntry 2 }

affirmedSecurityModexpStatsModexpReqTimeout OBJECT-TYPE
    SYNTAX      ConfdString
    MAX-ACCESS  read-only
    STATUS      current
    DESCRIPTION "modexp_req_timeout"
    ::= { affirmedSecurityModexpStatsEntry 3 }

affirmedSecurityModexpStatsModexpCompletion OBJECT-TYPE
    SYNTAX      ConfdString
    MAX-ACCESS  read-only
    STATUS      current
    DESCRIPTION "modexp_completion"
    ::= { affirmedSecurityModexpStatsEntry 4 }

affirmedSecurityModexpStatsModexpPerform OBJECT-TYPE
    SYNTAX      ConfdString
    MAX-ACCESS  read-only
    STATUS      current
    DESCRIPTION "modexp_perform"
    ::= { affirmedSecurityModexpStatsEntry 5 }

affirmedSecurityModexpStatsModexpFinishSwAssist OBJECT-TYPE
    SYNTAX      ConfdString
    MAX-ACCESS  read-only
    STATUS      current
    DESCRIPTION "modexp_finish_sw_assist"
    ::= { affirmedSecurityModexpStatsEntry 6 }

affirmedSecurityModexpStatsModexpAbort OBJECT-TYPE
    SYNTAX      ConfdString
    MAX-ACCESS  read-only
    STATUS      current
    DESCRIPTION "modexp_abort"
    ::= { affirmedSecurityModexpStatsEntry 7 }

affirmedSecurityModexpStatsModexpThreadCb OBJECT-TYPE
    SYNTAX      ConfdString
    MAX-ACCESS  read-only
    STATUS      current
    DESCRIPTION "modexp_thread_cb"
    ::= { affirmedSecurityModexpStatsEntry 8 }

END
